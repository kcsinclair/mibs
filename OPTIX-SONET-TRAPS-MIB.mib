--
-- OPTIX-SONET-TRAPS-MIB.mib
-- MIB generated by MG-SOFT Visual MIB Builder Version 3.0 Build 253
-- Monday, March 06, 2006 at 10:09:53
--

-- =================================================================
-- Copyright (C) 2006 by HUAWEI TECHNOLOGIES. All rights reserved
-- 
-- Description:This MIB describes the TRAP interface of Huawei SONET transmit
-- Reference:
-- Version: V1.10
-- History:
-- 1. <gongzhenyu>,<2006-04-15>,<modify traps name, to avoid hyphen character.>
-- 2. <yuanxiaoshu>,<2006-05-10>,<insert event traps into alarm traps,and insert alarm traps into event traps,
--    to make traps recognizable when alarm attribute changed.>
-- =================================================================

    OPTIX-SONET-TRAPS-MIB DEFINITIONS ::= BEGIN
 
        IMPORTS
            optixCommonSonet            
                FROM OPTIX-OID-MIB            
            MOD2Type, AlmDataNtfcnCdeType, AlarmEventType, AlmDataSrvEffType, LocationType, 
            DirectionType, ValidflagType, PerformanceEventType            
                FROM OPTIX-SONET-TC-MIB            
            OBJECT-GROUP, MODULE-COMPLIANCE, NOTIFICATION-GROUP            
                FROM SNMPv2-CONF            
            Integer32, Unsigned32, OBJECT-TYPE, MODULE-IDENTITY, NOTIFICATION-TYPE            
                FROM SNMPv2-SMI            
            DateAndTime, DisplayString            
                FROM SNMPv2-TC;
    
    
--  -------------------------------------------------------------------------
-- Module Identity
-- -------------------------------------------------------------------------
        optixSonetTraps MODULE-IDENTITY 
            LAST-UPDATED "200602250000Z"
            ORGANIZATION 
                "Huawei Technologies co.,Ltd."
            CONTACT-INFO 
                "R&D Building
                Huawei Technologies Co., Ltd.
                Bantian, Longgang District 
                Shenzhen, P. R. China
                http://www.huawei.com
                Zip:518129
                E-mail:support@huawei.com"
            DESCRIPTION 
                "This module describes the Alarm,Performance and Event interface of Huawei SONET transmit platform"
            REVISION "200602250000Z"
            DESCRIPTION
                "The initial revision of this MIB module."
            ::= { optixCommonSonet 40 }
        
    
    
--
-- Node definitions
--

-- *************************************************************************
--  Events                                                                                       
-- -------------------------------------------------------------------------
--  REPT^ALM
-- -------------------------------------------------------------------------
-- AAAAAAAAAAAAAAAAAAAAAAAAAAAAAAAAAAAAAAAAAAAAAAAAAAAAAAAAAAAAAAAAAAAAAAAAAAAA
-- Alarm trap definition begin.
-- AAAAAAAAAAAAAAAAAAAAAAAAAAAAAAAAAAAAAAAAAAAAAAAAAAAAAAAAAAAAAAAAAAAAAAAAAAAA
    
        -- 1.3.6.1.4.1.2011.2.25.3.20.40.10
        optixTrapsAlarm OBJECT IDENTIFIER ::= { optixSonetTraps 10 }
        
--  1.3.6.1.4.1.2011.2.25.3.20.40.10.3
        almLossOfClock NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Loss of clock."
            ::= { optixTrapsAlarm 3 }
        
--  1.3.6.1.4.1.2011.2.25.3.20.40.10.6
        almFileLost NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SOFTWARE FILE CORRUPTED OR MISSING."
            ::= { optixTrapsAlarm 6 }
        
--  1.3.6.1.4.1.2011.2.25.3.20.40.10.37
        almREILine NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Remote error indication - Line section."
            ::= { optixTrapsAlarm 37 }
        
--  1.3.6.1.4.1.2011.2.25.3.20.40.10.69
        almBiasTemperatureOfPumpHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Bias temperature of the pump laser over threshold."
            ::= { optixTrapsAlarm 69 }
        
--  1.3.6.1.4.1.2011.2.25.3.20.40.10.87
        almTimSection NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Section trace identifier mismatch."
            ::= { optixTrapsAlarm 87 }
        
--  1.3.6.1.4.1.2011.2.25.3.20.40.10.100
        almLossOfAllSynchronousSource NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Loss of all synchronous source."
            ::= { optixTrapsAlarm 100 }
        
--  1.3.6.1.4.1.2011.2.25.3.20.40.10.101
        almSynchronousSourceDegrade NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Synchronous source degrade."
            ::= { optixTrapsAlarm 101 }
        
--  1.3.6.1.4.1.2011.2.25.3.20.40.10.111
        almSyncLOS NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Loss of high synchronous source."
            ::= { optixTrapsAlarm 111 }
        
--  1.3.6.1.4.1.2011.2.25.3.20.40.10.120
        almProtectionSwitching NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: (PS)Protection switching happened indication."
            ::= { optixTrapsAlarm 120 }
        
--  1.3.6.1.4.1.2011.2.25.3.20.40.10.185
        almDbmsError NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: DATABASE ERROR."
            ::= { optixTrapsAlarm 185 }
        
--  1.3.6.1.4.1.2011.2.25.3.20.40.10.186
        almLossOfMultiplexSignal NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Loss of multiplex signal."
            ::= { optixTrapsAlarm 186 }
        
--  1.3.6.1.4.1.2011.2.25.3.20.40.10.187
        almLossOfSingleWavelengthSignal NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Loss of single-wavelength signal."
            ::= { optixTrapsAlarm 187 }
        
--  1.3.6.1.4.1.2011.2.25.3.20.40.10.188
        almAdditionOfSingleWavelengthSignal NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: (CHAN_ADD)Addition of single-wavelength signal."
            ::= { optixTrapsAlarm 188 }
        
--  1.3.6.1.4.1.2011.2.25.3.20.40.10.189
        almLaserDegraded NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: (TD)Laser degraded."
            ::= { optixTrapsAlarm 189 }
        
--  1.3.6.1.4.1.2011.2.25.3.20.40.10.192
        almPumpDiodeCoolingCurrentHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Pump diode cooling current exceeded standard level."
            ::= { optixTrapsAlarm 192 }
        
--  1.3.6.1.4.1.2011.2.25.3.20.40.10.193
        almS1ModeSynChange NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: (S1_SYN_CHANGE)Clock reference Source Change In S1_Mode."
            ::= { optixTrapsAlarm 193 }
        
--  1.3.6.1.4.1.2011.2.25.3.20.40.10.198
        almDbmsIsInProtectMode NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: DATABASE IS IN PROTECT MODE."
            ::= { optixTrapsAlarm 198 }
        
--  1.3.6.1.4.1.2011.2.25.3.20.40.10.200
        almSecuAlarm NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOGIN ILLEGAL."
            ::= { optixTrapsAlarm 200 }
        
--  1.3.6.1.4.1.2011.2.25.3.20.40.10.212
        almForwardErrorCorrectionLossOfFrame NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Forward Error Correction Loss of Frame."
            ::= { optixTrapsAlarm 212 }
        
--  1.3.6.1.4.1.2011.2.25.3.20.40.10.213
        almForwardErrorCorrectionOutOfFrame NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Forward Error Correction Out of Frame."
            ::= { optixTrapsAlarm 213 }
        
--  1.3.6.1.4.1.2011.2.25.3.20.40.10.223
        almRateOver NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: the rate over the threshold."
            ::= { optixTrapsAlarm 223 }
        
--  1.3.6.1.4.1.2011.2.25.3.20.40.10.232
        almCardConfigurationFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: This card does not support the configuration save.."
            ::= { optixTrapsAlarm 232 }
        
--  1.3.6.1.4.1.2011.2.25.3.20.40.10.240
        almLoopback NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Port in loopback operation."
            ::= { optixTrapsAlarm 240 }
        
--  1.3.6.1.4.1.2011.2.25.3.20.40.10.270
        almCoolingCurrentModeHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Alarm of module cooling current threshold crossing."
            ::= { optixTrapsAlarm 270 }
        
--  1.3.6.1.4.1.2011.2.25.3.20.40.10.272
        almOTULossOfFrame NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OTU layer Loss of Frame Alignment."
            ::= { optixTrapsAlarm 272 }
        
--  1.3.6.1.4.1.2011.2.25.3.20.40.10.273
        almOTUOutOfMultiFrame NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OTU layer Out of MultiFrame."
            ::= { optixTrapsAlarm 273 }
        
--  1.3.6.1.4.1.2011.2.25.3.20.40.10.274
        almSmTIM NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OTU layer SM TTI Mismatch."
            ::= { optixTrapsAlarm 274 }
        
--  1.3.6.1.4.1.2011.2.25.3.20.40.10.275
        almPmTIM NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ODU layer PM TTI Mismatch."
            ::= { optixTrapsAlarm 275 }
        
--  1.3.6.1.4.1.2011.2.25.3.20.40.10.276
        almSmBDI NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OTU layer SM BDI -Backward Defect Indication."
            ::= { optixTrapsAlarm 276 }
        
--  1.3.6.1.4.1.2011.2.25.3.20.40.10.277
        almPmBDI NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ODU layer PM BDI-Backward Defect Indication."
            ::= { optixTrapsAlarm 277 }
        
--  1.3.6.1.4.1.2011.2.25.3.20.40.10.278
        almSmBEI NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OTU layer SM BEI-Backward Error Indication."
            ::= { optixTrapsAlarm 278 }
        
--  1.3.6.1.4.1.2011.2.25.3.20.40.10.279
        almPmBEI NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ODU layer PM BEI-Backward Error Indication."
            ::= { optixTrapsAlarm 279 }
        
--  1.3.6.1.4.1.2011.2.25.3.20.40.10.280
        almSmIAE NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OTU layer SM IAE-Incoming Alignment Error."
            ::= { optixTrapsAlarm 280 }
        
--  1.3.6.1.4.1.2011.2.25.3.20.40.10.282
        almSmBipExcessive NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OTU layer SM BIP-8 Excessive error defect."
            ::= { optixTrapsAlarm 282 }
        
--  1.3.6.1.4.1.2011.2.25.3.20.40.10.283
        almPmBipExcessive NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ODU layer PM BIP-8 Excessive error defect."
            ::= { optixTrapsAlarm 283 }
        
--  1.3.6.1.4.1.2011.2.25.3.20.40.10.284
        almSmBipSignalDefect NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OTU layer SM BIP-8 Degraded signal defect."
            ::= { optixTrapsAlarm 284 }
        
--  1.3.6.1.4.1.2011.2.25.3.20.40.10.285
        almPmBipSignalDefect NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ODU layer PM BIP-8 Degraded signal defect."
            ::= { optixTrapsAlarm 285 }
        
--  1.3.6.1.4.1.2011.2.25.3.20.40.10.286
        almOTUAlarmIndicationSignal NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OTU layer AIS-Alarm Indication Signal."
            ::= { optixTrapsAlarm 286 }
        
--  1.3.6.1.4.1.2011.2.25.3.20.40.10.287
        almODUAlarmIndicationSignal NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ODU layer AIS-Alarm Indication Signal."
            ::= { optixTrapsAlarm 287 }
        
--  1.3.6.1.4.1.2011.2.25.3.20.40.10.288
        almODUOpenConnectionIndicationSignal NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ODU layer OCI-Open Connection Indication Signal."
            ::= { optixTrapsAlarm 288 }
        
--  1.3.6.1.4.1.2011.2.25.3.20.40.10.289
        almODULockedIndicationSignal NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ODU layer LCK-Locked Indication Signal."
            ::= { optixTrapsAlarm 289 }
        
--  1.3.6.1.4.1.2011.2.25.3.20.40.10.323
        almSumInputOpticalPowerHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Composite input optical power too high."
            ::= { optixTrapsAlarm 323 }
        
--  1.3.6.1.4.1.2011.2.25.3.20.40.10.324
        almSumInputOpticalPowerLow NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Composite input optical power too low."
            ::= { optixTrapsAlarm 324 }
        
--  1.3.6.1.4.1.2011.2.25.3.20.40.10.325
        almSumOutOpticalPowerHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Composite output optical power too high."
            ::= { optixTrapsAlarm 325 }
        
--  1.3.6.1.4.1.2011.2.25.3.20.40.10.326
        almOutOpticalPowerLow NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Composite output optical power too low."
            ::= { optixTrapsAlarm 326 }
        
--  1.3.6.1.4.1.2011.2.25.3.20.40.10.327
        almGainLow NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Alarm of OA gain is lower than standard level."
            ::= { optixTrapsAlarm 327 }
        
--  1.3.6.1.4.1.2011.2.25.3.20.40.10.335
        almExcessiveErrorDefectBeforeFEC NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Excessive Error defect before FEC."
            ::= { optixTrapsAlarm 335 }
        
--  1.3.6.1.4.1.2011.2.25.3.20.40.10.433
        almDgeAdjustmentFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: DGE adjustment fail alarm."
            ::= { optixTrapsAlarm 433 }
        
--  1.3.6.1.4.1.2011.2.25.3.20.40.10.439
        almWavelengthLockFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Wavelength locking failure alarm."
            ::= { optixTrapsAlarm 439 }
        
--  1.3.6.1.4.1.2011.2.25.3.20.40.10.440
        almHotSwitchControlUnavail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: HOT SWITCH CONTROL UNAVAILABLE."
            ::= { optixTrapsAlarm 440 }
        
--  1.3.6.1.4.1.2011.2.25.3.20.40.10.570
        almEsconCodeError NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ESCON Code Error.."
            ::= { optixTrapsAlarm 570 }
        
--  1.3.6.1.4.1.2011.2.25.3.20.40.10.573
        almCommitTimeout NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SOFTWARE PACKAGE NOT COMMIT IN TIME."
            ::= { optixTrapsAlarm 573 }
        
--  1.3.6.1.4.1.2011.2.25.3.20.40.10.574
        almSwdlNePackageCheck NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SWDL NE SOFTWARE PACKAGE CHECK, FILE CORRUPTED OR MISSING."
            ::= { optixTrapsAlarm 574 }
        
--  1.3.6.1.4.1.2011.2.25.3.20.40.10.575
        almSwdlChaGmngmMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SWDL SCC CHANGED AND SWPKG IS NOT THE OLD ONE."
            ::= { optixTrapsAlarm 575 }
        
--  1.3.6.1.4.1.2011.2.25.3.20.40.10.591
        almDBSyncFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: DATABASE SYNCHRONIZATION FAILED."
            ::= { optixTrapsAlarm 591 }
        
--  1.3.6.1.4.1.2011.2.25.3.20.40.10.604
        almClientMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Client signal type mismatch."
            ::= { optixTrapsAlarm 604 }
        
--  1.3.6.1.4.1.2011.2.25.3.20.40.10.606
        almLaserModuleMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Laser module is mismatch."
            ::= { optixTrapsAlarm 606 }

--  1.3.6.1.4.1.2011.2.25.3.20.40.10.12288
        almDlagProtFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: DLAG PROTECTION FAILED."
            ::= { optixTrapsAlarm 12288 }

--  1.3.6.1.4.1.2011.2.25.3.20.40.10.12291
        almOamRemoteLoop NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: REMOTE ETHERNET SIGNAL LOOP DETECTED BY P2P OAM."
            ::= { optixTrapsAlarm 12291 }

--  1.3.6.1.4.1.2011.2.25.3.20.40.10.12292
        almOamRemoteSD NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: REMOTE ETHERNET SIGNAL DEGRADE DETECTED BY P2P OAM."
            ::= { optixTrapsAlarm 12292 }

--  1.3.6.1.4.1.2011.2.25.3.20.40.10.12293
        almOamRemoteSF NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: REMOTE ETHERNET SIGNAL FAILURE DETECTED BY P2P OAM."
            ::= { optixTrapsAlarm 12293 }

--  1.3.6.1.4.1.2011.2.25.3.20.40.10.12294
        almOamFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: P2P ETHERNET OAM FUNCTION FAIL."
            ::= { optixTrapsAlarm 12294 }

--  1.3.6.1.4.1.2011.2.25.3.20.40.10.12298
        almCcLoss NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: CONTINUITY CHECK MESSAGE LOSS."
            ::= { optixTrapsAlarm 12298 }

--  1.3.6.1.4.1.2011.2.25.3.20.40.10.12299
        almMpConflict NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: MAINTENANCE IDENTITY CONFLICT."
            ::= { optixTrapsAlarm 12299 }


--  1.3.6.1.4.1.2011.2.25.3.20.40.10.12300
        almLptRfi NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LINK PATH STATE THROUGH REMOTE FAIL INDICATION."
            ::= { optixTrapsAlarm 12300 }

--  1.3.6.1.4.1.2011.2.25.3.20.40.10.12767
        almOamSelfLoop NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ETHERNET SELF-LOOP DETECTED BY P2P OAM."
            ::= { optixTrapsAlarm 12767 }

--  1.3.6.1.4.1.2011.2.25.3.20.40.10.12769
        almLagPortFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LINK AGGREGATION FAILED."
            ::= { optixTrapsAlarm 12769 }

--  1.3.6.1.4.1.2011.2.25.3.20.40.10.12823
        almEthCfmMismerge NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: MISCONNECTION ALARM."
            ::= { optixTrapsAlarm 12823 }

--  1.3.6.1.4.1.2011.2.25.3.20.40.10.12824
        almEthCfmUnexperi NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ERRORED FRAME ALARM."
            ::= { optixTrapsAlarm 12824 }

--  1.3.6.1.4.1.2011.2.25.3.20.40.10.12825
        almEthCfmLoc NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOSS OF CONTINUITY."
            ::= { optixTrapsAlarm 12825 }

--  1.3.6.1.4.1.2011.2.25.3.20.40.10.12826
        almEthCfmRdi NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: REMOTE DEFECT INDICATION."
            ::= { optixTrapsAlarm 12826 }
        
--  1.3.6.1.4.1.2011.2.25.3.20.40.10.32768
        almEqptNoServiceAffecting NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: NON-SERVICE-AFFECTING EQUIPMENT FAILURE."
            ::= { optixTrapsAlarm 32768 }
        
--  1.3.6.1.4.1.2011.2.25.3.20.40.10.32769
        almEqptServiceAffectingFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SERVICE-AFFECTING EQUIPMENT FAILURE."
            ::= { optixTrapsAlarm 32769 }
        
--  1.3.6.1.4.1.2011.2.25.3.20.40.10.32774
        almApsByteFailure NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PROTECTION SWITCHING BYTE FAILURE."
            ::= { optixTrapsAlarm 32774 }
        
--  1.3.6.1.4.1.2011.2.25.3.20.40.10.32776
        almFarEndProtectionLineFailure NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FAR END PROTECTION LINE FAILURE."
            ::= { optixTrapsAlarm 32776 }
        
--  1.3.6.1.4.1.2011.2.25.3.20.40.10.32777
        almApsChannelMismatchFailure NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PROTECTION SWITCHING CHANNEL MISMATCH FAILURE."
            ::= { optixTrapsAlarm 32777 }
        
--  1.3.6.1.4.1.2011.2.25.3.20.40.10.32778
        almApsModeMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: AUTOMATIC PROTECTION SWITCH MODE MISMATCH."
            ::= { optixTrapsAlarm 32778 }
        
--  1.3.6.1.4.1.2011.2.25.3.20.40.10.32779
        almApsTypeMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: AUTOMATIC PROTECTION SWITCH TYPE MISMATCH."
            ::= { optixTrapsAlarm 32779 }
        
--  1.3.6.1.4.1.2011.2.25.3.20.40.10.32791
        almHoldoverSync NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: HOLDOVER SYNCHRONIZATION MODE."
            ::= { optixTrapsAlarm 32791 }
        
--  1.3.6.1.4.1.2011.2.25.3.20.40.10.32792
        almFreeRunSync NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: IN FREE RUN SYNCHRONIZATION MODE."
            ::= { optixTrapsAlarm 32792 }
        
--  1.3.6.1.4.1.2011.2.25.3.20.40.10.32794
        almFastStartSync NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FAST START SYNCHRONIZATION MODE."
            ::= { optixTrapsAlarm 32794 }
        
--  1.3.6.1.4.1.2011.2.25.3.20.40.10.32798
        almManualSetSSM NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: MANUAL SET A REFERENCE'S SSM."
            ::= { optixTrapsAlarm 32798 }
        
--  1.3.6.1.4.1.2011.2.25.3.20.40.10.32802
        almFanOffline NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FAN OFFLINE."
            ::= { optixTrapsAlarm 32802 }
        
--  1.3.6.1.4.1.2011.2.25.3.20.40.10.32803
        almSingleFanFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SINGLE-FAN UNIT FAILED."
            ::= { optixTrapsAlarm 32803 }
        
--  1.3.6.1.4.1.2011.2.25.3.20.40.10.32804
        almMultiFanFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: MULTI-FAN UNIT FAILED."
            ::= { optixTrapsAlarm 32804 }
        
--  1.3.6.1.4.1.2011.2.25.3.20.40.10.32807
        almEquipmentTypeMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: EQUIPMENT TYPE MISMATCH."
            ::= { optixTrapsAlarm 32807 }
        
--  1.3.6.1.4.1.2011.2.25.3.20.40.10.32808
        almEquipmentOfflineOrUninstalled NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: EQUIPMENT  OFFLINE OR UNINSTALLED."
            ::= { optixTrapsAlarm 32808 }
        
--  1.3.6.1.4.1.2011.2.25.3.20.40.10.32814
        almTransmitterFailure NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TRANSMITTER FAILURE."
            ::= { optixTrapsAlarm 32814 }
        
--  1.3.6.1.4.1.2011.2.25.3.20.40.10.32815
        almSignalFailureSection NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SIGNAL FAILURE-SECTION."
            ::= { optixTrapsAlarm 32815 }
        
--  1.3.6.1.4.1.2011.2.25.3.20.40.10.32816
        almInputPowerHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: INPUT POWER EXCEEDS STANDARD LEVEL."
            ::= { optixTrapsAlarm 32816 }
        
--  1.3.6.1.4.1.2011.2.25.3.20.40.10.32817
        almInputPowerLow NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: INPUT POWER IS LOWER THAN STANDARD LEVEL."
            ::= { optixTrapsAlarm 32817 }
        
--  1.3.6.1.4.1.2011.2.25.3.20.40.10.32818
        almSignalFailureLine NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SIGNAL FAILURE-LINE."
            ::= { optixTrapsAlarm 32818 }
        
--  1.3.6.1.4.1.2011.2.25.3.20.40.10.32819
        almSignalDegradeLine NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SIGNAL DEGRADE-LINE."
            ::= { optixTrapsAlarm 32819 }
        
--  1.3.6.1.4.1.2011.2.25.3.20.40.10.32820
        almLaserApprochingEndOfLife NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER APPROACHING END OF LIFE."
            ::= { optixTrapsAlarm 32820 }
        
--  1.3.6.1.4.1.2011.2.25.3.20.40.10.32821
        almOutPowerHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OUTPUT POWER EXCEEDS STANDARD LEVEL."
            ::= { optixTrapsAlarm 32821 }
        
--  1.3.6.1.4.1.2011.2.25.3.20.40.10.32822
        almOutPowerLow NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OUTPUT POWER IS LOWER THAN STANDARD LEVEL."
            ::= { optixTrapsAlarm 32822 }
        
--  1.3.6.1.4.1.2011.2.25.3.20.40.10.32823
        almSignalDegradeSection NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SIGNAL DEGRADE-SECTION."
            ::= { optixTrapsAlarm 32823 }
        
--  1.3.6.1.4.1.2011.2.25.3.20.40.10.32824
        almAlarmIndicationSignalLine NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SONET AIS - LINE."
            ::= { optixTrapsAlarm 32824 }
        
--  1.3.6.1.4.1.2011.2.25.3.20.40.10.32825
        almRemoteFailureIindicationLine NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: REMOTE FAILURE INDICATION-LINE."
            ::= { optixTrapsAlarm 32825 }
        
--  1.3.6.1.4.1.2011.2.25.3.20.40.10.32826
        almAlarmIndicationSignalPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SONET AIS - PATH."
            ::= { optixTrapsAlarm 32826 }
        
--  1.3.6.1.4.1.2011.2.25.3.20.40.10.32827
        almLossOfPointerPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SONET LOSS OF POINTER STS-PATH."
            ::= { optixTrapsAlarm 32827 }
        
--  1.3.6.1.4.1.2011.2.25.3.20.40.10.32828
        almTraceIdentifierMismatchPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SONET TRACE IDENTIFIER MISMATCH STS-PATH."
            ::= { optixTrapsAlarm 32828 }
        
--  1.3.6.1.4.1.2011.2.25.3.20.40.10.32829
        almUnequippedPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: UNEQUIPPED - STS."
            ::= { optixTrapsAlarm 32829 }
        
--  1.3.6.1.4.1.2011.2.25.3.20.40.10.32830
        almSignalFailurePath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SIGNAL FAILURE STS-PATH."
            ::= { optixTrapsAlarm 32830 }
        
--  1.3.6.1.4.1.2011.2.25.3.20.40.10.32831
        almSignalDegradePath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SIGNAL DEGRADE STS-PATH."
            ::= { optixTrapsAlarm 32831 }
        
--  1.3.6.1.4.1.2011.2.25.3.20.40.10.32832
        almRemoteFailureIindicationPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SONET REMOTE FAILURE INDICATION-STS PATH."
            ::= { optixTrapsAlarm 32832 }
        
--  1.3.6.1.4.1.2011.2.25.3.20.40.10.32833
        almALS NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SHUTDOWN THE  LASER AUTOMATICALLY ON DETECTING LOS."
            ::= { optixTrapsAlarm 32833 }
        
--  1.3.6.1.4.1.2011.2.25.3.20.40.10.32834
        almLoopbackFacility NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOOPBACK,FACILITY."
            ::= { optixTrapsAlarm 32834 }
        
--  1.3.6.1.4.1.2011.2.25.3.20.40.10.32835
        almLoopbackTerminal NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOOPBACK, TERMINAL."
            ::= { optixTrapsAlarm 32835 }
        
--  1.3.6.1.4.1.2011.2.25.3.20.40.10.32836
        almPayloadLabelMisatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PAYLOAD LABEL MISMATCH-STS."
            ::= { optixTrapsAlarm 32836 }
        
--  1.3.6.1.4.1.2011.2.25.3.20.40.10.32837
        almEnhancedRemotePalyloadFailureIndicationPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ENHANCED REMOTE PAYLOAD FAILURE INDICATION - STS PATH."
            ::= { optixTrapsAlarm 32837 }
        
--  1.3.6.1.4.1.2011.2.25.3.20.40.10.32838
        almEnhancedRemoteServerFailureIndicationPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ENHANCED REMOTE SERVER FAILURE INDICATION - STS PATH."
            ::= { optixTrapsAlarm 32838 }
        
--  1.3.6.1.4.1.2011.2.25.3.20.40.10.32839
        almEnhancedRemoteConnectivityFailureIndicationPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ENHANCED REMOTE CONNECTIVITY FAILURE INDICATION - STS PATH."
            ::= { optixTrapsAlarm 32839 }
        
--  1.3.6.1.4.1.2011.2.25.3.20.40.10.32840
        almPDIPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PAYLOAD DEFECT INDICATION-STS."
            ::= { optixTrapsAlarm 32840 }
        
--  1.3.6.1.4.1.2011.2.25.3.20.40.10.32841
        almPowerFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: POWER SUPPLY FAILURE."
            ::= { optixTrapsAlarm 32841 }
        
--  1.3.6.1.4.1.2011.2.25.3.20.40.10.32842
        almLossOfPointerVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOSS OF VT POINTER."
            ::= { optixTrapsAlarm 32842 }
        
--  1.3.6.1.4.1.2011.2.25.3.20.40.10.32843
        almAlarmIndicationSignalVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: VT PATH ALARM INDICATION SIGNAL."
            ::= { optixTrapsAlarm 32843 }
        
--  1.3.6.1.4.1.2011.2.25.3.20.40.10.32844
        almPayloadLabelMismatchVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: VT PATH PAYLOAD LABEL MISMATCH."
            ::= { optixTrapsAlarm 32844 }
        
--  1.3.6.1.4.1.2011.2.25.3.20.40.10.32845
        almUnequippedVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: VT PATH UNEQUIPPED."
            ::= { optixTrapsAlarm 32845 }
        
--  1.3.6.1.4.1.2011.2.25.3.20.40.10.32846
        almRemoteFailureIndicationVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: VT PATH REMOTE FAILURE INDICATION."
            ::= { optixTrapsAlarm 32846 }
        
--  1.3.6.1.4.1.2011.2.25.3.20.40.10.32847
        almRemoteServerFailureIndicationVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: VT PATH REMOTE SERVER FAILURE INDICATION."
            ::= { optixTrapsAlarm 32847 }
        
--  1.3.6.1.4.1.2011.2.25.3.20.40.10.32848
        almEnhancedRemoteConnectivityFailureIndicationVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: VT PATH REMOTE CONNECTIVITY FAILURE INDICATION."
            ::= { optixTrapsAlarm 32848 }
        
--  1.3.6.1.4.1.2011.2.25.3.20.40.10.32849
        almEnhancedRemotePalyloadFailureIndicationVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: VT PATH REMOTE PAYLOAD FAILURE INDICATION."
            ::= { optixTrapsAlarm 32849 }
        
--  1.3.6.1.4.1.2011.2.25.3.20.40.10.32876
        almInterFaceCardOffline NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: INTERFACE CARD OFFLINE."
            ::= { optixTrapsAlarm 32876 }
        
--  1.3.6.1.4.1.2011.2.25.3.20.40.10.32877
        almSyncChangeSSM NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: RECEIVE SSM OF REFERENCE SOURCE HAS CHANGED."
            ::= { optixTrapsAlarm 32877 }
        
--  1.3.6.1.4.1.2011.2.25.3.20.40.10.32878
        almTimeingModeChange NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TIMEING SOURCE MODE CHANGE."
            ::= { optixTrapsAlarm 32878 }
        
--  1.3.6.1.4.1.2011.2.25.3.20.40.10.32879
        almLockoutWorkingUnit NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOCKOUT WORKING UNIT."
            ::= { optixTrapsAlarm 32879 }
        
--  1.3.6.1.4.1.2011.2.25.3.20.40.10.32880
        almLockoutProtectionUnit NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOCKOUT PROTECTION UNIT."
            ::= { optixTrapsAlarm 32880 }
        
--  1.3.6.1.4.1.2011.2.25.3.20.40.10.32881
        almForcedSwitch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FORCED SWITCH."
            ::= { optixTrapsAlarm 32881 }
        
--  1.3.6.1.4.1.2011.2.25.3.20.40.10.32882
        almManualSwitch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: MANUAL SWITCH."
            ::= { optixTrapsAlarm 32882 }
        
--  1.3.6.1.4.1.2011.2.25.3.20.40.10.32883
        almExerciseSwitch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: EXERCISE SWITCH."
            ::= { optixTrapsAlarm 32883 }
        
--  1.3.6.1.4.1.2011.2.25.3.20.40.10.32884
        almWaitToRestore NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: WAIT TO RESTORE."
            ::= { optixTrapsAlarm 32884 }
        
--  1.3.6.1.4.1.2011.2.25.3.20.40.10.32886
        almSwitchToIdle NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SWITCH TO IDLE."
            ::= { optixTrapsAlarm 32886 }
        
--  1.3.6.1.4.1.2011.2.25.3.20.40.10.32887
        almSwitchFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SWITCH FAIL EVENT."
            ::= { optixTrapsAlarm 32887 }
        
--  1.3.6.1.4.1.2011.2.25.3.20.40.10.32889
        almSyncSwitch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SWITCH EVENT."
            ::= { optixTrapsAlarm 32889 }
        
--  1.3.6.1.4.1.2011.2.25.3.20.40.10.32890
        almCommunicationFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: COMMUNICATION FAIL."
            ::= { optixTrapsAlarm 32890 }
        
--  1.3.6.1.4.1.2011.2.25.3.20.40.10.32891
        almPowerAFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FAILURES FOR THE  POWER SUPPLY."
            ::= { optixTrapsAlarm 32891 }
        
--  1.3.6.1.4.1.2011.2.25.3.20.40.10.32892
        almPowerBFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FAILURES FOR THE  POWER SUPPLY."
            ::= { optixTrapsAlarm 32892 }
        
--  1.3.6.1.4.1.2011.2.25.3.20.40.10.32899
        almInterfaceLinkMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: INTERFACE LINK MISMATCH."
            ::= { optixTrapsAlarm 32899 }
        
--  1.3.6.1.4.1.2011.2.25.3.20.40.10.32900
        almInterfaceCardFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: INTERFACE CARD FAIL."
            ::= { optixTrapsAlarm 32900 }
        
--  1.3.6.1.4.1.2011.2.25.3.20.40.10.32901
        almAIC NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PATH MISMATCH OF FRAMING APPLICATION."
            ::= { optixTrapsAlarm 32901 }
        
--  1.3.6.1.4.1.2011.2.25.3.20.40.10.32903
        almDbmsCfgCorrupted NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: CONFIGURATION DATABASE CORRUPTED."
            ::= { optixTrapsAlarm 32903 }
        
--  1.3.6.1.4.1.2011.2.25.3.20.40.10.32904
        almDefaultKByteDefect NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: DEFAULT K BYTE DEFECT."
            ::= { optixTrapsAlarm 32904 }
        
--  1.3.6.1.4.1.2011.2.25.3.20.40.10.32905
        almInconsistentApsCodes NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: INCONSISTENT APS CODES."
            ::= { optixTrapsAlarm 32905 }
        
--  1.3.6.1.4.1.2011.2.25.3.20.40.10.32906
        almImproperApsCodes NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: IMPROPER APS CODES."
            ::= { optixTrapsAlarm 32906 }
        
--  1.3.6.1.4.1.2011.2.25.3.20.40.10.32907
        almExtraTrafficIsBeingSquelched NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: EXTRA TRAFFIC IS BEING SQUELCHED."
            ::= { optixTrapsAlarm 32907 }
        
--  1.3.6.1.4.1.2011.2.25.3.20.40.10.32908
        almTopologyNeedsUpdatingOrIsInvalid NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TOPOLOGY NEEDS UPDATING OR IS INVALID."
            ::= { optixTrapsAlarm 32908 }
        
--  1.3.6.1.4.1.2011.2.25.3.20.40.10.32909
        almSquelchTableNeedsUpdatingOrIsInvalid NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SQUELCH TABLE NEEDS UPDATING OR IS INVALID."
            ::= { optixTrapsAlarm 32909 }
        
--  1.3.6.1.4.1.2011.2.25.3.20.40.10.32910
        almNodeIdDuplicatedOrMismatched NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: NODE ID DUPLICATED OR MISMATCHED."
            ::= { optixTrapsAlarm 32910 }
        
--  1.3.6.1.4.1.2011.2.25.3.20.40.10.32911
        almXconMismatched NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: CROSS-CONNECTION TYPE IS MISMATCHED WITH ADJACENT NODE."
            ::= { optixTrapsAlarm 32911 }
        
--  1.3.6.1.4.1.2011.2.25.3.20.40.10.32912
        almRingModeMisatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: RING MODE MISMATCHED. SOME NODES IN AUTO AND SOME IN MANUAL."
            ::= { optixTrapsAlarm 32912 }
        
--  1.3.6.1.4.1.2011.2.25.3.20.40.10.32913
        almSquelchModeMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SQUELCH MODE MISMATCHED. SOME NODES IN AUTO AND SOME IN MANUAL."
            ::= { optixTrapsAlarm 32913 }
        
--  1.3.6.1.4.1.2011.2.25.3.20.40.10.32915
        almLockoutProtectionSpan NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOCKOUT PROTECTION SPAN."
            ::= { optixTrapsAlarm 32915 }
        
--  1.3.6.1.4.1.2011.2.25.3.20.40.10.32916
        almLockoutWorkingRing NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOCKOUT WORKING-RING."
            ::= { optixTrapsAlarm 32916 }
        
--  1.3.6.1.4.1.2011.2.25.3.20.40.10.32917
        almLockoutWorkingSpan NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOCKOUT WORKING-SPAN."
            ::= { optixTrapsAlarm 32917 }
        
--  1.3.6.1.4.1.2011.2.25.3.20.40.10.32918
        almForceSwitchOfRing NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FORCE SWITCH OF RING."
            ::= { optixTrapsAlarm 32918 }
        
--  1.3.6.1.4.1.2011.2.25.3.20.40.10.32919
        almForceSwitchOfSpan NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FORCE SWITCH OF SPAN."
            ::= { optixTrapsAlarm 32919 }
        
--  1.3.6.1.4.1.2011.2.25.3.20.40.10.32920
        almManualSwitchOfRing NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: MANUAL SWITCH OF RING."
            ::= { optixTrapsAlarm 32920 }
        
--  1.3.6.1.4.1.2011.2.25.3.20.40.10.32921
        almManualSwitchOfSpan NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: MANUAL SWITCH OF SPAN."
            ::= { optixTrapsAlarm 32921 }
        
--  1.3.6.1.4.1.2011.2.25.3.20.40.10.32922
        almExerciseSwitchRing NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: EXERCISE SWITCH -RING."
            ::= { optixTrapsAlarm 32922 }
        
--  1.3.6.1.4.1.2011.2.25.3.20.40.10.32923
        almExerciseSwitchSpan NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: EXERCISE SWITCH -SPAN."
            ::= { optixTrapsAlarm 32923 }
        
--  1.3.6.1.4.1.2011.2.25.3.20.40.10.32924
        almLockoutProtectionForAllSpans NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOCKOUT PROTECTION FOR ALL SPANS."
            ::= { optixTrapsAlarm 32924 }
        
--  1.3.6.1.4.1.2011.2.25.3.20.40.10.32925
        almRingSwitch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: NODE STATE CHANGE TO SWITCHED."
            ::= { optixTrapsAlarm 32925 }
        
--  1.3.6.1.4.1.2011.2.25.3.20.40.10.32926
        almSpanSwitch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: NODE STATE CHANGE TO SWITCHED."
            ::= { optixTrapsAlarm 32926 }
        
--  1.3.6.1.4.1.2011.2.25.3.20.40.10.32927
        almSwitchToPassthru NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: NODE STATE CHANGE TO PASSTHRU."
            ::= { optixTrapsAlarm 32927 }
        
--  1.3.6.1.4.1.2011.2.25.3.20.40.10.32928
        almPersistentLineSquelching NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PERSISTENT LINE SQUELCHING."
            ::= { optixTrapsAlarm 32928 }
        
--  1.3.6.1.4.1.2011.2.25.3.20.40.10.33156
        almDbmsCfgBackupFailed NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: CONFIGURE DATA MISMATCH BETWEEN ACTIVE AND STANDBY XCS CARD."
            ::= { optixTrapsAlarm 33156 }
        
--  1.3.6.1.4.1.2011.2.25.3.20.40.10.33161
        almFanFailures NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FAN FAILURES."
            ::= { optixTrapsAlarm 33161 }
        
--  1.3.6.1.4.1.2011.2.25.3.20.40.10.33170
        almInvalidEQPT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: THE INSERTED PHYSICAL CARD IS NOT SUPPORTED BY THE SLOT."
            ::= { optixTrapsAlarm 33170 }
        
--  1.3.6.1.4.1.2011.2.25.3.20.40.10.33171
        almLaserApdBiasVoltageHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER APD BIAS VOLTAGE EXCEEDS STANDARD LEVEL."
            ::= { optixTrapsAlarm 33171 }
        
--  1.3.6.1.4.1.2011.2.25.3.20.40.10.33172
        almLaserApdBiasVoltageLow NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER APD BIAS VOLTAGE IS LOWER THAN STANDARD LEVEL."
            ::= { optixTrapsAlarm 33172 }
        
--  1.3.6.1.4.1.2011.2.25.3.20.40.10.33174
        almLBCHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER BIAS CURRENT EXCEEDS HIGH THRESHOLD."
            ::= { optixTrapsAlarm 33174 }
        
--  1.3.6.1.4.1.2011.2.25.3.20.40.10.33175
        almLBCLow NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER BIAS CURRENT IS LOWER THAN LOW THRESHOLD."
            ::= { optixTrapsAlarm 33175 }
        
--  1.3.6.1.4.1.2011.2.25.3.20.40.10.33176
        almLCCHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER DIODE COOLING CURRENT EXCEEDS STANDARD LEVEL."
            ::= { optixTrapsAlarm 33176 }
        
--  1.3.6.1.4.1.2011.2.25.3.20.40.10.33177
        almLCCLow NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER DIODE COOLING CURRENT IS LOWER THAN STANDARD LEVEL."
            ::= { optixTrapsAlarm 33177 }
        
--  1.3.6.1.4.1.2011.2.25.3.20.40.10.33280
        almLinkError NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LINK ERROR."
            ::= { optixTrapsAlarm 33280 }
        
--  1.3.6.1.4.1.2011.2.25.3.20.40.10.33281
        almLOA NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOSS OF ALIGNMENT OF H4 MULTIFRAME."
            ::= { optixTrapsAlarm 33281 }
        
--  1.3.6.1.4.1.2011.2.25.3.20.40.10.33282
        almLOF NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOSS OF FRAME."
            ::= { optixTrapsAlarm 33282 }
        
--  1.3.6.1.4.1.2011.2.25.3.20.40.10.33283
        almLOMPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: H4 MULTIFRAME LOST."
            ::= { optixTrapsAlarm 33283 }
        
--  1.3.6.1.4.1.2011.2.25.3.20.40.10.33284
        almLOS NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOSS OF SIGNAL."
            ::= { optixTrapsAlarm 33284 }
        
--  1.3.6.1.4.1.2011.2.25.3.20.40.10.33286
        almLaserTemperatureHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER TEMPERATURE EXCEEDS STANDARD LEVEL."
            ::= { optixTrapsAlarm 33286 }
        
--  1.3.6.1.4.1.2011.2.25.3.20.40.10.33287
        almLaserTemperatureLow NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER TEMPERATURE IS LOWER THAN STANDARD LEVEL."
            ::= { optixTrapsAlarm 33287 }
        
--  1.3.6.1.4.1.2011.2.25.3.20.40.10.33289
        almNeBdDataMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: CONFIGURE DATA MISMATCH BETWEEN NE'S AND CARD'S SOFTWARE."
            ::= { optixTrapsAlarm 33289 }
        
--  1.3.6.1.4.1.2011.2.25.3.20.40.10.33298
        almNoLaserParameter NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER PARAMETER-TABLE FILE IS CORRUPTED OR MISSING."
            ::= { optixTrapsAlarm 33298 }
        
--  1.3.6.1.4.1.2011.2.25.3.20.40.10.33301
        almSyncReferenceSourceFailure NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SYNC REFERENCE SOURCE FAILURE."
            ::= { optixTrapsAlarm 33301 }
        
--  1.3.6.1.4.1.2011.2.25.3.20.40.10.33304
        almSignalDegradeVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: BER SIGNAL DEGRADE-VT PATH."
            ::= { optixTrapsAlarm 33304 }
        
--  1.3.6.1.4.1.2011.2.25.3.20.40.10.33305
        almSignalFailureVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: BER SIGNAL FAILURE-VT PATH."
            ::= { optixTrapsAlarm 33305 }
        
--  1.3.6.1.4.1.2011.2.25.3.20.40.10.33312
        almSequenceNumberMismatchedVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: H4 MULTIFRAME SEQUENCE NUMBER MISMATCHED."
            ::= { optixTrapsAlarm 33312 }
        
--  1.3.6.1.4.1.2011.2.25.3.20.40.10.33314
        almSoftwareVersionMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SOFTWARE VERSION MISMATCH."
            ::= { optixTrapsAlarm 33314 }
        
--  1.3.6.1.4.1.2011.2.25.3.20.40.10.33315
        almTemperatureHigh NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: HIGH TEMPERATURE."
            ::= { optixTrapsAlarm 33315 }
        
--  1.3.6.1.4.1.2011.2.25.3.20.40.10.33316
        almAIS NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ALARM INDICATION SIGNAL."
            ::= { optixTrapsAlarm 33316 }
        
--  1.3.6.1.4.1.2011.2.25.3.20.40.10.33330
        almLoopbackInhibited NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: AUTOMATIC LOOPBACK INHIBITED."
            ::= { optixTrapsAlarm 33330 }
        
--  1.3.6.1.4.1.2011.2.25.3.20.40.10.33331
        almLockoutOfTheProtocol NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOCKOUT OF THE  PROTOCOL."
            ::= { optixTrapsAlarm 33331 }
        
--  1.3.6.1.4.1.2011.2.25.3.20.40.10.33332
        almLaserShutDown NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER SHUT DOWN."
            ::= { optixTrapsAlarm 33332 }
        
--  1.3.6.1.4.1.2011.2.25.3.20.40.10.33333
        almLoopbackAllDS1FEAC NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOOPBACK,ALL DS1S IN DS3 FEAC."
            ::= { optixTrapsAlarm 33333 }
        
--  1.3.6.1.4.1.2011.2.25.3.20.40.10.33335
        almLoopbackCrossConnect NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOOPBACK,CROSS-CONNECT."
            ::= { optixTrapsAlarm 33335 }
        
--  1.3.6.1.4.1.2011.2.25.3.20.40.10.33336
        almLoopbackDS1FEAC NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOOPBACK,DS1 FEAC."
            ::= { optixTrapsAlarm 33336 }
        
--  1.3.6.1.4.1.2011.2.25.3.20.40.10.33337
        almLoopbackDS3FEAC NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOOPBACK,DS3 FEAC."
            ::= { optixTrapsAlarm 33337 }
        
--  1.3.6.1.4.1.2011.2.25.3.20.40.10.33345
        almLoopbackFacilityPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOOPBACK,FACILITY -STS PATH."
            ::= { optixTrapsAlarm 33345 }
        
--  1.3.6.1.4.1.2011.2.25.3.20.40.10.33347
        almLoopbackTerminalPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOOPBACK,TERMINAL -STS PATH."
            ::= { optixTrapsAlarm 33347 }
        
--  1.3.6.1.4.1.2011.2.25.3.20.40.10.33348
        almPrimaryChannelChange NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PRIMARY CHANNEL CHANGE."
            ::= { optixTrapsAlarm 33348 }
        
--  1.3.6.1.4.1.2011.2.25.3.20.40.10.33349
        almRAI NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: REMOTE ALARM INDICATION."
            ::= { optixTrapsAlarm 33349 }
        
--  1.3.6.1.4.1.2011.2.25.3.20.40.10.33350
        almSsmDQL NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TIMING SOURCE IN SSM LESS THAN ST3."
            ::= { optixTrapsAlarm 33350 }
        
--  1.3.6.1.4.1.2011.2.25.3.20.40.10.33351
        almSsmLOS NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOSS OF SYNC MESSAGES."
            ::= { optixTrapsAlarm 33351 }
        
--  1.3.6.1.4.1.2011.2.25.3.20.40.10.33361
        almTestSessionActive NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TEST SESSION ACTIVE."
            ::= { optixTrapsAlarm 33361 }
        
--  1.3.6.1.4.1.2011.2.25.3.20.40.10.33363
        almNormalSyncMode NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: NORMAL SYNCHRONIZATION MODE."
            ::= { optixTrapsAlarm 33363 }
        
--  1.3.6.1.4.1.2011.2.25.3.20.40.10.33364
        almSwitchProtectionToWorkingUnit NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SWITCH PROTECTION TO WORKING UNIT."
            ::= { optixTrapsAlarm 33364 }
        
--  1.3.6.1.4.1.2011.2.25.3.20.40.10.33365
        almSwtichWokingToProtectingUnit NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SWITCH WORKING TO PROTECTING UNIT."
            ::= { optixTrapsAlarm 33365 }
        
--  1.3.6.1.4.1.2011.2.25.3.20.40.10.33368
        almATECardOfflineOrUninstalled NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: ATE CARD OFFLINE OR UNINSTALLED."
            ::= { optixTrapsAlarm 33368 }
        
--  1.3.6.1.4.1.2011.2.25.3.20.40.10.33370
        almPIUCardOfflineOrUninstalled NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PIU CARD OFFLINE OR UNINSTALLED."
            ::= { optixTrapsAlarm 33370 }
        
--  1.3.6.1.4.1.2011.2.25.3.20.40.10.33372
        almOOF NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: OUT OF FRAME."
            ::= { optixTrapsAlarm 33372 }
        
--  1.3.6.1.4.1.2011.2.25.3.20.40.10.33373
        almExerciseSwitchSuccess NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: EXERCISE SWITCH SUCCESS."
            ::= { optixTrapsAlarm 33373 }
        
--  1.3.6.1.4.1.2011.2.25.3.20.40.10.33374
        almExerciseSwitchFail NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: EXERCISE SWITCH FAIL."
            ::= { optixTrapsAlarm 33374 }
        
--  1.3.6.1.4.1.2011.2.25.3.20.40.10.33375
        almUpgradeInProcess NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: UPGRADE IN PROCESS."
            ::= { optixTrapsAlarm 33375 }
--  1.3.6.1.4.1.2011.2.25.3.20.40.10.33377
        almChassisMea NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: CARD NOT APPLICABLE TO THIS CHASSIS TYPE."
            ::= { optixTrapsAlarm 33377 }
        
--  1.3.6.1.4.1.2011.2.25.3.20.40.10.36923
        almLaserNotExist NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LASER IS NOT PLUGGED-IN."
            ::= { optixTrapsAlarm 36923 }
        
--  1.3.6.1.4.1.2011.2.25.3.20.40.10.36924
        almLCASBandwidthReduced NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LCAS BANDWIDTH REDUCED."
            ::= { optixTrapsAlarm 36924 }
        
--  1.3.6.1.4.1.2011.2.25.3.20.40.10.36925
        almGFPLossOfFrame NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: GFP LOSS OF FRAME."
            ::= { optixTrapsAlarm 36925 }
        
--  1.3.6.1.4.1.2011.2.25.3.20.40.10.36926
        almFanIsOpened NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FAN IS OPENED AUTOMATICALLY."
            ::= { optixTrapsAlarm 36926 }
        
--  1.3.6.1.4.1.2011.2.25.3.20.40.10.36927
        almFanIsClosed NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FAN IS CLOSED AUTOMATICALLY."
            ::= { optixTrapsAlarm 36927 }
        
--  1.3.6.1.4.1.2011.2.25.3.20.40.10.36928
        almPathLevelMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PATH LEVEL MISMATCH."
            ::= { optixTrapsAlarm 36928 }
        
--  1.3.6.1.4.1.2011.2.25.3.20.40.10.36930
        almTcaCVLine NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-CODING VIOLATIONS-LINE."
            ::= { optixTrapsAlarm 36930 }
        
--  1.3.6.1.4.1.2011.2.25.3.20.40.10.36936
        almDCCFailureIndication NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: DCC FAILURE INDICATION."
            ::= { optixTrapsAlarm 36936 }
        
--  1.3.6.1.4.1.2011.2.25.3.20.40.10.36937
        almLanLossOfCarrierSignal NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LAN LOSS OF CARRIER SIGNAL."
            ::= { optixTrapsAlarm 36937 }
        
--  1.3.6.1.4.1.2011.2.25.3.20.40.10.36938
        almTcaCVCPPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-CP BIT PARITY ERRORS-PATH."
            ::= { optixTrapsAlarm 36938 }
        
--  1.3.6.1.4.1.2011.2.25.3.20.40.10.36939
        almTcaCVPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-CODING VIOLATION-PATH."
            ::= { optixTrapsAlarm 36939 }
        
--  1.3.6.1.4.1.2011.2.25.3.20.40.10.36940
        almTcaCVPPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-CODING VIOLATION-PATH."
            ::= { optixTrapsAlarm 36940 }
        
--  1.3.6.1.4.1.2011.2.25.3.20.40.10.36941
        almTcaCVSection NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-CODING VIOLATIONS-SECTION."
            ::= { optixTrapsAlarm 36941 }
        
--  1.3.6.1.4.1.2011.2.25.3.20.40.10.36942
        almTcaCVVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-CODING VIOLATION-VT PATH."
            ::= { optixTrapsAlarm 36942 }
        
--  1.3.6.1.4.1.2011.2.25.3.20.40.10.36943
        almTcaESCPPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-CP BIT ERROR SECONDS-PATH."
            ::= { optixTrapsAlarm 36943 }
        
--  1.3.6.1.4.1.2011.2.25.3.20.40.10.36944
        almTcaESLine NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-ERROR SECONDS-LINE."
            ::= { optixTrapsAlarm 36944 }
        
--  1.3.6.1.4.1.2011.2.25.3.20.40.10.36945
        almTcaESPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-ERROR SECONDS-PATH."
            ::= { optixTrapsAlarm 36945 }
        
--  1.3.6.1.4.1.2011.2.25.3.20.40.10.36946
        almTcaESPPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-ERROR SECONDS-PATH."
            ::= { optixTrapsAlarm 36946 }
        
--  1.3.6.1.4.1.2011.2.25.3.20.40.10.36947
        almTcaESSection NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-ERROR SECONDS-SECTION."
            ::= { optixTrapsAlarm 36947 }
        
--  1.3.6.1.4.1.2011.2.25.3.20.40.10.36948
        almTcaESVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-ERROR SECONDS-VT PATH."
            ::= { optixTrapsAlarm 36948 }
        
--  1.3.6.1.4.1.2011.2.25.3.20.40.10.36949
        almTcaPjcsPdet NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-POINTER JUSTIFICATION COUNT SECONDS-  PATH DETECT."
            ::= { optixTrapsAlarm 36949 }
        
--  1.3.6.1.4.1.2011.2.25.3.20.40.10.36950
        almTcaPjcsVdet NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-POINTER JUSTIFICATION COUNT SECONDS- VT PATH DETECT."
            ::= { optixTrapsAlarm 36950 }
        
--  1.3.6.1.4.1.2011.2.25.3.20.40.10.36951
        almTcaSESCPPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-CP BIT SEVERELY ERROR SECONDS-PATH."
            ::= { optixTrapsAlarm 36951 }
        
--  1.3.6.1.4.1.2011.2.25.3.20.40.10.36952
        almTcaSESLine NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-SEVERELY ERROR SECONDS- LINE."
            ::= { optixTrapsAlarm 36952 }
        
--  1.3.6.1.4.1.2011.2.25.3.20.40.10.36953
        almTcaSESPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-SEVERELY ERROR SECONDS- PATH."
            ::= { optixTrapsAlarm 36953 }
        
--  1.3.6.1.4.1.2011.2.25.3.20.40.10.36954
        almTcaSESPPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-SEVERELY ERROR SECONDS- PATH."
            ::= { optixTrapsAlarm 36954 }
        
--  1.3.6.1.4.1.2011.2.25.3.20.40.10.36955
        almTcaSESSection NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-SEVERELY ERROR SECONDS- SECTION."
            ::= { optixTrapsAlarm 36955 }
        
--  1.3.6.1.4.1.2011.2.25.3.20.40.10.36956
        almTcaSESVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-SEVERELY ERROR SECONDS- VT PATH."
            ::= { optixTrapsAlarm 36956 }
        
--  1.3.6.1.4.1.2011.2.25.3.20.40.10.36957
        almTcaUASCPPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-CP BIT UNAVAILABLE SECONDS-PATH."
            ::= { optixTrapsAlarm 36957 }
        
--  1.3.6.1.4.1.2011.2.25.3.20.40.10.36958
        almTcaUASLine NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-UNAVAILABLE SECONDS-LINE."
            ::= { optixTrapsAlarm 36958 }
        
--  1.3.6.1.4.1.2011.2.25.3.20.40.10.36959
        almTcaUASPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-UNAVAILABLE SECONDS-PATH."
            ::= { optixTrapsAlarm 36959 }
        
--  1.3.6.1.4.1.2011.2.25.3.20.40.10.36960
        almTcaUASPPath NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA - UNAVAILABLE SECONDS - PATH."
            ::= { optixTrapsAlarm 36960 }
        
--  1.3.6.1.4.1.2011.2.25.3.20.40.10.36961
        almTcaUASVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TCA-UNAVAILABLE SECONDS-VT PATH."
            ::= { optixTrapsAlarm 36961 }
        
--  1.3.6.1.4.1.2011.2.25.3.20.40.10.36966
        almBitsAIS NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: RX ALARM INDICATION SIGNAL."
            ::= { optixTrapsAlarm 36966 }
        
--  1.3.6.1.4.1.2011.2.25.3.20.40.10.36967
        almBitsLOF NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOSS OF FRAME."
            ::= { optixTrapsAlarm 36967 }
        
--  1.3.6.1.4.1.2011.2.25.3.20.40.10.36968
        almBitsLOS NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOSS OF SIGNAL."
            ::= { optixTrapsAlarm 36968 }
        
--  1.3.6.1.4.1.2011.2.25.3.20.40.10.36969
        almBitsCodeViolationOver NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: CODE VIOLATION OVER THRESHOLD."
            ::= { optixTrapsAlarm 36969 }
        
--  1.3.6.1.4.1.2011.2.25.3.20.40.10.36970
        almBlsrSFofRing NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: BLSR AUTO SWITCH OF RING -SF."
            ::= { optixTrapsAlarm 36970 }
        
--  1.3.6.1.4.1.2011.2.25.3.20.40.10.36971
        almBlsrSFofSpan NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: BLSR AUTO SWITCH OF SPAN -SF."
            ::= { optixTrapsAlarm 36971 }
        
--  1.3.6.1.4.1.2011.2.25.3.20.40.10.36972
        almBlsrSDofRing NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: BLSR AUTO SWITCH OF RING -SD."
            ::= { optixTrapsAlarm 36972 }
        
--  1.3.6.1.4.1.2011.2.25.3.20.40.10.36973
        almBlsrSDofSpan NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: BLSR AUTO SWITCH OF SPAN -SD."
            ::= { optixTrapsAlarm 36973 }
        
--  1.3.6.1.4.1.2011.2.25.3.20.40.10.36974
        almBlsrNodeIsolate NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: BLSR NODE ISOLATED."
            ::= { optixTrapsAlarm 36974 }
        
--  1.3.6.1.4.1.2011.2.25.3.20.40.10.36975
        almSF NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LAPS AUTO SWITCH -SF."
            ::= { optixTrapsAlarm 36975 }
        
--  1.3.6.1.4.1.2011.2.25.3.20.40.10.36976
        almSD NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LAPS AUTO SWITCH -SD."
            ::= { optixTrapsAlarm 36976 }
        
--  1.3.6.1.4.1.2011.2.25.3.20.40.10.36977
        almAutoSwitch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: AUTO SWITCH."
            ::= { optixTrapsAlarm 36977 }

--  1.3.6.1.4.1.2011.2.25.3.20.40.10.36978
        almLcasPlct NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PARTIAL LOSS OF CAPACITY TRANSMIT."
            ::= { optixTrapsAlarm 36978 }

--  1.3.6.1.4.1.2011.2.25.3.20.40.10.36979
        almLcasPlcr NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: PARTIAL LOSS OF CAPACITY RECEIVE."
            ::= { optixTrapsAlarm 36979 }

--  1.3.6.1.4.1.2011.2.25.3.20.40.10.36980
        almLcasTlct NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TOTAL LOSS OF CAPACITY TRANSMIT."
            ::= { optixTrapsAlarm 36980 }

--  1.3.6.1.4.1.2011.2.25.3.20.40.10.36981
        almLcasTlcr NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: TOTAL LOSS OF CAPACITY RECEIVE."
            ::= { optixTrapsAlarm 36981 }
        
--  1.3.6.1.4.1.2011.2.25.3.20.40.10.36985
        almLcasFopt NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FOPT DEFECT INDICATES A FAILURE IN TRANSMITTING LCAS PROTOCOL."
            ::= { optixTrapsAlarm 36985 }

--  1.3.6.1.4.1.2011.2.25.3.20.40.10.36986
        almLcasFopr NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FOPT DEFECT INDICATES A FAILURE IN RECEIVING LCAS PROTOCOL."
            ::= { optixTrapsAlarm 36986 }

--  1.3.6.1.4.1.2011.2.25.3.20.40.10.40960
        almLoopbackFAC2NI NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: LOOPBACK,FAC2 NI."
            ::= { optixTrapsAlarm 40960 }

--  1.3.6.1.4.1.2011.2.25.3.20.40.10.40961
        almGfpCsf NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: GFP CLIENT LIENT SIGNAL FAIL INDICATION."
            ::= { optixTrapsAlarm 40961 }
            
--  1.3.6.1.4.1.2011.2.25.3.20.40.10.40970
        almRevertiveModeMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: REVERTIVE MODE MISMATCH."
            ::= { optixTrapsAlarm 40970 }
            
--  1.3.6.1.4.1.2011.2.25.3.20.40.10.40971
        almRingIDMismatch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: RING ID MISMATCH."
            ::= { optixTrapsAlarm 40971 }
            
--  1.3.6.1.4.1.2011.2.25.3.20.40.10.40972
        almIncorrectFiberConnection NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: INCORRECT FIBER CONNECTION FOR BLSR."
            ::= { optixTrapsAlarm 40972 }
            

--  1.3.6.1.4.1.2011.2.25.3.20.40.10.40973
        almStateChange NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: State Change."
            ::= { optixTrapsAlarm 40973 }
        
--  1.3.6.1.4.1.2011.2.25.3.20.40.10.40974
        almMtMode NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: The Entity Is In Maintenance State."
            ::= { optixTrapsAlarm 40974 }

-- 1.3.6.1.4.1.2011.2.25.3.20.40.10.40979
       almRmvToMt NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber } 
            STATUS current
            DESCRIPTION
                "Trap of Alarm: The Entity Is Removed To The Maintenance State."
            ::= { optixTrapsAlarm 40979 }

-- 1.3.6.1.4.1.2011.2.25.3.20.40.10.40980
       almRstFromMt NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber } 
            STATUS current
            DESCRIPTION
                "Trap of Alarm: The Entity Restored From The Maintenance State."
            ::= { optixTrapsAlarm 40980 }
            
-- 1.3.6.1.4.1.2011.2.25.3.20.40.10.40981
       almLpbk NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber } 
            STATUS current
            DESCRIPTION
                "Trap of Alarm: LoopBack Operated."
            ::= { optixTrapsAlarm 40981 }
            
-- 1.3.6.1.4.1.2011.2.25.3.20.40.10.40982
       almRlsLpbk NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber } 
            STATUS current
            DESCRIPTION
                "Trap of Alarm: LoopBack Released."
            ::= { optixTrapsAlarm 40982 }
                                    
--  1.3.6.1.4.1.2011.2.25.3.20.40.10.40983
        almSyncNotSyncnronized NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: THE SYSTEM CLOCK CANNOT BE SYNCHRONIZED WITH THE TIMING SOURCE."
            ::= { optixTrapsAlarm 40983 }

--  1.3.6.1.4.1.2011.2.25.3.20.40.10.40984
        almPowerExceed NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: THE POWER EXCEED FOR INSERTED CARDS."
            ::= { optixTrapsAlarm 40984 }

--  1.3.6.1.4.1.2011.2.25.3.20.40.10.40985
        almPartialUnprotected NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: SOME SERVICES ON THIS UNIT ARE NOT PROTECTED."
            ::= { optixTrapsAlarm 40985 }
            
--  1.3.6.1.4.1.2011.2.25.3.20.40.10.40986
        almFanMea NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: THE FAN DOES NOT MEET THE HEAT DISSIPATION REQUIRMENTS."
            ::= { optixTrapsAlarm 40986 }
        
--  1.3.6.1.4.1.2011.2.25.3.20.40.10.63604
        almRemoteClientSF NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Remote Client Singal Fail Alarm Indication."
            ::= { optixTrapsAlarm 63604 }
        
--  1.3.6.1.4.1.2011.2.25.3.20.40.10.63605
        almRemoteClientSD NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Remote Client Singal Degrade Alarm Indication."
            ::= { optixTrapsAlarm 63605 }
        
--  1.3.6.1.4.1.2011.2.25.3.20.40.10.63607
        almPowerSwitch NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Backup power use alarm."
            ::= { optixTrapsAlarm 63607 }
        
--  1.3.6.1.4.1.2011.2.25.3.20.40.10.63629
        almPortOffline NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: Pluggable port offline."
            ::= { optixTrapsAlarm 63629 }
        
--  1.3.6.1.4.1.2011.2.25.3.20.40.10.63630
        almDataLost NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: No Ethernet data received or transmited.."
            ::= { optixTrapsAlarm 63630 }
        
--  1.3.6.1.4.1.2011.2.25.3.20.40.10.65409
        almSqmVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: K4 MUITIFRAME SEQUENCE NUMBER MISMATCHED."
            ::= { optixTrapsAlarm 65409 }
        
--  1.3.6.1.4.1.2011.2.25.3.20.40.10.65410
        almLomVT NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: K4 MULTIFRAME LOST."
            ::= { optixTrapsAlarm 65410 }
        
--  1.3.6.1.4.1.2011.2.25.3.20.40.10.65411
        almFCSError NOTIFICATION-TYPE
            OBJECTS { rptEvtMOD2, rptEvtSlot, rptEvtPort, rptEvtPath, rptEvtVT, 
                rptEvtNtfcnCde, rptEvtState, rptEvtSrvEff, rptEvtDateTime, rptEvtLocation, 
                rptEvtDirection, rptEvtDescription, rptEvtAiddet, rptEvtSeqNumber }
            STATUS current
            DESCRIPTION 
                "Trap of Alarm: FRAME-CHECK SEQUENCE ERROR."
            ::= { optixTrapsAlarm 65411 }    
            

-- AAAAAAAAAAAAAAAAAAAAAAAAAAAAAAAAAAAAAAAAAAAAAAAAAAAAAAAAAAAAAAAAAAAAAAAAAAAA
-- Alarm trap definition end.
-- AAAAAAAAAAAAAAAAAAAAAAAAAAAAAAAAAAAAAAAAAAAAAAAAAAAAAAAAAAAAAAAAAAAAAAAAAAAA
-- -------------------------------------------------------------------------
--  REPT^EVT(include TCA)
-- -------------------------------------------------------------------------
-- BBBBBBBBBBBBBBBBBBBBBBBBBBBBBBBBBBBBBBBBBBBBBBBBBBBBBBBBBBBBBBBBBBBBBBBBBBBB
-- Event trap definition begin.
-- BBBBBBBBBBBBBBBBBBBBBBBBBBBBBBBBBBBBBBBBBBBBBBBBBBBBBBBBBBBBBBBBBBBBBBBBBBBB

        -- 1.3.6.1.4.1.2011.2.25.3.20.40.20
        optixTrapsEvent OBJECT IDENTIFIER ::= { optixSonetTraps 20 }
       
--  1.3.6.1.4.1.2011.2.25.3.20.40.20.3
        evtLossOfClock NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Loss of clock."
            ::= { optixTrapsEvent 3 }
        
--  1.3.6.1.4.1.2011.2.25.3.20.40.20.6
        evtFileLost NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SOFTWARE FILE CORRUPTED OR MISSING."
            ::= { optixTrapsEvent 6 }
        
--  1.3.6.1.4.1.2011.2.25.3.20.40.20.37
        evtREILine NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Remote error indication - Line section."
            ::= { optixTrapsEvent 37 }
        
--  1.3.6.1.4.1.2011.2.25.3.20.40.20.69
        evtBiasTemperatureOfPumpHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Bias temperature of the pump laser over threshold."
            ::= { optixTrapsEvent 69 }
        
--  1.3.6.1.4.1.2011.2.25.3.20.40.20.87
        evtTimSection NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Section trace identifier mismatch."
            ::= { optixTrapsEvent 87 }
        
--  1.3.6.1.4.1.2011.2.25.3.20.40.20.100
        evtLossOfAllSynchronousSource NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Loss of all synchronous source."
            ::= { optixTrapsEvent 100 }
        
--  1.3.6.1.4.1.2011.2.25.3.20.40.20.101
        evtSynchronousSourceDegrade NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Synchronous source degrade."
            ::= { optixTrapsEvent 101 }
        
--  1.3.6.1.4.1.2011.2.25.3.20.40.20.111
        evtSyncLOS NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Loss of high synchronous source."
            ::= { optixTrapsEvent 111 }
        
--  1.3.6.1.4.1.2011.2.25.3.20.40.20.120
        evtProtectionSwitching NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: (PS)Protection switching happened indication."
            ::= { optixTrapsEvent 120 }
        
--  1.3.6.1.4.1.2011.2.25.3.20.40.20.185
        evtDbmsError NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: DATABASE ERROR."
            ::= { optixTrapsEvent 185 }
        
--  1.3.6.1.4.1.2011.2.25.3.20.40.20.186
        evtLossOfMultiplexSignal NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Loss of multiplex signal."
            ::= { optixTrapsEvent 186 }
        
--  1.3.6.1.4.1.2011.2.25.3.20.40.20.187
        evtLossOfSingleWavelengthSignal NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Loss of single-wavelength signal."
            ::= { optixTrapsEvent 187 }
        
--  1.3.6.1.4.1.2011.2.25.3.20.40.20.188
        evtAdditionOfSingleWavelengthSignal NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: (CHAN_ADD)Addition of single-wavelength signal."
            ::= { optixTrapsEvent 188 }
        
--  1.3.6.1.4.1.2011.2.25.3.20.40.20.189
        evtLaserDegraded NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: (TD)Laser degraded."
            ::= { optixTrapsEvent 189 }
        
--  1.3.6.1.4.1.2011.2.25.3.20.40.20.192
        evtPumpDiodeCoolingCurrentHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Pump diode cooling current exceeded standard level."
            ::= { optixTrapsEvent 192 }
        
--  1.3.6.1.4.1.2011.2.25.3.20.40.20.193
        evtS1ModeSynChange NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: (S1_SYN_CHANGE)Clock reference Source Change In S1_Mode."
            ::= { optixTrapsEvent 193 }
        
--  1.3.6.1.4.1.2011.2.25.3.20.40.20.198
        evtDbmsIsInProtectMode NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: DATABASE IS IN PROTECT MODE."
            ::= { optixTrapsEvent 198 }
        
--  1.3.6.1.4.1.2011.2.25.3.20.40.20.200
        evtSecuAlarm NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOGIN ILLEGAL."
            ::= { optixTrapsEvent 200 }
        
--  1.3.6.1.4.1.2011.2.25.3.20.40.20.212
        evtForwardErrorCorrectionLossOfFrame NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Forward Error Correction Loss of Frame."
            ::= { optixTrapsEvent 212 }
        
--  1.3.6.1.4.1.2011.2.25.3.20.40.20.213
        evtForwardErrorCorrectionOutOfFrame NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Forward Error Correction Out of Frame."
            ::= { optixTrapsEvent 213 }
        
--  1.3.6.1.4.1.2011.2.25.3.20.40.20.223
        evtRateOver NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: the rate over the threshold."
            ::= { optixTrapsEvent 223 }
        
--  1.3.6.1.4.1.2011.2.25.3.20.40.20.232
        evtCardConfigurationFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: This card does not support the configuration save.."
            ::= { optixTrapsEvent 232 }
        
--  1.3.6.1.4.1.2011.2.25.3.20.40.20.240
        evtLoopback NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Port in loopback operation."
            ::= { optixTrapsEvent 240 }
        
--  1.3.6.1.4.1.2011.2.25.3.20.40.20.270
        evtCoolingCurrentModeHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Alarm of module cooling current threshold crossing."
            ::= { optixTrapsEvent 270 }
        
--  1.3.6.1.4.1.2011.2.25.3.20.40.20.272
        evtOTULossOfFrame NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OTU layer Loss of Frame Alignment."
            ::= { optixTrapsEvent 272 }
        
--  1.3.6.1.4.1.2011.2.25.3.20.40.20.273
        evtOTUOutOfMultiFrame NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OTU layer Out of MultiFrame."
            ::= { optixTrapsEvent 273 }
        
--  1.3.6.1.4.1.2011.2.25.3.20.40.20.274
        evtSmTIM NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OTU layer SM TTI Mismatch."
            ::= { optixTrapsEvent 274 }
        
--  1.3.6.1.4.1.2011.2.25.3.20.40.20.275
        evtPmTIM NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ODU layer PM TTI Mismatch."
            ::= { optixTrapsEvent 275 }
        
--  1.3.6.1.4.1.2011.2.25.3.20.40.20.276
        evtSmBDI NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OTU layer SM BDI -Backward Defect Indication."
            ::= { optixTrapsEvent 276 }
        
--  1.3.6.1.4.1.2011.2.25.3.20.40.20.277
        evtPmBDI NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ODU layer PM BDI-Backward Defect Indication."
            ::= { optixTrapsEvent 277 }
        
--  1.3.6.1.4.1.2011.2.25.3.20.40.20.278
        evtSmBEI NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OTU layer SM BEI-Backward Error Indication."
            ::= { optixTrapsEvent 278 }
        
--  1.3.6.1.4.1.2011.2.25.3.20.40.20.279
        evtPmBEI NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ODU layer PM BEI-Backward Error Indication."
            ::= { optixTrapsEvent 279 }
        
--  1.3.6.1.4.1.2011.2.25.3.20.40.20.280
        evtSmIAE NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OTU layer SM IAE-Incoming Alignment Error."
            ::= { optixTrapsEvent 280 }
        
--  1.3.6.1.4.1.2011.2.25.3.20.40.20.282
        evtSmBipExcessive NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OTU layer SM BIP-8 Excessive error defect."
            ::= { optixTrapsEvent 282 }
        
--  1.3.6.1.4.1.2011.2.25.3.20.40.20.283
        evtPmBipExcessive NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ODU layer PM BIP-8 Excessive error defect."
            ::= { optixTrapsEvent 283 }
        
--  1.3.6.1.4.1.2011.2.25.3.20.40.20.284
        evtSmBipSignalDefect NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OTU layer SM BIP-8 Degraded signal defect."
            ::= { optixTrapsEvent 284 }
        
--  1.3.6.1.4.1.2011.2.25.3.20.40.20.285
        evtPmBipSignalDefect NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ODU layer PM BIP-8 Degraded signal defect."
            ::= { optixTrapsEvent 285 }
        
--  1.3.6.1.4.1.2011.2.25.3.20.40.20.286
        evtOTUAlarmIndicationSignal NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OTU layer AIS-Alarm Indication Signal."
            ::= { optixTrapsEvent 286 }
        
--  1.3.6.1.4.1.2011.2.25.3.20.40.20.287
        evtODUAlarmIndicationSignal NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ODU layer AIS-Alarm Indication Signal."
            ::= { optixTrapsEvent 287 }
        
--  1.3.6.1.4.1.2011.2.25.3.20.40.20.288
        evtODUOpenConnectionIndicationSignal NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ODU layer OCI-Open Connection Indication Signal."
            ::= { optixTrapsEvent 288 }
        
--  1.3.6.1.4.1.2011.2.25.3.20.40.20.289
        evtODULockedIndicationSignal NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ODU layer LCK-Locked Indication Signal."
            ::= { optixTrapsEvent 289 }
        
--  1.3.6.1.4.1.2011.2.25.3.20.40.20.323
        evtSumInputOpticalPowerHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Composite input optical power too high."
            ::= { optixTrapsEvent 323 }
        
--  1.3.6.1.4.1.2011.2.25.3.20.40.20.324
        evtSumInputOpticalPowerLow NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Composite input optical power too low."
            ::= { optixTrapsEvent 324 }
        
--  1.3.6.1.4.1.2011.2.25.3.20.40.20.325
        evtSumOutOpticalPowerHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Composite output optical power too high."
            ::= { optixTrapsEvent 325 }
        
--  1.3.6.1.4.1.2011.2.25.3.20.40.20.326
        evtOutOpticalPowerLow NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Composite output optical power too low."
            ::= { optixTrapsEvent 326 }
        
--  1.3.6.1.4.1.2011.2.25.3.20.40.20.327
        evtGainLow NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Alarm of OA gain is lower than standard level."
            ::= { optixTrapsEvent 327 }
        
--  1.3.6.1.4.1.2011.2.25.3.20.40.20.335
        evtExcessiveErrorDefectBeforeFEC NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Excessive Error defect before FEC."
            ::= { optixTrapsEvent 335 }
        
--  1.3.6.1.4.1.2011.2.25.3.20.40.20.433
        evtDgeAdjustmentFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: DGE adjustment fail alarm."
            ::= { optixTrapsEvent 433 }
        
--  1.3.6.1.4.1.2011.2.25.3.20.40.20.439
        evtWavelengthLockFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Wavelength locking failure alarm."
            ::= { optixTrapsEvent 439 }
        
--  1.3.6.1.4.1.2011.2.25.3.20.40.20.440
        evtHotSwitchControlUnavail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: HOT SWITCH CONTROL UNAVAILABLE."
            ::= { optixTrapsEvent 440 }
        
--  1.3.6.1.4.1.2011.2.25.3.20.40.20.570
        evtEsconCodeError NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ESCON Code Error.."
            ::= { optixTrapsEvent 570 }
        
--  1.3.6.1.4.1.2011.2.25.3.20.40.20.573
        evtCommitTimeout NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SOFTWARE PACKAGE NOT COMMIT IN TIME."
            ::= { optixTrapsEvent 573 }
        
--  1.3.6.1.4.1.2011.2.25.3.20.40.20.574
        evtSwdlNePackageCheck NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SWDL NE SOFTWARE PACKAGE CHECK, FILE CORRUPTED OR MISSING."
            ::= { optixTrapsEvent 574 }
        
--  1.3.6.1.4.1.2011.2.25.3.20.40.20.575
        evtSwdlChaGmngmMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SWDL SCC CHANGED AND SWPKG IS NOT THE OLD ONE."
            ::= { optixTrapsEvent 575 }
        
--  1.3.6.1.4.1.2011.2.25.3.20.40.20.591
        evtDBSyncFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: DATABASE SYNCHRONIZATION FAILED."
            ::= { optixTrapsEvent 591 }
        
--  1.3.6.1.4.1.2011.2.25.3.20.40.20.604
        evtClientMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Client signal type mismatch."
            ::= { optixTrapsEvent 604 }
        
--  1.3.6.1.4.1.2011.2.25.3.20.40.20.606
        evtLaserModuleMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Laser module is mismatch."
            ::= { optixTrapsEvent 606 }

--  1.3.6.1.4.1.2011.2.25.3.20.40.20.12300
        evtLptRfi NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LINK PATH STATE THROUGH REMOTE FAIL INDICATION."
            ::= { optixTrapsEvent 12300 }
        
--  1.3.6.1.4.1.2011.2.25.3.20.40.20.32768
        evtEqptNoServiceAffecting NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: NON-SERVICE-AFFECTING EQUIPMENT FAILURE."
            ::= { optixTrapsEvent 32768 }
        
--  1.3.6.1.4.1.2011.2.25.3.20.40.20.32769
        evtEqptServiceAffectingFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SERVICE-AFFECTING EQUIPMENT FAILURE."
            ::= { optixTrapsEvent 32769 }
        
--  1.3.6.1.4.1.2011.2.25.3.20.40.20.32774
        evtApsByteFailure NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PROTECTION SWITCHING BYTE FAILURE."
            ::= { optixTrapsEvent 32774 }
        
--  1.3.6.1.4.1.2011.2.25.3.20.40.20.32776
        evtFarEndProtectionLineFailure NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FAR END PROTECTION LINE FAILURE."
            ::= { optixTrapsEvent 32776 }
        
--  1.3.6.1.4.1.2011.2.25.3.20.40.20.32777
        evtApsChannelMismatchFailure NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PROTECTION SWITCHING CHANNEL MISMATCH FAILURE."
            ::= { optixTrapsEvent 32777 }
        
--  1.3.6.1.4.1.2011.2.25.3.20.40.20.32778
        evtApsModeMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: AUTOMATIC PROTECTION SWITCH MODE MISMATCH."
            ::= { optixTrapsEvent 32778 }
        
--  1.3.6.1.4.1.2011.2.25.3.20.40.20.32779
        evtApsTypeMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: AUTOMATIC PROTECTION SWITCH TYPE MISMATCH."
            ::= { optixTrapsEvent 32779 }
        
--  1.3.6.1.4.1.2011.2.25.3.20.40.20.32791
        evtHoldoverSync NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: HOLDOVER SYNCHRONIZATION MODE."
            ::= { optixTrapsEvent 32791 }
        
--  1.3.6.1.4.1.2011.2.25.3.20.40.20.32792
        evtFreeRunSync NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: IN FREE RUN SYNCHRONIZATION MODE."
            ::= { optixTrapsEvent 32792 }
        
--  1.3.6.1.4.1.2011.2.25.3.20.40.20.32794
        evtFastStartSync NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FAST START SYNCHRONIZATION MODE."
            ::= { optixTrapsEvent 32794 }
        
--  1.3.6.1.4.1.2011.2.25.3.20.40.20.32798
        evtManualSetSSM NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: MANUAL SET A REFERENCE'S SSM."
            ::= { optixTrapsEvent 32798 }
        
--  1.3.6.1.4.1.2011.2.25.3.20.40.20.32802
        evtFanOffline NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FAN OFFLINE."
            ::= { optixTrapsEvent 32802 }
        
--  1.3.6.1.4.1.2011.2.25.3.20.40.20.32803
        evtSingleFanFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SINGLE-FAN UNIT FAILED."
            ::= { optixTrapsEvent 32803 }
        
--  1.3.6.1.4.1.2011.2.25.3.20.40.20.32804
        evtMultiFanFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: MULTI-FAN UNIT FAILED."
            ::= { optixTrapsEvent 32804 }
        
--  1.3.6.1.4.1.2011.2.25.3.20.40.20.32807
        evtEquipmentTypeMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: EQUIPMENT TYPE MISMATCH."
            ::= { optixTrapsEvent 32807 }
        
--  1.3.6.1.4.1.2011.2.25.3.20.40.20.32808
        evtEquipmentOfflineOrUninstalled NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: EQUIPMENT  OFFLINE OR UNINSTALLED."
            ::= { optixTrapsEvent 32808 }
        
--  1.3.6.1.4.1.2011.2.25.3.20.40.20.32814
        evtTransmitterFailure NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TRANSMITTER FAILURE."
            ::= { optixTrapsEvent 32814 }
        
--  1.3.6.1.4.1.2011.2.25.3.20.40.20.32815
        evtSignalFailureSection NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SIGNAL FAILURE-SECTION."
            ::= { optixTrapsEvent 32815 }
        
--  1.3.6.1.4.1.2011.2.25.3.20.40.20.32816
        evtInputPowerHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: INPUT POWER EXCEEDS STANDARD LEVEL."
            ::= { optixTrapsEvent 32816 }
        
--  1.3.6.1.4.1.2011.2.25.3.20.40.20.32817
        evtInputPowerLow NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: INPUT POWER IS LOWER THAN STANDARD LEVEL."
            ::= { optixTrapsEvent 32817 }
        
--  1.3.6.1.4.1.2011.2.25.3.20.40.20.32818
        evtSignalFailureLine NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SIGNAL FAILURE-LINE."
            ::= { optixTrapsEvent 32818 }
        
--  1.3.6.1.4.1.2011.2.25.3.20.40.20.32819
        evtSignalDegradeLine NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SIGNAL DEGRADE-LINE."
            ::= { optixTrapsEvent 32819 }
        
--  1.3.6.1.4.1.2011.2.25.3.20.40.20.32820
        evtLaserApprochingEndOfLife NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER APPROACHING END OF LIFE."
            ::= { optixTrapsEvent 32820 }
        
--  1.3.6.1.4.1.2011.2.25.3.20.40.20.32821
        evtOutPowerHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OUTPUT POWER EXCEEDS STANDARD LEVEL."
            ::= { optixTrapsEvent 32821 }
        
--  1.3.6.1.4.1.2011.2.25.3.20.40.20.32822
        evtOutPowerLow NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OUTPUT POWER IS LOWER THAN STANDARD LEVEL."
            ::= { optixTrapsEvent 32822 }
        
--  1.3.6.1.4.1.2011.2.25.3.20.40.20.32823
        evtSignalDegradeSection NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SIGNAL DEGRADE-SECTION."
            ::= { optixTrapsEvent 32823 }
        
--  1.3.6.1.4.1.2011.2.25.3.20.40.20.32824
        evtAlarmIndicationSignalLine NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SONET AIS - LINE."
            ::= { optixTrapsEvent 32824 }
        
--  1.3.6.1.4.1.2011.2.25.3.20.40.20.32825
        evtRemoteFailureIindicationLine NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: REMOTE FAILURE INDICATION-LINE."
            ::= { optixTrapsEvent 32825 }
        
--  1.3.6.1.4.1.2011.2.25.3.20.40.20.32826
        evtAlarmIndicationSignalPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SONET AIS - PATH."
            ::= { optixTrapsEvent 32826 }
        
--  1.3.6.1.4.1.2011.2.25.3.20.40.20.32827
        evtLossOfPointerPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SONET LOSS OF POINTER STS-PATH."
            ::= { optixTrapsEvent 32827 }
        
--  1.3.6.1.4.1.2011.2.25.3.20.40.20.32828
        evtTraceIdentifierMismatchPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SONET TRACE IDENTIFIER MISMATCH STS-PATH."
            ::= { optixTrapsEvent 32828 }
        
--  1.3.6.1.4.1.2011.2.25.3.20.40.20.32829
        evtUnequippedPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: UNEQUIPPED - STS."
            ::= { optixTrapsEvent 32829 }
        
--  1.3.6.1.4.1.2011.2.25.3.20.40.20.32830
        evtSignalFailurePath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SIGNAL FAILURE STS-PATH."
            ::= { optixTrapsEvent 32830 }
        
--  1.3.6.1.4.1.2011.2.25.3.20.40.20.32831
        evtSignalDegradePath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SIGNAL DEGRADE STS-PATH."
            ::= { optixTrapsEvent 32831 }
        
--  1.3.6.1.4.1.2011.2.25.3.20.40.20.32832
        evtRemoteFailureIindicationPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SONET REMOTE FAILURE INDICATION-STS PATH."
            ::= { optixTrapsEvent 32832 }
        
--  1.3.6.1.4.1.2011.2.25.3.20.40.20.32833
        evtALS NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SHUTDOWN THE  LASER AUTOMATICALLY ON DETECTING LOS."
            ::= { optixTrapsEvent 32833 }
        
--  1.3.6.1.4.1.2011.2.25.3.20.40.20.32834
        evtLoopbackFacility NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOOPBACK,FACILITY."
            ::= { optixTrapsEvent 32834 }
        
--  1.3.6.1.4.1.2011.2.25.3.20.40.20.32835
        evtLoopbackTerminal NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOOPBACK, TERMINAL."
            ::= { optixTrapsEvent 32835 }
        
--  1.3.6.1.4.1.2011.2.25.3.20.40.20.32836
        evtPayloadLabelMisatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PAYLOAD LABEL MISMATCH-STS."
            ::= { optixTrapsEvent 32836 }
        
--  1.3.6.1.4.1.2011.2.25.3.20.40.20.32837
        evtEnhancedRemotePalyloadFailureIndicationPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ENHANCED REMOTE PAYLOAD FAILURE INDICATION - STS PATH."
            ::= { optixTrapsEvent 32837 }
        
--  1.3.6.1.4.1.2011.2.25.3.20.40.20.32838
        evtEnhancedRemoteServerFailureIndicationPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ENHANCED REMOTE SERVER FAILURE INDICATION - STS PATH."
            ::= { optixTrapsEvent 32838 }
        
--  1.3.6.1.4.1.2011.2.25.3.20.40.20.32839
        evtEnhancedRemoteConnectivityFailureIndicationPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ENHANCED REMOTE CONNECTIVITY FAILURE INDICATION - STS PATH."
            ::= { optixTrapsEvent 32839 }
        
--  1.3.6.1.4.1.2011.2.25.3.20.40.20.32840
        evtPDIPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PAYLOAD DEFECT INDICATION-STS."
            ::= { optixTrapsEvent 32840 }
        
--  1.3.6.1.4.1.2011.2.25.3.20.40.20.32841
        evtPowerFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: POWER SUPPLY FAILURE."
            ::= { optixTrapsEvent 32841 }
        
--  1.3.6.1.4.1.2011.2.25.3.20.40.20.32842
        evtLossOfPointerVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOSS OF VT POINTER."
            ::= { optixTrapsEvent 32842 }
        
--  1.3.6.1.4.1.2011.2.25.3.20.40.20.32843
        evtAlarmIndicationSignalVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: VT PATH ALARM INDICATION SIGNAL."
            ::= { optixTrapsEvent 32843 }
        
--  1.3.6.1.4.1.2011.2.25.3.20.40.20.32844
        evtPayloadLabelMismatchVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: VT PATH PAYLOAD LABEL MISMATCH."
            ::= { optixTrapsEvent 32844 }
        
--  1.3.6.1.4.1.2011.2.25.3.20.40.20.32845
        evtUnequippedVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: VT PATH UNEQUIPPED."
            ::= { optixTrapsEvent 32845 }
        
--  1.3.6.1.4.1.2011.2.25.3.20.40.20.32846
        evtRemoteFailureIndicationVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: VT PATH REMOTE FAILURE INDICATION."
            ::= { optixTrapsEvent 32846 }
        
--  1.3.6.1.4.1.2011.2.25.3.20.40.20.32847
        evtRemoteServerFailureIndicationVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: VT PATH REMOTE SERVER FAILURE INDICATION."
            ::= { optixTrapsEvent 32847 }
        
--  1.3.6.1.4.1.2011.2.25.3.20.40.20.32848
        evtEnhancedRemoteConnectivityFailureIndicationVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: VT PATH REMOTE CONNECTIVITY FAILURE INDICATION."
            ::= { optixTrapsEvent 32848 }
        
--  1.3.6.1.4.1.2011.2.25.3.20.40.20.32849
        evtEnhancedRemotePalyloadFailureIndicationVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: VT PATH REMOTE PAYLOAD FAILURE INDICATION."
            ::= { optixTrapsEvent 32849 }
        
--  1.3.6.1.4.1.2011.2.25.3.20.40.20.32876
        evtInterFaceCardOffline NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: INTERFACE CARD OFFLINE."
            ::= { optixTrapsEvent 32876 }
        
--  1.3.6.1.4.1.2011.2.25.3.20.40.20.32877
        evtSyncChangeSSM NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: RECEIVE SSM OF REFERENCE SOURCE HAS CHANGED."
            ::= { optixTrapsEvent 32877 }
        
--  1.3.6.1.4.1.2011.2.25.3.20.40.20.32878
        evtTimeingModeChange NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TIMEING SOURCE MODE CHANGE."
            ::= { optixTrapsEvent 32878 }
        
--  1.3.6.1.4.1.2011.2.25.3.20.40.20.32879
        evtLockoutWorkingUnit NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOCKOUT WORKING UNIT."
            ::= { optixTrapsEvent 32879 }
        
--  1.3.6.1.4.1.2011.2.25.3.20.40.20.32880
        evtLockoutProtectionUnit NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOCKOUT PROTECTION UNIT."
            ::= { optixTrapsEvent 32880 }
        
--  1.3.6.1.4.1.2011.2.25.3.20.40.20.32881
        evtForcedSwitch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FORCED SWITCH."
            ::= { optixTrapsEvent 32881 }
        
--  1.3.6.1.4.1.2011.2.25.3.20.40.20.32882
        evtManualSwitch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: MANUAL SWITCH."
            ::= { optixTrapsEvent 32882 }
        
--  1.3.6.1.4.1.2011.2.25.3.20.40.20.32883
        evtExerciseSwitch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: EXERCISE SWITCH."
            ::= { optixTrapsEvent 32883 }
        
--  1.3.6.1.4.1.2011.2.25.3.20.40.20.32884
        evtWaitToRestore NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: WAIT TO RESTORE."
            ::= { optixTrapsEvent 32884 }
        
--  1.3.6.1.4.1.2011.2.25.3.20.40.20.32886
        evtSwitchToIdle NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SWITCH TO IDLE."
            ::= { optixTrapsEvent 32886 }
        
--  1.3.6.1.4.1.2011.2.25.3.20.40.20.32887
        evtSwitchFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SWITCH FAIL EVENT."
            ::= { optixTrapsEvent 32887 }
        
--  1.3.6.1.4.1.2011.2.25.3.20.40.20.32889
        evtSyncSwitch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SWITCH EVENT."
            ::= { optixTrapsEvent 32889 }
        
--  1.3.6.1.4.1.2011.2.25.3.20.40.20.32890
        evtCommunicationFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: COMMUNICATION FAIL."
            ::= { optixTrapsEvent 32890 }
        
--  1.3.6.1.4.1.2011.2.25.3.20.40.20.32891
        evtPowerAFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FAILURES FOR THE  POWER SUPPLY."
            ::= { optixTrapsEvent 32891 }
        
--  1.3.6.1.4.1.2011.2.25.3.20.40.20.32892
        evtPowerBFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FAILURES FOR THE  POWER SUPPLY."
            ::= { optixTrapsEvent 32892 }
        
--  1.3.6.1.4.1.2011.2.25.3.20.40.20.32899
        evtInterfaceLinkMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: INTERFACE LINK MISMATCH."
            ::= { optixTrapsEvent 32899 }
        
--  1.3.6.1.4.1.2011.2.25.3.20.40.20.32900
        evtInterfaceCardFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: INTERFACE CARD FAIL."
            ::= { optixTrapsEvent 32900 }
        
--  1.3.6.1.4.1.2011.2.25.3.20.40.20.32901
        evtAIC NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PATH MISMATCH OF FRAMING APPLICATION."
            ::= { optixTrapsEvent 32901 }
        
--  1.3.6.1.4.1.2011.2.25.3.20.40.20.32903
        evtDbmsCfgCorrupted NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: CONFIGURATION DATABASE CORRUPTED."
            ::= { optixTrapsEvent 32903 }
        
--  1.3.6.1.4.1.2011.2.25.3.20.40.20.32904
        evtDefaultKByteDefect NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: DEFAULT K BYTE DEFECT."
            ::= { optixTrapsEvent 32904 }
        
--  1.3.6.1.4.1.2011.2.25.3.20.40.20.32905
        evtInconsistentApsCodes NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: INCONSISTENT APS CODES."
            ::= { optixTrapsEvent 32905 }
        
--  1.3.6.1.4.1.2011.2.25.3.20.40.20.32906
        evtImproperApsCodes NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: IMPROPER APS CODES."
            ::= { optixTrapsEvent 32906 }
        
--  1.3.6.1.4.1.2011.2.25.3.20.40.20.32907
        evtExtraTrafficIsBeingSquelched NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: EXTRA TRAFFIC IS BEING SQUELCHED."
            ::= { optixTrapsEvent 32907 }
        
--  1.3.6.1.4.1.2011.2.25.3.20.40.20.32908
        evtTopologyNeedsUpdatingOrIsInvalid NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TOPOLOGY NEEDS UPDATING OR IS INVALID."
            ::= { optixTrapsEvent 32908 }
        
--  1.3.6.1.4.1.2011.2.25.3.20.40.20.32909
        evtSquelchTableNeedsUpdatingOrIsInvalid NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SQUELCH TABLE NEEDS UPDATING OR IS INVALID."
            ::= { optixTrapsEvent 32909 }
        
--  1.3.6.1.4.1.2011.2.25.3.20.40.20.32910
        evtNodeIdDuplicatedOrMismatched NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: NODE ID DUPLICATED OR MISMATCHED."
            ::= { optixTrapsEvent 32910 }
        
--  1.3.6.1.4.1.2011.2.25.3.20.40.20.32911
        evtXconMismatched NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: CROSS-CONNECTION TYPE IS MISMATCHED WITH ADJACENT NODE."
            ::= { optixTrapsEvent 32911 }
        
--  1.3.6.1.4.1.2011.2.25.3.20.40.20.32912
        evtRingModeMisatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: RING MODE MISMATCHED. SOME NODES IN AUTO AND SOME IN MANUAL."
            ::= { optixTrapsEvent 32912 }
        
--  1.3.6.1.4.1.2011.2.25.3.20.40.20.32913
        evtSquelchModeMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SQUELCH MODE MISMATCHED. SOME NODES IN AUTO AND SOME IN MANUAL."
            ::= { optixTrapsEvent 32913 }
        
--  1.3.6.1.4.1.2011.2.25.3.20.40.20.32915
        evtLockoutProtectionSpan NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOCKOUT PROTECTION SPAN."
            ::= { optixTrapsEvent 32915 }
        
--  1.3.6.1.4.1.2011.2.25.3.20.40.20.32916
        evtLockoutWorkingRing NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOCKOUT WORKING-RING."
            ::= { optixTrapsEvent 32916 }
        
--  1.3.6.1.4.1.2011.2.25.3.20.40.20.32917
        evtLockoutWorkingSpan NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOCKOUT WORKING-SPAN."
            ::= { optixTrapsEvent 32917 }
        
--  1.3.6.1.4.1.2011.2.25.3.20.40.20.32918
        evtForceSwitchOfRing NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FORCE SWITCH OF RING."
            ::= { optixTrapsEvent 32918 }
        
--  1.3.6.1.4.1.2011.2.25.3.20.40.20.32919
        evtForceSwitchOfSpan NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FORCE SWITCH OF SPAN."
            ::= { optixTrapsEvent 32919 }
        
--  1.3.6.1.4.1.2011.2.25.3.20.40.20.32920
        evtManualSwitchOfRing NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: MANUAL SWITCH OF RING."
            ::= { optixTrapsEvent 32920 }
        
--  1.3.6.1.4.1.2011.2.25.3.20.40.20.32921
        evtManualSwitchOfSpan NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: MANUAL SWITCH OF SPAN."
            ::= { optixTrapsEvent 32921 }
        
--  1.3.6.1.4.1.2011.2.25.3.20.40.20.32922
        evtExerciseSwitchRing NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: EXERCISE SWITCH -RING."
            ::= { optixTrapsEvent 32922 }
        
--  1.3.6.1.4.1.2011.2.25.3.20.40.20.32923
        evtExerciseSwitchSpan NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: EXERCISE SWITCH -SPAN."
            ::= { optixTrapsEvent 32923 }
        
--  1.3.6.1.4.1.2011.2.25.3.20.40.20.32924
        evtLockoutProtectionForAllSpans NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOCKOUT PROTECTION FOR ALL SPANS."
            ::= { optixTrapsEvent 32924 }
        
--  1.3.6.1.4.1.2011.2.25.3.20.40.20.32925
        evtRingSwitch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: NODE STATE CHANGE TO SWITCHED."
            ::= { optixTrapsEvent 32925 }
        
--  1.3.6.1.4.1.2011.2.25.3.20.40.20.32926
        evtSpanSwitch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: NODE STATE CHANGE TO SWITCHED."
            ::= { optixTrapsEvent 32926 }
        
--  1.3.6.1.4.1.2011.2.25.3.20.40.20.32927
        evtSwitchToPassthru NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: NODE STATE CHANGE TO PASSTHRU."
            ::= { optixTrapsEvent 32927 }
        
--  1.3.6.1.4.1.2011.2.25.3.20.40.20.32928
        evtPersistentLineSquelching NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PERSISTENT LINE SQUELCHING."
            ::= { optixTrapsEvent 32928 }
        
--  1.3.6.1.4.1.2011.2.25.3.20.40.20.33156
        evtDbmsCfgBackupFailed NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: CONFIGURE DATA MISMATCH BETWEEN ACTIVE AND STANDBY XCS CARD."
            ::= { optixTrapsEvent 33156 }
        
--  1.3.6.1.4.1.2011.2.25.3.20.40.20.33161
        evtFanFailures NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FAN FAILURES."
            ::= { optixTrapsEvent 33161 }
        
--  1.3.6.1.4.1.2011.2.25.3.20.40.20.33170
        evtInvalidEQPT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: THE INSERTED PHYSICAL CARD IS NOT SUPPORTED BY THE SLOT."
            ::= { optixTrapsEvent 33170 }
        
--  1.3.6.1.4.1.2011.2.25.3.20.40.20.33171
        evtLaserApdBiasVoltageHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER APD BIAS VOLTAGE EXCEEDS STANDARD LEVEL."
            ::= { optixTrapsEvent 33171 }
        
--  1.3.6.1.4.1.2011.2.25.3.20.40.20.33172
        evtLaserApdBiasVoltageLow NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER APD BIAS VOLTAGE IS LOWER THAN STANDARD LEVEL."
            ::= { optixTrapsEvent 33172 }
        
--  1.3.6.1.4.1.2011.2.25.3.20.40.20.33174
        evtLBCHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER BIAS CURRENT EXCEEDS HIGH THRESHOLD."
            ::= { optixTrapsEvent 33174 }
        
--  1.3.6.1.4.1.2011.2.25.3.20.40.20.33175
        evtLBCLow NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER BIAS CURRENT IS LOWER THAN LOW THRESHOLD."
            ::= { optixTrapsEvent 33175 }
        
--  1.3.6.1.4.1.2011.2.25.3.20.40.20.33176
        evtLCCHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER DIODE COOLING CURRENT EXCEEDS STANDARD LEVEL."
            ::= { optixTrapsEvent 33176 }
        
--  1.3.6.1.4.1.2011.2.25.3.20.40.20.33177
        evtLCCLow NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER DIODE COOLING CURRENT IS LOWER THAN STANDARD LEVEL."
            ::= { optixTrapsEvent 33177 }
        
--  1.3.6.1.4.1.2011.2.25.3.20.40.20.33280
        evtLinkError NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LINK ERROR."
            ::= { optixTrapsEvent 33280 }
        
--  1.3.6.1.4.1.2011.2.25.3.20.40.20.33281
        evtLOA NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOSS OF ALIGNMENT OF H4 MULTIFRAME."
            ::= { optixTrapsEvent 33281 }
        
--  1.3.6.1.4.1.2011.2.25.3.20.40.20.33282
        evtLOF NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOSS OF FRAME."
            ::= { optixTrapsEvent 33282 }
        
--  1.3.6.1.4.1.2011.2.25.3.20.40.20.33283
        evtLOMPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: H4 MULTIFRAME LOST."
            ::= { optixTrapsEvent 33283 }
        
--  1.3.6.1.4.1.2011.2.25.3.20.40.20.33284
        evtLOS NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOSS OF SIGNAL."
            ::= { optixTrapsEvent 33284 }
        
--  1.3.6.1.4.1.2011.2.25.3.20.40.20.33286
        evtLaserTemperatureHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER TEMPERATURE EXCEEDS STANDARD LEVEL."
            ::= { optixTrapsEvent 33286 }
        
--  1.3.6.1.4.1.2011.2.25.3.20.40.20.33287
        evtLaserTemperatureLow NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER TEMPERATURE IS LOWER THAN STANDARD LEVEL."
            ::= { optixTrapsEvent 33287 }
        
--  1.3.6.1.4.1.2011.2.25.3.20.40.20.33289
        evtNeBdDataMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: CONFIGURE DATA MISMATCH BETWEEN NE'S AND CARD'S SOFTWARE."
            ::= { optixTrapsEvent 33289 }
        
--  1.3.6.1.4.1.2011.2.25.3.20.40.20.33298
        evtNoLaserParameter NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER PARAMETER-TABLE FILE IS CORRUPTED OR MISSING."
            ::= { optixTrapsEvent 33298 }
        
--  1.3.6.1.4.1.2011.2.25.3.20.40.20.33301
        evtSyncReferenceSourceFailure NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SYNC REFERENCE SOURCE FAILURE."
            ::= { optixTrapsEvent 33301 }
        
--  1.3.6.1.4.1.2011.2.25.3.20.40.20.33304
        evtSignalDegradeVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: BER SIGNAL DEGRADE-VT PATH."
            ::= { optixTrapsEvent 33304 }
        
--  1.3.6.1.4.1.2011.2.25.3.20.40.20.33305
        evtSignalFailureVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: BER SIGNAL FAILURE-VT PATH."
            ::= { optixTrapsEvent 33305 }
        
--  1.3.6.1.4.1.2011.2.25.3.20.40.20.33312
        evtSequenceNumberMismatchedVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: H4 MULTIFRAME SEQUENCE NUMBER MISMATCHED."
            ::= { optixTrapsEvent 33312 }
        
--  1.3.6.1.4.1.2011.2.25.3.20.40.20.33314
        evtSoftwareVersionMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SOFTWARE VERSION MISMATCH."
            ::= { optixTrapsEvent 33314 }
        
--  1.3.6.1.4.1.2011.2.25.3.20.40.20.33315
        evtTemperatureHigh NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: HIGH TEMPERATURE."
            ::= { optixTrapsEvent 33315 }
        
--  1.3.6.1.4.1.2011.2.25.3.20.40.20.33316
        evtAIS NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ALARM INDICATION SIGNAL."
            ::= { optixTrapsEvent 33316 }
        
--  1.3.6.1.4.1.2011.2.25.3.20.40.20.33330
        evtLoopbackInhibited NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: AUTOMATIC LOOPBACK INHIBITED."
            ::= { optixTrapsEvent 33330 }
        
--  1.3.6.1.4.1.2011.2.25.3.20.40.20.33331
        evtLockoutOfTheProtocol NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOCKOUT OF THE  PROTOCOL."
            ::= { optixTrapsEvent 33331 }
        
--  1.3.6.1.4.1.2011.2.25.3.20.40.20.33332
        evtLaserShutDown NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER SHUT DOWN."
            ::= { optixTrapsEvent 33332 }
        
--  1.3.6.1.4.1.2011.2.25.3.20.40.20.33333
        evtLoopbackAllDS1FEAC NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOOPBACK,ALL DS1S IN DS3 FEAC."
            ::= { optixTrapsEvent 33333 }
        
--  1.3.6.1.4.1.2011.2.25.3.20.40.20.33335
        evtLoopbackCrossConnect NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOOPBACK,CROSS-CONNECT."
            ::= { optixTrapsEvent 33335 }
        
--  1.3.6.1.4.1.2011.2.25.3.20.40.20.33336
        evtLoopbackDS1FEAC NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOOPBACK,DS1 FEAC."
            ::= { optixTrapsEvent 33336 }
        
--  1.3.6.1.4.1.2011.2.25.3.20.40.20.33337
        evtLoopbackDS3FEAC NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOOPBACK,DS3 FEAC."
            ::= { optixTrapsEvent 33337 }
        
--  1.3.6.1.4.1.2011.2.25.3.20.40.20.33345
        evtLoopbackFacilityPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOOPBACK,FACILITY -STS PATH."
            ::= { optixTrapsEvent 33345 }
        
--  1.3.6.1.4.1.2011.2.25.3.20.40.20.33347
        evtLoopbackTerminalPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOOPBACK,TERMINAL -STS PATH."
            ::= { optixTrapsEvent 33347 }
        
--  1.3.6.1.4.1.2011.2.25.3.20.40.20.33348
        evtPrimaryChannelChange NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PRIMARY CHANNEL CHANGE."
            ::= { optixTrapsEvent 33348 }
        
--  1.3.6.1.4.1.2011.2.25.3.20.40.20.33349
        evtRAI NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: REMOTE ALARM INDICATION."
            ::= { optixTrapsEvent 33349 }
        
--  1.3.6.1.4.1.2011.2.25.3.20.40.20.33350
        evtSsmDQL NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TIMING SOURCE IN SSM LESS THAN ST3."
            ::= { optixTrapsEvent 33350 }
        
--  1.3.6.1.4.1.2011.2.25.3.20.40.20.33351
        evtSsmLOS NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOSS OF SYNC MESSAGES."
            ::= { optixTrapsEvent 33351 }
        
--  1.3.6.1.4.1.2011.2.25.3.20.40.20.33361
        evtTestSessionActive NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TEST SESSION ACTIVE."
            ::= { optixTrapsEvent 33361 }
        
--  1.3.6.1.4.1.2011.2.25.3.20.40.20.33363
        evtNormalSyncMode NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: NORMAL SYNCHRONIZATION MODE."
            ::= { optixTrapsEvent 33363 }
        
--  1.3.6.1.4.1.2011.2.25.3.20.40.20.33364
        evtSwitchProtectionToWorkingUnit NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SWITCH PROTECTION TO WORKING UNIT."
            ::= { optixTrapsEvent 33364 }
        
--  1.3.6.1.4.1.2011.2.25.3.20.40.20.33365
        evtSwtichWokingToProtectingUnit NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SWITCH WORKING TO PROTECTING UNIT."
            ::= { optixTrapsEvent 33365 }
        
--  1.3.6.1.4.1.2011.2.25.3.20.40.20.33368
        evtATECardOfflineOrUninstalled NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: ATE CARD OFFLINE OR UNINSTALLED."
            ::= { optixTrapsEvent 33368 }
        
--  1.3.6.1.4.1.2011.2.25.3.20.40.20.33370
        evtPIUCardOfflineOrUninstalled NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PIU CARD OFFLINE OR UNINSTALLED."
            ::= { optixTrapsEvent 33370 }
        
--  1.3.6.1.4.1.2011.2.25.3.20.40.20.33372
        evtOOF NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: OUT OF FRAME."
            ::= { optixTrapsEvent 33372 }
        
--  1.3.6.1.4.1.2011.2.25.3.20.40.20.33373
        evtExerciseSwitchSuccess NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: EXERCISE SWITCH SUCCESS."
            ::= { optixTrapsEvent 33373 }
        
--  1.3.6.1.4.1.2011.2.25.3.20.40.20.33374
        evtExerciseSwitchFail NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: EXERCISE SWITCH FAIL."
            ::= { optixTrapsEvent 33374 }
        
--  1.3.6.1.4.1.2011.2.25.3.20.40.20.33375
        evtUpgradeInProcess NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: UPGRADE IN PROCESS."
            ::= { optixTrapsEvent 33375 }
--  1.3.6.1.4.1.2011.2.25.3.20.40.20.33377
        evtChassisMea NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: CARD NOT APPLICABLE TO THIS CHASSIS TYPE."
            ::= { optixTrapsEvent 33377 }
        
--  1.3.6.1.4.1.2011.2.25.3.20.40.20.36923
        evtLaserNotExist NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LASER IS NOT PLUGGED-IN."
            ::= { optixTrapsEvent 36923 }
        
--  1.3.6.1.4.1.2011.2.25.3.20.40.20.36924
        evtLCASBandwidthReduced NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LCAS BANDWIDTH REDUCED."
            ::= { optixTrapsEvent 36924 }
        
--  1.3.6.1.4.1.2011.2.25.3.20.40.20.36925
        evtGFPLossOfFrame NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: GFP LOSS OF FRAME."
            ::= { optixTrapsEvent 36925 }
        
--  1.3.6.1.4.1.2011.2.25.3.20.40.20.36926
        evtFanIsOpened NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FAN IS OPENED AUTOMATICALLY."
            ::= { optixTrapsEvent 36926 }
        
--  1.3.6.1.4.1.2011.2.25.3.20.40.20.36927
        evtFanIsClosed NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FAN IS CLOSED AUTOMATICALLY."
            ::= { optixTrapsEvent 36927 }
        
--  1.3.6.1.4.1.2011.2.25.3.20.40.20.36928
        evtPathLevelMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PATH LEVEL MISMATCH."
            ::= { optixTrapsEvent 36928 }
        
--  1.3.6.1.4.1.2011.2.25.3.20.40.20.36930
        evtTcaCVLine NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-CODING VIOLATIONS-LINE."
            ::= { optixTrapsEvent 36930 }
        
--  1.3.6.1.4.1.2011.2.25.3.20.40.20.36936
        evtDCCFailureIndication NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: DCC FAILURE INDICATION."
            ::= { optixTrapsEvent 36936 }
        
--  1.3.6.1.4.1.2011.2.25.3.20.40.20.36937
        evtLanLossOfCarrierSignal NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LAN LOSS OF CARRIER SIGNAL."
            ::= { optixTrapsEvent 36937 }
        
--  1.3.6.1.4.1.2011.2.25.3.20.40.20.36938
        evtTcaCVCPPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-CP BIT PARITY ERRORS-PATH."
            ::= { optixTrapsEvent 36938 }
        
--  1.3.6.1.4.1.2011.2.25.3.20.40.20.36939
        evtTcaCVPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-CODING VIOLATION-PATH."
            ::= { optixTrapsEvent 36939 }
        
--  1.3.6.1.4.1.2011.2.25.3.20.40.20.36940
        evtTcaCVPPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-CODING VIOLATION-PATH."
            ::= { optixTrapsEvent 36940 }
        
--  1.3.6.1.4.1.2011.2.25.3.20.40.20.36941
        evtTcaCVSection NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-CODING VIOLATIONS-SECTION."
            ::= { optixTrapsEvent 36941 }
        
--  1.3.6.1.4.1.2011.2.25.3.20.40.20.36942
        evtTcaCVVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-CODING VIOLATION-VT PATH."
            ::= { optixTrapsEvent 36942 }
        
--  1.3.6.1.4.1.2011.2.25.3.20.40.20.36943
        evtTcaESCPPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-CP BIT ERROR SECONDS-PATH."
            ::= { optixTrapsEvent 36943 }
        
--  1.3.6.1.4.1.2011.2.25.3.20.40.20.36944
        evtTcaESLine NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-ERROR SECONDS-LINE."
            ::= { optixTrapsEvent 36944 }
        
--  1.3.6.1.4.1.2011.2.25.3.20.40.20.36945
        evtTcaESPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-ERROR SECONDS-PATH."
            ::= { optixTrapsEvent 36945 }
        
--  1.3.6.1.4.1.2011.2.25.3.20.40.20.36946
        evtTcaESPPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-ERROR SECONDS-PATH."
            ::= { optixTrapsEvent 36946 }
        
--  1.3.6.1.4.1.2011.2.25.3.20.40.20.36947
        evtTcaESSection NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-ERROR SECONDS-SECTION."
            ::= { optixTrapsEvent 36947 }
        
--  1.3.6.1.4.1.2011.2.25.3.20.40.20.36948
        evtTcaESVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-ERROR SECONDS-VT PATH."
            ::= { optixTrapsEvent 36948 }
        
--  1.3.6.1.4.1.2011.2.25.3.20.40.20.36949
        evtTcaPjcsPdet NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-POINTER JUSTIFICATION COUNT SECONDS-  PATH DETECT."
            ::= { optixTrapsEvent 36949 }
        
--  1.3.6.1.4.1.2011.2.25.3.20.40.20.36950
        evtTcaPjcsVdet NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-POINTER JUSTIFICATION COUNT SECONDS- VT PATH DETECT."
            ::= { optixTrapsEvent 36950 }
        
--  1.3.6.1.4.1.2011.2.25.3.20.40.20.36951
        evtTcaSESCPPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-CP BIT SEVERELY ERROR SECONDS-PATH."
            ::= { optixTrapsEvent 36951 }
        
--  1.3.6.1.4.1.2011.2.25.3.20.40.20.36952
        evtTcaSESLine NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-SEVERELY ERROR SECONDS- LINE."
            ::= { optixTrapsEvent 36952 }
        
--  1.3.6.1.4.1.2011.2.25.3.20.40.20.36953
        evtTcaSESPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-SEVERELY ERROR SECONDS- PATH."
            ::= { optixTrapsEvent 36953 }
        
--  1.3.6.1.4.1.2011.2.25.3.20.40.20.36954
        evtTcaSESPPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-SEVERELY ERROR SECONDS- PATH."
            ::= { optixTrapsEvent 36954 }
        
--  1.3.6.1.4.1.2011.2.25.3.20.40.20.36955
        evtTcaSESSection NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-SEVERELY ERROR SECONDS- SECTION."
            ::= { optixTrapsEvent 36955 }
        
--  1.3.6.1.4.1.2011.2.25.3.20.40.20.36956
        evtTcaSESVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-SEVERELY ERROR SECONDS- VT PATH."
            ::= { optixTrapsEvent 36956 }
        
--  1.3.6.1.4.1.2011.2.25.3.20.40.20.36957
        evtTcaUASCPPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-CP BIT UNAVAILABLE SECONDS-PATH."
            ::= { optixTrapsEvent 36957 }
        
--  1.3.6.1.4.1.2011.2.25.3.20.40.20.36958
        evtTcaUASLine NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-UNAVAILABLE SECONDS-LINE."
            ::= { optixTrapsEvent 36958 }
        
--  1.3.6.1.4.1.2011.2.25.3.20.40.20.36959
        evtTcaUASPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-UNAVAILABLE SECONDS-PATH."
            ::= { optixTrapsEvent 36959 }
        
--  1.3.6.1.4.1.2011.2.25.3.20.40.20.36960
        evtTcaUASPPath NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA - UNAVAILABLE SECONDS - PATH."
            ::= { optixTrapsEvent 36960 }
        
--  1.3.6.1.4.1.2011.2.25.3.20.40.20.36961
        evtTcaUASVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TCA-UNAVAILABLE SECONDS-VT PATH."
            ::= { optixTrapsEvent 36961 }
        
--  1.3.6.1.4.1.2011.2.25.3.20.40.20.36966
        evtBitsAIS NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: RX ALARM INDICATION SIGNAL."
            ::= { optixTrapsEvent 36966 }
        
--  1.3.6.1.4.1.2011.2.25.3.20.40.20.36967
        evtBitsLOF NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOSS OF FRAME."
            ::= { optixTrapsEvent 36967 }
        
--  1.3.6.1.4.1.2011.2.25.3.20.40.20.36968
        evtBitsLOS NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOSS OF SIGNAL."
            ::= { optixTrapsEvent 36968 }
        
--  1.3.6.1.4.1.2011.2.25.3.20.40.20.36969
        evtBitsCodeViolationOver NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: CODE VIOLATION OVER THRESHOLD."
            ::= { optixTrapsEvent 36969 }
        
--  1.3.6.1.4.1.2011.2.25.3.20.40.20.36970
        evtBlsrSFofRing NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: BLSR AUTO SWITCH OF RING -SF."
            ::= { optixTrapsEvent 36970 }
        
--  1.3.6.1.4.1.2011.2.25.3.20.40.20.36971
        evtBlsrSFofSpan NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: BLSR AUTO SWITCH OF SPAN -SF."
            ::= { optixTrapsEvent 36971 }
        
--  1.3.6.1.4.1.2011.2.25.3.20.40.20.36972
        evtBlsrSDofRing NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: BLSR AUTO SWITCH OF RING -SD."
            ::= { optixTrapsEvent 36972 }
        
--  1.3.6.1.4.1.2011.2.25.3.20.40.20.36973
        evtBlsrSDofSpan NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: BLSR AUTO SWITCH OF SPAN -SD."
            ::= { optixTrapsEvent 36973 }
        
--  1.3.6.1.4.1.2011.2.25.3.20.40.20.36974
        evtBlsrNodeIsolate NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: BLSR NODE ISOLATED."
            ::= { optixTrapsEvent 36974 }
        
--  1.3.6.1.4.1.2011.2.25.3.20.40.20.36975
        evtSF NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LAPS AUTO SWITCH -SF."
            ::= { optixTrapsEvent 36975 }
        
--  1.3.6.1.4.1.2011.2.25.3.20.40.20.36976
        evtSD NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LAPS AUTO SWITCH -SD."
            ::= { optixTrapsEvent 36976 }
        
--  1.3.6.1.4.1.2011.2.25.3.20.40.20.36977
        evtAutoSwitch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: AUTO SWITCH."
            ::= { optixTrapsEvent 36977 }
        
--  1.3.6.1.4.1.2011.2.25.3.20.40.20.36978
        evtLcasPlct NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PARTIAL LOSS OF CAPACITY TRANSMIT."
            ::= { optixTrapsEvent 36978 }

--  1.3.6.1.4.1.2011.2.25.3.20.40.20.36979
        evtLcasPlcr NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: PARTIAL LOSS OF CAPACITY RECEIVE."
            ::= { optixTrapsEvent 36979 }

--  1.3.6.1.4.1.2011.2.25.3.20.40.20.36980
        evtLcasTlct NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TOTAL LOSS OF CAPACITY TRANSMIT."
            ::= { optixTrapsEvent 36980 }

--  1.3.6.1.4.1.2011.2.25.3.20.40.20.36981
        evtLcasTlcr NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: TOTAL LOSS OF CAPACITY RECEIVE."
            ::= { optixTrapsEvent 36981 }

--  1.3.6.1.4.1.2011.2.25.3.20.40.20.36985
        evtLcasFopt NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: INDICATES A FAILURE IN TRANSMITTING LCAS PROTOCOL."
            ::= { optixTrapsEvent 36985 }
            
--  1.3.6.1.4.1.2011.2.25.3.20.40.20.36986
        evtLcasFopr NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: INDICATES A FAILURE IN RECEIVING LCAS PROTOCOL."
            ::= { optixTrapsEvent 36986 }
        
--  1.3.6.1.4.1.2011.2.25.3.20.40.20.40960
        evtLoopbackFAC2NI NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LOOPBACK,FAC2 NI."
            ::= { optixTrapsEvent 40960 }
            
--  1.3.6.1.4.1.2011.2.25.3.20.40.20.40961
        evtGfpCsf NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: GFP CLIENT LIENT SIGNAL FAIL INDICATION."
            ::= { optixTrapsEvent 40961 }
            
            
--  1.3.6.1.4.1.2011.2.25.3.20.40.20.40970
        evtRevertiveModeMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: REVERTIVE MODE MISMATCH."
            ::= { optixTrapsEvent 40970 }
            
--  1.3.6.1.4.1.2011.2.25.3.20.40.20.40971
        evtRingIDMismatch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: RING ID MISMATCH."
            ::= { optixTrapsEvent 40971 }
            
--  1.3.6.1.4.1.2011.2.25.3.20.40.20.40972
        evtIncorrectFiberConnection NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: INCORRECT FIBER CONNECTION FOR BLSR."
            ::= { optixTrapsEvent 40972 }
        
--  1.3.6.1.4.1.2011.2.25.3.20.40.20.40973
        evtStateChange NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: State Change."
            ::= { optixTrapsEvent 40973 }

--  1.3.6.1.4.1.2011.2.25.3.20.40.20.40974
        evtMtMode NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: The Entity Is In Maintenance State."
            ::= { optixTrapsEvent 40974 }
            
--  1.3.6.1.4.1.2011.2.25.3.20.40.20.40979
        evtRmvToMt NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: The Entity Is Removed To The Maintenance State."
            ::= { optixTrapsEvent 40979 }            
        
--  1.3.6.1.4.1.2011.2.25.3.20.40.20.40980
        evtRstFromMt NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: The Entity Restored From The Maintenance State."
            ::= { optixTrapsEvent 40980 }
            
--  1.3.6.1.4.1.2011.2.25.3.20.40.20.40981
        evtLpbk NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LoopBack Operated."
            ::= { optixTrapsEvent 40981 }
            
--  1.3.6.1.4.1.2011.2.25.3.20.40.20.40982
        evtRlsLpbk NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: LoopBack Released."
            ::= { optixTrapsEvent 40982 }           

            
--  1.3.6.1.4.1.2011.2.25.3.20.40.20.40983
        evtSyncNotSyncnronized NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: THE SYSTEM CLOCK CANNOT BE SYNCHRONIZED WITH THE TIMING SOURCE."
            ::= { optixTrapsEvent 40983 }

--  1.3.6.1.4.1.2011.2.25.3.20.40.20.40984
        evtPowerExceed NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: THE POWER EXCEED FOR INSERTED CARDS."
            ::= { optixTrapsEvent 40984 }

--  1.3.6.1.4.1.2011.2.25.3.20.40.20.40985
        evtPartialUnprotected NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: SOME SERVICES ON THIS UNIT ARE NOT PROTECTED."
            ::= { optixTrapsEvent 40985 }
            
--  1.3.6.1.4.1.2011.2.25.3.20.40.20.40986
        evtFanMea NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: THE FAN DOES NOT MEET THE HEAT DISSIPATION REQUIRMENTS."
            ::= { optixTrapsEvent 40986 }
                                                        
--  1.3.6.1.4.1.2011.2.25.3.20.40.20.63604
        evtRemoteClientSF NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Remote Client Singal Fail Alarm Indication."
            ::= { optixTrapsEvent 63604 }
        
--  1.3.6.1.4.1.2011.2.25.3.20.40.20.63605
        evtRemoteClientSD NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Remote Client Singal Degrade Alarm Indication."
            ::= { optixTrapsEvent 63605 }
        
--  1.3.6.1.4.1.2011.2.25.3.20.40.20.63607
        evtPowerSwitch NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Backup power use alarm."
            ::= { optixTrapsEvent 63607 }
        
--  1.3.6.1.4.1.2011.2.25.3.20.40.20.63629
        evtPortOffline NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: Pluggable port offline."
            ::= { optixTrapsEvent 63629 }
        
--  1.3.6.1.4.1.2011.2.25.3.20.40.20.63630
        evtDataLost NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: No Ethernet data received or transmited.."
            ::= { optixTrapsEvent 63630 }
        
--  1.3.6.1.4.1.2011.2.25.3.20.40.20.65409
        evtSqmVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: K4 MUITIFRAME SEQUENCE NUMBER MISMATCHED."
            ::= { optixTrapsEvent 65409 }
        
--  1.3.6.1.4.1.2011.2.25.3.20.40.20.65410
        evtLomVT NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: K4 MULTIFRAME LOST."
            ::= { optixTrapsEvent 65410 }
        
--  1.3.6.1.4.1.2011.2.25.3.20.40.20.65411
        evtFCSError NOTIFICATION-TYPE
            OBJECTS { rptEvtMOD2, rptEvtSlot, rptEvtPort, rptEvtPath, rptEvtVT, 
                rptEvtEffect, rptEvtDateTime, rptEvtLocation, rptEvtDirection, rptEvtMonValue, 
                rptEvtThValue, rptEvtPeriod, rptEvtDescription, rptEvtAiddet, rptEvtSeqNumber
                 }
            STATUS current
            DESCRIPTION 
                "Trap of Event: FRAME-CHECK SEQUENCE ERROR."
            ::= { optixTrapsEvent 65411 } 
            

-- BBBBBBBBBBBBBBBBBBBBBBBBBBBBBBBBBBBBBBBBBBBBBBBBBBBBBBBBBBBBBBBBBBBBBBBBBBBB
-- Event trap definition end.
-- BBBBBBBBBBBBBBBBBBBBBBBBBBBBBBBBBBBBBBBBBBBBBBBBBBBBBBBBBBBBBBBBBBBBBBBBBBBB
-- -------------------------------------------------------------------------
--  REPT^ALM^ENV
-- -------------------------------------------------------------------------
-- CCCCCCCCCCCCCCCCCCCCCCCCCCCCCCCCCCCCCCCCCCCCCCCCCCCCCCCCCCCCCCCCCCCCCCCCCCCC
-- Environment trap definition begin.
-- CCCCCCCCCCCCCCCCCCCCCCCCCCCCCCCCCCCCCCCCCCCCCCCCCCCCCCCCCCCCCCCCCCCCCCCCCCCC

        -- 1.3.6.1.4.1.2011.2.25.3.20.40.30
        optixTrapsEnvironment OBJECT IDENTIFIER ::= { optixSonetTraps 30 }
        
        -- 1.3.6.1.4.1.2011.2.25.3.20.40.30.502
        envAirCompressorFailure NOTIFICATION-TYPE
            OBJECTS { rptEvtNumber, rptEvtState, rptEvtDateTime, rptEvtDescription, rptEvtSeqNumber }
            STATUS current
            DESCRIPTION 
                "Trap of Environment: AIR COMPRESSOR FAILURE."
            ::= { optixTrapsEnvironment 502 }
        
        -- 1.3.6.1.4.1.2011.2.25.3.20.40.30.503
        envAirConditioningFailure NOTIFICATION-TYPE
            OBJECTS { rptEvtNumber, rptEvtState, rptEvtDateTime, rptEvtDescription, rptEvtSeqNumber }
            STATUS current
            DESCRIPTION 
                "Trap of Environment: AIR CONDITIONING FAILURE."
            ::= { optixTrapsEnvironment 503 }
        
        -- 1.3.6.1.4.1.2011.2.25.3.20.40.30.504
        envAirDryerFailure NOTIFICATION-TYPE
            OBJECTS { rptEvtNumber, rptEvtState, rptEvtDateTime, rptEvtDescription, rptEvtSeqNumber }
            STATUS current
            DESCRIPTION 
                "Trap of Environment: AIR DRYER FAILURE."
            ::= { optixTrapsEnvironment 504 }
        
        -- 1.3.6.1.4.1.2011.2.25.3.20.40.30.505
        envBatteryDischarging NOTIFICATION-TYPE
            OBJECTS { rptEvtNumber, rptEvtState, rptEvtDateTime, rptEvtDescription, rptEvtSeqNumber }
            STATUS current
            DESCRIPTION 
                "Trap of Environment: BATTERY DISCHARGING."
            ::= { optixTrapsEnvironment 505 }
        
        -- 1.3.6.1.4.1.2011.2.25.3.20.40.30.506
        envBatteryFailure NOTIFICATION-TYPE
            OBJECTS { rptEvtNumber, rptEvtState, rptEvtDateTime, rptEvtDescription, rptEvtSeqNumber }
            STATUS current
            DESCRIPTION 
                "Trap of Environment: BATTERY FAILURE."
            ::= { optixTrapsEnvironment 506 }
        
        -- 1.3.6.1.4.1.2011.2.25.3.20.40.30.507
        envCoolingFacFailure NOTIFICATION-TYPE
            OBJECTS { rptEvtNumber, rptEvtState, rptEvtDateTime, rptEvtDescription, rptEvtSeqNumber }
            STATUS current
            DESCRIPTION 
                "Trap of Environment: COOLING FAN FAILURE."
            ::= { optixTrapsEnvironment 507 }
        
        -- 1.3.6.1.4.1.2011.2.25.3.20.40.30.508
        envCPMAJOR NOTIFICATION-TYPE
            OBJECTS { rptEvtNumber, rptEvtState, rptEvtDateTime, rptEvtDescription, rptEvtSeqNumber }
            STATUS current
            DESCRIPTION 
                "Trap of Environment: CENTRALIZED POWER MAJOR ENVIRONMENTAL ALARM OR MAJOR."
            ::= { optixTrapsEnvironment 508 }
        
        -- 1.3.6.1.4.1.2011.2.25.3.20.40.30.509
        envCPMINOR NOTIFICATION-TYPE
            OBJECTS { rptEvtNumber, rptEvtState, rptEvtDateTime, rptEvtDescription, rptEvtSeqNumber }
            STATUS current
            DESCRIPTION 
                "Trap of Environment: CENTRALIZED POWER MINOR ENVIRONMENTAL ALARM OR MINOR."
            ::= { optixTrapsEnvironment 509 }
        
        -- 1.3.6.1.4.1.2011.2.25.3.20.40.30.510
        envEngineFailure NOTIFICATION-TYPE
            OBJECTS { rptEvtNumber, rptEvtState, rptEvtDateTime, rptEvtDescription, rptEvtSeqNumber }
            STATUS current
            DESCRIPTION 
                "Trap of Environment: ENGINE FAILURE."
            ::= { optixTrapsEnvironment 510 }
        
        -- 1.3.6.1.4.1.2011.2.25.3.20.40.30.511
        envEngineOperating NOTIFICATION-TYPE
            OBJECTS { rptEvtNumber, rptEvtState, rptEvtDateTime, rptEvtDescription, rptEvtSeqNumber }
            STATUS current
            DESCRIPTION 
                "Trap of Environment: ENGINE OPERATING."
            ::= { optixTrapsEnvironment 511 }
        
        -- 1.3.6.1.4.1.2011.2.25.3.20.40.30.512
        envExplosiveGas NOTIFICATION-TYPE
            OBJECTS { rptEvtNumber, rptEvtState, rptEvtDateTime, rptEvtDescription, rptEvtSeqNumber }
            STATUS current
            DESCRIPTION 
                "Trap of Environment: EXPLOSIVE GAS."
            ::= { optixTrapsEnvironment 512 }
        
        -- 1.3.6.1.4.1.2011.2.25.3.20.40.30.513
        envFireDetectorFailure NOTIFICATION-TYPE
            OBJECTS { rptEvtNumber, rptEvtState, rptEvtDateTime, rptEvtDescription, rptEvtSeqNumber }
            STATUS current
            DESCRIPTION 
                "Trap of Environment: FIRE DETECTOR FAILURE."
            ::= { optixTrapsEnvironment 513 }
        
        -- 1.3.6.1.4.1.2011.2.25.3.20.40.30.514
        envFire NOTIFICATION-TYPE
            OBJECTS { rptEvtNumber, rptEvtState, rptEvtDateTime, rptEvtDescription, rptEvtSeqNumber }
            STATUS current
            DESCRIPTION 
                "Trap of Environment: FIRE."
            ::= { optixTrapsEnvironment 514 }
        
        -- 1.3.6.1.4.1.2011.2.25.3.20.40.30.515
        envFlood NOTIFICATION-TYPE
            OBJECTS { rptEvtNumber, rptEvtState, rptEvtDateTime, rptEvtDescription, rptEvtSeqNumber }
            STATUS current
            DESCRIPTION 
                "Trap of Environment: FLOOD."
            ::= { optixTrapsEnvironment 515 }
        
        -- 1.3.6.1.4.1.2011.2.25.3.20.40.30.516
        envFuseFailure NOTIFICATION-TYPE
            OBJECTS { rptEvtNumber, rptEvtState, rptEvtDateTime, rptEvtDescription, rptEvtSeqNumber }
            STATUS current
            DESCRIPTION 
                "Trap of Environment: FUSE FAILURE."
            ::= { optixTrapsEnvironment 516 }
        
        -- 1.3.6.1.4.1.2011.2.25.3.20.40.30.517
        envGeneratorFailure NOTIFICATION-TYPE
            OBJECTS { rptEvtNumber, rptEvtState, rptEvtDateTime, rptEvtDescription, rptEvtSeqNumber }
            STATUS current
            DESCRIPTION 
                "Trap of Environment: GENERATOR FAILURE."
            ::= { optixTrapsEnvironment 517 }
        
        -- 1.3.6.1.4.1.2011.2.25.3.20.40.30.518
        envHighAirflow NOTIFICATION-TYPE
            OBJECTS { rptEvtNumber, rptEvtState, rptEvtDateTime, rptEvtDescription, rptEvtSeqNumber }
            STATUS current
            DESCRIPTION 
                "Trap of Environment: HIGH AIRFLOW."
            ::= { optixTrapsEnvironment 518 }
        
        -- 1.3.6.1.4.1.2011.2.25.3.20.40.30.519
        envHighHumidity NOTIFICATION-TYPE
            OBJECTS { rptEvtNumber, rptEvtState, rptEvtDateTime, rptEvtDescription, rptEvtSeqNumber }
            STATUS current
            DESCRIPTION 
                "Trap of Environment: HIGH HUMIDITY."
            ::= { optixTrapsEnvironment 519 }
        
        -- 1.3.6.1.4.1.2011.2.25.3.20.40.30.520
        envHighTemperature NOTIFICATION-TYPE
            OBJECTS { rptEvtNumber, rptEvtState, rptEvtDateTime, rptEvtDescription, rptEvtSeqNumber }
            STATUS current
            DESCRIPTION 
                "Trap of Environment: HIGH TEMPERATURE."
            ::= { optixTrapsEnvironment 520 }
        
        -- 1.3.6.1.4.1.2011.2.25.3.20.40.30.521
        envHighWater NOTIFICATION-TYPE
            OBJECTS { rptEvtNumber, rptEvtState, rptEvtDateTime, rptEvtDescription, rptEvtSeqNumber }
            STATUS current
            DESCRIPTION 
                "Trap of Environment: HIGH WATER."
            ::= { optixTrapsEnvironment 521 }
        
        -- 1.3.6.1.4.1.2011.2.25.3.20.40.30.522
        envIntrusion NOTIFICATION-TYPE
            OBJECTS { rptEvtNumber, rptEvtState, rptEvtDateTime, rptEvtDescription, rptEvtSeqNumber }
            STATUS current
            DESCRIPTION 
                "Trap of Environment: INTRUSION."
            ::= { optixTrapsEnvironment 522 }
        
        -- 1.3.6.1.4.1.2011.2.25.3.20.40.30.523
        envLowBatteryVoltage NOTIFICATION-TYPE
            OBJECTS { rptEvtNumber, rptEvtState, rptEvtDateTime, rptEvtDescription, rptEvtSeqNumber }
            STATUS current
            DESCRIPTION 
                "Trap of Environment: LOW BATTERY VOLTAGE."
            ::= { optixTrapsEnvironment 523 }
        
        -- 1.3.6.1.4.1.2011.2.25.3.20.40.30.524
        envLowFuel NOTIFICATION-TYPE
            OBJECTS { rptEvtNumber, rptEvtState, rptEvtDateTime, rptEvtDescription, rptEvtSeqNumber }
            STATUS current
            DESCRIPTION 
                "Trap of Environment: LOW FUEL."
            ::= { optixTrapsEnvironment 524 }
        
        -- 1.3.6.1.4.1.2011.2.25.3.20.40.30.525
        envLowHumidity NOTIFICATION-TYPE
            OBJECTS { rptEvtNumber, rptEvtState, rptEvtDateTime, rptEvtDescription, rptEvtSeqNumber }
            STATUS current
            DESCRIPTION 
                "Trap of Environment: LOW HUMIDITY."
            ::= { optixTrapsEnvironment 525 }
        
        -- 1.3.6.1.4.1.2011.2.25.3.20.40.30.526
        envLowCablePressure NOTIFICATION-TYPE
            OBJECTS { rptEvtNumber, rptEvtState, rptEvtDateTime, rptEvtDescription, rptEvtSeqNumber }
            STATUS current
            DESCRIPTION 
                "Trap of Environment: LOW CABLE PRESSURE."
            ::= { optixTrapsEnvironment 526 }
        
        -- 1.3.6.1.4.1.2011.2.25.3.20.40.30.527
        envLowTemperature NOTIFICATION-TYPE
            OBJECTS { rptEvtNumber, rptEvtState, rptEvtDateTime, rptEvtDescription, rptEvtSeqNumber }
            STATUS current
            DESCRIPTION 
                "Trap of Environment: LOW TEMPERATURE."
            ::= { optixTrapsEnvironment 527 }
        
        -- 1.3.6.1.4.1.2011.2.25.3.20.40.30.528
        envLowWater NOTIFICATION-TYPE
            OBJECTS { rptEvtNumber, rptEvtState, rptEvtDateTime, rptEvtDescription, rptEvtSeqNumber }
            STATUS current
            DESCRIPTION 
                "Trap of Environment: LOW WATER."
            ::= { optixTrapsEnvironment 528 }
        
        -- 1.3.6.1.4.1.2011.2.25.3.20.40.30.529
        envMiscellaneous NOTIFICATION-TYPE
            OBJECTS { rptEvtNumber, rptEvtState, rptEvtDateTime, rptEvtDescription, rptEvtSeqNumber }
            STATUS current
            DESCRIPTION 
                "Trap of Environment: MISCELLANEOUS."
            ::= { optixTrapsEnvironment 529 }
        
        -- 1.3.6.1.4.1.2011.2.25.3.20.40.30.530
        envOpenDoor NOTIFICATION-TYPE
            OBJECTS { rptEvtNumber, rptEvtState, rptEvtDateTime, rptEvtDescription, rptEvtSeqNumber }
            STATUS current
            DESCRIPTION 
                "Trap of Environment: OPEN DOOR."
            ::= { optixTrapsEnvironment 530 }
        
        -- 1.3.6.1.4.1.2011.2.25.3.20.40.30.531
        envCommercialPowerFailure NOTIFICATION-TYPE
            OBJECTS { rptEvtNumber, rptEvtState, rptEvtDateTime, rptEvtDescription, rptEvtSeqNumber }
            STATUS current
            DESCRIPTION 
                "Trap of Environment: COMMERCIAL POWER FAILURE."
            ::= { optixTrapsEnvironment 531 }
        
        -- 1.3.6.1.4.1.2011.2.25.3.20.40.30.532
        envPumpFailure NOTIFICATION-TYPE
            OBJECTS { rptEvtNumber, rptEvtState, rptEvtDateTime, rptEvtDescription, rptEvtSeqNumber }
            STATUS current
            DESCRIPTION 
                "Trap of Environment: PUMP FAILURE."
            ::= { optixTrapsEnvironment 532 }
        
        -- 1.3.6.1.4.1.2011.2.25.3.20.40.30.536
        env48VoltPowerSupplyFailure NOTIFICATION-TYPE
            OBJECTS { rptEvtNumber, rptEvtState, rptEvtDateTime, rptEvtDescription, rptEvtSeqNumber }
            STATUS current
            DESCRIPTION 
                "Trap of Environment: 48 VOLT POWER SUPPLY FAILURE."
            ::= { optixTrapsEnvironment 536 }
        
        -- 1.3.6.1.4.1.2011.2.25.3.20.40.30.537
        envRectifierFailure NOTIFICATION-TYPE
            OBJECTS { rptEvtNumber, rptEvtState, rptEvtDateTime, rptEvtDescription, rptEvtSeqNumber }
            STATUS current
            DESCRIPTION 
                "Trap of Environment: RECTIFIER FAILURE."
            ::= { optixTrapsEnvironment 537 }
        
        -- 1.3.6.1.4.1.2011.2.25.3.20.40.30.538
        envRectifierHighVoltage NOTIFICATION-TYPE
            OBJECTS { rptEvtNumber, rptEvtState, rptEvtDateTime, rptEvtDescription, rptEvtSeqNumber }
            STATUS current
            DESCRIPTION 
                "Trap of Environment: RECTIFIER HIGH VOLTAGE."
            ::= { optixTrapsEnvironment 538 }
        
        -- 1.3.6.1.4.1.2011.2.25.3.20.40.30.539
        envRectiFierLowVoltage NOTIFICATION-TYPE
            OBJECTS { rptEvtNumber, rptEvtState, rptEvtDateTime, rptEvtDescription, rptEvtSeqNumber }
            STATUS current
            DESCRIPTION 
                "Trap of Environment: RECTIFIER LOW VOLTAGE."
            ::= { optixTrapsEnvironment 539 }
        
        -- 1.3.6.1.4.1.2011.2.25.3.20.40.30.540
        envSmoke NOTIFICATION-TYPE
            OBJECTS { rptEvtNumber, rptEvtState, rptEvtDateTime, rptEvtDescription, rptEvtSeqNumber }
            STATUS current
            DESCRIPTION 
                "Trap of Environment: SMOKE."
            ::= { optixTrapsEnvironment 540 }
        
        -- 1.3.6.1.4.1.2011.2.25.3.20.40.30.541
        envToxicGas NOTIFICATION-TYPE
            OBJECTS { rptEvtNumber, rptEvtState, rptEvtDateTime, rptEvtDescription, rptEvtSeqNumber }
            STATUS current
            DESCRIPTION 
                "Trap of Environment: TOXIC GAS."
            ::= { optixTrapsEnvironment 541 }
        
        -- 1.3.6.1.4.1.2011.2.25.3.20.40.30.542
        envVentilationSystemFailure NOTIFICATION-TYPE
            OBJECTS { rptEvtNumber, rptEvtState, rptEvtDateTime, rptEvtDescription, rptEvtSeqNumber }
            STATUS current
            DESCRIPTION 
                "Trap of Environment: VENTILATION SYSTEM FAILURE."
            ::= { optixTrapsEnvironment 542 }

-- CCCCCCCCCCCCCCCCCCCCCCCCCCCCCCCCCCCCCCCCCCCCCCCCCCCCCCCCCCCCCCCCCCCCCCCCCCCC
-- Environment trap definition end.
-- CCCCCCCCCCCCCCCCCCCCCCCCCCCCCCCCCCCCCCCCCCCCCCCCCCCCCCCCCCCCCCCCCCCCCCCCCCCC
-- -------------------------------------------------------------------------
--  REPT^PM
-- -------------------------------------------------------------------------
-- DDDDDDDDDDDDDDDDDDDDDDDDDDDDDDDDDDDDDDDDDDDDDDDDDDDDDDDDDDDDDDDDDDDDDDDDDDDD
-- Performance trap definition begin.
-- DDDDDDDDDDDDDDDDDDDDDDDDDDDDDDDDDDDDDDDDDDDDDDDDDDDDDDDDDDDDDDDDDDDDDDDDDDDD
        
        -- 1.3.6.1.4.1.2011.2.25.3.20.40.40
        optixTrapsPerformance OBJECT IDENTIFIER ::= { optixSonetTraps 40 }
        
        -- 1.3.6.1.4.1.2011.2.25.3.20.40.40.32770
        pmSESSection NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Severely errored second-section."
            ::= { optixTrapsPerformance 32770 }
        
        -- 1.3.6.1.4.1.2011.2.25.3.20.40.40.32784
        pmCVLine NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Code voilation-line."
            ::= { optixTrapsPerformance 32784 }
        
        -- 1.3.6.1.4.1.2011.2.25.3.20.40.40.32785
        pmESLine NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Errored second-line."
            ::= { optixTrapsPerformance 32785 }
        
        -- 1.3.6.1.4.1.2011.2.25.3.20.40.40.32786
        pmSESLine NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Severely errored second-line."
            ::= { optixTrapsPerformance 32786 }
        
        -- 1.3.6.1.4.1.2011.2.25.3.20.40.40.32789
        pmUASLine NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Unavailable second-line."
            ::= { optixTrapsPerformance 32789 }
        
        -- 1.3.6.1.4.1.2011.2.25.3.20.40.40.32799
        pmPSD NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Protection switching duration."
            ::= { optixTrapsPerformance 32799 }
        
        -- 1.3.6.1.4.1.2011.2.25.3.20.40.40.32800
        pmCVPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Code voilation-path."
            ::= { optixTrapsPerformance 32800 }
        
        -- 1.3.6.1.4.1.2011.2.25.3.20.40.40.32801
        pmESPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Errored second-path."
            ::= { optixTrapsPerformance 32801 }
        
        -- 1.3.6.1.4.1.2011.2.25.3.20.40.40.32852
        pmPjcsVdet NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Pointer justification  count second-VT path detected."
            ::= { optixTrapsPerformance 32852 }
        
        -- 1.3.6.1.4.1.2011.2.25.3.20.40.40.32992
        pmBdTempCur NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Board temperature current."
            ::= { optixTrapsPerformance 32992 }
        
        -- 1.3.6.1.4.1.2011.2.25.3.20.40.40.32993
        pmBdTempMax NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Board temperature Maximum."
            ::= { optixTrapsPerformance 32993 }
        
        -- 1.3.6.1.4.1.2011.2.25.3.20.40.40.32994
        pmBdTempMin NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Board temperature Minimum."
            ::= { optixTrapsPerformance 32994 }
        
        -- 1.3.6.1.4.1.2011.2.25.3.20.40.40.33000
        pmPmuTempCur NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: PIU Board temperature current."
            ::= { optixTrapsPerformance 33000 }
        
        -- 1.3.6.1.4.1.2011.2.25.3.20.40.40.33001
        pmPmuTempMax NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: PIU Board temperature Maximum."
            ::= { optixTrapsPerformance 33001 }
        
        -- 1.3.6.1.4.1.2011.2.25.3.20.40.40.33002
        pmPmuTempMin NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: PIU Board temperature Minimum."
            ::= { optixTrapsPerformance 33002 }
        
        -- 1.3.6.1.4.1.2011.2.25.3.20.40.40.33008
        pmLbcCur NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser Bias Current."
            ::= { optixTrapsPerformance 33008 }
        
        -- 1.3.6.1.4.1.2011.2.25.3.20.40.40.33009
        pmLbcMax NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser Bias Maximum."
            ::= { optixTrapsPerformance 33009 }
        
        -- 1.3.6.1.4.1.2011.2.25.3.20.40.40.33010
        pmLbcMin NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser Bias Minimum."
            ::= { optixTrapsPerformance 33010 }
        
        -- 1.3.6.1.4.1.2011.2.25.3.20.40.40.33011
        pmOptCur NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Optical Power Transmitted current."
            ::= { optixTrapsPerformance 33011 }
        
        -- 1.3.6.1.4.1.2011.2.25.3.20.40.40.33012
        pmOptMax NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Optical Power Transmitted Maximum."
            ::= { optixTrapsPerformance 33012 }
        
        -- 1.3.6.1.4.1.2011.2.25.3.20.40.40.33013
        pmOptMin NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Optical Power Transmitted Minimum."
            ::= { optixTrapsPerformance 33013 }
        
        -- 1.3.6.1.4.1.2011.2.25.3.20.40.40.33014
        pmOprCur NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Optical Power Received current."
            ::= { optixTrapsPerformance 33014 }
        
        -- 1.3.6.1.4.1.2011.2.25.3.20.40.40.33015
        pmOprMax NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Optical Power Received Maximum."
            ::= { optixTrapsPerformance 33015 }
        
        -- 1.3.6.1.4.1.2011.2.25.3.20.40.40.33016
        pmOprMin NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Optical Power Received Minimum."
            ::= { optixTrapsPerformance 33016 }
        
        -- 1.3.6.1.4.1.2011.2.25.3.20.40.40.33056
        pmCVPPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Code voilation-path,P-bit."
            ::= { optixTrapsPerformance 33056 }
        
        -- 1.3.6.1.4.1.2011.2.25.3.20.40.40.33057
        pmCVCPPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Code voilation-path,CP-bit."
            ::= { optixTrapsPerformance 33057 }
        
        -- 1.3.6.1.4.1.2011.2.25.3.20.40.40.33058
        pmESPPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Errored second-path ,P-bit."
            ::= { optixTrapsPerformance 33058 }
        
        -- 1.3.6.1.4.1.2011.2.25.3.20.40.40.33059
        pmESCPPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Errored second-path ,CP-bit."
            ::= { optixTrapsPerformance 33059 }
        
        -- 1.3.6.1.4.1.2011.2.25.3.20.40.40.33060
        pmSESPPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Severely errored second-path ,P-bit."
            ::= { optixTrapsPerformance 33060 }
        
        -- 1.3.6.1.4.1.2011.2.25.3.20.40.40.33061
        pmSESCPPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Severely errored second-path ,CP-bit."
            ::= { optixTrapsPerformance 33061 }
        
        -- 1.3.6.1.4.1.2011.2.25.3.20.40.40.33064
        pmUASPPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Unavailable second-path ,P-bit."
            ::= { optixTrapsPerformance 33064 }
        
        -- 1.3.6.1.4.1.2011.2.25.3.20.40.40.33065
        pmUASCPPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Unavailable second-path ,CP-bit."
            ::= { optixTrapsPerformance 33065 }
        
        -- 1.3.6.1.4.1.2011.2.25.3.20.40.40.33088
        pmPscProtection NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: 2-fiber BLSR Protection switching count."
            ::= { optixTrapsPerformance 33088 }
        
        -- 1.3.6.1.4.1.2011.2.25.3.20.40.40.33089
        pmPsdProtection NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: 2-fiber BLSR Protection swithing duration."
            ::= { optixTrapsPerformance 33089 }
        
        -- 1.3.6.1.4.1.2011.2.25.3.20.40.40.33090
        pmPscSpan NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: 4-fiber BLSR Protection span switching count."
            ::= { optixTrapsPerformance 33090 }
        
        -- 1.3.6.1.4.1.2011.2.25.3.20.40.40.33091
        pmPsdSpan NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: 4-fiber BLSR Protection span switching duration."
            ::= { optixTrapsPerformance 33091 }
        
        -- 1.3.6.1.4.1.2011.2.25.3.20.40.40.33092
        pmPscRing NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: 4-fiber BLSR Protection ring switching count."
            ::= { optixTrapsPerformance 33092 }
        
        -- 1.3.6.1.4.1.2011.2.25.3.20.40.40.33093
        pmPsdRing NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: 4-fiber BLSR Protection ring switching duration."
            ::= { optixTrapsPerformance 33093 }
        
        -- 1.3.6.1.4.1.2011.2.25.3.20.40.40.33094
        pmPscWork NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: BLSR work switching count."
            ::= { optixTrapsPerformance 33094 }
        
        -- 1.3.6.1.4.1.2011.2.25.3.20.40.40.33095
        pmPsdWork NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: BLSR work switching duration."
            ::= { optixTrapsPerformance 33095 }
        
        -- 1.3.6.1.4.1.2011.2.25.3.20.40.40.36864
        pmLCCCur NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser Diode Cooling Current."
            ::= { optixTrapsPerformance 36864 }
        
        -- 1.3.6.1.4.1.2011.2.25.3.20.40.40.36865
        pmLCCMax NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser Diode Cooling Maximum."
            ::= { optixTrapsPerformance 36865 }
        
        -- 1.3.6.1.4.1.2011.2.25.3.20.40.40.36866
        pmLCCMin NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser Diode Cooling Minimum."
            ::= { optixTrapsPerformance 36866 }
        
        -- 1.3.6.1.4.1.2011.2.25.3.20.40.40.36867
        pmLTEMPCur NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser Temperature Current."
            ::= { optixTrapsPerformance 36867 }
        
        -- 1.3.6.1.4.1.2011.2.25.3.20.40.40.36868
        pmLTEMPMax NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser Temperature Maximum."
            ::= { optixTrapsPerformance 36868 }
        
        -- 1.3.6.1.4.1.2011.2.25.3.20.40.40.36869
        pmLTEMPMin NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser Temperature Minimum."
            ::= { optixTrapsPerformance 36869 }
        
        -- 1.3.6.1.4.1.2011.2.25.3.20.40.40.36870
        pmLAPDBVCur NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser APD Bias Voltage Current."
            ::= { optixTrapsPerformance 36870 }
        
        -- 1.3.6.1.4.1.2011.2.25.3.20.40.40.36871
        pmLAPDBVMax NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser APD Bias Voltage Maximum."
            ::= { optixTrapsPerformance 36871 }
        
        -- 1.3.6.1.4.1.2011.2.25.3.20.40.40.36872
        pmLAPDBVMin NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Laser APD Bias Voltage Minimum."
            ::= { optixTrapsPerformance 36872 }
        
        -- 1.3.6.1.4.1.2011.2.25.3.20.40.40.36873
        pmPLBCCur NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Pump Laser Back Face Monitor Current."
            ::= { optixTrapsPerformance 36873 }
        
        -- 1.3.6.1.4.1.2011.2.25.3.20.40.40.36874
        pmPLBCMax NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Pump Laser Back Face Monitor Current  Maximum."
            ::= { optixTrapsPerformance 36874 }
        
        -- 1.3.6.1.4.1.2011.2.25.3.20.40.40.36875
        pmPLBCMin NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Pump Laser Back Face Monitor Current Minimum."
            ::= { optixTrapsPerformance 36875 }
        
        -- 1.3.6.1.4.1.2011.2.25.3.20.40.40.36876
        pmPLWCCur NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Pump Laser Work Current."
            ::= { optixTrapsPerformance 36876 }
        
        -- 1.3.6.1.4.1.2011.2.25.3.20.40.40.36877
        pmPLWCMax NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Pump Laser Work Current Maximum."
            ::= { optixTrapsPerformance 36877 }
        
        -- 1.3.6.1.4.1.2011.2.25.3.20.40.40.36878
        pmPLWCMin NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Pump Laser Work Current Minimum."
            ::= { optixTrapsPerformance 36878 }
        
        -- 1.3.6.1.4.1.2011.2.25.3.20.40.40.36879
        pmCVSection NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Code voilation-section."
            ::= { optixTrapsPerformance 36879 }
        
        -- 1.3.6.1.4.1.2011.2.25.3.20.40.40.36880
        pmESSection NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Errored second-section."
            ::= { optixTrapsPerformance 36880 }
        
        -- 1.3.6.1.4.1.2011.2.25.3.20.40.40.36881
        pmSESPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Severely errored second-path."
            ::= { optixTrapsPerformance 36881 }
        
        -- 1.3.6.1.4.1.2011.2.25.3.20.40.40.36882
        pmUASPath NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Unavailable second-path."
            ::= { optixTrapsPerformance 36882 }
        
        -- 1.3.6.1.4.1.2011.2.25.3.20.40.40.36883
        pmCVVT NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Code voilation-VT path."
            ::= { optixTrapsPerformance 36883 }
        
        -- 1.3.6.1.4.1.2011.2.25.3.20.40.40.36884
        pmESVT NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Errored Second-VT path."
            ::= { optixTrapsPerformance 36884 }
        
        -- 1.3.6.1.4.1.2011.2.25.3.20.40.40.36885
        pmSESVT NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Severely Errored Second-VT path."
            ::= { optixTrapsPerformance 36885 }
        
        -- 1.3.6.1.4.1.2011.2.25.3.20.40.40.36886
        pmUASVT NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Unavailable Second-VT path."
            ::= { optixTrapsPerformance 36886 }
        
        -- 1.3.6.1.4.1.2011.2.25.3.20.40.40.36887
        pmPSC NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Protection switching count."
            ::= { optixTrapsPerformance 36887 }
        
        -- 1.3.6.1.4.1.2011.2.25.3.20.40.40.45065
        pmPjcsPdet NOTIFICATION-TYPE
            OBJECTS { rptEvtMOD2, rptEvtSlot, rptEvtPort, rptEvtPath, rptEvtVT, 
                rptEvtMonValue, rptEvtVldty, rptEvtLocation, rptEvtDirection, rptEvtPeriod, 
                rptEvtDateTime }
            STATUS current
            DESCRIPTION 
                "Trap of Performance: Pointer justification  count second-STS path detected."
            ::= { optixTrapsPerformance 45065 }
        
-- DDDDDDDDDDDDDDDDDDDDDDDDDDDDDDDDDDDDDDDDDDDDDDDDDDDDDDDDDDDDDDDDDDDDDDDDDDDD
-- Performance trap definition end.
-- DDDDDDDDDDDDDDDDDDDDDDDDDDDDDDDDDDDDDDDDDDDDDDDDDDDDDDDDDDDDDDDDDDDDDDDDDDDD
-- ---------------------------------------------------------------------
-- optixTrapsCommon(for bindings table only)
-- ----------------------------------------------------------------------

        -- 1.3.6.1.4.1.2011.2.25.3.20.40.50
        optixTrapsCommon OBJECT IDENTIFIER ::= { optixSonetTraps 50 }
        
        -- 1.3.6.1.4.1.2011.2.25.3.20.40.50.10
        rptAlmName OBJECT-TYPE
            SYNTAX AlarmEventType
            MAX-ACCESS accessible-for-notify
            STATUS current
            DESCRIPTION
                "Alarm name."
            ::= { optixTrapsCommon 10 }
        
        -- 1.3.6.1.4.1.2011.2.25.3.20.40.50.20
        rptEvtMOD2 OBJECT-TYPE
            SYNTAX MOD2Type
            MAX-ACCESS accessible-for-notify
            STATUS current
            DESCRIPTION
                "Signal mode."
            ::= { optixTrapsCommon 20 }
        
        -- 1.3.6.1.4.1.2011.2.25.3.20.40.50.30
        rptEvtSlot OBJECT-TYPE
            SYNTAX Unsigned32
            MAX-ACCESS accessible-for-notify
            STATUS current
            DESCRIPTION
                "Slot number.
                
                This will indicate what is the slot 
                of the object which raised this event.
                If not relevant to the event, will be
                zero."
            ::= { optixTrapsCommon 30 }
        
        -- 1.3.6.1.4.1.2011.2.25.3.20.40.50.40
        rptEvtPort OBJECT-TYPE
            SYNTAX Unsigned32
            MAX-ACCESS accessible-for-notify
            STATUS current
            DESCRIPTION
                "Port Number.
                
                This will indicate what is the Port 
                of the object which raised this event.
                If not relevant to the event, will be
                zero."
            ::= { optixTrapsCommon 40 }
        
        -- 1.3.6.1.4.1.2011.2.25.3.20.40.50.50
        rptEvtPath OBJECT-TYPE
            SYNTAX Unsigned32
            MAX-ACCESS accessible-for-notify
            STATUS current
            DESCRIPTION
                "Path number.
                
                This will indicate what is the Path 
                of the object which raised this event.
                If not relevant to the event, will be
                zero."
            ::= { optixTrapsCommon 50 }
        
        -- 1.3.6.1.4.1.2011.2.25.3.20.40.50.70
        rptEvtVT OBJECT-TYPE
            SYNTAX Unsigned32
            MAX-ACCESS accessible-for-notify
            STATUS current
            DESCRIPTION
                "VT path number.
                
                This will indicate what is the VT path 
                of the object which raised this event.
                If not relevant to the event, will be
                zero."
            ::= { optixTrapsCommon 70 }
        
        -- 1.3.6.1.4.1.2011.2.25.3.20.40.50.80
        rptEvtDateTime OBJECT-TYPE
            SYNTAX DateAndTime
            MAX-ACCESS accessible-for-notify
            STATUS current
            DESCRIPTION
                "Date and time when the triggering event occurred."
            ::= { optixTrapsCommon 80 }
        
        -- 1.3.6.1.4.1.2011.2.25.3.20.40.50.90
        rptEvtSrvEff OBJECT-TYPE
            SYNTAX AlmDataSrvEffType
            MAX-ACCESS accessible-for-notify
            STATUS current
            DESCRIPTION
                "The effect on service caused by the alarm condition.
                Only NSA(Nonservice-effecting)|SA(Service-effecting) will be represented here."
            ::= { optixTrapsCommon 90 }
        
        -- 1.3.6.1.4.1.2011.2.25.3.20.40.50.100
        rptEvtNtfcnCde OBJECT-TYPE
            SYNTAX AlmDataNtfcnCdeType
            MAX-ACCESS accessible-for-notify
            STATUS current
            DESCRIPTION
                "The notification code of the alarm. 
                Only CR|MJ|MN|NA|NR will be represented here."
            ::= { optixTrapsCommon 100 }
        
        -- 1.3.6.1.4.1.2011.2.25.3.20.40.50.110
        rptEvtLocation OBJECT-TYPE
            SYNTAX LocationType
            MAX-ACCESS accessible-for-notify
            STATUS current
            DESCRIPTION
                "Indicates the location.
                Only NEND(Near end)|FEND(Far end)|ALL will be represented here."
            ::= { optixTrapsCommon 110 }
        
        -- 1.3.6.1.4.1.2011.2.25.3.20.40.50.120
        rptEvtDirection OBJECT-TYPE
            SYNTAX DirectionType
            MAX-ACCESS accessible-for-notify
            STATUS current
            DESCRIPTION
                "specifies the direction of monitoring.
                Only RCV(Receive direction)|TRMT(Transmit direction)|ALL will be represented here."
            ::= { optixTrapsCommon 120 }
        
        -- 1.3.6.1.4.1.2011.2.25.3.20.40.50.130
        rptEvtMonValue OBJECT-TYPE
            SYNTAX Integer32
            MAX-ACCESS accessible-for-notify
            STATUS current
            DESCRIPTION
                "Monitored value"
            ::= { optixTrapsCommon 130 }
        
        -- 1.3.6.1.4.1.2011.2.25.3.20.40.50.140
        rptEvtThValue OBJECT-TYPE
            SYNTAX Unsigned32
            MAX-ACCESS accessible-for-notify
            STATUS current
            DESCRIPTION
                "Indicates the threshold level."
            ::= { optixTrapsCommon 140 }
        
        -- 1.3.6.1.4.1.2011.2.25.3.20.40.50.150
        rptEvtDescription OBJECT-TYPE
            SYNTAX DisplayString
            MAX-ACCESS accessible-for-notify
            STATUS current
            DESCRIPTION
                "Description"
            ::= { optixTrapsCommon 150 }
        
        -- 1.3.6.1.4.1.2011.2.25.3.20.40.50.160
        rptEvtNumber OBJECT-TYPE
            SYNTAX Unsigned32
            MAX-ACCESS accessible-for-notify
            STATUS current
            DESCRIPTION
                "The numble of Alarm Message"
            ::= { optixTrapsCommon 160 }
        
        -- 1.3.6.1.4.1.2011.2.25.3.20.40.50.170
        rptEvtPeriod OBJECT-TYPE
            SYNTAX INTEGER
                {
                null(0),
                period15m(1),
                period1day(2)
                }
            MAX-ACCESS accessible-for-notify
            STATUS current
            DESCRIPTION
                "Specifies the accumulation time period for the PM information.
                Only period15m|period1day|NULL will be represented here."
            ::= { optixTrapsCommon 170 }
        
        -- 1.3.6.1.4.1.2011.2.25.3.20.40.50.180
        rptEvtVldty OBJECT-TYPE
            SYNTAX ValidflagType
            MAX-ACCESS accessible-for-notify
            STATUS current
            DESCRIPTION
                "It indicates whether the information 
                for the specified time period was 
                accumulated over the entire time period 
                or some portion of it.
                Only INVALID|VALID will be represented here."
            ::= { optixTrapsCommon 180 }
        
        -- 1.3.6.1.4.1.2011.2.25.3.20.40.50.190
        rptEvtEffect OBJECT-TYPE
            SYNTAX INTEGER
                {
                tc(6),
                sc(7),
                cl(8)
                }
            MAX-ACCESS accessible-for-notify
            STATUS current
            DESCRIPTION
                "indicates the effect of the event on the condition of the NE.
                Only TC(Transient Condition)|SC(Raised Condition)|CL(Cleared Condition) will be represented here."
            ::= { optixTrapsCommon 190 }
        
        -- 1.3.6.1.4.1.2011.2.25.3.20.40.50.200
        rptEvtState OBJECT-TYPE
            SYNTAX INTEGER
                {
                start(1),
                clear(3)
                }
            MAX-ACCESS accessible-for-notify
            STATUS current
            DESCRIPTION
                "The state of alarm.
                Only START|CL(Cleared) will be represented here."
            ::= { optixTrapsCommon 200 }
        
        -- 1.3.6.1.4.1.2011.2.25.3.20.40.50.210
        rptEvtAiddet OBJECT-TYPE
            SYNTAX Unsigned32
            MAX-ACCESS accessible-for-notify
            STATUS current
            DESCRIPTION
                "The supplementary equipment identification used to identify the 
                location of the reported trouble. This is used in conjunction with 
                the AID."
            ::= { optixTrapsCommon 210 }
        
        -- 1.3.6.1.4.1.2011.2.25.3.20.40.50.220
        rptEvtSeqNumber OBJECT-TYPE
            SYNTAX Unsigned32
            MAX-ACCESS accessible-for-notify
            STATUS current
            DESCRIPTION
                "The sequence numble of report message."
            ::= { optixTrapsCommon 220 }
        
        -- 1.3.6.1.4.1.2011.2.25.3.20.40.50.230
        rptPmName OBJECT-TYPE
            SYNTAX PerformanceEventType
            MAX-ACCESS accessible-for-notify
            STATUS current
            DESCRIPTION
                "PM name."
            ::= { optixTrapsCommon 230 }
        
        -- 1.3.6.1.4.1.2011.2.25.3.20.40.60
        optixSonetTrapsConformance OBJECT IDENTIFIER ::= { optixSonetTraps 60 }
        
        -- 1.3.6.1.4.1.2011.2.25.3.20.40.60.1
        optixSonetTrapsGroups OBJECT IDENTIFIER ::= { optixSonetTrapsConformance 1 }
        
        -- 1.3.6.1.4.1.2011.2.25.3.20.40.60.1.1
        optixSonetTrapsObjectGroup OBJECT-GROUP
            OBJECTS { rptAlmName, rptEvtMOD2, rptEvtSlot, rptEvtPort, rptEvtPath, 
                rptEvtVT, rptEvtDateTime, rptEvtSrvEff, rptEvtNtfcnCde, rptEvtLocation, 
                rptEvtDirection, rptEvtMonValue, rptEvtThValue, rptEvtDescription, rptEvtNumber, 
                rptEvtPeriod, rptEvtVldty, rptEvtEffect, rptEvtState, rptEvtAiddet, 
                rptEvtSeqNumber, rptPmName }
            STATUS current
            DESCRIPTION 
                "Enter the description of the created OBJECT-GROUP."
            ::= { optixSonetTrapsGroups 1 }
        
        -- 1.3.6.1.4.1.2011.2.25.3.20.40.60.1.2
        optixSonetTrapsNotificationGroup NOTIFICATION-GROUP
            NOTIFICATIONS { almSignalDegradeVT, almSignalFailureVT, evtLossOfClock, evtFileLost, evtREILine, 
                evtBiasTemperatureOfPumpHigh, evtTimSection, evtLossOfAllSynchronousSource, evtSynchronousSourceDegrade, evtSyncLOS, 
                evtProtectionSwitching, evtDbmsError, evtLossOfMultiplexSignal, evtLossOfSingleWavelengthSignal, evtAdditionOfSingleWavelengthSignal, 
                evtLaserDegraded, evtPumpDiodeCoolingCurrentHigh, evtS1ModeSynChange, evtDbmsIsInProtectMode, evtSecuAlarm, 
                evtForwardErrorCorrectionLossOfFrame, evtForwardErrorCorrectionOutOfFrame, evtRateOver, evtCardConfigurationFail, evtLoopback, 
                evtCoolingCurrentModeHigh, evtOTULossOfFrame, evtOTUOutOfMultiFrame, evtSmTIM, evtPmTIM, 
                evtSmBDI, evtPmBDI, evtSmBEI, evtPmBEI, evtSmIAE, 
                evtSmBipExcessive, evtPmBipExcessive, evtSmBipSignalDefect, evtPmBipSignalDefect, evtOTUAlarmIndicationSignal, 
                evtODUAlarmIndicationSignal, evtODUOpenConnectionIndicationSignal, evtODULockedIndicationSignal, evtSumInputOpticalPowerHigh, evtSumInputOpticalPowerLow, 
                evtSumOutOpticalPowerHigh, evtOutOpticalPowerLow, evtGainLow, evtExcessiveErrorDefectBeforeFEC, evtDgeAdjustmentFail, 
                evtWavelengthLockFail, evtHotSwitchControlUnavail, evtEsconCodeError, evtCommitTimeout, evtSwdlNePackageCheck, 
                evtSwdlChaGmngmMismatch, evtDBSyncFail, evtClientMismatch, evtLaserModuleMismatch, evtEqptNoServiceAffecting, 
                evtEqptServiceAffectingFail, evtApsByteFailure, evtFarEndProtectionLineFailure, evtApsChannelMismatchFailure, evtApsModeMismatch, 
                evtApsTypeMismatch, evtHoldoverSync, evtFreeRunSync, evtFastStartSync, evtManualSetSSM, 
                evtFanOffline, evtSingleFanFail, evtMultiFanFail, evtEquipmentTypeMismatch, evtEquipmentOfflineOrUninstalled, 
                evtTransmitterFailure, evtSignalFailureSection, evtInputPowerHigh, evtInputPowerLow, evtSignalFailureLine, 
                evtSignalDegradeLine, evtLaserApprochingEndOfLife, evtOutPowerHigh, evtOutPowerLow, evtSignalDegradeSection, 
                evtAlarmIndicationSignalLine, evtRemoteFailureIindicationLine, evtAlarmIndicationSignalPath, evtLossOfPointerPath, evtTraceIdentifierMismatchPath, 
                evtUnequippedPath, evtSignalFailurePath, evtSignalDegradePath, evtRemoteFailureIindicationPath, evtALS, 
                evtLoopbackFacility, evtLoopbackTerminal, evtPayloadLabelMisatch, evtEnhancedRemotePalyloadFailureIndicationPath, evtEnhancedRemoteServerFailureIndicationPath, 
                evtEnhancedRemoteConnectivityFailureIndicationPath, evtPDIPath, evtPowerFail, evtLossOfPointerVT, evtAlarmIndicationSignalVT, 
                evtPayloadLabelMismatchVT, evtUnequippedVT, evtRemoteFailureIndicationVT, evtRemoteServerFailureIndicationVT, evtEnhancedRemoteConnectivityFailureIndicationVT, 
                evtEnhancedRemotePalyloadFailureIndicationVT, evtInterFaceCardOffline, evtSyncChangeSSM, evtTimeingModeChange, evtLockoutWorkingUnit, 
                evtLockoutProtectionUnit, evtForcedSwitch, evtManualSwitch, evtExerciseSwitch, evtWaitToRestore, 
                evtSwitchToIdle, evtSwitchFail, evtSyncSwitch, evtCommunicationFail, evtPowerAFail, 
                evtPowerBFail, evtInterfaceLinkMismatch, evtInterfaceCardFail, evtAIC, evtDbmsCfgCorrupted, 
                evtDefaultKByteDefect, evtInconsistentApsCodes, evtImproperApsCodes, evtExtraTrafficIsBeingSquelched, evtTopologyNeedsUpdatingOrIsInvalid, 
                evtSquelchTableNeedsUpdatingOrIsInvalid, evtNodeIdDuplicatedOrMismatched, evtXconMismatched, evtRingModeMisatch, evtSquelchModeMismatch, 
                evtLockoutProtectionSpan, evtLockoutWorkingRing, evtLockoutWorkingSpan, evtForceSwitchOfRing, evtForceSwitchOfSpan, 
                evtManualSwitchOfRing, evtManualSwitchOfSpan, evtExerciseSwitchRing, evtExerciseSwitchSpan, evtLockoutProtectionForAllSpans, 
                evtRingSwitch, evtSpanSwitch, evtSwitchToPassthru, evtPersistentLineSquelching, evtDbmsCfgBackupFailed, 
                evtFanFailures, evtInvalidEQPT, evtLaserApdBiasVoltageHigh, evtLaserApdBiasVoltageLow, evtLBCHigh, 
                evtLBCLow, evtLCCHigh, evtLCCLow, evtLinkError, evtLOA, 
                evtLOF, evtLOMPath, evtLOS, evtLaserTemperatureHigh, evtLaserTemperatureLow, 
                evtNeBdDataMismatch, evtNoLaserParameter, evtSyncReferenceSourceFailure, evtSignalDegradeVT, evtSignalFailureVT, 
                evtSequenceNumberMismatchedVT, evtSoftwareVersionMismatch, evtTemperatureHigh, evtAIS, evtLoopbackInhibited, 
                evtLockoutOfTheProtocol, evtLaserShutDown, evtLoopbackAllDS1FEAC, evtLoopbackCrossConnect, evtLoopbackDS1FEAC, 
                evtLoopbackDS3FEAC, evtLoopbackFacilityPath, evtLoopbackTerminalPath, evtPrimaryChannelChange, evtRAI, 
                evtSsmDQL, evtSsmLOS, evtTestSessionActive, evtNormalSyncMode, evtSwitchProtectionToWorkingUnit, 
                evtSwtichWokingToProtectingUnit, evtATECardOfflineOrUninstalled, evtPIUCardOfflineOrUninstalled, evtOOF, evtExerciseSwitchSuccess, 
                evtExerciseSwitchFail, evtUpgradeInProcess, evtLaserNotExist, evtLCASBandwidthReduced, evtGFPLossOfFrame, 
                evtFanIsOpened, evtFanIsClosed, evtPathLevelMismatch, evtTcaCVLine, evtDCCFailureIndication, 
                evtLanLossOfCarrierSignal, evtTcaCVCPPath, evtTcaCVPath, evtTcaCVPPath, evtTcaCVSection, 
                evtTcaCVVT, evtTcaESCPPath, evtTcaESLine, evtTcaESPath, evtTcaESPPath, 
                evtTcaESSection, evtTcaESVT, evtTcaPjcsPdet, evtTcaPjcsVdet, evtTcaSESCPPath, 
                evtTcaSESLine, evtTcaSESPath, evtTcaSESPPath, evtTcaSESSection, evtTcaSESVT, 
                evtTcaUASCPPath, evtTcaUASLine, evtTcaUASPath, evtTcaUASPPath, evtTcaUASVT, 
                evtBitsAIS, evtBitsLOF, evtBitsLOS, evtBitsCodeViolationOver, evtBlsrSFofRing, 
                evtBlsrSFofSpan, evtBlsrSDofRing, evtBlsrSDofSpan, evtBlsrNodeIsolate, evtSF, 
                evtSD, evtAutoSwitch, evtLoopbackFAC2NI, evtMtMode, evtStateChange, 
                evtRemoteClientSF, evtRemoteClientSD, evtPowerSwitch, evtPortOffline, evtDataLost, 
                evtSqmVT, evtLomVT, evtFCSError, almLossOfClock, almFileLost, 
                almBiasTemperatureOfPumpHigh, almTimSection, almLossOfAllSynchronousSource, almSynchronousSourceDegrade, almProtectionSwitching, 
                almDbmsError, almLossOfMultiplexSignal, almLossOfSingleWavelengthSignal, almAdditionOfSingleWavelengthSignal, almLaserDegraded, 
                almPumpDiodeCoolingCurrentHigh, almS1ModeSynChange, almDbmsIsInProtectMode, almForwardErrorCorrectionLossOfFrame, almForwardErrorCorrectionOutOfFrame, 
                almRateOver, almCardConfigurationFail, almLoopback, almCoolingCurrentModeHigh, almOTULossOfFrame, 
                almOTUOutOfMultiFrame, almSmTIM, almPmTIM, almSmBDI, almPmBDI, 
                almSmBEI, almPmBEI, almSmIAE, almSmBipExcessive, almPmBipExcessive, 
                almSmBipSignalDefect, almPmBipSignalDefect, almOTUAlarmIndicationSignal, almODUAlarmIndicationSignal, almODUOpenConnectionIndicationSignal, 
                almODULockedIndicationSignal, almSumInputOpticalPowerHigh, almSumInputOpticalPowerLow, almSumOutOpticalPowerHigh, almOutOpticalPowerLow, 
                almGainLow, almDgeAdjustmentFail, almWavelengthLockFail, almHotSwitchControlUnavail, almEsconCodeError, 
                almCommitTimeout, almSwdlNePackageCheck, almSwdlChaGmngmMismatch, almDBSyncFail, almClientMismatch, 
                almLaserModuleMismatch, almEqptNoServiceAffecting, almEqptServiceAffectingFail, almApsByteFailure, almFarEndProtectionLineFailure, 
                almApsChannelMismatchFailure, almApsModeMismatch, almApsTypeMismatch, almFreeRunSync, almFanOffline, 
                almSingleFanFail, almMultiFanFail, almEquipmentTypeMismatch, almEquipmentOfflineOrUninstalled, almTransmitterFailure, 
                almSignalFailureSection, almInputPowerHigh, almInputPowerLow, almSignalFailureLine, almSignalDegradeLine, 
                almLaserApprochingEndOfLife, almSignalDegradeSection, almAlarmIndicationSignalLine, almRemoteFailureIindicationLine, almAlarmIndicationSignalPath, 
                almLossOfPointerPath, almTraceIdentifierMismatchPath, almUnequippedPath, almSignalFailurePath, almSignalDegradePath, 
                almRemoteFailureIindicationPath, almPayloadLabelMisatch, almEnhancedRemotePalyloadFailureIndicationPath, almEnhancedRemoteServerFailureIndicationPath, almEnhancedRemoteConnectivityFailureIndicationPath, 
                almPowerFail, almLossOfPointerVT, almAlarmIndicationSignalVT, almPayloadLabelMismatchVT, almUnequippedVT, 
                almRemoteFailureIndicationVT, almRemoteServerFailureIndicationVT, almEnhancedRemoteConnectivityFailureIndicationVT, almEnhancedRemotePalyloadFailureIndicationVT, almInterFaceCardOffline, 
                almCommunicationFail, almPowerAFail, almPowerBFail, almInterfaceLinkMismatch, almInterfaceCardFail, 
                almAIC, almDbmsCfgCorrupted, almDefaultKByteDefect, almInconsistentApsCodes, almImproperApsCodes, 
                almExtraTrafficIsBeingSquelched, almTopologyNeedsUpdatingOrIsInvalid, almSquelchTableNeedsUpdatingOrIsInvalid, almNodeIdDuplicatedOrMismatched, almXconMismatched, 
                almRingModeMisatch, almSquelchModeMismatch, almDbmsCfgBackupFailed, almFanFailures, almInvalidEQPT, 
                almLaserApdBiasVoltageHigh, almLaserApdBiasVoltageLow, almLBCHigh, almLBCLow, almLCCHigh, 
                almLCCLow, almLinkError, almLOA, almLOF, almLOMPath, 
                almLOS, almLaserTemperatureHigh, almLaserTemperatureLow, almNeBdDataMismatch, almNoLaserParameter, 
                almSyncReferenceSourceFailure, almSequenceNumberMismatchedVT, almSoftwareVersionMismatch, almTemperatureHigh, almAIS, 
                almPrimaryChannelChange, almRAI, almSsmDQL, almSsmLOS, almATECardOfflineOrUninstalled, 
                almPIUCardOfflineOrUninstalled, almOOF, almLaserNotExist, almGFPLossOfFrame, almPathLevelMismatch, 
                almDCCFailureIndication, almLanLossOfCarrierSignal, almBitsAIS, almBitsLOF, almBitsLOS, 
                almBitsCodeViolationOver, almBlsrNodeIsolate, almRemoteClientSF, almRemoteClientSD, almPowerSwitch, 
                almPortOffline, almDataLost, almSqmVT, almLomVT, almFCSError, 
                almREILine, almSyncLOS, almSecuAlarm, almExcessiveErrorDefectBeforeFEC, almHoldoverSync, 
                almFastStartSync, almManualSetSSM, almOutPowerHigh, almOutPowerLow, almALS, 
                almLoopbackFacility, almLoopbackTerminal, almPDIPath, almSyncChangeSSM, almTimeingModeChange, 
                almLockoutWorkingUnit, almLockoutProtectionUnit, almForcedSwitch, almManualSwitch, almExerciseSwitch, 
                almWaitToRestore, almSwitchToIdle, almSwitchFail, almSyncSwitch, almLockoutProtectionSpan, 
                almLockoutWorkingRing, almLockoutWorkingSpan, almForceSwitchOfRing, almForceSwitchOfSpan, almManualSwitchOfRing, 
                almManualSwitchOfSpan, almExerciseSwitchRing, almExerciseSwitchSpan, almLockoutProtectionForAllSpans, almRingSwitch, 
                almSpanSwitch, almSwitchToPassthru, almPersistentLineSquelching, almLoopbackInhibited, almLockoutOfTheProtocol, 
                almLaserShutDown, almLoopbackAllDS1FEAC, almLoopbackCrossConnect, almLoopbackDS1FEAC, almLoopbackDS3FEAC, 
                almLoopbackFacilityPath, almLoopbackTerminalPath, almTestSessionActive, almNormalSyncMode, almSwitchProtectionToWorkingUnit, 
                almSwtichWokingToProtectingUnit, almExerciseSwitchSuccess, almExerciseSwitchFail, almUpgradeInProcess, almLCASBandwidthReduced, 
                almFanIsOpened, almFanIsClosed, almTcaCVLine, almTcaCVCPPath, almTcaCVPath, 
                almTcaCVPPath, almTcaCVSection, almTcaCVVT, almTcaESCPPath, almTcaESLine, 
                almTcaESPath, almTcaESPPath, almTcaESSection, almTcaESVT, almTcaPjcsPdet, 
                almTcaPjcsVdet, almTcaSESCPPath, almTcaSESLine, almTcaSESPath, almTcaSESPPath, 
                almTcaSESSection, almTcaSESVT, almTcaUASCPPath, almTcaUASLine, almTcaUASPath, 
                almTcaUASPPath, almTcaUASVT, almBlsrSFofRing, almBlsrSFofSpan, almBlsrSDofRing, 
                almBlsrSDofSpan, almSF, almSD, almAutoSwitch, almLoopbackFAC2NI, 
                almMtMode, almStateChange, envAirCompressorFailure, envAirConditioningFailure, envAirDryerFailure, 
                envBatteryDischarging, envBatteryFailure, envCoolingFacFailure, envCPMAJOR, envCPMINOR, 
                envEngineFailure, envEngineOperating, envExplosiveGas, envFireDetectorFailure, envFire, 
                envFlood, envFuseFailure, envGeneratorFailure, envHighAirflow, envHighHumidity, 
                envHighTemperature, envHighWater, envIntrusion, envLowBatteryVoltage, envLowFuel, 
                envLowHumidity, envLowCablePressure, envLowTemperature, envLowWater, envMiscellaneous, 
                envOpenDoor, envCommercialPowerFailure, envPumpFailure, env48VoltPowerSupplyFailure, envRectifierFailure, 
                envRectifierHighVoltage, envRectiFierLowVoltage, envSmoke, envToxicGas, envVentilationSystemFailure, 
                pmSESSection, pmCVLine, pmESLine, pmSESLine, pmUASLine, 
                pmPSD, pmCVPath, pmESPath, pmPjcsVdet, pmBdTempCur, 
                pmBdTempMax, pmBdTempMin, pmPmuTempCur, pmPmuTempMax, pmPmuTempMin, 
                pmLbcCur, pmLbcMax, pmLbcMin, pmOptCur, pmOptMax, 
                pmOptMin, pmOprCur, pmOprMax, pmOprMin, pmCVPPath, 
                pmCVCPPath, pmESPPath, pmESCPPath, pmSESPPath, pmSESCPPath, 
                pmUASPPath, pmUASCPPath, pmPscProtection, pmPsdProtection, pmPscSpan, 
                pmPsdSpan, pmPscRing, pmPsdRing, pmPscWork, pmPsdWork, 
                pmLCCCur, pmLCCMax, pmLCCMin, pmLTEMPCur, pmLTEMPMax, 
                pmLTEMPMin, pmLAPDBVCur, pmLAPDBVMax, pmLAPDBVMin, pmPLBCCur, 
                pmPLBCMax, pmPLBCMin, pmPLWCCur, pmPLWCMax, pmPLWCMin, 
                pmCVSection, pmESSection, pmSESPath, pmUASPath, pmCVVT, 
                pmESVT, pmSESVT, pmUASVT, pmPSC, pmPjcsPdet,
                almChassisMea, evtChassisMea,
                almRmvToMt, almRstFromMt, almLpbk, almRlsLpbk,
                evtRmvToMt, evtRstFromMt, evtLpbk, evtRlsLpbk,
                almPowerExceed,almLcasPlct,almLcasPlcr,almLcasTlct,almLcasTlcr,
                evtPowerExceed,evtLcasPlct,evtLcasPlcr,evtLcasTlct,evtLcasTlcr,
                almLcasFopt,almLcasFopr,almGfpCsf,almLptRfi,almPartialUnprotected,
                evtLcasFopt,evtLcasFopr,evtGfpCsf,evtLptRfi,evtPartialUnprotected,
                almFanMea,
                evtFanMea
                }
            STATUS current
            DESCRIPTION 
                "Enter the description of the created NOTIFICATION-GROUP."
            ::= { optixSonetTrapsGroups 2 }
        
        -- 1.3.6.1.4.1.2011.2.25.3.20.40.60.2
        optixSonetTrapsCompliances OBJECT IDENTIFIER ::= { optixSonetTrapsConformance 2 }
        
        -- 1.3.6.1.4.1.2011.2.25.3.20.40.60.2.1
        optixSonetBasicCompliance MODULE-COMPLIANCE
            STATUS current
            DESCRIPTION 
                "Enter the description of the created MODULE-COMPLIANCE."
            MODULE -- this module
                MANDATORY-GROUPS { optixSonetTrapsObjectGroup, optixSonetTrapsNotificationGroup }
            ::= { optixSonetTrapsCompliances 1 }
        
    
    END

--
-- OPTIX-SONET-TRAPS-MIB.mib
--
