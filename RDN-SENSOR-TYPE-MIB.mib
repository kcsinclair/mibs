-- *****************************************************************
-- RDN-SENSOR-TYPE-MIB.mib:
-- Motorola BSR's Sensor Types MIB
--
-- Copyright (C) 2001, 2008 by Motorola, Inc.
-- All rights reserved.
-- *****************************************************************
RDN-SENSOR-TYPE-MIB DEFINITIONS ::= BEGIN

    IMPORTS
        MODULE-IDENTITY
            FROM SNMPv2-SMI
        rdnDefinitions
            FROM RDN-DEFINITIONS-MIB;

    -- riverdelta sensor-types definitions mib module

    rdnSensorTypes MODULE-IDENTITY
        LAST-UPDATED "200808080000Z"  -- August 8, 2008 
        ORGANIZATION "Motorola"
        CONTACT-INFO "Motorola
                      Customer Service
                      101 Tournament Drive
                      Horsham, PA 19044
                      US Tel: +1 888 944 4357
                      Int Tel: +1 215 323 0044
	              Fax: +1 215 323 1502
                      Email: CPSSupport@Motorola.com"

        DESCRIPTION
                "MIB module for Motorola Sensor
                Type definitions.

		Copyright (C) 2001, 2008 by Motorola, Inc.
	     	All rights reserved."

	REVISION     "200808080000Z"  -- August 8, 2008
	DESCRIPTION
		"Added Copyright Statement into MIB modules's
	       	 description."	
        REVISION     "200311050000Z"
        DESCRIPTION
                "Updated the CONTACT-INFO."
        REVISION     "200108070000Z"
        DESCRIPTION
                "Initial creation."
        ::= { rdnDefinitions 6 }


      --
      -- module definitions for all riverdelta sensors
      --

      rdnSensorsUnknown     OBJECT IDENTIFIER ::= { rdnSensorTypes 0 }
      rdnSensorsSRM750      OBJECT IDENTIFIER ::= { rdnSensorTypes 1 }
      rdnSensorsSRMDIMM     OBJECT IDENTIFIER ::= { rdnSensorTypes 2 }
      rdnSensorsSRMDC2DC    OBJECT IDENTIFIER ::= { rdnSensorTypes 3 }
      rdnSensorsSRMXFAB     OBJECT IDENTIFIER ::= { rdnSensorTypes 4 }
      rdnSensorsFan         OBJECT IDENTIFIER ::= { rdnSensorTypes 5 }

END
