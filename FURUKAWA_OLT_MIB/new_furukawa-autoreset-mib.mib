--
-- FKOLTG1040-AUTORESET-MIB.my
-- MIB generated by MG-SOFT Visual MIB Builder Version 6.0  Build 88
-- Thursday, November 11, 2010 at 16:59:25
--

	FKOLTG1040-AUTORESET-MIB DEFINITIONS ::= BEGIN
 
		IMPORTS
			dsSwitchSystem			
				FROM FKOLTG1040-SWITCH-MIB			
			InterfaceIndex			
				FROM IF-MIB			
			FkControlStatusType, FkControlRequestResultType			
				FROM FK-TC-MIB			
			TimeTicks, IpAddress, Gauge32, OBJECT-TYPE, NOTIFICATION-TYPE			
				FROM SNMPv2-SMI			
			TruthValue, TEXTUAL-CONVENTION			
				FROM SNMPv2-TC;
	
	
--
-- Textual conventions
--
	
--  Textual Conventions

	
--
-- Node definitions
--
	
		-- 1.3.6.1.4.1.10428 9 1.9.1.1.1.31
		dsAutoReset OBJECT IDENTIFIER ::= { dsSwitchSystem 31 }

		
		-- 1.3.6.1.4.1.10428 9 1.9.1.1.1.31.1
		dsAutoResetBase OBJECT IDENTIFIER ::= { dsAutoReset 1 }

		
		-- 1.3.6.1.4.1.10428 9 1.9.1.1.1.31.1.1
		dsAutoResetBaseInfo OBJECT IDENTIFIER ::= { dsAutoResetBase 1 }

		
		-- 1.3.6.1.4.1.10428 9 1.9.1.1.1.31.1.1.1
		dsAutoResetEnable OBJECT-TYPE
			SYNTAX INTEGER
				{
				disable(0),
				enable(1)
				}
			MAX-ACCESS read-only
			STATUS current
			DESCRIPTION
				"Indicates whether AutoReset globally is enabled or not."
			::= { dsAutoResetBaseInfo 1 }

		
		-- 1.3.6.1.4.1.10428 9 1.9.1.1.1.31.1.1.2
		dsAutoResetForceReboot OBJECT-TYPE
			SYNTAX OCTET STRING
			MAX-ACCESS read-only
			STATUS current
			DESCRIPTION
				"The time when force-reboot will occur, ex) '17:25 15 Mar 2010'"
			::= { dsAutoResetBaseInfo 2 }

		
		-- 1.3.6.1.4.1.10428 9 1.9.1.1.1.31.1.1.3
		dsAutoResetResetCount OBJECT-TYPE
			SYNTAX INTEGER (1..100)
			MAX-ACCESS read-only
			STATUS current
			DESCRIPTION
				"Reboot count by AutoReset"
			::= { dsAutoResetBaseInfo 3 }

		
		-- 1.3.6.1.4.1.10428 9 1.9.1.1.1.31.1.1.4
		dsAutoResetResetThreshold OBJECT-TYPE
			SYNTAX INTEGER (1..100)
			MAX-ACCESS read-only
			STATUS current
			DESCRIPTION
				"Reboot threshold for AutoReset"
			::= { dsAutoResetBaseInfo 4 }

		
		-- 1.3.6.1.4.1.10428 9 1.9.1.1.1.31.1.2
		dsAutoResetBaseControl OBJECT IDENTIFIER ::= { dsAutoResetBase 2 }

		
		-- 1.3.6.1.4.1.10428 9 1.9.1.1.1.31.1.2.1
		dsAutoResetBaseControlRequest OBJECT-TYPE
			SYNTAX INTEGER
				{
				setAutoResetEnable(1),
				setAutoResetForceReboot(2)
				}
			MAX-ACCESS read-write
			STATUS current
			DESCRIPTION
				"Description."
			::= { dsAutoResetBaseControl 1 }

		
		-- 1.3.6.1.4.1.10428 9 1.9.1.1.1.31.1.2.2
		dsAutoResetBaseControlStatus OBJECT-TYPE
			SYNTAX FkControlStatusType
			MAX-ACCESS read-only
			STATUS current
			DESCRIPTION
				"Description."
			::= { dsAutoResetBaseControl 2 }

		
		-- 1.3.6.1.4.1.10428 9 1.9.1.1.1.31.1.2.3
		dsAutoResetBaseControlTimer OBJECT-TYPE
			SYNTAX Gauge32
			MAX-ACCESS read-write
			STATUS current
			DESCRIPTION
				"Description."
			::= { dsAutoResetBaseControl 3 }

		
		-- 1.3.6.1.4.1.10428 9 1.9.1.1.1.31.1.2.4
		dsAutoResetBaseControlTimeStamp OBJECT-TYPE
			SYNTAX TimeTicks
			MAX-ACCESS read-only
			STATUS current
			DESCRIPTION
				"Description."
			::= { dsAutoResetBaseControl 4 }

		
		-- 1.3.6.1.4.1.10428 9 1.9.1.1.1.31.1.2.5
		dsAutoResetBaseControlReqResult OBJECT-TYPE
			SYNTAX FkControlRequestResultType
			MAX-ACCESS read-only
			STATUS current
			DESCRIPTION
				"Description."
			::= { dsAutoResetBaseControl 5 }

		
		-- 1.3.6.1.4.1.10428 9 1.9.1.1.1.31.1.2.6
		dsAutoResetControlEnable OBJECT-TYPE
			SYNTAX INTEGER
				{
				disable(0),
				enable(1)
				}
			MAX-ACCESS read-write
			STATUS current
			DESCRIPTION
				"Indicates whether AutoReset globally is enabled or not."
			::= { dsAutoResetBaseControl 6 }

		
		-- 1.3.6.1.4.1.10428 9 1.9.1.1.1.31.1.2.7
		dsAutoResetControlForceReboot OBJECT-TYPE
			SYNTAX OCTET STRING
			MAX-ACCESS read-write
			STATUS current
			DESCRIPTION
				"The time when force-reboot will occur, ex) '17:25 15 Mar 2010'"
			::= { dsAutoResetBaseControl 7 }

		
		-- 1.3.6.1.4.1.10428 9 1.9.1.1.1.31.1.2.8
		dsAutoResetControlResetCount OBJECT-TYPE
			SYNTAX INTEGER (1..100)
			MAX-ACCESS read-write
			STATUS current
			DESCRIPTION
				"Reboot count by AutoReset"
			::= { dsAutoResetBaseControl 8 }

		
		-- 1.3.6.1.4.1.10428 9 1.9.1.1.1.31.1.2.9
		dsAutoResetControlResetThreshold OBJECT-TYPE
			SYNTAX INTEGER (1..100)
			MAX-ACCESS read-write
			STATUS current
			DESCRIPTION
				"Reboot threshold for AutoReset"
			::= { dsAutoResetBaseControl 9 }

		
		-- 1.3.6.1.4.1.10428 9 1.9.1.1.1.31.1.3
		dsAutoResetBaseNotification OBJECT IDENTIFIER ::= { dsAutoResetBase 3 }

		
		-- 1.3.6.1.4.1.10428 9 1.9.1.1.1.31.1.3.1
		dsAutoResetEnableChanged NOTIFICATION-TYPE
			OBJECTS { dsAutoResetBaseControlRequest, dsAutoResetBaseControlStatus, dsAutoResetBaseControlTimer, dsAutoResetBaseControlTimeStamp, dsAutoResetBaseControlReqResult, 
				dsAutoResetControlEnable }
			STATUS current
			DESCRIPTION 
				"setAutoResetEnable"
			::= { dsAutoResetBaseNotification 1 }

		
		-- 1.3.6.1.4.1.10428 9 1.9.1.1.1.31.1.3.2
		dsAutoResetForceRebootChanged NOTIFICATION-TYPE
			OBJECTS { dsAutoResetBaseControlRequest, dsAutoResetBaseControlStatus, dsAutoResetBaseControlTimer, dsAutoResetBaseControlTimeStamp, dsAutoResetBaseControlReqResult, 
				dsAutoResetControlForceReboot }
			STATUS current
			DESCRIPTION 
				"setAutoResetForceReboot"
			::= { dsAutoResetBaseNotification 2 }

		
		-- 1.3.6.1.4.1.10428 9 1.9.1.1.1.31.1.3.3
		dsAutoResetResetThresholdChanged NOTIFICATION-TYPE
			OBJECTS { dsAutoResetBaseControlRequest, dsAutoResetBaseControlStatus, dsAutoResetBaseControlTimer, dsAutoResetBaseControlTimeStamp, dsAutoResetBaseControlReqResult, 
				dsAutoResetControlResetThreshold }
			STATUS current
			DESCRIPTION 
				"setAutoResetResetThreshold"
			::= { dsAutoResetBaseNotification 3 }

		
		-- 1.3.6.1.4.1.10428 9 1.9.1.1.1.31.2
		dsAutoResetCpu OBJECT IDENTIFIER ::= { dsAutoReset 2 }

		
		-- 1.3.6.1.4.1.10428 9 1.9.1.1.1.31.2.1
		dsAutoResetCpuInfo OBJECT IDENTIFIER ::= { dsAutoResetCpu 1 }

		
		-- 1.3.6.1.4.1.10428 9 1.9.1.1.1.31.2.1.1
		dsAutoResetCpuEnable OBJECT-TYPE
			SYNTAX INTEGER
				{
				disable(0),
				enable(1)
				}
			MAX-ACCESS read-only
			STATUS current
			DESCRIPTION
				"Indicates whether CPU-based AutoReset is enabled or not."
			::= { dsAutoResetCpuInfo 1 }

		
		-- 1.3.6.1.4.1.10428 9 1.9.1.1.1.31.2.1.2
		dsAutoResetCpuThresholdHigh OBJECT-TYPE
			SYNTAX INTEGER (1..100)
			MAX-ACCESS read-only
			STATUS current
			DESCRIPTION
				"High threshold for the CPU load."
			::= { dsAutoResetCpuInfo 2 }

		
		-- 1.3.6.1.4.1.10428 9 1.9.1.1.1.31.2.1.3
		dsAutoResetCpuThresholdLow OBJECT-TYPE
			SYNTAX INTEGER (1..100)
			MAX-ACCESS read-only
			STATUS current
			DESCRIPTION
				"Low threshold for the CPU load."
			::= { dsAutoResetCpuInfo 3 }

		
		-- 1.3.6.1.4.1.10428 9 1.9.1.1.1.31.2.1.4
		dsAutoResetCpuContinueTime OBJECT-TYPE
			SYNTAX INTEGER (1..3600)
			MAX-ACCESS read-only
			STATUS current
			DESCRIPTION
				"The time of duration.
				AutoReset condition is met if CPU load continuously exceeds the threshold during the given time."
			::= { dsAutoResetCpuInfo 4 }

		
		-- 1.3.6.1.4.1.10428 9 1.9.1.1.1.31.2.1.5
		dsAutoResetCpuResetTime OBJECT-TYPE
			SYNTAX OCTET STRING
			MAX-ACCESS read-only
			STATUS current
			DESCRIPTION
				"The reboot time due to CPU-based AutoReset.
				Format : hh:mm"
			::= { dsAutoResetCpuInfo 5 }

		
		-- 1.3.6.1.4.1.10428 9 1.9.1.1.1.31.2.2
		dsAutoResetCpuControl OBJECT IDENTIFIER ::= { dsAutoResetCpu 2 }

		
		-- 1.3.6.1.4.1.10428 9 1.9.1.1.1.31.2.2.1
		dsAutoResetCpuControlRequest OBJECT-TYPE
			SYNTAX INTEGER { setAutoResetCpuEnable(1) }
			MAX-ACCESS read-write
			STATUS current
			DESCRIPTION
				"Description."
			::= { dsAutoResetCpuControl 1 }

		
		-- 1.3.6.1.4.1.10428 9 1.9.1.1.1.31.2.2.2
		dsAutoResetCpuControlStatus OBJECT-TYPE
			SYNTAX FkControlStatusType
			MAX-ACCESS read-only
			STATUS current
			DESCRIPTION
				"Description."
			::= { dsAutoResetCpuControl 2 }

		
		-- 1.3.6.1.4.1.10428 9 1.9.1.1.1.31.2.2.3
		dsAutoResetCpuControlTimer OBJECT-TYPE
			SYNTAX Gauge32
			MAX-ACCESS read-write
			STATUS current
			DESCRIPTION
				"Description."
			::= { dsAutoResetCpuControl 3 }

		
		-- 1.3.6.1.4.1.10428 9 1.9.1.1.1.31.2.2.4
		dsAutoResetCpuControlTimeStamp OBJECT-TYPE
			SYNTAX TimeTicks
			MAX-ACCESS read-only
			STATUS current
			DESCRIPTION
				"Description."
			::= { dsAutoResetCpuControl 4 }

		
		-- 1.3.6.1.4.1.10428 9 1.9.1.1.1.31.2.2.5
		dsAutoResetCpuControlReqResult OBJECT-TYPE
			SYNTAX FkControlRequestResultType
			MAX-ACCESS read-only
			STATUS current
			DESCRIPTION
				"Description."
			::= { dsAutoResetCpuControl 5 }

		
		-- 1.3.6.1.4.1.10428 9 1.9.1.1.1.31.2.2.6
		dsAutoResetCpuControlEnable OBJECT-TYPE
			SYNTAX INTEGER
				{
				disable(0),
				enable(1)
				}
			MAX-ACCESS read-write
			STATUS current
			DESCRIPTION
				"Indicates whether CPU-based AutoReset is enabled or not."
			::= { dsAutoResetCpuControl 6 }

		
		-- 1.3.6.1.4.1.10428 9 1.9.1.1.1.31.2.2.7
		dsAutoResetCpuControlThresholdHigh OBJECT-TYPE
			SYNTAX INTEGER (1..100)
			MAX-ACCESS read-write
			STATUS current
			DESCRIPTION
				"High threshold for the CPU load."
			::= { dsAutoResetCpuControl 7 }

		
		-- 1.3.6.1.4.1.10428 9 1.9.1.1.1.31.2.2.8
		dsAutoResetCpuControlThresholdLow OBJECT-TYPE
			SYNTAX INTEGER (1..100)
			MAX-ACCESS read-write
			STATUS current
			DESCRIPTION
				"Low threshold for the CPU load."
			::= { dsAutoResetCpuControl 8 }

		
		-- 1.3.6.1.4.1.10428 9 1.9.1.1.1.31.2.2.9
		dsAutoResetCpuControlContinueTime OBJECT-TYPE
			SYNTAX INTEGER (1..3600)
			MAX-ACCESS read-write
			STATUS current
			DESCRIPTION
				"The time of duration.
				AutoReset condition is met if CPU load continuously exceeds the threshold during the given time."
			::= { dsAutoResetCpuControl 9 }

		
		-- 1.3.6.1.4.1.10428 9 1.9.1.1.1.31.2.2.10
		dsAutoResetCpuControlResetTime OBJECT-TYPE
			SYNTAX OCTET STRING
			MAX-ACCESS read-write
			STATUS current
			DESCRIPTION
				"The reboot time due to CPU-based AutoReset.
				Format : hh:mm"
			::= { dsAutoResetCpuControl 10 }

		
		-- 1.3.6.1.4.1.10428 9 1.9.1.1.1.31.2.3
		dsAutoResetCpuNotification OBJECT IDENTIFIER ::= { dsAutoResetCpu 3 }

		
		-- 1.3.6.1.4.1.10428 9 1.9.1.1.1.31.2.3.1
		dsAutoResetCpuEnableChanged NOTIFICATION-TYPE
			OBJECTS { dsAutoResetCpuControlRequest, dsAutoResetCpuControlStatus, dsAutoResetCpuControlTimer, dsAutoResetCpuControlTimeStamp, dsAutoResetCpuControlReqResult, 
				dsAutoResetCpuControlEnable }
			STATUS current
			DESCRIPTION 
				"setAutoResetCpuEnable"
			::= { dsAutoResetCpuNotification 1 }

		
		-- 1.3.6.1.4.1.10428 9 1.9.1.1.1.31.3
		dsAutoResetMemory OBJECT IDENTIFIER ::= { dsAutoReset 3 }

		
		-- 1.3.6.1.4.1.10428 9 1.9.1.1.1.31.3.1
		dsAutoResetMemoryInfo OBJECT IDENTIFIER ::= { dsAutoResetMemory 1 }

		
		-- 1.3.6.1.4.1.10428 9 1.9.1.1.1.31.3.1.1
		dsAutoResetMemoryEnable OBJECT-TYPE
			SYNTAX INTEGER
				{
				disable(0),
				enable(1)
				}
			MAX-ACCESS read-only
			STATUS current
			DESCRIPTION
				"Indicates whether Memory-based AutoReset is enabled or not."
			::= { dsAutoResetMemoryInfo 1 }

		
		-- 1.3.6.1.4.1.10428 9 1.9.1.1.1.31.3.1.2
		dsAutoResetMemoryThresholdHigh OBJECT-TYPE
			SYNTAX INTEGER (1..100)
			MAX-ACCESS read-only
			STATUS current
			DESCRIPTION
				"High threshold for the Memory usage."
			::= { dsAutoResetMemoryInfo 2 }

		
		-- 1.3.6.1.4.1.10428 9 1.9.1.1.1.31.3.1.3
		dsAutoResetMemoryThresholdLow OBJECT-TYPE
			SYNTAX INTEGER (1..100)
			MAX-ACCESS read-only
			STATUS current
			DESCRIPTION
				"Low threshold for the Memory usage."
			::= { dsAutoResetMemoryInfo 3 }

		
		-- 1.3.6.1.4.1.10428 9 1.9.1.1.1.31.3.1.4
		dsAutoResetMemoryContinueTime OBJECT-TYPE
			SYNTAX INTEGER (1..3600)
			MAX-ACCESS read-only
			STATUS current
			DESCRIPTION
				"The time of duration.
				AutoReset condition is met if Memory usage continuously exceeds the threshold during the given time."
			::= { dsAutoResetMemoryInfo 4 }

		
		-- 1.3.6.1.4.1.10428 9 1.9.1.1.1.31.3.1.5
		dsAutoResetMemoryResetTime OBJECT-TYPE
			SYNTAX OCTET STRING
			MAX-ACCESS read-only
			STATUS current
			DESCRIPTION
				"The reboot time due to Memory-based AutoReset.
				Format : hh:mm"
			::= { dsAutoResetMemoryInfo 5 }

		
		-- 1.3.6.1.4.1.10428 9 1.9.1.1.1.31.3.2
		dsAutoResetMemoryControl OBJECT IDENTIFIER ::= { dsAutoResetMemory 2 }

		
		-- 1.3.6.1.4.1.10428 9 1.9.1.1.1.31.3.2.1
		dsAutoResetMemoryControlRequest OBJECT-TYPE
			SYNTAX INTEGER { setY1731Enable(1) }
			MAX-ACCESS read-write
			STATUS current
			DESCRIPTION
				"Description."
			::= { dsAutoResetMemoryControl 1 }

		
		-- 1.3.6.1.4.1.10428 9 1.9.1.1.1.31.3.2.2
		dsAutoResetMemoryControlStatus OBJECT-TYPE
			SYNTAX FkControlStatusType
			MAX-ACCESS read-only
			STATUS current
			DESCRIPTION
				"Description."
			::= { dsAutoResetMemoryControl 2 }

		
		-- 1.3.6.1.4.1.10428 9 1.9.1.1.1.31.3.2.3
		dsAutoResetMemoryControlTimer OBJECT-TYPE
			SYNTAX Gauge32
			MAX-ACCESS read-write
			STATUS current
			DESCRIPTION
				"Description."
			::= { dsAutoResetMemoryControl 3 }

		
		-- 1.3.6.1.4.1.10428 9 1.9.1.1.1.31.3.2.4
		dsAutoResetMemoryControlTimeStamp OBJECT-TYPE
			SYNTAX TimeTicks
			MAX-ACCESS read-only
			STATUS current
			DESCRIPTION
				"Description."
			::= { dsAutoResetMemoryControl 4 }

		
		-- 1.3.6.1.4.1.10428 9 1.9.1.1.1.31.3.2.5
		dsAutoResetMemoryControlReqResult OBJECT-TYPE
			SYNTAX FkControlRequestResultType
			MAX-ACCESS read-only
			STATUS current
			DESCRIPTION
				"Description."
			::= { dsAutoResetMemoryControl 5 }

		
		-- 1.3.6.1.4.1.10428 9 1.9.1.1.1.31.3.2.6
		dsAutoResetMemoryControlEnable OBJECT-TYPE
			SYNTAX INTEGER
				{
				disable(0),
				enable(1)
				}
			MAX-ACCESS read-write
			STATUS current
			DESCRIPTION
				"Indicates whether Memory-based AutoReset is enabled or not."
			::= { dsAutoResetMemoryControl 6 }

		
		-- 1.3.6.1.4.1.10428 9 1.9.1.1.1.31.3.2.7
		dsAutoResetMemoryControlThresholdHigh OBJECT-TYPE
			SYNTAX INTEGER (1..100)
			MAX-ACCESS read-write
			STATUS current
			DESCRIPTION
				"High threshold for the Memory usage."
			::= { dsAutoResetMemoryControl 7 }

		
		-- 1.3.6.1.4.1.10428 9 1.9.1.1.1.31.3.2.8
		dsAutoResetMemoryControlThresholdLow OBJECT-TYPE
			SYNTAX INTEGER (1..100)
			MAX-ACCESS read-write
			STATUS current
			DESCRIPTION
				"Low threshold for the Memory usage."
			::= { dsAutoResetMemoryControl 8 }

		
		-- 1.3.6.1.4.1.10428 9 1.9.1.1.1.31.3.2.9
		dsAutoResetMemoryControlContinueTime OBJECT-TYPE
			SYNTAX INTEGER (1..3600)
			MAX-ACCESS read-write
			STATUS current
			DESCRIPTION
				"The time of duration.
				AutoReset condition is met if Memory usage continuously exceeds the threshold during the given time."
			::= { dsAutoResetMemoryControl 9 }

		
		-- 1.3.6.1.4.1.10428 9 1.9.1.1.1.31.3.2.10
		dsAutoResetMemoryControlResetTime OBJECT-TYPE
			SYNTAX OCTET STRING
			MAX-ACCESS read-write
			STATUS current
			DESCRIPTION
				"The reboot time due to Memory-based AutoReset.
				Format : hh:mm"
			::= { dsAutoResetMemoryControl 10 }

		
		-- 1.3.6.1.4.1.10428 9 1.9.1.1.1.31.3.3
		dsAutoResetMemoryNotification OBJECT IDENTIFIER ::= { dsAutoResetMemory 3 }

		
		-- 1.3.6.1.4.1.10428 9 1.9.1.1.1.31.3.3.1
		dsAutoResetMemoryEnableChanged NOTIFICATION-TYPE
			OBJECTS { dsAutoResetMemoryControlRequest, dsAutoResetMemoryControlStatus, dsAutoResetMemoryControlTimer, dsAutoResetMemoryControlTimeStamp, dsAutoResetMemoryControlReqResult, 
				dsAutoResetMemoryControlEnable }
			STATUS current
			DESCRIPTION 
				"setAutoResetMemoryEnable"
			::= { dsAutoResetMemoryNotification 1 }

		
		-- 1.3.6.1.4.1.10428 9 1.9.1.1.1.31.4
		dsAutoResetNetwork OBJECT IDENTIFIER ::= { dsAutoReset 4 }

		
		-- 1.3.6.1.4.1.10428 9 1.9.1.1.1.31.4.1
		dsAutoResetNetworkInfo OBJECT IDENTIFIER ::= { dsAutoResetNetwork 1 }

		
		-- 1.3.6.1.4.1.10428 9 1.9.1.1.1.31.4.1.1
		dsAutoResetNetworkEnable OBJECT-TYPE
			SYNTAX INTEGER
				{
				disable(0),
				enable(1)
				}
			MAX-ACCESS read-only
			STATUS current
			DESCRIPTION
				"Indicates whether Network-based AutoReset is enabled or not."
			::= { dsAutoResetNetworkInfo 1 }

		
		-- 1.3.6.1.4.1.10428 9 1.9.1.1.1.31.4.1.2
		dsAutoResetNetworkInterval OBJECT-TYPE
			SYNTAX INTEGER (1..60)
			MAX-ACCESS read-only
			STATUS current
			DESCRIPTION
				"The interval between ping request."
			::= { dsAutoResetNetworkInfo 2 }

		
		-- 1.3.6.1.4.1.10428 9 1.9.1.1.1.31.4.1.3
		dsAutoResetNetworkCount OBJECT-TYPE
			SYNTAX INTEGER (1..60)
			MAX-ACCESS read-only
			STATUS current
			DESCRIPTION
				"The count of ping request
				AutoReset condition is met if there was no ping reply for the count of continuous ping request."
			::= { dsAutoResetNetworkInfo 3 }

		
		-- 1.3.6.1.4.1.10428 9 1.9.1.1.1.31.4.1.4
		dsAutoResetNetworkTargetIp OBJECT-TYPE
			SYNTAX IpAddress
			MAX-ACCESS read-only
			STATUS current
			DESCRIPTION
				"The ping destination IP address"
			::= { dsAutoResetNetworkInfo 4 }

		
		-- 1.3.6.1.4.1.10428 9 1.9.1.1.1.31.4.1.5
		dsAutoResetNetworkResetTime OBJECT-TYPE
			SYNTAX OCTET STRING
			MAX-ACCESS read-only
			STATUS current
			DESCRIPTION
				"The reboot time due to Memory-based AutoReset.
				Format : hh:mm"
			::= { dsAutoResetNetworkInfo 5 }

		
		-- 1.3.6.1.4.1.10428 9 1.9.1.1.1.31.4.2
		dsAutoResetNetworkControl OBJECT IDENTIFIER ::= { dsAutoResetNetwork 2 }

		
		-- 1.3.6.1.4.1.10428 9 1.9.1.1.1.31.4.2.1
		dsAutoResetNetworkControlRequest OBJECT-TYPE
			SYNTAX INTEGER { setAutoResetNetworkEnable(1) }
			MAX-ACCESS read-write
			STATUS current
			DESCRIPTION
				"Description."
			::= { dsAutoResetNetworkControl 1 }

		
		-- 1.3.6.1.4.1.10428 9 1.9.1.1.1.31.4.2.2
		dsAutoResetNetworkControlStatus OBJECT-TYPE
			SYNTAX FkControlStatusType
			MAX-ACCESS read-only
			STATUS current
			DESCRIPTION
				"Description."
			::= { dsAutoResetNetworkControl 2 }

		
		-- 1.3.6.1.4.1.10428 9 1.9.1.1.1.31.4.2.3
		dsAutoResetNetworkControlTimer OBJECT-TYPE
			SYNTAX Gauge32
			MAX-ACCESS read-write
			STATUS current
			DESCRIPTION
				"Description."
			::= { dsAutoResetNetworkControl 3 }

		
		-- 1.3.6.1.4.1.10428 9 1.9.1.1.1.31.4.2.4
		dsAutoResetNetworkControlTimeStamp OBJECT-TYPE
			SYNTAX TimeTicks
			MAX-ACCESS read-only
			STATUS current
			DESCRIPTION
				"Description."
			::= { dsAutoResetNetworkControl 4 }

		
		-- 1.3.6.1.4.1.10428 9 1.9.1.1.1.31.4.2.5
		dsAutoResetNetworkControlReqResult OBJECT-TYPE
			SYNTAX FkControlRequestResultType
			MAX-ACCESS read-only
			STATUS current
			DESCRIPTION
				"Description."
			::= { dsAutoResetNetworkControl 5 }

		
		-- 1.3.6.1.4.1.10428 9 1.9.1.1.1.31.4.2.6
		dsAutoResetNetworkControlEnable OBJECT-TYPE
			SYNTAX INTEGER
				{
				disable(0),
				enable(1)
				}
			MAX-ACCESS read-write
			STATUS current
			DESCRIPTION
				"Indicates whether Network-based AutoReset is enabled or not."
			::= { dsAutoResetNetworkControl 6 }

		
		-- 1.3.6.1.4.1.10428 9 1.9.1.1.1.31.4.2.7
		dsAutoResetNetworkControlInterval OBJECT-TYPE
			SYNTAX INTEGER (1..60)
			MAX-ACCESS read-write
			STATUS current
			DESCRIPTION
				"The interval between ping request."
			::= { dsAutoResetNetworkControl 7 }

		
		-- 1.3.6.1.4.1.10428 9 1.9.1.1.1.31.4.2.8
		dsAutoResetNetworkControlCount OBJECT-TYPE
			SYNTAX INTEGER (1..60)
			MAX-ACCESS read-write
			STATUS current
			DESCRIPTION
				"The count of ping request
				AutoReset condition is met if there was no ping reply for the count of continuous ping request."
			::= { dsAutoResetNetworkControl 8 }

		
		-- 1.3.6.1.4.1.10428 9 1.9.1.1.1.31.4.2.9
		dsAutoResetNetworkControlTargetIp OBJECT-TYPE
			SYNTAX IpAddress
			MAX-ACCESS read-write
			STATUS current
			DESCRIPTION
				"The ping destination IP address"
			::= { dsAutoResetNetworkControl 9 }

		
		-- 1.3.6.1.4.1.10428 9 1.9.1.1.1.31.4.2.10
		dsAutoResetNetworkControlResetTime OBJECT-TYPE
			SYNTAX OCTET STRING
			MAX-ACCESS read-write
			STATUS current
			DESCRIPTION
				"The reboot time due to Network-based AutoReset.
				Format : hh:mm"
			::= { dsAutoResetNetworkControl 10 }

		
		-- 1.3.6.1.4.1.10428 9 1.9.1.1.1.31.4.3
		dsAutoResetNetworkNotification OBJECT IDENTIFIER ::= { dsAutoResetNetwork 3 }

		
		-- 1.3.6.1.4.1.10428 9 1.9.1.1.1.31.4.3.1
		dsAutoResetNetworkEnableChanged NOTIFICATION-TYPE
			OBJECTS { dsAutoResetMemoryControlRequest, dsAutoResetMemoryControlStatus, dsAutoResetMemoryControlTimer, dsAutoResetMemoryControlTimeStamp, dsAutoResetMemoryControlReqResult, 
				dsAutoResetMemoryControlEnable }
			STATUS current
			DESCRIPTION 
				"setAutoResetNetworkEnable"
			::= { dsAutoResetNetworkNotification 1 }

		
		-- 1.3.6.1.4.1.10428 9 1.9.1.1.1.31.5
		dsAutoResetProcess OBJECT IDENTIFIER ::= { dsAutoReset 5 }

		
		-- 1.3.6.1.4.1.10428 9 1.9.1.1.1.31.5.1
		dsAutoResetProcessInfo OBJECT IDENTIFIER ::= { dsAutoResetProcess 1 }

		
		-- 1.3.6.1.4.1.10428 9 1.9.1.1.1.31.5.1.1
		dsAutoResetProcessEnable OBJECT-TYPE
			SYNTAX INTEGER
				{
				disable(0),
				enable(1)
				}
			MAX-ACCESS read-only
			STATUS current
			DESCRIPTION
				"Indicates whether Process-based AutoReset is enabled or not."
			::= { dsAutoResetProcessInfo 1 }

		
		-- 1.3.6.1.4.1.10428 9 1.9.1.1.1.31.5.1.2
		dsAutoResetProcessResetTime OBJECT-TYPE
			SYNTAX OCTET STRING
			MAX-ACCESS read-only
			STATUS current
			DESCRIPTION
				"The reboot time due to Process-based AutoReset.
				Format : hh:mm"
			::= { dsAutoResetProcessInfo 2 }

		
		-- 1.3.6.1.4.1.10428 9 1.9.1.1.1.31.5.2
		dsAutoResetProcessControl OBJECT IDENTIFIER ::= { dsAutoResetProcess 2 }

		
		-- 1.3.6.1.4.1.10428 9 1.9.1.1.1.31.5.2.1
		dsAutoResetProcessControlRequest OBJECT-TYPE
			SYNTAX INTEGER { setAutoResetProcessEnable(1) }
			MAX-ACCESS read-write
			STATUS current
			DESCRIPTION
				"Description."
			::= { dsAutoResetProcessControl 1 }

		
		-- 1.3.6.1.4.1.10428 9 1.9.1.1.1.31.5.2.2
		dsAutoResetProcessControlStatus OBJECT-TYPE
			SYNTAX FkControlStatusType
			MAX-ACCESS read-only
			STATUS current
			DESCRIPTION
				"Description."
			::= { dsAutoResetProcessControl 2 }

		
		-- 1.3.6.1.4.1.10428 9 1.9.1.1.1.31.5.2.3
		dsAutoResetProcessControlTimer OBJECT-TYPE
			SYNTAX Gauge32
			MAX-ACCESS read-write
			STATUS current
			DESCRIPTION
				"Description."
			::= { dsAutoResetProcessControl 3 }

		
		-- 1.3.6.1.4.1.10428 9 1.9.1.1.1.31.5.2.4
		dsAutoResetProcessControlTimeStamp OBJECT-TYPE
			SYNTAX TimeTicks
			MAX-ACCESS read-only
			STATUS current
			DESCRIPTION
				"Description."
			::= { dsAutoResetProcessControl 4 }

		
		-- 1.3.6.1.4.1.10428 9 1.9.1.1.1.31.5.2.5
		dsAutoResetProcessControlReqResult OBJECT-TYPE
			SYNTAX FkControlRequestResultType
			MAX-ACCESS read-only
			STATUS current
			DESCRIPTION
				"Description."
			::= { dsAutoResetProcessControl 5 }

		
		-- 1.3.6.1.4.1.10428 9 1.9.1.1.1.31.5.2.6
		dsAutoResetProcessControlEnable OBJECT-TYPE
			SYNTAX INTEGER
				{
				disable(0),
				enable(1)
				}
			MAX-ACCESS read-write
			STATUS current
			DESCRIPTION
				"Indicates whether Process-based AutoReset is enabled or not."
			::= { dsAutoResetProcessControl 6 }

		
		-- 1.3.6.1.4.1.10428 9 1.9.1.1.1.31.5.2.7
		dsAutoResetProcessControlResetTime OBJECT-TYPE
			SYNTAX OCTET STRING
			MAX-ACCESS read-write
			STATUS current
			DESCRIPTION
				"Enables/Disables Y.1731 OAM on a trunk port"
			::= { dsAutoResetProcessControl 7 }

		
		-- 1.3.6.1.4.1.10428 9 1.9.1.1.1.31.5.3
		dsAutoResetProcessNotification OBJECT IDENTIFIER ::= { dsAutoResetProcess 3 }

		
		-- 1.3.6.1.4.1.10428 9 1.9.1.1.1.31.5.3.1
		dsAutoResetProcessEnableChanged NOTIFICATION-TYPE
			OBJECTS { dsAutoResetProcessControlRequest, dsAutoResetProcessControlStatus, dsAutoResetProcessControlTimer, dsAutoResetProcessControlTimeStamp, dsAutoResetProcessControlReqResult, 
				dsAutoResetProcessControlEnable }
			STATUS current
			DESCRIPTION 
				"setAutoResetProcessEnable"
			::= { dsAutoResetProcessNotification 1 }

		
		-- 1.3.6.1.4.1.10428 9 1.9.1.1.1.31.6
		dsAutoResetCpuNetwork OBJECT IDENTIFIER ::= { dsAutoReset 6 }

		
		-- 1.3.6.1.4.1.10428 9 1.9.1.1.1.31.6.1
		dsAutoResetCpuNetworkInfo OBJECT IDENTIFIER ::= { dsAutoResetCpuNetwork 1 }

		
		-- 1.3.6.1.4.1.10428 9 1.9.1.1.1.31.6.1.1
		dsAutoResetCpuNetworkEnable OBJECT-TYPE
			SYNTAX INTEGER
				{
				disable(0),
				enable(1)
				}
			MAX-ACCESS read-only
			STATUS current
			DESCRIPTION
				"Indicates whether CPU&Network-based AutoReset is enabled or not."
			::= { dsAutoResetCpuNetworkInfo 1 }

		
		-- 1.3.6.1.4.1.10428 9 1.9.1.1.1.31.6.1.2
		dsAutoResetCpuNetworkResetTime OBJECT-TYPE
			SYNTAX OCTET STRING
			MAX-ACCESS read-only
			STATUS current
			DESCRIPTION
				"The reboot time due to CPU&Network-based AutoReset.
				Format : hh:mm"
			::= { dsAutoResetCpuNetworkInfo 2 }

		
		-- 1.3.6.1.4.1.10428 9 1.9.1.1.1.31.6.1.3
		dsAutoResetCpuNetworkCpuEnable OBJECT-TYPE
			SYNTAX INTEGER
				{
				disable(0),
				enable(1)
				}
			MAX-ACCESS read-only
			STATUS current
			DESCRIPTION
				"Indicates whether CPU condition of the CPU&Network-based AutoReset is enabled or not."
			::= { dsAutoResetCpuNetworkInfo 3 }

		
		-- 1.3.6.1.4.1.10428 9 1.9.1.1.1.31.6.1.4
		dsAutoResetCpuNetworkCpuThresholdHigh OBJECT-TYPE
			SYNTAX INTEGER (1..100)
			MAX-ACCESS read-only
			STATUS current
			DESCRIPTION
				"High threshold for the CPU load."
			::= { dsAutoResetCpuNetworkInfo 4 }

		
		-- 1.3.6.1.4.1.10428 9 1.9.1.1.1.31.6.1.5
		dsAutoResetCpuNetworkCpuThresholdLow OBJECT-TYPE
			SYNTAX INTEGER (1..100)
			MAX-ACCESS read-only
			STATUS current
			DESCRIPTION
				"Low threshold for the CPU load."
			::= { dsAutoResetCpuNetworkInfo 5 }

		
		-- 1.3.6.1.4.1.10428 9 1.9.1.1.1.31.6.1.6
		dsAutoResetCpuNetworkCpuContinueTime OBJECT-TYPE
			SYNTAX INTEGER (1..3600)
			MAX-ACCESS read-only
			STATUS current
			DESCRIPTION
				"The time of duration.
				AutoReset condition is met if CPU load continuously exceeds the threshold during the given time."
			::= { dsAutoResetCpuNetworkInfo 6 }

		
		-- 1.3.6.1.4.1.10428 9 1.9.1.1.1.31.6.1.7
		dsAutoResetCpuNetworkNetworkEnable OBJECT-TYPE
			SYNTAX INTEGER
				{
				disable(0),
				enable(1)
				}
			MAX-ACCESS read-only
			STATUS current
			DESCRIPTION
				"Indicates whether Network condition of the CPU&Network-based AutoReset is enabled or not."
			::= { dsAutoResetCpuNetworkInfo 7 }

		
		-- 1.3.6.1.4.1.10428 9 1.9.1.1.1.31.6.1.8
		dsAutoResetCpuNetworkNetworkInterval OBJECT-TYPE
			SYNTAX INTEGER (1..100)
			MAX-ACCESS read-only
			STATUS current
			DESCRIPTION
				"The interval between ping request."
			::= { dsAutoResetCpuNetworkInfo 8 }

		
		-- 1.3.6.1.4.1.10428 9 1.9.1.1.1.31.6.1.9
		dsAutoResetCpuNetworkNetworkCount OBJECT-TYPE
			SYNTAX INTEGER (1..100)
			MAX-ACCESS read-only
			STATUS current
			DESCRIPTION
				"The count of ping request
				AutoReset condition is met if there was no ping reply for the count of continuous ping request."
			::= { dsAutoResetCpuNetworkInfo 9 }

		
		-- 1.3.6.1.4.1.10428 9 1.9.1.1.1.31.6.1.10
		dsAutoResetCpuNetworkNetworkTargetIp OBJECT-TYPE
			SYNTAX IpAddress
			MAX-ACCESS read-only
			STATUS current
			DESCRIPTION
				"The ping destination IP address"
			::= { dsAutoResetCpuNetworkInfo 10 }

		
		-- 1.3.6.1.4.1.10428 9 1.9.1.1.1.31.6.2
		dsAutoResetCpuNetworkControl OBJECT IDENTIFIER ::= { dsAutoResetCpuNetwork 2 }

		
		-- 1.3.6.1.4.1.10428 9 1.9.1.1.1.31.6.2.1
		dsAutoResetCpuNetworkControlRequest OBJECT-TYPE
			SYNTAX INTEGER
				{
				setAutoResetCpuNetworkEnable(1),
				setAutoResetCpuNetworkCpuEnable(2),
				setAutoResetCpuNetworkNetworkEnable(3)
				}
			MAX-ACCESS read-write
			STATUS current
			DESCRIPTION
				"Description."
			::= { dsAutoResetCpuNetworkControl 1 }

		
		-- 1.3.6.1.4.1.10428 9 1.9.1.1.1.31.6.2.2
		dsAutoResetCpuNetworkControlStatus OBJECT-TYPE
			SYNTAX FkControlStatusType
			MAX-ACCESS read-only
			STATUS current
			DESCRIPTION
				"Description."
			::= { dsAutoResetCpuNetworkControl 2 }

		
		-- 1.3.6.1.4.1.10428 9 1.9.1.1.1.31.6.2.3
		dsAutoResetCpuNetworkControlTimer OBJECT-TYPE
			SYNTAX Gauge32
			MAX-ACCESS read-write
			STATUS current
			DESCRIPTION
				"Description."
			::= { dsAutoResetCpuNetworkControl 3 }

		
		-- 1.3.6.1.4.1.10428 9 1.9.1.1.1.31.6.2.4
		dsAutoResetCpuNetworkControlTimeStamp OBJECT-TYPE
			SYNTAX TimeTicks
			MAX-ACCESS read-only
			STATUS current
			DESCRIPTION
				"Description."
			::= { dsAutoResetCpuNetworkControl 4 }

		
		-- 1.3.6.1.4.1.10428 9 1.9.1.1.1.31.6.2.5
		dsAutoResetCpuNetworkControlReqResult OBJECT-TYPE
			SYNTAX FkControlRequestResultType
			MAX-ACCESS read-only
			STATUS current
			DESCRIPTION
				"Description."
			::= { dsAutoResetCpuNetworkControl 5 }

		
		-- 1.3.6.1.4.1.10428 9 1.9.1.1.1.31.6.2.6
		dsAutoResetCpuNetworkControlEnable OBJECT-TYPE
			SYNTAX INTEGER
				{
				disable(0),
				enable(1)
				}
			MAX-ACCESS read-write
			STATUS current
			DESCRIPTION
				"Indicates whether CPU&Network-based AutoReset is enabled or not."
			::= { dsAutoResetCpuNetworkControl 6 }

		
		-- 1.3.6.1.4.1.10428 9 1.9.1.1.1.31.6.2.7
		dsAutoResetCpuNetworkControlResetTime OBJECT-TYPE
			SYNTAX OCTET STRING
			MAX-ACCESS read-write
			STATUS current
			DESCRIPTION
				"The reboot time due to CPU&Network-based AutoReset.
				Format : hh:mm"
			::= { dsAutoResetCpuNetworkControl 7 }

		
		-- 1.3.6.1.4.1.10428 9 1.9.1.1.1.31.6.2.8
		dsAutoResetCpuNetworkControlCpuEnable OBJECT-TYPE
			SYNTAX INTEGER
				{
				disable(0),
				enable(1)
				}
			MAX-ACCESS read-write
			STATUS current
			DESCRIPTION
				"Indicates whether CPU condition of the CPU&Network-based AutoReset is enabled or not."
			::= { dsAutoResetCpuNetworkControl 8 }

		
		-- 1.3.6.1.4.1.10428 9 1.9.1.1.1.31.6.2.9
		dsAutoResetCpuNetworkControlCpuThresholdHigh OBJECT-TYPE
			SYNTAX INTEGER (1..100)
			MAX-ACCESS read-write
			STATUS current
			DESCRIPTION
				"High threshold for the CPU load."
			::= { dsAutoResetCpuNetworkControl 9 }

		
		-- 1.3.6.1.4.1.10428 9 1.9.1.1.1.31.6.2.10
		dsAutoResetCpuNetworkControlCpuThresholdLow OBJECT-TYPE
			SYNTAX INTEGER (1..100)
			MAX-ACCESS read-write
			STATUS current
			DESCRIPTION
				"Low threshold for the CPU load."
			::= { dsAutoResetCpuNetworkControl 10 }

		
		-- 1.3.6.1.4.1.10428 9 1.9.1.1.1.31.6.2.11
		dsAutoResetCpuNetworkControlCpuContinueTime OBJECT-TYPE
			SYNTAX INTEGER (1..3600)
			MAX-ACCESS read-write
			STATUS current
			DESCRIPTION
				"The time of duration.
				AutoReset condition is met if CPU load continuously exceeds the threshold during the given time."
			::= { dsAutoResetCpuNetworkControl 11 }

		
		-- 1.3.6.1.4.1.10428 9 1.9.1.1.1.31.6.2.12
		dsAutoResetCpuNetworkControlNetworkEnable OBJECT-TYPE
			SYNTAX INTEGER
				{
				disable(0),
				enable(1)
				}
			MAX-ACCESS read-write
			STATUS current
			DESCRIPTION
				"Indicates whether Network condition of the CPU&Network-based AutoReset is enabled or not."
			::= { dsAutoResetCpuNetworkControl 12 }

		
		-- 1.3.6.1.4.1.10428 9 1.9.1.1.1.31.6.2.13
		dsAutoResetCpuNetworkControlNetworkInterval OBJECT-TYPE
			SYNTAX INTEGER (1..60)
			MAX-ACCESS read-write
			STATUS current
			DESCRIPTION
				"The interval between ping request."
			::= { dsAutoResetCpuNetworkControl 13 }

		
		-- 1.3.6.1.4.1.10428 9 1.9.1.1.1.31.6.2.14
		dsAutoResetCpuNetworkControlNetworkCount OBJECT-TYPE
			SYNTAX INTEGER (1..60)
			MAX-ACCESS read-write
			STATUS current
			DESCRIPTION
				"The count of ping request
				AutoReset condition is met if there was no ping reply for the count of continuous ping request."
			::= { dsAutoResetCpuNetworkControl 14 }

		
		-- 1.3.6.1.4.1.10428 9 1.9.1.1.1.31.6.2.15
		dsAutoResetCpuNetworkControlNetworkTargetIp OBJECT-TYPE
			SYNTAX IpAddress
			MAX-ACCESS read-write
			STATUS current
			DESCRIPTION
				"The ping destination IP address"
			::= { dsAutoResetCpuNetworkControl 15 }

		
		-- 1.3.6.1.4.1.10428 9 1.9.1.1.1.31.6.3
		dsAutoResetCpuNetworkNotification OBJECT IDENTIFIER ::= { dsAutoResetCpuNetwork 3 }

		
		-- 1.3.6.1.4.1.10428 9 1.9.1.1.1.31.6.3.1
		dsAutoResetCpuNetworkEnableChanged NOTIFICATION-TYPE
			OBJECTS { dsAutoResetCpuNetworkControlRequest, dsAutoResetCpuNetworkControlStatus, dsAutoResetCpuNetworkControlTimer, dsAutoResetCpuNetworkControlTimeStamp, dsAutoResetCpuNetworkControlReqResult, 
				dsAutoResetCpuNetworkControlEnable }
			STATUS current
			DESCRIPTION 
				"setAutoResetCpuNetworkEnable"
			::= { dsAutoResetCpuNetworkNotification 1 }

		
		-- 1.3.6.1.4.1.10428 9 1.9.1.1.1.31.6.3.2
		dsAutoResetCpuNetworkCpuEnableChanged NOTIFICATION-TYPE
			OBJECTS { dsAutoResetCpuNetworkControlRequest, dsAutoResetCpuNetworkControlStatus, dsAutoResetCpuNetworkControlTimer, dsAutoResetCpuNetworkControlTimeStamp, dsAutoResetCpuNetworkControlReqResult, 
				dsAutoResetCpuNetworkControlCpuEnable }
			STATUS current
			DESCRIPTION 
				"setAutoResetCpuNetworkCpuEnable"
			::= { dsAutoResetCpuNetworkNotification 2 }

		
		-- 1.3.6.1.4.1.10428 9 1.9.1.1.1.31.6.3.3
		dsAutoResetCpuNetworkNetworkEnableChanged NOTIFICATION-TYPE
			OBJECTS { dsAutoResetCpuNetworkControlRequest, dsAutoResetCpuNetworkControlStatus, dsAutoResetCpuNetworkControlTimer, dsAutoResetCpuNetworkControlTimeStamp, dsAutoResetCpuNetworkControlReqResult, 
				dsAutoResetCpuNetworkControlNetworkEnable }
			STATUS current
			DESCRIPTION 
				"setAutoResetCpuNetworkNetworkEnable"
			::= { dsAutoResetCpuNetworkNotification 3 }

		
	
	END

--
-- FKOLTG1040-AUTORESET-MIB.my
--
