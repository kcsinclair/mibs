--
-- fk-epon-mib.mib
-- MIB generated by MG-SOFT Visual MIB Builder Version 6.0  Build 88
-- Monday, April 08, 2013 at 20:02:37
--

	FK-EPON-MIB DEFINITIONS ::= BEGIN
 
		IMPORTS
			fkMgmt			
				FROM FKOLTG1040-SMI			
			ifIndex			
				FROM IF-MIB			
			VlanIndex, PortList			
				FROM Q-BRIDGE-MIB			
			sysDescr			
				FROM RFC1213-MIB			
			FkControlStatusType, FkControlRequestResultType			
				FROM FK-TC-MIB			
			OBJECT-GROUP, NOTIFICATION-GROUP			
				FROM SNMPv2-CONF			
			TimeTicks, IpAddress, Integer32, Gauge32, Counter32, 
			Counter64, OBJECT-TYPE, MODULE-IDENTITY, NOTIFICATION-TYPE			
				FROM SNMPv2-SMI			
			MacAddress, TEXTUAL-CONVENTION			
				FROM SNMPv2-TC;
	
	
		-- 1.3.6.1.4.1.10428 9 1.101.20
		fkEpon MODULE-IDENTITY 
			LAST-UPDATED "200601251753Z"		-- January 25, 2006 at 17:53 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 20 }

		
	
	
--
-- Textual conventions
--
	
		EnableFlag ::= TEXTUAL-CONVENTION
			STATUS current
			DESCRIPTION 
				"Description."
			SYNTAX INTEGER
				{
				enable(1),
				disable(2)
				}

	
--
-- Node definitions
--
	
		-- 1.3.6.1.4.1.10428 9 1.101.20.1
		fkEponBase OBJECT IDENTIFIER ::= { fkEpon 1 }

		
		-- 1.3.6.1.4.1.10428 9 1.101.20.1.1
		fkEponBaseInfo OBJECT IDENTIFIER ::= { fkEponBase 1 }

		
		-- 1.3.6.1.4.1.10428 9 1.101.20.1.1.1
		fkEponBaseSlaPlatoMaxBandwdith OBJECT-TYPE
			SYNTAX INTEGER (1000..900000 | 1000000)
			UNITS "kbps"
			MAX-ACCESS read-only
			STATUS current
			DESCRIPTION
				"Description."
			::= { fkEponBaseInfo 1 }

		
		-- 1.3.6.1.4.1.10428 9 1.101.20.1.1.2
		fkEponBaseDPShapingMaxBandwidth OBJECT-TYPE
			SYNTAX INTEGER (0 | 1000..900000)
			UNITS "kbps"
			MAX-ACCESS read-only
			STATUS current
			DESCRIPTION
				"Description."
			::= { fkEponBaseInfo 2 }

		
		-- 1.3.6.1.4.1.10428 9 1.101.20.1.1.3
		fkEponBasePortMaxHost OBJECT-TYPE
			SYNTAX INTEGER (0 | 1..16)
			MAX-ACCESS read-only
			STATUS current
			DESCRIPTION
				"Description."
			::= { fkEponBaseInfo 3 }

		
		-- 1.3.6.1.4.1.10428 9 1.101.20.1.1.4
		fkEponBaseOnuAutoUpgrade OBJECT-TYPE
			SYNTAX EnableFlag
			MAX-ACCESS read-only
			STATUS current
			DESCRIPTION
				"The status of ONU auto-upgrade."
			::= { fkEponBaseInfo 4 }

		
		-- 1.3.6.1.4.1.10428 9 1.101.20.1.1.5
		fkEponBaseOnuAutoUpgradeRebootTime OBJECT-TYPE
			SYNTAX INTEGER (-1 | 0..23)
			UNITS "hour"
			MAX-ACCESS read-only
			STATUS current
			DESCRIPTION
				"The reboot-time of ONU auto-upgrade."
			::= { fkEponBaseInfo 5 }

		
		-- 1.3.6.1.4.1.10428 9 1.101.20.1.1.6
		fkEponBaseOnuAgingTime OBJECT-TYPE
			SYNTAX Integer32 (0..30)
			UNITS "day"
			MAX-ACCESS read-only
			STATUS current
			DESCRIPTION
				"Description."
			::= { fkEponBaseInfo 6 }

		
		-- 1.3.6.1.4.1.10428 9 1.101.20.1.1.7
		fkEponBaseAlarmStatus OBJECT-TYPE
			SYNTAX BITS
				{
				critical(0),
				major(1),
				minor(2)
				}
			MAX-ACCESS read-only
			STATUS current
			DESCRIPTION
				"Description."
			::= { fkEponBaseInfo 7 }

		
		-- 1.3.6.1.4.1.10428 9 1.101.20.1.1.8
		fkEponBaseAlarmMode OBJECT-TYPE
			SYNTAX INTEGER
				{
				auto(0),
				manual(1)
				}
			MAX-ACCESS read-only
			STATUS current
			DESCRIPTION
				"Description."
			::= { fkEponBaseInfo 8 }

		
		-- 1.3.6.1.4.1.10428 9 1.101.20.1.2
		fkEponBaseControl OBJECT IDENTIFIER ::= { fkEponBase 2 }

		
		-- 1.3.6.1.4.1.10428 9 1.101.20.1.2.1
		fkEponBaseControlRequest OBJECT-TYPE
			SYNTAX INTEGER
				{
				setEponBaseDefaultBandwidth(1),
				setEponBaseDefaultMaxhost(2),
				setEponBaseOnuAutoUpgrade(3),
				setEponBaseOnuAgingTime(4),
				setEponBaseAlarmStatus(5),
				setEponBaseAlarmMode(6)
				}
			MAX-ACCESS read-write
			STATUS current
			DESCRIPTION
				"Description."
			::= { fkEponBaseControl 1 }

		
		-- 1.3.6.1.4.1.10428 9 1.101.20.1.2.2
		fkEponBaseControlStatus OBJECT-TYPE
			SYNTAX FkControlStatusType
			MAX-ACCESS read-only
			STATUS current
			DESCRIPTION
				"Description."
			::= { fkEponBaseControl 2 }

		
		-- 1.3.6.1.4.1.10428 9 1.101.20.1.2.3
		fkEponBaseControlTimer OBJECT-TYPE
			SYNTAX Gauge32
			MAX-ACCESS read-write
			STATUS current
			DESCRIPTION
				"Description."
			::= { fkEponBaseControl 3 }

		
		-- 1.3.6.1.4.1.10428 9 1.101.20.1.2.4
		fkEponBaseControlTimeStamp OBJECT-TYPE
			SYNTAX TimeTicks
			MAX-ACCESS read-only
			STATUS current
			DESCRIPTION
				"Description."
			::= { fkEponBaseControl 4 }

		
		-- 1.3.6.1.4.1.10428 9 1.101.20.1.2.5
		fkEponBaseControlReqResult OBJECT-TYPE
			SYNTAX FkControlRequestResultType
			MAX-ACCESS read-only
			STATUS current
			DESCRIPTION
				"Description."
			::= { fkEponBaseControl 5 }

		
		-- 1.3.6.1.4.1.10428 9 1.101.20.1.2.6
		fkEponBaseControlSlaPlatoMaxBandwdith OBJECT-TYPE
			SYNTAX INTEGER (1000..900000 | 1000000)
			UNITS "kbps"
			MAX-ACCESS read-write
			STATUS current
			DESCRIPTION
				"Description."
			::= { fkEponBaseControl 6 }

		
		-- 1.3.6.1.4.1.10428 9 1.101.20.1.2.7
		fkEponBaseControlDPShapingMaxBandwidth OBJECT-TYPE
			SYNTAX INTEGER (0 | 1000..900000)
			UNITS "Mbps"
			MAX-ACCESS read-write
			STATUS current
			DESCRIPTION
				"Description."
			::= { fkEponBaseControl 7 }

		
		-- 1.3.6.1.4.1.10428 9 1.101.20.1.2.8
		fkEponBaseControlPortMaxHost OBJECT-TYPE
			SYNTAX INTEGER (0 | 1..16)
			MAX-ACCESS read-write
			STATUS current
			DESCRIPTION
				"Description."
			::= { fkEponBaseControl 8 }

		
		-- 1.3.6.1.4.1.10428 9 1.101.20.1.2.9
		fkEponBaseControlOnuAutoUpgrade OBJECT-TYPE
			SYNTAX EnableFlag
			MAX-ACCESS read-write
			STATUS current
			DESCRIPTION
				"The status of ONU auto-upgrade."
			::= { fkEponBaseControl 9 }

		
		-- 1.3.6.1.4.1.10428 9 1.101.20.1.2.10
		fkEponBaseControlOnuAutoUpgradeRebootTime OBJECT-TYPE
			SYNTAX INTEGER (-1 | 0..23)
			UNITS "hour"
			MAX-ACCESS read-write
			STATUS current
			DESCRIPTION
				"The reboot-time of ONU auto-upgrade."
			::= { fkEponBaseControl 10 }

		
		-- 1.3.6.1.4.1.10428 9 1.101.20.1.2.11
		fkEponBaseControlOnuAgingTime OBJECT-TYPE
			SYNTAX Integer32 (0..30)
			UNITS "day"
			MAX-ACCESS read-write
			STATUS current
			DESCRIPTION
				"Description."
			::= { fkEponBaseControl 11 }

		
		-- 1.3.6.1.4.1.10428 9 1.101.20.1.2.12
		fkEponBaseControlAlarmStatus OBJECT-TYPE
			SYNTAX BITS
				{
				critical(0),
				major(1),
				minor(2)
				}
			MAX-ACCESS read-write
			STATUS current
			DESCRIPTION
				"Description."
			::= { fkEponBaseControl 12 }

		
		-- 1.3.6.1.4.1.10428 9 1.101.20.1.2.13
		fkEponBaseControlAlarmMode OBJECT-TYPE
			SYNTAX INTEGER
				{
				auto(0),
				manual(1)
				}
			MAX-ACCESS read-write
			STATUS current
			DESCRIPTION
				"Description."
			::= { fkEponBaseControl 13 }

		
		-- 1.3.6.1.4.1.10428 9 1.101.20.1.3
		fkEponBaseNotification OBJECT IDENTIFIER ::= { fkEponBase 3 }

		
		-- 1.3.6.1.4.1.10428 9 1.101.20.1.3.1
		fkEponBaseDefaultBandwidthChanged NOTIFICATION-TYPE
			OBJECTS { fkEponBaseControlRequest, fkEponBaseControlTimeStamp, fkEponBaseControlReqResult, fkEponBaseControlSlaPlatoMaxBandwdith, fkEponBaseControlDPShapingMaxBandwidth
				 }
			STATUS current
			DESCRIPTION 
				"Description."
			::= { fkEponBaseNotification 1 }

		
		-- 1.3.6.1.4.1.10428 9 1.101.20.1.3.2
		fkEponBaseDefaultMaxHost NOTIFICATION-TYPE
			OBJECTS { fkEponBaseControlRequest, fkEponBaseControlTimeStamp, fkEponBaseControlReqResult, fkEponBaseControlPortMaxHost }
			STATUS current
			DESCRIPTION 
				"Description."
			::= { fkEponBaseNotification 2 }

		
		-- 1.3.6.1.4.1.10428 9 1.101.20.1.3.3
		fkEponBaseOnuAutoUpgradeChanged NOTIFICATION-TYPE
			OBJECTS { fkEponBaseControlRequest, fkEponBaseControlTimeStamp, fkEponBaseControlReqResult, fkEponBaseControlOnuAutoUpgrade, fkEponBaseControlOnuAutoUpgradeRebootTime
				 }
			STATUS current
			DESCRIPTION 
				"Description."
			::= { fkEponBaseNotification 3 }

		
		-- 1.3.6.1.4.1.10428 9 1.101.20.1.3.4
		fkEponBaseOnuAgingTimeChanged NOTIFICATION-TYPE
			OBJECTS { fkEponBaseControlRequest, fkEponBaseControlTimeStamp, fkEponBaseControlReqResult, fkEponBaseControlOnuAgingTime }
			STATUS current
			DESCRIPTION 
				"Description."
			::= { fkEponBaseNotification 4 }

		
		-- 1.3.6.1.4.1.10428 9 1.101.20.1.3.5
		fkEponBaseAlarmStatusChanged NOTIFICATION-TYPE
			OBJECTS { fkEponBaseControlRequest, fkEponBaseControlTimeStamp, fkEponBaseControlReqResult, fkEponBaseControlAlarmStatus }
			STATUS current
			DESCRIPTION 
				"Description."
			::= { fkEponBaseNotification 5 }

		
		-- 1.3.6.1.4.1.10428 9 1.101.20.1.3.6
		fkEponBaseAlarmModeChanged NOTIFICATION-TYPE
			OBJECTS { fkEponBaseControlRequest, fkEponBaseControlTimeStamp, fkEponBaseControlReqResult, fkEponBaseAlarmMode }
			STATUS current
			DESCRIPTION 
				"Description."
			::= { fkEponBaseNotification 6 }

		
		-- 1.3.6.1.4.1.10428 9 1.101.20.2
		fkEponOlt OBJECT IDENTIFIER ::= { fkEpon 2 }

		
		-- 1.3.6.1.4.1.10428 9 1.101.20.2.1
		fkEponOltTable OBJECT-TYPE
			SYNTAX SEQUENCE OF FkEponOltEntry
			MAX-ACCESS not-accessible
			STATUS current
			DESCRIPTION
				"Description."
			::= { fkEponOlt 1 }

		
		-- 1.3.6.1.4.1.10428 9 1.101.20.2.1.1
		fkEponOltEntry OBJECT-TYPE
			SYNTAX FkEponOltEntry
			MAX-ACCESS not-accessible
			STATUS current
			DESCRIPTION
				"Description."
			INDEX { fkEponOltIndex }
			::= { fkEponOltTable 1 }

		
		FkEponOltEntry ::=
			SEQUENCE { 
				fkEponOltIndex
					INTEGER,
				fkEponOltRegMode
					INTEGER,
				fkEponOltStatus
					EnableFlag,
				fkEponOltEncryptionPolicy
					INTEGER,
				fkEponOltP2pAccessControl
					EnableFlag,
				fkEponOltDbaInternal
					EnableFlag,
				fkEponOltDbaCycle
					INTEGER,
				fkEponOltDbaDiscoveryFrequency
					INTEGER,
				fkEponOltDbaDiscoveryLength
					INTEGER,
				fkEponOltProfile
					OCTET STRING,
				fkEponOltTxFault
					INTEGER,
				fkEponOltLossOfSignal
					INTEGER,
				fkEponOltAdminRegMode
					INTEGER,
				fkEponOltSC
					EnableFlag,
				fkEponOltSCAutoOnuBlock
					EnableFlag,
				fkEponOltOperStatus
					INTEGER,
				fkEponOltFirmwareRev
					OCTET STRING,
				fkEponOltKeyExchangeTimeout
					INTEGER,
				fkEponOltRssiStatus
					EnableFlag,
				fkEponOltOnuRegisterCount
					INTEGER
			 }

		-- 1.3.6.1.4.1.10428 9 1.101.20.2.1.1.1
		fkEponOltIndex OBJECT-TYPE
			SYNTAX INTEGER (1..512)
			MAX-ACCESS read-only
			STATUS current
			DESCRIPTION
				"OLT port Index"
			::= { fkEponOltEntry 1 }

		
		-- 1.3.6.1.4.1.10428 9 1.101.20.2.1.1.2
		fkEponOltRegMode OBJECT-TYPE
			SYNTAX INTEGER
				{
				auto(1),
				manual(2),
				fixed(3),
				autoToManual(4),
				webBasedRegistry(5)
				}
			MAX-ACCESS read-only
			STATUS current
			DESCRIPTION
				"OLT port registeraton Mode {auto(1), manual(2)}"
			DEFVAL { auto }
			::= { fkEponOltEntry 2 }

		
		-- 1.3.6.1.4.1.10428 9 1.101.20.2.1.1.3
		fkEponOltStatus OBJECT-TYPE
			SYNTAX EnableFlag
			MAX-ACCESS read-only
			STATUS current
			DESCRIPTION
				"OLT port status "
			::= { fkEponOltEntry 3 }

		
		-- 1.3.6.1.4.1.10428 9 1.101.20.2.1.1.4
		fkEponOltEncryptionPolicy OBJECT-TYPE
			SYNTAX INTEGER
				{
				disable(1),
				down(2),
				both(3)
				}
			MAX-ACCESS read-only
			STATUS current
			DESCRIPTION
				"OLT port encryption policy"
			DEFVAL { disable }
			::= { fkEponOltEntry 4 }

		
		-- 1.3.6.1.4.1.10428 9 1.101.20.2.1.1.5
		fkEponOltP2pAccessControl OBJECT-TYPE
			SYNTAX EnableFlag
			MAX-ACCESS read-only
			STATUS current
			DESCRIPTION
				"OLT port p2p access Control "
			DEFVAL { disable }
			::= { fkEponOltEntry 5 }

		
		-- 1.3.6.1.4.1.10428 9 1.101.20.2.1.1.6
		fkEponOltDbaInternal OBJECT-TYPE
			SYNTAX EnableFlag
			MAX-ACCESS read-only
			STATUS current
			DESCRIPTION
				"OLT port DBA internal "
			DEFVAL { disable }
			::= { fkEponOltEntry 6 }

		
		-- 1.3.6.1.4.1.10428 9 1.101.20.2.1.1.7
		fkEponOltDbaCycle OBJECT-TYPE
			SYNTAX INTEGER (0 | 200..16777215)
			MAX-ACCESS read-only
			STATUS current
			DESCRIPTION
				"OLT port DBA cycle "
			::= { fkEponOltEntry 7 }

		
		-- 1.3.6.1.4.1.10428 9 1.101.20.2.1.1.8
		fkEponOltDbaDiscoveryFrequency OBJECT-TYPE
			SYNTAX INTEGER (0 | 1..65535)
			MAX-ACCESS read-only
			STATUS current
			DESCRIPTION
				"OLT port DBA Discovery Frequency"
			::= { fkEponOltEntry 8 }

		
		-- 1.3.6.1.4.1.10428 9 1.101.20.2.1.1.9
		fkEponOltDbaDiscoveryLength OBJECT-TYPE
			SYNTAX INTEGER (0 | 1..65535)
			MAX-ACCESS read-only
			STATUS current
			DESCRIPTION
				"OLT port DBA Discovery Length"
			::= { fkEponOltEntry 9 }

		
		-- 1.3.6.1.4.1.10428 9 1.101.20.2.1.1.10
		fkEponOltProfile OBJECT-TYPE
			SYNTAX OCTET STRING (SIZE (1..64))
			MAX-ACCESS read-only
			STATUS current
			DESCRIPTION
				"OLT port auto profile name"
			::= { fkEponOltEntry 10 }

		
		-- 1.3.6.1.4.1.10428 9 1.101.20.2.1.1.11
		fkEponOltTxFault OBJECT-TYPE
			SYNTAX INTEGER
				{
				unknown(0),
				normal(1),
				lagerFault(2)
				}
			MAX-ACCESS read-only
			STATUS current
			DESCRIPTION
				"This object indicates the status of Tx fault."
			::= { fkEponOltEntry 11 }

		
		-- 1.3.6.1.4.1.10428 9 1.101.20.2.1.1.12
		fkEponOltLossOfSignal OBJECT-TYPE
			SYNTAX INTEGER
				{
				unknown(0),
				normal(1),
				loss(2)
				}
			MAX-ACCESS read-only
			STATUS current
			DESCRIPTION
				"This object indicates the status of loss of signal"
			::= { fkEponOltEntry 12 }

		
		-- 1.3.6.1.4.1.10428 9 1.101.20.2.1.1.13
		fkEponOltAdminRegMode OBJECT-TYPE
			SYNTAX INTEGER
				{
				auto(1),
				manual(2),
				autoToManual(3),
				webBasedRegistry(4)
				}
			MAX-ACCESS read-only
			STATUS current
			DESCRIPTION
				"OLT port admin registeraton Mode {auto(1), manual(2), auto-to-manual(3), web-based-registry(4)}"
			::= { fkEponOltEntry 13 }

		
		-- 1.3.6.1.4.1.10428 9 1.101.20.2.1.1.14
		fkEponOltSC OBJECT-TYPE
			SYNTAX EnableFlag
			MAX-ACCESS read-only
			STATUS current
			DESCRIPTION
				"Description."
			::= { fkEponOltEntry 14 }

		
		-- 1.3.6.1.4.1.10428 9 1.101.20.2.1.1.15
		fkEponOltSCAutoOnuBlock OBJECT-TYPE
			SYNTAX EnableFlag
			MAX-ACCESS read-only
			STATUS current
			DESCRIPTION
				"Description."
			::= { fkEponOltEntry 15 }

		
		-- 1.3.6.1.4.1.10428 9 1.101.20.2.1.1.16
		fkEponOltOperStatus OBJECT-TYPE
			SYNTAX INTEGER
				{
				up(1),
				down(2),
				cableDown(3)
				}
			MAX-ACCESS read-only
			STATUS current
			DESCRIPTION
				"Description."
			::= { fkEponOltEntry 16 }

		
		-- 1.3.6.1.4.1.10428 9 1.101.20.2.1.1.17
		fkEponOltFirmwareRev OBJECT-TYPE
			SYNTAX OCTET STRING (SIZE (1..64))
			MAX-ACCESS read-only
			STATUS current
			DESCRIPTION
				"The firmware revision of OLT port."
			::= { fkEponOltEntry 17 }

		
		-- 1.3.6.1.4.1.10428 9 1.101.20.2.1.1.18
		fkEponOltKeyExchangeTimeout OBJECT-TYPE
			SYNTAX INTEGER (600..65535)
			MAX-ACCESS read-only
			STATUS current
			DESCRIPTION
				"Key Exchange Timeout"
			::= { fkEponOltEntry 18 }

		
		-- 1.3.6.1.4.1.10428 9 1.101.20.2.1.1.19
		fkEponOltRssiStatus OBJECT-TYPE
			SYNTAX EnableFlag
			MAX-ACCESS read-only
			STATUS current
			DESCRIPTION
				"Epon olt rssi disable/enable."
			::= { fkEponOltEntry 19 }

		
		-- 1.3.6.1.4.1.10428 9 1.101.20.2.1.1.20
		fkEponOltOnuRegisterCount OBJECT-TYPE
			SYNTAX INTEGER (1..32)
			MAX-ACCESS read-only
			STATUS current
			DESCRIPTION
				"onu register count."
			::= { fkEponOltEntry 20 }

		
		-- 1.3.6.1.4.1.10428 9 1.101.20.2.2
		fkEponOltControl OBJECT IDENTIFIER ::= { fkEponOlt 2 }

		
		-- 1.3.6.1.4.1.10428 9 1.101.20.2.2.1
		fkEponOltControlRequest OBJECT-TYPE
			SYNTAX INTEGER
				{
				setEponOltRegMode(1),
				setEponOltStatus(2),
				setEponOltAttributes(3),
				setEponOltProfile(4),
				setEponOltAttributeSC(5),
				setEponOltUpgrade(6),
				setEponOltReset(7),
				setEponOltRssiStatus(8)
				}
			MAX-ACCESS read-write
			STATUS current
			DESCRIPTION
				"The request of a user command"
			::= { fkEponOltControl 1 }

		
		-- 1.3.6.1.4.1.10428 9 1.101.20.2.2.2
		fkEponOltControlStatus OBJECT-TYPE
			SYNTAX FkControlStatusType
			MAX-ACCESS read-only
			STATUS current
			DESCRIPTION
				"The status of user command"
			::= { fkEponOltControl 2 }

		
		-- 1.3.6.1.4.1.10428 9 1.101.20.2.2.3
		fkEponOltControlTimer OBJECT-TYPE
			SYNTAX Gauge32
			MAX-ACCESS read-write
			STATUS current
			DESCRIPTION
				"The maximum time for the manager for a long running user command"
			::= { fkEponOltControl 3 }

		
		-- 1.3.6.1.4.1.10428 9 1.101.20.2.2.4
		fkEponOltControlTimeStamp OBJECT-TYPE
			SYNTAX TimeTicks
			MAX-ACCESS read-only
			STATUS current
			DESCRIPTION
				"The time stamp of the last command(end of command)"
			::= { fkEponOltControl 4 }

		
		-- 1.3.6.1.4.1.10428 9 1.101.20.2.2.5
		fkEponOltControlReqResult OBJECT-TYPE
			SYNTAX FkControlRequestResultType
			MAX-ACCESS read-only
			STATUS current
			DESCRIPTION
				"The result of the last user command"
			::= { fkEponOltControl 5 }

		
		-- 1.3.6.1.4.1.10428 9 1.101.20.2.2.6
		fkEponOltControlOltIndex OBJECT-TYPE
			SYNTAX Integer32
			MAX-ACCESS read-write
			STATUS current
			DESCRIPTION
				"OLT port Index"
			::= { fkEponOltControl 6 }

		
		-- 1.3.6.1.4.1.10428 9 1.101.20.2.2.7
		fkEponOltControlRegMode OBJECT-TYPE
			SYNTAX INTEGER
				{
				auto(1),
				manual(2),
				fixed(3),
				autoToManual(4),
				webBasedRegistry(5)
				}
			MAX-ACCESS read-write
			STATUS current
			DESCRIPTION
				"auto(1), manual(2), fixed(3) / DEFVAL : auto"
			DEFVAL { auto }
			::= { fkEponOltControl 7 }

		
		-- 1.3.6.1.4.1.10428 9 1.101.20.2.2.8
		fkEponOltControlOltStatus OBJECT-TYPE
			SYNTAX EnableFlag
			MAX-ACCESS read-write
			STATUS current
			DESCRIPTION
				"enable(1), disable(2)"
			::= { fkEponOltControl 8 }

		
		-- 1.3.6.1.4.1.10428 9 1.101.20.2.2.9
		fkEponOltControlEncryptionPolicy OBJECT-TYPE
			SYNTAX INTEGER
				{
				disable(1),
				down(2),
				both(3)
				}
			MAX-ACCESS read-write
			STATUS current
			DESCRIPTION
				"disable(1), down(2), both(3) / DEFVAL : disable"
			DEFVAL { disable }
			::= { fkEponOltControl 9 }

		
		-- 1.3.6.1.4.1.10428 9 1.101.20.2.2.10
		fkEponOltControlP2pAccessControl OBJECT-TYPE
			SYNTAX EnableFlag
			MAX-ACCESS read-write
			STATUS current
			DESCRIPTION
				"enable(1), disable(2)  / DEFVAL : disable "
			DEFVAL { disable }
			::= { fkEponOltControl 10 }

		
		-- 1.3.6.1.4.1.10428 9 1.101.20.2.2.11
		fkEponOltControlDbaInternal OBJECT-TYPE
			SYNTAX EnableFlag
			MAX-ACCESS read-write
			STATUS current
			DESCRIPTION
				"enable(1), disable(2)  / DEFVAL : disable"
			DEFVAL { disable }
			::= { fkEponOltControl 11 }

		
		-- 1.3.6.1.4.1.10428 9 1.101.20.2.2.12
		fkEponOltControlDbaCycle OBJECT-TYPE
			SYNTAX INTEGER (200..16777215)
			MAX-ACCESS read-write
			STATUS current
			DESCRIPTION
				"< 0 | 200..16777215>  / DEFVAL : 65536"
			DEFVAL { 65536 }
			::= { fkEponOltControl 12 }

		
		-- 1.3.6.1.4.1.10428 9 1.101.20.2.2.13
		fkEponOltControlDbaDiscoveryFrequency OBJECT-TYPE
			SYNTAX INTEGER (1..65535)
			MAX-ACCESS read-write
			STATUS current
			DESCRIPTION
				"< 0 | 1..65535>  /DEFVAL : 1792"
			DEFVAL { 1792 }
			::= { fkEponOltControl 13 }

		
		-- 1.3.6.1.4.1.10428 9 1.101.20.2.2.14
		fkEponOltControlDbaDiscoveryLength OBJECT-TYPE
			SYNTAX INTEGER (1..65535)
			MAX-ACCESS read-write
			STATUS current
			DESCRIPTION
				"< 0 | 1..65535>  /DEFVAL : 500"
			DEFVAL { 500 }
			::= { fkEponOltControl 14 }

		
		-- 1.3.6.1.4.1.10428 9 1.101.20.2.2.15
		fkEponOltControlProfile OBJECT-TYPE
			SYNTAX OCTET STRING (SIZE (1..64))
			MAX-ACCESS read-write
			STATUS current
			DESCRIPTION
				"OLT port auto profile name"
			::= { fkEponOltControl 15 }

		
		-- 1.3.6.1.4.1.10428 9 1.101.20.2.2.16
		fkEponOltControlSC OBJECT-TYPE
			SYNTAX EnableFlag
			MAX-ACCESS read-write
			STATUS current
			DESCRIPTION
				"Description."
			::= { fkEponOltControl 16 }

		
		-- 1.3.6.1.4.1.10428 9 1.101.20.2.2.17
		fkEponOltControlSCAutoOnuBlock OBJECT-TYPE
			SYNTAX EnableFlag
			MAX-ACCESS read-write
			STATUS current
			DESCRIPTION
				"Description."
			::= { fkEponOltControl 17 }

		
		-- 1.3.6.1.4.1.10428 9 1.101.20.2.2.18
		fkEponOltControlUpgradeFilename OBJECT-TYPE
			SYNTAX OCTET STRING (SIZE (1..64))
			MAX-ACCESS read-write
			STATUS current
			DESCRIPTION
				"Description."
			::= { fkEponOltControl 18 }

		
		-- 1.3.6.1.4.1.10428 9 1.101.20.2.2.19
		fkEponOltControlKeyExchangeTimeout OBJECT-TYPE
			SYNTAX INTEGER (600..65535)
			MAX-ACCESS read-write
			STATUS current
			DESCRIPTION
				"Key Exchange Timeout"
			::= { fkEponOltControl 19 }

		
		-- 1.3.6.1.4.1.10428 9 1.101.20.2.2.20
		fkEponOltControlRssiStatus OBJECT-TYPE
			SYNTAX EnableFlag
			MAX-ACCESS read-write
			STATUS current
			DESCRIPTION
				"Epon olt rssi disable/enable."
			::= { fkEponOltControl 20 }

		
		-- 1.3.6.1.4.1.10428 9 1.101.20.2.3
		fkEponOltNotification OBJECT IDENTIFIER ::= { fkEponOlt 3 }

		
		-- 1.3.6.1.4.1.10428 9 1.101.20.2.3.1
		fkEponOltRegModeChanged NOTIFICATION-TYPE
			OBJECTS { fkEponOltControlRequest, fkEponOltControlTimeStamp, fkEponOltControlReqResult, fkEponOltControlOltIndex, fkEponOltControlRegMode
				 }
			STATUS current
			DESCRIPTION 
				"Description."
			::= { fkEponOltNotification 1 }

		
		-- 1.3.6.1.4.1.10428 9 1.101.20.2.3.2
		fkEponOltStatusChanged NOTIFICATION-TYPE
			OBJECTS { fkEponOltControlRequest, fkEponOltControlTimeStamp, fkEponOltControlReqResult, fkEponOltControlOltIndex, fkEponOltControlOltStatus
				 }
			STATUS current
			DESCRIPTION 
				"Description."
			::= { fkEponOltNotification 2 }

		
		-- 1.3.6.1.4.1.10428 9 1.101.20.2.3.3
		fkEponOltAttributesChanged NOTIFICATION-TYPE
			OBJECTS { fkEponOltControlRequest, fkEponOltControlTimeStamp, fkEponOltControlReqResult, fkEponOltControlOltIndex, fkEponOltControlDbaInternal, 
				fkEponOltControlDbaCycle, fkEponOltControlDbaDiscoveryFrequency, fkEponOltControlDbaDiscoveryLength }
			STATUS current
			DESCRIPTION 
				"Description."
			::= { fkEponOltNotification 3 }

		
		-- 1.3.6.1.4.1.10428 9 1.101.20.2.3.4
		fkEponOltProfileChanged NOTIFICATION-TYPE
			OBJECTS { fkEponOltControlRequest, fkEponOltControlTimeStamp, fkEponOltControlReqResult, fkEponOltControlOltIndex, fkEponOltControlProfile
				 }
			STATUS current
			DESCRIPTION 
				"Description."
			::= { fkEponOltNotification 4 }

		
		-- 1.3.6.1.4.1.10428 9 1.101.20.2.3.5
		fkEponOltSCChanged NOTIFICATION-TYPE
			OBJECTS { fkEponOltControlRequest, fkEponOltControlTimeStamp, fkEponOltControlReqResult, fkEponOltControlOltIndex, fkEponOltControlSC, 
				fkEponOltControlSCAutoOnuBlock }
			STATUS current
			DESCRIPTION 
				"Description."
			::= { fkEponOltNotification 5 }

		
		-- 1.3.6.1.4.1.10428 9 1.101.20.2.3.6
		fkEponOltUpgraded NOTIFICATION-TYPE
			OBJECTS { fkEponOltControlRequest, fkEponOltControlTimeStamp, fkEponOltControlReqResult, fkEponOltControlOltIndex, fkEponOltControlUpgradeFilename
				 }
			STATUS current
			DESCRIPTION 
				"Description."
			::= { fkEponOltNotification 6 }

		
		-- 1.3.6.1.4.1.10428 9 1.101.20.2.3.7
		fkEponOltReset NOTIFICATION-TYPE
			OBJECTS { fkEponOltControlRequest, fkEponOltControlTimeStamp, fkEponOltControlReqResult, fkEponOltControlOltIndex }
			STATUS current
			DESCRIPTION 
				"Description."
			::= { fkEponOltNotification 7 }

		
		-- 1.3.6.1.4.1.10428 9 1.101.20.2.3.8
		fkEponOltRssiStatusChanged NOTIFICATION-TYPE
			OBJECTS { fkEponOltControlRequest, fkEponOltControlTimeStamp, fkEponOltControlReqResult, fkEponOltControlOltIndex, fkEponOltControlRssiStatus
				 }
			STATUS current
			DESCRIPTION 
				"Description."
			::= { fkEponOltNotification 8 }

		
		-- 1.3.6.1.4.1.10428 9 1.101.20.2.4
		fkEponOltP2PTable OBJECT-TYPE
			SYNTAX SEQUENCE OF FkEponOltP2PEntry
			MAX-ACCESS not-accessible
			STATUS current
			DESCRIPTION
				"Description."
			::= { fkEponOlt 4 }

		
		-- 1.3.6.1.4.1.10428 9 1.101.20.2.4.1
		fkEponOltP2PEntry OBJECT-TYPE
			SYNTAX FkEponOltP2PEntry
			MAX-ACCESS not-accessible
			STATUS current
			DESCRIPTION
				"Description."
			INDEX { fkEponOltIndex, fkEponOltP2PIndex }
			::= { fkEponOltP2PTable 1 }

		
		FkEponOltP2PEntry ::=
			SEQUENCE { 
				fkEponOltP2PIndex
					INTEGER,
				fkEponOltP2PEnable
					OCTET STRING,
				fkEponOltP2POnuID1
					Integer32,
				fkEponOltP2POnuID2
					Integer32
			 }

		-- 1.3.6.1.4.1.10428 9 1.101.20.2.4.1.1
		fkEponOltP2PIndex OBJECT-TYPE
			SYNTAX INTEGER (1..20)
			MAX-ACCESS read-only
			STATUS current
			DESCRIPTION
				"p2p index"
			::= { fkEponOltP2PEntry 1 }

		
		-- 1.3.6.1.4.1.10428 9 1.101.20.2.4.1.2
		fkEponOltP2PEnable OBJECT-TYPE
			SYNTAX OCTET STRING
			MAX-ACCESS read-only
			STATUS current
			DESCRIPTION
				"status of p2p access control : enable "
			::= { fkEponOltP2PEntry 2 }

		
		-- 1.3.6.1.4.1.10428 9 1.101.20.2.4.1.3
		fkEponOltP2POnuID1 OBJECT-TYPE
			SYNTAX Integer32 (1..64)
			MAX-ACCESS read-only
			STATUS current
			DESCRIPTION
				"p2p onu id 1"
			::= { fkEponOltP2PEntry 3 }

		
		-- 1.3.6.1.4.1.10428 9 1.101.20.2.4.1.4
		fkEponOltP2POnuID2 OBJECT-TYPE
			SYNTAX Integer32 (1..64)
			MAX-ACCESS read-only
			STATUS current
			DESCRIPTION
				"p2p onu id 2"
			::= { fkEponOltP2PEntry 4 }

		
		-- 1.3.6.1.4.1.10428 9 1.101.20.2.5
		fkEponOltP2PControl OBJECT IDENTIFIER ::= { fkEponOlt 5 }

		
		-- 1.3.6.1.4.1.10428 9 1.101.20.2.5.1
		fkEponOltP2PControlRequest OBJECT-TYPE
			SYNTAX INTEGER { setEponOltP2PAccessControl(1) }
			MAX-ACCESS read-write
			STATUS current
			DESCRIPTION
				"The request of a user command"
			::= { fkEponOltP2PControl 1 }

		
		-- 1.3.6.1.4.1.10428 9 1.101.20.2.5.2
		fkEponOltP2PControlStatus OBJECT-TYPE
			SYNTAX FkControlStatusType
			MAX-ACCESS read-only
			STATUS current
			DESCRIPTION
				"The status of user command"
			::= { fkEponOltP2PControl 2 }

		
		-- 1.3.6.1.4.1.10428 9 1.101.20.2.5.3
		fkEponOltP2PControlTimer OBJECT-TYPE
			SYNTAX Gauge32
			MAX-ACCESS read-write
			STATUS current
			DESCRIPTION
				"The maximum time for the manager for a long running user command"
			::= { fkEponOltP2PControl 3 }

		
		-- 1.3.6.1.4.1.10428 9 1.101.20.2.5.4
		fkEponOltP2PControlTimeStamp OBJECT-TYPE
			SYNTAX TimeTicks
			MAX-ACCESS read-only
			STATUS current
			DESCRIPTION
				"The time stamp of the last command(end of command)"
			::= { fkEponOltP2PControl 4 }

		
		-- 1.3.6.1.4.1.10428 9 1.101.20.2.5.5
		fkEponOltP2PControlReqResult OBJECT-TYPE
			SYNTAX FkControlRequestResultType
			MAX-ACCESS read-only
			STATUS current
			DESCRIPTION
				"The result of the last user command"
			::= { fkEponOltP2PControl 5 }

		
		-- 1.3.6.1.4.1.10428 9 1.101.20.2.5.6
		fkEponOltP2PControlOltIndex OBJECT-TYPE
			SYNTAX Integer32
			MAX-ACCESS read-write
			STATUS current
			DESCRIPTION
				"OLT port Index"
			::= { fkEponOltP2PControl 6 }

		
		-- 1.3.6.1.4.1.10428 9 1.101.20.2.5.7
		fkEponOltP2PControlEnable OBJECT-TYPE
			SYNTAX EnableFlag
			MAX-ACCESS read-write
			STATUS current
			DESCRIPTION
				"enable(1), disable(2)  / DEFVAL : disable "
			DEFVAL { disable }
			::= { fkEponOltP2PControl 7 }

		
		-- 1.3.6.1.4.1.10428 9 1.101.20.2.5.8
		fkEponOltP2PControlOnuID1 OBJECT-TYPE
			SYNTAX Integer32 (1..64)
			MAX-ACCESS read-write
			STATUS current
			DESCRIPTION
				"P2p onu id 1."
			::= { fkEponOltP2PControl 8 }

		
		-- 1.3.6.1.4.1.10428 9 1.101.20.2.5.9
		fkEponOltP2PControlOnuID2 OBJECT-TYPE
			SYNTAX Integer32 (1..64)
			MAX-ACCESS read-write
			STATUS current
			DESCRIPTION
				"P2p onu id 2."
			::= { fkEponOltP2PControl 9 }

		
		-- 1.3.6.1.4.1.10428 9 1.101.20.2.6
		fkEponOltP2PNotification OBJECT IDENTIFIER ::= { fkEponOlt 6 }

		
		-- 1.3.6.1.4.1.10428 9 1.101.20.2.6.1
		fkEponOltP2PAccessControlChanged NOTIFICATION-TYPE
			OBJECTS { fkEponOltP2PControlRequest, fkEponOltP2PControlTimeStamp, fkEponOltP2PControlReqResult, fkEponOltP2PControlOltIndex }
			STATUS current
			DESCRIPTION 
				"Description."
			::= { fkEponOltP2PNotification 1 }

		
		-- 1.3.6.1.4.1.10428 9 1.101.20.2.7
		fkEponOltDMI OBJECT IDENTIFIER ::= { fkEponOlt 7 }

		
		-- 1.3.6.1.4.1.10428 9 1.101.20.2.7.1
		fkEponOltDMITable OBJECT-TYPE
			SYNTAX SEQUENCE OF FkEponOltDMIEntry
			MAX-ACCESS not-accessible
			STATUS current
			DESCRIPTION
				"Description."
			::= { fkEponOltDMI 1 }

		
		-- 1.3.6.1.4.1.10428 9 1.101.20.2.7.1.1
		fkEponOltDMIEntry OBJECT-TYPE
			SYNTAX FkEponOltDMIEntry
			MAX-ACCESS not-accessible
			STATUS current
			DESCRIPTION
				"Description."
			INDEX { fkEponOltIndex, fkEponOnuIndex }
			::= { fkEponOltDMITable 1 }

		
		FkEponOltDMIEntry ::=
			SEQUENCE { 
				fkEponOltDMITemper
					OCTET STRING,
				fkEponOltDMIVoltage
					OCTET STRING,
				fkEponOltDMITxBias
					OCTET STRING,
				fkEponOltDMITxPower
					OCTET STRING,
				fkEponOltDMIRxPower
					OCTET STRING
			 }

		-- 1.3.6.1.4.1.10428 9 1.101.20.2.7.1.1.1
		fkEponOltDMITemper OBJECT-TYPE
			SYNTAX OCTET STRING
			MAX-ACCESS read-only
			STATUS current
			DESCRIPTION
				"onu DMI Temperature ,range is (-128 ~ 127.99 C)
				"
			::= { fkEponOltDMIEntry 1 }

		
		-- 1.3.6.1.4.1.10428 9 1.101.20.2.7.1.1.2
		fkEponOltDMIVoltage OBJECT-TYPE
			SYNTAX OCTET STRING
			MAX-ACCESS read-only
			STATUS current
			DESCRIPTION
				"onu DMI voltage,range is (0 ~ 6.5535 V).
				
				"
			::= { fkEponOltDMIEntry 2 }

		
		-- 1.3.6.1.4.1.10428 9 1.101.20.2.7.1.1.3
		fkEponOltDMITxBias OBJECT-TYPE
			SYNTAX OCTET STRING
			MAX-ACCESS read-only
			STATUS current
			DESCRIPTION
				"onu DMI txbias,range is (0 ~ 131 mA).
				"
			::= { fkEponOltDMIEntry 3 }

		
		-- 1.3.6.1.4.1.10428 9 1.101.20.2.7.1.1.4
		fkEponOltDMITxPower OBJECT-TYPE
			SYNTAX OCTET STRING
			MAX-ACCESS read-only
			STATUS current
			DESCRIPTION
				"onu DMI txpower, range is (-40 ~ 8.1647 dBm).
				"
			::= { fkEponOltDMIEntry 4 }

		
		-- 1.3.6.1.4.1.10428 9 1.101.20.2.7.1.1.5
		fkEponOltDMIRxPower OBJECT-TYPE
			SYNTAX OCTET STRING
			MAX-ACCESS read-only
			STATUS current
			DESCRIPTION
				"onu DMI rxpower,range is (-40 ~ 8.1647 dBm)."
			::= { fkEponOltDMIEntry 5 }

		
		-- 1.3.6.1.4.1.10428 9 1.101.20.3
		fkEponOnu OBJECT IDENTIFIER ::= { fkEpon 3 }

		
		-- 1.3.6.1.4.1.10428 9 1.101.20.3.1
		fkEponOnuTable OBJECT-TYPE
			SYNTAX SEQUENCE OF FkEponOnuEntry
			MAX-ACCESS not-accessible
			STATUS current
			DESCRIPTION
				"Description."
			::= { fkEponOnu 1 }

		
		-- 1.3.6.1.4.1.10428 9 1.101.20.3.1.1
		fkEponOnuEntry OBJECT-TYPE
			SYNTAX FkEponOnuEntry
			MAX-ACCESS not-accessible
			STATUS current
			DESCRIPTION
				"Description."
			INDEX { fkEponOltIndex, fkEponOnuIndex }
			::= { fkEponOnuTable 1 }

		
		FkEponOnuEntry ::=
			SEQUENCE { 
				fkEponOnuIndex
					INTEGER,
				fkEponOnuLlid
					INTEGER,
				fkEponOnuRegMode
					INTEGER,
				fkEponOnuStatus
					INTEGER,
				fkEponOnuMacAddress
					MacAddress,
				fkEponOnuRtt
					INTEGER,
				fkEponOnuDescription
					OCTET STRING,
				fkEponOnuProfile
					OCTET STRING,
				fkEponOnuLoopbackProvision
					INTEGER,
				fkEponOnuVendor
					OCTET STRING,
				fkEponOnuFirmwareRev
					OCTET STRING,
				fkEponOnuTxPowerOffTimer
					INTEGER,
				fkEponOnuLgPathStatus
					INTEGER,
				fkEponOnuModelType
					OCTET STRING,
				fkEponOnuSipGlobalConfigMode
					INTEGER,
				fkEponOnuSipGlobalConfigIp
					IpAddress,
				fkEponOnuSipGlobalConfigNetmask
					IpAddress,
				fkEponOnuSipGlobalConfigGateway
					IpAddress,
				fkEponOnuSipGlobalUserName
					OCTET STRING,
				fkEponOnuSipGlobalPasswd
					OCTET STRING,
				fkEponOnuSipGlobalConfigVid
					INTEGER,
				fkEponOnuRxPower
					Gauge32,
				fkEponOnuRxPowerAlarmStatus
					INTEGER,
				fkEponOnuRssiInfo
					OCTET STRING,
				fkEponOnuLoopDetectUnblockStatus
					INTEGER,
				fkEponOnuUpgradeStatus
					INTEGER,
				fkEponOnuOltRssiStatus
					INTEGER,
				fkEponOnuOltRssiInfo
					OCTET STRING,
				fkEponOnuMultiLlid
					INTEGER,
				fkEponOnuMultiMacAddress
					MacAddress,
				fkEponOltDBAMutilLLidLinkOperate
					INTEGER
			 }

		-- 1.3.6.1.4.1.10428 9 1.101.20.3.1.1.1
		fkEponOnuIndex OBJECT-TYPE
			SYNTAX INTEGER (1..64)
			MAX-ACCESS read-only
			STATUS current
			DESCRIPTION
				"ONU Index"
			::= { fkEponOnuEntry 1 }

		
		-- 1.3.6.1.4.1.10428 9 1.101.20.3.1.1.2
		fkEponOnuLlid OBJECT-TYPE
			SYNTAX INTEGER (1..64)
			MAX-ACCESS read-only
			STATUS current
			DESCRIPTION
				"ONU LLID"
			::= { fkEponOnuEntry 2 }

		
		-- 1.3.6.1.4.1.10428 9 1.101.20.3.1.1.3
		fkEponOnuRegMode OBJECT-TYPE
			SYNTAX INTEGER
				{
				auto(1),
				manual(2),
				static(3)
				}
			MAX-ACCESS read-only
			STATUS current
			DESCRIPTION
				"ONU registration mode"
			DEFVAL { auto }
			::= { fkEponOnuEntry 3 }

		
		-- 1.3.6.1.4.1.10428 9 1.101.20.3.1.1.4
		fkEponOnuStatus OBJECT-TYPE
			SYNTAX INTEGER
				{
				inactive(1),
				deny(2),
				block(3),
				active(4),
				reset(5)
				}
			MAX-ACCESS read-only
			STATUS current
			DESCRIPTION
				"ONU current status"
			::= { fkEponOnuEntry 4 }

		
		-- 1.3.6.1.4.1.10428 9 1.101.20.3.1.1.5
		fkEponOnuMacAddress OBJECT-TYPE
			SYNTAX MacAddress
			MAX-ACCESS read-only
			STATUS current
			DESCRIPTION
				"ONU Hardware address"
			::= { fkEponOnuEntry 5 }

		
		-- 1.3.6.1.4.1.10428 9 1.101.20.3.1.1.6
		fkEponOnuRtt OBJECT-TYPE
			SYNTAX INTEGER
			MAX-ACCESS read-only
			STATUS current
			DESCRIPTION
				"ONU Round Trip Time"
			::= { fkEponOnuEntry 6 }

		
		-- 1.3.6.1.4.1.10428 9 1.101.20.3.1.1.7
		fkEponOnuDescription OBJECT-TYPE
			SYNTAX OCTET STRING (SIZE (1..64))
			MAX-ACCESS read-only
			STATUS current
			DESCRIPTION
				"ONU Description"
			::= { fkEponOnuEntry 7 }

		
		-- 1.3.6.1.4.1.10428 9 1.101.20.3.1.1.8
		fkEponOnuProfile OBJECT-TYPE
			SYNTAX OCTET STRING (SIZE (1..64))
			MAX-ACCESS read-only
			STATUS current
			DESCRIPTION
				"ONU assigned-profile"
			::= { fkEponOnuEntry 8 }

		
		-- 1.3.6.1.4.1.10428 9 1.101.20.3.1.1.9
		fkEponOnuLoopbackProvision OBJECT-TYPE
			SYNTAX INTEGER
			MAX-ACCESS read-only
			STATUS current
			DESCRIPTION
				"ONU loopback test result
				-2 : not exist
				-1 : fail
				 X > 0  : Time.
				"
			::= { fkEponOnuEntry 9 }

		
		-- 1.3.6.1.4.1.10428 9 1.101.20.3.1.1.10
		fkEponOnuVendor OBJECT-TYPE
			SYNTAX OCTET STRING
			MAX-ACCESS read-only
			STATUS current
			DESCRIPTION
				"The name of ONU vendor"
			::= { fkEponOnuEntry 10 }

		
		-- 1.3.6.1.4.1.10428 9 1.101.20.3.1.1.11
		fkEponOnuFirmwareRev OBJECT-TYPE
			SYNTAX OCTET STRING
			MAX-ACCESS read-only
			STATUS current
			DESCRIPTION
				"The vendor-specific firmware revision"
			::= { fkEponOnuEntry 11 }

		
		-- 1.3.6.1.4.1.10428 9 1.101.20.3.1.1.12
		fkEponOnuTxPowerOffTimer OBJECT-TYPE
			SYNTAX INTEGER (0 | 10..65535)
			MAX-ACCESS read-only
			STATUS current
			DESCRIPTION
				"Description."
			::= { fkEponOnuEntry 12 }

		
		-- 1.3.6.1.4.1.10428 9 1.101.20.3.1.1.13
		fkEponOnuLgPathStatus OBJECT-TYPE
			SYNTAX INTEGER
			MAX-ACCESS read-only
			STATUS current
			DESCRIPTION
				"Description."
			::= { fkEponOnuEntry 13 }

		
		-- 1.3.6.1.4.1.10428 9 1.101.20.3.1.1.14
		fkEponOnuModelType OBJECT-TYPE
			SYNTAX OCTET STRING (SIZE (1..32))
			MAX-ACCESS read-only
			STATUS current
			DESCRIPTION
				"Description."
			::= { fkEponOnuEntry 14 }

		
		-- 1.3.6.1.4.1.10428 9 1.101.20.3.1.1.15
		fkEponOnuSipGlobalConfigMode OBJECT-TYPE
			SYNTAX INTEGER
				{
				ip(0),
				dhcp(1),
				pppoe(2)
				}
			MAX-ACCESS read-only
			STATUS current
			DESCRIPTION
				"Description."
			::= { fkEponOnuEntry 15 }

		
		-- 1.3.6.1.4.1.10428 9 1.101.20.3.1.1.16
		fkEponOnuSipGlobalConfigIp OBJECT-TYPE
			SYNTAX IpAddress
			MAX-ACCESS read-only
			STATUS current
			DESCRIPTION
				"Description."
			::= { fkEponOnuEntry 16 }

		
		-- 1.3.6.1.4.1.10428 9 1.101.20.3.1.1.17
		fkEponOnuSipGlobalConfigNetmask OBJECT-TYPE
			SYNTAX IpAddress
			MAX-ACCESS read-only
			STATUS current
			DESCRIPTION
				"Description."
			::= { fkEponOnuEntry 17 }

		
		-- 1.3.6.1.4.1.10428 9 1.101.20.3.1.1.18
		fkEponOnuSipGlobalConfigGateway OBJECT-TYPE
			SYNTAX IpAddress
			MAX-ACCESS read-only
			STATUS current
			DESCRIPTION
				"Description."
			::= { fkEponOnuEntry 18 }

		
		-- 1.3.6.1.4.1.10428 9 1.101.20.3.1.1.19
		fkEponOnuSipGlobalUserName OBJECT-TYPE
			SYNTAX OCTET STRING (SIZE (0..32))
			MAX-ACCESS read-only
			STATUS current
			DESCRIPTION
				"Description."
			::= { fkEponOnuEntry 19 }

		
		-- 1.3.6.1.4.1.10428 9 1.101.20.3.1.1.20
		fkEponOnuSipGlobalPasswd OBJECT-TYPE
			SYNTAX OCTET STRING (SIZE (0..32))
			MAX-ACCESS read-only
			STATUS current
			DESCRIPTION
				"Description."
			::= { fkEponOnuEntry 20 }

		
		-- 1.3.6.1.4.1.10428 9 1.101.20.3.1.1.21
		fkEponOnuSipGlobalConfigVid OBJECT-TYPE
			SYNTAX INTEGER
			MAX-ACCESS read-only
			STATUS current
			DESCRIPTION
				"Description."
			::= { fkEponOnuEntry 21 }

		
		-- 1.3.6.1.4.1.10428 9 1.101.20.3.1.1.22
		fkEponOnuRxPower OBJECT-TYPE
			SYNTAX Gauge32
			MAX-ACCESS read-only
			STATUS current
			DESCRIPTION
				"Description."
			::= { fkEponOnuEntry 22 }

		
		-- 1.3.6.1.4.1.10428 9 1.101.20.3.1.1.23
		fkEponOnuRxPowerAlarmStatus OBJECT-TYPE
			SYNTAX INTEGER
			MAX-ACCESS read-write
			STATUS current
			DESCRIPTION
				"Onu Rx Optical power alarm state of olt-side.
				1: RX Optical Power Alarm - Caution (orange)
				2: RX Optical Power Alarm cleard - OK (Green)
				"
			::= { fkEponOnuEntry 23 }

		
		-- 1.3.6.1.4.1.10428 9 1.101.20.3.1.1.24
		fkEponOnuRssiInfo OBJECT-TYPE
			SYNTAX OCTET STRING
			MAX-ACCESS read-only
			STATUS current
			DESCRIPTION
				"Epon onu rssi-info."
			::= { fkEponOnuEntry 24 }

		
		-- 1.3.6.1.4.1.10428 9 1.101.20.3.1.1.25
		fkEponOnuLoopDetectUnblockStatus OBJECT-TYPE
			SYNTAX INTEGER
				{
				blocked(1),
				unblocked(2)
				}
			MAX-ACCESS read-only
			STATUS current
			DESCRIPTION
				"Epon onu loopdetect unblock status."
			::= { fkEponOnuEntry 25 }

		
		-- 1.3.6.1.4.1.10428 9 1.101.20.3.1.1.26
		fkEponOnuUpgradeStatus OBJECT-TYPE
			SYNTAX INTEGER
				{
				notUpgrade(1),
				inactiveONT(2),
				waitingUpgrade(3),
				firmwareSending(4),
				firmwareSend(5),
				writingFlashOnOnu(6),
				upgradeOK(7),
				upgradeFail(8)
				}
			MAX-ACCESS read-only
			STATUS current
			DESCRIPTION
				"Onu upgrade state."
			::= { fkEponOnuEntry 26 }

		
		-- 1.3.6.1.4.1.10428 9 1.101.20.3.1.1.27
		fkEponOnuOltRssiStatus OBJECT-TYPE
			SYNTAX INTEGER
				{
				na(0),
				enable(1),
				disable(2),
				average(3)
				}
			MAX-ACCESS read-only
			STATUS current
			DESCRIPTION
				"Epon olt rssi-info."
			::= { fkEponOnuEntry 27 }

		
		-- 1.3.6.1.4.1.10428 9 1.101.20.3.1.1.28
		fkEponOnuOltRssiInfo OBJECT-TYPE
			SYNTAX OCTET STRING
			MAX-ACCESS read-only
			STATUS current
			DESCRIPTION
				"Epon olt rssi-info value."
			::= { fkEponOnuEntry 28 }

		
		-- 1.3.6.1.4.1.10428 9 1.101.20.3.1.1.29
		fkEponOnuMultiLlid OBJECT-TYPE
			SYNTAX INTEGER (1..64)
			MAX-ACCESS read-only
			STATUS current
			DESCRIPTION
				"ONU Multi LLID"
			::= { fkEponOnuEntry 29 }

		
		-- 1.3.6.1.4.1.10428 9 1.101.20.3.1.1.30
		fkEponOnuMultiMacAddress OBJECT-TYPE
			SYNTAX MacAddress
			MAX-ACCESS read-only
			STATUS current
			DESCRIPTION
				"ONU Hardware address"
			::= { fkEponOnuEntry 30 }

		
		-- 1.3.6.1.4.1.10428 9 1.101.20.3.1.1.31
		fkEponOltDBAMutilLLidLinkOperate OBJECT-TYPE
			SYNTAX INTEGER
				{
				disable(0),
				enable(1)
				}
			MAX-ACCESS read-write
			STATUS current
			DESCRIPTION
				"DBA multi llid link."
			::= { fkEponOnuEntry 31 }

		
		-- 1.3.6.1.4.1.10428 9 1.101.20.3.2
		fkEponOnuControl OBJECT IDENTIFIER ::= { fkEponOnu 2 }

		
		-- 1.3.6.1.4.1.10428 9 1.101.20.3.2.1
		fkEponOnuControlRequest OBJECT-TYPE
			SYNTAX INTEGER
				{
				setEponOnuRegMode(1),
				setEponOnuStatus(2),
				setEponOnuAttributes(3),
				setEponOnuRegister(4),
				setEponOnuDeregister(5),
				setEponOnuProfile(6),
				setEponOnuUpgrade(7),
				setEPonOnuLoopbackProvision(8),
				setEponOnuTxPowerOffTimer(9),
				setEponOnuProfileByMac(10),
				setEponOnuDeregisterByMac(11),
				setEponOnuSipGlobalConfigIP(13),
				setEponOnuSipGlobalConfigDHCP(14),
				setEponOnuSipGlobalConfigPPPoE(15),
				destroyEponOnuSipGlobalConfig(16),
				setEponOnuPingTest(17),
				setEponOnuLoopDetectUnblock(18),
				setEponOltRssiOnuSingle(19),
				setDBAMultiLLidLinkEnable(20),
				setDBAMultLLidLinkDisable(21)
				}
			MAX-ACCESS read-write
			STATUS current
			DESCRIPTION
				"The request of a user command"
			::= { fkEponOnuControl 1 }

		
		-- 1.3.6.1.4.1.10428 9 1.101.20.3.2.2
		fkEponOnuControlStatus OBJECT-TYPE
			SYNTAX FkControlStatusType
			MAX-ACCESS read-only
			STATUS current
			DESCRIPTION
				"The status of user command"
			::= { fkEponOnuControl 2 }

		
		-- 1.3.6.1.4.1.10428 9 1.101.20.3.2.3
		fkEponOnuControlTimer OBJECT-TYPE
			SYNTAX Gauge32
			MAX-ACCESS read-write
			STATUS current
			DESCRIPTION
				"The maximum time for the manager for a long running user command"
			::= { fkEponOnuControl 3 }

		
		-- 1.3.6.1.4.1.10428 9 1.101.20.3.2.4
		fkEponOnuControlTimeStamp OBJECT-TYPE
			SYNTAX TimeTicks
			MAX-ACCESS read-only
			STATUS current
			DESCRIPTION
				"The time stamp of the last command(end of command)"
			::= { fkEponOnuControl 4 }

		
		-- 1.3.6.1.4.1.10428 9 1.101.20.3.2.5
		fkEponOnuControlReqResult OBJECT-TYPE
			SYNTAX FkControlRequestResultType
			MAX-ACCESS read-only
			STATUS current
			DESCRIPTION
				"The result of the last user command"
			::= { fkEponOnuControl 5 }

		
		-- 1.3.6.1.4.1.10428 9 1.101.20.3.2.6
		fkEponOnuControlOltIndex OBJECT-TYPE
			SYNTAX INTEGER (1..512)
			MAX-ACCESS read-write
			STATUS current
			DESCRIPTION
				"OLT index"
			::= { fkEponOnuControl 6 }

		
		-- 1.3.6.1.4.1.10428 9 1.101.20.3.2.7
		fkEponOnuControlOnuIndex OBJECT-TYPE
			SYNTAX INTEGER (1..64)
			MAX-ACCESS read-write
			STATUS current
			DESCRIPTION
				"ONU index <1-32>"
			::= { fkEponOnuControl 7 }

		
		-- 1.3.6.1.4.1.10428 9 1.101.20.3.2.8
		fkEponOnuControlRegMode OBJECT-TYPE
			SYNTAX INTEGER
				{
				auto(1),
				manual(2)
				}
			MAX-ACCESS read-write
			STATUS current
			DESCRIPTION
				"ONU register mode {auto(1), manual(2)}"
			DEFVAL { auto }
			::= { fkEponOnuControl 8 }

		
		-- 1.3.6.1.4.1.10428 9 1.101.20.3.2.9
		fkEponOnuControlOnuStatus OBJECT-TYPE
			SYNTAX INTEGER
				{
				inactive(1),
				deny(2),
				block(3),
				active(4),
				reset(5)
				}
			MAX-ACCESS read-write
			STATUS current
			DESCRIPTION
				"1 : inactive 
				2 : deny 
				3 : block
				4 : active
				5 : reset
				"
			::= { fkEponOnuControl 9 }

		
		-- 1.3.6.1.4.1.10428 9 1.101.20.3.2.10
		fkEponOnuControlMacAddress OBJECT-TYPE
			SYNTAX MacAddress
			MAX-ACCESS read-write
			STATUS current
			DESCRIPTION
				"ONU MAC address"
			::= { fkEponOnuControl 10 }

		
		-- 1.3.6.1.4.1.10428 9 1.101.20.3.2.11
		fkEponOnuControlDescription OBJECT-TYPE
			SYNTAX OCTET STRING
			MAX-ACCESS read-write
			STATUS current
			DESCRIPTION
				"ONU description"
			::= { fkEponOnuControl 11 }

		
		-- 1.3.6.1.4.1.10428 9 1.101.20.3.2.12
		fkEponOnuControlProfile OBJECT-TYPE
			SYNTAX OCTET STRING (SIZE (1..64))
			MAX-ACCESS read-write
			STATUS current
			DESCRIPTION
				"Profile name"
			::= { fkEponOnuControl 12 }

		
		-- 1.3.6.1.4.1.10428 9 1.101.20.3.2.13
		fkEponOnuControlUpgradePath OBJECT-TYPE
			SYNTAX OCTET STRING (SIZE (1..64))
			UNITS "byte"
			MAX-ACCESS read-write
			STATUS current
			DESCRIPTION
				"Upgrade path"
			::= { fkEponOnuControl 13 }

		
		-- 1.3.6.1.4.1.10428 9 1.101.20.3.2.14
		fkEponOnuControlLoopbackProvision OBJECT-TYPE
			SYNTAX INTEGER { test(1) }
			MAX-ACCESS read-write
			STATUS current
			DESCRIPTION
				"1 : test"
			::= { fkEponOnuControl 14 }

		
		-- 1.3.6.1.4.1.10428 9 1.101.20.3.2.15
		fkEponOnuControlTxPowerOffTimer OBJECT-TYPE
			SYNTAX INTEGER (0 | 10..65535)
			MAX-ACCESS read-write
			STATUS current
			DESCRIPTION
				"Description."
			::= { fkEponOnuControl 15 }

		
		-- 1.3.6.1.4.1.10428 9 1.101.20.3.2.18
		fkEponOnuControlSipGlobalConfigMode OBJECT-TYPE
			SYNTAX INTEGER
				{
				ip(0),
				dhcp(1),
				pppoe(2)
				}
			MAX-ACCESS read-write
			STATUS current
			DESCRIPTION
				"Description."
			::= { fkEponOnuControl 18 }

		
		-- 1.3.6.1.4.1.10428 9 1.101.20.3.2.19
		fkEponOnuControlSipGlobalConfigIp OBJECT-TYPE
			SYNTAX IpAddress
			MAX-ACCESS read-write
			STATUS current
			DESCRIPTION
				"Description."
			::= { fkEponOnuControl 19 }

		
		-- 1.3.6.1.4.1.10428 9 1.101.20.3.2.20
		fkEponOnuControlSipGlobalConfigNetmask OBJECT-TYPE
			SYNTAX IpAddress
			MAX-ACCESS read-write
			STATUS current
			DESCRIPTION
				"Description."
			::= { fkEponOnuControl 20 }

		
		-- 1.3.6.1.4.1.10428 9 1.101.20.3.2.21
		fkEponOnuControlSipGlobalConfigGateway OBJECT-TYPE
			SYNTAX IpAddress
			MAX-ACCESS read-write
			STATUS current
			DESCRIPTION
				"Description."
			::= { fkEponOnuControl 21 }

		
		-- 1.3.6.1.4.1.10428 9 1.101.20.3.2.22
		fkEponOnuControlSipGlobalConfigUserName OBJECT-TYPE
			SYNTAX OCTET STRING (SIZE (0..32))
			MAX-ACCESS read-write
			STATUS current
			DESCRIPTION
				"Description."
			::= { fkEponOnuControl 22 }

		
		-- 1.3.6.1.4.1.10428 9 1.101.20.3.2.23
		fkEponOnuControlSipGlobalConfigUserPasswd OBJECT-TYPE
			SYNTAX OCTET STRING (SIZE (0..32))
			MAX-ACCESS read-write
			STATUS current
			DESCRIPTION
				"Description."
			::= { fkEponOnuControl 23 }

		
		-- 1.3.6.1.4.1.10428 9 1.101.20.3.2.24
		fkEponOnuControlSipGlobalConfigVid OBJECT-TYPE
			SYNTAX INTEGER
			MAX-ACCESS read-write
			STATUS current
			DESCRIPTION
				"Description."
			::= { fkEponOnuControl 24 }

		
		-- 1.3.6.1.4.1.10428 9 1.101.20.3.2.25
		fkEponOnuControlPingCount OBJECT-TYPE
			SYNTAX Integer32 (1..20)
			MAX-ACCESS read-write
			STATUS current
			DESCRIPTION
				"Onu Ping Test count."
			::= { fkEponOnuControl 25 }

		
		-- 1.3.6.1.4.1.10428 9 1.101.20.3.3
		fkEponOnuNotification OBJECT IDENTIFIER ::= { fkEponOnu 3 }

		
		-- 1.3.6.1.4.1.10428 9 1.101.20.3.3.1
		fkEponOnuRegModeChanged NOTIFICATION-TYPE
			OBJECTS { fkEponOnuControlRequest, fkEponOnuControlTimeStamp, fkEponOnuControlReqResult, fkEponOnuControlOltIndex, fkEponOnuControlOnuIndex, 
				fkEponOnuControlRegMode }
			STATUS current
			DESCRIPTION 
				"Description."
			::= { fkEponOnuNotification 1 }

		
		-- 1.3.6.1.4.1.10428 9 1.101.20.3.3.2
		fkEponOnuStatusChanged NOTIFICATION-TYPE
			OBJECTS { fkEponOnuControlRequest, fkEponOnuControlTimeStamp, fkEponOnuControlReqResult, fkEponOnuControlOltIndex, fkEponOnuControlOnuIndex, 
				fkEponOnuControlOnuStatus }
			STATUS current
			DESCRIPTION 
				"Description."
			::= { fkEponOnuNotification 2 }

		
		-- 1.3.6.1.4.1.10428 9 1.101.20.3.3.3
		fkEponOnuAttibutesChanged NOTIFICATION-TYPE
			OBJECTS { fkEponOnuControlRequest, fkEponOnuControlTimeStamp, fkEponOnuControlReqResult, fkEponOnuControlOltIndex, fkEponOnuControlOnuIndex, 
				fkEponOnuControlDescription }
			STATUS current
			DESCRIPTION 
				"Description."
			::= { fkEponOnuNotification 3 }

		
		-- 1.3.6.1.4.1.10428 9 1.101.20.3.3.4
		fkEponOnuRegistered NOTIFICATION-TYPE
			OBJECTS { fkEponOnuControlRequest, fkEponOnuControlTimeStamp, fkEponOnuControlReqResult, fkEponOnuControlOltIndex, fkEponOnuControlOnuIndex, 
				fkEponOnuControlMacAddress, fkEponOnuControlDescription }
			STATUS current
			DESCRIPTION 
				"Description."
			::= { fkEponOnuNotification 4 }

		
		-- 1.3.6.1.4.1.10428 9 1.101.20.3.3.5
		fkEponOnuDeregistered NOTIFICATION-TYPE
			OBJECTS { fkEponOnuControlRequest, fkEponOnuControlTimeStamp, fkEponOnuControlReqResult, fkEponOnuControlOltIndex, fkEponOnuControlOnuIndex
				 }
			STATUS current
			DESCRIPTION 
				"Description."
			::= { fkEponOnuNotification 5 }

		
		-- 1.3.6.1.4.1.10428 9 1.101.20.3.3.6
		fkEponOnuProfileChanged NOTIFICATION-TYPE
			OBJECTS { fkEponOnuControlRequest, fkEponOnuControlTimeStamp, fkEponOnuControlReqResult, fkEponOnuControlOltIndex, fkEponOnuControlOnuIndex, 
				fkEponOnuControlProfile }
			STATUS current
			DESCRIPTION 
				"Description."
			::= { fkEponOnuNotification 6 }

		
		-- 1.3.6.1.4.1.10428 9 1.101.20.3.3.7
		fkEponOnuUpgraded NOTIFICATION-TYPE
			OBJECTS { fkEponOnuControlRequest, fkEponOnuControlTimeStamp, fkEponOnuControlReqResult, fkEponOnuControlOltIndex, fkEponOnuControlOnuIndex, 
				fkEponOnuControlUpgradePath }
			STATUS current
			DESCRIPTION 
				"Description."
			::= { fkEponOnuNotification 7 }

		
		-- 1.3.6.1.4.1.10428 9 1.101.20.3.3.8
		fkEponOnuLoopbackProvisioned NOTIFICATION-TYPE
			OBJECTS { fkEponOnuControlRequest, fkEponOnuControlTimeStamp, fkEponOnuControlReqResult, fkEponOnuControlOltIndex, fkEponOnuControlOnuIndex, 
				fkEponOnuControlLoopbackProvision }
			STATUS current
			DESCRIPTION 
				"Description."
			::= { fkEponOnuNotification 8 }

		
		-- 1.3.6.1.4.1.10428 9 1.101.20.3.3.9
		fkEponOnuTxPowerOffChanged NOTIFICATION-TYPE
			OBJECTS { fkEponOnuControlRequest, fkEponOnuControlTimeStamp, fkEponOnuControlReqResult, fkEponOnuControlOltIndex, fkEponOnuControlOnuIndex, 
				fkEponOnuControlTxPowerOffTimer }
			STATUS current
			DESCRIPTION 
				"Description."
			::= { fkEponOnuNotification 9 }

		
		-- 1.3.6.1.4.1.10428 9 1.101.20.3.3.10
		fkEponOnuFristRegisteredOnAutoToManual NOTIFICATION-TYPE
			OBJECTS { sysDescr, fkEponOltIndex, fkEponOnuIndex }
			STATUS current
			DESCRIPTION 
				"Description."
			::= { fkEponOnuNotification 10 }

		
		-- 1.3.6.1.4.1.10428 9 1.101.20.3.3.11
		fkEponOnuProfileChangedByMac NOTIFICATION-TYPE
			OBJECTS { fkEponOnuControlRequest, fkEponOnuControlTimeStamp, fkEponOnuControlReqResult, fkEponOnuControlOltIndex, fkEponOnuControlMacAddress, 
				fkEponOnuControlProfile }
			STATUS current
			DESCRIPTION 
				"Description."
			::= { fkEponOnuNotification 11 }

		
		-- 1.3.6.1.4.1.10428 9 1.101.20.3.3.12
		fkEponOnuDeregisteredByMac NOTIFICATION-TYPE
			OBJECTS { fkEponOnuControlRequest, fkEponOnuControlTimeStamp, fkEponOnuControlReqResult, fkEponOnuControlOltIndex, fkEponOnuControlMacAddress
				 }
			STATUS current
			DESCRIPTION 
				"Description."
			::= { fkEponOnuNotification 12 }

		
		-- 1.3.6.1.4.1.10428 9 1.101.20.3.3.13
		fkEponOnuLgpauthStatusChanged NOTIFICATION-TYPE
			OBJECTS { fkEponOnuControlRequest, fkEponOnuControlTimeStamp, fkEponOnuControlReqResult, fkEponOnuControlOltIndex, fkEponOnuControlOnuIndex
				 }
			STATUS current
			DESCRIPTION 
				"Lgpauth status changed trap."
			::= { fkEponOnuNotification 13 }

		
		-- 1.3.6.1.4.1.10428 9 1.101.20.3.3.14
		fkEponOnuSipGlobalConfigIpChanged NOTIFICATION-TYPE
			OBJECTS { fkEponOnuControlRequest, fkEponOnuControlTimeStamp, fkEponOnuControlReqResult, fkEponOnuControlOltIndex, fkEponOnuControlOnuIndex, 
				fkEponOnuControlSipGlobalConfigMode, fkEponOnuControlSipGlobalConfigIp, fkEponOnuControlSipGlobalConfigNetmask, fkEponOnuControlSipGlobalConfigGateway, fkEponOnuControlSipGlobalConfigVid
				 }
			STATUS current
			DESCRIPTION 
				"Description."
			::= { fkEponOnuNotification 14 }

		
		-- 1.3.6.1.4.1.10428 9 1.101.20.3.3.15
		fkEponOnuSipGlobalConfigDhcpChanged NOTIFICATION-TYPE
			OBJECTS { fkEponOnuControlRequest, fkEponOnuControlTimeStamp, fkEponOnuControlReqResult, fkEponOnuControlOltIndex, fkEponOnuControlOnuIndex, 
				fkEponOnuControlSipGlobalConfigMode, fkEponOnuControlSipGlobalConfigVid }
			STATUS current
			DESCRIPTION 
				"Description."
			::= { fkEponOnuNotification 15 }

		
		-- 1.3.6.1.4.1.10428 9 1.101.20.3.3.16
		fkEponOnuSipGlobalConfigPPPoEChanged NOTIFICATION-TYPE
			OBJECTS { fkEponOnuControlRequest, fkEponOnuControlTimeStamp, fkEponOnuControlReqResult, fkEponOnuControlOltIndex, fkEponOnuControlOnuIndex, 
				fkEponOnuControlSipGlobalConfigMode, fkEponOnuControlSipGlobalConfigUserName, fkEponOnuControlSipGlobalConfigUserPasswd, fkEponOnuControlSipGlobalConfigVid }
			STATUS current
			DESCRIPTION 
				"Description."
			::= { fkEponOnuNotification 16 }

		
		-- 1.3.6.1.4.1.10428 9 1.101.20.3.3.17
		fkEponOnuSipGlobalConfigDestroyed NOTIFICATION-TYPE
			OBJECTS { fkEponOnuControlRequest, fkEponOnuControlTimeStamp, fkEponOnuControlReqResult, fkEponOnuControlOltIndex, fkEponOnuControlOnuIndex
				 }
			STATUS current
			DESCRIPTION 
				"Description."
			::= { fkEponOnuNotification 17 }

		
		-- 1.3.6.1.4.1.10428 9 1.101.20.3.3.18
		fkEponOnuPingTest NOTIFICATION-TYPE
			OBJECTS { fkEponOnuControlRequest, fkEponOnuControlTimeStamp, fkEponOnuControlReqResult, fkEponOnuControlOltIndex, fkEponOnuControlOnuIndex, 
				fkEponOnuControlPingCount }
			STATUS current
			DESCRIPTION 
				"Description."
			::= { fkEponOnuNotification 18 }

		
		-- 1.3.6.1.4.1.10428 9 1.101.20.3.3.19
		fkEponOnuLoopDectectUnblock NOTIFICATION-TYPE
			OBJECTS { fkEponOnuControlRequest, fkEponOnuControlTimeStamp, fkEponOnuControlReqResult, fkEponOnuControlOltIndex, fkEponOnuControlOnuIndex
				 }
			STATUS current
			DESCRIPTION 
				"Loop dectect unblock trap."
			::= { fkEponOnuNotification 19 }

		
		-- 1.3.6.1.4.1.10428 9 1.101.20.3.3.20
		setEponOnuOltRssiOnuSingle NOTIFICATION-TYPE
			OBJECTS { fkEponOnuControlRequest, fkEponOnuControlTimeStamp, fkEponOnuControlReqResult, fkEponOnuControlOltIndex, fkEponOnuControlOnuIndex
				 }
			STATUS current
			DESCRIPTION 
				"Description."
			::= { fkEponOnuNotification 20 }

		
		-- 1.3.6.1.4.1.10428 9 1.101.20.3.3.21
		fkEponOnuDBAMultiLLidLink NOTIFICATION-TYPE
			OBJECTS { fkEponOnuControlRequest, fkEponOnuControlTimeStamp, fkEponOnuControlReqResult, fkEponOnuControlOltIndex, fkEponOnuControlOnuIndex
				 }
			STATUS current
			DESCRIPTION 
				"Multi-llid link enable and disable trap."
			::= { fkEponOnuNotification 21 }

		
		-- 1.3.6.1.4.1.10428 9 1.101.20.3.4
		fkEponOnuDMI OBJECT IDENTIFIER ::= { fkEponOnu 4 }

		
		-- 1.3.6.1.4.1.10428 9 1.101.20.3.4.1
		fkEponOnuDMITable OBJECT-TYPE
			SYNTAX SEQUENCE OF FkEponOnuDMIEntry
			MAX-ACCESS not-accessible
			STATUS current
			DESCRIPTION
				"Description."
			::= { fkEponOnuDMI 1 }

		
		-- 1.3.6.1.4.1.10428 9 1.101.20.3.4.1.1
		fkEponOnuDMIEntry OBJECT-TYPE
			SYNTAX FkEponOnuDMIEntry
			MAX-ACCESS not-accessible
			STATUS current
			DESCRIPTION
				"Description."
			INDEX { fkEponOltIndex, fkEponOnuIndex }
			::= { fkEponOnuDMITable 1 }

		
		FkEponOnuDMIEntry ::=
			SEQUENCE { 
				fkEponOnuDMITemper
					OCTET STRING,
				fkEponOnuDMIVoltage
					OCTET STRING,
				fkEponOnuDMITxBias
					OCTET STRING,
				fkEponOnuDMITxPower
					OCTET STRING,
				fkEponOnuDMIRxPower
					OCTET STRING
			 }

		-- 1.3.6.1.4.1.10428 9 1.101.20.3.4.1.1.1
		fkEponOnuDMITemper OBJECT-TYPE
			SYNTAX OCTET STRING
			MAX-ACCESS read-only
			STATUS current
			DESCRIPTION
				"Onu DMI Temperature ,range is (-128 ~ 127.99 C)
				"
			::= { fkEponOnuDMIEntry 1 }

		
		-- 1.3.6.1.4.1.10428 9 1.101.20.3.4.1.1.2
		fkEponOnuDMIVoltage OBJECT-TYPE
			SYNTAX OCTET STRING
			MAX-ACCESS read-only
			STATUS current
			DESCRIPTION
				"Onu DMI voltage,range is (0 ~ 6.5535 V).
				
				"
			::= { fkEponOnuDMIEntry 2 }

		
		-- 1.3.6.1.4.1.10428 9 1.101.20.3.4.1.1.3
		fkEponOnuDMITxBias OBJECT-TYPE
			SYNTAX OCTET STRING
			MAX-ACCESS read-only
			STATUS current
			DESCRIPTION
				"Onu DMI txbias,range is (0 ~ 131 mA).
				"
			::= { fkEponOnuDMIEntry 3 }

		
		-- 1.3.6.1.4.1.10428 9 1.101.20.3.4.1.1.4
		fkEponOnuDMITxPower OBJECT-TYPE
			SYNTAX OCTET STRING
			MAX-ACCESS read-only
			STATUS current
			DESCRIPTION
				"Onu DMI txpower, range is (-40 ~ 8.1647 dBm).
				"
			::= { fkEponOnuDMIEntry 4 }

		
		-- 1.3.6.1.4.1.10428 9 1.101.20.3.4.1.1.5
		fkEponOnuDMIRxPower OBJECT-TYPE
			SYNTAX OCTET STRING
			MAX-ACCESS read-only
			STATUS current
			DESCRIPTION
				"Onu DMI rxpower,range is (-40 ~ 8.1647 dBm)."
			::= { fkEponOnuDMIEntry 5 }

		
		-- 1.3.6.1.4.1.10428 9 1.101.20.3.4.2
		fkEponOnuDMIThresholdTable OBJECT-TYPE
			SYNTAX SEQUENCE OF FkEponOnuDMIThresholdEntry
			MAX-ACCESS not-accessible
			STATUS current
			DESCRIPTION
				"Description."
			::= { fkEponOnuDMI 2 }

		
		-- 1.3.6.1.4.1.10428 9 1.101.20.3.4.2.1
		fkEponOnuDMIThresholdEntry OBJECT-TYPE
			SYNTAX FkEponOnuDMIThresholdEntry
			MAX-ACCESS not-accessible
			STATUS current
			DESCRIPTION
				"Description."
			INDEX { fkEponOltIndex, fkEponOnuIndex }
			::= { fkEponOnuDMIThresholdTable 1 }

		
		FkEponOnuDMIThresholdEntry ::=
			SEQUENCE { 
				fkEponOnuDMIThresholdWarnTemperLow
					Integer32,
				fkEponOnuDMIThresholdWarnTemperHigh
					Integer32,
				fkEponOnuDMIThresholdAlarmTemperLow
					Integer32,
				fkEponOnuDMIThresholdAlarmTemperHigh
					Integer32,
				fkEponOnuDMIThresholdWarnVoltageLow
					Integer32,
				fkEponOnuDMIThresholdWarnVoltageHigh
					Integer32,
				fkEponOnuDMIThresholdAlarmVoltageLow
					Integer32,
				fkEponOnuDMIThresholdAlarmVoltageHigh
					Integer32,
				fkEponOnuDMIThresholdWarnTxbiasLow
					Integer32,
				fkEponOnuDMIThresholdWarnTxbiasHigh
					Integer32,
				fkEponOnuDMIThresholdAlarmTxbiasLow
					Integer32,
				fkEponOnuDMIThresholdAlarmTxbiasHigh
					Integer32,
				fkEponOnuDMIThresholdWarnTxPowerLow
					Integer32,
				fkEponOnuDMIThresholdWarnTxPowerHigh
					Integer32,
				fkEponOnuDMIThresholdAlarmTxPowerLow
					Integer32,
				fkEponOnuDMIThresholdAlarmTxPowerHigh
					Integer32,
				fkEponOnuDMIThresholdWarnRxPowerLow
					Integer32,
				fkEponOnuDMIThresholdWarnRxPowerHigh
					Integer32,
				fkEponOnuDMIThresholdAlarmRxPowerLow
					Integer32,
				fkEponOnuDMIThresholdAlarmRxPowerHigh
					Integer32
			 }

		-- 1.3.6.1.4.1.10428 9 1.101.20.3.4.2.1.1
		fkEponOnuDMIThresholdWarnTemperLow OBJECT-TYPE
			SYNTAX Integer32
			MAX-ACCESS read-only
			STATUS current
			DESCRIPTION
				"The Temperature threshold -128~127.99(C)
				It must be devided by 10000."
			::= { fkEponOnuDMIThresholdEntry 1 }

		
		-- 1.3.6.1.4.1.10428 9 1.101.20.3.4.2.1.2
		fkEponOnuDMIThresholdWarnTemperHigh OBJECT-TYPE
			SYNTAX Integer32
			MAX-ACCESS read-only
			STATUS current
			DESCRIPTION
				"The Temperature threshold -128~127.99(C)
				It must be devided by 10000."
			::= { fkEponOnuDMIThresholdEntry 2 }

		
		-- 1.3.6.1.4.1.10428 9 1.101.20.3.4.2.1.3
		fkEponOnuDMIThresholdAlarmTemperLow OBJECT-TYPE
			SYNTAX Integer32
			MAX-ACCESS read-only
			STATUS current
			DESCRIPTION
				"The Temperature threshold -128~127.99(C)
				It must be devided by 10000."
			::= { fkEponOnuDMIThresholdEntry 3 }

		
		-- 1.3.6.1.4.1.10428 9 1.101.20.3.4.2.1.4
		fkEponOnuDMIThresholdAlarmTemperHigh OBJECT-TYPE
			SYNTAX Integer32
			MAX-ACCESS read-only
			STATUS current
			DESCRIPTION
				"The Temperature threshold -128~127.99(C)
				It must be devided by 10000."
			::= { fkEponOnuDMIThresholdEntry 4 }

		
		-- 1.3.6.1.4.1.10428 9 1.101.20.3.4.2.1.5
		fkEponOnuDMIThresholdWarnVoltageLow OBJECT-TYPE
			SYNTAX Integer32
			MAX-ACCESS read-only
			STATUS current
			DESCRIPTION
				"The Voltage threshold 0~6.5535(V)
				It must be devided by 10000."
			::= { fkEponOnuDMIThresholdEntry 5 }

		
		-- 1.3.6.1.4.1.10428 9 1.101.20.3.4.2.1.6
		fkEponOnuDMIThresholdWarnVoltageHigh OBJECT-TYPE
			SYNTAX Integer32
			MAX-ACCESS read-only
			STATUS current
			DESCRIPTION
				"The Voltage threshold 0~6.5535(V)
				It must be devided by 10000."
			::= { fkEponOnuDMIThresholdEntry 6 }

		
		-- 1.3.6.1.4.1.10428 9 1.101.20.3.4.2.1.7
		fkEponOnuDMIThresholdAlarmVoltageLow OBJECT-TYPE
			SYNTAX Integer32
			MAX-ACCESS read-only
			STATUS current
			DESCRIPTION
				"The Voltage threshold 0~6.5535(V)
				It must be devided by 10000."
			::= { fkEponOnuDMIThresholdEntry 7 }

		
		-- 1.3.6.1.4.1.10428 9 1.101.20.3.4.2.1.8
		fkEponOnuDMIThresholdAlarmVoltageHigh OBJECT-TYPE
			SYNTAX Integer32
			MAX-ACCESS read-only
			STATUS current
			DESCRIPTION
				"The Voltage threshold 0~6.5535(V)
				It must be devided by 10000."
			::= { fkEponOnuDMIThresholdEntry 8 }

		
		-- 1.3.6.1.4.1.10428 9 1.101.20.3.4.2.1.9
		fkEponOnuDMIThresholdWarnTxbiasLow OBJECT-TYPE
			SYNTAX Integer32 (0..131)
			MAX-ACCESS read-only
			STATUS current
			DESCRIPTION
				"The Txbias Threshold 0~131(mA)
				It must be devided by 10000.
				"
			::= { fkEponOnuDMIThresholdEntry 9 }

		
		-- 1.3.6.1.4.1.10428 9 1.101.20.3.4.2.1.10
		fkEponOnuDMIThresholdWarnTxbiasHigh OBJECT-TYPE
			SYNTAX Integer32 (0..131)
			MAX-ACCESS read-only
			STATUS current
			DESCRIPTION
				"The Txbias Threshold 0~131(mA)
				It must be devided by 10000."
			::= { fkEponOnuDMIThresholdEntry 10 }

		
		-- 1.3.6.1.4.1.10428 9 1.101.20.3.4.2.1.11
		fkEponOnuDMIThresholdAlarmTxbiasLow OBJECT-TYPE
			SYNTAX Integer32 (0..131)
			MAX-ACCESS read-only
			STATUS current
			DESCRIPTION
				"The Txbias Threshold 0~131(mA)
				It must be devided by 10000.
				"
			::= { fkEponOnuDMIThresholdEntry 11 }

		
		-- 1.3.6.1.4.1.10428 9 1.101.20.3.4.2.1.12
		fkEponOnuDMIThresholdAlarmTxbiasHigh OBJECT-TYPE
			SYNTAX Integer32 (0..131)
			MAX-ACCESS read-only
			STATUS current
			DESCRIPTION
				"The Txbias Threshold 0~131(mA)
				It must be devided by 10000.
				"
			::= { fkEponOnuDMIThresholdEntry 12 }

		
		-- 1.3.6.1.4.1.10428 9 1.101.20.3.4.2.1.13
		fkEponOnuDMIThresholdWarnTxPowerLow OBJECT-TYPE
			SYNTAX Integer32
			MAX-ACCESS read-only
			STATUS current
			DESCRIPTION
				"The Power threshold -40~8,1647 (dBm)
				It must be devided by 10000.
				"
			::= { fkEponOnuDMIThresholdEntry 13 }

		
		-- 1.3.6.1.4.1.10428 9 1.101.20.3.4.2.1.14
		fkEponOnuDMIThresholdWarnTxPowerHigh OBJECT-TYPE
			SYNTAX Integer32
			MAX-ACCESS read-only
			STATUS current
			DESCRIPTION
				"The Power threshold -40~8,1647 (dBm)
				It must be devided by 10000."
			::= { fkEponOnuDMIThresholdEntry 14 }

		
		-- 1.3.6.1.4.1.10428 9 1.101.20.3.4.2.1.15
		fkEponOnuDMIThresholdAlarmTxPowerLow OBJECT-TYPE
			SYNTAX Integer32
			MAX-ACCESS read-only
			STATUS current
			DESCRIPTION
				"The Power threshold -40~8,1647 (dBm)
				It must be devided by 10000.
				"
			::= { fkEponOnuDMIThresholdEntry 15 }

		
		-- 1.3.6.1.4.1.10428 9 1.101.20.3.4.2.1.16
		fkEponOnuDMIThresholdAlarmTxPowerHigh OBJECT-TYPE
			SYNTAX Integer32
			MAX-ACCESS read-only
			STATUS current
			DESCRIPTION
				"The Power threshold -40~8,1647 (dBm)
				It must be devided by 10000.
				"
			::= { fkEponOnuDMIThresholdEntry 16 }

		
		-- 1.3.6.1.4.1.10428 9 1.101.20.3.4.2.1.17
		fkEponOnuDMIThresholdWarnRxPowerLow OBJECT-TYPE
			SYNTAX Integer32
			MAX-ACCESS read-only
			STATUS current
			DESCRIPTION
				"The Power threshold -40~8,1647 (dBm)
				It must be devided by 10000.
				"
			::= { fkEponOnuDMIThresholdEntry 17 }

		
		-- 1.3.6.1.4.1.10428 9 1.101.20.3.4.2.1.18
		fkEponOnuDMIThresholdWarnRxPowerHigh OBJECT-TYPE
			SYNTAX Integer32
			MAX-ACCESS read-only
			STATUS current
			DESCRIPTION
				"The Power threshold -40~8,1647 (dBm)
				It must be devided by 10000.
				"
			::= { fkEponOnuDMIThresholdEntry 18 }

		
		-- 1.3.6.1.4.1.10428 9 1.101.20.3.4.2.1.19
		fkEponOnuDMIThresholdAlarmRxPowerLow OBJECT-TYPE
			SYNTAX Integer32
			MAX-ACCESS read-only
			STATUS current
			DESCRIPTION
				"The Power threshold -40~8,1647 (dBm)
				It must be devided by 10000.
				"
			::= { fkEponOnuDMIThresholdEntry 19 }

		
		-- 1.3.6.1.4.1.10428 9 1.101.20.3.4.2.1.20
		fkEponOnuDMIThresholdAlarmRxPowerHigh OBJECT-TYPE
			SYNTAX Integer32
			MAX-ACCESS read-only
			STATUS current
			DESCRIPTION
				"The Power threshold -40~8,1647 (dBm)
				It must be devided by 10000.
				"
			::= { fkEponOnuDMIThresholdEntry 20 }

		
		-- 1.3.6.1.4.1.10428 9 1.101.20.3.4.3
		fkEponOnuDMIThresholdControl OBJECT IDENTIFIER ::= { fkEponOnuDMI 3 }

		
		-- 1.3.6.1.4.1.10428 9 1.101.20.3.4.3.1
		fkEponOnuDMIThresholdControlRequest OBJECT-TYPE
			SYNTAX INTEGER
				{
				setEponOnuDMIThreshold(1),
				noEponOnuDMIThreshold(2)
				}
			MAX-ACCESS read-write
			STATUS current
			DESCRIPTION
				"The request of a user command"
			::= { fkEponOnuDMIThresholdControl 1 }

		
		-- 1.3.6.1.4.1.10428 9 1.101.20.3.4.3.2
		fkEponOnuDMIThresholdControlStatus OBJECT-TYPE
			SYNTAX FkControlStatusType
			MAX-ACCESS read-only
			STATUS current
			DESCRIPTION
				"The status of user command"
			::= { fkEponOnuDMIThresholdControl 2 }

		
		-- 1.3.6.1.4.1.10428 9 1.101.20.3.4.3.3
		fkEponOnuDMIThresholdControlTimer OBJECT-TYPE
			SYNTAX Gauge32
			MAX-ACCESS read-write
			STATUS current
			DESCRIPTION
				"The maximum time for the manager for a long running user command"
			::= { fkEponOnuDMIThresholdControl 3 }

		
		-- 1.3.6.1.4.1.10428 9 1.101.20.3.4.3.4
		fkEponOnuDMIThresholdControlTimeStamp OBJECT-TYPE
			SYNTAX TimeTicks
			MAX-ACCESS read-only
			STATUS current
			DESCRIPTION
				"The time stamp of the last command(end of command)"
			::= { fkEponOnuDMIThresholdControl 4 }

		
		-- 1.3.6.1.4.1.10428 9 1.101.20.3.4.3.5
		fkEponOnuDMIThresholdControlReqResult OBJECT-TYPE
			SYNTAX FkControlRequestResultType
			MAX-ACCESS read-only
			STATUS current
			DESCRIPTION
				"The result of the last user command"
			::= { fkEponOnuDMIThresholdControl 5 }

		
		-- 1.3.6.1.4.1.10428 9 1.101.20.3.4.3.6
		fkEponOnuDMIThresholdControlOltIndex OBJECT-TYPE
			SYNTAX INTEGER (1..255)
			MAX-ACCESS read-write
			STATUS current
			DESCRIPTION
				"OLT index"
			::= { fkEponOnuDMIThresholdControl 6 }

		
		-- 1.3.6.1.4.1.10428 9 1.101.20.3.4.3.7
		fkEponOnuDMIThresholdControlOnuIndex OBJECT-TYPE
			SYNTAX Integer32 (1..64)
			MAX-ACCESS read-write
			STATUS current
			DESCRIPTION
				"ONU index"
			::= { fkEponOnuDMIThresholdControl 7 }

		
		-- 1.3.6.1.4.1.10428 9 1.101.20.3.4.3.8
		fkEponOnuDMIThresholdControlMonitorType OBJECT-TYPE
			SYNTAX INTEGER
				{
				temper(1),
				voltage(2),
				txbias(3),
				txpower(4),
				rxpower(5)
				}
			MAX-ACCESS read-write
			STATUS current
			DESCRIPTION
				"Onu DMI monitor type."
			::= { fkEponOnuDMIThresholdControl 8 }

		
		-- 1.3.6.1.4.1.10428 9 1.101.20.3.4.3.9
		fkEponOnuDMIThresholdControlMode OBJECT-TYPE
			SYNTAX INTEGER
				{
				warning(1),
				alarm(2)
				}
			MAX-ACCESS read-write
			STATUS current
			DESCRIPTION
				"Onu DMI monitor threshold mode ,alarm or warning."
			::= { fkEponOnuDMIThresholdControl 9 }

		
		-- 1.3.6.1.4.1.10428 9 1.101.20.3.4.3.10
		fkEponOnuDMIThresholdControlLowThreshold OBJECT-TYPE
			SYNTAX Integer32
			MAX-ACCESS read-write
			STATUS current
			DESCRIPTION
				"onu DMI monitor low threshold, it must multiplied by 10000 and less than high threshold.
				temper threshold (-128 ~ 127.99 C)
				voltage threshold (0 ~ 6.5535 V)
				txbias threshold (0 ~ 131 mA)
				txpower threshold (-40 ~ 8.1647 dBm)
				rxpower threshold (-40 ~ 8.1647 dBm)"
			::= { fkEponOnuDMIThresholdControl 10 }

		
		-- 1.3.6.1.4.1.10428 9 1.101.20.3.4.3.11
		fkEponOnuDMIThresholdControlHighThreshold OBJECT-TYPE
			SYNTAX Integer32
			MAX-ACCESS read-write
			STATUS current
			DESCRIPTION
				"onu DMI monitor high threshold,it must multiplied by 10000 and more than low threshold.
				temper threshold (-128 ~ 127.99 C)
				voltage threshold (0 ~ 6.5535 V)
				txbias threshold (0 ~ 131 mA)
				txpower threshold (-40 ~ 8.1647 dBm)
				rxpower threshold (-40 ~ 8.1647 dBm)"
			::= { fkEponOnuDMIThresholdControl 11 }

		
		-- 1.3.6.1.4.1.10428 9 1.101.20.3.4.4
		fkEponOnuDMIThresholdNotification OBJECT IDENTIFIER ::= { fkEponOnuDMI 4 }

		
		-- 1.3.6.1.4.1.10428 9 1.101.20.3.4.4.1
		fkEponOnuDMIMonitorThresholdChanged NOTIFICATION-TYPE
			OBJECTS { fkEponOnuDmiThresholdControlRequest, fkEponOnuDmiThresholdControlTimeStamp, fkEponOnuDmiThresholdControlReqResult, fkEponOnuDmiThresholdControlOltIndex, fkEponOnuDmiThresholdControlOnuIndex, 
				fkEponOnuDmiThresholdControlMonitorType, fkEponOnuDmiThresholdControlMode, fkEponOnuDmiThresholdControlLowThreshold, fkEponOnuDmiThresholdControlHighThreshold }
			STATUS current
			DESCRIPTION 
				"Description."
			::= { fkEponOnuDMIThresholdNotification 1 }

		
		-- 1.3.6.1.4.1.10428 9 1.101.20.4
		fkEponOnuBridge OBJECT IDENTIFIER ::= { fkEpon 4 }

		
		-- 1.3.6.1.4.1.10428 9 1.101.20.4.1
		fkEponOnuVlan OBJECT IDENTIFIER ::= { fkEponOnuBridge 1 }

		
		-- 1.3.6.1.4.1.10428 9 1.101.20.4.1.1
		fkEponOnuVlanTable OBJECT-TYPE
			SYNTAX SEQUENCE OF FkEponOnuVlanEntry
			MAX-ACCESS not-accessible
			STATUS current
			DESCRIPTION
				"Description."
			::= { fkEponOnuVlan 1 }

		
		-- 1.3.6.1.4.1.10428 9 1.101.20.4.1.1.1
		fkEponOnuVlanEntry OBJECT-TYPE
			SYNTAX FkEponOnuVlanEntry
			MAX-ACCESS not-accessible
			STATUS current
			DESCRIPTION
				"Description."
			INDEX { fkEponOltIndex, fkEponOnuIndex, fkEponOnuVlanIndex }
			::= { fkEponOnuVlanTable 1 }

		
		FkEponOnuVlanEntry ::=
			SEQUENCE { 
				fkEponOnuVlanIndex
					VlanIndex,
				fkEponOnuVlanEgressPorts
					PortList,
				fkEponOnuVlanUntaggedPorts
					PortList
			 }

		-- 1.3.6.1.4.1.10428 9 1.101.20.4.1.1.1.1
		fkEponOnuVlanIndex OBJECT-TYPE
			SYNTAX VlanIndex (1..4094)
			MAX-ACCESS read-only
			STATUS current
			DESCRIPTION
				"The index of ONU VLAN"
			::= { fkEponOnuVlanEntry 1 }

		
		-- 1.3.6.1.4.1.10428 9 1.101.20.4.1.1.1.2
		fkEponOnuVlanEgressPorts OBJECT-TYPE
			SYNTAX PortList
			MAX-ACCESS read-only
			STATUS current
			DESCRIPTION
				"The set of ports which are transmitting traffic for this ONU VLAN as either tagged or untagged frames."
			::= { fkEponOnuVlanEntry 2 }

		
		-- 1.3.6.1.4.1.10428 9 1.101.20.4.1.1.1.3
		fkEponOnuVlanUntaggedPorts OBJECT-TYPE
			SYNTAX PortList
			MAX-ACCESS read-only
			STATUS current
			DESCRIPTION
				"The set of ports which are transmitting traffic for this VLAN as untagged frames"
			::= { fkEponOnuVlanEntry 3 }

		
		-- 1.3.6.1.4.1.10428 9 1.101.20.4.2
		fkEponOnuPort OBJECT IDENTIFIER ::= { fkEponOnuBridge 2 }

		
		-- 1.3.6.1.4.1.10428 9 1.101.20.4.2.1
		fkEponOnuPortTable OBJECT-TYPE
			SYNTAX SEQUENCE OF FkEponOnuPortEntry
			MAX-ACCESS not-accessible
			STATUS current
			DESCRIPTION
				"Description."
			::= { fkEponOnuPort 1 }

		
		-- 1.3.6.1.4.1.10428 9 1.101.20.4.2.1.1
		fkEponOnuPortEntry OBJECT-TYPE
			SYNTAX FkEponOnuPortEntry
			MAX-ACCESS not-accessible
			STATUS current
			DESCRIPTION
				"Description."
			INDEX { fkEponOltIndex, fkEponOnuIndex, fkEponOnuPortIndex }
			::= { fkEponOnuPortTable 1 }

		
		FkEponOnuPortEntry ::=
			SEQUENCE { 
				fkEponOnuPortIndex
					INTEGER,
				fkEponOnuPortAdminStatus
					INTEGER,
				fkEponOnuPortOperStatus
					INTEGER,
				fkEponOnuPortNego
					INTEGER,
				fkEponOnuPortSpeed
					Integer32,
				fkEponOnuPortDuplex
					INTEGER,
				fkEponOnuPortMaxHost
					Integer32,
				fkEponOnuPortPvid
					VlanIndex,
				fkEponOnuPortIngressRateLimitMode
					INTEGER,
				fkEponOnuPortIngressRateLimit
					INTEGER,
				fkEponOnuPortEgressRateLimit
					INTEGER,
				fkEponOnuPortFlowControl
					INTEGER,
				fkEponOnuPortAgingTime
					Integer32,
				fkEponOnuPortForwardMode
					EnableFlag
			 }

		-- 1.3.6.1.4.1.10428 9 1.101.20.4.2.1.1.1
		fkEponOnuPortIndex OBJECT-TYPE
			SYNTAX INTEGER (1..256)
			MAX-ACCESS read-only
			STATUS current
			DESCRIPTION
				"The index of the ONU port"
			::= { fkEponOnuPortEntry 1 }

		
		-- 1.3.6.1.4.1.10428 9 1.101.20.4.2.1.1.2
		fkEponOnuPortAdminStatus OBJECT-TYPE
			SYNTAX INTEGER
				{
				na(0),
				enable(1),
				disable(2)
				}
			MAX-ACCESS read-only
			STATUS current
			DESCRIPTION
				"The desired state of the ONU port"
			::= { fkEponOnuPortEntry 2 }

		
		-- 1.3.6.1.4.1.10428 9 1.101.20.4.2.1.1.3
		fkEponOnuPortOperStatus OBJECT-TYPE
			SYNTAX INTEGER
				{
				na(0),
				enable(1),
				disable(2)
				}
			MAX-ACCESS read-only
			STATUS current
			DESCRIPTION
				"The current operational state of the ONU port"
			::= { fkEponOnuPortEntry 3 }

		
		-- 1.3.6.1.4.1.10428 9 1.101.20.4.2.1.1.4
		fkEponOnuPortNego OBJECT-TYPE
			SYNTAX INTEGER
				{
				na(0),
				on(1),
				off(2)
				}
			MAX-ACCESS read-only
			STATUS current
			DESCRIPTION
				"It's auto-negotiation for a port, automatically to match the transmission speed and the duplex mode of the attached device"
			::= { fkEponOnuPortEntry 4 }

		
		-- 1.3.6.1.4.1.10428 9 1.101.20.4.2.1.1.5
		fkEponOnuPortSpeed OBJECT-TYPE
			SYNTAX Integer32
			MAX-ACCESS read-only
			STATUS current
			DESCRIPTION
				"It express port speed that configure transmit rate of each port."
			::= { fkEponOnuPortEntry 5 }

		
		-- 1.3.6.1.4.1.10428 9 1.101.20.4.2.1.1.6
		fkEponOnuPortDuplex OBJECT-TYPE
			SYNTAX INTEGER
				{
				na(0),
				full(1),
				half(2)
				}
			MAX-ACCESS read-only
			STATUS current
			DESCRIPTION
				"It express half duplex or full duplex mode. Only unidirectional communication is possible on half duplex mode and bi-directional communication is possible on full duplex mode to transmit packet for two ways."
			::= { fkEponOnuPortEntry 6 }

		
		-- 1.3.6.1.4.1.10428 9 1.101.20.4.2.1.1.7
		fkEponOnuPortMaxHost OBJECT-TYPE
			SYNTAX Integer32
			MAX-ACCESS read-only
			STATUS current
			DESCRIPTION
				"It can limit the number of users by configuring maximum number of users also named as Max host for each ONU port"
			::= { fkEponOnuPortEntry 7 }

		
		-- 1.3.6.1.4.1.10428 9 1.101.20.4.2.1.1.8
		fkEponOnuPortPvid OBJECT-TYPE
			SYNTAX VlanIndex
			MAX-ACCESS read-only
			STATUS current
			DESCRIPTION
				"It is PVID that configure in ONU port"
			::= { fkEponOnuPortEntry 8 }

		
		-- 1.3.6.1.4.1.10428 9 1.101.20.4.2.1.1.9
		fkEponOnuPortIngressRateLimitMode OBJECT-TYPE
			SYNTAX INTEGER
				{
				all(0),
				multiBroadUnicast(1),
				multiBroadcast(2),
				broadcast(3)
				}
			MAX-ACCESS read-only
			STATUS current
			DESCRIPTION
				"It is rate limit mode in Ingress"
			::= { fkEponOnuPortEntry 9 }

		
		-- 1.3.6.1.4.1.10428 9 1.101.20.4.2.1.1.10
		fkEponOnuPortIngressRateLimit OBJECT-TYPE
			SYNTAX INTEGER (0 | 62..100000)
			MAX-ACCESS read-only
			STATUS current
			DESCRIPTION
				"It is configurable port rate limit in Ingress"
			::= { fkEponOnuPortEntry 10 }

		
		-- 1.3.6.1.4.1.10428 9 1.101.20.4.2.1.1.11
		fkEponOnuPortEgressRateLimit OBJECT-TYPE
			SYNTAX INTEGER (0 | 62..100000)
			MAX-ACCESS read-only
			STATUS current
			DESCRIPTION
				"It is configurable port rate limit in Egress"
			::= { fkEponOnuPortEntry 11 }

		
		-- 1.3.6.1.4.1.10428 9 1.101.20.4.2.1.1.12
		fkEponOnuPortFlowControl OBJECT-TYPE
			SYNTAX INTEGER
				{
				none(0),
				on(1),
				off(2)
				}
			MAX-ACCESS read-only
			STATUS current
			DESCRIPTION
				"Description."
			::= { fkEponOnuPortEntry 12 }

		
		-- 1.3.6.1.4.1.10428 9 1.101.20.4.2.1.1.13
		fkEponOnuPortAgingTime OBJECT-TYPE
			SYNTAX Integer32
			MAX-ACCESS read-only
			STATUS current
			DESCRIPTION
				"onu max-host aging time."
			::= { fkEponOnuPortEntry 13 }

		
		-- 1.3.6.1.4.1.10428 9 1.101.20.4.2.1.1.14
		fkEponOnuPortForwardMode OBJECT-TYPE
			SYNTAX EnableFlag
			MAX-ACCESS read-write
			STATUS current
			DESCRIPTION
				"onu max-host forward mode."
			::= { fkEponOnuPortEntry 14 }

		
		-- 1.3.6.1.4.1.10428 9 1.101.20.4.2.2
		fkEponOnuPortControl OBJECT IDENTIFIER ::= { fkEponOnuPort 2 }

		
		-- 1.3.6.1.4.1.10428 9 1.101.20.4.2.2.1
		fkEponOnuPortControlRequest OBJECT-TYPE
			SYNTAX INTEGER { setEponOnuPortReset(1) }
			MAX-ACCESS read-write
			STATUS current
			DESCRIPTION
				"The request of a user command"
			::= { fkEponOnuPortControl 1 }

		
		-- 1.3.6.1.4.1.10428 9 1.101.20.4.2.2.2
		fkEponOnuPortControlStatus OBJECT-TYPE
			SYNTAX FkControlStatusType
			MAX-ACCESS read-only
			STATUS current
			DESCRIPTION
				"The status of user command"
			::= { fkEponOnuPortControl 2 }

		
		-- 1.3.6.1.4.1.10428 9 1.101.20.4.2.2.3
		fkEponOnuPortControlTimer OBJECT-TYPE
			SYNTAX Gauge32
			MAX-ACCESS read-write
			STATUS current
			DESCRIPTION
				"The maximum time for the manager for a long running user command"
			::= { fkEponOnuPortControl 3 }

		
		-- 1.3.6.1.4.1.10428 9 1.101.20.4.2.2.4
		fkEponOnuPortControlTimeStamp OBJECT-TYPE
			SYNTAX TimeTicks
			MAX-ACCESS read-only
			STATUS current
			DESCRIPTION
				"The time stamp of the last command(end of command)"
			::= { fkEponOnuPortControl 4 }

		
		-- 1.3.6.1.4.1.10428 9 1.101.20.4.2.2.5
		fkEponOnuPortControlReqResult OBJECT-TYPE
			SYNTAX FkControlRequestResultType
			MAX-ACCESS read-only
			STATUS current
			DESCRIPTION
				"The result of the last user command"
			::= { fkEponOnuPortControl 5 }

		
		-- 1.3.6.1.4.1.10428 9 1.101.20.4.2.2.6
		fkEponOnuPortControlOltIndex OBJECT-TYPE
			SYNTAX INTEGER (1..512)
			MAX-ACCESS read-write
			STATUS current
			DESCRIPTION
				"OLT port Index"
			::= { fkEponOnuPortControl 6 }

		
		-- 1.3.6.1.4.1.10428 9 1.101.20.4.2.2.7
		fkEponOnuPortControlOnuIndex OBJECT-TYPE
			SYNTAX INTEGER (1..64)
			MAX-ACCESS read-write
			STATUS current
			DESCRIPTION
				"ONU Index"
			::= { fkEponOnuPortControl 7 }

		
		-- 1.3.6.1.4.1.10428 9 1.101.20.4.2.2.8
		fkEponOnuPortControlPortIndex OBJECT-TYPE
			SYNTAX INTEGER (1..256)
			MAX-ACCESS read-write
			STATUS current
			DESCRIPTION
				"The index of the ONU port"
			::= { fkEponOnuPortControl 8 }

		
		-- 1.3.6.1.4.1.10428 9 1.101.20.4.2.3
		fkEponOnuPortNotification OBJECT IDENTIFIER ::= { fkEponOnuPort 3 }

		
		-- 1.3.6.1.4.1.10428 9 1.101.20.4.2.3.1
		fkEponOnuPortReset NOTIFICATION-TYPE
			OBJECTS { fkEponOnuPortControlRequest, fkEponOnuPortControlTimeStamp, fkEponOnuPortControlReqResult, fkEponOnuPortControlOltIndex, fkEponOnuPortControlOnuIndex, 
				fkEponOnuPortControlPortIndex }
			STATUS current
			DESCRIPTION 
				"Description."
			::= { fkEponOnuPortNotification 1 }

		
		-- 1.3.6.1.4.1.10428 9 1.101.20.4.3
		fkEponOnuFdb OBJECT IDENTIFIER ::= { fkEponOnuBridge 3 }

		
		-- 1.3.6.1.4.1.10428 9 1.101.20.4.3.1
		fkEponOnuFdbTable OBJECT-TYPE
			SYNTAX SEQUENCE OF FkEponOnuFdbEntry
			MAX-ACCESS not-accessible
			STATUS current
			DESCRIPTION
				"Description."
			::= { fkEponOnuFdb 1 }

		
		-- 1.3.6.1.4.1.10428 9 1.101.20.4.3.1.1
		fkEponOnuFdbEntry OBJECT-TYPE
			SYNTAX FkEponOnuFdbEntry
			MAX-ACCESS not-accessible
			STATUS current
			DESCRIPTION
				"Description."
			INDEX { fkEponOltIndex, fkEponOnuIndex, fkEponOnuFdbMacAddress }
			::= { fkEponOnuFdbTable 1 }

		
		FkEponOnuFdbEntry ::=
			SEQUENCE { 
				fkEponOnuFdbMacAddress
					MacAddress,
				fkEponOnuFdbType
					INTEGER,
				fkEponOnuFdbPermission
					INTEGER
			 }

		-- 1.3.6.1.4.1.10428 9 1.101.20.4.3.1.1.1
		fkEponOnuFdbMacAddress OBJECT-TYPE
			SYNTAX MacAddress
			MAX-ACCESS read-only
			STATUS current
			DESCRIPTION
				"The fdb address of ONT"
			::= { fkEponOnuFdbEntry 1 }

		
		-- 1.3.6.1.4.1.10428 9 1.101.20.4.3.1.1.2
		fkEponOnuFdbType OBJECT-TYPE
			SYNTAX INTEGER
				{
				local(0),
				static(1),
				dynamic(2)
				}
			MAX-ACCESS read-only
			STATUS current
			DESCRIPTION
				"The type of fdb address."
			::= { fkEponOnuFdbEntry 2 }

		
		-- 1.3.6.1.4.1.10428 9 1.101.20.4.3.1.1.3
		fkEponOnuFdbPermission OBJECT-TYPE
			SYNTAX INTEGER
				{
				deny(0),
				permit(1)
				}
			MAX-ACCESS read-only
			STATUS current
			DESCRIPTION
				"Description."
			::= { fkEponOnuFdbEntry 3 }

		
		-- 1.3.6.1.4.1.10428 9 1.101.20.4.3.2
		fkEponOnuFdbControl OBJECT IDENTIFIER ::= { fkEponOnuFdb 2 }

		
		-- 1.3.6.1.4.1.10428 9 1.101.20.4.3.2.1
		fkEponOnuFdbControlRequest OBJECT-TYPE
			SYNTAX INTEGER { clearOltMac(1) }
			MAX-ACCESS read-write
			STATUS current
			DESCRIPTION
				"Description."
			::= { fkEponOnuFdbControl 1 }

		
		-- 1.3.6.1.4.1.10428 9 1.101.20.4.3.2.2
		fkEponOnuFdbControlStatus OBJECT-TYPE
			SYNTAX FkControlStatusType
			MAX-ACCESS read-only
			STATUS current
			DESCRIPTION
				"Description."
			::= { fkEponOnuFdbControl 2 }

		
		-- 1.3.6.1.4.1.10428 9 1.101.20.4.3.2.3
		fkEponOnuFdbControlTimer OBJECT-TYPE
			SYNTAX Gauge32
			MAX-ACCESS read-write
			STATUS current
			DESCRIPTION
				"Description."
			::= { fkEponOnuFdbControl 3 }

		
		-- 1.3.6.1.4.1.10428 9 1.101.20.4.3.2.4
		fkEponOnuFdbControlTimeStamp OBJECT-TYPE
			SYNTAX TimeTicks
			MAX-ACCESS read-only
			STATUS current
			DESCRIPTION
				"Description."
			::= { fkEponOnuFdbControl 4 }

		
		-- 1.3.6.1.4.1.10428 9 1.101.20.4.3.2.5
		fkEponOnuFdbControlReqResult OBJECT-TYPE
			SYNTAX FkControlRequestResultType
			MAX-ACCESS read-only
			STATUS current
			DESCRIPTION
				"Description."
			::= { fkEponOnuFdbControl 5 }

		
		-- 1.3.6.1.4.1.10428 9 1.101.20.4.3.2.6
		fkEponOnuFdbControlOltIndex OBJECT-TYPE
			SYNTAX INTEGER (1..512)
			MAX-ACCESS read-write
			STATUS current
			DESCRIPTION
				"Description."
			::= { fkEponOnuFdbControl 6 }

		
		-- 1.3.6.1.4.1.10428 9 1.101.20.4.3.2.7
		fkEponOnuFdbControlOnuIndex OBJECT-TYPE
			SYNTAX INTEGER (1..64)
			MAX-ACCESS read-write
			STATUS current
			DESCRIPTION
				"Description."
			::= { fkEponOnuFdbControl 7 }

		
		-- 1.3.6.1.4.1.10428 9 1.101.20.4.3.2.8
		fkEponOnuFdbControlType OBJECT-TYPE
			SYNTAX INTEGER
				{
				dynamic(1),
				static(2),
				all(3)
				}
			MAX-ACCESS read-write
			STATUS current
			DESCRIPTION
				"Description."
			::= { fkEponOnuFdbControl 8 }

		
		-- 1.3.6.1.4.1.10428 9 1.101.20.4.3.3
		fkEponOnuFdbNotification OBJECT IDENTIFIER ::= { fkEponOnuFdb 3 }

		
		-- 1.3.6.1.4.1.10428 9 1.101.20.4.3.3.1
		fkEponOnuFdbMacCleared NOTIFICATION-TYPE
			OBJECTS { fkEponOnuFdbControlRequest, fkEponOnuFdbControlTimeStamp, fkEponOnuFdbControlReqResult, fkEponOnuFdbControlOltIndex, fkEponOnuFdbControlOnuIndex, 
				fkEponOnuFdbControlType }
			STATUS current
			DESCRIPTION 
				"Description."
			::= { fkEponOnuFdbNotification 1 }

		
		-- 1.3.6.1.4.1.10428 9 1.101.20.4.4
		fkEponOnuUserMac OBJECT IDENTIFIER ::= { fkEponOnuBridge 4 }

		
		-- 1.3.6.1.4.1.10428 9 1.101.20.4.4.1
		fkEponOnuUserMacTable OBJECT-TYPE
			SYNTAX SEQUENCE OF FkEponOnuUserMacEntry
			MAX-ACCESS not-accessible
			STATUS current
			DESCRIPTION
				"Description."
			::= { fkEponOnuUserMac 1 }

		
		-- 1.3.6.1.4.1.10428 9 1.101.20.4.4.1.1
		fkEponOnuUserMacEntry OBJECT-TYPE
			SYNTAX FkEponOnuUserMacEntry
			MAX-ACCESS not-accessible
			STATUS current
			DESCRIPTION
				"Description."
			INDEX { fkEponOltIndex, fkEponOnuIndex, fkEponOnuUserMacIndex }
			::= { fkEponOnuUserMacTable 1 }

		
		FkEponOnuUserMacEntry ::=
			SEQUENCE { 
				fkEponOnuUserMacIndex
					INTEGER,
				fkEponOnuUserMacMacAddress
					MacAddress,
				fkEponOnuUserMacUsedTime
					TimeTicks
			 }

		-- 1.3.6.1.4.1.10428 9 1.101.20.4.4.1.1.1
		fkEponOnuUserMacIndex OBJECT-TYPE
			SYNTAX INTEGER (1..8)
			MAX-ACCESS read-only
			STATUS current
			DESCRIPTION
				"Description."
			::= { fkEponOnuUserMacEntry 1 }

		
		-- 1.3.6.1.4.1.10428 9 1.101.20.4.4.1.1.2
		fkEponOnuUserMacMacAddress OBJECT-TYPE
			SYNTAX MacAddress
			MAX-ACCESS read-only
			STATUS current
			DESCRIPTION
				"Description."
			::= { fkEponOnuUserMacEntry 2 }

		
		-- 1.3.6.1.4.1.10428 9 1.101.20.4.4.1.1.3
		fkEponOnuUserMacUsedTime OBJECT-TYPE
			SYNTAX TimeTicks
			MAX-ACCESS read-only
			STATUS current
			DESCRIPTION
				"Description."
			::= { fkEponOnuUserMacEntry 3 }

		
		-- 1.3.6.1.4.1.10428 9 1.101.20.4.5
		fkEponOnuSubscriber OBJECT IDENTIFIER ::= { fkEponOnuBridge 5 }

		
		-- 1.3.6.1.4.1.10428 9 1.101.20.4.5.1
		fkEponOnuSubscriberCurrentTable OBJECT-TYPE
			SYNTAX SEQUENCE OF FkEponOnuSubscriberCurrentEntry
			MAX-ACCESS not-accessible
			STATUS current
			DESCRIPTION
				"Description."
			::= { fkEponOnuSubscriber 1 }

		
		-- 1.3.6.1.4.1.10428 9 1.101.20.4.5.1.1
		fkEponOnuSubscriberCurrentEntry OBJECT-TYPE
			SYNTAX FkEponOnuSubscriberCurrentEntry
			MAX-ACCESS not-accessible
			STATUS current
			DESCRIPTION
				"Description."
			INDEX { fkEponOltIndex, fkEponOnuIndex, fkEponOnuSubscriberCurrentIpAddress }
			::= { fkEponOnuSubscriberCurrentTable 1 }

		
		FkEponOnuSubscriberCurrentEntry ::=
			SEQUENCE { 
				fkEponOnuSubscriberCurrentIpAddress
					IpAddress,
				fkEponOnuSubscriberCurrentMacAddress
					MacAddress,
				fkEponOnuSubscriberCurrentPort
					INTEGER,
				fkEponOnuSubscriberCurrentTime
					Gauge32
			 }

		-- 1.3.6.1.4.1.10428 9 1.101.20.4.5.1.1.1
		fkEponOnuSubscriberCurrentIpAddress OBJECT-TYPE
			SYNTAX IpAddress
			MAX-ACCESS read-only
			STATUS current
			DESCRIPTION
				"Description."
			::= { fkEponOnuSubscriberCurrentEntry 1 }

		
		-- 1.3.6.1.4.1.10428 9 1.101.20.4.5.1.1.2
		fkEponOnuSubscriberCurrentMacAddress OBJECT-TYPE
			SYNTAX MacAddress
			MAX-ACCESS read-only
			STATUS current
			DESCRIPTION
				"Description."
			::= { fkEponOnuSubscriberCurrentEntry 2 }

		
		-- 1.3.6.1.4.1.10428 9 1.101.20.4.5.1.1.3
		fkEponOnuSubscriberCurrentPort OBJECT-TYPE
			SYNTAX INTEGER (1..256)
			MAX-ACCESS read-only
			STATUS current
			DESCRIPTION
				"Description."
			::= { fkEponOnuSubscriberCurrentEntry 3 }

		
		-- 1.3.6.1.4.1.10428 9 1.101.20.4.5.1.1.4
		fkEponOnuSubscriberCurrentTime OBJECT-TYPE
			SYNTAX Gauge32
			MAX-ACCESS read-only
			STATUS current
			DESCRIPTION
				"Description."
			::= { fkEponOnuSubscriberCurrentEntry 4 }

		
		-- 1.3.6.1.4.1.10428 9 1.101.20.4.5.2
		fkEponOnuSubscriberHistoryTable OBJECT-TYPE
			SYNTAX SEQUENCE OF FkEponOnuSubscriberHistoryEntry
			MAX-ACCESS not-accessible
			STATUS current
			DESCRIPTION
				"Description."
			::= { fkEponOnuSubscriber 2 }

		
		-- 1.3.6.1.4.1.10428 9 1.101.20.4.5.2.1
		fkEponOnuSubscriberHistoryEntry OBJECT-TYPE
			SYNTAX FkEponOnuSubscriberHistoryEntry
			MAX-ACCESS not-accessible
			STATUS current
			DESCRIPTION
				"Description."
			INDEX { fkEponOltIndex, fkEponOnuIndex, fkEponOnuSubscriberHistoryTime, fkEponOnuSubscriberHistoryIpAddress }
			::= { fkEponOnuSubscriberHistoryTable 1 }

		
		FkEponOnuSubscriberHistoryEntry ::=
			SEQUENCE { 
				fkEponOnuSubscriberHistoryIpAddress
					IpAddress,
				fkEponOnuSubscriberHistoryMacAddress
					MacAddress,
				fkEponOnuSubscriberHistoryPort
					INTEGER,
				fkEponOnuSubscriberHistoryTime
					Gauge32
			 }

		-- 1.3.6.1.4.1.10428 9 1.101.20.4.5.2.1.1
		fkEponOnuSubscriberHistoryIpAddress OBJECT-TYPE
			SYNTAX IpAddress
			MAX-ACCESS read-only
			STATUS current
			DESCRIPTION
				"Description."
			::= { fkEponOnuSubscriberHistoryEntry 1 }

		
		-- 1.3.6.1.4.1.10428 9 1.101.20.4.5.2.1.2
		fkEponOnuSubscriberHistoryMacAddress OBJECT-TYPE
			SYNTAX MacAddress
			MAX-ACCESS read-only
			STATUS current
			DESCRIPTION
				"Description."
			::= { fkEponOnuSubscriberHistoryEntry 2 }

		
		-- 1.3.6.1.4.1.10428 9 1.101.20.4.5.2.1.3
		fkEponOnuSubscriberHistoryPort OBJECT-TYPE
			SYNTAX INTEGER (1..256)
			MAX-ACCESS read-only
			STATUS current
			DESCRIPTION
				"Description."
			::= { fkEponOnuSubscriberHistoryEntry 3 }

		
		-- 1.3.6.1.4.1.10428 9 1.101.20.4.5.2.1.4
		fkEponOnuSubscriberHistoryTime OBJECT-TYPE
			SYNTAX Gauge32 (1..65535)
			MAX-ACCESS read-only
			STATUS current
			DESCRIPTION
				"Description."
			::= { fkEponOnuSubscriberHistoryEntry 4 }

		
		-- 1.3.6.1.4.1.10428 9 1.101.20.4.5.3
		fkEponOnuSubscriberControl OBJECT IDENTIFIER ::= { fkEponOnuSubscriber 3 }

		
		-- 1.3.6.1.4.1.10428 9 1.101.20.4.5.3.1
		fkEponOnuSubscriberControlRequest OBJECT-TYPE
			SYNTAX INTEGER
				{
				clearSubscriberHistoryOlt(1),
				clearSubscriberHistoryOnu(2)
				}
			MAX-ACCESS read-write
			STATUS current
			DESCRIPTION
				"Description."
			::= { fkEponOnuSubscriberControl 1 }

		
		-- 1.3.6.1.4.1.10428 9 1.101.20.4.5.3.2
		fkEponOnuSubscriberControlStatus OBJECT-TYPE
			SYNTAX FkControlStatusType
			MAX-ACCESS read-only
			STATUS current
			DESCRIPTION
				"Description."
			::= { fkEponOnuSubscriberControl 2 }

		
		-- 1.3.6.1.4.1.10428 9 1.101.20.4.5.3.3
		fkEponOnuSubscriberControlTimer OBJECT-TYPE
			SYNTAX Gauge32
			MAX-ACCESS read-write
			STATUS current
			DESCRIPTION
				"Description."
			::= { fkEponOnuSubscriberControl 3 }

		
		-- 1.3.6.1.4.1.10428 9 1.101.20.4.5.3.4
		fkEponOnuSubscriberControlTimeStamp OBJECT-TYPE
			SYNTAX Counter64
			MAX-ACCESS read-only
			STATUS current
			DESCRIPTION
				"Description."
			::= { fkEponOnuSubscriberControl 4 }

		
		-- 1.3.6.1.4.1.10428 9 1.101.20.4.5.3.5
		fkEponOnuSubscriberControlReqResult OBJECT-TYPE
			SYNTAX Integer32
			MAX-ACCESS read-write
			STATUS current
			DESCRIPTION
				"Description."
			::= { fkEponOnuSubscriberControl 5 }

		
		-- 1.3.6.1.4.1.10428 9 1.101.20.4.5.3.6
		fkEponOnuSubscriberControlOltIndex OBJECT-TYPE
			SYNTAX INTEGER (1..512)
			MAX-ACCESS read-write
			STATUS current
			DESCRIPTION
				"Description."
			::= { fkEponOnuSubscriberControl 6 }

		
		-- 1.3.6.1.4.1.10428 9 1.101.20.4.5.3.7
		fkEponOnuSubscriberControlOnuIndex OBJECT-TYPE
			SYNTAX INTEGER (1..64)
			MAX-ACCESS read-write
			STATUS current
			DESCRIPTION
				"Description."
			::= { fkEponOnuSubscriberControl 7 }

		
		-- 1.3.6.1.4.1.10428 9 1.101.20.4.5.4
		fkEponOnuSubscriberNotification OBJECT IDENTIFIER ::= { fkEponOnuSubscriber 4 }

		
		-- 1.3.6.1.4.1.10428 9 1.101.20.4.5.4.1
		fkEponOnuSubscriberHistoryOltCleared NOTIFICATION-TYPE
			OBJECTS { fkEponOnuSubscriberControlRequest, fkEponOnuSubscriberControlTimeStamp, fkEponOnuSubscriberControlReqResult, fkEponOnuSubscriberControlOltIndex }
			STATUS current
			DESCRIPTION 
				"Description."
			::= { fkEponOnuSubscriberNotification 1 }

		
		-- 1.3.6.1.4.1.10428 9 1.101.20.4.5.4.2
		fkEponOnuSubscriberHistroyOnuCleared NOTIFICATION-TYPE
			OBJECTS { fkEponOnuSubscriberControlRequest, fkEponOnuSubscriberControlTimeStamp, fkEponOnuSubscriberControlReqResult, fkEponOnuSubscriberControlOltIndex, fkEponOnuSubscriberControlOnuIndex
				 }
			STATUS current
			DESCRIPTION 
				"Description."
			::= { fkEponOnuSubscriberNotification 2 }

		
		-- 1.3.6.1.4.1.10428 9 1.101.20.4.6
		fkEponOnuMacTable OBJECT IDENTIFIER ::= { fkEponOnuBridge 6 }

		
		-- 1.3.6.1.4.1.10428 9 1.101.20.4.6.1
		fkEponOnuMacTableTable OBJECT-TYPE
			SYNTAX SEQUENCE OF FkEponOnuMacTableEntry
			MAX-ACCESS not-accessible
			STATUS current
			DESCRIPTION
				"Description."
			::= { fkEponOnuMacTable 1 }

		
		-- 1.3.6.1.4.1.10428 9 1.101.20.4.6.1.1
		fkEponOnuMacTableEntry OBJECT-TYPE
			SYNTAX FkEponOnuMacTableEntry
			MAX-ACCESS not-accessible
			STATUS current
			DESCRIPTION
				"Description."
			INDEX { fkEponOltIndex, fkEponOnuIndex, fkEponOnuFdbMacAddress }
			::= { fkEponOnuMacTableTable 1 }

		
		FkEponOnuMacTableEntry ::=
			SEQUENCE { 
				fkEponOnuMacTableDynamicMacAddress
					MacAddress,
				fkEponOnuMacTableStaticMacAddress
					MacAddress
			 }

		-- 1.3.6.1.4.1.10428 9 1.101.20.4.6.1.1.1
		fkEponOnuMacTableDynamicMacAddress OBJECT-TYPE
			SYNTAX MacAddress
			MAX-ACCESS read-only
			STATUS current
			DESCRIPTION
				"The fdb address of ONT"
			::= { fkEponOnuMacTableEntry 1 }

		
		-- 1.3.6.1.4.1.10428 9 1.101.20.4.6.1.1.2
		fkEponOnuMacTableStaticMacAddress OBJECT-TYPE
			SYNTAX MacAddress
			MAX-ACCESS read-only
			STATUS current
			DESCRIPTION
				"The fdb address of ONT"
			::= { fkEponOnuMacTableEntry 2 }

		
		-- 1.3.6.1.4.1.10428 9 1.101.20.5
		fkEponProfile OBJECT IDENTIFIER ::= { fkEpon 5 }

		
		-- 1.3.6.1.4.1.10428 9 1.101.20.5.1
		fkEponProfileBase OBJECT IDENTIFIER ::= { fkEponProfile 1 }

		
		-- 1.3.6.1.4.1.10428 9 1.101.20.5.1.1
		fkEponProfileTable OBJECT-TYPE
			SYNTAX SEQUENCE OF FkEponProfileEntry
			MAX-ACCESS not-accessible
			STATUS current
			DESCRIPTION
				"Description."
			::= { fkEponProfileBase 1 }

		
		-- 1.3.6.1.4.1.10428 9 1.101.20.5.1.1.1
		fkEponProfileEntry OBJECT-TYPE
			SYNTAX FkEponProfileEntry
			MAX-ACCESS not-accessible
			STATUS current
			DESCRIPTION
				"Description."
			INDEX { fkEponProfileIndex }
			::= { fkEponProfileTable 1 }

		
		FkEponProfileEntry ::=
			SEQUENCE { 
				fkEponProfileIndex
					INTEGER,
				fkEponProfileName
					OCTET STRING,
				fkEponProfileDPDownMaxBandwidth
					INTEGER,
				fkEponProfileDPDownMaxBurstSize
					INTEGER,
				fkEponProfileDPP2pMaxBandwidth
					INTEGER,
				fkEponProfileDPP2pMaxBurstSize
					INTEGER,
				fkEponProfileSlaGuaranteedBandwidth
					INTEGER,
				fkEponProfileSlaBestEffortBandwidth
					INTEGER,
				fkEponProfileSlaPlatoClass
					INTEGER,
				fkEponProfileSlaPlatoMinBandwidth1m
					INTEGER,
				fkEponProfileSlaPlatoMinBandwdith64k
					INTEGER,
				fkEponProfileSlaPlatoMaxBandwidth1m
					INTEGER,
				fkEponProfileSlaPlatoMaxBandwidth64k
					INTEGER,
				fkEponProfileSlaPlatoDelayLevel
					INTEGER,
				fkEponProfileExtendMtu
					EnableFlag,
				fkEponProfileIgmpFilter
					EnableFlag,
				fkEponProfileIgmpSnooping
					EnableFlag,
				fkEponProfileSTPenable
					EnableFlag,
				fkEponProfileSubscriberInfoCollection
					EnableFlag,
				fkEponProfileLoopDetectStatus
					EnableFlag,
				fkEponProfileLoopDetectBlockTimer
					INTEGER,
				fkEponProfileLoopDetectSendingpacket
					INTEGER,
				fkEponProfileSipMgPort
					INTEGER,
				fkEponProfileSipProxyServer
					OCTET STRING,
				fkEponProfileSipProxyServerPort
					INTEGER,
				fkEponProfileSipBackupProxyServer
					OCTET STRING,
				fkEponProfileSipBackupProxyServerPort
					INTEGER,
				fkEponProfileSipActiveServer
					OCTET STRING,
				fkEponProfileSipRegisterServer
					OCTET STRING,
				fkEponProfileSipRegisterServerPort
					INTEGER,
				fkEponProfileSipBackupRegisterServer
					OCTET STRING,
				fkEponProfileSipBackupRegisterServerPort
					INTEGER,
				fkEponProfileSipOutBindServer
					OCTET STRING,
				fkEponProfileSipOutBindServerPort
					INTEGER,
				fkEponProfileSipRegisterInterval
					INTEGER,
				fkEponProfileSipHeartBeatSwitch
					EnableFlag,
				fkEponProfileSipHeartBeatCycle
					INTEGER,
				fkEponProfileSipHeartBeatCount
					INTEGER,
				fkEponProfileSipDNS1Server
					OCTET STRING,
				fkEponProfileSipDNS2Server
					OCTET STRING,
				fkEponProfileVoiceT38enable
					EnableFlag,
				fkEponProfileModemControl
					EnableFlag,
				fkEponProfileDHCPEnable
					Integer32,
				fkEponProfileMacLearnStatus
					OCTET STRING
			 }

		-- 1.3.6.1.4.1.10428 9 1.101.20.5.1.1.1.1
		fkEponProfileIndex OBJECT-TYPE
			SYNTAX INTEGER (1..32)
			MAX-ACCESS read-only
			STATUS current
			DESCRIPTION
				"Profile Index"
			::= { fkEponProfileEntry 1 }

		
		-- 1.3.6.1.4.1.10428 9 1.101.20.5.1.1.1.2
		fkEponProfileName OBJECT-TYPE
			SYNTAX OCTET STRING (SIZE (1..64))
			MAX-ACCESS read-only
			STATUS current
			DESCRIPTION
				"Profile name"
			::= { fkEponProfileEntry 2 }

		
		-- 1.3.6.1.4.1.10428 9 1.101.20.5.1.1.1.3
		fkEponProfileDPDownMaxBandwidth OBJECT-TYPE
			SYNTAX INTEGER (0 | 1..1000000)
			UNITS "kbps"
			MAX-ACCESS read-only
			STATUS current
			DESCRIPTION
				"Download policy Down Max Bandwidth 
				
				"
			::= { fkEponProfileEntry 3 }

		
		-- 1.3.6.1.4.1.10428 9 1.101.20.5.1.1.1.4
		fkEponProfileDPDownMaxBurstSize OBJECT-TYPE
			SYNTAX INTEGER (0 | 128..8388479)
			UNITS "byte"
			MAX-ACCESS read-only
			STATUS current
			DESCRIPTION
				"Download policy Down Max Burst Size 
				
				"
			::= { fkEponProfileEntry 4 }

		
		-- 1.3.6.1.4.1.10428 9 1.101.20.5.1.1.1.5
		fkEponProfileDPP2pMaxBandwidth OBJECT-TYPE
			SYNTAX INTEGER (0 | 1..1000000)
			UNITS "kbps"
			MAX-ACCESS read-only
			STATUS current
			DESCRIPTION
				"Download policy P2P Max Bandwidth "
			::= { fkEponProfileEntry 5 }

		
		-- 1.3.6.1.4.1.10428 9 1.101.20.5.1.1.1.6
		fkEponProfileDPP2pMaxBurstSize OBJECT-TYPE
			SYNTAX INTEGER (0 | 128..8388479)
			UNITS "byte"
			MAX-ACCESS read-only
			STATUS current
			DESCRIPTION
				"Download policy P2P Max Burst Size "
			::= { fkEponProfileEntry 6 }

		
		-- 1.3.6.1.4.1.10428 9 1.101.20.5.1.1.1.7
		fkEponProfileSlaGuaranteedBandwidth OBJECT-TYPE
			SYNTAX INTEGER (43..65535)
			UNITS "TQ"
			MAX-ACCESS read-only
			STATUS current
			DESCRIPTION
				"SLA-internal Guranteed Bandwidth"
			DEFVAL { 85 }
			::= { fkEponProfileEntry 7 }

		
		-- 1.3.6.1.4.1.10428 9 1.101.20.5.1.1.1.8
		fkEponProfileSlaBestEffortBandwidth OBJECT-TYPE
			SYNTAX INTEGER (43..65535)
			UNITS "TQ"
			MAX-ACCESS read-only
			STATUS current
			DESCRIPTION
				"SLA-internal Best effort Bandwidth"
			DEFVAL { 85 }
			::= { fkEponProfileEntry 8 }

		
		-- 1.3.6.1.4.1.10428 9 1.101.20.5.1.1.1.9
		fkEponProfileSlaPlatoClass OBJECT-TYPE
			SYNTAX INTEGER (0..7)
			MAX-ACCESS read-only
			STATUS current
			DESCRIPTION
				"SLA-Plato Class"
			DEFVAL { 1 }
			::= { fkEponProfileEntry 9 }

		
		-- 1.3.6.1.4.1.10428 9 1.101.20.5.1.1.1.10
		fkEponProfileSlaPlatoMinBandwidth1m OBJECT-TYPE
			SYNTAX INTEGER (1..1000)
			UNITS "Mbps"
			MAX-ACCESS read-only
			STATUS current
			DESCRIPTION
				"SLA-Plato Minimum Bandwidth_1m"
			DEFVAL { '1'b }
			::= { fkEponProfileEntry 10 }

		
		-- 1.3.6.1.4.1.10428 9 1.101.20.5.1.1.1.11
		fkEponProfileSlaPlatoMinBandwdith64k OBJECT-TYPE
			SYNTAX INTEGER (0..1024)
			UNITS "64Kbps"
			MAX-ACCESS read-only
			STATUS current
			DESCRIPTION
				"SLA-plato Minimum Bandwidth_64k"
			DEFVAL { '0'b }
			::= { fkEponProfileEntry 11 }

		
		-- 1.3.6.1.4.1.10428 9 1.101.20.5.1.1.1.12
		fkEponProfileSlaPlatoMaxBandwidth1m OBJECT-TYPE
			SYNTAX INTEGER (1..1000)
			UNITS "Mbps"
			MAX-ACCESS read-only
			STATUS current
			DESCRIPTION
				"SLA-plato Max bandwidth_1m"
			DEFVAL { 2 }
			::= { fkEponProfileEntry 12 }

		
		-- 1.3.6.1.4.1.10428 9 1.101.20.5.1.1.1.13
		fkEponProfileSlaPlatoMaxBandwidth64k OBJECT-TYPE
			SYNTAX INTEGER (0..1024)
			UNITS "64Kbps"
			MAX-ACCESS read-only
			STATUS current
			DESCRIPTION
				"SLA-plato Max bandwidth_64k"
			DEFVAL { 0 }
			::= { fkEponProfileEntry 13 }

		
		-- 1.3.6.1.4.1.10428 9 1.101.20.5.1.1.1.14
		fkEponProfileSlaPlatoDelayLevel OBJECT-TYPE
			SYNTAX INTEGER (1..2)
			MAX-ACCESS read-only
			STATUS current
			DESCRIPTION
				"SLA-plato Delay  level"
			DEFVAL { 1 }
			::= { fkEponProfileEntry 14 }

		
		-- 1.3.6.1.4.1.10428 9 1.101.20.5.1.1.1.15
		fkEponProfileExtendMtu OBJECT-TYPE
			SYNTAX EnableFlag
			MAX-ACCESS read-only
			STATUS current
			DESCRIPTION
				"Description."
			::= { fkEponProfileEntry 15 }

		
		-- 1.3.6.1.4.1.10428 9 1.101.20.5.1.1.1.16
		fkEponProfileIgmpFilter OBJECT-TYPE
			SYNTAX EnableFlag
			MAX-ACCESS read-only
			STATUS current
			DESCRIPTION
				"Description."
			::= { fkEponProfileEntry 16 }

		
		-- 1.3.6.1.4.1.10428 9 1.101.20.5.1.1.1.17
		fkEponProfileIgmpSnooping OBJECT-TYPE
			SYNTAX EnableFlag
			MAX-ACCESS read-only
			STATUS current
			DESCRIPTION
				"Description."
			::= { fkEponProfileEntry 17 }

		
		-- 1.3.6.1.4.1.10428 9 1.101.20.5.1.1.1.18
		fkEponProfileSTPenable OBJECT-TYPE
			SYNTAX EnableFlag
			MAX-ACCESS read-only
			STATUS current
			DESCRIPTION
				"Description."
			::= { fkEponProfileEntry 18 }

		
		-- 1.3.6.1.4.1.10428 9 1.101.20.5.1.1.1.19
		fkEponProfileSubscriberInfoCollection OBJECT-TYPE
			SYNTAX EnableFlag
			MAX-ACCESS read-only
			STATUS current
			DESCRIPTION
				"Description."
			::= { fkEponProfileEntry 19 }

		
		-- 1.3.6.1.4.1.10428 9 1.101.20.5.1.1.1.20
		fkEponProfileLoopDetectStatus OBJECT-TYPE
			SYNTAX EnableFlag
			MAX-ACCESS read-only
			STATUS current
			DESCRIPTION
				"Description."
			::= { fkEponProfileEntry 20 }

		
		-- 1.3.6.1.4.1.10428 9 1.101.20.5.1.1.1.21
		fkEponProfileLoopDetectBlockTimer OBJECT-TYPE
			SYNTAX INTEGER (0 | 10..86400)
			MAX-ACCESS read-only
			STATUS current
			DESCRIPTION
				"Description."
			::= { fkEponProfileEntry 21 }

		
		-- 1.3.6.1.4.1.10428 9 1.101.20.5.1.1.1.22
		fkEponProfileLoopDetectSendingpacket OBJECT-TYPE
			SYNTAX INTEGER (0 | 1..60)
			MAX-ACCESS read-only
			STATUS current
			DESCRIPTION
				"Description."
			::= { fkEponProfileEntry 22 }

		
		-- 1.3.6.1.4.1.10428 9 1.101.20.5.1.1.1.23
		fkEponProfileSipMgPort OBJECT-TYPE
			SYNTAX INTEGER
			MAX-ACCESS read-only
			STATUS current
			DESCRIPTION
				"Description."
			::= { fkEponProfileEntry 23 }

		
		-- 1.3.6.1.4.1.10428 9 1.101.20.5.1.1.1.24
		fkEponProfileSipProxyServer OBJECT-TYPE
			SYNTAX OCTET STRING (SIZE (0..64))
			MAX-ACCESS read-only
			STATUS current
			DESCRIPTION
				"Description."
			::= { fkEponProfileEntry 24 }

		
		-- 1.3.6.1.4.1.10428 9 1.101.20.5.1.1.1.25
		fkEponProfileSipProxyServerPort OBJECT-TYPE
			SYNTAX INTEGER
			MAX-ACCESS read-only
			STATUS current
			DESCRIPTION
				"Description."
			::= { fkEponProfileEntry 25 }

		
		-- 1.3.6.1.4.1.10428 9 1.101.20.5.1.1.1.26
		fkEponProfileSipBackupProxyServer OBJECT-TYPE
			SYNTAX OCTET STRING (SIZE (0..64))
			MAX-ACCESS read-only
			STATUS current
			DESCRIPTION
				"Description."
			::= { fkEponProfileEntry 26 }

		
		-- 1.3.6.1.4.1.10428 9 1.101.20.5.1.1.1.27
		fkEponProfileSipBackupProxyServerPort OBJECT-TYPE
			SYNTAX INTEGER
			MAX-ACCESS read-only
			STATUS current
			DESCRIPTION
				"Description."
			::= { fkEponProfileEntry 27 }

		
		-- 1.3.6.1.4.1.10428 9 1.101.20.5.1.1.1.28
		fkEponProfileSipActiveServer OBJECT-TYPE
			SYNTAX OCTET STRING (SIZE (0..64))
			MAX-ACCESS read-only
			STATUS current
			DESCRIPTION
				"Description."
			::= { fkEponProfileEntry 28 }

		
		-- 1.3.6.1.4.1.10428 9 1.101.20.5.1.1.1.29
		fkEponProfileSipRegisterServer OBJECT-TYPE
			SYNTAX OCTET STRING (SIZE (0..64))
			MAX-ACCESS read-only
			STATUS current
			DESCRIPTION
				"Description."
			::= { fkEponProfileEntry 29 }

		
		-- 1.3.6.1.4.1.10428 9 1.101.20.5.1.1.1.30
		fkEponProfileSipRegisterServerPort OBJECT-TYPE
			SYNTAX INTEGER
			MAX-ACCESS read-only
			STATUS current
			DESCRIPTION
				"Description."
			::= { fkEponProfileEntry 30 }

		
		-- 1.3.6.1.4.1.10428 9 1.101.20.5.1.1.1.31
		fkEponProfileSipBackupRegisterServer OBJECT-TYPE
			SYNTAX OCTET STRING (SIZE (0..64))
			MAX-ACCESS read-only
			STATUS current
			DESCRIPTION
				"Description."
			::= { fkEponProfileEntry 31 }

		
		-- 1.3.6.1.4.1.10428 9 1.101.20.5.1.1.1.32
		fkEponProfileSipBackupRegisterServerPort OBJECT-TYPE
			SYNTAX INTEGER
			MAX-ACCESS read-only
			STATUS current
			DESCRIPTION
				"Description."
			::= { fkEponProfileEntry 32 }

		
		-- 1.3.6.1.4.1.10428 9 1.101.20.5.1.1.1.33
		fkEponProfileSipOutBindServer OBJECT-TYPE
			SYNTAX OCTET STRING (SIZE (0..64))
			MAX-ACCESS read-only
			STATUS current
			DESCRIPTION
				"Description."
			::= { fkEponProfileEntry 33 }

		
		-- 1.3.6.1.4.1.10428 9 1.101.20.5.1.1.1.34
		fkEponProfileSipOutBindServerPort OBJECT-TYPE
			SYNTAX INTEGER
			MAX-ACCESS read-only
			STATUS current
			DESCRIPTION
				"Description."
			::= { fkEponProfileEntry 34 }

		
		-- 1.3.6.1.4.1.10428 9 1.101.20.5.1.1.1.35
		fkEponProfileSipRegisterInterval OBJECT-TYPE
			SYNTAX INTEGER
			MAX-ACCESS read-only
			STATUS current
			DESCRIPTION
				"Description."
			::= { fkEponProfileEntry 35 }

		
		-- 1.3.6.1.4.1.10428 9 1.101.20.5.1.1.1.36
		fkEponProfileSipHeartBeatSwitch OBJECT-TYPE
			SYNTAX EnableFlag
			MAX-ACCESS read-only
			STATUS current
			DESCRIPTION
				"Description."
			::= { fkEponProfileEntry 36 }

		
		-- 1.3.6.1.4.1.10428 9 1.101.20.5.1.1.1.37
		fkEponProfileSipHeartBeatCycle OBJECT-TYPE
			SYNTAX INTEGER
			MAX-ACCESS read-only
			STATUS current
			DESCRIPTION
				"Description."
			::= { fkEponProfileEntry 37 }

		
		-- 1.3.6.1.4.1.10428 9 1.101.20.5.1.1.1.38
		fkEponProfileSipHeartBeatCount OBJECT-TYPE
			SYNTAX INTEGER
			MAX-ACCESS read-only
			STATUS current
			DESCRIPTION
				"Description."
			::= { fkEponProfileEntry 38 }

		
		-- 1.3.6.1.4.1.10428 9 1.101.20.5.1.1.1.39
		fkEponProfileSipDNS1Server OBJECT-TYPE
			SYNTAX OCTET STRING (SIZE (0..64))
			MAX-ACCESS read-only
			STATUS current
			DESCRIPTION
				"Description."
			::= { fkEponProfileEntry 39 }

		
		-- 1.3.6.1.4.1.10428 9 1.101.20.5.1.1.1.40
		fkEponProfileSipDNS2Server OBJECT-TYPE
			SYNTAX OCTET STRING (SIZE (0..64))
			MAX-ACCESS read-only
			STATUS current
			DESCRIPTION
				"Description."
			::= { fkEponProfileEntry 40 }

		
		-- 1.3.6.1.4.1.10428 9 1.101.20.5.1.1.1.41
		fkEponProfileVoiceT38enable OBJECT-TYPE
			SYNTAX EnableFlag
			MAX-ACCESS read-only
			STATUS current
			DESCRIPTION
				"Description."
			::= { fkEponProfileEntry 41 }

		
		-- 1.3.6.1.4.1.10428 9 1.101.20.5.1.1.1.42
		fkEponProfileModemControl OBJECT-TYPE
			SYNTAX EnableFlag
			MAX-ACCESS read-only
			STATUS current
			DESCRIPTION
				"Description."
			::= { fkEponProfileEntry 42 }

		
		-- 1.3.6.1.4.1.10428 9 1.101.20.5.1.1.1.43
		fkEponProfileDHCPEnable OBJECT-TYPE
			SYNTAX Integer32
			MAX-ACCESS read-only
			STATUS current
			DESCRIPTION
				"dhcp enable"
			::= { fkEponProfileEntry 43 }

		
		-- 1.3.6.1.4.1.10428 9 1.101.20.5.1.1.1.44
		fkEponProfileMacLearnStatus OBJECT-TYPE
			SYNTAX OCTET STRING
			MAX-ACCESS read-only
			STATUS current
			DESCRIPTION
				"mac learn status : enable or disable"
			::= { fkEponProfileEntry 44 }

		
		-- 1.3.6.1.4.1.10428 9 1.101.20.5.1.2
		fkEponProfileControl OBJECT IDENTIFIER ::= { fkEponProfileBase 2 }

		
		-- 1.3.6.1.4.1.10428 9 1.101.20.5.1.2.1
		fkEponProfileControlRequest OBJECT-TYPE
			SYNTAX INTEGER
				{
				createProfile(1),
				modifyProfile(2),
				destroyProfile(3),
				modifyProfileMtu(4),
				modifyProfileIgmp(5),
				modifyProfileSTP(6),
				createDefaultProfile(7),
				modifyProfileSubscriber(8),
				modifyProfileLoopDetect(9),
				modifyProfileSipConfig(10),
				modifyProfileModemConfig(11),
				modifyProfileDHCP(12),
				modifyProfileMacLearn(13)
				}
			MAX-ACCESS read-write
			STATUS current
			DESCRIPTION
				"The request of a user command"
			::= { fkEponProfileControl 1 }

		
		-- 1.3.6.1.4.1.10428 9 1.101.20.5.1.2.2
		fkEponProfileControlStatus OBJECT-TYPE
			SYNTAX FkControlStatusType
			MAX-ACCESS read-only
			STATUS current
			DESCRIPTION
				"The status of user command"
			::= { fkEponProfileControl 2 }

		
		-- 1.3.6.1.4.1.10428 9 1.101.20.5.1.2.3
		fkEponProfileControlTimer OBJECT-TYPE
			SYNTAX Gauge32
			MAX-ACCESS read-write
			STATUS current
			DESCRIPTION
				"The maximum time for the manager for a long running user command"
			::= { fkEponProfileControl 3 }

		
		-- 1.3.6.1.4.1.10428 9 1.101.20.5.1.2.4
		fkEponProfileControlTimeStamp OBJECT-TYPE
			SYNTAX TimeTicks
			MAX-ACCESS read-only
			STATUS current
			DESCRIPTION
				"The time stamp of the last command(end of command)"
			::= { fkEponProfileControl 4 }

		
		-- 1.3.6.1.4.1.10428 9 1.101.20.5.1.2.5
		fkEponProfileControlReqResult OBJECT-TYPE
			SYNTAX FkControlRequestResultType
			MAX-ACCESS read-only
			STATUS current
			DESCRIPTION
				"The result of the last user command"
			::= { fkEponProfileControl 5 }

		
		-- 1.3.6.1.4.1.10428 9 1.101.20.5.1.2.6
		fkEponProfileControlIndex OBJECT-TYPE
			SYNTAX INTEGER (1..32)
			MAX-ACCESS read-write
			STATUS current
			DESCRIPTION
				"Profile index"
			::= { fkEponProfileControl 6 }

		
		-- 1.3.6.1.4.1.10428 9 1.101.20.5.1.2.7
		fkEponProfileControlName OBJECT-TYPE
			SYNTAX OCTET STRING (SIZE (1..64))
			MAX-ACCESS read-write
			STATUS current
			DESCRIPTION
				"Profile name"
			::= { fkEponProfileControl 7 }

		
		-- 1.3.6.1.4.1.10428 9 1.101.20.5.1.2.8
		fkEponProfileControlDPDownMaxBandwidth OBJECT-TYPE
			SYNTAX INTEGER (0 | 1..1000000)
			UNITS "kbps"
			MAX-ACCESS read-write
			STATUS current
			DESCRIPTION
				"Download policy Down Max Bandwidth "
			::= { fkEponProfileControl 8 }

		
		-- 1.3.6.1.4.1.10428 9 1.101.20.5.1.2.9
		fkEponProfileControlDPDownMaxBurstSize OBJECT-TYPE
			SYNTAX INTEGER (0 | 128..8388479)
			UNITS "byte"
			MAX-ACCESS read-write
			STATUS current
			DESCRIPTION
				"Download policy Down Max Burst Size"
			::= { fkEponProfileControl 9 }

		
		-- 1.3.6.1.4.1.10428 9 1.101.20.5.1.2.10
		fkEponProfileControlDPP2pMaxBandwidth OBJECT-TYPE
			SYNTAX INTEGER (0 | 1..1000000)
			UNITS "kbps"
			MAX-ACCESS read-write
			STATUS current
			DESCRIPTION
				"Download policy P2P Max Bandwidth"
			::= { fkEponProfileControl 10 }

		
		-- 1.3.6.1.4.1.10428 9 1.101.20.5.1.2.11
		fkEponProfileControlDPP2pMaxBurstSize OBJECT-TYPE
			SYNTAX INTEGER (0 | 128..8388479)
			UNITS "byte"
			MAX-ACCESS read-write
			STATUS current
			DESCRIPTION
				"Download policy P2P Max Burst Size "
			::= { fkEponProfileControl 11 }

		
		-- 1.3.6.1.4.1.10428 9 1.101.20.5.1.2.12
		fkEponProfileControlSlaGuaranteedBandwidth OBJECT-TYPE
			SYNTAX INTEGER (43..65535)
			UNITS "TQ"
			MAX-ACCESS read-write
			STATUS current
			DESCRIPTION
				"SLA-internal Guranteed Bandwidth"
			DEFVAL { 85 }
			::= { fkEponProfileControl 12 }

		
		-- 1.3.6.1.4.1.10428 9 1.101.20.5.1.2.13
		fkEponProfileControlSlaBestEffortBandwidth OBJECT-TYPE
			SYNTAX INTEGER (43..65535)
			UNITS "TQ"
			MAX-ACCESS read-write
			STATUS current
			DESCRIPTION
				"SLA-internal Best effort Bandwidth"
			DEFVAL { 85 }
			::= { fkEponProfileControl 13 }

		
		-- 1.3.6.1.4.1.10428 9 1.101.20.5.1.2.14
		fkEponProfileControlSlaPlatoClass OBJECT-TYPE
			SYNTAX INTEGER (0..7)
			MAX-ACCESS read-write
			STATUS current
			DESCRIPTION
				"SLA-Plato Class"
			::= { fkEponProfileControl 14 }

		
		-- 1.3.6.1.4.1.10428 9 1.101.20.5.1.2.15
		fkEponProfileControlSlaPlatoGuaranteedBandwidth1m OBJECT-TYPE
			SYNTAX INTEGER (1..1000)
			UNITS "Mbps"
			MAX-ACCESS read-write
			STATUS current
			DESCRIPTION
				"SLA-Plato Minimum Bandwidth_1m"
			DEFVAL { 1 }
			::= { fkEponProfileControl 15 }

		
		-- 1.3.6.1.4.1.10428 9 1.101.20.5.1.2.16
		fkEponProfileControlSlaPlatoGuaranteedBandwdith64k OBJECT-TYPE
			SYNTAX INTEGER (0..1024)
			UNITS "64Kbps"
			MAX-ACCESS read-write
			STATUS current
			DESCRIPTION
				"SLA-plato Minimum Bandwidth_64k"
			DEFVAL { 0 }
			::= { fkEponProfileControl 16 }

		
		-- 1.3.6.1.4.1.10428 9 1.101.20.5.1.2.17
		fkEponProfileControlSlaPlatoBestEffortBandwidth1m OBJECT-TYPE
			SYNTAX INTEGER (1..1000)
			UNITS "Mbps"
			MAX-ACCESS read-write
			STATUS current
			DESCRIPTION
				"SLA-plato Max bandwidth_1m"
			DEFVAL { 2 }
			::= { fkEponProfileControl 17 }

		
		-- 1.3.6.1.4.1.10428 9 1.101.20.5.1.2.18
		fkEponProfileControlSlaPlatoBestEffortBandwidth64k OBJECT-TYPE
			SYNTAX INTEGER (0..1024)
			UNITS "64Kbps"
			MAX-ACCESS read-write
			STATUS current
			DESCRIPTION
				"SLA-plato Max bandwidth_64k"
			DEFVAL { 0 }
			::= { fkEponProfileControl 18 }

		
		-- 1.3.6.1.4.1.10428 9 1.101.20.5.1.2.19
		fkEponProfileControlSlaPlatoDelayLevel OBJECT-TYPE
			SYNTAX INTEGER (1..2)
			MAX-ACCESS read-write
			STATUS current
			DESCRIPTION
				"SLA-plato Delay  level"
			DEFVAL { 1 }
			::= { fkEponProfileControl 19 }

		
		-- 1.3.6.1.4.1.10428 9 1.101.20.5.1.2.20
		fkEponProfileControlExtendMtu OBJECT-TYPE
			SYNTAX EnableFlag
			MAX-ACCESS read-write
			STATUS current
			DESCRIPTION
				"Description."
			::= { fkEponProfileControl 20 }

		
		-- 1.3.6.1.4.1.10428 9 1.101.20.5.1.2.21
		fkEponProfileControlIgmpFilter OBJECT-TYPE
			SYNTAX EnableFlag
			MAX-ACCESS read-write
			STATUS current
			DESCRIPTION
				"Description."
			::= { fkEponProfileControl 21 }

		
		-- 1.3.6.1.4.1.10428 9 1.101.20.5.1.2.22
		fkEponProfileControlSnooping OBJECT-TYPE
			SYNTAX EnableFlag
			MAX-ACCESS read-write
			STATUS current
			DESCRIPTION
				"Description."
			::= { fkEponProfileControl 22 }

		
		-- 1.3.6.1.4.1.10428 9 1.101.20.5.1.2.23
		fkEponProfileControlSTPenable OBJECT-TYPE
			SYNTAX EnableFlag
			MAX-ACCESS read-write
			STATUS current
			DESCRIPTION
				"Description."
			::= { fkEponProfileControl 23 }

		
		-- 1.3.6.1.4.1.10428 9 1.101.20.5.1.2.24
		fkEponProfileControlSubscriberInfoCollection OBJECT-TYPE
			SYNTAX EnableFlag
			MAX-ACCESS read-write
			STATUS current
			DESCRIPTION
				"Description."
			::= { fkEponProfileControl 24 }

		
		-- 1.3.6.1.4.1.10428 9 1.101.20.5.1.2.25
		fkEponProfileControlLoopDetectStatus OBJECT-TYPE
			SYNTAX EnableFlag
			MAX-ACCESS read-write
			STATUS current
			DESCRIPTION
				"Description."
			::= { fkEponProfileControl 25 }

		
		-- 1.3.6.1.4.1.10428 9 1.101.20.5.1.2.26
		fkEponProfileControlLoopDetectBlockTimer OBJECT-TYPE
			SYNTAX INTEGER (0 | 10..86400)
			MAX-ACCESS read-write
			STATUS current
			DESCRIPTION
				"Description."
			::= { fkEponProfileControl 26 }

		
		-- 1.3.6.1.4.1.10428 9 1.101.20.5.1.2.27
		fkEponProfileControlLoopDetectSendingpacket OBJECT-TYPE
			SYNTAX INTEGER (0 | 1..60)
			MAX-ACCESS read-write
			STATUS current
			DESCRIPTION
				"Description."
			::= { fkEponProfileControl 27 }

		
		-- 1.3.6.1.4.1.10428 9 1.101.20.5.1.2.28
		fkEponProfileControlSipMgPort OBJECT-TYPE
			SYNTAX INTEGER
			MAX-ACCESS read-write
			STATUS current
			DESCRIPTION
				"Description."
			::= { fkEponProfileControl 28 }

		
		-- 1.3.6.1.4.1.10428 9 1.101.20.5.1.2.29
		fkEponProfileControlSipProxyServer OBJECT-TYPE
			SYNTAX OCTET STRING (SIZE (0..64))
			MAX-ACCESS read-write
			STATUS current
			DESCRIPTION
				"Description."
			::= { fkEponProfileControl 29 }

		
		-- 1.3.6.1.4.1.10428 9 1.101.20.5.1.2.30
		fkEponProfileControlSipProxyServerPort OBJECT-TYPE
			SYNTAX INTEGER
			MAX-ACCESS read-write
			STATUS current
			DESCRIPTION
				"Description."
			::= { fkEponProfileControl 30 }

		
		-- 1.3.6.1.4.1.10428 9 1.101.20.5.1.2.31
		fkEponProfileControlSipBackupProxyServer OBJECT-TYPE
			SYNTAX OCTET STRING (SIZE (0..64))
			MAX-ACCESS read-write
			STATUS current
			DESCRIPTION
				"Description."
			::= { fkEponProfileControl 31 }

		
		-- 1.3.6.1.4.1.10428 9 1.101.20.5.1.2.32
		fkEponProfileControlSipBackupProxyServerPort OBJECT-TYPE
			SYNTAX INTEGER
			MAX-ACCESS read-write
			STATUS current
			DESCRIPTION
				"Description."
			::= { fkEponProfileControl 32 }

		
		-- 1.3.6.1.4.1.10428 9 1.101.20.5.1.2.33
		fkEponProfileControlSipActiveServer OBJECT-TYPE
			SYNTAX OCTET STRING (SIZE (0..64))
			MAX-ACCESS read-write
			STATUS current
			DESCRIPTION
				"Description."
			::= { fkEponProfileControl 33 }

		
		-- 1.3.6.1.4.1.10428 9 1.101.20.5.1.2.34
		fkEponProfileControlSipRegisterServer OBJECT-TYPE
			SYNTAX OCTET STRING (SIZE (0..64))
			MAX-ACCESS read-write
			STATUS current
			DESCRIPTION
				"Description."
			::= { fkEponProfileControl 34 }

		
		-- 1.3.6.1.4.1.10428 9 1.101.20.5.1.2.35
		fkEponProfileControlSipRegisterServerPort OBJECT-TYPE
			SYNTAX INTEGER
			MAX-ACCESS read-write
			STATUS current
			DESCRIPTION
				"Description."
			::= { fkEponProfileControl 35 }

		
		-- 1.3.6.1.4.1.10428 9 1.101.20.5.1.2.36
		fkEponProfileControlSipBackupRegisterServer OBJECT-TYPE
			SYNTAX OCTET STRING (SIZE (0..64))
			MAX-ACCESS read-write
			STATUS current
			DESCRIPTION
				"Description."
			::= { fkEponProfileControl 36 }

		
		-- 1.3.6.1.4.1.10428 9 1.101.20.5.1.2.37
		fkEponProfileControlSipBackupRegisterServerPort OBJECT-TYPE
			SYNTAX INTEGER
			MAX-ACCESS read-write
			STATUS current
			DESCRIPTION
				"Description."
			::= { fkEponProfileControl 37 }

		
		-- 1.3.6.1.4.1.10428 9 1.101.20.5.1.2.38
		fkEponProfileControlSipOutBindServer OBJECT-TYPE
			SYNTAX OCTET STRING (SIZE (0..64))
			MAX-ACCESS read-write
			STATUS current
			DESCRIPTION
				"Description."
			::= { fkEponProfileControl 38 }

		
		-- 1.3.6.1.4.1.10428 9 1.101.20.5.1.2.39
		fkEponProfileControlSipOutBindServerPort OBJECT-TYPE
			SYNTAX INTEGER
			MAX-ACCESS read-write
			STATUS current
			DESCRIPTION
				"Description."
			::= { fkEponProfileControl 39 }

		
		-- 1.3.6.1.4.1.10428 9 1.101.20.5.1.2.40
		fkEponProfileControlSipRegisterInterval OBJECT-TYPE
			SYNTAX INTEGER
			MAX-ACCESS read-write
			STATUS current
			DESCRIPTION
				"Description."
			::= { fkEponProfileControl 40 }

		
		-- 1.3.6.1.4.1.10428 9 1.101.20.5.1.2.41
		fkEponProfileControlSipHeartBeatSwitch OBJECT-TYPE
			SYNTAX EnableFlag
			MAX-ACCESS read-write
			STATUS current
			DESCRIPTION
				"Description."
			::= { fkEponProfileControl 41 }

		
		-- 1.3.6.1.4.1.10428 9 1.101.20.5.1.2.42
		fkEponProfileControlSipHeartBeatCycle OBJECT-TYPE
			SYNTAX INTEGER
			MAX-ACCESS read-write
			STATUS current
			DESCRIPTION
				"Description."
			::= { fkEponProfileControl 42 }

		
		-- 1.3.6.1.4.1.10428 9 1.101.20.5.1.2.43
		fkEponProfileControlSipHeartBeatCount OBJECT-TYPE
			SYNTAX INTEGER
			MAX-ACCESS read-write
			STATUS current
			DESCRIPTION
				"Description."
			::= { fkEponProfileControl 43 }

		
		-- 1.3.6.1.4.1.10428 9 1.101.20.5.1.2.44
		fkEponProfileControlSipDNS1Server OBJECT-TYPE
			SYNTAX OCTET STRING (SIZE (0..64))
			MAX-ACCESS read-write
			STATUS current
			DESCRIPTION
				"Description."
			::= { fkEponProfileControl 44 }

		
		-- 1.3.6.1.4.1.10428 9 1.101.20.5.1.2.45
		fkEponProfileControlSipDNS2Server OBJECT-TYPE
			SYNTAX OCTET STRING (SIZE (0..64))
			MAX-ACCESS read-write
			STATUS current
			DESCRIPTION
				"Description."
			::= { fkEponProfileControl 45 }

		
		-- 1.3.6.1.4.1.10428 9 1.101.20.5.1.2.46
		fkEponProfileControlVoiceT38enable OBJECT-TYPE
			SYNTAX EnableFlag
			MAX-ACCESS read-write
			STATUS current
			DESCRIPTION
				"Description."
			::= { fkEponProfileControl 46 }

		
		-- 1.3.6.1.4.1.10428 9 1.101.20.5.1.2.47
		fkEponProfileControlModemControl OBJECT-TYPE
			SYNTAX EnableFlag
			MAX-ACCESS read-write
			STATUS current
			DESCRIPTION
				"Description."
			::= { fkEponProfileControl 47 }

		
		-- 1.3.6.1.4.1.10428 9 1.101.20.5.1.2.48
		fkEponProfileControlDHCPEnable OBJECT-TYPE
			SYNTAX Integer32
			MAX-ACCESS read-write
			STATUS current
			DESCRIPTION
				"dhcp enable"
			::= { fkEponProfileControl 48 }

		
		-- 1.3.6.1.4.1.10428 9 1.101.20.5.1.2.49
		fkEponProfileControlMacLearnStatus OBJECT-TYPE
			SYNTAX EnableFlag
			MAX-ACCESS read-write
			STATUS current
			DESCRIPTION
				"mac learn : enbale 1 , diable 2"
			DEFVAL { enable }
			::= { fkEponProfileControl 49 }

		
		-- 1.3.6.1.4.1.10428 9 1.101.20.5.1.3
		fkEponProfileNotification OBJECT IDENTIFIER ::= { fkEponProfileBase 3 }

		
		-- 1.3.6.1.4.1.10428 9 1.101.20.5.1.3.1
		fkEponProfileCreated NOTIFICATION-TYPE
			OBJECTS { fkEponProfileControlRequest, fkEponProfileControlTimeStamp, fkEponProfileControlReqResult, fkEponProfileControlIndex, fkEponProfileControlName
				 }
			STATUS current
			DESCRIPTION 
				"Description."
			::= { fkEponProfileNotification 1 }

		
		-- 1.3.6.1.4.1.10428 9 1.101.20.5.1.3.2
		fkEponProfileModified NOTIFICATION-TYPE
			OBJECTS { fkEponProfileControlRequest, fkEponProfileControlTimeStamp, fkEponProfileControlReqResult, fkEponProfileControlIndex, fkEponProfileControlName
				 }
			STATUS current
			DESCRIPTION 
				"Description."
			::= { fkEponProfileNotification 2 }

		
		-- 1.3.6.1.4.1.10428 9 1.101.20.5.1.3.3
		fkEponProfileDestroyed NOTIFICATION-TYPE
			OBJECTS { fkEponProfileControlRequest, fkEponProfileControlTimeStamp, fkEponProfileControlReqResult, fkEponProfileControlIndex, fkEponProfileControlName
				 }
			STATUS current
			DESCRIPTION 
				"Description."
			::= { fkEponProfileNotification 3 }

		
		-- 1.3.6.1.4.1.10428 9 1.101.20.5.1.3.4
		fkEponProfileExtendMtuChanged NOTIFICATION-TYPE
			OBJECTS { fkEponProfileControlRequest, fkEponProfileControlTimeStamp, fkEponProfileControlReqResult, fkEponProfileControlIndex, fkEponProfileControlName, 
				fkEponProfileControlExtendMtu }
			STATUS current
			DESCRIPTION 
				"Description."
			::= { fkEponProfileNotification 4 }

		
		-- 1.3.6.1.4.1.10428 9 1.101.20.5.1.3.5
		fkEponProfileIgmpChanged NOTIFICATION-TYPE
			OBJECTS { fkEponProfileControlRequest, fkEponProfileControlTimeStamp, fkEponProfileControlReqResult, fkEponProfileControlIndex, fkEponProfileControlName, 
				fkEponProfileControlIgmpFilter, fkEponProfileControlSnooping }
			STATUS current
			DESCRIPTION 
				"Description."
			::= { fkEponProfileNotification 5 }

		
		-- 1.3.6.1.4.1.10428 9 1.101.20.5.1.3.6
		fkEponProfileSTPChanged NOTIFICATION-TYPE
			OBJECTS { fkEponProfileControlRequest, fkEponProfileControlTimeStamp, fkEponProfileControlReqResult, fkEponProfileControlIndex, fkEponProfileControlName, 
				fkEponProfileControlSTPenable }
			STATUS current
			DESCRIPTION 
				"Description."
			::= { fkEponProfileNotification 6 }

		
		-- 1.3.6.1.4.1.10428 9 1.101.20.5.1.3.7
		fkEponProfileDefaultProfileCreated NOTIFICATION-TYPE
			OBJECTS { fkEponProfileQueueControlRequest, fkEponProfileQueueControlTimeStamp, fkEponProfileQueueControlReqResult }
			STATUS current
			DESCRIPTION 
				"Description."
			::= { fkEponProfileNotification 7 }

		
		-- 1.3.6.1.4.1.10428 9 1.101.20.5.1.3.8
		fkEponProfileSubscriberChanged NOTIFICATION-TYPE
			OBJECTS { fkEponProfileControlRequest, fkEponProfileControlTimeStamp, fkEponProfileControlReqResult, fkEponProfileControlIndex, fkEponProfileControlName, 
				fkEponProfileControlSubscriberInfoCollection }
			STATUS current
			DESCRIPTION 
				"Description."
			::= { fkEponProfileNotification 8 }

		
		-- 1.3.6.1.4.1.10428 9 1.101.20.5.1.3.9
		fkEponProfileLoopDetectChanged NOTIFICATION-TYPE
			OBJECTS { fkEponProfileControlRequest, fkEponProfileControlTimeStamp, fkEponProfileControlReqResult, fkEponProfileControlIndex, fkEponProfileControlName, 
				fkEponProfileControlLoopDetectStatus, fkEponProfileControlLoopDetectBlockTimer, fkEponProfileControlLoopDetectSendingpacket }
			STATUS current
			DESCRIPTION 
				"Description."
			::= { fkEponProfileNotification 9 }

		
		-- 1.3.6.1.4.1.10428 9 1.101.20.5.1.3.10
		fkEponProfileSipConfigChanged NOTIFICATION-TYPE
			OBJECTS { fkEponProfileControlRequest, fkEponProfileControlTimeStamp, fkEponProfileControlReqResult, fkEponProfileControlIndex, fkEponProfileControlName, 
				fkEponProfileControlSipMgPort, fkEponProfileControlSipProxyServer, fkEponProfileControlSipProxyServerPort, fkEponProfileControlSipBackupProxyServer, fkEponProfileControlSipBackupProxyServerPort, 
				fkEponProfileControlSipActiveServer, fkEponProfileControlSipRegisterServer, fkEponProfileControlSipRegisterServerPort, fkEponProfileControlSipBackupRegisterServer, fkEponProfileControlSipBackupRegisterServerPort, 
				fkEponProfileControlSipOutBindServer, fkEponProfileControlSipOutBindServerPort, fkEponProfileControlSipRegisterInterval, fkEponProfileControlSipHeartBeatSwitch, fkEponProfileControlSipHeartBeatCycle, 
				fkEponProfileControlSipHeartBeatCount, fkEponProfileControlSipDNS1Server, fkEponProfileControlSipDNS2Server }
			STATUS current
			DESCRIPTION 
				"Description."
			::= { fkEponProfileNotification 10 }

		
		-- 1.3.6.1.4.1.10428 9 1.101.20.5.1.3.11
		fkEponProfileModemConfigChanged NOTIFICATION-TYPE
			OBJECTS { fkEponProfileControlRequest, fkEponProfileControlTimeStamp, fkEponProfileControlReqResult, fkEponProfileControlIndex, fkEponProfileControlName, 
				fkEponProfileControlVoiceT38enable, fkEponProfileControlModemControl }
			STATUS current
			DESCRIPTION 
				"Description."
			::= { fkEponProfileNotification 11 }

		
		-- 1.3.6.1.4.1.10428 9 1.101.20.5.1.3.12
		fkEponProfileDHCPChanged NOTIFICATION-TYPE
			STATUS current
			DESCRIPTION 
				"Description."
			::= { fkEponProfileNotification 12 }

		
		-- 1.3.6.1.4.1.10428 9 1.101.20.5.1.3.13
		fkEponProfileModemMacLearnChanged NOTIFICATION-TYPE
			OBJECTS { fkEponProfileControlRequest, fkEponProfileControlTimeStamp, fkEponProfileControlReqResult, fkEponProfileControlMacLearnStatus }
			STATUS current
			DESCRIPTION 
				"mac learn status changed trap"
			::= { fkEponProfileNotification 13 }

		
		-- 1.3.6.1.4.1.10428 9 1.101.20.5.1.4
		fkEponProfileIgmpSnoopingTable OBJECT-TYPE
			SYNTAX SEQUENCE OF FkEponProfileIgmpSnoopingEntry
			MAX-ACCESS not-accessible
			STATUS current
			DESCRIPTION
				"Description."
			::= { fkEponProfileBase 4 }

		
		-- 1.3.6.1.4.1.10428 9 1.101.20.5.1.4.1
		fkEponProfileIgmpSnoopingEntry OBJECT-TYPE
			SYNTAX FkEponProfileIgmpSnoopingEntry
			MAX-ACCESS not-accessible
			STATUS current
			DESCRIPTION
				"Description."
			INDEX { fkEponProfileIndex, fkEponProfileIgmpSnoopingIndex }
			::= { fkEponProfileIgmpSnoopingTable 1 }

		
		FkEponProfileIgmpSnoopingEntry ::=
			SEQUENCE { 
				fkEponProfileIgmpSnoopingIndex
					Integer32,
				fkEponProfileIgmpSnoopingState
					EnableFlag,
				fkEponProfileIgmpSnoopingMaxch
					Integer32,
				fkEponProfileIgmpSnoopingTagVlan
					Integer32
			 }

		-- 1.3.6.1.4.1.10428 9 1.101.20.5.1.4.1.1
		fkEponProfileIgmpSnoopingIndex OBJECT-TYPE
			SYNTAX Integer32 (1..5)
			MAX-ACCESS read-only
			STATUS current
			DESCRIPTION
				"Igmp snooping count."
			::= { fkEponProfileIgmpSnoopingEntry 1 }

		
		-- 1.3.6.1.4.1.10428 9 1.101.20.5.1.4.1.2
		fkEponProfileIgmpSnoopingState OBJECT-TYPE
			SYNTAX EnableFlag
			MAX-ACCESS read-only
			STATUS current
			DESCRIPTION
				"Description."
			::= { fkEponProfileIgmpSnoopingEntry 2 }

		
		-- 1.3.6.1.4.1.10428 9 1.101.20.5.1.4.1.3
		fkEponProfileIgmpSnoopingMaxch OBJECT-TYPE
			SYNTAX Integer32 (1..255)
			MAX-ACCESS read-only
			STATUS current
			DESCRIPTION
				"Maximum number of channels."
			::= { fkEponProfileIgmpSnoopingEntry 3 }

		
		-- 1.3.6.1.4.1.10428 9 1.101.20.5.1.4.1.4
		fkEponProfileIgmpSnoopingTagVlan OBJECT-TYPE
			SYNTAX Integer32 (1..4096)
			MAX-ACCESS read-write
			STATUS current
			DESCRIPTION
				"Igmp snooping tag vlan id."
			::= { fkEponProfileIgmpSnoopingEntry 4 }

		
		-- 1.3.6.1.4.1.10428 9 1.101.20.5.1.5
		fkEponProfileIgmpSnoopingControl OBJECT IDENTIFIER ::= { fkEponProfileBase 5 }

		
		-- 1.3.6.1.4.1.10428 9 1.101.20.5.1.5.1
		fkEponProfileIgmpSnoopingControlRequest OBJECT-TYPE
			SYNTAX INTEGER { modifyProfileIgmpSnooping(1) }
			MAX-ACCESS read-write
			STATUS current
			DESCRIPTION
				"The request of a user command"
			::= { fkEponProfileIgmpSnoopingControl 1 }

		
		-- 1.3.6.1.4.1.10428 9 1.101.20.5.1.5.2
		fkEponProfileIgmpSnoopingControlStatus OBJECT-TYPE
			SYNTAX FkControlStatusType
			MAX-ACCESS read-only
			STATUS current
			DESCRIPTION
				"The status of user command"
			::= { fkEponProfileIgmpSnoopingControl 2 }

		
		-- 1.3.6.1.4.1.10428 9 1.101.20.5.1.5.3
		fkEponProfileIgmpSnoopingControlTimer OBJECT-TYPE
			SYNTAX Gauge32
			MAX-ACCESS read-write
			STATUS current
			DESCRIPTION
				"The maximum time for the manager for a long running user command"
			::= { fkEponProfileIgmpSnoopingControl 3 }

		
		-- 1.3.6.1.4.1.10428 9 1.101.20.5.1.5.4
		fkEponProfileIgmpSnoopingControlTimeStamp OBJECT-TYPE
			SYNTAX TimeTicks
			MAX-ACCESS read-only
			STATUS current
			DESCRIPTION
				"The time stamp of the last command(end of command)"
			::= { fkEponProfileIgmpSnoopingControl 4 }

		
		-- 1.3.6.1.4.1.10428 9 1.101.20.5.1.5.5
		fkEponProfileIgmpSnoopingControlReqResult OBJECT-TYPE
			SYNTAX FkControlRequestResultType
			MAX-ACCESS read-only
			STATUS current
			DESCRIPTION
				"The result of the last user command"
			::= { fkEponProfileIgmpSnoopingControl 5 }

		
		-- 1.3.6.1.4.1.10428 9 1.101.20.5.1.5.6
		fkEponProfileIgmpSnoopingControlProfileIndex OBJECT-TYPE
			SYNTAX INTEGER (1..32)
			MAX-ACCESS read-write
			STATUS current
			DESCRIPTION
				"Profile index"
			::= { fkEponProfileIgmpSnoopingControl 6 }

		
		-- 1.3.6.1.4.1.10428 9 1.101.20.5.1.5.7
		fkEponProfileIgmpSnoopingControlState OBJECT-TYPE
			SYNTAX EnableFlag
			MAX-ACCESS read-write
			STATUS current
			DESCRIPTION
				"enable(1), disable(2)."
			::= { fkEponProfileIgmpSnoopingControl 7 }

		
		-- 1.3.6.1.4.1.10428 9 1.101.20.5.1.5.8
		fkEponProfileIgmpSnoopingControlMaxch OBJECT-TYPE
			SYNTAX Integer32 (1..255)
			MAX-ACCESS read-write
			STATUS current
			DESCRIPTION
				"Maximum number of channels."
			DEFVAL { 255 }
			::= { fkEponProfileIgmpSnoopingControl 8 }

		
		-- 1.3.6.1.4.1.10428 9 1.101.20.5.1.5.9
		fkEponProfileIgmpSnoopingControlTagVlan OBJECT-TYPE
			SYNTAX Integer32 (1..4096)
			MAX-ACCESS read-write
			STATUS current
			DESCRIPTION
				"Igmp snooping tag vlan id."
			::= { fkEponProfileIgmpSnoopingControl 9 }

		
		-- 1.3.6.1.4.1.10428 9 1.101.20.5.1.6
		fkEponProfileIgmpSnoopingNotification OBJECT IDENTIFIER ::= { fkEponProfileBase 6 }

		
		-- 1.3.6.1.4.1.10428 9 1.101.20.5.1.6.1
		fkEponProfileIgmpSnoopingChanged NOTIFICATION-TYPE
			OBJECTS { fkEponProfileIgmpSnoopingControlRequest, fkEponProfileIgmpSnoopingControlTimeStamp, fkEponProfileIgmpSnoopingControlReqResult, fkEponProfileIgmpSnoopingControlProfileName, fkEponProfileIgmpSnoopingControlState, 
				fkEponProfileIgmpSnoopingControlMaxch, fkEponProfileIgmpSnoopingControlTagVlan }
			STATUS current
			DESCRIPTION 
				"Description."
			::= { fkEponProfileIgmpSnoopingNotification 1 }

		
		-- 1.3.6.1.4.1.10428 9 1.101.20.5.1.7
		fkEponProfileOnuRuleTable OBJECT-TYPE
			SYNTAX SEQUENCE OF FkEponProfileOnuRuleEntry
			MAX-ACCESS not-accessible
			STATUS current
			DESCRIPTION
				"Description."
			::= { fkEponProfileBase 7 }

		
		-- 1.3.6.1.4.1.10428 9 1.101.20.5.1.7.1
		fkEponProfileOnuRuleEntry OBJECT-TYPE
			SYNTAX FkEponProfileOnuRuleEntry
			MAX-ACCESS not-accessible
			STATUS current
			DESCRIPTION
				"Profile Onu rule table."
			INDEX { fkEponProfileIndex, fkEponOnuProfileOnuRuleIndex }
			::= { fkEponProfileOnuRuleTable 1 }

		
		FkEponProfileOnuRuleEntry ::=
			SEQUENCE { 
				fkEponOnuProfileOnuRuleIndex
					INTEGER,
				fkEponProfileOnuRuleName
					OCTET STRING
			 }

		-- 1.3.6.1.4.1.10428 9 1.101.20.5.1.7.1.1
		fkEponOnuProfileOnuRuleIndex OBJECT-TYPE
			SYNTAX INTEGER (0..24)
			MAX-ACCESS read-only
			STATUS current
			DESCRIPTION
				"Onu rule index."
			::= { fkEponProfileOnuRuleEntry 1 }

		
		-- 1.3.6.1.4.1.10428 9 1.101.20.5.1.7.1.2
		fkEponProfileOnuRuleName OBJECT-TYPE
			SYNTAX OCTET STRING
			MAX-ACCESS read-only
			STATUS current
			DESCRIPTION
				"Rule name."
			::= { fkEponProfileOnuRuleEntry 2 }

		
		-- 1.3.6.1.4.1.10428 9 1.101.20.5.1.8
		fkEponProfileOnuRuleControl OBJECT IDENTIFIER ::= { fkEponProfileBase 8 }

		
		-- 1.3.6.1.4.1.10428 9 1.101.20.5.1.8.1
		fkEponProfileOnuRuleControlRequest OBJECT-TYPE
			SYNTAX INTEGER
				{
				applyProfileOnuRule(1),
				noApplyProfileOnuRule(2)
				}
			MAX-ACCESS read-write
			STATUS current
			DESCRIPTION
				"The request of a user command"
			::= { fkEponProfileOnuRuleControl 1 }

		
		-- 1.3.6.1.4.1.10428 9 1.101.20.5.1.8.2
		fkEponProfileOnuRuleControlStatus OBJECT-TYPE
			SYNTAX FkControlStatusType
			MAX-ACCESS read-only
			STATUS current
			DESCRIPTION
				"The status of user command"
			::= { fkEponProfileOnuRuleControl 2 }

		
		-- 1.3.6.1.4.1.10428 9 1.101.20.5.1.8.3
		fkEponProfileOnuRuleControlTimer OBJECT-TYPE
			SYNTAX Gauge32
			MAX-ACCESS read-write
			STATUS current
			DESCRIPTION
				"The maximum time for the manager for a long running user command"
			::= { fkEponProfileOnuRuleControl 3 }

		
		-- 1.3.6.1.4.1.10428 9 1.101.20.5.1.8.4
		fkEponProfileOnuRuleControlTimeStamp OBJECT-TYPE
			SYNTAX TimeTicks
			MAX-ACCESS read-only
			STATUS current
			DESCRIPTION
				"The time stamp of the last command(end of command)"
			::= { fkEponProfileOnuRuleControl 4 }

		
		-- 1.3.6.1.4.1.10428 9 1.101.20.5.1.8.5
		fkEponProfleOnuRuleControlReqResult OBJECT-TYPE
			SYNTAX FkControlRequestResultType
			MAX-ACCESS read-write
			STATUS current
			DESCRIPTION
				"The result of the last user command"
			::= { fkEponProfileOnuRuleControl 5 }

		
		-- 1.3.6.1.4.1.10428 9 1.101.20.5.1.8.6
		fkEponProfileOnuRuleControlProfileIndex OBJECT-TYPE
			SYNTAX INTEGER (1..32)
			MAX-ACCESS read-write
			STATUS current
			DESCRIPTION
				"Profile Index"
			::= { fkEponProfileOnuRuleControl 6 }

		
		-- 1.3.6.1.4.1.10428 9 1.101.20.5.1.8.7
		fkEponProfileOnuRuleControlName OBJECT-TYPE
			SYNTAX OCTET STRING
			MAX-ACCESS read-write
			STATUS current
			DESCRIPTION
				"Rule name."
			::= { fkEponProfileOnuRuleControl 7 }

		
		-- 1.3.6.1.4.1.10428 9 1.101.20.5.1.9
		fkEponProfileOnuRuleNotification OBJECT IDENTIFIER ::= { fkEponProfileBase 9 }

		
		-- 1.3.6.1.4.1.10428 9 1.101.20.5.1.9.1
		fkEponProfileOnuRuleChanged NOTIFICATION-TYPE
			OBJECTS { fkEponProfileOnuRuleControlRequest, fkEponProfileOnuRuleControlTimeStamp, fkEponProfleOnuRuleControlReqResult, fkEponProfileOnuRuleControlName }
			STATUS current
			DESCRIPTION 
				"Create or delete rule."
			::= { fkEponProfileOnuRuleNotification 1 }

		
		-- 1.3.6.1.4.1.10428 9 1.101.20.5.2
		fkEponProfileQueue OBJECT IDENTIFIER ::= { fkEponProfile 2 }

		
		-- 1.3.6.1.4.1.10428 9 1.101.20.5.2.1
		fkEponProfileQueueTable OBJECT-TYPE
			SYNTAX SEQUENCE OF FkEponProfileQueueEntry
			MAX-ACCESS not-accessible
			STATUS current
			DESCRIPTION
				"Description."
			::= { fkEponProfileQueue 1 }

		
		-- 1.3.6.1.4.1.10428 9 1.101.20.5.2.1.1
		fkEponProfileQueueEntry OBJECT-TYPE
			SYNTAX FkEponProfileQueueEntry
			MAX-ACCESS not-accessible
			STATUS current
			DESCRIPTION
				"Description."
			INDEX { fkEponProfileIndex, fkEponProfileQueueIndex }
			::= { fkEponProfileQueueTable 1 }

		
		FkEponProfileQueueEntry ::=
			SEQUENCE { 
				fkEponProfileQueueIndex
					INTEGER,
				fkEponProfileQueueQPUpQueue
					INTEGER,
				fkEponProfileQueueQPUpMaxBandwidth
					INTEGER,
				fkEponProfileQueueQPUpMAxBurstSize
					INTEGER,
				fkEponProfileQueueQPDownQueue
					INTEGER,
				fkEponProfileQueueQPDownMaxBandwidth
					INTEGER,
				fkEponProfileQueueQPDownMAxBurstSize
					INTEGER,
				fkEponProfileQueueQLimitUpBlockSize
					INTEGER,
				fkEponProfileQueueQLimitDownBlockSize
					INTEGER
			 }

		-- 1.3.6.1.4.1.10428 9 1.101.20.5.2.1.1.1
		fkEponProfileQueueIndex OBJECT-TYPE
			SYNTAX INTEGER (1..8)
			MAX-ACCESS read-only
			STATUS current
			DESCRIPTION
				"Profile Queue index "
			::= { fkEponProfileQueueEntry 1 }

		
		-- 1.3.6.1.4.1.10428 9 1.101.20.5.2.1.1.2
		fkEponProfileQueueQPUpQueue OBJECT-TYPE
			SYNTAX INTEGER (0..7)
			MAX-ACCESS read-only
			STATUS current
			DESCRIPTION
				"Upstream queue number"
			::= { fkEponProfileQueueEntry 2 }

		
		-- 1.3.6.1.4.1.10428 9 1.101.20.5.2.1.1.3
		fkEponProfileQueueQPUpMaxBandwidth OBJECT-TYPE
			SYNTAX INTEGER (0 | 100..1000000)
			UNITS "kbps"
			MAX-ACCESS read-only
			STATUS current
			DESCRIPTION
				"Upstream queue max bandwidth"
			::= { fkEponProfileQueueEntry 3 }

		
		-- 1.3.6.1.4.1.10428 9 1.101.20.5.2.1.1.4
		fkEponProfileQueueQPUpMAxBurstSize OBJECT-TYPE
			SYNTAX INTEGER (0 | 2..16777214)
			UNITS "byte"
			MAX-ACCESS read-only
			STATUS current
			DESCRIPTION
				"Upstream queue max burst size"
			::= { fkEponProfileQueueEntry 4 }

		
		-- 1.3.6.1.4.1.10428 9 1.101.20.5.2.1.1.5
		fkEponProfileQueueQPDownQueue OBJECT-TYPE
			SYNTAX INTEGER (0..7)
			MAX-ACCESS read-only
			STATUS current
			DESCRIPTION
				"Downstream queue number"
			::= { fkEponProfileQueueEntry 5 }

		
		-- 1.3.6.1.4.1.10428 9 1.101.20.5.2.1.1.6
		fkEponProfileQueueQPDownMaxBandwidth OBJECT-TYPE
			SYNTAX INTEGER (0 | 100..1000000)
			UNITS "kbps"
			MAX-ACCESS read-only
			STATUS current
			DESCRIPTION
				"Downtream queue max bandwidth"
			::= { fkEponProfileQueueEntry 6 }

		
		-- 1.3.6.1.4.1.10428 9 1.101.20.5.2.1.1.7
		fkEponProfileQueueQPDownMAxBurstSize OBJECT-TYPE
			SYNTAX INTEGER (0 | 2..16777214)
			UNITS "byte"
			MAX-ACCESS read-only
			STATUS current
			DESCRIPTION
				"Downtream queue max burst size"
			::= { fkEponProfileQueueEntry 7 }

		
		-- 1.3.6.1.4.1.10428 9 1.101.20.5.2.1.1.8
		fkEponProfileQueueQLimitUpBlockSize OBJECT-TYPE
			SYNTAX INTEGER (-1 | 0..9215)
			MAX-ACCESS read-only
			STATUS current
			DESCRIPTION
				"Description."
			::= { fkEponProfileQueueEntry 8 }

		
		-- 1.3.6.1.4.1.10428 9 1.101.20.5.2.1.1.9
		fkEponProfileQueueQLimitDownBlockSize OBJECT-TYPE
			SYNTAX INTEGER (-1 | 0..9215)
			MAX-ACCESS read-only
			STATUS current
			DESCRIPTION
				"Description."
			::= { fkEponProfileQueueEntry 9 }

		
		-- 1.3.6.1.4.1.10428 9 1.101.20.5.2.2
		fkEponProfileQueueControl OBJECT IDENTIFIER ::= { fkEponProfileQueue 2 }

		
		-- 1.3.6.1.4.1.10428 9 1.101.20.5.2.2.1
		fkEponProfileQueueControlRequest OBJECT-TYPE
			SYNTAX INTEGER
				{
				modifyProfileQuuePolicyUp(1),
				modifyProfileQuuePolicyDown(2),
				modifyProfileQueueLimit(3)
				}
			MAX-ACCESS read-write
			STATUS current
			DESCRIPTION
				"The request of a user command"
			::= { fkEponProfileQueueControl 1 }

		
		-- 1.3.6.1.4.1.10428 9 1.101.20.5.2.2.2
		fkEponProfileQueueControlStatus OBJECT-TYPE
			SYNTAX FkControlStatusType
			MAX-ACCESS read-only
			STATUS current
			DESCRIPTION
				"The status of user command"
			::= { fkEponProfileQueueControl 2 }

		
		-- 1.3.6.1.4.1.10428 9 1.101.20.5.2.2.3
		fkEponProfileQueueControlTimer OBJECT-TYPE
			SYNTAX Gauge32
			MAX-ACCESS read-write
			STATUS current
			DESCRIPTION
				"The maximum time for the manager for a long running user command"
			::= { fkEponProfileQueueControl 3 }

		
		-- 1.3.6.1.4.1.10428 9 1.101.20.5.2.2.4
		fkEponProfileQueueControlTimeStamp OBJECT-TYPE
			SYNTAX TimeTicks
			MAX-ACCESS read-only
			STATUS current
			DESCRIPTION
				"The time stamp of the last command(end of command)"
			::= { fkEponProfileQueueControl 4 }

		
		-- 1.3.6.1.4.1.10428 9 1.101.20.5.2.2.5
		fkEponProfileQueueControlReqResult OBJECT-TYPE
			SYNTAX FkControlRequestResultType
			MAX-ACCESS read-only
			STATUS current
			DESCRIPTION
				"The result of the last user command"
			::= { fkEponProfileQueueControl 5 }

		
		-- 1.3.6.1.4.1.10428 9 1.101.20.5.2.2.6
		fkEponProfileQueueControlProfileIndex OBJECT-TYPE
			SYNTAX INTEGER (1..32)
			MAX-ACCESS read-write
			STATUS current
			DESCRIPTION
				"Profile Index"
			::= { fkEponProfileQueueControl 6 }

		
		-- 1.3.6.1.4.1.10428 9 1.101.20.5.2.2.7
		fkEponProfileQueueControlQueueIndex OBJECT-TYPE
			SYNTAX INTEGER (1..8)
			MAX-ACCESS read-write
			STATUS current
			DESCRIPTION
				"Profile Queue index "
			::= { fkEponProfileQueueControl 7 }

		
		-- 1.3.6.1.4.1.10428 9 1.101.20.5.2.2.8
		fkEponProfileQueueControlQPUpQueue OBJECT-TYPE
			SYNTAX INTEGER (0..7)
			MAX-ACCESS read-write
			STATUS current
			DESCRIPTION
				"Upstream queue number"
			::= { fkEponProfileQueueControl 8 }

		
		-- 1.3.6.1.4.1.10428 9 1.101.20.5.2.2.9
		fkEponProfileQueueControlQPUpMaxBandwidth OBJECT-TYPE
			SYNTAX INTEGER (0 | 100..1000000)
			UNITS "kbps"
			MAX-ACCESS read-write
			STATUS current
			DESCRIPTION
				"Upstream queue max bandwidth"
			::= { fkEponProfileQueueControl 9 }

		
		-- 1.3.6.1.4.1.10428 9 1.101.20.5.2.2.10
		fkEponProfileQueueControlQPUpMAxBurstSize OBJECT-TYPE
			SYNTAX INTEGER (0 | 2..16777214)
			UNITS "byte"
			MAX-ACCESS read-write
			STATUS current
			DESCRIPTION
				"Upstream queue max burst size"
			::= { fkEponProfileQueueControl 10 }

		
		-- 1.3.6.1.4.1.10428 9 1.101.20.5.2.2.11
		fkEponProfileQueueControlQPDownQueue OBJECT-TYPE
			SYNTAX INTEGER (0..7)
			MAX-ACCESS read-write
			STATUS current
			DESCRIPTION
				"Downstream queue number"
			::= { fkEponProfileQueueControl 11 }

		
		-- 1.3.6.1.4.1.10428 9 1.101.20.5.2.2.12
		fkEponProfileQueueControlQPDownMaxBandwidth OBJECT-TYPE
			SYNTAX INTEGER (0 | 100..1000000)
			UNITS "kbps"
			MAX-ACCESS read-write
			STATUS current
			DESCRIPTION
				"Downtream queue max bandwidth"
			::= { fkEponProfileQueueControl 12 }

		
		-- 1.3.6.1.4.1.10428 9 1.101.20.5.2.2.13
		fkEponProfileQueueControlQPDownMAxBurstSize OBJECT-TYPE
			SYNTAX INTEGER (0 | 2..16777214)
			UNITS "byte"
			MAX-ACCESS read-write
			STATUS current
			DESCRIPTION
				"Downtream queue max burst size"
			::= { fkEponProfileQueueControl 13 }

		
		-- 1.3.6.1.4.1.10428 9 1.101.20.5.2.2.14
		fkEponProfileQueueControlLimitFlag OBJECT-TYPE
			SYNTAX INTEGER
				{
				up(1),
				down(2)
				}
			MAX-ACCESS read-write
			STATUS current
			DESCRIPTION
				"Description."
			::= { fkEponProfileQueueControl 14 }

		
		-- 1.3.6.1.4.1.10428 9 1.101.20.5.2.2.15
		fkEponProfileQueueControlBlockSize0 OBJECT-TYPE
			SYNTAX INTEGER (-1 | 0..9215)
			MAX-ACCESS read-write
			STATUS current
			DESCRIPTION
				"Description."
			::= { fkEponProfileQueueControl 15 }

		
		-- 1.3.6.1.4.1.10428 9 1.101.20.5.2.2.16
		fkEponProfileQueueControlBlockSize1 OBJECT-TYPE
			SYNTAX INTEGER (-1 | 0..9215)
			MAX-ACCESS read-write
			STATUS current
			DESCRIPTION
				"Description."
			::= { fkEponProfileQueueControl 16 }

		
		-- 1.3.6.1.4.1.10428 9 1.101.20.5.2.2.17
		fkEponProfileQueueControlBlockSize2 OBJECT-TYPE
			SYNTAX INTEGER (-1 | 0..9215)
			MAX-ACCESS read-write
			STATUS current
			DESCRIPTION
				"Description."
			::= { fkEponProfileQueueControl 17 }

		
		-- 1.3.6.1.4.1.10428 9 1.101.20.5.2.2.18
		fkEponProfileQueueControlBlockSize3 OBJECT-TYPE
			SYNTAX INTEGER (-1 | 0..9215)
			MAX-ACCESS read-write
			STATUS current
			DESCRIPTION
				"Description."
			::= { fkEponProfileQueueControl 18 }

		
		-- 1.3.6.1.4.1.10428 9 1.101.20.5.2.2.19
		fkEponProfileQueueControlBlockSize4 OBJECT-TYPE
			SYNTAX INTEGER (-1 | 0..9152)
			MAX-ACCESS read-write
			STATUS current
			DESCRIPTION
				"Description."
			::= { fkEponProfileQueueControl 19 }

		
		-- 1.3.6.1.4.1.10428 9 1.101.20.5.2.2.20
		fkEponProfileQueueControlBlockSize5 OBJECT-TYPE
			SYNTAX INTEGER (-1 | 0..9152)
			MAX-ACCESS read-write
			STATUS current
			DESCRIPTION
				"Description."
			::= { fkEponProfileQueueControl 20 }

		
		-- 1.3.6.1.4.1.10428 9 1.101.20.5.2.2.21
		fkEponProfileQueueControlBlockSize6 OBJECT-TYPE
			SYNTAX INTEGER (-1 | 0..9152)
			MAX-ACCESS read-write
			STATUS current
			DESCRIPTION
				"Description."
			::= { fkEponProfileQueueControl 21 }

		
		-- 1.3.6.1.4.1.10428 9 1.101.20.5.2.2.22
		fkEponProfileQueueControlBlockSize7 OBJECT-TYPE
			SYNTAX INTEGER (-1 | 0..9152)
			MAX-ACCESS read-write
			STATUS current
			DESCRIPTION
				"Description."
			::= { fkEponProfileQueueControl 22 }

		
		-- 1.3.6.1.4.1.10428 9 1.101.20.5.2.3
		fkEponProfileQueueNotification OBJECT IDENTIFIER ::= { fkEponProfileQueue 3 }

		
		-- 1.3.6.1.4.1.10428 9 1.101.20.5.2.3.1
		fkEponProfileQueueModifyQueuePolicy NOTIFICATION-TYPE
			OBJECTS { fkEponProfileQueueControlRequest, fkEponProfileQueueControlTimeStamp, fkEponProfileQueueControlReqResult, fkEponProfileQueueControlProfileIndex, fkEponProfileQueueControlQueueIndex
				 }
			STATUS current
			DESCRIPTION 
				"Description."
			::= { fkEponProfileQueueNotification 1 }

		
		-- 1.3.6.1.4.1.10428 9 1.101.20.5.2.3.2
		fkEponProfileQueueModifyQueueLimit NOTIFICATION-TYPE
			OBJECTS { fkEponProfileQueueControlRequest, fkEponProfileQueueControlTimeStamp, fkEponProfileQueueControlReqResult, fkEponProfileQueueControlProfileIndex, fkEponProfileQueueControlLimitFlag, 
				fkEponProfileQueueControlBlockSize0, fkEponProfileQueueControlBlockSize1, fkEponProfileQueueControlBlockSize2, fkEponProfileQueueControlBlockSize3, fkEponProfileQueueControlBlockSize4, 
				fkEponProfileQueueControlBlockSize5, fkEponProfileQueueControlBlockSize6, fkEponProfileQueueControlBlockSize7 }
			STATUS current
			DESCRIPTION 
				"Description."
			::= { fkEponProfileQueueNotification 2 }

		
		-- 1.3.6.1.4.1.10428 9 1.101.20.5.3
		fkEponProfileVlan OBJECT IDENTIFIER ::= { fkEponProfile 3 }

		
		-- 1.3.6.1.4.1.10428 9 1.101.20.5.3.1
		fkEponProfileVlanTable OBJECT-TYPE
			SYNTAX SEQUENCE OF FkEponProfileVlanEntry
			MAX-ACCESS not-accessible
			STATUS current
			DESCRIPTION
				"Description."
			::= { fkEponProfileVlan 1 }

		
		-- 1.3.6.1.4.1.10428 9 1.101.20.5.3.1.1
		fkEponProfileVlanEntry OBJECT-TYPE
			SYNTAX FkEponProfileVlanEntry
			MAX-ACCESS not-accessible
			STATUS current
			DESCRIPTION
				"Description."
			INDEX { fkEponProfileIndex, fkEponProfileVlanIndex }
			::= { fkEponProfileVlanTable 1 }

		
		FkEponProfileVlanEntry ::=
			SEQUENCE { 
				fkEponProfileVlanIndex
					VlanIndex,
				fkEponProfileVlanEgressPorts
					PortList,
				fkEponProfileVlanUntaggedPorts
					PortList
			 }

		-- 1.3.6.1.4.1.10428 9 1.101.20.5.3.1.1.1
		fkEponProfileVlanIndex OBJECT-TYPE
			SYNTAX VlanIndex (1..4094)
			MAX-ACCESS read-only
			STATUS current
			DESCRIPTION
				"The index of ONU VLAN"
			::= { fkEponProfileVlanEntry 1 }

		
		-- 1.3.6.1.4.1.10428 9 1.101.20.5.3.1.1.2
		fkEponProfileVlanEgressPorts OBJECT-TYPE
			SYNTAX PortList
			MAX-ACCESS read-only
			STATUS current
			DESCRIPTION
				"The set of ports which are transmitting traffic for this ONU VLAN as either tagged or untagged frames."
			::= { fkEponProfileVlanEntry 2 }

		
		-- 1.3.6.1.4.1.10428 9 1.101.20.5.3.1.1.3
		fkEponProfileVlanUntaggedPorts OBJECT-TYPE
			SYNTAX PortList
			MAX-ACCESS read-only
			STATUS current
			DESCRIPTION
				"The set of ports which are transmitting traffic for this VLAN as untagged frames"
			::= { fkEponProfileVlanEntry 3 }

		
		-- 1.3.6.1.4.1.10428 9 1.101.20.5.3.2
		fkEponProfileVlanControl OBJECT IDENTIFIER ::= { fkEponProfileVlan 2 }

		
		-- 1.3.6.1.4.1.10428 9 1.101.20.5.3.2.1
		fkEponProfileVlanControlRequest OBJECT-TYPE
			SYNTAX INTEGER
				{
				createVlan(1),
				destroyVlan(2),
				setAddVlanProfile(3)
				}
			MAX-ACCESS read-write
			STATUS current
			DESCRIPTION
				"The request of a user command"
			::= { fkEponProfileVlanControl 1 }

		
		-- 1.3.6.1.4.1.10428 9 1.101.20.5.3.2.2
		fkEponProfileVlanControlStatus OBJECT-TYPE
			SYNTAX FkControlStatusType
			MAX-ACCESS read-only
			STATUS current
			DESCRIPTION
				"The status of user command"
			::= { fkEponProfileVlanControl 2 }

		
		-- 1.3.6.1.4.1.10428 9 1.101.20.5.3.2.3
		fkEponProfileVlanControlTimer OBJECT-TYPE
			SYNTAX Gauge32
			MAX-ACCESS read-write
			STATUS current
			DESCRIPTION
				"The maximum time for the manager for a long running user command"
			::= { fkEponProfileVlanControl 3 }

		
		-- 1.3.6.1.4.1.10428 9 1.101.20.5.3.2.4
		fkEponProfileVlanControlTimeStamp OBJECT-TYPE
			SYNTAX TimeTicks
			MAX-ACCESS read-only
			STATUS current
			DESCRIPTION
				"The time stamp of the last command(end of command)"
			::= { fkEponProfileVlanControl 4 }

		
		-- 1.3.6.1.4.1.10428 9 1.101.20.5.3.2.5
		fkEponProfileVlanControlReqResult OBJECT-TYPE
			SYNTAX FkControlRequestResultType
			MAX-ACCESS read-only
			STATUS current
			DESCRIPTION
				"The result of the last user command"
			::= { fkEponProfileVlanControl 5 }

		
		-- 1.3.6.1.4.1.10428 9 1.101.20.5.3.2.6
		fkEponProfileVlanControlProfileIndex OBJECT-TYPE
			SYNTAX INTEGER (1..32)
			MAX-ACCESS read-write
			STATUS current
			DESCRIPTION
				"Description."
			::= { fkEponProfileVlanControl 6 }

		
		-- 1.3.6.1.4.1.10428 9 1.101.20.5.3.2.7
		fkEponProfileVlanControlVlanIndex OBJECT-TYPE
			SYNTAX VlanIndex
			MAX-ACCESS read-write
			STATUS current
			DESCRIPTION
				"The index of ONU VLAN"
			::= { fkEponProfileVlanControl 7 }

		
		-- 1.3.6.1.4.1.10428 9 1.101.20.5.3.2.8
		fkEponProfileVlanControlVlanEgressPorts OBJECT-TYPE
			SYNTAX PortList
			MAX-ACCESS read-write
			STATUS current
			DESCRIPTION
				"The set of ports which are transmitting traffic for this ONU VLAN as either tagged or untagged frames."
			::= { fkEponProfileVlanControl 8 }

		
		-- 1.3.6.1.4.1.10428 9 1.101.20.5.3.2.9
		fkEponProfileVlanControlVlanUntaggedPorts OBJECT-TYPE
			SYNTAX PortList
			MAX-ACCESS read-write
			STATUS current
			DESCRIPTION
				"The set of ports which are transmitting traffic for this VLAN as untagged frames"
			::= { fkEponProfileVlanControl 9 }

		
		-- 1.3.6.1.4.1.10428 9 1.101.20.5.3.3
		fkEponProfileVlanNotification OBJECT IDENTIFIER ::= { fkEponProfileVlan 3 }

		
		-- 1.3.6.1.4.1.10428 9 1.101.20.5.3.3.1
		fkEponProfileVlanCreated NOTIFICATION-TYPE
			OBJECTS { fkEponProfileVlanControlRequest, fkEponProfileVlanControlTimeStamp, fkEponProfileVlanControlReqResult, fkEponProfileControlIndex, fkEponProfileControlName, 
				fkEponProfileVlanControlVlanIndex }
			STATUS current
			DESCRIPTION 
				"Description."
			::= { fkEponProfileVlanNotification 1 }

		
		-- 1.3.6.1.4.1.10428 9 1.101.20.5.3.3.2
		fkEponProfileVlanDestroyed NOTIFICATION-TYPE
			OBJECTS { fkEponProfileVlanControlRequest, fkEponProfileVlanControlTimeStamp, fkEponProfileVlanControlReqResult, fkEponProfileControlIndex, fkEponProfileControlName, 
				fkEponProfileVlanControlVlanIndex }
			STATUS current
			DESCRIPTION 
				"Description."
			::= { fkEponProfileVlanNotification 2 }

		
		-- 1.3.6.1.4.1.10428 9 1.101.20.5.3.3.3
		fkEponProfileVlanProfileChanged NOTIFICATION-TYPE
			OBJECTS { fkEponProfileVlanControlRequest, fkEponProfileVlanControlTimeStamp, fkEponProfileVlanControlReqResult, fkEponProfileControlIndex, fkEponProfileControlName, 
				fkEponProfileVlanControlVlanIndex, fkEponProfileVlanControlVlanEgressPorts, fkEponProfileVlanControlVlanUntaggedPorts }
			STATUS current
			DESCRIPTION 
				"Description."
			::= { fkEponProfileVlanNotification 3 }

		
		-- 1.3.6.1.4.1.10428 9 1.101.20.5.4
		fkEponProfilePort OBJECT IDENTIFIER ::= { fkEponProfile 4 }

		
		-- 1.3.6.1.4.1.10428 9 1.101.20.5.4.1
		fkEponProfilePortTable OBJECT-TYPE
			SYNTAX SEQUENCE OF FkEponProfilePortEntry
			MAX-ACCESS not-accessible
			STATUS current
			DESCRIPTION
				"Description."
			::= { fkEponProfilePort 1 }

		
		-- 1.3.6.1.4.1.10428 9 1.101.20.5.4.1.1
		fkEponProfilePortEntry OBJECT-TYPE
			SYNTAX FkEponProfilePortEntry
			MAX-ACCESS not-accessible
			STATUS current
			DESCRIPTION
				"Description."
			INDEX { fkEponProfileIndex, fkEponProfilePortIndex }
			::= { fkEponProfilePortTable 1 }

		
		FkEponProfilePortEntry ::=
			SEQUENCE { 
				fkEponProfilePortIndex
					INTEGER,
				fkEponProfilePortAdminStatus
					INTEGER,
				fkEponProfilePortNego
					INTEGER,
				fkEponProfilePortSpeed
					INTEGER,
				fkEponProfilePortduplex
					INTEGER,
				fkEponProfilePortMaxHost
					Integer32,
				fkEponProfilePortPvid
					VlanIndex,
				fkEponProfilePortIngressRateLimitMode
					INTEGER,
				fkEponProfilePortIngressRateLimit
					INTEGER,
				fkEponProfilePortEgressRateLimit
					INTEGER,
				fkEponProfilePortFlowControl
					INTEGER,
				fkEponProfilePortIsolationStatus
					EnableFlag,
				fkEponProfilePortMaxHostAgingTime
					INTEGER
			 }

		-- 1.3.6.1.4.1.10428 9 1.101.20.5.4.1.1.1
		fkEponProfilePortIndex OBJECT-TYPE
			SYNTAX INTEGER (1..256)
			MAX-ACCESS read-only
			STATUS current
			DESCRIPTION
				"The index of the ONU port"
			::= { fkEponProfilePortEntry 1 }

		
		-- 1.3.6.1.4.1.10428 9 1.101.20.5.4.1.1.2
		fkEponProfilePortAdminStatus OBJECT-TYPE
			SYNTAX INTEGER
				{
				enable(1),
				disable(2)
				}
			MAX-ACCESS read-only
			STATUS current
			DESCRIPTION
				"The desired state of the ONU port"
			::= { fkEponProfilePortEntry 2 }

		
		-- 1.3.6.1.4.1.10428 9 1.101.20.5.4.1.1.3
		fkEponProfilePortNego OBJECT-TYPE
			SYNTAX INTEGER
				{
				on(1),
				off(2)
				}
			MAX-ACCESS read-only
			STATUS current
			DESCRIPTION
				"The current operational state of the ONU port"
			::= { fkEponProfilePortEntry 3 }

		
		-- 1.3.6.1.4.1.10428 9 1.101.20.5.4.1.1.4
		fkEponProfilePortSpeed OBJECT-TYPE
			SYNTAX INTEGER (10 | 100 | 1000)
			UNITS "Mbits/sec"
			MAX-ACCESS read-only
			STATUS current
			DESCRIPTION
				"It's auto-negotiation for a port, automatically to match the transmission speed and the duplex mode of the attached device"
			::= { fkEponProfilePortEntry 4 }

		
		-- 1.3.6.1.4.1.10428 9 1.101.20.5.4.1.1.5
		fkEponProfilePortduplex OBJECT-TYPE
			SYNTAX INTEGER
				{
				full(1),
				half(2)
				}
			MAX-ACCESS read-only
			STATUS current
			DESCRIPTION
				"It express port speed that configure transmit rate of each port."
			::= { fkEponProfilePortEntry 5 }

		
		-- 1.3.6.1.4.1.10428 9 1.101.20.5.4.1.1.6
		fkEponProfilePortMaxHost OBJECT-TYPE
			SYNTAX Integer32
			MAX-ACCESS read-only
			STATUS current
			DESCRIPTION
				"It express half duplex or full duplex mode. Only unidirectional communication is possible on half duplex mode and bi-directional communication is possible on full duplex mode to transmit packet for two ways."
			::= { fkEponProfilePortEntry 6 }

		
		-- 1.3.6.1.4.1.10428 9 1.101.20.5.4.1.1.7
		fkEponProfilePortPvid OBJECT-TYPE
			SYNTAX VlanIndex
			MAX-ACCESS read-only
			STATUS current
			DESCRIPTION
				"It is PVID that configure in ONU port"
			::= { fkEponProfilePortEntry 7 }

		
		-- 1.3.6.1.4.1.10428 9 1.101.20.5.4.1.1.8
		fkEponProfilePortIngressRateLimitMode OBJECT-TYPE
			SYNTAX INTEGER
				{
				all(0),
				multiBroadUnicast(1),
				multiBroadcast(2),
				broadcast(3)
				}
			MAX-ACCESS read-only
			STATUS current
			DESCRIPTION
				"It is rate limit mode in Ingress
				0  Limit all frames
				 1  Limit multicast, broadcast and flooded unicast frame
				 2  Limit multicast, broadcast frame
				 3  Limit broadcast frame only"
			::= { fkEponProfilePortEntry 8 }

		
		-- 1.3.6.1.4.1.10428 9 1.101.20.5.4.1.1.9
		fkEponProfilePortIngressRateLimit OBJECT-TYPE
			SYNTAX INTEGER (0 | 62..100000)
			MAX-ACCESS read-only
			STATUS current
			DESCRIPTION
				"It is configurable port rate limit in Ingress
				The value of 0 is unlimit
				"
			DEFVAL { 0 }
			::= { fkEponProfilePortEntry 9 }

		
		-- 1.3.6.1.4.1.10428 9 1.101.20.5.4.1.1.10
		fkEponProfilePortEgressRateLimit OBJECT-TYPE
			SYNTAX INTEGER (0 | 62..100000)
			MAX-ACCESS read-only
			STATUS current
			DESCRIPTION
				"It is configurable port rate limit in Egress
				The value of 0 is unlimit
				"
			DEFVAL { 0 }
			::= { fkEponProfilePortEntry 10 }

		
		-- 1.3.6.1.4.1.10428 9 1.101.20.5.4.1.1.11
		fkEponProfilePortFlowControl OBJECT-TYPE
			SYNTAX INTEGER
				{
				on(1),
				off(2)
				}
			MAX-ACCESS read-only
			STATUS current
			DESCRIPTION
				"Description."
			::= { fkEponProfilePortEntry 11 }

		
		-- 1.3.6.1.4.1.10428 9 1.101.20.5.4.1.1.12
		fkEponProfilePortIsolationStatus OBJECT-TYPE
			SYNTAX EnableFlag
			MAX-ACCESS read-only
			STATUS current
			DESCRIPTION
				"Description."
			::= { fkEponProfilePortEntry 12 }

		
		-- 1.3.6.1.4.1.10428 9 1.101.20.5.4.1.1.13
		fkEponProfilePortMaxHostAgingTime OBJECT-TYPE
			SYNTAX INTEGER (10..300)
			MAX-ACCESS read-write
			STATUS current
			DESCRIPTION
				"Max Host Aging Time."
			::= { fkEponProfilePortEntry 13 }

		
		-- 1.3.6.1.4.1.10428 9 1.101.20.5.4.2
		fkEponProfilePortControl OBJECT IDENTIFIER ::= { fkEponProfilePort 2 }

		
		-- 1.3.6.1.4.1.10428 9 1.101.20.5.4.2.1
		fkEponProfilePortControlRequest OBJECT-TYPE
			SYNTAX INTEGER
				{
				setPortAdminStatus(1),
				setPortNego(2),
				setPortSpeed(3),
				setPortDuplex(4),
				setPortMaxHost(5),
				setPortPvid(6),
				setPortRateLimit(7),
				setPortFlowControl(8),
				setPortIsolation(9),
				setPortMaxHostAgingTime(10),
				noMaxHost(11)
				}
			MAX-ACCESS read-write
			STATUS current
			DESCRIPTION
				"The request of a user command"
			::= { fkEponProfilePortControl 1 }

		
		-- 1.3.6.1.4.1.10428 9 1.101.20.5.4.2.2
		fkEponProfilePortControlStatus OBJECT-TYPE
			SYNTAX FkControlStatusType
			MAX-ACCESS read-only
			STATUS current
			DESCRIPTION
				"The status of user command"
			::= { fkEponProfilePortControl 2 }

		
		-- 1.3.6.1.4.1.10428 9 1.101.20.5.4.2.3
		fkEponProfilePortControlTimer OBJECT-TYPE
			SYNTAX Gauge32
			MAX-ACCESS read-write
			STATUS current
			DESCRIPTION
				"The maximum time for the manager for a long running user command"
			::= { fkEponProfilePortControl 3 }

		
		-- 1.3.6.1.4.1.10428 9 1.101.20.5.4.2.4
		fkEponProfilePortControlTimeStamp OBJECT-TYPE
			SYNTAX TimeTicks
			MAX-ACCESS read-only
			STATUS current
			DESCRIPTION
				"The time stamp of the last command(end of command)"
			::= { fkEponProfilePortControl 4 }

		
		-- 1.3.6.1.4.1.10428 9 1.101.20.5.4.2.5
		fkEponProfilePortControlReqResult OBJECT-TYPE
			SYNTAX FkControlRequestResultType
			MAX-ACCESS read-only
			STATUS current
			DESCRIPTION
				"The result of the last user command"
			::= { fkEponProfilePortControl 5 }

		
		-- 1.3.6.1.4.1.10428 9 1.101.20.5.4.2.6
		fkEponProfilePortControlProfileIndex OBJECT-TYPE
			SYNTAX INTEGER (1..32)
			MAX-ACCESS read-write
			STATUS current
			DESCRIPTION
				"Description."
			::= { fkEponProfilePortControl 6 }

		
		-- 1.3.6.1.4.1.10428 9 1.101.20.5.4.2.7
		fkEponProfilePortControlPortIndex OBJECT-TYPE
			SYNTAX INTEGER (1..256)
			MAX-ACCESS read-write
			STATUS current
			DESCRIPTION
				"Description."
			::= { fkEponProfilePortControl 7 }

		
		-- 1.3.6.1.4.1.10428 9 1.101.20.5.4.2.8
		fkEponProfilePortControlAdminStatus OBJECT-TYPE
			SYNTAX INTEGER
				{
				enable(1),
				disable(2)
				}
			MAX-ACCESS read-write
			STATUS current
			DESCRIPTION
				"Description."
			DEFVAL { 0 }
			::= { fkEponProfilePortControl 8 }

		
		-- 1.3.6.1.4.1.10428 9 1.101.20.5.4.2.9
		fkEponProfilePortControlNego OBJECT-TYPE
			SYNTAX INTEGER
				{
				on(1),
				off(2)
				}
			MAX-ACCESS read-write
			STATUS current
			DESCRIPTION
				"Description."
			DEFVAL { 1 }
			::= { fkEponProfilePortControl 9 }

		
		-- 1.3.6.1.4.1.10428 9 1.101.20.5.4.2.10
		fkEponProfilePortControlSpeed OBJECT-TYPE
			SYNTAX INTEGER (10 | 100 | 1000)
			UNITS "Mbits/sec"
			MAX-ACCESS read-write
			STATUS current
			DESCRIPTION
				"Description."
			::= { fkEponProfilePortControl 10 }

		
		-- 1.3.6.1.4.1.10428 9 1.101.20.5.4.2.11
		fkEponProfilePortControlDuplex OBJECT-TYPE
			SYNTAX INTEGER
				{
				full(1),
				half(2)
				}
			MAX-ACCESS read-write
			STATUS current
			DESCRIPTION
				"Description."
			DEFVAL { 1 }
			::= { fkEponProfilePortControl 11 }

		
		-- 1.3.6.1.4.1.10428 9 1.101.20.5.4.2.12
		fkEponProfilePortControlMaxHost OBJECT-TYPE
			SYNTAX Integer32
			MAX-ACCESS read-write
			STATUS current
			DESCRIPTION
				"Description."
			::= { fkEponProfilePortControl 12 }

		
		-- 1.3.6.1.4.1.10428 9 1.101.20.5.4.2.13
		fkEponProfilePortControlPvid OBJECT-TYPE
			SYNTAX VlanIndex
			MAX-ACCESS read-write
			STATUS current
			DESCRIPTION
				"It is PVID that configure in ONU port"
			DEFVAL { '1'b }
			::= { fkEponProfilePortControl 13 }

		
		-- 1.3.6.1.4.1.10428 9 1.101.20.5.4.2.14
		fkEponProfilePortControlIngressRateLimitMode OBJECT-TYPE
			SYNTAX INTEGER
				{
				all(0),
				multiBroadUnicast(1),
				multiBroadcast(2),
				broadcast(3)
				}
			MAX-ACCESS read-write
			STATUS current
			DESCRIPTION
				"It is rate limit mode in Ingress 
				0  Limit all frames
				  1  Limit multicast, broadcast and flooded unicast frame
				  2  Limit multicast, broadcast frame
				  3  Limit broadcast frame only"
			DEFVAL { 0 }
			::= { fkEponProfilePortControl 14 }

		
		-- 1.3.6.1.4.1.10428 9 1.101.20.5.4.2.15
		fkEponProfilePortControlIngressRateLimit OBJECT-TYPE
			SYNTAX INTEGER (62..100000)
			MAX-ACCESS read-write
			STATUS current
			DESCRIPTION
				"It is configurable port rate limit in Ingress
				The value of 0 is unlimit
				"
			DEFVAL { 0 }
			::= { fkEponProfilePortControl 15 }

		
		-- 1.3.6.1.4.1.10428 9 1.101.20.5.4.2.16
		fkEponProfilePortControlEgressRateLimit OBJECT-TYPE
			SYNTAX INTEGER (62..100000)
			MAX-ACCESS read-write
			STATUS current
			DESCRIPTION
				"It is configurable port rate limit in Egress
				The value of 0 is unlimit
				"
			DEFVAL { 0 }
			::= { fkEponProfilePortControl 16 }

		
		-- 1.3.6.1.4.1.10428 9 1.101.20.5.4.2.17
		fkEponProfilePortControlFlowControl OBJECT-TYPE
			SYNTAX INTEGER
				{
				on(1),
				off(2)
				}
			MAX-ACCESS read-write
			STATUS current
			DESCRIPTION
				"Description."
			::= { fkEponProfilePortControl 17 }

		
		-- 1.3.6.1.4.1.10428 9 1.101.20.5.4.2.18
		fkEponProfilePortControlIsolationStatus OBJECT-TYPE
			SYNTAX EnableFlag
			MAX-ACCESS read-write
			STATUS current
			DESCRIPTION
				"Description."
			::= { fkEponProfilePortControl 18 }

		
		-- 1.3.6.1.4.1.10428 9 1.101.20.5.4.2.19
		fkEponProfilePortControlMaxHostAgingTime OBJECT-TYPE
			SYNTAX INTEGER (10..300)
			MAX-ACCESS read-write
			STATUS current
			DESCRIPTION
				"Max Host Aging Time."
			::= { fkEponProfilePortControl 19 }

		
		-- 1.3.6.1.4.1.10428 9 1.101.20.5.4.3
		fkEponProfilePortNotification OBJECT IDENTIFIER ::= { fkEponProfilePort 3 }

		
		-- 1.3.6.1.4.1.10428 9 1.101.20.5.4.3.1
		fkEponProfilePortAdminStatusChanged NOTIFICATION-TYPE
			OBJECTS { fkEponProfilePortControlRequest, fkEponProfilePortControlTimeStamp, fkEponProfilePortControlReqResult, fkEponProfilePortControlProfileIndex, fkEponProfileControlName, 
				fkEponProfilePortControlPortIndex, fkEponProfilePortControlAdminStatus }
			STATUS current
			DESCRIPTION 
				"Description."
			::= { fkEponProfilePortNotification 1 }

		
		-- 1.3.6.1.4.1.10428 9 1.101.20.5.4.3.2
		fkEponProfilePortNegoChanged NOTIFICATION-TYPE
			OBJECTS { fkEponProfilePortControlRequest, fkEponProfilePortControlTimeStamp, fkEponProfilePortControlReqResult, fkEponProfilePortControlProfileIndex, fkEponProfilePortControlPortIndex, 
				fkEponProfilePortControlNego, fkEponProfileControlName }
			STATUS current
			DESCRIPTION 
				"Description."
			::= { fkEponProfilePortNotification 2 }

		
		-- 1.3.6.1.4.1.10428 9 1.101.20.5.4.3.3
		fkEponProfilePortSpeedChanged NOTIFICATION-TYPE
			OBJECTS { fkEponProfilePortControlRequest, fkEponProfilePortControlTimeStamp, fkEponProfilePortControlReqResult, fkEponProfilePortControlProfileIndex, fkEponProfileControlName, 
				fkEponProfilePortControlPortIndex, fkEponProfilePortControlSpeed }
			STATUS current
			DESCRIPTION 
				"Description."
			::= { fkEponProfilePortNotification 3 }

		
		-- 1.3.6.1.4.1.10428 9 1.101.20.5.4.3.4
		fkEponProfilePortDuplexChanged NOTIFICATION-TYPE
			OBJECTS { fkEponProfilePortControlRequest, fkEponProfilePortControlTimeStamp, fkEponProfilePortControlReqResult, fkEponProfilePortControlProfileIndex, fkEponProfileControlName, 
				fkEponProfilePortControlPortIndex, fkEponProfilePortControlDuplex }
			STATUS current
			DESCRIPTION 
				"Description."
			::= { fkEponProfilePortNotification 4 }

		
		-- 1.3.6.1.4.1.10428 9 1.101.20.5.4.3.5
		fkEponProfilePortMaxHostChanged NOTIFICATION-TYPE
			OBJECTS { fkEponProfilePortControlRequest, fkEponProfilePortControlTimeStamp, fkEponProfilePortControlReqResult, fkEponProfilePortControlProfileIndex, fkEponProfileControlName, 
				fkEponProfilePortControlPortIndex, fkEponProfilePortControlMaxHost }
			STATUS current
			DESCRIPTION 
				"Description."
			::= { fkEponProfilePortNotification 5 }

		
		-- 1.3.6.1.4.1.10428 9 1.101.20.5.4.3.6
		fkEponProfilePortPvidChanged NOTIFICATION-TYPE
			OBJECTS { fkEponProfilePortControlRequest, fkEponProfilePortControlTimeStamp, fkEponProfilePortControlReqResult, fkEponProfilePortControlProfileIndex, fkEponProfileControlName, 
				fkEponProfilePortControlPortIndex, fkEponProfilePortControlPvid }
			STATUS current
			DESCRIPTION 
				"Description."
			::= { fkEponProfilePortNotification 6 }

		
		-- 1.3.6.1.4.1.10428 9 1.101.20.5.4.3.7
		fkEponProfilePortRateLimitChanged NOTIFICATION-TYPE
			OBJECTS { fkEponProfilePortControlRequest, fkEponProfilePortControlTimeStamp, fkEponProfilePortControlReqResult, fkEponProfilePortControlProfileIndex, fkEponProfileControlName, 
				fkEponProfilePortControlPortIndex, fkEponProfilePortControlIngressRateLimitMode, fkEponProfilePortControlIngressRateLimit, fkEponProfilePortControlEgressRateLimit }
			STATUS current
			DESCRIPTION 
				"Description."
			::= { fkEponProfilePortNotification 7 }

		
		-- 1.3.6.1.4.1.10428 9 1.101.20.5.4.3.8
		fkEponProfilePortFlowControlChanged NOTIFICATION-TYPE
			OBJECTS { fkEponProfilePortControlRequest, fkEponProfilePortControlTimeStamp, fkEponProfilePortControlReqResult, fkEponProfilePortControlProfileIndex, fkEponProfileControlName, 
				fkEponProfilePortControlPortIndex, fkEponProfilePortControlFlowControl }
			STATUS current
			DESCRIPTION 
				"Description."
			::= { fkEponProfilePortNotification 8 }

		
		-- 1.3.6.1.4.1.10428 9 1.101.20.5.4.3.9
		fkEponProfilePortIsolationChanged NOTIFICATION-TYPE
			OBJECTS { fkEponProfilePortControlRequest, fkEponProfilePortControlTimeStamp, fkEponProfilePortControlReqResult, fkEponProfilePortControlProfileIndex, fkEponProfilePortControlPortIndex, 
				fkEponProfilePortControlIsolationStatus }
			STATUS current
			DESCRIPTION 
				"Description."
			::= { fkEponProfilePortNotification 9 }

		
		-- 1.3.6.1.4.1.10428 9 1.101.20.5.5
		fkEponProfileClassification OBJECT IDENTIFIER ::= { fkEponProfile 5 }

		
		-- 1.3.6.1.4.1.10428 9 1.101.20.5.5.1
		fkEponProfileClassificationTable OBJECT-TYPE
			SYNTAX SEQUENCE OF FkEponProfileClassificationEntry
			MAX-ACCESS not-accessible
			STATUS current
			DESCRIPTION
				"Description."
			::= { fkEponProfileClassification 1 }

		
		-- 1.3.6.1.4.1.10428 9 1.101.20.5.5.1.1
		fkEponProfileClassificationEntry OBJECT-TYPE
			SYNTAX FkEponProfileClassificationEntry
			MAX-ACCESS not-accessible
			STATUS current
			DESCRIPTION
				"Description."
			INDEX { fkEponProfileIndex, fkEponProfileClassificationIndex }
			::= { fkEponProfileClassificationTable 1 }

		
		FkEponProfileClassificationEntry ::=
			SEQUENCE { 
				fkEponProfileClassificationIndex
					INTEGER,
				fkEponProfileClassificationMatchAction
					INTEGER,
				fkEponProfileClassificationQueue
					INTEGER
			 }

		-- 1.3.6.1.4.1.10428 9 1.101.20.5.5.1.1.1
		fkEponProfileClassificationIndex OBJECT-TYPE
			SYNTAX INTEGER (1..256)
			MAX-ACCESS read-only
			STATUS current
			DESCRIPTION
				"Description."
			::= { fkEponProfileClassificationEntry 1 }

		
		-- 1.3.6.1.4.1.10428 9 1.101.20.5.5.1.1.2
		fkEponProfileClassificationMatchAction OBJECT-TYPE
			SYNTAX INTEGER
				{
				permit(1),
				deny(2),
				notUse(3)
				}
			MAX-ACCESS read-only
			STATUS current
			DESCRIPTION
				"Description."
			::= { fkEponProfileClassificationEntry 2 }

		
		-- 1.3.6.1.4.1.10428 9 1.101.20.5.5.1.1.3
		fkEponProfileClassificationQueue OBJECT-TYPE
			SYNTAX INTEGER (-1 | 0..7)
			MAX-ACCESS read-only
			STATUS current
			DESCRIPTION
				"The value of -1 is all of the queue"
			::= { fkEponProfileClassificationEntry 3 }

		
		-- 1.3.6.1.4.1.10428 9 1.101.20.5.5.2
		fkEponProfileClassificationControl OBJECT IDENTIFIER ::= { fkEponProfileClassification 2 }

		
		-- 1.3.6.1.4.1.10428 9 1.101.20.5.5.2.1
		fkEponProfileClassificationControlRequest OBJECT-TYPE
			SYNTAX INTEGER
				{
				createClassification(1),
				destroyClassification(2)
				}
			MAX-ACCESS read-write
			STATUS current
			DESCRIPTION
				"Description."
			::= { fkEponProfileClassificationControl 1 }

		
		-- 1.3.6.1.4.1.10428 9 1.101.20.5.5.2.2
		fkEponProfileClassificationControlStatus OBJECT-TYPE
			SYNTAX FkControlStatusType
			MAX-ACCESS read-only
			STATUS current
			DESCRIPTION
				"Description."
			::= { fkEponProfileClassificationControl 2 }

		
		-- 1.3.6.1.4.1.10428 9 1.101.20.5.5.2.3
		fkEponProfileClassificationControlTimer OBJECT-TYPE
			SYNTAX Gauge32
			MAX-ACCESS read-write
			STATUS current
			DESCRIPTION
				"Description."
			::= { fkEponProfileClassificationControl 3 }

		
		-- 1.3.6.1.4.1.10428 9 1.101.20.5.5.2.4
		fkEponProfileClassificationControlTimeStamp OBJECT-TYPE
			SYNTAX TimeTicks
			MAX-ACCESS read-only
			STATUS current
			DESCRIPTION
				"Description."
			::= { fkEponProfileClassificationControl 4 }

		
		-- 1.3.6.1.4.1.10428 9 1.101.20.5.5.2.5
		fkEponProfileClassificationControlReqResult OBJECT-TYPE
			SYNTAX FkControlRequestResultType
			MAX-ACCESS read-only
			STATUS current
			DESCRIPTION
				"Description."
			::= { fkEponProfileClassificationControl 5 }

		
		-- 1.3.6.1.4.1.10428 9 1.101.20.5.5.2.6
		fkEponProfileClassificationControlProfileIndex OBJECT-TYPE
			SYNTAX INTEGER (1..32)
			MAX-ACCESS read-write
			STATUS current
			DESCRIPTION
				"Description."
			::= { fkEponProfileClassificationControl 6 }

		
		-- 1.3.6.1.4.1.10428 9 1.101.20.5.5.2.7
		fkEponProfileClassificationControlClassificationIndex OBJECT-TYPE
			SYNTAX INTEGER (1..256)
			MAX-ACCESS read-write
			STATUS current
			DESCRIPTION
				"Description."
			::= { fkEponProfileClassificationControl 7 }

		
		-- 1.3.6.1.4.1.10428 9 1.101.20.5.5.2.8
		fkEponProfileClassificationControlMatchAction OBJECT-TYPE
			SYNTAX INTEGER
				{
				permit(1),
				deny(2),
				notUse(3)
				}
			MAX-ACCESS read-write
			STATUS current
			DESCRIPTION
				"Description."
			::= { fkEponProfileClassificationControl 8 }

		
		-- 1.3.6.1.4.1.10428 9 1.101.20.5.5.2.9
		fkEponProfileClassificationControlQueue OBJECT-TYPE
			SYNTAX INTEGER (-1 | 0..7)
			MAX-ACCESS read-write
			STATUS current
			DESCRIPTION
				"Description."
			::= { fkEponProfileClassificationControl 9 }

		
		-- 1.3.6.1.4.1.10428 9 1.101.20.5.5.3
		fkEponProfileClassificationNotification OBJECT IDENTIFIER ::= { fkEponProfileClassification 3 }

		
		-- 1.3.6.1.4.1.10428 9 1.101.20.5.5.3.1
		fkEponProfileClassificationCreated NOTIFICATION-TYPE
			OBJECTS { fkEponProfileClassificationControlRequest, fkEponProfileClassificationControlTimeStamp, fkEponProfileClassificationControlReqResult, fkEponProfileClassificationControlProfileIndex, fkEponProfileClassificationControlClassificationIndex, 
				fkEponProfileClassificationControlMatchAction, fkEponProfileClassificationControlQueue }
			STATUS current
			DESCRIPTION 
				"Description."
			::= { fkEponProfileClassificationNotification 1 }

		
		-- 1.3.6.1.4.1.10428 9 1.101.20.5.5.3.2
		fkEponProfileClassificationDestroyed NOTIFICATION-TYPE
			OBJECTS { fkEponProfileClassificationControlRequest, fkEponProfileClassificationControlTimeStamp, fkEponProfileClassificationControlReqResult, fkEponProfileClassificationControlProfileIndex, fkEponProfileControlName, 
				fkEponProfileClassificationControlClassificationIndex, fkEponOnuClassificationControlName }
			STATUS current
			DESCRIPTION 
				"Description."
			::= { fkEponProfileClassificationNotification 2 }

		
		-- 1.3.6.1.4.1.10428 9 1.101.20.5.6
		fkEponProfileUNIQueue OBJECT IDENTIFIER ::= { fkEponProfile 6 }

		
		-- 1.3.6.1.4.1.10428 9 1.101.20.5.6.1
		fkEponProfileUNIQueueTable OBJECT-TYPE
			SYNTAX SEQUENCE OF FkEponProfileUNIQueueEntry
			MAX-ACCESS not-accessible
			STATUS current
			DESCRIPTION
				"Description."
			::= { fkEponProfileUNIQueue 1 }

		
		-- 1.3.6.1.4.1.10428 9 1.101.20.5.6.1.1
		fkEponProfileUNIQueueEntry OBJECT-TYPE
			SYNTAX FkEponProfileUNIQueueEntry
			MAX-ACCESS not-accessible
			STATUS current
			DESCRIPTION
				"Description."
			INDEX { fkEponProfileIndex }
			::= { fkEponProfileUNIQueueTable 1 }

		
		FkEponProfileUNIQueueEntry ::=
			SEQUENCE { 
				fkEponProfileUNIQueueUpMaxBandwidth
					INTEGER,
				fkEponProfileUNIQueueUpMaxBurstSize
					INTEGER,
				fkEponProfileUNIQueueDownMaxBandwidth
					INTEGER,
				fkEponProfileUNIQueueDownMaxBurstSize
					INTEGER
			 }

		-- 1.3.6.1.4.1.10428 9 1.101.20.5.6.1.1.1
		fkEponProfileUNIQueueUpMaxBandwidth OBJECT-TYPE
			SYNTAX INTEGER (100..1000000)
			UNITS "kbps"
			MAX-ACCESS read-only
			STATUS current
			DESCRIPTION
				"Description."
			::= { fkEponProfileUNIQueueEntry 1 }

		
		-- 1.3.6.1.4.1.10428 9 1.101.20.5.6.1.1.2
		fkEponProfileUNIQueueUpMaxBurstSize OBJECT-TYPE
			SYNTAX INTEGER (128..16777214)
			UNITS "byte"
			MAX-ACCESS read-only
			STATUS current
			DESCRIPTION
				"Description."
			::= { fkEponProfileUNIQueueEntry 2 }

		
		-- 1.3.6.1.4.1.10428 9 1.101.20.5.6.1.1.3
		fkEponProfileUNIQueueDownMaxBandwidth OBJECT-TYPE
			SYNTAX INTEGER (100..1000000)
			UNITS "kbps"
			MAX-ACCESS read-only
			STATUS current
			DESCRIPTION
				"Description."
			::= { fkEponProfileUNIQueueEntry 3 }

		
		-- 1.3.6.1.4.1.10428 9 1.101.20.5.6.1.1.4
		fkEponProfileUNIQueueDownMaxBurstSize OBJECT-TYPE
			SYNTAX INTEGER (128..16777214)
			MAX-ACCESS read-only
			STATUS current
			DESCRIPTION
				"Description."
			::= { fkEponProfileUNIQueueEntry 4 }

		
		-- 1.3.6.1.4.1.10428 9 1.101.20.5.6.2
		fkEponProfileUNIQueueControl OBJECT IDENTIFIER ::= { fkEponProfileUNIQueue 2 }

		
		-- 1.3.6.1.4.1.10428 9 1.101.20.5.6.2.1
		fkEponProfileUNIQueueControlRequest OBJECT-TYPE
			SYNTAX INTEGER
				{
				modifyProfileUNIQuuePolicyUp(1),
				modifyProfileUNIQuuePolicyDown(2)
				}
			MAX-ACCESS read-write
			STATUS current
			DESCRIPTION
				"Description."
			::= { fkEponProfileUNIQueueControl 1 }

		
		-- 1.3.6.1.4.1.10428 9 1.101.20.5.6.2.2
		fkEponProfileUNIQueueControlStatus OBJECT-TYPE
			SYNTAX FkControlStatusType
			MAX-ACCESS read-only
			STATUS current
			DESCRIPTION
				"Description."
			::= { fkEponProfileUNIQueueControl 2 }

		
		-- 1.3.6.1.4.1.10428 9 1.101.20.5.6.2.3
		fkEponProfileUNIQueueControlTimer OBJECT-TYPE
			SYNTAX Gauge32
			MAX-ACCESS read-write
			STATUS current
			DESCRIPTION
				"Description."
			::= { fkEponProfileUNIQueueControl 3 }

		
		-- 1.3.6.1.4.1.10428 9 1.101.20.5.6.2.4
		fkEponProfileUNIQueueControlTimeStamp OBJECT-TYPE
			SYNTAX TimeTicks
			MAX-ACCESS read-only
			STATUS current
			DESCRIPTION
				"Description."
			::= { fkEponProfileUNIQueueControl 4 }

		
		-- 1.3.6.1.4.1.10428 9 1.101.20.5.6.2.5
		fkEponProfileUNIQueueControlReqResult OBJECT-TYPE
			SYNTAX FkControlRequestResultType
			MAX-ACCESS read-only
			STATUS current
			DESCRIPTION
				"Description."
			::= { fkEponProfileUNIQueueControl 5 }

		
		-- 1.3.6.1.4.1.10428 9 1.101.20.5.6.2.6
		fkEponProfileUNIQueueControlProfileIndex OBJECT-TYPE
			SYNTAX INTEGER (1..32)
			MAX-ACCESS read-write
			STATUS current
			DESCRIPTION
				"Description."
			::= { fkEponProfileUNIQueueControl 6 }

		
		-- 1.3.6.1.4.1.10428 9 1.101.20.5.6.2.7
		fkEponProfileUNIQueueControlUpMaxBandwidth OBJECT-TYPE
			SYNTAX INTEGER (0 | 100..1000000)
			UNITS "kbps"
			MAX-ACCESS read-write
			STATUS current
			DESCRIPTION
				"Description."
			::= { fkEponProfileUNIQueueControl 7 }

		
		-- 1.3.6.1.4.1.10428 9 1.101.20.5.6.2.8
		fkEponProfileUNIQueueControlUpMaxBurstSize OBJECT-TYPE
			SYNTAX INTEGER (0 | 128..16777214)
			UNITS "byte"
			MAX-ACCESS read-write
			STATUS current
			DESCRIPTION
				"Description."
			::= { fkEponProfileUNIQueueControl 8 }

		
		-- 1.3.6.1.4.1.10428 9 1.101.20.5.6.2.9
		fkEponProfileUNIQueueControlDownMaxBandwidth OBJECT-TYPE
			SYNTAX INTEGER (0 | 100..1000000)
			UNITS "kbps"
			MAX-ACCESS read-write
			STATUS current
			DESCRIPTION
				"Description."
			::= { fkEponProfileUNIQueueControl 9 }

		
		-- 1.3.6.1.4.1.10428 9 1.101.20.5.6.2.10
		fkEponProfileUNIQueueControlDownMaxBurstSize OBJECT-TYPE
			SYNTAX INTEGER (0 | 128..16777214)
			UNITS "byte"
			MAX-ACCESS read-write
			STATUS current
			DESCRIPTION
				"Description."
			::= { fkEponProfileUNIQueueControl 10 }

		
		-- 1.3.6.1.4.1.10428 9 1.101.20.5.6.3
		fkEponProfileUNIQueueNotification OBJECT IDENTIFIER ::= { fkEponProfileUNIQueue 3 }

		
		-- 1.3.6.1.4.1.10428 9 1.101.20.5.6.3.1
		fkEponProfileUNIQueueModifyQueuePolicy NOTIFICATION-TYPE
			OBJECTS { fkEponProfileUNIQueueControlRequest, fkEponProfileUNIQueueControlTimeStamp, fkEponProfileUNIQueueControlReqResult, fkEponProfileUNIQueueControlProfileIndex }
			STATUS current
			DESCRIPTION 
				"Description."
			::= { fkEponProfileUNIQueueNotification 1 }

		
		-- 1.3.6.1.4.1.10428 9 1.101.20.6
		fkEponAlarm OBJECT IDENTIFIER ::= { fkEpon 6 }

		
		-- 1.3.6.1.4.1.10428 9 1.101.20.6.1
		fkEponAlarmTable OBJECT-TYPE
			SYNTAX SEQUENCE OF FkEponAlarmEntry
			MAX-ACCESS not-accessible
			STATUS current
			DESCRIPTION
				"Description."
			::= { fkEponAlarm 1 }

		
		-- 1.3.6.1.4.1.10428 9 1.101.20.6.1.1
		fkEponAlarmEntry OBJECT-TYPE
			SYNTAX FkEponAlarmEntry
			MAX-ACCESS not-accessible
			STATUS current
			DESCRIPTION
				"Description."
			INDEX { fkEponOltIndex }
			::= { fkEponAlarmTable 1 }

		
		FkEponAlarmEntry ::=
			SEQUENCE { 
				fkEponAlarmBadEncryption
					EnableFlag,
				fkEponAlarmDyingGasp
					EnableFlag,
				fkEponAlarmLlidMismatch
					EnableFlag,
				fkEponAlarmOnuRegistrationError
					EnableFlag,
				fkEponAlarmTooManyOnuRegistration
					EnableFlag,
				fkEponAlarmOpticSignalError
					EnableFlag,
				fkEponAlarmStandardLinkFault
					EnableFlag,
				fkEponAlarmLossOfSignal
					EnableFlag,
				fkEponAlarmTransmitFail
					EnableFlag,
				fkEponAlarmMacLearningOverflow
					EnableFlag,
				fkEponAlarmLoopback
					EnableFlag,
				fkEponAlarmStandardDyingGasp
					EnableFlag,
				fkEponAlarmExternalDyingGasp
					EnableFlag,
				fkEponAlarmStandardCriticalEvent
					EnableFlag,
				fkEponAlarmExternalCriticalEvent
					EnableFlag,
				fkEponAlarmEponStandbyLos
					EnableFlag
			 }

		-- 1.3.6.1.4.1.10428 9 1.101.20.6.1.1.1
		fkEponAlarmBadEncryption OBJECT-TYPE
			SYNTAX EnableFlag
			MAX-ACCESS read-only
			STATUS current
			DESCRIPTION
				"alarm type: Bad encryption"
			DEFVAL { enable }
			::= { fkEponAlarmEntry 1 }

		
		-- 1.3.6.1.4.1.10428 9 1.101.20.6.1.1.2
		fkEponAlarmDyingGasp OBJECT-TYPE
			SYNTAX EnableFlag
			MAX-ACCESS read-only
			STATUS current
			DESCRIPTION
				"alarm type: Dying gasp"
			DEFVAL { enable }
			::= { fkEponAlarmEntry 2 }

		
		-- 1.3.6.1.4.1.10428 9 1.101.20.6.1.1.3
		fkEponAlarmLlidMismatch OBJECT-TYPE
			SYNTAX EnableFlag
			MAX-ACCESS read-only
			STATUS current
			DESCRIPTION
				"alarm type: llid mismatch"
			DEFVAL { enable }
			::= { fkEponAlarmEntry 3 }

		
		-- 1.3.6.1.4.1.10428 9 1.101.20.6.1.1.4
		fkEponAlarmOnuRegistrationError OBJECT-TYPE
			SYNTAX EnableFlag
			MAX-ACCESS read-only
			STATUS current
			DESCRIPTION
				"alarm type: onu registration error"
			DEFVAL { enable }
			::= { fkEponAlarmEntry 4 }

		
		-- 1.3.6.1.4.1.10428 9 1.101.20.6.1.1.5
		fkEponAlarmTooManyOnuRegistration OBJECT-TYPE
			SYNTAX EnableFlag
			MAX-ACCESS read-only
			STATUS current
			DESCRIPTION
				"alarm type: too many onu registration"
			DEFVAL { enable }
			::= { fkEponAlarmEntry 5 }

		
		-- 1.3.6.1.4.1.10428 9 1.101.20.6.1.1.6
		fkEponAlarmOpticSignalError OBJECT-TYPE
			SYNTAX EnableFlag
			MAX-ACCESS read-only
			STATUS current
			DESCRIPTION
				"alarm type: onu optical signal error"
			DEFVAL { enable }
			::= { fkEponAlarmEntry 6 }

		
		-- 1.3.6.1.4.1.10428 9 1.101.20.6.1.1.7
		fkEponAlarmStandardLinkFault OBJECT-TYPE
			SYNTAX EnableFlag
			MAX-ACCESS read-only
			STATUS current
			DESCRIPTION
				"alarm type: link falult"
			DEFVAL { enable }
			::= { fkEponAlarmEntry 7 }

		
		-- 1.3.6.1.4.1.10428 9 1.101.20.6.1.1.8
		fkEponAlarmLossOfSignal OBJECT-TYPE
			SYNTAX EnableFlag
			MAX-ACCESS read-only
			STATUS current
			DESCRIPTION
				"alarm type:loss of signal."
			DEFVAL { enable }
			::= { fkEponAlarmEntry 8 }

		
		-- 1.3.6.1.4.1.10428 9 1.101.20.6.1.1.9
		fkEponAlarmTransmitFail OBJECT-TYPE
			SYNTAX EnableFlag
			MAX-ACCESS read-only
			STATUS current
			DESCRIPTION
				"alarm type: transmit fail."
			DEFVAL { enable }
			::= { fkEponAlarmEntry 9 }

		
		-- 1.3.6.1.4.1.10428 9 1.101.20.6.1.1.10
		fkEponAlarmMacLearningOverflow OBJECT-TYPE
			SYNTAX EnableFlag
			MAX-ACCESS read-only
			STATUS current
			DESCRIPTION
				"alarm type: mac learning overflow."
			DEFVAL { enable }
			::= { fkEponAlarmEntry 10 }

		
		-- 1.3.6.1.4.1.10428 9 1.101.20.6.1.1.11
		fkEponAlarmLoopback OBJECT-TYPE
			SYNTAX EnableFlag
			MAX-ACCESS read-write
			STATUS current
			DESCRIPTION
				"alarm type: loopback."
			DEFVAL { enable }
			::= { fkEponAlarmEntry 11 }

		
		-- 1.3.6.1.4.1.10428 9 1.101.20.6.1.1.12
		fkEponAlarmStandardDyingGasp OBJECT-TYPE
			SYNTAX EnableFlag
			MAX-ACCESS read-only
			STATUS current
			DESCRIPTION
				"alarm type:standard dying gasp."
			DEFVAL { enable }
			::= { fkEponAlarmEntry 12 }

		
		-- 1.3.6.1.4.1.10428 9 1.101.20.6.1.1.13
		fkEponAlarmExternalDyingGasp OBJECT-TYPE
			SYNTAX EnableFlag
			MAX-ACCESS read-only
			STATUS current
			DESCRIPTION
				"alarm type :external dying gasp."
			DEFVAL { enable }
			::= { fkEponAlarmEntry 13 }

		
		-- 1.3.6.1.4.1.10428 9 1.101.20.6.1.1.14
		fkEponAlarmStandardCriticalEvent OBJECT-TYPE
			SYNTAX EnableFlag
			MAX-ACCESS read-only
			STATUS current
			DESCRIPTION
				"alarm type:standard critical event.
				"
			DEFVAL { enable }
			::= { fkEponAlarmEntry 14 }

		
		-- 1.3.6.1.4.1.10428 9 1.101.20.6.1.1.15
		fkEponAlarmExternalCriticalEvent OBJECT-TYPE
			SYNTAX EnableFlag
			MAX-ACCESS read-only
			STATUS current
			DESCRIPTION
				"alarm type:external critical event."
			DEFVAL { enable }
			::= { fkEponAlarmEntry 15 }

		
		-- 1.3.6.1.4.1.10428 9 1.101.20.6.1.1.16
		fkEponAlarmEponStandbyLos OBJECT-TYPE
			SYNTAX EnableFlag
			MAX-ACCESS read-only
			STATUS current
			DESCRIPTION
				"alarm type: epon standby lose."
			DEFVAL { enable }
			::= { fkEponAlarmEntry 16 }

		
		-- 1.3.6.1.4.1.10428 9 1.101.20.6.2
		fkEponAlarmControl OBJECT IDENTIFIER ::= { fkEponAlarm 2 }

		
		-- 1.3.6.1.4.1.10428 9 1.101.20.6.2.1
		fkEponAlarmControlRequest OBJECT-TYPE
			SYNTAX INTEGER
				{
				setEponAlarmProfile(1),
				setEponAlarm(2)
				}
			MAX-ACCESS read-write
			STATUS current
			DESCRIPTION
				"The request of a user command"
			::= { fkEponAlarmControl 1 }

		
		-- 1.3.6.1.4.1.10428 9 1.101.20.6.2.2
		fkEponAlarmControlStatus OBJECT-TYPE
			SYNTAX FkControlStatusType
			MAX-ACCESS read-only
			STATUS current
			DESCRIPTION
				"The status of user command"
			::= { fkEponAlarmControl 2 }

		
		-- 1.3.6.1.4.1.10428 9 1.101.20.6.2.3
		fkEponAlarmControlTimer OBJECT-TYPE
			SYNTAX Gauge32
			MAX-ACCESS read-write
			STATUS current
			DESCRIPTION
				"The maximum time for the manager for a long running user command"
			::= { fkEponAlarmControl 3 }

		
		-- 1.3.6.1.4.1.10428 9 1.101.20.6.2.4
		fkEponAlarmControlTimeStamp OBJECT-TYPE
			SYNTAX TimeTicks
			MAX-ACCESS read-only
			STATUS current
			DESCRIPTION
				"The time stamp of the last command(end of command)"
			::= { fkEponAlarmControl 4 }

		
		-- 1.3.6.1.4.1.10428 9 1.101.20.6.2.5
		fkEponAlarmControlReqResult OBJECT-TYPE
			SYNTAX FkControlRequestResultType
			MAX-ACCESS read-only
			STATUS current
			DESCRIPTION
				"The result of the last user command"
			::= { fkEponAlarmControl 5 }

		
		-- 1.3.6.1.4.1.10428 9 1.101.20.6.2.6
		fkEponAlarmControlOltIndex OBJECT-TYPE
			SYNTAX Integer32
			MAX-ACCESS read-write
			STATUS current
			DESCRIPTION
				"OLT index"
			::= { fkEponAlarmControl 6 }

		
		-- 1.3.6.1.4.1.10428 9 1.101.20.6.2.7
		fkEponAlarmControlBadEncryption OBJECT-TYPE
			SYNTAX EnableFlag
			MAX-ACCESS read-write
			STATUS current
			DESCRIPTION
				"disable(1), enable(2)"
			DEFVAL { enable }
			::= { fkEponAlarmControl 7 }

		
		-- 1.3.6.1.4.1.10428 9 1.101.20.6.2.8
		fkEponAlarmControlDyingGasp OBJECT-TYPE
			SYNTAX EnableFlag
			MAX-ACCESS read-write
			STATUS current
			DESCRIPTION
				"disable(1), enable(2)"
			DEFVAL { enable }
			::= { fkEponAlarmControl 8 }

		
		-- 1.3.6.1.4.1.10428 9 1.101.20.6.2.9
		fkEponAlarmControlLlidMismatch OBJECT-TYPE
			SYNTAX EnableFlag
			MAX-ACCESS read-write
			STATUS current
			DESCRIPTION
				"disable(1), enable(2)"
			DEFVAL { enable }
			::= { fkEponAlarmControl 9 }

		
		-- 1.3.6.1.4.1.10428 9 1.101.20.6.2.10
		fkEponAlarmControlOnuRegistrationError OBJECT-TYPE
			SYNTAX EnableFlag
			MAX-ACCESS read-write
			STATUS current
			DESCRIPTION
				"disable(1), enable(2)"
			DEFVAL { enable }
			::= { fkEponAlarmControl 10 }

		
		-- 1.3.6.1.4.1.10428 9 1.101.20.6.2.11
		fkEponAlarmControlTooManyOnuRegistration OBJECT-TYPE
			SYNTAX EnableFlag
			MAX-ACCESS read-write
			STATUS current
			DESCRIPTION
				"disable(1), enable(2)"
			DEFVAL { enable }
			::= { fkEponAlarmControl 11 }

		
		-- 1.3.6.1.4.1.10428 9 1.101.20.6.2.12
		fkEponAlarmControlOpticSignalError OBJECT-TYPE
			SYNTAX EnableFlag
			MAX-ACCESS read-write
			STATUS current
			DESCRIPTION
				"disable(1), enable(2)"
			DEFVAL { enable }
			::= { fkEponAlarmControl 12 }

		
		-- 1.3.6.1.4.1.10428 9 1.101.20.6.2.13
		fkEponAlarmControlStandardLinkFault OBJECT-TYPE
			SYNTAX EnableFlag
			MAX-ACCESS read-write
			STATUS current
			DESCRIPTION
				"disable(1), enable(2)"
			DEFVAL { enable }
			::= { fkEponAlarmControl 13 }

		
		-- 1.3.6.1.4.1.10428 9 1.101.20.6.2.14
		fkEponAlarmControlLossOfSignal OBJECT-TYPE
			SYNTAX EnableFlag
			MAX-ACCESS read-write
			STATUS current
			DESCRIPTION
				"disable(1), enable(2)"
			DEFVAL { enable }
			::= { fkEponAlarmControl 14 }

		
		-- 1.3.6.1.4.1.10428 9 1.101.20.6.2.15
		fkEponAlarmControlTransmitFail OBJECT-TYPE
			SYNTAX EnableFlag
			MAX-ACCESS read-write
			STATUS current
			DESCRIPTION
				"disable(1), enable(2)"
			DEFVAL { enable }
			::= { fkEponAlarmControl 15 }

		
		-- 1.3.6.1.4.1.10428 9 1.101.20.6.2.16
		fkEponAlarmControlMacLearningOverflow OBJECT-TYPE
			SYNTAX EnableFlag
			MAX-ACCESS read-write
			STATUS current
			DESCRIPTION
				"disable(1), enable(2)"
			DEFVAL { enable }
			::= { fkEponAlarmControl 16 }

		
		-- 1.3.6.1.4.1.10428 9 1.101.20.6.2.17
		fkEponAlarmControlLoopback OBJECT-TYPE
			SYNTAX EnableFlag
			MAX-ACCESS read-write
			STATUS current
			DESCRIPTION
				"disable(1), enable(2)"
			DEFVAL { enable }
			::= { fkEponAlarmControl 17 }

		
		-- 1.3.6.1.4.1.10428 9 1.101.20.6.2.18
		fkEponAlarmControlStandardDyingGasp OBJECT-TYPE
			SYNTAX EnableFlag
			MAX-ACCESS read-write
			STATUS current
			DESCRIPTION
				"disable(1), enable(2)"
			DEFVAL { enable }
			::= { fkEponAlarmControl 18 }

		
		-- 1.3.6.1.4.1.10428 9 1.101.20.6.2.19
		fkEponAlarmControlExternalDyingGasp OBJECT-TYPE
			SYNTAX EnableFlag
			MAX-ACCESS read-write
			STATUS current
			DESCRIPTION
				"disable(1), enable(2)"
			DEFVAL { enable }
			::= { fkEponAlarmControl 19 }

		
		-- 1.3.6.1.4.1.10428 9 1.101.20.6.2.20
		fkEponAlarmControlStandardCriticalevent OBJECT-TYPE
			SYNTAX EnableFlag
			MAX-ACCESS read-write
			STATUS current
			DESCRIPTION
				"disable(1), enable(2)"
			DEFVAL { enable }
			::= { fkEponAlarmControl 20 }

		
		-- 1.3.6.1.4.1.10428 9 1.101.20.6.2.21
		fkEponAlarmControlExternalCriticalEvent OBJECT-TYPE
			SYNTAX EnableFlag
			MAX-ACCESS read-write
			STATUS current
			DESCRIPTION
				"disable(1), enable(2)"
			DEFVAL { enable }
			::= { fkEponAlarmControl 21 }

		
		-- 1.3.6.1.4.1.10428 9 1.101.20.6.2.22
		fkEponAlarmControlEponStandbyLos OBJECT-TYPE
			SYNTAX EnableFlag
			MAX-ACCESS read-write
			STATUS current
			DESCRIPTION
				"disable(1), enable(2)"
			DEFVAL { enable }
			::= { fkEponAlarmControl 22 }

		
		-- 1.3.6.1.4.1.10428 9 1.101.20.6.3
		fkEponAlarmNotification OBJECT IDENTIFIER ::= { fkEponAlarm 3 }

		
		-- 1.3.6.1.4.1.10428 9 1.101.20.6.3.1
		fkEponAlarmProfileChanged NOTIFICATION-TYPE
			OBJECTS { fkEponAlarmControlRequest, fkEponAlarmControlTimeStamp, fkEponAlarmControlReqResult, fkEponAlarmControlOltIndex }
			STATUS current
			DESCRIPTION 
				"alarm profile changed trap"
			::= { fkEponAlarmNotification 1 }

		
		-- 1.3.6.1.4.1.10428 9 1.101.20.6.3.2
		fkEponAlarmChanged NOTIFICATION-TYPE
			OBJECTS { fkEponAlarmControlRequest, fkEponAlarmControlTimeStamp, fkEponAlarmControlReqResult }
			STATUS current
			DESCRIPTION 
				"alarm changed trap"
			::= { fkEponAlarmNotification 2 }

		
		-- 1.3.6.1.4.1.10428 9 1.101.20.7
		fkEponStatistics OBJECT IDENTIFIER ::= { fkEpon 7 }

		
		-- 1.3.6.1.4.1.10428 9 1.101.20.7.1
		fkEponOltStatistics OBJECT IDENTIFIER ::= { fkEponStatistics 1 }

		
		-- 1.3.6.1.4.1.10428 9 1.101.20.7.1.1
		fkEponStatsOltTable OBJECT-TYPE
			SYNTAX SEQUENCE OF FkEponStatsOltEntry
			MAX-ACCESS not-accessible
			STATUS current
			DESCRIPTION
				"Description."
			::= { fkEponOltStatistics 1 }

		
		-- 1.3.6.1.4.1.10428 9 1.101.20.7.1.1.1
		fkEponStatsOltEntry OBJECT-TYPE
			SYNTAX FkEponStatsOltEntry
			MAX-ACCESS not-accessible
			STATUS current
			DESCRIPTION
				"Description."
			INDEX { fkEponOltIndex }
			::= { fkEponStatsOltTable 1 }

		
		FkEponStatsOltEntry ::=
			SEQUENCE { 
				fkEponStatsOltInOctets
					Counter64,
				fkEponStatsOltInPkts
					Counter32,
				fkEponStatsOltInPause
					Counter32,
				fkEponStatsOltInErroredFrame
					Counter32,
				fkEponStatsOltInUnicastPkts
					Counter32,
				fkEponstatsOltInBroadcastPkts
					Counter32,
				fkEponStatsOltInMulticastPkts
					Counter32,
				fkEponStatsOltOutOctets
					Counter64,
				fkEponStatsOltOutPkts
					Counter32,
				fkEponStatsOltOutPause
					Counter32,
				fkEponStatsOltOutDropped
					Counter32,
				fkEponStatsOltOutUnicastPkts
					Counter32,
				fkEponstatsOltOutBroadcastPkts
					Counter32,
				fkEponStatsOltOutMulticastPkts
					Counter32,
				fkEponStatsOltHostFrame
					Counter32,
				fkEponStatsOltInTooLongFrame
					Counter32,
				fkEponStatsOltHostFrameDropped
					Counter32
			 }

		-- 1.3.6.1.4.1.10428 9 1.101.20.7.1.1.1.1
		fkEponStatsOltInOctets OBJECT-TYPE
			SYNTAX Counter64
			MAX-ACCESS read-only
			STATUS current
			DESCRIPTION
				"The total number of octets received on the switch side"
			::= { fkEponStatsOltEntry 1 }

		
		-- 1.3.6.1.4.1.10428 9 1.101.20.7.1.1.1.2
		fkEponStatsOltInPkts OBJECT-TYPE
			SYNTAX Counter32
			MAX-ACCESS read-only
			STATUS current
			DESCRIPTION
				"The total number of packets received on the switch side"
			::= { fkEponStatsOltEntry 2 }

		
		-- 1.3.6.1.4.1.10428 9 1.101.20.7.1.1.1.3
		fkEponStatsOltInPause OBJECT-TYPE
			SYNTAX Counter32
			MAX-ACCESS read-only
			STATUS current
			DESCRIPTION
				"The total number of paused packet received on the switch side"
			::= { fkEponStatsOltEntry 3 }

		
		-- 1.3.6.1.4.1.10428 9 1.101.20.7.1.1.1.4
		fkEponStatsOltInErroredFrame OBJECT-TYPE
			SYNTAX Counter32
			MAX-ACCESS read-only
			STATUS current
			DESCRIPTION
				"The total number of errored frame received on the switch side"
			::= { fkEponStatsOltEntry 4 }

		
		-- 1.3.6.1.4.1.10428 9 1.101.20.7.1.1.1.5
		fkEponStatsOltInUnicastPkts OBJECT-TYPE
			SYNTAX Counter32
			MAX-ACCESS read-only
			STATUS current
			DESCRIPTION
				"The total number of unicast packets received on the switch side"
			::= { fkEponStatsOltEntry 5 }

		
		-- 1.3.6.1.4.1.10428 9 1.101.20.7.1.1.1.6
		fkEponstatsOltInBroadcastPkts OBJECT-TYPE
			SYNTAX Counter32
			MAX-ACCESS read-only
			STATUS current
			DESCRIPTION
				"The total number of broadcast packets received on the switch side"
			::= { fkEponStatsOltEntry 6 }

		
		-- 1.3.6.1.4.1.10428 9 1.101.20.7.1.1.1.7
		fkEponStatsOltInMulticastPkts OBJECT-TYPE
			SYNTAX Counter32
			MAX-ACCESS read-only
			STATUS current
			DESCRIPTION
				"The total number of multicast packets received on the switch side"
			::= { fkEponStatsOltEntry 7 }

		
		-- 1.3.6.1.4.1.10428 9 1.101.20.7.1.1.1.8
		fkEponStatsOltOutOctets OBJECT-TYPE
			SYNTAX Counter64
			MAX-ACCESS read-only
			STATUS current
			DESCRIPTION
				"The total number of octets transmitted out of the switch side"
			::= { fkEponStatsOltEntry 8 }

		
		-- 1.3.6.1.4.1.10428 9 1.101.20.7.1.1.1.9
		fkEponStatsOltOutPkts OBJECT-TYPE
			SYNTAX Counter32
			MAX-ACCESS read-only
			STATUS current
			DESCRIPTION
				"The total number of packets transmitted out of the switch side"
			::= { fkEponStatsOltEntry 9 }

		
		-- 1.3.6.1.4.1.10428 9 1.101.20.7.1.1.1.10
		fkEponStatsOltOutPause OBJECT-TYPE
			SYNTAX Counter32
			MAX-ACCESS read-only
			STATUS current
			DESCRIPTION
				"The total number of paused packets transmitted out of the switch side"
			::= { fkEponStatsOltEntry 10 }

		
		-- 1.3.6.1.4.1.10428 9 1.101.20.7.1.1.1.11
		fkEponStatsOltOutDropped OBJECT-TYPE
			SYNTAX Counter32
			MAX-ACCESS read-only
			STATUS current
			DESCRIPTION
				"The total number of droped packets transmitted out of the switch side"
			::= { fkEponStatsOltEntry 11 }

		
		-- 1.3.6.1.4.1.10428 9 1.101.20.7.1.1.1.12
		fkEponStatsOltOutUnicastPkts OBJECT-TYPE
			SYNTAX Counter32
			MAX-ACCESS read-only
			STATUS current
			DESCRIPTION
				"The total number of unicast packets transmitted out of the switch side"
			::= { fkEponStatsOltEntry 12 }

		
		-- 1.3.6.1.4.1.10428 9 1.101.20.7.1.1.1.13
		fkEponstatsOltOutBroadcastPkts OBJECT-TYPE
			SYNTAX Counter32
			MAX-ACCESS read-only
			STATUS current
			DESCRIPTION
				"The total number of broadcast packets transmitted out of the switch side"
			::= { fkEponStatsOltEntry 13 }

		
		-- 1.3.6.1.4.1.10428 9 1.101.20.7.1.1.1.14
		fkEponStatsOltOutMulticastPkts OBJECT-TYPE
			SYNTAX Counter32
			MAX-ACCESS read-only
			STATUS current
			DESCRIPTION
				"The total number of multicast packets transmitted out of the switch side"
			::= { fkEponStatsOltEntry 14 }

		
		-- 1.3.6.1.4.1.10428 9 1.101.20.7.1.1.1.15
		fkEponStatsOltHostFrame OBJECT-TYPE
			SYNTAX Counter32
			MAX-ACCESS read-only
			STATUS current
			DESCRIPTION
				"The total number of host frame received on the switch side."
			::= { fkEponStatsOltEntry 15 }

		
		-- 1.3.6.1.4.1.10428 9 1.101.20.7.1.1.1.16
		fkEponStatsOltInTooLongFrame OBJECT-TYPE
			SYNTAX Counter32
			MAX-ACCESS read-only
			STATUS current
			DESCRIPTION
				"The total number of too long frame received on the switch side."
			::= { fkEponStatsOltEntry 16 }

		
		-- 1.3.6.1.4.1.10428 9 1.101.20.7.1.1.1.17
		fkEponStatsOltHostFrameDropped OBJECT-TYPE
			SYNTAX Counter32
			MAX-ACCESS read-write
			STATUS current
			DESCRIPTION
				"The total number of droped frame transmitted out of the switch side."
			::= { fkEponStatsOltEntry 17 }

		
		-- 1.3.6.1.4.1.10428 9 1.101.20.7.1.2
		fkEponStatsOltPonTable OBJECT-TYPE
			SYNTAX SEQUENCE OF FkEponStatsOltPonEntry
			MAX-ACCESS not-accessible
			STATUS current
			DESCRIPTION
				"Description."
			::= { fkEponOltStatistics 2 }

		
		-- 1.3.6.1.4.1.10428 9 1.101.20.7.1.2.1
		fkEponStatsOltPonEntry OBJECT-TYPE
			SYNTAX FkEponStatsOltPonEntry
			MAX-ACCESS not-accessible
			STATUS current
			DESCRIPTION
				"Description."
			INDEX { fkEponOltIndex }
			::= { fkEponStatsOltPonTable 1 }

		
		FkEponStatsOltPonEntry ::=
			SEQUENCE { 
				fkEponStatsOltPonInOctets
					Counter64,
				fkEponStatsOltPonInPkts
					Counter32,
				fkEponStatsOltPonInPause
					Counter32,
				fkEponStatsOltPonInErroredFrame
					Counter32,
				fkEponStatsOltPonInUnicastPkts
					Counter32,
				fkEponstatsOltPonInBroadcastPkts
					Counter32,
				fkEponStatsOltPonInMulticastPkts
					Counter32,
				fkEponStatsOltPonOutOctets
					Counter64,
				fkEponStatsOltPonOutPkts
					Counter32,
				fkEponStatsOltPonOutPause
					Counter32,
				fkEponStatsOltPonOutDropped
					Counter32,
				fkEponStatsOltPonOutUnicastPkts
					Counter32,
				fkEponstatsOltPonOutBroadcastPkts
					Counter32,
				fkEponStatsOltPonOutMulticastPkts
					Counter32,
				fkEponStatsOltPonInHostFrame
					Counter32,
				fkEponStatsOltPonInTooLongFrame
					Counter32,
				fkEponStatsOltPonInHostFrameDropped
					Counter32,
				fkEponStatsOltPonInHECErrorFrame
					Counter32
			 }

		-- 1.3.6.1.4.1.10428 9 1.101.20.7.1.2.1.1
		fkEponStatsOltPonInOctets OBJECT-TYPE
			SYNTAX Counter64
			MAX-ACCESS read-only
			STATUS current
			DESCRIPTION
				"The total number of octets received on the OLT side"
			::= { fkEponStatsOltPonEntry 1 }

		
		-- 1.3.6.1.4.1.10428 9 1.101.20.7.1.2.1.2
		fkEponStatsOltPonInPkts OBJECT-TYPE
			SYNTAX Counter32
			MAX-ACCESS read-only
			STATUS current
			DESCRIPTION
				"The total number of packets received on the OLT side"
			::= { fkEponStatsOltPonEntry 2 }

		
		-- 1.3.6.1.4.1.10428 9 1.101.20.7.1.2.1.3
		fkEponStatsOltPonInPause OBJECT-TYPE
			SYNTAX Counter32
			MAX-ACCESS read-only
			STATUS current
			DESCRIPTION
				"The total number of paused packet received on the OLT side"
			::= { fkEponStatsOltPonEntry 3 }

		
		-- 1.3.6.1.4.1.10428 9 1.101.20.7.1.2.1.4
		fkEponStatsOltPonInErroredFrame OBJECT-TYPE
			SYNTAX Counter32
			MAX-ACCESS read-only
			STATUS current
			DESCRIPTION
				"The total number of errored frame received on the OLT side"
			::= { fkEponStatsOltPonEntry 4 }

		
		-- 1.3.6.1.4.1.10428 9 1.101.20.7.1.2.1.5
		fkEponStatsOltPonInUnicastPkts OBJECT-TYPE
			SYNTAX Counter32
			MAX-ACCESS read-only
			STATUS current
			DESCRIPTION
				"The total number of unicast packets received on the OLT side"
			::= { fkEponStatsOltPonEntry 5 }

		
		-- 1.3.6.1.4.1.10428 9 1.101.20.7.1.2.1.6
		fkEponstatsOltPonInBroadcastPkts OBJECT-TYPE
			SYNTAX Counter32
			MAX-ACCESS read-only
			STATUS current
			DESCRIPTION
				"The total number of broadcast packets received on the OLT side"
			::= { fkEponStatsOltPonEntry 6 }

		
		-- 1.3.6.1.4.1.10428 9 1.101.20.7.1.2.1.7
		fkEponStatsOltPonInMulticastPkts OBJECT-TYPE
			SYNTAX Counter32
			MAX-ACCESS read-only
			STATUS current
			DESCRIPTION
				"The total number of multicast packets received on the OLT side"
			::= { fkEponStatsOltPonEntry 7 }

		
		-- 1.3.6.1.4.1.10428 9 1.101.20.7.1.2.1.8
		fkEponStatsOltPonOutOctets OBJECT-TYPE
			SYNTAX Counter64
			MAX-ACCESS read-only
			STATUS current
			DESCRIPTION
				"The total number of octets transmitted out of the OLT side"
			::= { fkEponStatsOltPonEntry 8 }

		
		-- 1.3.6.1.4.1.10428 9 1.101.20.7.1.2.1.9
		fkEponStatsOltPonOutPkts OBJECT-TYPE
			SYNTAX Counter32
			MAX-ACCESS read-only
			STATUS current
			DESCRIPTION
				"The total number of packets transmitted out of the OLT side"
			::= { fkEponStatsOltPonEntry 9 }

		
		-- 1.3.6.1.4.1.10428 9 1.101.20.7.1.2.1.10
		fkEponStatsOltPonOutPause OBJECT-TYPE
			SYNTAX Counter32
			MAX-ACCESS read-only
			STATUS current
			DESCRIPTION
				"The total number of paused packets transmitted out of the OLT side"
			::= { fkEponStatsOltPonEntry 10 }

		
		-- 1.3.6.1.4.1.10428 9 1.101.20.7.1.2.1.11
		fkEponStatsOltPonOutDropped OBJECT-TYPE
			SYNTAX Counter32
			MAX-ACCESS read-only
			STATUS current
			DESCRIPTION
				"The total number of droped packets transmitted out of the OLT side"
			::= { fkEponStatsOltPonEntry 11 }

		
		-- 1.3.6.1.4.1.10428 9 1.101.20.7.1.2.1.12
		fkEponStatsOltPonOutUnicastPkts OBJECT-TYPE
			SYNTAX Counter32
			MAX-ACCESS read-only
			STATUS current
			DESCRIPTION
				"The total number of unicast packets transmitted out of the OLT side"
			::= { fkEponStatsOltPonEntry 12 }

		
		-- 1.3.6.1.4.1.10428 9 1.101.20.7.1.2.1.13
		fkEponstatsOltPonOutBroadcastPkts OBJECT-TYPE
			SYNTAX Counter32
			MAX-ACCESS read-only
			STATUS current
			DESCRIPTION
				"The total number of broadcast packets transmitted out of the OLT side"
			::= { fkEponStatsOltPonEntry 13 }

		
		-- 1.3.6.1.4.1.10428 9 1.101.20.7.1.2.1.14
		fkEponStatsOltPonOutMulticastPkts OBJECT-TYPE
			SYNTAX Counter32
			MAX-ACCESS read-only
			STATUS current
			DESCRIPTION
				"The total number of multicast packets transmitted out of the OLT side"
			::= { fkEponStatsOltPonEntry 14 }

		
		-- 1.3.6.1.4.1.10428 9 1.101.20.7.1.2.1.15
		fkEponStatsOltPonInHostFrame OBJECT-TYPE
			SYNTAX Counter32
			MAX-ACCESS read-only
			STATUS current
			DESCRIPTION
				"The total number of frame received on the OLT side."
			::= { fkEponStatsOltPonEntry 15 }

		
		-- 1.3.6.1.4.1.10428 9 1.101.20.7.1.2.1.16
		fkEponStatsOltPonInTooLongFrame OBJECT-TYPE
			SYNTAX Counter32
			MAX-ACCESS read-only
			STATUS current
			DESCRIPTION
				"The total number of long frame received on the OLT side."
			::= { fkEponStatsOltPonEntry 16 }

		
		-- 1.3.6.1.4.1.10428 9 1.101.20.7.1.2.1.17
		fkEponStatsOltPonInHostFrameDropped OBJECT-TYPE
			SYNTAX Counter32
			MAX-ACCESS read-only
			STATUS current
			DESCRIPTION
				"The total number of droped frame received on the OLT side."
			::= { fkEponStatsOltPonEntry 17 }

		
		-- 1.3.6.1.4.1.10428 9 1.101.20.7.1.2.1.18
		fkEponStatsOltPonInHECErrorFrame OBJECT-TYPE
			SYNTAX Counter32
			MAX-ACCESS read-only
			STATUS current
			DESCRIPTION
				"The total number of HEC error frame received on the OLT side."
			::= { fkEponStatsOltPonEntry 18 }

		
		-- 1.3.6.1.4.1.10428 9 1.101.20.7.1.3
		fkEponStatsOltChannelTable OBJECT-TYPE
			SYNTAX SEQUENCE OF FkEponStatsOltChannelEntry
			MAX-ACCESS not-accessible
			STATUS current
			DESCRIPTION
				"Description."
			::= { fkEponOltStatistics 3 }

		
		-- 1.3.6.1.4.1.10428 9 1.101.20.7.1.3.1
		fkEponStatsOltChannelEntry OBJECT-TYPE
			SYNTAX FkEponStatsOltChannelEntry
			MAX-ACCESS not-accessible
			STATUS current
			DESCRIPTION
				"Description."
			INDEX { fkEponOltIndex, fkEponOnuIndex }
			::= { fkEponStatsOltChannelTable 1 }

		
		FkEponStatsOltChannelEntry ::=
			SEQUENCE { 
				fkEponStatsOltChannelInOctets
					Counter64,
				fkEponStatsOltChannelInDataOctets
					Counter64,
				fkEponStatsOltChannelInPkts
					Counter32,
				fkEponStatsOltChannelInMulticastPkts
					Counter32,
				fkEponStatsOltChannelInBroadcastPkts
					Counter32,
				fkEponStatsOltChannelInErrorOctets
					Counter32,
				fkEponStatsOltChannelInErrorPkts
					Counter32,
				fkEponStatsOltChannelOutOctets
					Counter64,
				fkEponStatsOltChannelOutPkts
					Counter32,
				fkEponStatsOltChannelOutPolicerDroppedPkts
					Counter32,
				fkEponStatsOltChannelOutMismatchDroppedPkts
					Counter32,
				fkEponStatsOltChannelOutMulticastPkts
					Counter32,
				fkEponStatsOltChannelOutBroadcastPkts
					Counter32,
				fkEponStatsOltChannelFCS
					Counter32,
				fkEponStatsOltChannelInRangeLengthErrors
					Counter32,
				fkEponStatsOltChannelFrameTooLongErrors
					Counter32,
				fkEponStatsOltChannelInUnicastPkts
					Counter32,
				fkEponStatsOltChannelOutUnicastPkts
					Counter32
			 }

		-- 1.3.6.1.4.1.10428 9 1.101.20.7.1.3.1.1
		fkEponStatsOltChannelInOctets OBJECT-TYPE
			SYNTAX Counter64
			MAX-ACCESS read-only
			STATUS current
			DESCRIPTION
				"The total number of octets received on the ONU side"
			::= { fkEponStatsOltChannelEntry 1 }

		
		-- 1.3.6.1.4.1.10428 9 1.101.20.7.1.3.1.2
		fkEponStatsOltChannelInDataOctets OBJECT-TYPE
			SYNTAX Counter64
			MAX-ACCESS read-only
			STATUS current
			DESCRIPTION
				"The total number of  data octets received on the ONU side"
			::= { fkEponStatsOltChannelEntry 2 }

		
		-- 1.3.6.1.4.1.10428 9 1.101.20.7.1.3.1.3
		fkEponStatsOltChannelInPkts OBJECT-TYPE
			SYNTAX Counter32
			MAX-ACCESS read-only
			STATUS current
			DESCRIPTION
				"The total number of packets transmitted out of the ONU side"
			::= { fkEponStatsOltChannelEntry 3 }

		
		-- 1.3.6.1.4.1.10428 9 1.101.20.7.1.3.1.4
		fkEponStatsOltChannelInMulticastPkts OBJECT-TYPE
			SYNTAX Counter32
			MAX-ACCESS read-only
			STATUS current
			DESCRIPTION
				"The total number of multicast packets received on the ONU side"
			::= { fkEponStatsOltChannelEntry 4 }

		
		-- 1.3.6.1.4.1.10428 9 1.101.20.7.1.3.1.5
		fkEponStatsOltChannelInBroadcastPkts OBJECT-TYPE
			SYNTAX Counter32
			MAX-ACCESS read-only
			STATUS current
			DESCRIPTION
				"The total number of broadcast packets received on the ONU side"
			::= { fkEponStatsOltChannelEntry 5 }

		
		-- 1.3.6.1.4.1.10428 9 1.101.20.7.1.3.1.6
		fkEponStatsOltChannelInErrorOctets OBJECT-TYPE
			SYNTAX Counter32
			MAX-ACCESS read-only
			STATUS current
			DESCRIPTION
				"The total number of errored octets received on the ONU side"
			::= { fkEponStatsOltChannelEntry 6 }

		
		-- 1.3.6.1.4.1.10428 9 1.101.20.7.1.3.1.7
		fkEponStatsOltChannelInErrorPkts OBJECT-TYPE
			SYNTAX Counter32
			MAX-ACCESS read-only
			STATUS current
			DESCRIPTION
				"The total number of errored packets received on the ONU side"
			::= { fkEponStatsOltChannelEntry 7 }

		
		-- 1.3.6.1.4.1.10428 9 1.101.20.7.1.3.1.8
		fkEponStatsOltChannelOutOctets OBJECT-TYPE
			SYNTAX Counter64
			MAX-ACCESS read-only
			STATUS current
			DESCRIPTION
				"The total number of octets transmitted out of the ONU side"
			::= { fkEponStatsOltChannelEntry 8 }

		
		-- 1.3.6.1.4.1.10428 9 1.101.20.7.1.3.1.9
		fkEponStatsOltChannelOutPkts OBJECT-TYPE
			SYNTAX Counter32
			MAX-ACCESS read-only
			STATUS current
			DESCRIPTION
				"The total number of packets transmitted out of the ONU side"
			::= { fkEponStatsOltChannelEntry 9 }

		
		-- 1.3.6.1.4.1.10428 9 1.101.20.7.1.3.1.10
		fkEponStatsOltChannelOutPolicerDroppedPkts OBJECT-TYPE
			SYNTAX Counter32
			MAX-ACCESS read-only
			STATUS current
			DESCRIPTION
				"The total number of policer dropped transmitted out of the ONU side"
			::= { fkEponStatsOltChannelEntry 10 }

		
		-- 1.3.6.1.4.1.10428 9 1.101.20.7.1.3.1.11
		fkEponStatsOltChannelOutMismatchDroppedPkts OBJECT-TYPE
			SYNTAX Counter32
			MAX-ACCESS read-only
			STATUS current
			DESCRIPTION
				"The total number of mismatch dropped packets transmitted out of the ONU side"
			::= { fkEponStatsOltChannelEntry 11 }

		
		-- 1.3.6.1.4.1.10428 9 1.101.20.7.1.3.1.12
		fkEponStatsOltChannelOutMulticastPkts OBJECT-TYPE
			SYNTAX Counter32
			MAX-ACCESS read-only
			STATUS current
			DESCRIPTION
				"The total number of multicast packets transmitted out of the ONU side"
			::= { fkEponStatsOltChannelEntry 12 }

		
		-- 1.3.6.1.4.1.10428 9 1.101.20.7.1.3.1.13
		fkEponStatsOltChannelOutBroadcastPkts OBJECT-TYPE
			SYNTAX Counter32
			MAX-ACCESS read-only
			STATUS current
			DESCRIPTION
				"The total number of broadcast packets transmitted out of the ONU side"
			::= { fkEponStatsOltChannelEntry 13 }

		
		-- 1.3.6.1.4.1.10428 9 1.101.20.7.1.3.1.14
		fkEponStatsOltChannelFCS OBJECT-TYPE
			SYNTAX Counter32
			MAX-ACCESS read-only
			STATUS current
			DESCRIPTION
				"The total number of FCS transmitted out of the ONU side"
			::= { fkEponStatsOltChannelEntry 14 }

		
		-- 1.3.6.1.4.1.10428 9 1.101.20.7.1.3.1.15
		fkEponStatsOltChannelInRangeLengthErrors OBJECT-TYPE
			SYNTAX Counter32
			MAX-ACCESS read-only
			STATUS current
			DESCRIPTION
				"The total number of range length errors received on th ONU side"
			::= { fkEponStatsOltChannelEntry 15 }

		
		-- 1.3.6.1.4.1.10428 9 1.101.20.7.1.3.1.16
		fkEponStatsOltChannelFrameTooLongErrors OBJECT-TYPE
			SYNTAX Counter32
			MAX-ACCESS read-only
			STATUS current
			DESCRIPTION
				"The total number of frame to long errors on the ONU side"
			::= { fkEponStatsOltChannelEntry 16 }

		
		-- 1.3.6.1.4.1.10428 9 1.101.20.7.1.3.1.17
		fkEponStatsOltChannelInUnicastPkts OBJECT-TYPE
			SYNTAX Counter32
			MAX-ACCESS read-only
			STATUS current
			DESCRIPTION
				"The total number of unicast packets received on the ONU side"
			::= { fkEponStatsOltChannelEntry 17 }

		
		-- 1.3.6.1.4.1.10428 9 1.101.20.7.1.3.1.18
		fkEponStatsOltChannelOutUnicastPkts OBJECT-TYPE
			SYNTAX Counter32
			MAX-ACCESS read-only
			STATUS current
			DESCRIPTION
				"The total number of unicast packets transmitted out of the ONU side"
			::= { fkEponStatsOltChannelEntry 18 }

		
		-- 1.3.6.1.4.1.10428 9 1.101.20.7.1.4
		fkEponStatsOltControl OBJECT IDENTIFIER ::= { fkEponOltStatistics 4 }

		
		-- 1.3.6.1.4.1.10428 9 1.101.20.7.1.4.1
		fkEponStatsOltControlRequest OBJECT-TYPE
			SYNTAX INTEGER
				{
				clearEponStatsOlt(1),
				clearEponStatsOltChannel(2),
				clearEponStatsAll(3)
				}
			MAX-ACCESS read-write
			STATUS current
			DESCRIPTION
				"The request of a user command"
			::= { fkEponStatsOltControl 1 }

		
		-- 1.3.6.1.4.1.10428 9 1.101.20.7.1.4.2
		fkEponStatsOltControlStatus OBJECT-TYPE
			SYNTAX FkControlStatusType
			MAX-ACCESS read-only
			STATUS current
			DESCRIPTION
				"The status of user command"
			::= { fkEponStatsOltControl 2 }

		
		-- 1.3.6.1.4.1.10428 9 1.101.20.7.1.4.3
		fkEponStatsOltControlTimer OBJECT-TYPE
			SYNTAX Gauge32
			MAX-ACCESS read-write
			STATUS current
			DESCRIPTION
				"The maximum time for the manager for a long running user command"
			::= { fkEponStatsOltControl 3 }

		
		-- 1.3.6.1.4.1.10428 9 1.101.20.7.1.4.4
		fkEponStatsOltControlTimeStamp OBJECT-TYPE
			SYNTAX TimeTicks
			MAX-ACCESS read-only
			STATUS current
			DESCRIPTION
				"The time stamp of the last command(end of command)"
			::= { fkEponStatsOltControl 4 }

		
		-- 1.3.6.1.4.1.10428 9 1.101.20.7.1.4.5
		fkEponStatsOltControlReqResult OBJECT-TYPE
			SYNTAX FkControlRequestResultType
			MAX-ACCESS read-only
			STATUS current
			DESCRIPTION
				"The result of the last user command"
			::= { fkEponStatsOltControl 5 }

		
		-- 1.3.6.1.4.1.10428 9 1.101.20.7.1.4.6
		fkEponStatsOltControlOltIndex OBJECT-TYPE
			SYNTAX INTEGER (1..512)
			MAX-ACCESS read-write
			STATUS current
			DESCRIPTION
				"OLT index"
			::= { fkEponStatsOltControl 6 }

		
		-- 1.3.6.1.4.1.10428 9 1.101.20.7.1.4.7
		fkEponStatsOltControlChannelIndex OBJECT-TYPE
			SYNTAX INTEGER (1..32)
			MAX-ACCESS read-write
			STATUS current
			DESCRIPTION
				"ONU index"
			::= { fkEponStatsOltControl 7 }

		
		-- 1.3.6.1.4.1.10428 9 1.101.20.7.1.5
		fkEponStatsOltNotification OBJECT IDENTIFIER ::= { fkEponOltStatistics 5 }

		
		-- 1.3.6.1.4.1.10428 9 1.101.20.7.1.5.1
		fkEponstatsOltCleared NOTIFICATION-TYPE
			OBJECTS { fkEponStatsOltControlRequest, fkEponStatsOltControlTimeStamp, fkEponStatsOltControlReqResult, fkEponStatsOltControlOltIndex }
			STATUS current
			DESCRIPTION 
				"Description."
			::= { fkEponStatsOltNotification 1 }

		
		-- 1.3.6.1.4.1.10428 9 1.101.20.7.1.5.2
		fkEponStatsOltChannelCleared NOTIFICATION-TYPE
			OBJECTS { fkEponStatsOltControlRequest, fkEponStatsOltControlTimeStamp, fkEponStatsOltControlReqResult, fkEponStatsOltControlOltIndex, fkEponStatsOltControlChannelIndex
				 }
			STATUS current
			DESCRIPTION 
				"Description."
			::= { fkEponStatsOltNotification 2 }

		
		-- 1.3.6.1.4.1.10428 9 1.101.20.7.1.5.3
		fkEponStatsAllCleared NOTIFICATION-TYPE
			OBJECTS { fkEponStatsOltControlRequest, fkEponStatsOltControlTimeStamp, fkEponStatsOltControlReqResult, fkEponStatsOltControlOltIndex, fkEponStatsOltControlChannelIndex
				 }
			STATUS current
			DESCRIPTION 
				"Description."
			::= { fkEponStatsOltNotification 3 }

		
		-- 1.3.6.1.4.1.10428 9 1.101.20.7.1.6
		fkEponStatsOltFromOnuTable OBJECT-TYPE
			SYNTAX SEQUENCE OF FkEponStatsOltFromOnuEntry
			MAX-ACCESS not-accessible
			STATUS current
			DESCRIPTION
				"Description."
			::= { fkEponOltStatistics 6 }

		
		-- 1.3.6.1.4.1.10428 9 1.101.20.7.1.6.1
		fkEponStatsOltFromOnuEntry OBJECT-TYPE
			SYNTAX FkEponStatsOltFromOnuEntry
			MAX-ACCESS not-accessible
			STATUS current
			DESCRIPTION
				"Olt statistics: from onu."
			INDEX { fkEponOltIndex }
			::= { fkEponStatsOltFromOnuTable 1 }

		
		FkEponStatsOltFromOnuEntry ::=
			SEQUENCE { 
				fkEponStatsOltFromOnuInFrame
					Counter32,
				fkEponStatsOltFromOnuInErrorFrame
					Counter32,
				fkEponStatsOltFromOnuInMulticastFrame
					Counter32,
				fkEponStatsOltFromOnuInBroadcastFrame
					Counter32,
				fkEponStatsOltFromOnuInReportFrame
					Counter32,
				fkEponStatsOltFromOnuInCheckSeqErrorFrame
					Counter32,
				fkEponStatsOltFromOnuInRangeLenErrors
					Counter32,
				fkEponStatsOltFromOnuInTooLongFrame
					Counter32,
				fkEponStatsOltFromOnuOutFrame
					Counter32,
				fkEponStatsOltFromOnuOutFrameBytes
					Counter64,
				fkEponStatsOltFromOnuOutMulticastFrame
					Counter32,
				fkEponStatsOltFromOnuOutBroadcastFrame
					Counter32,
				fkEponStatsOltFromOnuOutDBAGrantFrame
					Counter32,
				fkEponStatsOltFromOnuOutControlGrantFrame
					Counter32
			 }

		-- 1.3.6.1.4.1.10428 9 1.101.20.7.1.6.1.1
		fkEponStatsOltFromOnuInFrame OBJECT-TYPE
			SYNTAX Counter32
			MAX-ACCESS read-only
			STATUS current
			DESCRIPTION
				"The total number of Rx frame."
			::= { fkEponStatsOltFromOnuEntry 1 }

		
		-- 1.3.6.1.4.1.10428 9 1.101.20.7.1.6.1.2
		fkEponStatsOltFromOnuInErrorFrame OBJECT-TYPE
			SYNTAX Counter32
			MAX-ACCESS read-only
			STATUS current
			DESCRIPTION
				"Rx error frame count."
			::= { fkEponStatsOltFromOnuEntry 2 }

		
		-- 1.3.6.1.4.1.10428 9 1.101.20.7.1.6.1.3
		fkEponStatsOltFromOnuInMulticastFrame OBJECT-TYPE
			SYNTAX Counter32
			MAX-ACCESS read-only
			STATUS current
			DESCRIPTION
				"Rx multicast frame count."
			::= { fkEponStatsOltFromOnuEntry 3 }

		
		-- 1.3.6.1.4.1.10428 9 1.101.20.7.1.6.1.4
		fkEponStatsOltFromOnuInBroadcastFrame OBJECT-TYPE
			SYNTAX Counter32
			MAX-ACCESS read-only
			STATUS current
			DESCRIPTION
				"Rx broadcast frame count."
			::= { fkEponStatsOltFromOnuEntry 4 }

		
		-- 1.3.6.1.4.1.10428 9 1.101.20.7.1.6.1.5
		fkEponStatsOltFromOnuInReportFrame OBJECT-TYPE
			SYNTAX Counter32
			MAX-ACCESS read-only
			STATUS current
			DESCRIPTION
				"Rx report frame count."
			::= { fkEponStatsOltFromOnuEntry 5 }

		
		-- 1.3.6.1.4.1.10428 9 1.101.20.7.1.6.1.6
		fkEponStatsOltFromOnuInCheckSeqErrorFrame OBJECT-TYPE
			SYNTAX Counter32
			MAX-ACCESS read-only
			STATUS current
			DESCRIPTION
				"Rx check sequenece error frame count."
			::= { fkEponStatsOltFromOnuEntry 6 }

		
		-- 1.3.6.1.4.1.10428 9 1.101.20.7.1.6.1.7
		fkEponStatsOltFromOnuInRangeLenErrors OBJECT-TYPE
			SYNTAX Counter32
			MAX-ACCESS read-only
			STATUS current
			DESCRIPTION
				"Rx range of length error frame count."
			::= { fkEponStatsOltFromOnuEntry 7 }

		
		-- 1.3.6.1.4.1.10428 9 1.101.20.7.1.6.1.8
		fkEponStatsOltFromOnuInTooLongFrame OBJECT-TYPE
			SYNTAX Counter32
			MAX-ACCESS read-only
			STATUS current
			DESCRIPTION
				"Rx too long frame counts."
			::= { fkEponStatsOltFromOnuEntry 8 }

		
		-- 1.3.6.1.4.1.10428 9 1.101.20.7.1.6.1.9
		fkEponStatsOltFromOnuOutFrame OBJECT-TYPE
			SYNTAX Counter32
			MAX-ACCESS read-only
			STATUS current
			DESCRIPTION
				"Tx frame count."
			::= { fkEponStatsOltFromOnuEntry 9 }

		
		-- 1.3.6.1.4.1.10428 9 1.101.20.7.1.6.1.10
		fkEponStatsOltFromOnuOutFrameBytes OBJECT-TYPE
			SYNTAX Counter64
			MAX-ACCESS read-only
			STATUS current
			DESCRIPTION
				"Tx frame bytes."
			::= { fkEponStatsOltFromOnuEntry 10 }

		
		-- 1.3.6.1.4.1.10428 9 1.101.20.7.1.6.1.11
		fkEponStatsOltFromOnuOutMulticastFrame OBJECT-TYPE
			SYNTAX Counter32
			MAX-ACCESS read-only
			STATUS current
			DESCRIPTION
				"Tx multicast frame count."
			::= { fkEponStatsOltFromOnuEntry 11 }

		
		-- 1.3.6.1.4.1.10428 9 1.101.20.7.1.6.1.12
		fkEponStatsOltFromOnuOutBroadcastFrame OBJECT-TYPE
			SYNTAX Counter32
			MAX-ACCESS read-only
			STATUS current
			DESCRIPTION
				"Tx broadcast frame count."
			::= { fkEponStatsOltFromOnuEntry 12 }

		
		-- 1.3.6.1.4.1.10428 9 1.101.20.7.1.6.1.13
		fkEponStatsOltFromOnuOutDBAGrantFrame OBJECT-TYPE
			SYNTAX Counter32
			MAX-ACCESS read-only
			STATUS current
			DESCRIPTION
				"Tx grant DBA frame count."
			::= { fkEponStatsOltFromOnuEntry 13 }

		
		-- 1.3.6.1.4.1.10428 9 1.101.20.7.1.6.1.14
		fkEponStatsOltFromOnuOutControlGrantFrame OBJECT-TYPE
			SYNTAX Counter32
			MAX-ACCESS read-only
			STATUS current
			DESCRIPTION
				"Tx grant frame count."
			::= { fkEponStatsOltFromOnuEntry 14 }

		
		-- 1.3.6.1.4.1.10428 9 1.101.20.7.2
		fkEponOnuStatistics OBJECT IDENTIFIER ::= { fkEponStatistics 2 }

		
		-- 1.3.6.1.4.1.10428 9 1.101.20.7.2.1
		fkEponStatsOnuPortTable OBJECT-TYPE
			SYNTAX SEQUENCE OF FkEponStatsOnuPortEntry
			MAX-ACCESS not-accessible
			STATUS current
			DESCRIPTION
				"Description."
			::= { fkEponOnuStatistics 1 }

		
		-- 1.3.6.1.4.1.10428 9 1.101.20.7.2.1.1
		fkEponStatsOnuPortEntry OBJECT-TYPE
			SYNTAX FkEponStatsOnuPortEntry
			MAX-ACCESS not-accessible
			STATUS current
			DESCRIPTION
				"Description."
			INDEX { fkEponOltIndex, fkEponOnuIndex, fkEponOnuPortIndex }
			::= { fkEponStatsOnuPortTable 1 }

		
		FkEponStatsOnuPortEntry ::=
			SEQUENCE { 
				fkEponStatsOnuPortInOctets
					Counter64,
				fkEponStatsOnuPortInPkts
					Counter32,
				fkEponStatsOnuPortInUcastPkts
					Counter32,
				fkEponStatsOnuPortInBcastPkts
					Counter32,
				fkEponStatsOnuPortInMcastPkts
					Counter32,
				fkEponStatsOnuPortOutOctets
					Counter64,
				fkEponStatsOnuPortOutPkts
					Counter32,
				fkEponStatsOnuPortOutUcastPkts
					Counter32,
				fkEponStatsOnuPortOutBcastPkts
					Counter32,
				fkEponStatsOnuPortOutMcastPkts
					Counter32,
				fkEponStatsOnuPortInUndersize
					Counter32,
				fkEponStatsOnuPortInOversize
					Counter32,
				fkEponStatsOnuPortInJabber
					Counter32,
				fkEponStatsOnuPortInRxError
					Counter32,
				fkEponStatsOnuPortInRxFcsError
					Counter32
			 }

		-- 1.3.6.1.4.1.10428 9 1.101.20.7.2.1.1.1
		fkEponStatsOnuPortInOctets OBJECT-TYPE
			SYNTAX Counter64
			MAX-ACCESS read-only
			STATUS current
			DESCRIPTION
				"Description."
			::= { fkEponStatsOnuPortEntry 1 }

		
		-- 1.3.6.1.4.1.10428 9 1.101.20.7.2.1.1.2
		fkEponStatsOnuPortInPkts OBJECT-TYPE
			SYNTAX Counter32
			MAX-ACCESS read-only
			STATUS current
			DESCRIPTION
				"Description."
			::= { fkEponStatsOnuPortEntry 2 }

		
		-- 1.3.6.1.4.1.10428 9 1.101.20.7.2.1.1.3
		fkEponStatsOnuPortInUcastPkts OBJECT-TYPE
			SYNTAX Counter32
			MAX-ACCESS read-only
			STATUS current
			DESCRIPTION
				"Description."
			::= { fkEponStatsOnuPortEntry 3 }

		
		-- 1.3.6.1.4.1.10428 9 1.101.20.7.2.1.1.4
		fkEponStatsOnuPortInBcastPkts OBJECT-TYPE
			SYNTAX Counter32
			MAX-ACCESS read-only
			STATUS current
			DESCRIPTION
				"Description."
			::= { fkEponStatsOnuPortEntry 4 }

		
		-- 1.3.6.1.4.1.10428 9 1.101.20.7.2.1.1.5
		fkEponStatsOnuPortInMcastPkts OBJECT-TYPE
			SYNTAX Counter32
			MAX-ACCESS read-only
			STATUS current
			DESCRIPTION
				"Description."
			::= { fkEponStatsOnuPortEntry 5 }

		
		-- 1.3.6.1.4.1.10428 9 1.101.20.7.2.1.1.6
		fkEponStatsOnuPortOutOctets OBJECT-TYPE
			SYNTAX Counter64
			MAX-ACCESS read-only
			STATUS current
			DESCRIPTION
				"Description."
			::= { fkEponStatsOnuPortEntry 6 }

		
		-- 1.3.6.1.4.1.10428 9 1.101.20.7.2.1.1.7
		fkEponStatsOnuPortOutPkts OBJECT-TYPE
			SYNTAX Counter32
			MAX-ACCESS read-only
			STATUS current
			DESCRIPTION
				"Description."
			::= { fkEponStatsOnuPortEntry 7 }

		
		-- 1.3.6.1.4.1.10428 9 1.101.20.7.2.1.1.8
		fkEponStatsOnuPortOutUcastPkts OBJECT-TYPE
			SYNTAX Counter32
			MAX-ACCESS read-only
			STATUS current
			DESCRIPTION
				"Description."
			::= { fkEponStatsOnuPortEntry 8 }

		
		-- 1.3.6.1.4.1.10428 9 1.101.20.7.2.1.1.9
		fkEponStatsOnuPortOutBcastPkts OBJECT-TYPE
			SYNTAX Counter32
			MAX-ACCESS read-only
			STATUS current
			DESCRIPTION
				"Description."
			::= { fkEponStatsOnuPortEntry 9 }

		
		-- 1.3.6.1.4.1.10428 9 1.101.20.7.2.1.1.10
		fkEponStatsOnuPortOutMcastPkts OBJECT-TYPE
			SYNTAX Counter32
			MAX-ACCESS read-only
			STATUS current
			DESCRIPTION
				"Description."
			::= { fkEponStatsOnuPortEntry 10 }

		
		-- 1.3.6.1.4.1.10428 9 1.101.20.7.2.1.1.11
		fkEponStatsOnuPortInUndersize OBJECT-TYPE
			SYNTAX Counter32
			MAX-ACCESS read-only
			STATUS current
			DESCRIPTION
				"Description."
			::= { fkEponStatsOnuPortEntry 11 }

		
		-- 1.3.6.1.4.1.10428 9 1.101.20.7.2.1.1.12
		fkEponStatsOnuPortInOversize OBJECT-TYPE
			SYNTAX Counter32
			MAX-ACCESS read-only
			STATUS current
			DESCRIPTION
				"Description."
			::= { fkEponStatsOnuPortEntry 12 }

		
		-- 1.3.6.1.4.1.10428 9 1.101.20.7.2.1.1.13
		fkEponStatsOnuPortInJabber OBJECT-TYPE
			SYNTAX Counter32
			MAX-ACCESS read-only
			STATUS current
			DESCRIPTION
				"Description."
			::= { fkEponStatsOnuPortEntry 13 }

		
		-- 1.3.6.1.4.1.10428 9 1.101.20.7.2.1.1.14
		fkEponStatsOnuPortInRxError OBJECT-TYPE
			SYNTAX Counter32
			MAX-ACCESS read-only
			STATUS current
			DESCRIPTION
				"Description."
			::= { fkEponStatsOnuPortEntry 14 }

		
		-- 1.3.6.1.4.1.10428 9 1.101.20.7.2.1.1.15
		fkEponStatsOnuPortInRxFcsError OBJECT-TYPE
			SYNTAX Counter32
			MAX-ACCESS read-only
			STATUS current
			DESCRIPTION
				"Description."
			::= { fkEponStatsOnuPortEntry 15 }

		
		-- 1.3.6.1.4.1.10428 9 1.101.20.7.2.2
		fkEponStatsOnuUniTable OBJECT-TYPE
			SYNTAX SEQUENCE OF FkEponStatsOnuUniEntry
			MAX-ACCESS not-accessible
			STATUS current
			DESCRIPTION
				"Description."
			::= { fkEponOnuStatistics 2 }

		
		-- 1.3.6.1.4.1.10428 9 1.101.20.7.2.2.1
		fkEponStatsOnuUniEntry OBJECT-TYPE
			SYNTAX FkEponStatsOnuUniEntry
			MAX-ACCESS not-accessible
			STATUS current
			DESCRIPTION
				"Description."
			INDEX { fkEponOltIndex, fkEponOnuIndex }
			::= { fkEponStatsOnuUniTable 1 }

		
		FkEponStatsOnuUniEntry ::=
			SEQUENCE { 
				fkEponStatsOnuUniInPkts
					Counter32,
				fkEponStatsOnuUniInBytes
					Counter64,
				fkEponStatsOnuUniInErrPkts
					Counter32,
				fkEponStatsOnuUniInErrBytes
					Counter32,
				fkEponStatsOnuUniInPause
					Counter32,
				fkEponStatsOnuUniFrameLongError
					Counter32,
				fkEponStatsOnuUniOutPkts
					Counter32,
				fkEponStatsOnuUniOutBytes
					Counter64,
				fkEponStatsOnuUniOutPause
					Counter32,
				fkEponStatsOnuUniOutDropPkts
					Counter32,
				fkEponStatsOnuUnInMcastPkts
					Counter32,
				fkEponStatsOnuUnInBcastPkts
					Counter32,
				fkEponStatsOnuUniInDropPkts
					Counter32,
				fkEponStatsOnuUniOutMcastPkts
					Counter32,
				fkEponStatsOnuUniOutBcastPkts
					Counter32
			 }

		-- 1.3.6.1.4.1.10428 9 1.101.20.7.2.2.1.1
		fkEponStatsOnuUniInPkts OBJECT-TYPE
			SYNTAX Counter32
			MAX-ACCESS read-only
			STATUS current
			DESCRIPTION
				"Description."
			::= { fkEponStatsOnuUniEntry 1 }

		
		-- 1.3.6.1.4.1.10428 9 1.101.20.7.2.2.1.2
		fkEponStatsOnuUniInBytes OBJECT-TYPE
			SYNTAX Counter64
			MAX-ACCESS read-only
			STATUS current
			DESCRIPTION
				"Description."
			::= { fkEponStatsOnuUniEntry 2 }

		
		-- 1.3.6.1.4.1.10428 9 1.101.20.7.2.2.1.3
		fkEponStatsOnuUniInErrPkts OBJECT-TYPE
			SYNTAX Counter32
			MAX-ACCESS read-only
			STATUS current
			DESCRIPTION
				"Description."
			::= { fkEponStatsOnuUniEntry 3 }

		
		-- 1.3.6.1.4.1.10428 9 1.101.20.7.2.2.1.4
		fkEponStatsOnuUniInErrBytes OBJECT-TYPE
			SYNTAX Counter32
			MAX-ACCESS read-only
			STATUS current
			DESCRIPTION
				"Description."
			::= { fkEponStatsOnuUniEntry 4 }

		
		-- 1.3.6.1.4.1.10428 9 1.101.20.7.2.2.1.5
		fkEponStatsOnuUniInPause OBJECT-TYPE
			SYNTAX Counter32
			MAX-ACCESS read-only
			STATUS current
			DESCRIPTION
				"Description."
			::= { fkEponStatsOnuUniEntry 5 }

		
		-- 1.3.6.1.4.1.10428 9 1.101.20.7.2.2.1.6
		fkEponStatsOnuUniFrameLongError OBJECT-TYPE
			SYNTAX Counter32
			MAX-ACCESS read-only
			STATUS current
			DESCRIPTION
				"Description."
			::= { fkEponStatsOnuUniEntry 6 }

		
		-- 1.3.6.1.4.1.10428 9 1.101.20.7.2.2.1.7
		fkEponStatsOnuUniOutPkts OBJECT-TYPE
			SYNTAX Counter32
			MAX-ACCESS read-only
			STATUS current
			DESCRIPTION
				"Description."
			::= { fkEponStatsOnuUniEntry 7 }

		
		-- 1.3.6.1.4.1.10428 9 1.101.20.7.2.2.1.8
		fkEponStatsOnuUniOutBytes OBJECT-TYPE
			SYNTAX Counter64
			MAX-ACCESS read-only
			STATUS current
			DESCRIPTION
				"Description."
			::= { fkEponStatsOnuUniEntry 8 }

		
		-- 1.3.6.1.4.1.10428 9 1.101.20.7.2.2.1.9
		fkEponStatsOnuUniOutPause OBJECT-TYPE
			SYNTAX Counter32
			MAX-ACCESS read-only
			STATUS current
			DESCRIPTION
				"Description."
			::= { fkEponStatsOnuUniEntry 9 }

		
		-- 1.3.6.1.4.1.10428 9 1.101.20.7.2.2.1.10
		fkEponStatsOnuUniOutDropPkts OBJECT-TYPE
			SYNTAX Counter32
			MAX-ACCESS read-only
			STATUS current
			DESCRIPTION
				"Description."
			::= { fkEponStatsOnuUniEntry 10 }

		
		-- 1.3.6.1.4.1.10428 9 1.101.20.7.2.2.1.11
		fkEponStatsOnuUnInMcastPkts OBJECT-TYPE
			SYNTAX Counter32
			MAX-ACCESS read-only
			STATUS current
			DESCRIPTION
				"The total number of Rx multicast packets on the ONU Uni side."
			::= { fkEponStatsOnuUniEntry 11 }

		
		-- 1.3.6.1.4.1.10428 9 1.101.20.7.2.2.1.12
		fkEponStatsOnuUnInBcastPkts OBJECT-TYPE
			SYNTAX Counter32
			MAX-ACCESS read-only
			STATUS current
			DESCRIPTION
				"The total number of Rx broadcast packets on the ONU Uni side."
			::= { fkEponStatsOnuUniEntry 12 }

		
		-- 1.3.6.1.4.1.10428 9 1.101.20.7.2.2.1.13
		fkEponStatsOnuUniInDropPkts OBJECT-TYPE
			SYNTAX Counter32
			MAX-ACCESS read-only
			STATUS current
			DESCRIPTION
				"The total number of Rx dropped packets on the ONU Uni side."
			::= { fkEponStatsOnuUniEntry 13 }

		
		-- 1.3.6.1.4.1.10428 9 1.101.20.7.2.2.1.14
		fkEponStatsOnuUniOutMcastPkts OBJECT-TYPE
			SYNTAX Counter32
			MAX-ACCESS read-only
			STATUS current
			DESCRIPTION
				"The total number of Tx multicast packets on the ONU Uni side."
			::= { fkEponStatsOnuUniEntry 14 }

		
		-- 1.3.6.1.4.1.10428 9 1.101.20.7.2.2.1.15
		fkEponStatsOnuUniOutBcastPkts OBJECT-TYPE
			SYNTAX Counter32
			MAX-ACCESS read-only
			STATUS current
			DESCRIPTION
				"The total number of Tx braocast packets on the ONU Uni side."
			::= { fkEponStatsOnuUniEntry 15 }

		
		-- 1.3.6.1.4.1.10428 9 1.101.20.7.2.3
		fkEponStatsOnuPonTable OBJECT-TYPE
			SYNTAX SEQUENCE OF FkEponStatsOnuPonEntry
			MAX-ACCESS not-accessible
			STATUS current
			DESCRIPTION
				"Description."
			::= { fkEponOnuStatistics 3 }

		
		-- 1.3.6.1.4.1.10428 9 1.101.20.7.2.3.1
		fkEponStatsOnuPonEntry OBJECT-TYPE
			SYNTAX FkEponStatsOnuPonEntry
			MAX-ACCESS not-accessible
			STATUS current
			DESCRIPTION
				"Description."
			INDEX { fkEponOltIndex, fkEponOnuIndex }
			::= { fkEponStatsOnuPonTable 1 }

		
		FkEponStatsOnuPonEntry ::=
			SEQUENCE { 
				fkEponStatsOnuPonInPkts
					Counter32,
				fkEponStatsOnuPonInBytes
					Counter32,
				fkEponStatsOnuPonInMcastPkts
					Counter32,
				fkEponStatsOnuPonIntBcastPkts
					Counter32,
				fkEponStatsOnuPonInErrPkts
					Counter32,
				fkEponStatsOnuPonInErrBytes
					Counter32,
				fkEponStatsOnuPonInPause
					Counter32,
				fkEponStatsOnuPonInHostPkts
					Counter32,
				fkEponStatsOnuPonInDropHostPkts
					Counter32,
				fkEponStatsOnuPonFrameLongError
					Counter32,
				fkEponStatsOnuPonOutPkts
					Counter32,
				fkEponStatsOnuPonOutBytes
					Counter32,
				fkEponStatsOnuPonOutMcastPkts
					Counter32,
				fkEponStatsOnuPonOutBcastPkts
					Counter32,
				fkEponStatsOnuPonOutPause
					Counter32,
				fkEponStatsOnuPonOutDropPkts
					Counter32,
				fkEponStatsOnuPonOutHostPkts
					Counter32,
				fkEponStatsOnuPonOutChipErrPkts
					Counter32,
				fkEponStatsOnuPonInDropPkts
					Counter32
			 }

		-- 1.3.6.1.4.1.10428 9 1.101.20.7.2.3.1.1
		fkEponStatsOnuPonInPkts OBJECT-TYPE
			SYNTAX Counter32
			MAX-ACCESS read-only
			STATUS current
			DESCRIPTION
				"Description."
			::= { fkEponStatsOnuPonEntry 1 }

		
		-- 1.3.6.1.4.1.10428 9 1.101.20.7.2.3.1.2
		fkEponStatsOnuPonInBytes OBJECT-TYPE
			SYNTAX Counter32
			MAX-ACCESS read-only
			STATUS current
			DESCRIPTION
				"Description."
			::= { fkEponStatsOnuPonEntry 2 }

		
		-- 1.3.6.1.4.1.10428 9 1.101.20.7.2.3.1.3
		fkEponStatsOnuPonInMcastPkts OBJECT-TYPE
			SYNTAX Counter32
			MAX-ACCESS read-only
			STATUS current
			DESCRIPTION
				"Description."
			::= { fkEponStatsOnuPonEntry 3 }

		
		-- 1.3.6.1.4.1.10428 9 1.101.20.7.2.3.1.4
		fkEponStatsOnuPonIntBcastPkts OBJECT-TYPE
			SYNTAX Counter32
			MAX-ACCESS read-only
			STATUS current
			DESCRIPTION
				"Description."
			::= { fkEponStatsOnuPonEntry 4 }

		
		-- 1.3.6.1.4.1.10428 9 1.101.20.7.2.3.1.5
		fkEponStatsOnuPonInErrPkts OBJECT-TYPE
			SYNTAX Counter32
			MAX-ACCESS read-only
			STATUS current
			DESCRIPTION
				"Description."
			::= { fkEponStatsOnuPonEntry 5 }

		
		-- 1.3.6.1.4.1.10428 9 1.101.20.7.2.3.1.6
		fkEponStatsOnuPonInErrBytes OBJECT-TYPE
			SYNTAX Counter32
			MAX-ACCESS read-only
			STATUS current
			DESCRIPTION
				"Description."
			::= { fkEponStatsOnuPonEntry 6 }

		
		-- 1.3.6.1.4.1.10428 9 1.101.20.7.2.3.1.7
		fkEponStatsOnuPonInPause OBJECT-TYPE
			SYNTAX Counter32
			MAX-ACCESS read-only
			STATUS current
			DESCRIPTION
				"Description."
			::= { fkEponStatsOnuPonEntry 7 }

		
		-- 1.3.6.1.4.1.10428 9 1.101.20.7.2.3.1.8
		fkEponStatsOnuPonInHostPkts OBJECT-TYPE
			SYNTAX Counter32
			MAX-ACCESS read-only
			STATUS current
			DESCRIPTION
				"Description."
			::= { fkEponStatsOnuPonEntry 8 }

		
		-- 1.3.6.1.4.1.10428 9 1.101.20.7.2.3.1.9
		fkEponStatsOnuPonInDropHostPkts OBJECT-TYPE
			SYNTAX Counter32
			MAX-ACCESS read-only
			STATUS current
			DESCRIPTION
				"Description."
			::= { fkEponStatsOnuPonEntry 9 }

		
		-- 1.3.6.1.4.1.10428 9 1.101.20.7.2.3.1.10
		fkEponStatsOnuPonFrameLongError OBJECT-TYPE
			SYNTAX Counter32
			MAX-ACCESS read-only
			STATUS current
			DESCRIPTION
				"Description."
			::= { fkEponStatsOnuPonEntry 10 }

		
		-- 1.3.6.1.4.1.10428 9 1.101.20.7.2.3.1.11
		fkEponStatsOnuPonOutPkts OBJECT-TYPE
			SYNTAX Counter32
			MAX-ACCESS read-only
			STATUS current
			DESCRIPTION
				"Description."
			::= { fkEponStatsOnuPonEntry 11 }

		
		-- 1.3.6.1.4.1.10428 9 1.101.20.7.2.3.1.12
		fkEponStatsOnuPonOutBytes OBJECT-TYPE
			SYNTAX Counter32
			MAX-ACCESS read-only
			STATUS current
			DESCRIPTION
				"Description."
			::= { fkEponStatsOnuPonEntry 12 }

		
		-- 1.3.6.1.4.1.10428 9 1.101.20.7.2.3.1.13
		fkEponStatsOnuPonOutMcastPkts OBJECT-TYPE
			SYNTAX Counter32
			MAX-ACCESS read-only
			STATUS current
			DESCRIPTION
				"Description."
			::= { fkEponStatsOnuPonEntry 13 }

		
		-- 1.3.6.1.4.1.10428 9 1.101.20.7.2.3.1.14
		fkEponStatsOnuPonOutBcastPkts OBJECT-TYPE
			SYNTAX Counter32
			MAX-ACCESS read-only
			STATUS current
			DESCRIPTION
				"Description."
			::= { fkEponStatsOnuPonEntry 14 }

		
		-- 1.3.6.1.4.1.10428 9 1.101.20.7.2.3.1.15
		fkEponStatsOnuPonOutPause OBJECT-TYPE
			SYNTAX Counter32
			MAX-ACCESS read-only
			STATUS current
			DESCRIPTION
				"Description."
			::= { fkEponStatsOnuPonEntry 15 }

		
		-- 1.3.6.1.4.1.10428 9 1.101.20.7.2.3.1.16
		fkEponStatsOnuPonOutDropPkts OBJECT-TYPE
			SYNTAX Counter32
			MAX-ACCESS read-only
			STATUS current
			DESCRIPTION
				"Description."
			::= { fkEponStatsOnuPonEntry 16 }

		
		-- 1.3.6.1.4.1.10428 9 1.101.20.7.2.3.1.17
		fkEponStatsOnuPonOutHostPkts OBJECT-TYPE
			SYNTAX Counter32
			MAX-ACCESS read-only
			STATUS current
			DESCRIPTION
				"Description."
			::= { fkEponStatsOnuPonEntry 17 }

		
		-- 1.3.6.1.4.1.10428 9 1.101.20.7.2.3.1.18
		fkEponStatsOnuPonOutChipErrPkts OBJECT-TYPE
			SYNTAX Counter32
			MAX-ACCESS read-only
			STATUS current
			DESCRIPTION
				"Description."
			::= { fkEponStatsOnuPonEntry 18 }

		
		-- 1.3.6.1.4.1.10428 9 1.101.20.7.2.3.1.19
		fkEponStatsOnuPonInDropPkts OBJECT-TYPE
			SYNTAX Counter32
			MAX-ACCESS read-only
			STATUS current
			DESCRIPTION
				"The total number of Rx droped packest received on the ONU Pon side."
			::= { fkEponStatsOnuPonEntry 19 }

		
		-- 1.3.6.1.4.1.10428 9 1.101.20.7.3
		fkEponPerTimeStatistics OBJECT IDENTIFIER ::= { fkEponStatistics 3 }

		
		-- 1.3.6.1.4.1.10428 9 1.101.20.7.3.1
		fkEponPTimeStatsPortTable OBJECT-TYPE
			SYNTAX SEQUENCE OF FkEponPTimeStatsPortEntry
			MAX-ACCESS not-accessible
			STATUS current
			DESCRIPTION
				"Description."
			::= { fkEponPerTimeStatistics 1 }

		
		-- 1.3.6.1.4.1.10428 9 1.101.20.7.3.1.1
		fkEponPTimeStatsPortEntry OBJECT-TYPE
			SYNTAX FkEponPTimeStatsPortEntry
			MAX-ACCESS not-accessible
			STATUS current
			DESCRIPTION
				"Description."
			INDEX { ifIndex }
			::= { fkEponPTimeStatsPortTable 1 }

		
		FkEponPTimeStatsPortEntry ::=
			SEQUENCE { 
				fkEponPTimeStatsPortSaveTime
					Gauge32,
				fkEponPTimeStatsPortHourInOctets
					Counter64,
				fkEponPTimeStatsPortHourOutOctets
					Counter64,
				fkEponPTimeStatsPortDayInOctets
					Counter64,
				fkEponPTimeStatsPortDayOutOctets
					Counter64
			 }

		-- 1.3.6.1.4.1.10428 9 1.101.20.7.3.1.1.1
		fkEponPTimeStatsPortSaveTime OBJECT-TYPE
			SYNTAX Gauge32
			MAX-ACCESS read-only
			STATUS current
			DESCRIPTION
				"Description."
			::= { fkEponPTimeStatsPortEntry 1 }

		
		-- 1.3.6.1.4.1.10428 9 1.101.20.7.3.1.1.2
		fkEponPTimeStatsPortHourInOctets OBJECT-TYPE
			SYNTAX Counter64
			MAX-ACCESS read-only
			STATUS current
			DESCRIPTION
				"Description."
			::= { fkEponPTimeStatsPortEntry 2 }

		
		-- 1.3.6.1.4.1.10428 9 1.101.20.7.3.1.1.3
		fkEponPTimeStatsPortHourOutOctets OBJECT-TYPE
			SYNTAX Counter64
			MAX-ACCESS read-only
			STATUS current
			DESCRIPTION
				"Description."
			::= { fkEponPTimeStatsPortEntry 3 }

		
		-- 1.3.6.1.4.1.10428 9 1.101.20.7.3.1.1.4
		fkEponPTimeStatsPortDayInOctets OBJECT-TYPE
			SYNTAX Counter64
			MAX-ACCESS read-only
			STATUS current
			DESCRIPTION
				"Description."
			::= { fkEponPTimeStatsPortEntry 4 }

		
		-- 1.3.6.1.4.1.10428 9 1.101.20.7.3.1.1.5
		fkEponPTimeStatsPortDayOutOctets OBJECT-TYPE
			SYNTAX Counter64
			MAX-ACCESS read-only
			STATUS current
			DESCRIPTION
				"Description."
			::= { fkEponPTimeStatsPortEntry 5 }

		
		-- 1.3.6.1.4.1.10428 9 1.101.20.7.3.2
		fkEponPTimeStatsOltTable OBJECT-TYPE
			SYNTAX SEQUENCE OF FkEponPTimeStatsOltEntry
			MAX-ACCESS not-accessible
			STATUS current
			DESCRIPTION
				"Description."
			::= { fkEponPerTimeStatistics 2 }

		
		-- 1.3.6.1.4.1.10428 9 1.101.20.7.3.2.1
		fkEponPTimeStatsOltEntry OBJECT-TYPE
			SYNTAX FkEponPTimeStatsOltEntry
			MAX-ACCESS not-accessible
			STATUS current
			DESCRIPTION
				"Description."
			INDEX { fkEponOltIndex }
			::= { fkEponPTimeStatsOltTable 1 }

		
		FkEponPTimeStatsOltEntry ::=
			SEQUENCE { 
				fkEponPTimeStatsOltSaveTime
					Gauge32,
				fkEponPTimeStatsOltHourInOctets
					Counter64,
				fkEponPTimeStatsOltHourOutOctets
					Counter64,
				fkEponPTimeStatsOltDayInOctets
					Counter64,
				fkEponPTimeStatsOltDayOutOctets
					Counter64
			 }

		-- 1.3.6.1.4.1.10428 9 1.101.20.7.3.2.1.1
		fkEponPTimeStatsOltSaveTime OBJECT-TYPE
			SYNTAX Gauge32
			MAX-ACCESS read-only
			STATUS current
			DESCRIPTION
				"Description."
			::= { fkEponPTimeStatsOltEntry 1 }

		
		-- 1.3.6.1.4.1.10428 9 1.101.20.7.3.2.1.2
		fkEponPTimeStatsOltHourInOctets OBJECT-TYPE
			SYNTAX Counter64
			MAX-ACCESS read-only
			STATUS current
			DESCRIPTION
				"Description."
			::= { fkEponPTimeStatsOltEntry 2 }

		
		-- 1.3.6.1.4.1.10428 9 1.101.20.7.3.2.1.3
		fkEponPTimeStatsOltHourOutOctets OBJECT-TYPE
			SYNTAX Counter64
			MAX-ACCESS read-only
			STATUS current
			DESCRIPTION
				"Description."
			::= { fkEponPTimeStatsOltEntry 3 }

		
		-- 1.3.6.1.4.1.10428 9 1.101.20.7.3.2.1.4
		fkEponPTimeStatsOltDayInOctets OBJECT-TYPE
			SYNTAX Counter64
			MAX-ACCESS read-only
			STATUS current
			DESCRIPTION
				"Description."
			::= { fkEponPTimeStatsOltEntry 4 }

		
		-- 1.3.6.1.4.1.10428 9 1.101.20.7.3.2.1.5
		fkEponPTimeStatsOltDayOutOctets OBJECT-TYPE
			SYNTAX Counter64
			MAX-ACCESS read-only
			STATUS current
			DESCRIPTION
				"Description."
			::= { fkEponPTimeStatsOltEntry 5 }

		
		-- 1.3.6.1.4.1.10428 9 1.101.20.7.3.3
		fkEponPTimeStatsOnuTable OBJECT-TYPE
			SYNTAX SEQUENCE OF FkEponPTimeStatsOnuEntry
			MAX-ACCESS not-accessible
			STATUS current
			DESCRIPTION
				"Description."
			::= { fkEponPerTimeStatistics 3 }

		
		-- 1.3.6.1.4.1.10428 9 1.101.20.7.3.3.1
		fkEponPTimeStatsOnuEntry OBJECT-TYPE
			SYNTAX FkEponPTimeStatsOnuEntry
			MAX-ACCESS not-accessible
			STATUS current
			DESCRIPTION
				"Description."
			INDEX { fkEponOltIndex, fkEponOnuIndex }
			::= { fkEponPTimeStatsOnuTable 1 }

		
		FkEponPTimeStatsOnuEntry ::=
			SEQUENCE { 
				fkEponPTimeStatsOnuSaveTime
					Gauge32,
				fkEponPTimeStatsOnuHourInOctets
					Counter64,
				fkEponPTimeStatsOnuHourOutOctets
					Counter64,
				fkEponPTimeStatsOnuDayInOctets
					Counter64,
				fkEponPTimeStatsOnuDayOutOctets
					Counter64
			 }

		-- 1.3.6.1.4.1.10428 9 1.101.20.7.3.3.1.1
		fkEponPTimeStatsOnuSaveTime OBJECT-TYPE
			SYNTAX Gauge32
			MAX-ACCESS read-only
			STATUS current
			DESCRIPTION
				"Description."
			::= { fkEponPTimeStatsOnuEntry 1 }

		
		-- 1.3.6.1.4.1.10428 9 1.101.20.7.3.3.1.2
		fkEponPTimeStatsOnuHourInOctets OBJECT-TYPE
			SYNTAX Counter64
			MAX-ACCESS read-only
			STATUS current
			DESCRIPTION
				"Description."
			::= { fkEponPTimeStatsOnuEntry 2 }

		
		-- 1.3.6.1.4.1.10428 9 1.101.20.7.3.3.1.3
		fkEponPTimeStatsOnuHourOutOctets OBJECT-TYPE
			SYNTAX Counter64
			MAX-ACCESS read-only
			STATUS current
			DESCRIPTION
				"Description."
			::= { fkEponPTimeStatsOnuEntry 3 }

		
		-- 1.3.6.1.4.1.10428 9 1.101.20.7.3.3.1.4
		fkEponPTimeStatsOnuDayInOctets OBJECT-TYPE
			SYNTAX Counter64
			MAX-ACCESS read-only
			STATUS current
			DESCRIPTION
				"Description."
			::= { fkEponPTimeStatsOnuEntry 4 }

		
		-- 1.3.6.1.4.1.10428 9 1.101.20.7.3.3.1.5
		fkEponPTimeStatsOnuDayOutOctets OBJECT-TYPE
			SYNTAX Counter64
			MAX-ACCESS read-only
			STATUS current
			DESCRIPTION
				"Description."
			::= { fkEponPTimeStatsOnuEntry 5 }

		
		-- 1.3.6.1.4.1.10428 9 1.101.20.7.3.4
		fkEponPTimeStatsInfo OBJECT IDENTIFIER ::= { fkEponPerTimeStatistics 4 }

		
		-- 1.3.6.1.4.1.10428 9 1.101.20.7.3.4.1
		fkEponPTimeStatsBase OBJECT IDENTIFIER ::= { fkEponPTimeStatsInfo 1 }

		
		-- 1.3.6.1.4.1.10428 9 1.101.20.7.3.4.1.1
		fkEponPTimeStatsServiceActivity OBJECT-TYPE
			SYNTAX EnableFlag
			MAX-ACCESS read-only
			STATUS current
			DESCRIPTION
				"Description."
			::= { fkEponPTimeStatsBase 1 }

		
		-- 1.3.6.1.4.1.10428 9 1.101.20.7.3.4.2
		fkEponPTimeStatsControl OBJECT IDENTIFIER ::= { fkEponPTimeStatsInfo 2 }

		
		-- 1.3.6.1.4.1.10428 9 1.101.20.7.3.4.2.1
		fkEponPTimeStatsControlRequest OBJECT-TYPE
			SYNTAX INTEGER
				{
				setEponPerTimeStatisticsServiceActivity(1),
				clearEponPerTimeStatistics(2)
				}
			MAX-ACCESS read-write
			STATUS current
			DESCRIPTION
				"Description."
			::= { fkEponPTimeStatsControl 1 }

		
		-- 1.3.6.1.4.1.10428 9 1.101.20.7.3.4.2.2
		fkEponPTimeStatsControlStatus OBJECT-TYPE
			SYNTAX FkControlStatusType
			MAX-ACCESS read-only
			STATUS current
			DESCRIPTION
				"Description."
			::= { fkEponPTimeStatsControl 2 }

		
		-- 1.3.6.1.4.1.10428 9 1.101.20.7.3.4.2.3
		fkEponPTimeStatsControlTimer OBJECT-TYPE
			SYNTAX Gauge32
			MAX-ACCESS read-write
			STATUS current
			DESCRIPTION
				"Description."
			::= { fkEponPTimeStatsControl 3 }

		
		-- 1.3.6.1.4.1.10428 9 1.101.20.7.3.4.2.4
		fkEponPTimeStatsControlTimeStamp OBJECT-TYPE
			SYNTAX TimeTicks
			MAX-ACCESS read-only
			STATUS current
			DESCRIPTION
				"Description."
			::= { fkEponPTimeStatsControl 4 }

		
		-- 1.3.6.1.4.1.10428 9 1.101.20.7.3.4.2.5
		fkEponPTimeStatsControlReqResult OBJECT-TYPE
			SYNTAX FkControlRequestResultType
			MAX-ACCESS read-only
			STATUS current
			DESCRIPTION
				"Description."
			::= { fkEponPTimeStatsControl 5 }

		
		-- 1.3.6.1.4.1.10428 9 1.101.20.7.3.4.2.6
		fkEponPTimeStatsControlServiceActivity OBJECT-TYPE
			SYNTAX EnableFlag
			MAX-ACCESS read-write
			STATUS current
			DESCRIPTION
				"Description."
			::= { fkEponPTimeStatsControl 6 }

		
		-- 1.3.6.1.4.1.10428 9 1.101.20.7.3.4.3
		fkEponPTimeStatsNotification OBJECT IDENTIFIER ::= { fkEponPTimeStatsInfo 3 }

		
		-- 1.3.6.1.4.1.10428 9 1.101.20.7.3.4.3.1
		fkEponPTimeStatsServiceActivityChanged NOTIFICATION-TYPE
			OBJECTS { fkEponPTimeStatsControlRequest, fkEponPTimeStatsControlTimeStamp, fkEponPTimeStatsControlReqResult, fkEponPTimeStatsControlServiceActivity }
			STATUS current
			DESCRIPTION 
				"Description."
			::= { fkEponPTimeStatsNotification 1 }

		
		-- 1.3.6.1.4.1.10428 9 1.101.20.7.3.4.3.2
		fkEponPTimeStatsCleared NOTIFICATION-TYPE
			OBJECTS { fkEponPTimeStatsControlRequest, fkEponPTimeStatsControlTimeStamp, fkEponPTimeStatsControlReqResult }
			STATUS current
			DESCRIPTION 
				"Description."
			::= { fkEponPTimeStatsNotification 2 }

		
		-- 1.3.6.1.4.1.10428 9 1.101.20.8
		fkEponOnuClassification OBJECT IDENTIFIER ::= { fkEpon 8 }

		
		-- 1.3.6.1.4.1.10428 9 1.101.20.8.1
		fkEponOnuClassificationTable OBJECT-TYPE
			SYNTAX SEQUENCE OF FkEponOnuClassificationEntry
			MAX-ACCESS not-accessible
			STATUS current
			DESCRIPTION
				"Description."
			::= { fkEponOnuClassification 1 }

		
		-- 1.3.6.1.4.1.10428 9 1.101.20.8.1.1
		fkEponOnuClassificationEntry OBJECT-TYPE
			SYNTAX FkEponOnuClassificationEntry
			MAX-ACCESS not-accessible
			STATUS current
			DESCRIPTION
				"Description."
			INDEX { fkEponOnuClassificationIndex }
			::= { fkEponOnuClassificationTable 1 }

		
		FkEponOnuClassificationEntry ::=
			SEQUENCE { 
				fkEponOnuClassificationIndex
					INTEGER,
				fkEponOnuClassificationName
					OCTET STRING,
				fkEponOnuClassificationTrafficDirection
					INTEGER,
				fkEponOnuClassificationLayer
					INTEGER,
				fkEponOnuClassificationEtherType
					Integer32,
				fkEponOnuClassificationProtoTypeNum
					INTEGER,
				fkEponOnuClassificationL3Addr
					IpAddress,
				fkEponOnuClassificationL4Num
					Integer32
			 }

		-- 1.3.6.1.4.1.10428 9 1.101.20.8.1.1.1
		fkEponOnuClassificationIndex OBJECT-TYPE
			SYNTAX INTEGER (1..256)
			MAX-ACCESS read-only
			STATUS current
			DESCRIPTION
				"Description."
			::= { fkEponOnuClassificationEntry 1 }

		
		-- 1.3.6.1.4.1.10428 9 1.101.20.8.1.1.2
		fkEponOnuClassificationName OBJECT-TYPE
			SYNTAX OCTET STRING (SIZE (1..32))
			MAX-ACCESS read-only
			STATUS current
			DESCRIPTION
				"Description."
			::= { fkEponOnuClassificationEntry 2 }

		
		-- 1.3.6.1.4.1.10428 9 1.101.20.8.1.1.3
		fkEponOnuClassificationTrafficDirection OBJECT-TYPE
			SYNTAX INTEGER
				{
				downstream(1),
				upstream(2)
				}
			MAX-ACCESS read-only
			STATUS current
			DESCRIPTION
				"Description."
			::= { fkEponOnuClassificationEntry 3 }

		
		-- 1.3.6.1.4.1.10428 9 1.101.20.8.1.1.4
		fkEponOnuClassificationLayer OBJECT-TYPE
			SYNTAX INTEGER
				{
				etherType(1),
				protoType(2),
				layer3Destination(3),
				layer3Source(4),
				layer4Tcp(5),
				layer4Udp(6),
				layer2Cos(7),
				layer2vid(8)
				}
			MAX-ACCESS read-only
			STATUS current
			DESCRIPTION
				"Description."
			::= { fkEponOnuClassificationEntry 4 }

		
		-- 1.3.6.1.4.1.10428 9 1.101.20.8.1.1.5
		fkEponOnuClassificationEtherType OBJECT-TYPE
			SYNTAX Integer32
			MAX-ACCESS read-only
			STATUS current
			DESCRIPTION
				"Description."
			::= { fkEponOnuClassificationEntry 5 }

		
		-- 1.3.6.1.4.1.10428 9 1.101.20.8.1.1.6
		fkEponOnuClassificationProtoTypeNum OBJECT-TYPE
			SYNTAX INTEGER (0 | 1..255)
			MAX-ACCESS read-only
			STATUS current
			DESCRIPTION
				"Description."
			::= { fkEponOnuClassificationEntry 6 }

		
		-- 1.3.6.1.4.1.10428 9 1.101.20.8.1.1.7
		fkEponOnuClassificationL3Addr OBJECT-TYPE
			SYNTAX IpAddress
			MAX-ACCESS read-only
			STATUS current
			DESCRIPTION
				"Description."
			::= { fkEponOnuClassificationEntry 7 }

		
		-- 1.3.6.1.4.1.10428 9 1.101.20.8.1.1.8
		fkEponOnuClassificationL4Num OBJECT-TYPE
			SYNTAX Integer32
			MAX-ACCESS read-only
			STATUS current
			DESCRIPTION
				"Description."
			::= { fkEponOnuClassificationEntry 8 }

		
		-- 1.3.6.1.4.1.10428 9 1.101.20.8.2
		fkEponOnuClassificationControl OBJECT IDENTIFIER ::= { fkEponOnuClassification 2 }

		
		-- 1.3.6.1.4.1.10428 9 1.101.20.8.2.1
		fkEponOnuClassificationControlRequest OBJECT-TYPE
			SYNTAX INTEGER
				{
				createOnuClassification(1),
				destroyOnuClassification(2)
				}
			MAX-ACCESS read-write
			STATUS current
			DESCRIPTION
				"The request of a user command"
			::= { fkEponOnuClassificationControl 1 }

		
		-- 1.3.6.1.4.1.10428 9 1.101.20.8.2.2
		fkEponOnuClassificationControlStatus OBJECT-TYPE
			SYNTAX FkControlStatusType
			MAX-ACCESS read-only
			STATUS current
			DESCRIPTION
				"The status of user command"
			::= { fkEponOnuClassificationControl 2 }

		
		-- 1.3.6.1.4.1.10428 9 1.101.20.8.2.3
		fkEponOnuClassificationControlTimer OBJECT-TYPE
			SYNTAX Gauge32
			MAX-ACCESS read-write
			STATUS current
			DESCRIPTION
				"The maximum time for the manager for a long running user command"
			::= { fkEponOnuClassificationControl 3 }

		
		-- 1.3.6.1.4.1.10428 9 1.101.20.8.2.4
		fkEponOnuClassificationControlTimeStamp OBJECT-TYPE
			SYNTAX TimeTicks
			MAX-ACCESS read-only
			STATUS current
			DESCRIPTION
				"The time stamp of the last command(end of command)"
			::= { fkEponOnuClassificationControl 4 }

		
		-- 1.3.6.1.4.1.10428 9 1.101.20.8.2.5
		fkEponOnuClassificationControlReqResult OBJECT-TYPE
			SYNTAX FkControlRequestResultType
			MAX-ACCESS read-only
			STATUS current
			DESCRIPTION
				"The result of the last user command"
			::= { fkEponOnuClassificationControl 5 }

		
		-- 1.3.6.1.4.1.10428 9 1.101.20.8.2.6
		fkEponOnuClassificationControlName OBJECT-TYPE
			SYNTAX OCTET STRING (SIZE (1..32))
			MAX-ACCESS read-write
			STATUS current
			DESCRIPTION
				"Description."
			::= { fkEponOnuClassificationControl 6 }

		
		-- 1.3.6.1.4.1.10428 9 1.101.20.8.2.7
		fkEponOnuClassificationControlTrafficDirection OBJECT-TYPE
			SYNTAX INTEGER
				{
				downstream(1),
				upstream(2)
				}
			MAX-ACCESS read-write
			STATUS current
			DESCRIPTION
				"Description."
			::= { fkEponOnuClassificationControl 7 }

		
		-- 1.3.6.1.4.1.10428 9 1.101.20.8.2.8
		fkEponOnuClassificationControlLayer OBJECT-TYPE
			SYNTAX INTEGER
				{
				etherType(1),
				protoType(2),
				layer3Destination(3),
				layer3Source(4),
				layer4Tcp(5),
				layer4Udp(6),
				layer2Cos(7),
				layer2Vid(8)
				}
			MAX-ACCESS read-write
			STATUS current
			DESCRIPTION
				"Description."
			::= { fkEponOnuClassificationControl 8 }

		
		-- 1.3.6.1.4.1.10428 9 1.101.20.8.2.9
		fkEponOnuClassificationControlEtherType OBJECT-TYPE
			SYNTAX Integer32
			MAX-ACCESS read-write
			STATUS current
			DESCRIPTION
				"Description."
			::= { fkEponOnuClassificationControl 9 }

		
		-- 1.3.6.1.4.1.10428 9 1.101.20.8.2.10
		fkEponOnuClassificationControlProtoTypeNum OBJECT-TYPE
			SYNTAX INTEGER (0 | 1..255)
			MAX-ACCESS read-write
			STATUS current
			DESCRIPTION
				"Description."
			::= { fkEponOnuClassificationControl 10 }

		
		-- 1.3.6.1.4.1.10428 9 1.101.20.8.2.11
		fkEponOnuClassificationControlL3Addr OBJECT-TYPE
			SYNTAX IpAddress
			MAX-ACCESS read-write
			STATUS current
			DESCRIPTION
				"Description."
			::= { fkEponOnuClassificationControl 11 }

		
		-- 1.3.6.1.4.1.10428 9 1.101.20.8.2.12
		fkEponOnuClassificationControlL4Num OBJECT-TYPE
			SYNTAX Integer32
			MAX-ACCESS read-write
			STATUS current
			DESCRIPTION
				"Description."
			::= { fkEponOnuClassificationControl 12 }

		
		-- 1.3.6.1.4.1.10428 9 1.101.20.8.3
		fkEponOnuClassificationNotification OBJECT IDENTIFIER ::= { fkEponOnuClassification 3 }

		
		-- 1.3.6.1.4.1.10428 9 1.101.20.8.3.1
		fkEponOnuClassificationCreated NOTIFICATION-TYPE
			OBJECTS { fkEponOnuClassificationControlName }
			STATUS current
			DESCRIPTION 
				"Description."
			::= { fkEponOnuClassificationNotification 1 }

		
		-- 1.3.6.1.4.1.10428 9 1.101.20.8.3.2
		fkEponOnuClassificationDestroyed NOTIFICATION-TYPE
			OBJECTS { fkEponOnuClassificationControlName }
			STATUS current
			DESCRIPTION 
				"Description."
			::= { fkEponOnuClassificationNotification 2 }

		
		-- 1.3.6.1.4.1.10428 9 1.101.20.9
		fkEponVlan OBJECT IDENTIFIER ::= { fkEpon 9 }

		
		-- 1.3.6.1.4.1.10428 9 1.101.20.9.1
		fkEponVlanOltVlan OBJECT IDENTIFIER ::= { fkEponVlan 1 }

		
		-- 1.3.6.1.4.1.10428 9 1.101.20.9.1.1
		fkEponVlanOltVlanTable OBJECT-TYPE
			SYNTAX SEQUENCE OF FkEponVlanOltVlanEntry
			MAX-ACCESS not-accessible
			STATUS current
			DESCRIPTION
				"Description."
			::= { fkEponVlanOltVlan 1 }

		
		-- 1.3.6.1.4.1.10428 9 1.101.20.9.1.1.1
		fkEponVlanOltVlanEntry OBJECT-TYPE
			SYNTAX FkEponVlanOltVlanEntry
			MAX-ACCESS not-accessible
			STATUS current
			DESCRIPTION
				"Description."
			INDEX { fkEponOltIndex, fkEponOnuIndex }
			::= { fkEponVlanOltVlanTable 1 }

		
		FkEponVlanOltVlanEntry ::=
			SEQUENCE { 
				fkEponVlanOltVlanMode
					INTEGER,
				fkEponVlanOltVlanNestedStack
					EnableFlag,
				fkEponVlanOltVlanPrefix
					INTEGER,
				fkEponVlanOltVlanSuffix
					INTEGER,
				fkEponVlanOltVlanTag
					INTEGER,
				fkEponVlanOltVlanEtherType
					INTEGER
			 }

		-- 1.3.6.1.4.1.10428 9 1.101.20.9.1.1.1.1
		fkEponVlanOltVlanMode OBJECT-TYPE
			SYNTAX INTEGER
				{
				none(0),
				exchange(1),
				stack(2)
				}
			MAX-ACCESS read-only
			STATUS current
			DESCRIPTION
				"Description."
			::= { fkEponVlanOltVlanEntry 1 }

		
		-- 1.3.6.1.4.1.10428 9 1.101.20.9.1.1.1.2
		fkEponVlanOltVlanNestedStack OBJECT-TYPE
			SYNTAX EnableFlag
			MAX-ACCESS read-only
			STATUS current
			DESCRIPTION
				"Description."
			::= { fkEponVlanOltVlanEntry 2 }

		
		-- 1.3.6.1.4.1.10428 9 1.101.20.9.1.1.1.3
		fkEponVlanOltVlanPrefix OBJECT-TYPE
			SYNTAX INTEGER (-1 | 0..255)
			MAX-ACCESS read-only
			STATUS current
			DESCRIPTION
				"Description."
			::= { fkEponVlanOltVlanEntry 3 }

		
		-- 1.3.6.1.4.1.10428 9 1.101.20.9.1.1.1.4
		fkEponVlanOltVlanSuffix OBJECT-TYPE
			SYNTAX INTEGER (-1 | 0..15)
			MAX-ACCESS read-only
			STATUS current
			DESCRIPTION
				"Description."
			::= { fkEponVlanOltVlanEntry 4 }

		
		-- 1.3.6.1.4.1.10428 9 1.101.20.9.1.1.1.5
		fkEponVlanOltVlanTag OBJECT-TYPE
			SYNTAX INTEGER (-1 | 1..4096)
			MAX-ACCESS read-only
			STATUS current
			DESCRIPTION
				"Description."
			::= { fkEponVlanOltVlanEntry 5 }

		
		-- 1.3.6.1.4.1.10428 9 1.101.20.9.1.1.1.6
		fkEponVlanOltVlanEtherType OBJECT-TYPE
			SYNTAX INTEGER
				{
				none(0),
				etherType0x8100(1),
				etherType0x9100(2)
				}
			MAX-ACCESS read-only
			STATUS current
			DESCRIPTION
				"Description."
			::= { fkEponVlanOltVlanEntry 6 }

		
		-- 1.3.6.1.4.1.10428 9 1.101.20.9.1.2
		fkEponVlanOltVlanControl OBJECT IDENTIFIER ::= { fkEponVlanOltVlan 2 }

		
		-- 1.3.6.1.4.1.10428 9 1.101.20.9.1.2.1
		fkEponVlanOltVlanControlRequest OBJECT-TYPE
			SYNTAX INTEGER
				{
				setEponVlanOltVlanPrefix(1),
				setEponVlanOltVlanProfile(2)
				}
			MAX-ACCESS read-write
			STATUS current
			DESCRIPTION
				"Description."
			::= { fkEponVlanOltVlanControl 1 }

		
		-- 1.3.6.1.4.1.10428 9 1.101.20.9.1.2.2
		fkEponVlanOltVlanControlStatus OBJECT-TYPE
			SYNTAX FkControlStatusType
			MAX-ACCESS read-only
			STATUS current
			DESCRIPTION
				"Description."
			::= { fkEponVlanOltVlanControl 2 }

		
		-- 1.3.6.1.4.1.10428 9 1.101.20.9.1.2.3
		fkEponVlanOltVlanControlTimer OBJECT-TYPE
			SYNTAX Gauge32
			MAX-ACCESS read-write
			STATUS current
			DESCRIPTION
				"Description."
			::= { fkEponVlanOltVlanControl 3 }

		
		-- 1.3.6.1.4.1.10428 9 1.101.20.9.1.2.4
		fkEponVlanOltVlanControlTimeStamp OBJECT-TYPE
			SYNTAX TimeTicks
			MAX-ACCESS read-only
			STATUS current
			DESCRIPTION
				"Description."
			::= { fkEponVlanOltVlanControl 4 }

		
		-- 1.3.6.1.4.1.10428 9 1.101.20.9.1.2.5
		fkEponVlanOltVlanControlReqResult OBJECT-TYPE
			SYNTAX FkControlRequestResultType
			MAX-ACCESS read-only
			STATUS current
			DESCRIPTION
				"Description."
			::= { fkEponVlanOltVlanControl 5 }

		
		-- 1.3.6.1.4.1.10428 9 1.101.20.9.1.2.6
		fkEponVlanOltVlanControlOltIndex OBJECT-TYPE
			SYNTAX INTEGER (1..512)
			MAX-ACCESS read-write
			STATUS current
			DESCRIPTION
				"Description."
			::= { fkEponVlanOltVlanControl 6 }

		
		-- 1.3.6.1.4.1.10428 9 1.101.20.9.1.2.7
		fkEponVlanOltVlanControlOnuIndex OBJECT-TYPE
			SYNTAX INTEGER (1..64)
			MAX-ACCESS read-write
			STATUS current
			DESCRIPTION
				"Description."
			::= { fkEponVlanOltVlanControl 7 }

		
		-- 1.3.6.1.4.1.10428 9 1.101.20.9.1.2.8
		fkEponVlanOltVlanControlMode OBJECT-TYPE
			SYNTAX INTEGER
				{
				none(0),
				exchange(1),
				stack(2)
				}
			MAX-ACCESS read-write
			STATUS current
			DESCRIPTION
				"Description."
			::= { fkEponVlanOltVlanControl 8 }

		
		-- 1.3.6.1.4.1.10428 9 1.101.20.9.1.2.9
		fkEponVlanOltVlanControlNestedStack OBJECT-TYPE
			SYNTAX EnableFlag
			MAX-ACCESS read-write
			STATUS current
			DESCRIPTION
				"Description."
			::= { fkEponVlanOltVlanControl 9 }

		
		-- 1.3.6.1.4.1.10428 9 1.101.20.9.1.2.10
		fkEponVlanOltVlanControlPrefix OBJECT-TYPE
			SYNTAX INTEGER (-1 | 0..255)
			MAX-ACCESS read-write
			STATUS current
			DESCRIPTION
				"Description."
			::= { fkEponVlanOltVlanControl 10 }

		
		-- 1.3.6.1.4.1.10428 9 1.101.20.9.1.2.11
		fkEponVlanOltVlanControlSuffix OBJECT-TYPE
			SYNTAX INTEGER (-1 | 0..15)
			MAX-ACCESS read-write
			STATUS current
			DESCRIPTION
				"Description."
			::= { fkEponVlanOltVlanControl 11 }

		
		-- 1.3.6.1.4.1.10428 9 1.101.20.9.1.2.12
		fkEponVlanOltVlanControlVlanTag OBJECT-TYPE
			SYNTAX INTEGER (-1 | 1..4094)
			MAX-ACCESS read-write
			STATUS current
			DESCRIPTION
				"Description."
			::= { fkEponVlanOltVlanControl 12 }

		
		-- 1.3.6.1.4.1.10428 9 1.101.20.9.1.2.13
		fkEponVlanOltVlanControlEtherType OBJECT-TYPE
			SYNTAX INTEGER
				{
				none(0),
				etherType0x8100(1),
				etherType0x9100(2)
				}
			MAX-ACCESS read-write
			STATUS current
			DESCRIPTION
				"Description."
			::= { fkEponVlanOltVlanControl 13 }

		
		-- 1.3.6.1.4.1.10428 9 1.101.20.9.1.3
		fkEponVlanOltVlanNotification OBJECT IDENTIFIER ::= { fkEponVlanOltVlan 3 }

		
		-- 1.3.6.1.4.1.10428 9 1.101.20.9.1.3.1
		fkEponVlanOltVlanPrefixChanged NOTIFICATION-TYPE
			OBJECTS { fkEponVlanOltVlanControlRequest, fkEponVlanOltVlanControlTimeStamp, fkEponVlanOltVlanControlReqResult, fkEponVlanOltVlanControlOltIndex, fkEponVlanOltVlanControlPrefix
				 }
			STATUS current
			DESCRIPTION 
				"Description."
			::= { fkEponVlanOltVlanNotification 1 }

		
		-- 1.3.6.1.4.1.10428 9 1.101.20.9.1.3.2
		fkEponVlanOltVlanProfileChanged NOTIFICATION-TYPE
			OBJECTS { fkEponVlanOltVlanControlRequest, fkEponVlanOltVlanControlTimeStamp, fkEponVlanOltVlanControlReqResult, fkEponVlanOltVlanControlOltIndex, fkEponVlanOltVlanControlOnuIndex, 
				fkEponVlanOltVlanControlMode, fkEponVlanOltVlanControlNestedStack, fkEponVlanOltVlanControlSuffix, fkEponVlanOltVlanControlVlanTag, fkEponVlanOltVlanControlEtherType
				 }
			STATUS current
			DESCRIPTION 
				"Description."
			::= { fkEponVlanOltVlanNotification 2 }

		
		-- 1.3.6.1.4.1.10428 9 1.101.20.9.2
		fkEponVlanOnuVlan OBJECT IDENTIFIER ::= { fkEponVlan 2 }

		
		-- 1.3.6.1.4.1.10428 9 1.101.20.9.2.1
		fkEponVlanOnuVlanTable OBJECT-TYPE
			SYNTAX SEQUENCE OF FkEponVlanOnuVlanEntry
			MAX-ACCESS not-accessible
			STATUS current
			DESCRIPTION
				"Description."
			::= { fkEponVlanOnuVlan 1 }

		
		-- 1.3.6.1.4.1.10428 9 1.101.20.9.2.1.1
		fkEponVlanOnuVlanEntry OBJECT-TYPE
			SYNTAX FkEponVlanOnuVlanEntry
			MAX-ACCESS not-accessible
			STATUS current
			DESCRIPTION
				"Description."
			INDEX { fkEponOltIndex, fkEponOnuIndex }
			::= { fkEponVlanOnuVlanTable 1 }

		
		FkEponVlanOnuVlanEntry ::=
			SEQUENCE { 
				fkEponVlanOnuVlanUpMode
					INTEGER,
				fkEponVlanOnuVlanUpVlanTag
					INTEGER,
				fkEponVlanOnuVlanUpEtherType
					INTEGER,
				fkEponVlanOnuVlanUpPriority
					Integer32,
				fkEponVlanOnuVlanDownMode
					INTEGER,
				fkEponVlanOnuVlanDownVlanTag
					INTEGER,
				fkEponVlanOnuVlanDownPriority
					Integer32
			 }

		-- 1.3.6.1.4.1.10428 9 1.101.20.9.2.1.1.1
		fkEponVlanOnuVlanUpMode OBJECT-TYPE
			SYNTAX INTEGER
				{
				none(0),
				exchange(1),
				stack(2)
				}
			MAX-ACCESS read-only
			STATUS current
			DESCRIPTION
				"Description."
			::= { fkEponVlanOnuVlanEntry 1 }

		
		-- 1.3.6.1.4.1.10428 9 1.101.20.9.2.1.1.2
		fkEponVlanOnuVlanUpVlanTag OBJECT-TYPE
			SYNTAX INTEGER (-1 | 1..4094)
			MAX-ACCESS read-only
			STATUS current
			DESCRIPTION
				"Description."
			::= { fkEponVlanOnuVlanEntry 2 }

		
		-- 1.3.6.1.4.1.10428 9 1.101.20.9.2.1.1.3
		fkEponVlanOnuVlanUpEtherType OBJECT-TYPE
			SYNTAX INTEGER
				{
				none(0),
				etherType0x8100(1),
				etherType0x9100(2)
				}
			MAX-ACCESS read-only
			STATUS current
			DESCRIPTION
				"Description."
			::= { fkEponVlanOnuVlanEntry 3 }

		
		-- 1.3.6.1.4.1.10428 9 1.101.20.9.2.1.1.4
		fkEponVlanOnuVlanUpPriority OBJECT-TYPE
			SYNTAX Integer32
			MAX-ACCESS read-only
			STATUS current
			DESCRIPTION
				"Description."
			::= { fkEponVlanOnuVlanEntry 4 }

		
		-- 1.3.6.1.4.1.10428 9 1.101.20.9.2.1.1.5
		fkEponVlanOnuVlanDownMode OBJECT-TYPE
			SYNTAX INTEGER
				{
				none(0),
				exchange(1),
				stack(2)
				}
			MAX-ACCESS read-only
			STATUS current
			DESCRIPTION
				"Description."
			::= { fkEponVlanOnuVlanEntry 5 }

		
		-- 1.3.6.1.4.1.10428 9 1.101.20.9.2.1.1.6
		fkEponVlanOnuVlanDownVlanTag OBJECT-TYPE
			SYNTAX INTEGER (-1 | 1..4094)
			MAX-ACCESS read-only
			STATUS current
			DESCRIPTION
				"Description."
			::= { fkEponVlanOnuVlanEntry 6 }

		
		-- 1.3.6.1.4.1.10428 9 1.101.20.9.2.1.1.7
		fkEponVlanOnuVlanDownPriority OBJECT-TYPE
			SYNTAX Integer32
			MAX-ACCESS read-write
			STATUS current
			DESCRIPTION
				"Description."
			::= { fkEponVlanOnuVlanEntry 7 }

		
		-- 1.3.6.1.4.1.10428 9 1.101.20.9.2.2
		fkEponVlanOnuVlanControl OBJECT IDENTIFIER ::= { fkEponVlanOnuVlan 2 }

		
		-- 1.3.6.1.4.1.10428 9 1.101.20.9.2.2.1
		fkEponVlanOnuVlanControlRequest OBJECT-TYPE
			SYNTAX INTEGER { setEponVlanOnuVlanProfile(1) }
			MAX-ACCESS read-write
			STATUS current
			DESCRIPTION
				"Description."
			::= { fkEponVlanOnuVlanControl 1 }

		
		-- 1.3.6.1.4.1.10428 9 1.101.20.9.2.2.2
		fkEponVlanOnuVlanControlStatus OBJECT-TYPE
			SYNTAX FkControlStatusType
			MAX-ACCESS read-only
			STATUS current
			DESCRIPTION
				"Description."
			::= { fkEponVlanOnuVlanControl 2 }

		
		-- 1.3.6.1.4.1.10428 9 1.101.20.9.2.2.3
		fkEponVlanOnuVlanControlTimer OBJECT-TYPE
			SYNTAX Gauge32
			MAX-ACCESS read-write
			STATUS current
			DESCRIPTION
				"Description."
			::= { fkEponVlanOnuVlanControl 3 }

		
		-- 1.3.6.1.4.1.10428 9 1.101.20.9.2.2.4
		fkEponVlanOnuVlanControlTimeStamp OBJECT-TYPE
			SYNTAX TimeTicks
			MAX-ACCESS read-only
			STATUS current
			DESCRIPTION
				"Description."
			::= { fkEponVlanOnuVlanControl 4 }

		
		-- 1.3.6.1.4.1.10428 9 1.101.20.9.2.2.5
		fkEponVlanOnuVlanControlReqResult OBJECT-TYPE
			SYNTAX FkControlRequestResultType
			MAX-ACCESS read-only
			STATUS current
			DESCRIPTION
				"Description."
			::= { fkEponVlanOnuVlanControl 5 }

		
		-- 1.3.6.1.4.1.10428 9 1.101.20.9.2.2.6
		fkEponVlanOnuVlanControlOltIndex OBJECT-TYPE
			SYNTAX INTEGER (1..512)
			MAX-ACCESS read-write
			STATUS current
			DESCRIPTION
				"Description."
			::= { fkEponVlanOnuVlanControl 6 }

		
		-- 1.3.6.1.4.1.10428 9 1.101.20.9.2.2.7
		fkEponVlanOnuVlanControlOnuIndex OBJECT-TYPE
			SYNTAX INTEGER (1..64)
			MAX-ACCESS read-write
			STATUS current
			DESCRIPTION
				"Description."
			::= { fkEponVlanOnuVlanControl 7 }

		
		-- 1.3.6.1.4.1.10428 9 1.101.20.9.2.2.8
		fkEponVlanOnuVlanControlUpMode OBJECT-TYPE
			SYNTAX INTEGER
				{
				none(0),
				exchange(1),
				stack(2)
				}
			MAX-ACCESS read-write
			STATUS current
			DESCRIPTION
				"Description."
			::= { fkEponVlanOnuVlanControl 8 }

		
		-- 1.3.6.1.4.1.10428 9 1.101.20.9.2.2.9
		fkEponVlanOnuVlanControlUpVlanTag OBJECT-TYPE
			SYNTAX INTEGER (-1 | 1..4094)
			MAX-ACCESS read-write
			STATUS current
			DESCRIPTION
				"Description."
			::= { fkEponVlanOnuVlanControl 9 }

		
		-- 1.3.6.1.4.1.10428 9 1.101.20.9.2.2.10
		fkEponVlanOnuVlanControlUpEtherType OBJECT-TYPE
			SYNTAX INTEGER
				{
				none(0),
				etherType0x8100(1),
				etherType0x9100(2)
				}
			MAX-ACCESS read-write
			STATUS current
			DESCRIPTION
				"Description."
			::= { fkEponVlanOnuVlanControl 10 }

		
		-- 1.3.6.1.4.1.10428 9 1.101.20.9.2.2.11
		fkEponVlanOnuVlanControlUpPriority OBJECT-TYPE
			SYNTAX Integer32
			MAX-ACCESS read-write
			STATUS current
			DESCRIPTION
				"Description."
			::= { fkEponVlanOnuVlanControl 11 }

		
		-- 1.3.6.1.4.1.10428 9 1.101.20.9.2.2.12
		fkEponVlanOnuVlanControlDownMode OBJECT-TYPE
			SYNTAX INTEGER
				{
				none(0),
				exchange(1),
				stack(2)
				}
			MAX-ACCESS read-write
			STATUS current
			DESCRIPTION
				"Description."
			::= { fkEponVlanOnuVlanControl 12 }

		
		-- 1.3.6.1.4.1.10428 9 1.101.20.9.2.2.13
		fkEponVlanOnuVlanControlDownVlanTag OBJECT-TYPE
			SYNTAX INTEGER (-1 | 1..4094)
			MAX-ACCESS read-write
			STATUS current
			DESCRIPTION
				"Description."
			::= { fkEponVlanOnuVlanControl 13 }

		
		-- 1.3.6.1.4.1.10428 9 1.101.20.9.2.2.14
		fkEponVlanOnuVlanControlDownPriority OBJECT-TYPE
			SYNTAX Integer32
			MAX-ACCESS read-write
			STATUS current
			DESCRIPTION
				"Description."
			::= { fkEponVlanOnuVlanControl 14 }

		
		-- 1.3.6.1.4.1.10428 9 1.101.20.9.2.3
		fkEponVlanOnuVlanNotification OBJECT IDENTIFIER ::= { fkEponVlanOnuVlan 3 }

		
		-- 1.3.6.1.4.1.10428 9 1.101.20.9.2.3.1
		fkEponVlanOnuVlanProfileChanged NOTIFICATION-TYPE
			OBJECTS { fkEponVlanOnuVlanControlRequest, fkEponVlanOnuVlanControlTimeStamp, fkEponVlanOnuVlanControlReqResult, fkEponVlanOnuVlanControlOltIndex, fkEponVlanOnuVlanControlOnuIndex, 
				fkEponVlanOnuVlanControlUpMode, fkEponVlanOnuVlanControlUpVlanTag, fkEponVlanOnuVlanControlUpEtherType, fkEponVlanOnuVlanControlDownMode, fkEponVlanOnuVlanControlDownVlanTag
				 }
			STATUS current
			DESCRIPTION 
				"Description."
			::= { fkEponVlanOnuVlanNotification 1 }

		
		-- 1.3.6.1.4.1.10428 9 1.101.20.10
		fkEponFirmwareMgmt OBJECT IDENTIFIER ::= { fkEpon 10 }

		
		-- 1.3.6.1.4.1.10428 9 1.101.20.10.1
		fkEponFirmwareTable OBJECT-TYPE
			SYNTAX SEQUENCE OF FkEponFirmwareEntry
			MAX-ACCESS not-accessible
			STATUS current
			DESCRIPTION
				"Description."
			::= { fkEponFirmwareMgmt 1 }

		
		-- 1.3.6.1.4.1.10428 9 1.101.20.10.1.1
		fkEponFirmwareEntry OBJECT-TYPE
			SYNTAX FkEponFirmwareEntry
			MAX-ACCESS not-accessible
			STATUS current
			DESCRIPTION
				"Description."
			INDEX { fkEponFirmwareType, fkEponFirmwareName }
			::= { fkEponFirmwareTable 1 }

		
		FkEponFirmwareEntry ::=
			SEQUENCE { 
				fkEponFirmwareType
					INTEGER,
				fkEponFirmwareName
					OCTET STRING
			 }

		-- 1.3.6.1.4.1.10428 9 1.101.20.10.1.1.1
		fkEponFirmwareType OBJECT-TYPE
			SYNTAX INTEGER
				{
				olt(1),
				onu(2)
				}
			MAX-ACCESS read-only
			STATUS current
			DESCRIPTION
				"Description."
			::= { fkEponFirmwareEntry 1 }

		
		-- 1.3.6.1.4.1.10428 9 1.101.20.10.1.1.2
		fkEponFirmwareName OBJECT-TYPE
			SYNTAX OCTET STRING (SIZE (1..128))
			MAX-ACCESS read-only
			STATUS current
			DESCRIPTION
				"Description."
			::= { fkEponFirmwareEntry 2 }

		
		-- 1.3.6.1.4.1.10428 9 1.101.20.10.2
		fkEponFirmwareControl OBJECT IDENTIFIER ::= { fkEponFirmwareMgmt 2 }

		
		-- 1.3.6.1.4.1.10428 9 1.101.20.10.2.1
		fkEponFirmwareControlRequest OBJECT-TYPE
			SYNTAX INTEGER
				{
				setEponFirmwareUpgradeProfile(1),
				deleteEponFirmware(2)
				}
			MAX-ACCESS read-write
			STATUS current
			DESCRIPTION
				"Description."
			::= { fkEponFirmwareControl 1 }

		
		-- 1.3.6.1.4.1.10428 9 1.101.20.10.2.2
		fkEponFirmwareControlStatus OBJECT-TYPE
			SYNTAX FkControlStatusType
			MAX-ACCESS read-only
			STATUS current
			DESCRIPTION
				"Description."
			::= { fkEponFirmwareControl 2 }

		
		-- 1.3.6.1.4.1.10428 9 1.101.20.10.2.3
		fkEponFirmwareControlTimer OBJECT-TYPE
			SYNTAX Gauge32
			MAX-ACCESS read-write
			STATUS current
			DESCRIPTION
				"Description."
			::= { fkEponFirmwareControl 3 }

		
		-- 1.3.6.1.4.1.10428 9 1.101.20.10.2.4
		fkEponFirmwareControlTimeStamp OBJECT-TYPE
			SYNTAX TimeTicks
			MAX-ACCESS read-only
			STATUS current
			DESCRIPTION
				"Description."
			::= { fkEponFirmwareControl 4 }

		
		-- 1.3.6.1.4.1.10428 9 1.101.20.10.2.5
		fkEponFirmwareControlReqResult OBJECT-TYPE
			SYNTAX FkControlRequestResultType
			MAX-ACCESS read-only
			STATUS current
			DESCRIPTION
				"Description."
			::= { fkEponFirmwareControl 5 }

		
		-- 1.3.6.1.4.1.10428 9 1.101.20.10.2.6
		fkEponFirmwareControlName OBJECT-TYPE
			SYNTAX OCTET STRING (SIZE (1..128))
			MAX-ACCESS read-write
			STATUS current
			DESCRIPTION
				"Description."
			::= { fkEponFirmwareControl 6 }

		
		-- 1.3.6.1.4.1.10428 9 1.101.20.10.2.7
		fkEponFirmwareControlUpgradeMethod OBJECT-TYPE
			SYNTAX INTEGER
				{
				ftp(1),
				tftp(2)
				}
			MAX-ACCESS read-write
			STATUS current
			DESCRIPTION
				"Description."
			::= { fkEponFirmwareControl 7 }

		
		-- 1.3.6.1.4.1.10428 9 1.101.20.10.2.8
		fkEponFirmwareControlUpgradeMode OBJECT-TYPE
			SYNTAX INTEGER
				{
				upload(1),
				download(2)
				}
			MAX-ACCESS read-write
			STATUS current
			DESCRIPTION
				"Description."
			::= { fkEponFirmwareControl 8 }

		
		-- 1.3.6.1.4.1.10428 9 1.101.20.10.2.9
		fkEponFirmwareControlServerAddress OBJECT-TYPE
			SYNTAX IpAddress
			MAX-ACCESS read-write
			STATUS current
			DESCRIPTION
				"Description."
			::= { fkEponFirmwareControl 9 }

		
		-- 1.3.6.1.4.1.10428 9 1.101.20.10.2.10
		fkEponFirmwareControlUser OBJECT-TYPE
			SYNTAX OCTET STRING
			MAX-ACCESS read-write
			STATUS current
			DESCRIPTION
				"Description."
			::= { fkEponFirmwareControl 10 }

		
		-- 1.3.6.1.4.1.10428 9 1.101.20.10.2.11
		fkEponFirmwareControlPasswd OBJECT-TYPE
			SYNTAX OCTET STRING
			MAX-ACCESS read-write
			STATUS current
			DESCRIPTION
				"Description."
			::= { fkEponFirmwareControl 11 }

		
		-- 1.3.6.1.4.1.10428 9 1.101.20.10.3
		fkEponFirmwareNotification OBJECT IDENTIFIER ::= { fkEponFirmwareMgmt 3 }

		
		-- 1.3.6.1.4.1.10428 9 1.101.20.10.3.1
		fkEponFirmwareUpgradeProfileChanged NOTIFICATION-TYPE
			OBJECTS { fkEponFirmwareControlRequest, fkEponFirmwareControlTimeStamp, fkEponFirmwareControlReqResult, fkEponFirmwareControlName, fkEponFirmwareControlUpgradeMethod, 
				fkEponFirmwareControlUpgradeMode, fkEponFirmwareControlServerAddress, fkEponFirmwareControlUser, fkEponFirmwareControlPasswd }
			STATUS current
			DESCRIPTION 
				"Description."
			::= { fkEponFirmwareNotification 1 }

		
		-- 1.3.6.1.4.1.10428 9 1.101.20.10.3.2
		fkEponFirmwareDeleted NOTIFICATION-TYPE
			OBJECTS { fkEponFirmwareControlRequest, fkEponFirmwareControlTimeStamp, fkEponFirmwareControlReqResult, fkEponFirmwareControlName }
			STATUS current
			DESCRIPTION 
				"Description."
			::= { fkEponFirmwareNotification 2 }

		
		-- 1.3.6.1.4.1.10428 9 1.101.20.11
		fkEponOnuSipUserConfig OBJECT IDENTIFIER ::= { fkEpon 11 }

		
		-- 1.3.6.1.4.1.10428 9 1.101.20.11.1
		fkEponOnuSipUserConfigTable OBJECT-TYPE
			SYNTAX SEQUENCE OF FkEponOnuSipUserConfigEntry
			MAX-ACCESS not-accessible
			STATUS current
			DESCRIPTION
				"Description."
			::= { fkEponOnuSipUserConfig 1 }

		
		-- 1.3.6.1.4.1.10428 9 1.101.20.11.1.1
		fkEponOnuSipUserConfigEntry OBJECT-TYPE
			SYNTAX FkEponOnuSipUserConfigEntry
			MAX-ACCESS not-accessible
			STATUS current
			DESCRIPTION
				"Description."
			INDEX { fkEponOltIndex, fkEponOnuIndex, fkEponOnuSipUserConfigPots }
			::= { fkEponOnuSipUserConfigTable 1 }

		
		FkEponOnuSipUserConfigEntry ::=
			SEQUENCE { 
				fkEponOnuSipUserConfigPots
					INTEGER,
				fkEponOnuSipUserConfigAccount
					OCTET STRING,
				fkEponOnuSipUserConfigName
					OCTET STRING,
				fkEponOnuSipUserConfigPasswd
					OCTET STRING
			 }

		-- 1.3.6.1.4.1.10428 9 1.101.20.11.1.1.1
		fkEponOnuSipUserConfigPots OBJECT-TYPE
			SYNTAX INTEGER (0..65535)
			MAX-ACCESS read-only
			STATUS current
			DESCRIPTION
				"Description."
			::= { fkEponOnuSipUserConfigEntry 1 }

		
		-- 1.3.6.1.4.1.10428 9 1.101.20.11.1.1.2
		fkEponOnuSipUserConfigAccount OBJECT-TYPE
			SYNTAX OCTET STRING
			MAX-ACCESS read-only
			STATUS current
			DESCRIPTION
				"Description."
			::= { fkEponOnuSipUserConfigEntry 2 }

		
		-- 1.3.6.1.4.1.10428 9 1.101.20.11.1.1.3
		fkEponOnuSipUserConfigName OBJECT-TYPE
			SYNTAX OCTET STRING
			MAX-ACCESS read-only
			STATUS current
			DESCRIPTION
				"Description."
			::= { fkEponOnuSipUserConfigEntry 3 }

		
		-- 1.3.6.1.4.1.10428 9 1.101.20.11.1.1.4
		fkEponOnuSipUserConfigPasswd OBJECT-TYPE
			SYNTAX OCTET STRING
			MAX-ACCESS read-only
			STATUS current
			DESCRIPTION
				"Description."
			::= { fkEponOnuSipUserConfigEntry 4 }

		
		-- 1.3.6.1.4.1.10428 9 1.101.20.11.2
		fkEponOnuSipUserConfigControl OBJECT IDENTIFIER ::= { fkEponOnuSipUserConfig 2 }

		
		-- 1.3.6.1.4.1.10428 9 1.101.20.11.2.1
		fkEponOnuSipUserConfigControlRequest OBJECT-TYPE
			SYNTAX INTEGER
				{
				setEponOnuSipUserConfig(1),
				destroyEponOnuSipUserConfig(2)
				}
			MAX-ACCESS read-write
			STATUS current
			DESCRIPTION
				"Description."
			::= { fkEponOnuSipUserConfigControl 1 }

		
		-- 1.3.6.1.4.1.10428 9 1.101.20.11.2.2
		fkEponOnuSipUserConfigControlStatus OBJECT-TYPE
			SYNTAX FkControlStatusType
			MAX-ACCESS read-only
			STATUS current
			DESCRIPTION
				"Description."
			::= { fkEponOnuSipUserConfigControl 2 }

		
		-- 1.3.6.1.4.1.10428 9 1.101.20.11.2.3
		fkEponOnuSipUserConfigControlTimer OBJECT-TYPE
			SYNTAX Gauge32
			MAX-ACCESS read-write
			STATUS current
			DESCRIPTION
				"Description."
			::= { fkEponOnuSipUserConfigControl 3 }

		
		-- 1.3.6.1.4.1.10428 9 1.101.20.11.2.4
		fkEponOnuSipUserConfigControlTimeStamp OBJECT-TYPE
			SYNTAX TimeTicks
			MAX-ACCESS read-only
			STATUS current
			DESCRIPTION
				"Description."
			::= { fkEponOnuSipUserConfigControl 4 }

		
		-- 1.3.6.1.4.1.10428 9 1.101.20.11.2.5
		fkEponOnuSipUserConfigControlReqResult OBJECT-TYPE
			SYNTAX FkControlRequestResultType
			MAX-ACCESS read-only
			STATUS current
			DESCRIPTION
				"Description."
			::= { fkEponOnuSipUserConfigControl 5 }

		
		-- 1.3.6.1.4.1.10428 9 1.101.20.11.2.6
		fkEponOnuSipUserConfigControlOltIndex OBJECT-TYPE
			SYNTAX INTEGER
			MAX-ACCESS read-write
			STATUS current
			DESCRIPTION
				"Description."
			::= { fkEponOnuSipUserConfigControl 6 }

		
		-- 1.3.6.1.4.1.10428 9 1.101.20.11.2.7
		fkEponOnuSipUserConfigControlOnuIndex OBJECT-TYPE
			SYNTAX INTEGER
			MAX-ACCESS read-write
			STATUS current
			DESCRIPTION
				"Description."
			::= { fkEponOnuSipUserConfigControl 7 }

		
		-- 1.3.6.1.4.1.10428 9 1.101.20.11.2.8
		fkEponOnuSipUserConfigControlPots OBJECT-TYPE
			SYNTAX INTEGER
			MAX-ACCESS read-write
			STATUS current
			DESCRIPTION
				"Description."
			::= { fkEponOnuSipUserConfigControl 8 }

		
		-- 1.3.6.1.4.1.10428 9 1.101.20.11.2.9
		fkEponOnuSipUserConfigControlAccount OBJECT-TYPE
			SYNTAX OCTET STRING
			MAX-ACCESS read-write
			STATUS current
			DESCRIPTION
				"Description."
			::= { fkEponOnuSipUserConfigControl 9 }

		
		-- 1.3.6.1.4.1.10428 9 1.101.20.11.2.10
		fkEponOnuSipUserConfigControlName OBJECT-TYPE
			SYNTAX OCTET STRING
			MAX-ACCESS read-write
			STATUS current
			DESCRIPTION
				"Description."
			::= { fkEponOnuSipUserConfigControl 10 }

		
		-- 1.3.6.1.4.1.10428 9 1.101.20.11.2.11
		fkEponOnuSipUserConfigControlPasswd OBJECT-TYPE
			SYNTAX OCTET STRING
			MAX-ACCESS read-write
			STATUS current
			DESCRIPTION
				"Description."
			::= { fkEponOnuSipUserConfigControl 11 }

		
		-- 1.3.6.1.4.1.10428 9 1.101.20.11.3
		fkEponOnuSipNotification OBJECT IDENTIFIER ::= { fkEponOnuSipUserConfig 3 }

		
		-- 1.3.6.1.4.1.10428 9 1.101.20.11.3.1
		fkEponOnuSipUserConfigChanged NOTIFICATION-TYPE
			OBJECTS { fkEponOnuSipUserConfigControlRequest, fkEponOnuSipUserConfigControlTimeStamp, fkEponOnuSipUserConfigControlReqResult, fkEponOnuSipUserConfigControlOltIndex, fkEponOnuSipUserConfigControlOnuIndex, 
				fkEponOnuSipUserConfigControlPots, fkEponOnuSipUserConfigControlAccount, fkEponOnuSipUserConfigControlName, fkEponOnuSipUserConfigControlPasswd }
			STATUS current
			DESCRIPTION 
				"Description."
			::= { fkEponOnuSipNotification 1 }

		
		-- 1.3.6.1.4.1.10428 9 1.101.20.11.3.2
		fkEponOnuSipUserConfigDestroyed NOTIFICATION-TYPE
			OBJECTS { fkEponOnuSipUserConfigControlRequest, fkEponOnuSipUserConfigControlTimeStamp, fkEponOnuSipUserConfigControlReqResult, fkEponOnuSipUserConfigControlOltIndex, fkEponOnuSipUserConfigControlOnuIndex, 
				fkEponOnuSipUserConfigControlPots }
			STATUS current
			DESCRIPTION 
				"Description."
			::= { fkEponOnuSipNotification 2 }

		
		-- 1.3.6.1.4.1.10428 9 1.101.20.12
		fkEponOnuSipPortStatus OBJECT IDENTIFIER ::= { fkEpon 12 }

		
		-- 1.3.6.1.4.1.10428 9 1.101.20.12.1
		fkEponOnuSipPortStatusTable OBJECT-TYPE
			SYNTAX SEQUENCE OF FkEponOnuSipPortStatusEntry
			MAX-ACCESS not-accessible
			STATUS current
			DESCRIPTION
				"Description."
			::= { fkEponOnuSipPortStatus 1 }

		
		-- 1.3.6.1.4.1.10428 9 1.101.20.12.1.1
		fkEponOnuSipPortStatusEntry OBJECT-TYPE
			SYNTAX FkEponOnuSipPortStatusEntry
			MAX-ACCESS not-accessible
			STATUS current
			DESCRIPTION
				"Description."
			INDEX { fkEponOltIndex, fkEponOnuIndex, fkEponOnuSipUserConfigPots }
			::= { fkEponOnuSipPortStatusTable 1 }

		
		FkEponOnuSipPortStatusEntry ::=
			SEQUENCE { 
				fkEponOnuVoipPortStatus
					OCTET STRING,
				fkEponOnuSipPortServiceState
					OCTET STRING,
				fkEponOnuSipPortCodecMode
					OCTET STRING
			 }

		-- 1.3.6.1.4.1.10428 9 1.101.20.12.1.1.1
		fkEponOnuVoipPortStatus OBJECT-TYPE
			SYNTAX OCTET STRING
			MAX-ACCESS read-only
			STATUS current
			DESCRIPTION
				"Description."
			::= { fkEponOnuSipPortStatusEntry 1 }

		
		-- 1.3.6.1.4.1.10428 9 1.101.20.12.1.1.2
		fkEponOnuSipPortServiceState OBJECT-TYPE
			SYNTAX OCTET STRING
			MAX-ACCESS read-only
			STATUS current
			DESCRIPTION
				"Description."
			::= { fkEponOnuSipPortStatusEntry 2 }

		
		-- 1.3.6.1.4.1.10428 9 1.101.20.12.1.1.3
		fkEponOnuSipPortCodecMode OBJECT-TYPE
			SYNTAX OCTET STRING
			MAX-ACCESS read-only
			STATUS current
			DESCRIPTION
				"Description."
			::= { fkEponOnuSipPortStatusEntry 3 }

		
		-- 1.3.6.1.4.1.10428 9 1.101.20.13
		fkEponRule OBJECT IDENTIFIER ::= { fkEpon 13 }

		
		-- 1.3.6.1.4.1.10428 9 1.101.20.13.1
		fkEponRuleClause OBJECT IDENTIFIER ::= { fkEponRule 1 }

		
		-- 1.3.6.1.4.1.10428 9 1.101.20.13.1.1
		fkEponRuleClauseTable OBJECT-TYPE
			SYNTAX SEQUENCE OF FkEponRuleClauseEntry
			MAX-ACCESS not-accessible
			STATUS current
			DESCRIPTION
				"Description."
			::= { fkEponRuleClause 1 }

		
		-- 1.3.6.1.4.1.10428 9 1.101.20.13.1.1.1
		fkEponRuleClauseEntry OBJECT-TYPE
			SYNTAX FkEponRuleClauseEntry
			MAX-ACCESS not-accessible
			STATUS current
			DESCRIPTION
				"Description."
			INDEX { fkEponOltIndex }
			::= { fkEponRuleClauseTable 1 }

		
		FkEponRuleClauseEntry ::=
			SEQUENCE { 
				fkEponRuleClauseQueue
					INTEGER,
				fkEponRuleClauseQueueValue
					Integer32,
				fkEponRuleClauseLayerOperation
					INTEGER,
				fkEponRuleClauseLayerValue
					INTEGER,
				fkEponRuleClauseL2Mac
					MacAddress,
				fkEponRuleClauseL2EthertypeValue
					INTEGER,
				fkEponRuleClauseNetmask
					INTEGER,
				fkEponRuleClauseL3Addr
					IpAddress,
				fkEponRuleClauseTcpUdpPort
					INTEGER,
				fkEponRuleClauseTcpUdpPortNum
					Integer32,
				fkEponRuleClauseProtoType
					INTEGER,
				fkEponRuleClauseProtoTypeNum
					Integer32,
				fkEponRuleClauseVlanType
					INTEGER,
				fkEponRuleClauseVlanValue
					Integer32,
				fkEponRuleClauseLinkIndexValue
					Integer32,
				fkEponRuleClauseMatchMode
					INTEGER
			 }

		-- 1.3.6.1.4.1.10428 9 1.101.20.13.1.1.1.1
		fkEponRuleClauseQueue OBJECT-TYPE
			SYNTAX INTEGER
				{
				queuea(1),
				queueb(2)
				}
			MAX-ACCESS read-only
			STATUS current
			DESCRIPTION
				"State Variable Queue
				1.queue-a
				2.queue-b"
			::= { fkEponRuleClauseEntry 1 }

		
		-- 1.3.6.1.4.1.10428 9 1.101.20.13.1.1.1.2
		fkEponRuleClauseQueueValue OBJECT-TYPE
			SYNTAX Integer32
			MAX-ACCESS read-only
			STATUS current
			DESCRIPTION
				"rule clause rule queue."
			::= { fkEponRuleClauseEntry 2 }

		
		-- 1.3.6.1.4.1.10428 9 1.101.20.13.1.1.1.3
		fkEponRuleClauseLayerOperation OBJECT-TYPE
			SYNTAX INTEGER
				{
				layer2SrcAddr(1),
				layer2DesAddr(2),
				layer2Tos(3),
				layer2Ttl(4),
				layer2EtherType(5),
				layer3SrcAddr(6),
				layer3DesAddr(7)
				}
			MAX-ACCESS read-only
			STATUS current
			DESCRIPTION
				"The rule clause be used to which layer and which type."
			::= { fkEponRuleClauseEntry 3 }

		
		-- 1.3.6.1.4.1.10428 9 1.101.20.13.1.1.1.4
		fkEponRuleClauseLayerValue OBJECT-TYPE
			SYNTAX INTEGER (0..7)
			MAX-ACCESS read-only
			STATUS current
			DESCRIPTION
				"layer value."
			::= { fkEponRuleClauseEntry 4 }

		
		-- 1.3.6.1.4.1.10428 9 1.101.20.13.1.1.1.5
		fkEponRuleClauseL2Mac OBJECT-TYPE
			SYNTAX MacAddress
			MAX-ACCESS read-only
			STATUS current
			DESCRIPTION
				"Layer 2 MAC address."
			::= { fkEponRuleClauseEntry 5 }

		
		-- 1.3.6.1.4.1.10428 9 1.101.20.13.1.1.1.6
		fkEponRuleClauseL2EthertypeValue OBJECT-TYPE
			SYNTAX INTEGER
				{
				null(0),
				ip0x0800(1),
				arp0x0806(2)
				}
			MAX-ACCESS read-write
			STATUS current
			DESCRIPTION
				"Rule Clause L2 Ethertype Value."
			::= { fkEponRuleClauseEntry 6 }

		
		-- 1.3.6.1.4.1.10428 9 1.101.20.13.1.1.1.7
		fkEponRuleClauseNetmask OBJECT-TYPE
			SYNTAX INTEGER (1..48)
			MAX-ACCESS read-only
			STATUS current
			DESCRIPTION
				"The netmask.
				1.layer2 range from 1-48
				2.layer3 range from 1-32"
			::= { fkEponRuleClauseEntry 7 }

		
		-- 1.3.6.1.4.1.10428 9 1.101.20.13.1.1.1.8
		fkEponRuleClauseL3Addr OBJECT-TYPE
			SYNTAX IpAddress
			MAX-ACCESS read-only
			STATUS current
			DESCRIPTION
				"Chooseing the sourse or destination IP address be used to the rule clause."
			::= { fkEponRuleClauseEntry 8 }

		
		-- 1.3.6.1.4.1.10428 9 1.101.20.13.1.1.1.9
		fkEponRuleClauseTcpUdpPort OBJECT-TYPE
			SYNTAX INTEGER
				{
				srcport(1),
				desport(2)
				}
			MAX-ACCESS read-only
			STATUS current
			DESCRIPTION
				"rule clause tcp/udp port."
			::= { fkEponRuleClauseEntry 9 }

		
		-- 1.3.6.1.4.1.10428 9 1.101.20.13.1.1.1.10
		fkEponRuleClauseTcpUdpPortNum OBJECT-TYPE
			SYNTAX Integer32 (0..65535)
			MAX-ACCESS read-only
			STATUS current
			DESCRIPTION
				"rule clause tcp/udp port, number range from 0 to 65535."
			::= { fkEponRuleClauseEntry 10 }

		
		-- 1.3.6.1.4.1.10428 9 1.101.20.13.1.1.1.11
		fkEponRuleClauseProtoType OBJECT-TYPE
			SYNTAX INTEGER
				{
				protoType(1),
				slowProto(2)
				}
			MAX-ACCESS read-only
			STATUS current
			DESCRIPTION
				"Protocol type
				1.proto-type 
				2.slow-proto 
				ex:For protocol type 1=ICMP 2=IGMP 6=TCP 17=UDP"
			::= { fkEponRuleClauseEntry 11 }

		
		-- 1.3.6.1.4.1.10428 9 1.101.20.13.1.1.1.12
		fkEponRuleClauseProtoTypeNum OBJECT-TYPE
			SYNTAX Integer32 (1..255)
			MAX-ACCESS read-only
			STATUS current
			DESCRIPTION
				"The range from 1 to 255"
			::= { fkEponRuleClauseEntry 12 }

		
		-- 1.3.6.1.4.1.10428 9 1.101.20.13.1.1.1.13
		fkEponRuleClauseVlanType OBJECT-TYPE
			SYNTAX INTEGER
				{
				svlan0(1),
				svlan1(2),
				cvlan0(3),
				cvlan1(4)
				}
			MAX-ACCESS read-only
			STATUS current
			DESCRIPTION
				"The rule VLAN type:
				1.s-vlan0
				2.s-vlan1
				3.c-vlan0
				4.c-vlan1"
			::= { fkEponRuleClauseEntry 13 }

		
		-- 1.3.6.1.4.1.10428 9 1.101.20.13.1.1.1.14
		fkEponRuleClauseVlanValue OBJECT-TYPE
			SYNTAX Integer32
			MAX-ACCESS read-write
			STATUS current
			DESCRIPTION
				"vlan value."
			::= { fkEponRuleClauseEntry 14 }

		
		-- 1.3.6.1.4.1.10428 9 1.101.20.13.1.1.1.15
		fkEponRuleClauseLinkIndexValue OBJECT-TYPE
			SYNTAX Integer32
			MAX-ACCESS read-write
			STATUS current
			DESCRIPTION
				"Link index."
			::= { fkEponRuleClauseEntry 15 }

		
		-- 1.3.6.1.4.1.10428 9 1.101.20.13.1.1.1.16
		fkEponRuleClauseMatchMode OBJECT-TYPE
			SYNTAX INTEGER
				{
				eq(1),
				neq(2),
				lte(3),
				gte(4),
				fe(5),
				nfe(6),
				al(7)
				}
			MAX-ACCESS read-write
			STATUS current
			DESCRIPTION
				"Description."
			::= { fkEponRuleClauseEntry 16 }

		
		-- 1.3.6.1.4.1.10428 9 1.101.20.13.1.2
		fkEponRuleClauseControl OBJECT IDENTIFIER ::= { fkEponRuleClause 2 }

		
		-- 1.3.6.1.4.1.10428 9 1.101.20.13.1.2.1
		fkEponRuleClauseControlRequest OBJECT-TYPE
			SYNTAX INTEGER
				{
				setRuleClauseQueue(1),
				setRuleClauseLayer2(2),
				setRuleClauseVlan(3),
				setRuleClauseLayer3(4),
				setRuleClauseTcpUdp(5),
				setRuleClauseProtocol(6),
				setRuleClauseLinkIndex(7),
				noRuleClause(8)
				}
			MAX-ACCESS read-write
			STATUS current
			DESCRIPTION
				"The request of a user command."
			::= { fkEponRuleClauseControl 1 }

		
		-- 1.3.6.1.4.1.10428 9 1.101.20.13.1.2.2
		fkEponRuleClauseControlStatus OBJECT-TYPE
			SYNTAX FkControlStatusType
			MAX-ACCESS read-only
			STATUS current
			DESCRIPTION
				"The status of user command"
			::= { fkEponRuleClauseControl 2 }

		
		-- 1.3.6.1.4.1.10428 9 1.101.20.13.1.2.3
		fkEponRuleClauseControlTimer OBJECT-TYPE
			SYNTAX Gauge32
			MAX-ACCESS read-write
			STATUS current
			DESCRIPTION
				"The maximum time for the manager for a long running user command"
			::= { fkEponRuleClauseControl 3 }

		
		-- 1.3.6.1.4.1.10428 9 1.101.20.13.1.2.4
		fkEponRuleClauseControlTimeStamp OBJECT-TYPE
			SYNTAX TimeTicks
			MAX-ACCESS read-only
			STATUS current
			DESCRIPTION
				"The time stamp of the last command(end of command)"
			::= { fkEponRuleClauseControl 4 }

		
		-- 1.3.6.1.4.1.10428 9 1.101.20.13.1.2.5
		fkEponRuleClauseControlReqResult OBJECT-TYPE
			SYNTAX FkControlRequestResultType
			MAX-ACCESS read-only
			STATUS current
			DESCRIPTION
				"The result of the last user command"
			::= { fkEponRuleClauseControl 5 }

		
		-- 1.3.6.1.4.1.10428 9 1.101.20.13.1.2.6
		fkEponRuleClauseControlClauseIndex OBJECT-TYPE
			SYNTAX Integer32
			MAX-ACCESS read-write
			STATUS current
			DESCRIPTION
				"Rule clause index"
			::= { fkEponRuleClauseControl 6 }

		
		-- 1.3.6.1.4.1.10428 9 1.101.20.13.1.2.7
		fkEponRuleClauseControlClauseMatch OBJECT-TYPE
			SYNTAX INTEGER
				{
				eq(1),
				neq(2),
				lte(3),
				gte(4),
				fe(5),
				nfe(6),
				al(7)
				}
			MAX-ACCESS read-write
			STATUS current
			DESCRIPTION
				"match mode."
			::= { fkEponRuleClauseControl 7 }

		
		-- 1.3.6.1.4.1.10428 9 1.101.20.13.1.2.8
		fkEponRuleClauseControlQueue OBJECT-TYPE
			SYNTAX INTEGER
				{
				queueA(1),
				queueB(2)
				}
			MAX-ACCESS read-write
			STATUS current
			DESCRIPTION
				"State Variable Queue."
			::= { fkEponRuleClauseControl 8 }

		
		-- 1.3.6.1.4.1.10428 9 1.101.20.13.1.2.9
		fkEponRuleClauseControlQueueValue OBJECT-TYPE
			SYNTAX INTEGER (0..7)
			MAX-ACCESS read-write
			STATUS current
			DESCRIPTION
				"State Variable Queue Value."
			::= { fkEponRuleClauseControl 9 }

		
		-- 1.3.6.1.4.1.10428 9 1.101.20.13.1.2.10
		fkEponRuleClauseControlLayerOperation OBJECT-TYPE
			SYNTAX INTEGER
				{
				layer2SrcAddress(1),
				layer2DesAddress(2),
				layer2Tos(3),
				layer2Ttl(4),
				layer2EtherType(5),
				layer3SrcIPAddress(6),
				layer3DesIPAddress(7)
				}
			MAX-ACCESS read-write
			STATUS current
			DESCRIPTION
				"The rule clause be used to which layer and which type.The layer as following:
				"
			::= { fkEponRuleClauseControl 10 }

		
		-- 1.3.6.1.4.1.10428 9 1.101.20.13.1.2.11
		fkEponRuleClauseControlLayerValue OBJECT-TYPE
			SYNTAX Integer32
			MAX-ACCESS read-write
			STATUS current
			DESCRIPTION
				"layer value."
			::= { fkEponRuleClauseControl 11 }

		
		-- 1.3.6.1.4.1.10428 9 1.101.20.13.1.2.12
		fkEponRuleClauseControlL2Mac OBJECT-TYPE
			SYNTAX MacAddress
			MAX-ACCESS read-write
			STATUS current
			DESCRIPTION
				"Layer2 Mac address."
			::= { fkEponRuleClauseControl 12 }

		
		-- 1.3.6.1.4.1.10428 9 1.101.20.13.1.2.13
		fkEponRuleClauseControlL2EtherType OBJECT-TYPE
			SYNTAX INTEGER
				{
				null(0),
				ip0x0800(1),
				arp0x0806(2)
				}
			MAX-ACCESS read-write
			STATUS current
			DESCRIPTION
				"Rule Clause L2 Ethertype Value."
			::= { fkEponRuleClauseControl 13 }

		
		-- 1.3.6.1.4.1.10428 9 1.101.20.13.1.2.14
		fkEponRuleClauseControlNetmask OBJECT-TYPE
			SYNTAX Integer32 (1..48)
			MAX-ACCESS read-write
			STATUS current
			DESCRIPTION
				"The netmask.
				1.layer2 range from 1-48
				2.layer3 range from 1-32"
			::= { fkEponRuleClauseControl 14 }

		
		-- 1.3.6.1.4.1.10428 9 1.101.20.13.1.2.15
		fkEponRuleClauseControlL3Addr OBJECT-TYPE
			SYNTAX IpAddress
			MAX-ACCESS read-write
			STATUS current
			DESCRIPTION
				"L3 IP address."
			::= { fkEponRuleClauseControl 15 }

		
		-- 1.3.6.1.4.1.10428 9 1.101.20.13.1.2.16
		fkEponRuleClauseControlTcpUdpPort OBJECT-TYPE
			SYNTAX INTEGER
				{
				srcPort(1),
				desPort(2)
				}
			MAX-ACCESS read-write
			STATUS current
			DESCRIPTION
				"Tcp port or Udp port."
			::= { fkEponRuleClauseControl 16 }

		
		-- 1.3.6.1.4.1.10428 9 1.101.20.13.1.2.17
		fkEponRuleClauseControlTcpUdpPortNum OBJECT-TYPE
			SYNTAX Integer32 (0..65535)
			MAX-ACCESS read-write
			STATUS current
			DESCRIPTION
				"Port number range from 0 to 65535."
			::= { fkEponRuleClauseControl 17 }

		
		-- 1.3.6.1.4.1.10428 9 1.101.20.13.1.2.18
		fkEponRuleClauseControlProtoType OBJECT-TYPE
			SYNTAX INTEGER
				{
				protoType(1),
				slowProtocol(2)
				}
			MAX-ACCESS read-write
			STATUS current
			DESCRIPTION
				"Protocol type
				1.proto-type 
				2.slow-proto 
				ex:For protocol type 1=ICMP 2=IGMP 6=TCP 17=UDP"
			::= { fkEponRuleClauseControl 18 }

		
		-- 1.3.6.1.4.1.10428 9 1.101.20.13.1.2.19
		fkEponRuleClauseControlProtoTypeNum OBJECT-TYPE
			SYNTAX INTEGER (1..255)
			MAX-ACCESS read-write
			STATUS current
			DESCRIPTION
				"For protocol type .ex :1=ICMP 2=IGMP 6=TCP 17=UDP
				The range from 1 to 255."
			::= { fkEponRuleClauseControl 19 }

		
		-- 1.3.6.1.4.1.10428 9 1.101.20.13.1.2.20
		fkEponRuleClauseControlVlanType OBJECT-TYPE
			SYNTAX INTEGER
				{
				svlan0(1),
				svlan1(2),
				cvlan0(3),
				cvlan1(4)
				}
			MAX-ACCESS read-write
			STATUS current
			DESCRIPTION
				"The rule VLAN type."
			::= { fkEponRuleClauseControl 20 }

		
		-- 1.3.6.1.4.1.10428 9 1.101.20.13.1.2.21
		fkEponRuleClauseControlVlanValue OBJECT-TYPE
			SYNTAX Integer32
			MAX-ACCESS read-write
			STATUS current
			DESCRIPTION
				"vlan value."
			::= { fkEponRuleClauseControl 21 }

		
		-- 1.3.6.1.4.1.10428 9 1.101.20.13.1.2.22
		fkEponRuleClauseControlLinkIndexValue OBJECT-TYPE
			SYNTAX INTEGER (1..32)
			MAX-ACCESS read-write
			STATUS current
			DESCRIPTION
				"Link index."
			::= { fkEponRuleClauseControl 22 }

		
		-- 1.3.6.1.4.1.10428 9 1.101.20.13.1.3
		fkEponRuleClauseNotification OBJECT IDENTIFIER ::= { fkEponRuleClause 3 }

		
		-- 1.3.6.1.4.1.10428 9 1.101.20.13.1.3.1
		fkEponRuleClauseQueueChanged NOTIFICATION-TYPE
			OBJECTS { fkEponRuleClauseControlRequest, fkEponRuleClauseControlTimeStamp, fkEponRuleClauseControlReqResult, fkEponRuleClauseControlClauseIndex, fkEponRuleClauseControlQueue, 
				fkEponRuleClauseControlQueueValue }
			STATUS current
			DESCRIPTION 
				"Description."
			::= { fkEponRuleClauseNotification 1 }

		
		-- 1.3.6.1.4.1.10428 9 1.101.20.13.1.3.2
		fkEponRuleClauseLayer2Changed NOTIFICATION-TYPE
			OBJECTS { fkEponRuleClauseControlRequest, fkEponRuleClauseControlTimeStamp, fkEponRuleClauseControlReqResult, fkEponRuleClauseControlClauseIndex, fkEponRuleClauseControlLayerOperation, 
				fkEponRuleClauseControlL2Mac, fkEponRuleClauseControlL2EtherType, fkEponRuleClauseControlNetmask }
			STATUS current
			DESCRIPTION 
				"Description."
			::= { fkEponRuleClauseNotification 2 }

		
		-- 1.3.6.1.4.1.10428 9 1.101.20.13.1.3.3
		fkEponRuleClauseVlanChanged NOTIFICATION-TYPE
			OBJECTS { fkEponRuleClauseControlRequest, fkEponRuleClauseControlTimeStamp, fkEponRuleClauseControlReqResult, fkEponRuleClauseControlClauseIndex, fkEponRuleClauseControlVlanType, 
				fkEponRuleClauseControlVlanValue }
			STATUS current
			DESCRIPTION 
				"Description."
			::= { fkEponRuleClauseNotification 3 }

		
		-- 1.3.6.1.4.1.10428 9 1.101.20.13.1.3.4
		fkEponRuleClauseLayer3Changed NOTIFICATION-TYPE
			OBJECTS { fkEponRuleClauseControlRequest, fkEponRuleClauseControlTimeStamp, fkEponRuleClauseControlReqResult, fkEponRuleClauseControlClauseIndex, fkEponRuleClauseControlTcpUdpPort, 
				fkEponRuleClauseControlTcpUdpPortNum }
			STATUS current
			DESCRIPTION 
				"Description."
			::= { fkEponRuleClauseNotification 4 }

		
		-- 1.3.6.1.4.1.10428 9 1.101.20.13.1.3.5
		fkEponRuleClauseTcpUdpChanged NOTIFICATION-TYPE
			OBJECTS { fkEponRuleClauseControlRequest, fkEponRuleClauseControlTimeStamp, fkEponRuleClauseControlReqResult, fkEponRuleClauseControlClauseIndex, fkEponRuleClauseControlTcpUdpPort, 
				fkEponRuleClauseControlTcpUdpPortNum }
			STATUS current
			DESCRIPTION 
				"Description."
			::= { fkEponRuleClauseNotification 5 }

		
		-- 1.3.6.1.4.1.10428 9 1.101.20.13.1.3.6
		fkEponRuleClauseProtocolChanged NOTIFICATION-TYPE
			OBJECTS { fkEponRuleClauseControlRequest, fkEponRuleClauseControlTimeStamp, fkEponRuleClauseControlReqResult, fkEponRuleClauseControlClauseIndex, fkEponRuleClauseControlProtoType, 
				fkEponRuleClauseControlProtoTypeNum }
			STATUS current
			DESCRIPTION 
				"Description."
			::= { fkEponRuleClauseNotification 6 }

		
		-- 1.3.6.1.4.1.10428 9 1.101.20.13.1.3.7
		fkEponRuleClauseLinkIndexChanged NOTIFICATION-TYPE
			OBJECTS { fkEponRuleClauseControlRequest, fkEponRuleClauseControlTimeStamp, fkEponRuleClauseControlReqResult, fkEponRuleClauseControlClauseIndex, fkEponRuleClauseControlLinkIndexValue
				 }
			STATUS current
			DESCRIPTION 
				"Description."
			::= { fkEponRuleClauseNotification 7 }

		
		-- 1.3.6.1.4.1.10428 9 1.101.20.13.1.3.8
		fkEponRuleClauseDel NOTIFICATION-TYPE
			OBJECTS { fkEponRuleClauseControlRequest, fkEponRuleClauseControlTimeStamp, fkEponRuleClauseControlReqResult, fkEponRuleClauseControlClauseIndex }
			STATUS current
			DESCRIPTION 
				"Description."
			::= { fkEponRuleClauseNotification 8 }

		
		-- 1.3.6.1.4.1.10428 9 1.101.20.13.2
		fkEponRuleAction OBJECT IDENTIFIER ::= { fkEponRule 2 }

		
		-- 1.3.6.1.4.1.10428 9 1.101.20.13.2.1
		fkEponRuleActionTable OBJECT-TYPE
			SYNTAX SEQUENCE OF FkEponRuleActionEntry
			MAX-ACCESS not-accessible
			STATUS current
			DESCRIPTION
				"Description."
			::= { fkEponRuleAction 1 }

		
		-- 1.3.6.1.4.1.10428 9 1.101.20.13.2.1.1
		fkEponRuleActionEntry OBJECT-TYPE
			SYNTAX FkEponRuleActionEntry
			MAX-ACCESS not-accessible
			STATUS current
			DESCRIPTION
				"Description."
			INDEX { fkEponOltIndex }
			::= { fkEponRuleActionTable 1 }

		
		FkEponRuleActionEntry ::=
			SEQUENCE { 
				fkEponRuleActionVlanOperate
					INTEGER,
				fkEponRuleActionVlanMap
					INTEGER,
				fkEponRuleActionEtherType
					OCTET STRING,
				fkEponRuleActionVlanID
					Integer32,
				fkEponRuleActionDiscardOperate
					INTEGER,
				fkEponRuleActionDiscardOperateValue
					INTEGER,
				fkEponRuleActionCaptureHostOperate
					INTEGER,
				fkEponRuleActionCaptureHostFlexibleOperate
					INTEGER,
				fkEponRuleActionQueueId
					Integer32,
				fkEponRuleActionUnicastLinkDestID
					Integer32,
				fkEponRuleActionUnicastLinkDestOffset
					Integer32,
				fkEponRuleActionMulticastLinkDomID
					Integer32,
				fkEponRuleActionMulticastLinkDomOffset
					Integer32,
				fkEponRuleActionCosOperate
					INTEGER,
				fkEponRuleActionCosValue
					Integer32,
				fkEponRuleActionTosOperate
					INTEGER,
				fkEponRuleActionTosValue
					Integer32,
				fkEponRuleActionOutputOperate
					INTEGER,
				fkEponRuleActionOutputValue
					Integer32,
				fkEponRuleActionOutputVlanContent
					INTEGER,
				fkEponRuleActionOutputSourceFiledCopy
					INTEGER,
				fkEponRuleActionQueuePendingOperate
					INTEGER
			 }

		-- 1.3.6.1.4.1.10428 9 1.101.20.13.2.1.1.1
		fkEponRuleActionVlanOperate OBJECT-TYPE
			SYNTAX INTEGER
				{
				addEthertype(1),
				clearAdd(2),
				clearDelete(3),
				delete(4),
				addNoEthertype(5)
				}
			MAX-ACCESS read-only
			STATUS current
			DESCRIPTION
				"Vlan Operate."
			::= { fkEponRuleActionEntry 1 }

		
		-- 1.3.6.1.4.1.10428 9 1.101.20.13.2.1.1.2
		fkEponRuleActionVlanMap OBJECT-TYPE
			SYNTAX INTEGER (0..15)
			MAX-ACCESS read-only
			STATUS current
			DESCRIPTION
				"VLAN map:0-null,1-Vlan0,2-Vlan1,4-Vlan2
				VLAN map:0x01-vlan0  0x02-vlan1  0x04-vlan2  0x08-vlan3
				"
			::= { fkEponRuleActionEntry 2 }

		
		-- 1.3.6.1.4.1.10428 9 1.101.20.13.2.1.1.3
		fkEponRuleActionEtherType OBJECT-TYPE
			SYNTAX OCTET STRING
			MAX-ACCESS read-only
			STATUS current
			DESCRIPTION
				"Ether Type.
				"
			::= { fkEponRuleActionEntry 3 }

		
		-- 1.3.6.1.4.1.10428 9 1.101.20.13.2.1.1.4
		fkEponRuleActionVlanID OBJECT-TYPE
			SYNTAX Integer32
			MAX-ACCESS read-only
			STATUS current
			DESCRIPTION
				"vlan ID.Range from 1 to 4096"
			::= { fkEponRuleActionEntry 4 }

		
		-- 1.3.6.1.4.1.10428 9 1.101.20.13.2.1.1.5
		fkEponRuleActionDiscardOperate OBJECT-TYPE
			SYNTAX INTEGER
				{
				discard(1),
				cleardiscard(2)
				}
			MAX-ACCESS read-only
			STATUS current
			DESCRIPTION
				"port map operate
				discard(1),
				clear-discard(2)"
			::= { fkEponRuleActionEntry 5 }

		
		-- 1.3.6.1.4.1.10428 9 1.101.20.13.2.1.1.6
		fkEponRuleActionDiscardOperateValue OBJECT-TYPE
			SYNTAX INTEGER
				{
				eponPort(1),
				eponPort1(2),
				nniPort0(4),
				nniPort1(8)
				}
			MAX-ACCESS read-only
			STATUS current
			DESCRIPTION
				"Port map:Epon-port0 x01, Epon-port1 0x02 ,NNI-port0 0x04 ,NNI-port1 0x08."
			::= { fkEponRuleActionEntry 6 }

		
		-- 1.3.6.1.4.1.10428 9 1.101.20.13.2.1.1.7
		fkEponRuleActionCaptureHostOperate OBJECT-TYPE
			SYNTAX INTEGER
				{
				premod(1),
				postmod(2),
				premodd(3),
				postmodd(4)
				}
			MAX-ACCESS read-only
			STATUS current
			DESCRIPTION
				"Capture to host operate
				pre-mod(1),Pre-modifications
				post-mod(2),Post-modifications
				pre-mod-d(3),Pre-modifications with domain/destination
				post-mod-d(4),Post-modifications with domain/destination"
			::= { fkEponRuleActionEntry 7 }

		
		-- 1.3.6.1.4.1.10428 9 1.101.20.13.2.1.1.8
		fkEponRuleActionCaptureHostFlexibleOperate OBJECT-TYPE
			SYNTAX INTEGER
				{
				preMod(1),
				domDest(2),
				queuePend(3),
				clearD(4)
				}
			MAX-ACCESS read-only
			STATUS current
			DESCRIPTION
				"Capture Host Flexible Operate."
			::= { fkEponRuleActionEntry 8 }

		
		-- 1.3.6.1.4.1.10428 9 1.101.20.13.2.1.1.9
		fkEponRuleActionQueueId OBJECT-TYPE
			SYNTAX Integer32
			MAX-ACCESS read-only
			STATUS current
			DESCRIPTION
				"Queue Id."
			::= { fkEponRuleActionEntry 9 }

		
		-- 1.3.6.1.4.1.10428 9 1.101.20.13.2.1.1.10
		fkEponRuleActionUnicastLinkDestID OBJECT-TYPE
			SYNTAX Integer32
			MAX-ACCESS read-only
			STATUS current
			DESCRIPTION
				"Destination ID on which to set the link"
			::= { fkEponRuleActionEntry 10 }

		
		-- 1.3.6.1.4.1.10428 9 1.101.20.13.2.1.1.11
		fkEponRuleActionUnicastLinkDestOffset OBJECT-TYPE
			SYNTAX Integer32
			MAX-ACCESS read-only
			STATUS current
			DESCRIPTION
				"Offset to the link within the destination"
			::= { fkEponRuleActionEntry 11 }

		
		-- 1.3.6.1.4.1.10428 9 1.101.20.13.2.1.1.12
		fkEponRuleActionMulticastLinkDomID OBJECT-TYPE
			SYNTAX Integer32
			MAX-ACCESS read-only
			STATUS current
			DESCRIPTION
				"Domain ID on which to set the multicast link
				"
			::= { fkEponRuleActionEntry 12 }

		
		-- 1.3.6.1.4.1.10428 9 1.101.20.13.2.1.1.13
		fkEponRuleActionMulticastLinkDomOffset OBJECT-TYPE
			SYNTAX Integer32
			MAX-ACCESS read-only
			STATUS current
			DESCRIPTION
				"Offset to the multicast link within the domain."
			::= { fkEponRuleActionEntry 13 }

		
		-- 1.3.6.1.4.1.10428 9 1.101.20.13.2.1.1.14
		fkEponRuleActionCosOperate OBJECT-TYPE
			SYNTAX INTEGER
				{
				cos(1),
				cosRegTag(2),
				cosCopy(3),
				cosClear(4)
				}
			MAX-ACCESS read-write
			STATUS current
			DESCRIPTION
				"Cos Operate."
			::= { fkEponRuleActionEntry 14 }

		
		-- 1.3.6.1.4.1.10428 9 1.101.20.13.2.1.1.15
		fkEponRuleActionCosValue OBJECT-TYPE
			SYNTAX Integer32
			MAX-ACCESS read-write
			STATUS current
			DESCRIPTION
				"Cos Value."
			::= { fkEponRuleActionEntry 15 }

		
		-- 1.3.6.1.4.1.10428 9 1.101.20.13.2.1.1.16
		fkEponRuleActionTosOperate OBJECT-TYPE
			SYNTAX INTEGER
				{
				tos(1),
				tosClear(2)
				}
			MAX-ACCESS read-write
			STATUS current
			DESCRIPTION
				"Tos Operate."
			::= { fkEponRuleActionEntry 16 }

		
		-- 1.3.6.1.4.1.10428 9 1.101.20.13.2.1.1.17
		fkEponRuleActionTosValue OBJECT-TYPE
			SYNTAX Integer32
			MAX-ACCESS read-write
			STATUS current
			DESCRIPTION
				"tos value."
			::= { fkEponRuleActionEntry 17 }

		
		-- 1.3.6.1.4.1.10428 9 1.101.20.13.2.1.1.18
		fkEponRuleActionOutputOperate OBJECT-TYPE
			SYNTAX INTEGER
				{
				and(1),
				or(2),
				set(3),
				add(4),
				copy(5)
				}
			MAX-ACCESS read-only
			STATUS current
			DESCRIPTION
				"Rule action output on the selected field
				1.and,Perform a binary AND on the selected field
				2.or,Perform a binary OR on the selected field
				3.set,Set the selected field
				4.add,Add the selected field
				5.copy,Copy the selected field from another field."
			::= { fkEponRuleActionEntry 18 }

		
		-- 1.3.6.1.4.1.10428 9 1.101.20.13.2.1.1.19
		fkEponRuleActionOutputValue OBJECT-TYPE
			SYNTAX Integer32
			MAX-ACCESS read-write
			STATUS current
			DESCRIPTION
				"output value."
			::= { fkEponRuleActionEntry 19 }

		
		-- 1.3.6.1.4.1.10428 9 1.101.20.13.2.1.1.20
		fkEponRuleActionOutputVlanContent OBJECT-TYPE
			SYNTAX INTEGER (0..8)
			MAX-ACCESS read-only
			STATUS current
			DESCRIPTION
				"0-3 vlan0 4-7 vlan1(0-TPID 1-CoS 2-VID 3-CoS and VID 4-TPID 5-CoS 6-VID 7-CoS and VID 8-IPv4 ToS
				"
			::= { fkEponRuleActionEntry 20 }

		
		-- 1.3.6.1.4.1.10428 9 1.101.20.13.2.1.1.21
		fkEponRuleActionOutputSourceFiledCopy OBJECT-TYPE
			SYNTAX INTEGER (0..25)
			MAX-ACCESS read-only
			STATUS current
			DESCRIPTION
				"Source field for the copy."
			::= { fkEponRuleActionEntry 21 }

		
		-- 1.3.6.1.4.1.10428 9 1.101.20.13.2.1.1.22
		fkEponRuleActionQueuePendingOperate OBJECT-TYPE
			SYNTAX INTEGER
				{
				set(1),
				clear(2)
				}
			MAX-ACCESS read-only
			STATUS current
			DESCRIPTION
				"queue-pending operate."
			::= { fkEponRuleActionEntry 22 }

		
		-- 1.3.6.1.4.1.10428 9 1.101.20.13.2.2
		fkEponRuleActionControl OBJECT IDENTIFIER ::= { fkEponRuleAction 2 }

		
		-- 1.3.6.1.4.1.10428 9 1.101.20.13.2.2.1
		fkEponRuleActionControlRequest OBJECT-TYPE
			SYNTAX INTEGER
				{
				ruleActionVlanSet(1),
				ruleActionDiscardSet(2),
				ruleActionCaptureHostSet(3),
				ruleActionCaptureHostFlexibleSet(4),
				ruleActionQueueSet(5),
				ruleActionUnicastLinkSet(6),
				ruleActionMulticastLinkSet(7),
				ruleActionNoOperation(8),
				ruleActionCosSet(9),
				ruleActionTosSet(10),
				ruleActionOutputSet(11),
				ruleActionQueuePendingSet(12),
				ruleActionFkSet(13),
				noRuleAction(14)
				}
			MAX-ACCESS read-write
			STATUS current
			DESCRIPTION
				"The request of a user command."
			::= { fkEponRuleActionControl 1 }

		
		-- 1.3.6.1.4.1.10428 9 1.101.20.13.2.2.2
		fkEponRuleActionControlStatus OBJECT-TYPE
			SYNTAX FkControlStatusType
			MAX-ACCESS read-only
			STATUS current
			DESCRIPTION
				"The status of user command"
			::= { fkEponRuleActionControl 2 }

		
		-- 1.3.6.1.4.1.10428 9 1.101.20.13.2.2.3
		fkEponRuleActionControlTimer OBJECT-TYPE
			SYNTAX Gauge32
			MAX-ACCESS read-write
			STATUS current
			DESCRIPTION
				"The maximum time for the manager for a long running user command."
			::= { fkEponRuleActionControl 3 }

		
		-- 1.3.6.1.4.1.10428 9 1.101.20.13.2.2.4
		fkEponRuleActionControlTimeStamp OBJECT-TYPE
			SYNTAX TimeTicks
			MAX-ACCESS read-only
			STATUS current
			DESCRIPTION
				"The time stamp of the last command(end of command)"
			::= { fkEponRuleActionControl 4 }

		
		-- 1.3.6.1.4.1.10428 9 1.101.20.13.2.2.5
		fkEponRuleActionControlReqResult OBJECT-TYPE
			SYNTAX FkControlRequestResultType
			MAX-ACCESS read-only
			STATUS current
			DESCRIPTION
				"The result of the last user command"
			::= { fkEponRuleActionControl 5 }

		
		-- 1.3.6.1.4.1.10428 9 1.101.20.13.2.2.6
		fkEponRuleActionControlIndex OBJECT-TYPE
			SYNTAX Integer32
			MAX-ACCESS read-write
			STATUS current
			DESCRIPTION
				"Rule action index."
			::= { fkEponRuleActionControl 6 }

		
		-- 1.3.6.1.4.1.10428 9 1.101.20.13.2.2.7
		fkEponRuleActionControlVlanOperate OBJECT-TYPE
			SYNTAX INTEGER
				{
				addEthertype(1),
				clearAdd(2),
				clearD(3),
				delete(4),
				addNoEthertype(5)
				}
			MAX-ACCESS read-write
			STATUS current
			DESCRIPTION
				"Vlan Operate.
				"
			::= { fkEponRuleActionControl 7 }

		
		-- 1.3.6.1.4.1.10428 9 1.101.20.13.2.2.8
		fkEponRuleActionControlVlanMap OBJECT-TYPE
			SYNTAX INTEGER (0..15)
			MAX-ACCESS read-write
			STATUS current
			DESCRIPTION
				"Rule action VLAN map:0-null,1-Vlan0,2-Vlan1,4-Vlan2.
				Rule action cos copy VLAN map:0x01-vlan0  0x02-vlan1  0x04-vlan2  0x08-vlan3."
			::= { fkEponRuleActionControl 8 }

		
		-- 1.3.6.1.4.1.10428 9 1.101.20.13.2.2.9
		fkEponRuleActionControlEtherType OBJECT-TYPE
			SYNTAX OCTET STRING
			MAX-ACCESS read-write
			STATUS current
			DESCRIPTION
				"Ethernet Type."
			::= { fkEponRuleActionControl 9 }

		
		-- 1.3.6.1.4.1.10428 9 1.101.20.13.2.2.10
		fkEponRuleActionControlVlanID OBJECT-TYPE
			SYNTAX Integer32 (1..4096)
			MAX-ACCESS read-write
			STATUS current
			DESCRIPTION
				"vlan ID.Range from 1 to 4096."
			::= { fkEponRuleActionControl 10 }

		
		-- 1.3.6.1.4.1.10428 9 1.101.20.13.2.2.11
		fkEponRuleActionControlDiscardOperate OBJECT-TYPE
			SYNTAX INTEGER
				{
				discard(1),
				clearDdiscard(2)
				}
			MAX-ACCESS read-write
			STATUS current
			DESCRIPTION
				"discard operate.
				"
			::= { fkEponRuleActionControl 11 }

		
		-- 1.3.6.1.4.1.10428 9 1.101.20.13.2.2.12
		fkEponRuleActionControlDiscardOperateValue OBJECT-TYPE
			SYNTAX INTEGER
				{
				eponPort(1),
				eponPort1(2),
				nniPort0(4),
				nniPort1(8)
				}
			MAX-ACCESS read-write
			STATUS current
			DESCRIPTION
				"Port map:Epon-port0 x01, Epon-port1 0x02 ,NNI-port0 0x04 ,NNI-port1 0x08."
			::= { fkEponRuleActionControl 12 }

		
		-- 1.3.6.1.4.1.10428 9 1.101.20.13.2.2.13
		fkEponRuleActionControlCaptureHostOperate OBJECT-TYPE
			SYNTAX INTEGER
				{
				preMod(1),
				postMod(2),
				preModD(3),
				postModD(4)
				}
			MAX-ACCESS read-write
			STATUS current
			DESCRIPTION
				"Capture to host operate."
			::= { fkEponRuleActionControl 13 }

		
		-- 1.3.6.1.4.1.10428 9 1.101.20.13.2.2.14
		fkEponRuleActionControlCaptureHostFlexibleOperate OBJECT-TYPE
			SYNTAX INTEGER
				{
				perMod(1),
				domDest(2),
				queuePend(3),
				clearD(4)
				}
			MAX-ACCESS read-write
			STATUS current
			DESCRIPTION
				"Capture Host Flexible Operate."
			::= { fkEponRuleActionControl 14 }

		
		-- 1.3.6.1.4.1.10428 9 1.101.20.13.2.2.15
		fkEponRuleActionControlQueueId OBJECT-TYPE
			SYNTAX Integer32
			MAX-ACCESS read-write
			STATUS current
			DESCRIPTION
				"QueueId."
			::= { fkEponRuleActionControl 15 }

		
		-- 1.3.6.1.4.1.10428 9 1.101.20.13.2.2.16
		fkEponRuleActionControlQueuependingOperate OBJECT-TYPE
			SYNTAX INTEGER
				{
				set(1),
				clear(2)
				}
			MAX-ACCESS read-write
			STATUS current
			DESCRIPTION
				"queue-pending operate."
			::= { fkEponRuleActionControl 16 }

		
		-- 1.3.6.1.4.1.10428 9 1.101.20.13.2.2.17
		fkEponRuleActionControlUnicastLinkDestID OBJECT-TYPE
			SYNTAX Integer32
			MAX-ACCESS read-write
			STATUS current
			DESCRIPTION
				"Destination ID on which to set the link."
			::= { fkEponRuleActionControl 17 }

		
		-- 1.3.6.1.4.1.10428 9 1.101.20.13.2.2.18
		fkEponRuleActionControlUnicastLinkDestOffset OBJECT-TYPE
			SYNTAX Integer32
			MAX-ACCESS read-write
			STATUS current
			DESCRIPTION
				"Offset to the link within the destination."
			::= { fkEponRuleActionControl 18 }

		
		-- 1.3.6.1.4.1.10428 9 1.101.20.13.2.2.19
		fkEponRuleActionControlMulticastLinkDomID OBJECT-TYPE
			SYNTAX Integer32
			MAX-ACCESS read-write
			STATUS current
			DESCRIPTION
				"Domain ID on which to set the multicast link."
			::= { fkEponRuleActionControl 19 }

		
		-- 1.3.6.1.4.1.10428 9 1.101.20.13.2.2.20
		fkEponRuleActionControlMulticastLinkDomOffset OBJECT-TYPE
			SYNTAX Integer32
			MAX-ACCESS read-write
			STATUS current
			DESCRIPTION
				"Offset to the multicast link within the domain."
			::= { fkEponRuleActionControl 20 }

		
		-- 1.3.6.1.4.1.10428 9 1.101.20.13.2.2.21
		fkEponRuleActionControlCosOperate OBJECT-TYPE
			SYNTAX INTEGER
				{
				cos(1),
				cosRepTag(2),
				cosCopy(3),
				cosClear(4)
				}
			MAX-ACCESS read-write
			STATUS current
			DESCRIPTION
				"cos operate.
				"
			::= { fkEponRuleActionControl 21 }

		
		-- 1.3.6.1.4.1.10428 9 1.101.20.13.2.2.22
		fkEponRuleActionControlCosValue OBJECT-TYPE
			SYNTAX Integer32
			MAX-ACCESS read-write
			STATUS current
			DESCRIPTION
				"cos value."
			::= { fkEponRuleActionControl 22 }

		
		-- 1.3.6.1.4.1.10428 9 1.101.20.13.2.2.23
		fkEponRuleActionControlTosOperate OBJECT-TYPE
			SYNTAX INTEGER
				{
				tos(1),
				tosClear(2)
				}
			MAX-ACCESS read-write
			STATUS current
			DESCRIPTION
				"tos operate."
			::= { fkEponRuleActionControl 23 }

		
		-- 1.3.6.1.4.1.10428 9 1.101.20.13.2.2.24
		fkEponRuleActionControlTosValue OBJECT-TYPE
			SYNTAX Integer32
			MAX-ACCESS read-write
			STATUS current
			DESCRIPTION
				"tos value."
			::= { fkEponRuleActionControl 24 }

		
		-- 1.3.6.1.4.1.10428 9 1.101.20.13.2.2.25
		fkEponRuleActionControlOutputOperate OBJECT-TYPE
			SYNTAX INTEGER
				{
				and(1),
				or(2),
				set(3),
				add(4),
				copy(5)
				}
			MAX-ACCESS read-write
			STATUS current
			DESCRIPTION
				"Rule action output on the selected field
				1.and,Perform a binary AND on the selected field
				2.or,Perform a binary OR on the selected field
				3.set,Set the selected field
				4.add,Add the selected field
				5.copy,Copy the selected field from another field.
				"
			::= { fkEponRuleActionControl 25 }

		
		-- 1.3.6.1.4.1.10428 9 1.101.20.13.2.2.26
		fkEponRuleActionControlOutputValue OBJECT-TYPE
			SYNTAX Integer32
			MAX-ACCESS read-write
			STATUS current
			DESCRIPTION
				"output value."
			::= { fkEponRuleActionControl 26 }

		
		-- 1.3.6.1.4.1.10428 9 1.101.20.13.2.2.27
		fkEponRuleActionControlOutputVlanContent OBJECT-TYPE
			SYNTAX INTEGER (0..8)
			MAX-ACCESS read-write
			STATUS current
			DESCRIPTION
				"0-3 vlan0 4-7 vlan1(0-TPID 1-CoS 2-VID 3-CoS and VID 4-TPID 5-CoS 6-VID 7-CoS and VID 8-IPv4 ToS."
			::= { fkEponRuleActionControl 27 }

		
		-- 1.3.6.1.4.1.10428 9 1.101.20.13.2.2.28
		fkEponRuleActionControlOutputSourceFiledCopy OBJECT-TYPE
			SYNTAX Integer32 (1..25)
			MAX-ACCESS read-write
			STATUS current
			DESCRIPTION
				"Source field for the copy."
			::= { fkEponRuleActionControl 28 }

		
		-- 1.3.6.1.4.1.10428 9 1.101.20.13.2.3
		fkEponRuleActionNotification OBJECT IDENTIFIER ::= { fkEponRuleAction 3 }

		
		-- 1.3.6.1.4.1.10428 9 1.101.20.13.2.3.1
		fkEponRuleActionVlanChanged NOTIFICATION-TYPE
			OBJECTS { fkEponRuleActionControlRequest, fkEponRuleActionControlTimeStamp, fkEponRuleActionControlReqResult, fkEponRuleActionControlIndex, fkEponRuleActionControlVlanOperate, 
				fkEponRuleActionControlVlanMap, fkEponRuleActionControlEtherType, fkEponRuleActionControlVlanID }
			STATUS current
			DESCRIPTION 
				"Description."
			::= { fkEponRuleActionNotification 1 }

		
		-- 1.3.6.1.4.1.10428 9 1.101.20.13.2.3.2
		fkEponRuleActionDiscardChanged NOTIFICATION-TYPE
			OBJECTS { fkEponRuleActionControlRequest, fkEponRuleActionControlTimeStamp, fkEponRuleActionControlReqResult, fkEponRuleActionControlIndex, fkEponRuleActionControlDiscardOperate, 
				fkEponRuleActionControlDiscardOperateValue }
			STATUS current
			DESCRIPTION 
				"Description."
			::= { fkEponRuleActionNotification 2 }

		
		-- 1.3.6.1.4.1.10428 9 1.101.20.13.2.3.3
		fkEponRuleActionCaptureHostChanged NOTIFICATION-TYPE
			OBJECTS { fkEponRuleActionControlRequest, fkEponRuleActionControlTimeStamp, fkEponRuleActionControlReqResult, fkEponRuleActionControlIndex, fkEponRuleActionControlCaptureHostOperate
				 }
			STATUS current
			DESCRIPTION 
				"Description."
			::= { fkEponRuleActionNotification 3 }

		
		-- 1.3.6.1.4.1.10428 9 1.101.20.13.2.3.4
		fkEponRuleActionCaptureHostFlexibleChanged NOTIFICATION-TYPE
			OBJECTS { fkEponRuleActionControlRequest, fkEponRuleActionControlTimeStamp, fkEponRuleActionControlReqResult, fkEponRuleActionControlIndex, fkEponRuleActionControlCaptureHostFlexibleOperate
				 }
			STATUS current
			DESCRIPTION 
				"Description."
			::= { fkEponRuleActionNotification 4 }

		
		-- 1.3.6.1.4.1.10428 9 1.101.20.13.2.3.5
		fkEponRuleActionQueueChanged NOTIFICATION-TYPE
			OBJECTS { fkEponRuleActionControlRequest, fkEponRuleActionControlTimeStamp, fkEponRuleActionControlReqResult, fkEponRuleActionControlIndex, fkEponRuleActionControlQueueId
				 }
			STATUS current
			DESCRIPTION 
				"Description."
			::= { fkEponRuleActionNotification 5 }

		
		-- 1.3.6.1.4.1.10428 9 1.101.20.13.2.3.6
		fkEponRuleActionUnicastLinkChanged NOTIFICATION-TYPE
			OBJECTS { fkEponRuleActionControlRequest, fkEponRuleActionControlTimeStamp, fkEponRuleActionControlReqResult, fkEponRuleActionControlIndex, fkEponRuleActionControlUnicastLinkDestID, 
				fkEponRuleActionControlUnicastLinkDestOffset }
			STATUS current
			DESCRIPTION 
				"Description."
			::= { fkEponRuleActionNotification 6 }

		
		-- 1.3.6.1.4.1.10428 9 1.101.20.13.2.3.7
		fkEponRuleActionMulticastLinkChanged NOTIFICATION-TYPE
			OBJECTS { fkEponRuleActionControlRequest, fkEponRuleActionControlTimeStamp, fkEponRuleActionControlReqResult, fkEponRuleActionControlMulticastLinkDomID, fkEponRuleActionControlMulticastLinkDomOffset
				 }
			STATUS current
			DESCRIPTION 
				"Description."
			::= { fkEponRuleActionNotification 7 }

		
		-- 1.3.6.1.4.1.10428 9 1.101.20.13.2.3.8
		fkEponRuleActionNoOperation NOTIFICATION-TYPE
			OBJECTS { fkEponRuleActionControlRequest, fkEponRuleActionControlTimeStamp, fkEponRuleActionControlReqResult, fkEponRuleActionControlIndex }
			STATUS current
			DESCRIPTION 
				"Description."
			::= { fkEponRuleActionNotification 8 }

		
		-- 1.3.6.1.4.1.10428 9 1.101.20.13.2.3.9
		fkEponRuleActionCosChanged NOTIFICATION-TYPE
			OBJECTS { fkEponRuleActionControlRequest, fkEponRuleActionControlTimeStamp, fkEponRuleActionControlReqResult, fkEponRuleActionControlIndex, fkEponRuleActionControlCosOperate, 
				fkEponRuleActionControlCosValue }
			STATUS current
			DESCRIPTION 
				"Description."
			::= { fkEponRuleActionNotification 9 }

		
		-- 1.3.6.1.4.1.10428 9 1.101.20.13.2.3.10
		fkEponRuleActionTosChanged NOTIFICATION-TYPE
			OBJECTS { fkEponRuleActionControlRequest, fkEponRuleActionControlTimeStamp, fkEponRuleActionControlReqResult, fkEponRuleActionControlIndex, fkEponRuleActionControlTosOperate, 
				fkEponRuleActionControlTosValue }
			STATUS current
			DESCRIPTION 
				"Description."
			::= { fkEponRuleActionNotification 10 }

		
		-- 1.3.6.1.4.1.10428 9 1.101.20.13.2.3.11
		fkEponRuleActionOutputChanged NOTIFICATION-TYPE
			OBJECTS { fkEponRuleActionControlRequest, fkEponRuleActionControlTimeStamp, fkEponRuleActionControlReqResult, fkEponRuleActionControlIndex, fkEponRuleActionControlOutputOperate, 
				fkEponRuleActionControlOutputValue, fkEponRuleActionControlOutputSourceFiledCopy }
			STATUS current
			DESCRIPTION 
				"Description."
			::= { fkEponRuleActionNotification 11 }

		
		-- 1.3.6.1.4.1.10428 9 1.101.20.13.2.3.12
		fkEponRuleActionQueuePendingChanged NOTIFICATION-TYPE
			OBJECTS { fkEponRuleActionControlRequest, fkEponRuleActionControlTimeStamp, fkEponRuleActionControlReqResult, fkEponRuleActionControlQueueId }
			STATUS current
			DESCRIPTION 
				"Description."
			::= { fkEponRuleActionNotification 12 }

		
		-- 1.3.6.1.4.1.10428 9 1.101.20.13.2.3.13
		fkEponRuleActionFkChanged NOTIFICATION-TYPE
			OBJECTS { fkEponRuleActionControlRequest, fkEponRuleActionControlTimeStamp, fkEponRuleActionControlReqResult, fkEponRuleActionControlIndex }
			STATUS current
			DESCRIPTION 
				"Description."
			::= { fkEponRuleActionNotification 13 }

		
		-- 1.3.6.1.4.1.10428 9 1.101.20.13.2.3.14
		fkEponRuleActionNoRuleAction NOTIFICATION-TYPE
			OBJECTS { fkEponProfilePortControlRequest, fkEponRuleActionControlRequest, fkEponRuleActionControlTimeStamp, fkEponRuleActionControlReqResult, fkEponRuleActionControlIndex
				 }
			STATUS current
			DESCRIPTION 
				"Description."
			::= { fkEponRuleActionNotification 14 }

		
		-- 1.3.6.1.4.1.10428 9 1.101.20.13.3
		fkEponRuleModify OBJECT IDENTIFIER ::= { fkEponRule 3 }

		
		-- 1.3.6.1.4.1.10428 9 1.101.20.13.3.1
		fkEponRuleModifyTable OBJECT-TYPE
			SYNTAX SEQUENCE OF FkEponRuleModifyEntry
			MAX-ACCESS not-accessible
			STATUS current
			DESCRIPTION
				"Description."
			::= { fkEponRuleModify 1 }

		
		-- 1.3.6.1.4.1.10428 9 1.101.20.13.3.1.1
		fkEponRuleModifyEntry OBJECT-TYPE
			SYNTAX FkEponRuleModifyEntry
			MAX-ACCESS not-accessible
			STATUS current
			DESCRIPTION
				"Description."
			INDEX { fkEponOltIndex }
			::= { fkEponRuleModifyTable 1 }

		
		FkEponRuleModifyEntry ::=
			SEQUENCE { 
				fkEponRuleModifyRuleName
					OCTET STRING,
				fkEponRuleModifyTrafficDirection
					INTEGER,
				fkEponRuleModifyPriorityValue
					INTEGER,
				fkEponRuleModifyCIndex
					OCTET STRING,
				fkEponRuleModifyAIndex
					OCTET STRING
			 }

		-- 1.3.6.1.4.1.10428 9 1.101.20.13.3.1.1.1
		fkEponRuleModifyRuleName OBJECT-TYPE
			SYNTAX OCTET STRING
			MAX-ACCESS read-only
			STATUS current
			DESCRIPTION
				"Pon rule name."
			::= { fkEponRuleModifyEntry 1 }

		
		-- 1.3.6.1.4.1.10428 9 1.101.20.13.3.1.1.2
		fkEponRuleModifyTrafficDirection OBJECT-TYPE
			SYNTAX INTEGER
				{
				downstream(1),
				upstream(2)
				}
			MAX-ACCESS read-only
			STATUS current
			DESCRIPTION
				"The traffic direction of Rule .
				"
			::= { fkEponRuleModifyEntry 2 }

		
		-- 1.3.6.1.4.1.10428 9 1.101.20.13.3.1.1.3
		fkEponRuleModifyPriorityValue OBJECT-TYPE
			SYNTAX INTEGER (0..15)
			MAX-ACCESS read-only
			STATUS current
			DESCRIPTION
				"Priority Value."
			::= { fkEponRuleModifyEntry 3 }

		
		-- 1.3.6.1.4.1.10428 9 1.101.20.13.3.1.1.4
		fkEponRuleModifyCIndex OBJECT-TYPE
			SYNTAX OCTET STRING
			MAX-ACCESS read-only
			STATUS current
			DESCRIPTION
				"Rule clause index."
			::= { fkEponRuleModifyEntry 4 }

		
		-- 1.3.6.1.4.1.10428 9 1.101.20.13.3.1.1.5
		fkEponRuleModifyAIndex OBJECT-TYPE
			SYNTAX OCTET STRING
			MAX-ACCESS read-only
			STATUS current
			DESCRIPTION
				"Rule action index."
			::= { fkEponRuleModifyEntry 5 }

		
		-- 1.3.6.1.4.1.10428 9 1.101.20.13.3.2
		fkEponRuleModifyControl OBJECT IDENTIFIER ::= { fkEponRuleModify 2 }

		
		-- 1.3.6.1.4.1.10428 9 1.101.20.13.3.2.1
		fkEponRuleModifyControlRequest OBJECT-TYPE
			SYNTAX INTEGER
				{
				ponRuleCreate(1),
				ponRuleModifyPriority(2),
				ponRuleModifyTrafficDir(3),
				ponRuleModifyClauseAdd(4),
				ponRuleModifyActionAdd(5),
				ponRuleModifyClauseDel(6),
				ponRuleModifyActionDel(7),
				noPonRule(8),
				oltRuleAddApply(9),
				oltRuleDelApply(10)
				}
			MAX-ACCESS read-write
			STATUS current
			DESCRIPTION
				"The request of a user command."
			::= { fkEponRuleModifyControl 1 }

		
		-- 1.3.6.1.4.1.10428 9 1.101.20.13.3.2.2
		fkEponRuleModifyControlStatus OBJECT-TYPE
			SYNTAX FkControlStatusType
			MAX-ACCESS read-only
			STATUS current
			DESCRIPTION
				"The status of user command"
			::= { fkEponRuleModifyControl 2 }

		
		-- 1.3.6.1.4.1.10428 9 1.101.20.13.3.2.3
		fkEponRuleModifyControlTimer OBJECT-TYPE
			SYNTAX Gauge32
			MAX-ACCESS read-write
			STATUS current
			DESCRIPTION
				"The maximum time for the manager for a long running user command"
			::= { fkEponRuleModifyControl 3 }

		
		-- 1.3.6.1.4.1.10428 9 1.101.20.13.3.2.4
		fkEponRuleModifyControlTimeStamp OBJECT-TYPE
			SYNTAX TimeTicks
			MAX-ACCESS read-only
			STATUS current
			DESCRIPTION
				"The time stamp of the last command(end of command)"
			::= { fkEponRuleModifyControl 4 }

		
		-- 1.3.6.1.4.1.10428 9 1.101.20.13.3.2.5
		fkEponRuleModifyControlReqResult OBJECT-TYPE
			SYNTAX FkControlRequestResultType
			MAX-ACCESS read-only
			STATUS current
			DESCRIPTION
				"The result of the last user command"
			::= { fkEponRuleModifyControl 5 }

		
		-- 1.3.6.1.4.1.10428 9 1.101.20.13.3.2.6
		fkEponRuleModifyControlOltId OBJECT-TYPE
			SYNTAX INTEGER (1..24)
			MAX-ACCESS read-write
			STATUS current
			DESCRIPTION
				"Olt index."
			::= { fkEponRuleModifyControl 6 }

		
		-- 1.3.6.1.4.1.10428 9 1.101.20.13.3.2.7
		fkEponRuleModifyControlRuleName OBJECT-TYPE
			SYNTAX OCTET STRING
			MAX-ACCESS read-write
			STATUS current
			DESCRIPTION
				"Pon rule name."
			::= { fkEponRuleModifyControl 7 }

		
		-- 1.3.6.1.4.1.10428 9 1.101.20.13.3.2.8
		fkEponRuleModifyControlTrafficDirection OBJECT-TYPE
			SYNTAX INTEGER
				{
				downstream(1),
				upstream(2)
				}
			MAX-ACCESS read-write
			STATUS current
			DESCRIPTION
				"The traffic direction of Rule .
				"
			::= { fkEponRuleModifyControl 8 }

		
		-- 1.3.6.1.4.1.10428 9 1.101.20.13.3.2.9
		fkEponRuleModifyControlPriorityValue OBJECT-TYPE
			SYNTAX INTEGER (0..15)
			MAX-ACCESS read-write
			STATUS current
			DESCRIPTION
				"Priority Value."
			::= { fkEponRuleModifyControl 9 }

		
		-- 1.3.6.1.4.1.10428 9 1.101.20.13.3.2.10
		fkEponRuleModifyControlCIndex OBJECT-TYPE
			SYNTAX INTEGER (1..8)
			MAX-ACCESS read-write
			STATUS current
			DESCRIPTION
				"Rule clause index."
			::= { fkEponRuleModifyControl 10 }

		
		-- 1.3.6.1.4.1.10428 9 1.101.20.13.3.2.11
		fkEponRuleModifyControlAIndex OBJECT-TYPE
			SYNTAX INTEGER (1..8)
			MAX-ACCESS read-write
			STATUS current
			DESCRIPTION
				"Rule action index."
			::= { fkEponRuleModifyControl 11 }

		
		-- 1.3.6.1.4.1.10428 9 1.101.20.13.3.3
		fkEponRuleModifyNotification OBJECT IDENTIFIER ::= { fkEponRuleModify 3 }

		
		-- 1.3.6.1.4.1.10428 9 1.101.20.13.3.3.1
		fkEponRuleOltRuleCreate NOTIFICATION-TYPE
			OBJECTS { fkEponRuleModifyControlRequest, fkEponRuleModifyControlTimeStamp, fkEponRuleModifyControlReqResult, fkEponRuleModifyControlRuleName, fkEponRuleModifyControlPriorityValue, 
				fkEponRuleModifyControlCIndex, fkEponRuleModifyControlAIndex }
			STATUS current
			DESCRIPTION 
				"Description."
			::= { fkEponRuleModifyNotification 1 }

		
		-- 1.3.6.1.4.1.10428 9 1.101.20.13.3.3.2
		fkEponRuleModifyPriorityChange NOTIFICATION-TYPE
			OBJECTS { fkEponRuleModifyControlRequest, fkEponRuleModifyControlTimeStamp, fkEponRuleModifyControlReqResult, fkEponRuleModifyControlRuleName, fkEponRuleModifyControlPriorityValue, 
				fkEponRuleModifyControlTrafficDirection }
			STATUS current
			DESCRIPTION 
				"Description."
			::= { fkEponRuleModifyNotification 2 }

		
		-- 1.3.6.1.4.1.10428 9 1.101.20.13.3.3.3
		fkEponRuleModifyTrafficDirChange NOTIFICATION-TYPE
			OBJECTS { fkEponRuleModifyControlRequest, fkEponRuleModifyControlTimeStamp, fkEponRuleModifyControlReqResult, fkEponRuleModifyControlRuleName, fkEponRuleModifyControlPriorityValue, 
				fkEponRuleModifyControlTrafficDirection }
			STATUS current
			DESCRIPTION 
				"Description."
			::= { fkEponRuleModifyNotification 3 }

		
		-- 1.3.6.1.4.1.10428 9 1.101.20.13.3.3.4
		fkEponRuleModifyClauseAdd NOTIFICATION-TYPE
			OBJECTS { fkEponRuleModifyControlRequest, fkEponRuleModifyControlTimeStamp, fkEponRuleModifyControlReqResult, fkEponRuleModifyControlRuleName, fkEponRuleModifyControlCIndex, 
				fkEponRuleModifyControlAIndex }
			STATUS current
			DESCRIPTION 
				"Description."
			::= { fkEponRuleModifyNotification 4 }

		
		-- 1.3.6.1.4.1.10428 9 1.101.20.13.3.3.5
		fkEponRuleModifyActionAdd NOTIFICATION-TYPE
			OBJECTS { fkEponRuleModifyControlRequest, fkEponRuleModifyControlTimeStamp, fkEponRuleModifyControlReqResult, fkEponRuleModifyControlRuleName, fkEponRuleModifyControlCIndex, 
				fkEponRuleModifyControlAIndex }
			STATUS current
			DESCRIPTION 
				"Description."
			::= { fkEponRuleModifyNotification 5 }

		
		-- 1.3.6.1.4.1.10428 9 1.101.20.13.3.3.6
		fkEponRuleModifyClauseDel NOTIFICATION-TYPE
			OBJECTS { fkEponRuleModifyControlRequest, fkEponRuleModifyControlTimeStamp, fkEponRuleModifyControlReqResult, fkEponRuleModifyControlRuleName, fkEponRuleModifyControlCIndex, 
				fkEponRuleModifyControlAIndex }
			STATUS current
			DESCRIPTION 
				"Description."
			::= { fkEponRuleModifyNotification 6 }

		
		-- 1.3.6.1.4.1.10428 9 1.101.20.13.3.3.7
		fkEponRuleModifyActionDel NOTIFICATION-TYPE
			OBJECTS { fkEponRuleModifyControlRequest, fkEponRuleModifyControlTimeStamp, fkEponRuleModifyControlReqResult, fkEponRuleModifyControlRuleName, fkEponRuleModifyControlCIndex, 
				fkEponRuleModifyControlAIndex }
			STATUS current
			DESCRIPTION 
				"Description."
			::= { fkEponRuleModifyNotification 7 }

		
		-- 1.3.6.1.4.1.10428 9 1.101.20.13.3.3.8
		fkEponRuleOltRuleDelete NOTIFICATION-TYPE
			OBJECTS { fkEponRuleModifyControlRequest, fkEponRuleModifyControlReqResult, fkEponRuleModifyControlOltId, fkEponRuleModifyControlTimeStamp, fkEponRuleModifyControlRuleName
				 }
			STATUS current
			DESCRIPTION 
				"Description."
			::= { fkEponRuleModifyNotification 8 }

		
		-- 1.3.6.1.4.1.10428 9 1.101.20.13.3.3.9
		fkEponRuleOltRuleAddApply NOTIFICATION-TYPE
			OBJECTS { fkEponRuleModifyControlRequest, fkEponRuleModifyControlTimeStamp, fkEponRuleModifyControlReqResult, fkEponRuleModifyControlOltId, fkEponRuleModifyControlRuleName
				 }
			STATUS current
			DESCRIPTION 
				"Description."
			::= { fkEponRuleModifyNotification 9 }

		
		-- 1.3.6.1.4.1.10428 9 1.101.20.13.3.3.10
		fkEponRuleOltRuleDelApply NOTIFICATION-TYPE
			OBJECTS { fkEponRuleModifyControlRequest, fkEponRuleModifyControlTimeStamp, fkEponRuleModifyControlReqResult, fkEponRuleModifyControlOltId, fkEponRuleModifyControlRuleName
				 }
			STATUS current
			DESCRIPTION 
				"Description."
			::= { fkEponRuleModifyNotification 10 }

		
		-- 1.3.6.1.4.1.10428 9 1.101.20.13.4
		fkEponOnuRule OBJECT IDENTIFIER ::= { fkEponRule 4 }

		
		-- 1.3.6.1.4.1.10428 9 1.101.20.13.4.1
		fkEponOnuRuleTable OBJECT-TYPE
			SYNTAX SEQUENCE OF FkEponOnuRuleEntry
			MAX-ACCESS not-accessible
			STATUS current
			DESCRIPTION
				"Description."
			::= { fkEponOnuRule 1 }

		
		-- 1.3.6.1.4.1.10428 9 1.101.20.13.4.1.1
		fkEponOnuRuleEntry OBJECT-TYPE
			SYNTAX FkEponOnuRuleEntry
			MAX-ACCESS not-accessible
			STATUS current
			DESCRIPTION
				"Epon onu rule table."
			INDEX { fkEponOnuRuleIndex }
			::= { fkEponOnuRuleTable 1 }

		
		FkEponOnuRuleEntry ::=
			SEQUENCE { 
				fkEponOnuRuleName
					OCTET STRING,
				fkEponOnuRuleIndex
					Integer32,
				fkEponOnuRuleDirection
					INTEGER,
				fkEponOnuRulePriority
					Integer32,
				fkEponOnuRuleDscp
					OCTET STRING,
				fkEponOnuRuleLinkIndex
					INTEGER,
				fkEponOnuRuleQueueIndex
					INTEGER
			 }

		-- 1.3.6.1.4.1.10428 9 1.101.20.13.4.1.1.1
		fkEponOnuRuleName OBJECT-TYPE
			SYNTAX OCTET STRING
			MAX-ACCESS read-only
			STATUS current
			DESCRIPTION
				"Epon onu rule name."
			::= { fkEponOnuRuleEntry 1 }

		
		-- 1.3.6.1.4.1.10428 9 1.101.20.13.4.1.1.2
		fkEponOnuRuleIndex OBJECT-TYPE
			SYNTAX Integer32 (1..512)
			MAX-ACCESS read-only
			STATUS current
			DESCRIPTION
				"Rule Index"
			::= { fkEponOnuRuleEntry 2 }

		
		-- 1.3.6.1.4.1.10428 9 1.101.20.13.4.1.1.3
		fkEponOnuRuleDirection OBJECT-TYPE
			SYNTAX INTEGER
				{
				dowbStream(1),
				upStream(2)
				}
			MAX-ACCESS read-only
			STATUS current
			DESCRIPTION
				"Traffic direction."
			::= { fkEponOnuRuleEntry 3 }

		
		-- 1.3.6.1.4.1.10428 9 1.101.20.13.4.1.1.4
		fkEponOnuRulePriority OBJECT-TYPE
			SYNTAX Integer32
			MAX-ACCESS read-only
			STATUS current
			DESCRIPTION
				"Priority."
			::= { fkEponOnuRuleEntry 4 }

		
		-- 1.3.6.1.4.1.10428 9 1.101.20.13.4.1.1.5
		fkEponOnuRuleDscp OBJECT-TYPE
			SYNTAX OCTET STRING
			MAX-ACCESS read-write
			STATUS current
			DESCRIPTION
				"Epon onu rule dscp."
			::= { fkEponOnuRuleEntry 5 }

		
		-- 1.3.6.1.4.1.10428 9 1.101.20.13.4.1.1.6
		fkEponOnuRuleLinkIndex OBJECT-TYPE
			SYNTAX INTEGER (0..1)
			MAX-ACCESS read-write
			STATUS current
			DESCRIPTION
				"Epon onu rule link index."
			::= { fkEponOnuRuleEntry 6 }

		
		-- 1.3.6.1.4.1.10428 9 1.101.20.13.4.1.1.7
		fkEponOnuRuleQueueIndex OBJECT-TYPE
			SYNTAX INTEGER (0..3)
			MAX-ACCESS read-write
			STATUS current
			DESCRIPTION
				"Epon onu rule queue index"
			::= { fkEponOnuRuleEntry 7 }

		
		-- 1.3.6.1.4.1.10428 9 1.101.20.13.4.2
		fkEponOnuRuleControl OBJECT IDENTIFIER ::= { fkEponOnuRule 2 }

		
		-- 1.3.6.1.4.1.10428 9 1.101.20.13.4.2.1
		fkEponOnuRuleControlRequest OBJECT-TYPE
			SYNTAX INTEGER
				{
				createOnuRule(1),
				deleteOnuRule(2)
				}
			MAX-ACCESS read-write
			STATUS current
			DESCRIPTION
				"The request of a user command."
			::= { fkEponOnuRuleControl 1 }

		
		-- 1.3.6.1.4.1.10428 9 1.101.20.13.4.2.2
		fkEponOnuRuleControlStatus OBJECT-TYPE
			SYNTAX FkControlStatusType
			MAX-ACCESS read-only
			STATUS current
			DESCRIPTION
				"The status of user command."
			::= { fkEponOnuRuleControl 2 }

		
		-- 1.3.6.1.4.1.10428 9 1.101.20.13.4.2.3
		fkEponOnuRuleControlTimer OBJECT-TYPE
			SYNTAX Gauge32
			MAX-ACCESS read-write
			STATUS current
			DESCRIPTION
				"The maximum time for the manager for a long running user command."
			::= { fkEponOnuRuleControl 3 }

		
		-- 1.3.6.1.4.1.10428 9 1.101.20.13.4.2.4
		fkEponOnuRuleControlTimeStamp OBJECT-TYPE
			SYNTAX TimeTicks
			MAX-ACCESS read-only
			STATUS current
			DESCRIPTION
				"The time stamp of the last command(end of command)."
			::= { fkEponOnuRuleControl 4 }

		
		-- 1.3.6.1.4.1.10428 9 1.101.20.13.4.2.5
		fkEponOnuRuleControlReqResult OBJECT-TYPE
			SYNTAX FkControlRequestResultType
			MAX-ACCESS read-only
			STATUS current
			DESCRIPTION
				"The result of the last user command."
			::= { fkEponOnuRuleControl 5 }

		
		-- 1.3.6.1.4.1.10428 9 1.101.20.13.4.2.6
		fkEponOnuRuleControlRuleName OBJECT-TYPE
			SYNTAX OCTET STRING
			MAX-ACCESS read-write
			STATUS current
			DESCRIPTION
				"Epon onu rule name."
			::= { fkEponOnuRuleControl 6 }

		
		-- 1.3.6.1.4.1.10428 9 1.101.20.13.4.2.7
		fkEponOnuRuleControlDscp OBJECT-TYPE
			SYNTAX INTEGER
				{
				cs01(1),
				cs23(2),
				cs45(3),
				cs67(4)
				}
			MAX-ACCESS read-write
			STATUS current
			DESCRIPTION
				"Epon onu rule dscp."
			::= { fkEponOnuRuleControl 7 }

		
		-- 1.3.6.1.4.1.10428 9 1.101.20.13.4.2.8
		fkEponOnuRuleControlLinkIndex OBJECT-TYPE
			SYNTAX INTEGER (0..1)
			MAX-ACCESS read-write
			STATUS current
			DESCRIPTION
				"Epon onu rule link index."
			::= { fkEponOnuRuleControl 8 }

		
		-- 1.3.6.1.4.1.10428 9 1.101.20.13.4.2.9
		fkEponOnuRuleControlQueueIndex OBJECT-TYPE
			SYNTAX INTEGER (0..3)
			MAX-ACCESS read-write
			STATUS current
			DESCRIPTION
				"Epon onu rule queue index"
			::= { fkEponOnuRuleControl 9 }

		
		-- 1.3.6.1.4.1.10428 9 1.101.20.13.4.3
		fkEponOnuRuleNotification OBJECT IDENTIFIER ::= { fkEponOnuRule 3 }

		
		-- 1.3.6.1.4.1.10428 9 1.101.20.13.4.3.1
		fkEponOnuRuleChanged NOTIFICATION-TYPE
			OBJECTS { fkEponOnuRuleControlRequest, fkEponOnuRuleControlTimeStamp, fkEponOnuRuleControlReqResult, fkEponOnuRuleControlRuleName }
			STATUS current
			DESCRIPTION 
				"Trap of create or delete onu rule."
			::= { fkEponOnuRuleNotification 1 }

		
		-- 1.3.6.1.4.1.10428 9 1.101.20.14
		fkEponDBA OBJECT IDENTIFIER ::= { fkEpon 14 }

		
		-- 1.3.6.1.4.1.10428 9 1.101.20.14.1
		fkEponOltDBA OBJECT IDENTIFIER ::= { fkEponDBA 1 }

		
		-- 1.3.6.1.4.1.10428 9 1.101.20.14.1.1
		fkEponOltDBATable OBJECT-TYPE
			SYNTAX SEQUENCE OF FkEponOltDBAEntry
			MAX-ACCESS not-accessible
			STATUS current
			DESCRIPTION
				"Description."
			::= { fkEponOltDBA 1 }

		
		-- 1.3.6.1.4.1.10428 9 1.101.20.14.1.1.1
		fkEponOltDBAEntry OBJECT-TYPE
			SYNTAX FkEponOltDBAEntry
			MAX-ACCESS not-accessible
			STATUS current
			DESCRIPTION
				"Description."
			INDEX { fkEponOltIndex }
			::= { fkEponOltDBATable 1 }

		
		FkEponOltDBAEntry ::=
			SEQUENCE { 
				fkEponOltDBAGlobalOltLinkOperate
					INTEGER,
				fkEponOltDBAOverGrantMonConfMonitoringInterval
					INTEGER,
				fkEponOltDBAOverGrantMonConfMaxDBAGrantSize
					INTEGER,
				fkEponOltDBAOverGrantMonConfMinGrantUtilization
					INTEGER,
				fkEponOltDBAOverGrantMonConfLeakyBucketCounterValue
					INTEGER,
				fkEponOltDBAMinShaperBandwidth
					INTEGER,
				fkEponOltDBAMinShaperBurstSize
					INTEGER,
				fkEponOltDBAMinShaperScheduleLevel
					INTEGER,
				fkEponOltDBAMinShaperWeight
					INTEGER,
				fkEponOltDBAMaxShaperBandwidth
					INTEGER,
				fkEponOltDBAMaxShaperBurstSize
					INTEGER,
				fkEponOltDBAMaxShaperScheduleLevel
					INTEGER,
				fkEponOltDBAMaxShaperWeight
					INTEGER
			 }

		-- 1.3.6.1.4.1.10428 9 1.101.20.14.1.1.1.1
		fkEponOltDBAGlobalOltLinkOperate OBJECT-TYPE
			SYNTAX INTEGER
				{
				disable(0),
				enable(1)
				}
			MAX-ACCESS read-only
			STATUS current
			DESCRIPTION
				"Global olt link options.
				enable
				disable"
			::= { fkEponOltDBAEntry 1 }

		
		-- 1.3.6.1.4.1.10428 9 1.101.20.14.1.1.1.2
		fkEponOltDBAOverGrantMonConfMonitoringInterval OBJECT-TYPE
			SYNTAX INTEGER (50..65535)
			MAX-ACCESS read-only
			STATUS current
			DESCRIPTION
				"Monitoring Interval."
			::= { fkEponOltDBAEntry 2 }

		
		-- 1.3.6.1.4.1.10428 9 1.101.20.14.1.1.1.3
		fkEponOltDBAOverGrantMonConfMaxDBAGrantSize OBJECT-TYPE
			SYNTAX INTEGER (0..65535)
			MAX-ACCESS read-only
			STATUS current
			DESCRIPTION
				"Maximum DBA grant size."
			::= { fkEponOltDBAEntry 3 }

		
		-- 1.3.6.1.4.1.10428 9 1.101.20.14.1.1.1.4
		fkEponOltDBAOverGrantMonConfMinGrantUtilization OBJECT-TYPE
			SYNTAX INTEGER (0..255)
			MAX-ACCESS read-only
			STATUS current
			DESCRIPTION
				"Minimum grant utilization."
			::= { fkEponOltDBAEntry 4 }

		
		-- 1.3.6.1.4.1.10428 9 1.101.20.14.1.1.1.5
		fkEponOltDBAOverGrantMonConfLeakyBucketCounterValue OBJECT-TYPE
			SYNTAX INTEGER (0..255)
			MAX-ACCESS read-only
			STATUS current
			DESCRIPTION
				"Leaky bucket counter value."
			::= { fkEponOltDBAEntry 5 }

		
		-- 1.3.6.1.4.1.10428 9 1.101.20.14.1.1.1.6
		fkEponOltDBAMinShaperBandwidth OBJECT-TYPE
			SYNTAX INTEGER (256..1000000)
			MAX-ACCESS read-only
			STATUS current
			DESCRIPTION
				"min shaper bandwidth"
			::= { fkEponOltDBAEntry 6 }

		
		-- 1.3.6.1.4.1.10428 9 1.101.20.14.1.1.1.7
		fkEponOltDBAMinShaperBurstSize OBJECT-TYPE
			SYNTAX INTEGER (1..256)
			MAX-ACCESS read-only
			STATUS current
			DESCRIPTION
				"min shaper burst size"
			::= { fkEponOltDBAEntry 7 }

		
		-- 1.3.6.1.4.1.10428 9 1.101.20.14.1.1.1.8
		fkEponOltDBAMinShaperScheduleLevel OBJECT-TYPE
			SYNTAX INTEGER (0..7)
			MAX-ACCESS read-only
			STATUS current
			DESCRIPTION
				"min shaper schedule level"
			::= { fkEponOltDBAEntry 8 }

		
		-- 1.3.6.1.4.1.10428 9 1.101.20.14.1.1.1.9
		fkEponOltDBAMinShaperWeight OBJECT-TYPE
			SYNTAX INTEGER (2..32)
			MAX-ACCESS read-only
			STATUS current
			DESCRIPTION
				"Min shaper weight"
			::= { fkEponOltDBAEntry 9 }

		
		-- 1.3.6.1.4.1.10428 9 1.101.20.14.1.1.1.10
		fkEponOltDBAMaxShaperBandwidth OBJECT-TYPE
			SYNTAX INTEGER (256..1000000)
			MAX-ACCESS read-only
			STATUS current
			DESCRIPTION
				"max shaper bandwidth"
			::= { fkEponOltDBAEntry 10 }

		
		-- 1.3.6.1.4.1.10428 9 1.101.20.14.1.1.1.11
		fkEponOltDBAMaxShaperBurstSize OBJECT-TYPE
			SYNTAX INTEGER (1..256)
			MAX-ACCESS read-only
			STATUS current
			DESCRIPTION
				"max shaper burst size"
			::= { fkEponOltDBAEntry 11 }

		
		-- 1.3.6.1.4.1.10428 9 1.101.20.14.1.1.1.12
		fkEponOltDBAMaxShaperScheduleLevel OBJECT-TYPE
			SYNTAX INTEGER (0..7)
			MAX-ACCESS read-only
			STATUS current
			DESCRIPTION
				"max shaper schedule level"
			::= { fkEponOltDBAEntry 12 }

		
		-- 1.3.6.1.4.1.10428 9 1.101.20.14.1.1.1.13
		fkEponOltDBAMaxShaperWeight OBJECT-TYPE
			SYNTAX INTEGER (2..32)
			MAX-ACCESS read-only
			STATUS current
			DESCRIPTION
				"max shaper weight"
			::= { fkEponOltDBAEntry 13 }

		
		-- 1.3.6.1.4.1.10428 9 1.101.20.14.1.2
		fkEponOltDBAPollingRateTable OBJECT-TYPE
			SYNTAX SEQUENCE OF FkEponOltDBAPollingRateEntry
			MAX-ACCESS not-accessible
			STATUS current
			DESCRIPTION
				"olt dba polling rate table"
			::= { fkEponOltDBA 2 }

		
		-- 1.3.6.1.4.1.10428 9 1.101.20.14.1.2.1
		fkEponOltDBAPollingRateEntry OBJECT-TYPE
			SYNTAX FkEponOltDBAPollingRateEntry
			MAX-ACCESS not-accessible
			STATUS current
			DESCRIPTION
				"Description."
			INDEX { fkEponOltIndex, fkEponOltDBADBAPollingRateLevel }
			::= { fkEponOltDBAPollingRateTable 1 }

		
		FkEponOltDBAPollingRateEntry ::=
			SEQUENCE { 
				fkEponOltDBADBAPollingRateLevel
					INTEGER,
				fkEponOltDBADBAPollingRateRate
					INTEGER
			 }

		-- 1.3.6.1.4.1.10428 9 1.101.20.14.1.2.1.1
		fkEponOltDBADBAPollingRateLevel OBJECT-TYPE
			SYNTAX INTEGER (0..7)
			MAX-ACCESS read-only
			STATUS current
			DESCRIPTION
				"Polling rate level."
			::= { fkEponOltDBAPollingRateEntry 1 }

		
		-- 1.3.6.1.4.1.10428 9 1.101.20.14.1.2.1.2
		fkEponOltDBADBAPollingRateRate OBJECT-TYPE
			SYNTAX INTEGER (0..65535)
			MAX-ACCESS read-write
			STATUS current
			DESCRIPTION
				"Polling rate rate."
			::= { fkEponOltDBAPollingRateEntry 2 }

		
		-- 1.3.6.1.4.1.10428 9 1.101.20.14.1.3
		fkEponOltDBADropDownTable OBJECT-TYPE
			SYNTAX SEQUENCE OF FkEponOltDBADropDownEntry
			MAX-ACCESS not-accessible
			STATUS current
			DESCRIPTION
				"shaper drop down and  drop down"
			::= { fkEponOltDBA 3 }

		
		-- 1.3.6.1.4.1.10428 9 1.101.20.14.1.3.1
		fkEponOltDBADropDownEntry OBJECT-TYPE
			SYNTAX FkEponOltDBADropDownEntry
			MAX-ACCESS not-accessible
			STATUS current
			DESCRIPTION
				"Description."
			INDEX { fkEponOltIndex, eEponOltDBADropDownLevel }
			::= { fkEponOltDBADropDownTable 1 }

		
		FkEponOltDBADropDownEntry ::=
			SEQUENCE { 
				eEponOltDBADropDownLevel
					INTEGER,
				fkEponOltDBAShaDropDownWeights
					INTEGER,
				fkEponOltDBADropDownWeights
					Integer32
			 }

		-- 1.3.6.1.4.1.10428 9 1.101.20.14.1.3.1.1
		eEponOltDBADropDownLevel OBJECT-TYPE
			SYNTAX INTEGER (1..7)
			MAX-ACCESS read-only
			STATUS current
			DESCRIPTION
				"the level of shaper drop down and drop down weights "
			::= { fkEponOltDBADropDownEntry 1 }

		
		-- 1.3.6.1.4.1.10428 9 1.101.20.14.1.3.1.2
		fkEponOltDBAShaDropDownWeights OBJECT-TYPE
			SYNTAX INTEGER (0..256)
			MAX-ACCESS read-write
			STATUS current
			DESCRIPTION
				"Shaper drop down weights."
			::= { fkEponOltDBADropDownEntry 2 }

		
		-- 1.3.6.1.4.1.10428 9 1.101.20.14.1.3.1.3
		fkEponOltDBADropDownWeights OBJECT-TYPE
			SYNTAX Integer32
			MAX-ACCESS read-write
			STATUS current
			DESCRIPTION
				"Drop down weights."
			::= { fkEponOltDBADropDownEntry 3 }

		
		-- 1.3.6.1.4.1.10428 9 1.101.20.14.1.4
		fkEponOltDBAControl OBJECT IDENTIFIER ::= { fkEponOltDBA 4 }

		
		-- 1.3.6.1.4.1.10428 9 1.101.20.14.1.4.1
		fkEponOltDBAControlRequest OBJECT-TYPE
			SYNTAX INTEGER
				{
				setDBAPollingRate(1),
				setDBAShaperDropDownWeights(2),
				setDBADropDownWeights(3),
				setDBALinkEnable(4),
				setDBALinkDisable(5),
				setDBAGlobalOltLinkOptions(6),
				setDBALinkGrantMonConf(7),
				setDBAMultiQueueSla(8),
				noDBAMultiQueueSla(9)
				}
			MAX-ACCESS read-write
			STATUS current
			DESCRIPTION
				"The request of a user command."
			::= { fkEponOltDBAControl 1 }

		
		-- 1.3.6.1.4.1.10428 9 1.101.20.14.1.4.2
		fkEponOltDBAControlStatus OBJECT-TYPE
			SYNTAX FkControlStatusType
			MAX-ACCESS read-only
			STATUS current
			DESCRIPTION
				"The status of user command."
			::= { fkEponOltDBAControl 2 }

		
		-- 1.3.6.1.4.1.10428 9 1.101.20.14.1.4.3
		fkEponOltDBAControlTimer OBJECT-TYPE
			SYNTAX Gauge32
			MAX-ACCESS read-write
			STATUS current
			DESCRIPTION
				"The maximum time for the manager for a long running user command."
			::= { fkEponOltDBAControl 3 }

		
		-- 1.3.6.1.4.1.10428 9 1.101.20.14.1.4.4
		fkEponOltDBAControlTimeStamp OBJECT-TYPE
			SYNTAX TimeTicks
			MAX-ACCESS read-only
			STATUS current
			DESCRIPTION
				"The time stamp of the last command(end of command)."
			::= { fkEponOltDBAControl 4 }

		
		-- 1.3.6.1.4.1.10428 9 1.101.20.14.1.4.5
		fkEponOltDBAControlReqResult OBJECT-TYPE
			SYNTAX FkControlRequestResultType
			MAX-ACCESS read-only
			STATUS current
			DESCRIPTION
				"The result of the last user command."
			::= { fkEponOltDBAControl 5 }

		
		-- 1.3.6.1.4.1.10428 9 1.101.20.14.1.4.6
		fkEponOltDBAControlOltIndex OBJECT-TYPE
			SYNTAX INTEGER (1..32)
			MAX-ACCESS read-write
			STATUS current
			DESCRIPTION
				"Olt index."
			::= { fkEponOltDBAControl 6 }

		
		-- 1.3.6.1.4.1.10428 9 1.101.20.14.1.4.7
		fkEponOltDBAControlOnuIndex OBJECT-TYPE
			SYNTAX INTEGER (1..64)
			MAX-ACCESS read-write
			STATUS current
			DESCRIPTION
				"Onu index."
			::= { fkEponOltDBAControl 7 }

		
		-- 1.3.6.1.4.1.10428 9 1.101.20.14.1.4.8
		fkEponOltDBAControlDBAPollingRateLevel OBJECT-TYPE
			SYNTAX INTEGER (0..7)
			MAX-ACCESS read-write
			STATUS current
			DESCRIPTION
				"Polling rate level."
			::= { fkEponOltDBAControl 8 }

		
		-- 1.3.6.1.4.1.10428 9 1.101.20.14.1.4.9
		fkEponOltDBAControlDBAPollingRateRate OBJECT-TYPE
			SYNTAX INTEGER (0..65535)
			MAX-ACCESS read-write
			STATUS current
			DESCRIPTION
				"Polling rate."
			::= { fkEponOltDBAControl 9 }

		
		-- 1.3.6.1.4.1.10428 9 1.101.20.14.1.4.10
		fkEponOltDBAControlShaDropDownWeightsLevel OBJECT-TYPE
			SYNTAX INTEGER (1..7)
			MAX-ACCESS read-write
			STATUS current
			DESCRIPTION
				"Shaper dropdown weights level."
			::= { fkEponOltDBAControl 10 }

		
		-- 1.3.6.1.4.1.10428 9 1.101.20.14.1.4.11
		fkEponOltDBAControlShaDropDownWeights OBJECT-TYPE
			SYNTAX INTEGER (0..256)
			MAX-ACCESS read-write
			STATUS current
			DESCRIPTION
				"Shaper drop down weights."
			::= { fkEponOltDBAControl 11 }

		
		-- 1.3.6.1.4.1.10428 9 1.101.20.14.1.4.12
		fkEponOltDBAControlDropDownWeightsLevel OBJECT-TYPE
			SYNTAX INTEGER (1..7)
			MAX-ACCESS read-write
			STATUS current
			DESCRIPTION
				"Drop down weights level."
			::= { fkEponOltDBAControl 12 }

		
		-- 1.3.6.1.4.1.10428 9 1.101.20.14.1.4.13
		fkEponOltDBAControlDropDownWeightsl OBJECT-TYPE
			SYNTAX INTEGER (0..256)
			MAX-ACCESS read-write
			STATUS current
			DESCRIPTION
				"Drop down weights."
			::= { fkEponOltDBAControl 13 }

		
		-- 1.3.6.1.4.1.10428 9 1.101.20.14.1.4.14
		fkEponOltDBAControlGlobalOltLinkOperate OBJECT-TYPE
			SYNTAX INTEGER
				{
				disable(0),
				enable(1)
				}
			MAX-ACCESS read-write
			STATUS current
			DESCRIPTION
				"Global olt link options.
				enable
				disable"
			::= { fkEponOltDBAControl 14 }

		
		-- 1.3.6.1.4.1.10428 9 1.101.20.14.1.4.15
		fkEponOltDBAControlOverGrantMonConfMonitoringInterval OBJECT-TYPE
			SYNTAX INTEGER (50..65535)
			MAX-ACCESS read-write
			STATUS current
			DESCRIPTION
				"Monitoring Interval."
			::= { fkEponOltDBAControl 15 }

		
		-- 1.3.6.1.4.1.10428 9 1.101.20.14.1.4.16
		fkEponOltDBAControlOverGrantMonConfMaxDBAGrantSize OBJECT-TYPE
			SYNTAX INTEGER (0..65535)
			MAX-ACCESS read-write
			STATUS current
			DESCRIPTION
				"Maximum DBA grant size."
			::= { fkEponOltDBAControl 16 }

		
		-- 1.3.6.1.4.1.10428 9 1.101.20.14.1.4.17
		fkEponOltDBAControlOverGrantMonConfMinGrantUtilization OBJECT-TYPE
			SYNTAX INTEGER (0..255)
			MAX-ACCESS read-write
			STATUS current
			DESCRIPTION
				"Minimum grant utilization."
			::= { fkEponOltDBAControl 17 }

		
		-- 1.3.6.1.4.1.10428 9 1.101.20.14.1.4.18
		fkEponOltDBAControlOverGrantMonConfLeakyBucketCounterValue OBJECT-TYPE
			SYNTAX INTEGER (0..255)
			MAX-ACCESS read-write
			STATUS current
			DESCRIPTION
				"Leaky bucket counter value."
			::= { fkEponOltDBAControl 18 }

		
		-- 1.3.6.1.4.1.10428 9 1.101.20.14.1.4.19
		fkEponOltDBAControlMinShaperBandwidth OBJECT-TYPE
			SYNTAX INTEGER (256..1000000)
			MAX-ACCESS read-write
			STATUS current
			DESCRIPTION
				"min shaper bandwidth"
			::= { fkEponOltDBAControl 19 }

		
		-- 1.3.6.1.4.1.10428 9 1.101.20.14.1.4.20
		fkEponOltDBAControlMinShaperBurstSize OBJECT-TYPE
			SYNTAX INTEGER (1..256)
			MAX-ACCESS read-write
			STATUS current
			DESCRIPTION
				"min shaper burst size"
			::= { fkEponOltDBAControl 20 }

		
		-- 1.3.6.1.4.1.10428 9 1.101.20.14.1.4.21
		fkEponOltDBAControlMinShaperScheduleLevel OBJECT-TYPE
			SYNTAX INTEGER (0..7)
			MAX-ACCESS read-write
			STATUS current
			DESCRIPTION
				"min shaper schedule level"
			::= { fkEponOltDBAControl 21 }

		
		-- 1.3.6.1.4.1.10428 9 1.101.20.14.1.4.22
		fkEponOltDBAControlMinShaperWeight OBJECT-TYPE
			SYNTAX INTEGER (2..32)
			MAX-ACCESS read-write
			STATUS current
			DESCRIPTION
				"min shaper weight"
			::= { fkEponOltDBAControl 22 }

		
		-- 1.3.6.1.4.1.10428 9 1.101.20.14.1.4.23
		fkEponOltDBAControlMaxShaperBandwidth OBJECT-TYPE
			SYNTAX INTEGER (256..1000000)
			MAX-ACCESS read-write
			STATUS current
			DESCRIPTION
				"max shaper bandwidth"
			::= { fkEponOltDBAControl 23 }

		
		-- 1.3.6.1.4.1.10428 9 1.101.20.14.1.4.24
		fkEponOltDBAControlMaxShaperBurstSize OBJECT-TYPE
			SYNTAX INTEGER (1..256)
			MAX-ACCESS read-write
			STATUS current
			DESCRIPTION
				"max shaper burst size"
			::= { fkEponOltDBAControl 24 }

		
		-- 1.3.6.1.4.1.10428 9 1.101.20.14.1.4.25
		fkEponOltDBAControlMaxShaperScheduleLevel OBJECT-TYPE
			SYNTAX INTEGER (0..7)
			MAX-ACCESS read-write
			STATUS current
			DESCRIPTION
				"max shaper schedule level"
			::= { fkEponOltDBAControl 25 }

		
		-- 1.3.6.1.4.1.10428 9 1.101.20.14.1.4.26
		fkEponOltDBAControlMaxShaperWeight OBJECT-TYPE
			SYNTAX INTEGER (2..32)
			MAX-ACCESS read-write
			STATUS current
			DESCRIPTION
				"max shaper weight"
			::= { fkEponOltDBAControl 26 }

		
		-- 1.3.6.1.4.1.10428 9 1.101.20.14.1.5
		fkEponOltDBANotification OBJECT IDENTIFIER ::= { fkEponOltDBA 5 }

		
		-- 1.3.6.1.4.1.10428 9 1.101.20.14.1.5.1
		fkEponOLtDBAShaperDropDownWeightsChanged NOTIFICATION-TYPE
			OBJECTS { fkEponOltDBAControlRequest, fkEponOltDBAControlTimeStamp, fkEponOltDBAControlReqResult, fkEponOltDBAControlShaDropDownWeightsLevel, fkEponOltDBAControlShaDropDownWeights
				 }
			STATUS current
			DESCRIPTION 
				"Shaper drop down weights changed."
			::= { fkEponOltDBANotification 1 }

		
		-- 1.3.6.1.4.1.10428 9 1.101.20.14.1.5.2
		fkEponOLtDBADropDownWeightsChanged NOTIFICATION-TYPE
			OBJECTS { fkEponOltDBAControlRequest, fkEponOltDBAControlTimeStamp, fkEponOltDBAControlReqResult, fkEponOltDBAControlDropDownWeightsLevel, fkEponOltDBAControlDropDownWeightsl
				 }
			STATUS current
			DESCRIPTION 
				"DBA drop down weights changed."
			::= { fkEponOltDBANotification 2 }

		
		-- 1.3.6.1.4.1.10428 9 1.101.20.14.1.5.3
		fkEponOltDBALinkChanged NOTIFICATION-TYPE
			OBJECTS { fkEponOltDBAControlRequest, fkEponOltDBAControlTimeStamp, fkEponOltDBAControlReqResult }
			STATUS current
			DESCRIPTION 
				"DBA link state changed."
			::= { fkEponOltDBANotification 3 }

		
		-- 1.3.6.1.4.1.10428 9 1.101.20.14.1.5.4
		fkEponOLtDBADGlobalOltLinkChanged NOTIFICATION-TYPE
			OBJECTS { fkEponOltDBAControlRequest, fkEponOltDBAControlTimeStamp, fkEponOltDBAControlReqResult, fkEponOltDBAControlGlobalOltLinkOperate }
			STATUS current
			DESCRIPTION 
				"Global olt link state changed trap."
			::= { fkEponOltDBANotification 4 }

		
		-- 1.3.6.1.4.1.10428 9 1.101.20.14.1.5.5
		fkEponOLtDBADOverGrantMonConfChanged NOTIFICATION-TYPE
			OBJECTS { fkEponOltDBAControlRequest, fkEponOltDBAControlTimeStamp, fkEponOltDBAControlReqResult, fkEponOltDBAControlOverGrantMonConfMonitoringInterval, fkEponOltDBAControlOverGrantMonConfMaxDBAGrantSize, 
				fkEponOltDBAControlOverGrantMonConfMinGrantUtilization, fkEponOltDBAControlOverGrantMonConfLeakyBucketCounterValue }
			STATUS current
			DESCRIPTION 
				"Olt DBA over-grant-mon-conf changed trap."
			::= { fkEponOltDBANotification 5 }

		
		-- 1.3.6.1.4.1.10428 9 1.101.20.14.1.5.6
		fkEponOltDBAPollingRateChanged NOTIFICATION-TYPE
			OBJECTS { fkEponOltDBAControlRequest, fkEponOltDBAControlTimeStamp, fkEponOltDBAControlReqResult, fkEponOltDBAControlDBAPollingRateLevel, fkEponOltDBAControlDBAPollingRateRate
				 }
			STATUS current
			DESCRIPTION 
				"Polling rate changed trap."
			::= { fkEponOltDBANotification 6 }

		
		-- 1.3.6.1.4.1.10428 9 1.101.20.14.1.5.7
		fkEponOltDBAMultiQueueSlaChanged NOTIFICATION-TYPE
			OBJECTS { fkEponOltDBAControlRequest, fkEponOltDBAControlTimeStamp, fkEponOltDBAControlReqResult, fkEponOltDBAControlOltIndex }
			STATUS current
			DESCRIPTION 
				"multicast queue sla changed trap"
			::= { fkEponOltDBANotification 7 }

		
		-- 1.3.6.1.4.1.10428 9 1.101.20.14.2
		fkEponOnuProfileDBA OBJECT IDENTIFIER ::= { fkEponDBA 2 }

		
		-- 1.3.6.1.4.1.10428 9 1.101.20.14.2.1
		fkEponOnuProfileDBALinkTable OBJECT-TYPE
			SYNTAX SEQUENCE OF FkEponOnuProfileDBALinkEntry
			MAX-ACCESS not-accessible
			STATUS current
			DESCRIPTION
				"Epon onu profile DBA link entry."
			::= { fkEponOnuProfileDBA 1 }

		
		-- 1.3.6.1.4.1.10428 9 1.101.20.14.2.1.1
		fkEponOnuProfileDBALinkEntry OBJECT-TYPE
			SYNTAX FkEponOnuProfileDBALinkEntry
			MAX-ACCESS not-accessible
			STATUS current
			DESCRIPTION
				"Description."
			INDEX { fkEponProfileIndex }
			::= { fkEponOnuProfileDBALinkTable 1 }

		
		FkEponOnuProfileDBALinkEntry ::=
			SEQUENCE { 
				fkEponOnuProfileDBAProfileName
					OCTET STRING,
				fkEponOnuProfileDBALinkSlaMinShaBandwidth
					INTEGER,
				fkEponOnuProfileDBALinkSlaMinShaBurstSize
					INTEGER,
				fkEponOnuProfileDBALinkSlaMinShaSchedulerLevel
					INTEGER,
				fkEponOnuProfileDBALinkSlaMinShaWeight
					INTEGER,
				fkEponOnuProfileDBALinkSlaMaxShaBandwidth
					INTEGER,
				fkEponOnuProfileDBALinkSlaMaxShaBurstSize
					INTEGER,
				fkEponOnuProfileDBALinkSlaMaxShaSchedulerLevel
					INTEGER,
				fkEponOnuProfileDBALinkSlaMaxShaWeight
					INTEGER,
				fkEponOnuProfileDBALinkSlaOperate
					INTEGER,
				fkEponOnuProfileDBALinkSlaPollingLevel
					INTEGER,
				fkEponOnuProfileDBALinkSlaTDMRate
					INTEGER,
				fkEponOnuProfileDBALinkSlaTDMGrantLength
					INTEGER,
				fkEponOnuProfileDBALinkOAMMaxOAMRate
					INTEGER,
				fkEponOnuProfileDBALinkOAMMinOAMRate
					INTEGER
			 }

		-- 1.3.6.1.4.1.10428 9 1.101.20.14.2.1.1.1
		fkEponOnuProfileDBAProfileName OBJECT-TYPE
			SYNTAX OCTET STRING (SIZE (1..64))
			MAX-ACCESS read-only
			STATUS current
			DESCRIPTION
				"Profile name.
				'all' means configure all the onu profile."
			::= { fkEponOnuProfileDBALinkEntry 1 }

		
		-- 1.3.6.1.4.1.10428 9 1.101.20.14.2.1.1.2
		fkEponOnuProfileDBALinkSlaMinShaBandwidth OBJECT-TYPE
			SYNTAX INTEGER (0 | 256..1000000)
			MAX-ACCESS read-only
			STATUS current
			DESCRIPTION
				"Guaranteed Bandwidth(Kbps).
				System default: 0
				"
			DEFVAL { 0 }
			::= { fkEponOnuProfileDBALinkEntry 2 }

		
		-- 1.3.6.1.4.1.10428 9 1.101.20.14.2.1.1.3
		fkEponOnuProfileDBALinkSlaMinShaBurstSize OBJECT-TYPE
			SYNTAX INTEGER (1..256 | 65535)
			MAX-ACCESS read-only
			STATUS current
			DESCRIPTION
				"Minimum Burst Size.
				System default: 65535"
			DEFVAL { 65535 }
			::= { fkEponOnuProfileDBALinkEntry 3 }

		
		-- 1.3.6.1.4.1.10428 9 1.101.20.14.2.1.1.4
		fkEponOnuProfileDBALinkSlaMinShaSchedulerLevel OBJECT-TYPE
			SYNTAX INTEGER (0..7 | 255)
			MAX-ACCESS read-only
			STATUS current
			DESCRIPTION
				"Scheduler Level.
				System default 255."
			DEFVAL { 255 }
			::= { fkEponOnuProfileDBALinkEntry 4 }

		
		-- 1.3.6.1.4.1.10428 9 1.101.20.14.2.1.1.5
		fkEponOnuProfileDBALinkSlaMinShaWeight OBJECT-TYPE
			SYNTAX INTEGER (2..32 | 65535)
			MAX-ACCESS read-only
			STATUS current
			DESCRIPTION
				"Weight
				System default: 65535."
			DEFVAL { 65535 }
			::= { fkEponOnuProfileDBALinkEntry 5 }

		
		-- 1.3.6.1.4.1.10428 9 1.101.20.14.2.1.1.6
		fkEponOnuProfileDBALinkSlaMaxShaBandwidth OBJECT-TYPE
			SYNTAX INTEGER (0 | 256..1000000)
			MAX-ACCESS read-only
			STATUS current
			DESCRIPTION
				"Guaranteed Bandwidth(Kbps).
				System default: 100000"
			DEFVAL { 100000 }
			::= { fkEponOnuProfileDBALinkEntry 6 }

		
		-- 1.3.6.1.4.1.10428 9 1.101.20.14.2.1.1.7
		fkEponOnuProfileDBALinkSlaMaxShaBurstSize OBJECT-TYPE
			SYNTAX INTEGER (1..256)
			MAX-ACCESS read-only
			STATUS current
			DESCRIPTION
				"Maximum Burst Size.
				System default: 255"
			DEFVAL { 255 }
			::= { fkEponOnuProfileDBALinkEntry 7 }

		
		-- 1.3.6.1.4.1.10428 9 1.101.20.14.2.1.1.8
		fkEponOnuProfileDBALinkSlaMaxShaSchedulerLevel OBJECT-TYPE
			SYNTAX INTEGER (0..7)
			MAX-ACCESS read-only
			STATUS current
			DESCRIPTION
				"Scheduler Level.
				System default 2."
			DEFVAL { 2 }
			::= { fkEponOnuProfileDBALinkEntry 8 }

		
		-- 1.3.6.1.4.1.10428 9 1.101.20.14.2.1.1.9
		fkEponOnuProfileDBALinkSlaMaxShaWeight OBJECT-TYPE
			SYNTAX INTEGER (2..32)
			MAX-ACCESS read-only
			STATUS current
			DESCRIPTION
				"Weight
				System default: 24."
			DEFVAL { 24 }
			::= { fkEponOnuProfileDBALinkEntry 9 }

		
		-- 1.3.6.1.4.1.10428 9 1.101.20.14.2.1.1.10
		fkEponOnuProfileDBALinkSlaOperate OBJECT-TYPE
			SYNTAX INTEGER
				{
				none(1),
				forceReport(2),
				disableOamUplift(3)
				}
			MAX-ACCESS read-only
			STATUS current
			DESCRIPTION
				"Onu profile DBA options."
			::= { fkEponOnuProfileDBALinkEntry 10 }

		
		-- 1.3.6.1.4.1.10428 9 1.101.20.14.2.1.1.11
		fkEponOnuProfileDBALinkSlaPollingLevel OBJECT-TYPE
			SYNTAX INTEGER (0..7)
			MAX-ACCESS read-only
			STATUS current
			DESCRIPTION
				"Polling Interval Select."
			::= { fkEponOnuProfileDBALinkEntry 11 }

		
		-- 1.3.6.1.4.1.10428 9 1.101.20.14.2.1.1.12
		fkEponOnuProfileDBALinkSlaTDMRate OBJECT-TYPE
			SYNTAX INTEGER (0 | 1..4000)
			MAX-ACCESS read-only
			STATUS current
			DESCRIPTION
				"TDM Rate.
				System default 0."
			DEFVAL { 0 }
			::= { fkEponOnuProfileDBALinkEntry 12 }

		
		-- 1.3.6.1.4.1.10428 9 1.101.20.14.2.1.1.13
		fkEponOnuProfileDBALinkSlaTDMGrantLength OBJECT-TYPE
			SYNTAX INTEGER (0 | 84..131072)
			MAX-ACCESS read-only
			STATUS current
			DESCRIPTION
				"TDM grant length.
				System default 0."
			DEFVAL { 0 }
			::= { fkEponOnuProfileDBALinkEntry 13 }

		
		-- 1.3.6.1.4.1.10428 9 1.101.20.14.2.1.1.14
		fkEponOnuProfileDBALinkOAMMaxOAMRate OBJECT-TYPE
			SYNTAX INTEGER (0..25)
			MAX-ACCESS read-only
			STATUS current
			DESCRIPTION
				"Maximum OAM rate.
				System default 3."
			DEFVAL { 3 }
			::= { fkEponOnuProfileDBALinkEntry 14 }

		
		-- 1.3.6.1.4.1.10428 9 1.101.20.14.2.1.1.15
		fkEponOnuProfileDBALinkOAMMinOAMRate OBJECT-TYPE
			SYNTAX INTEGER (0..10)
			MAX-ACCESS read-only
			STATUS current
			DESCRIPTION
				"Minimum OAM rate.
				System default 10."
			DEFVAL { 10 }
			::= { fkEponOnuProfileDBALinkEntry 15 }

		
		-- 1.3.6.1.4.1.10428 9 1.101.20.14.2.2
		fkEponOnuProfileDBAQueueSlaTable OBJECT-TYPE
			SYNTAX SEQUENCE OF FkEponOnuProfileDBAQueueSlaEntry
			MAX-ACCESS not-accessible
			STATUS current
			DESCRIPTION
				"Description."
			::= { fkEponOnuProfileDBA 2 }

		
		-- 1.3.6.1.4.1.10428 9 1.101.20.14.2.2.1
		fkEponOnuProfileDBAQueueSlaEntry OBJECT-TYPE
			SYNTAX FkEponOnuProfileDBAQueueSlaEntry
			MAX-ACCESS not-accessible
			STATUS current
			DESCRIPTION
				"Epon onu profile DBA queue sla entry."
			INDEX { fkEponProfileIndex, fkEponOnuProfileDBAQueueIndex }
			::= { fkEponOnuProfileDBAQueueSlaTable 1 }

		
		FkEponOnuProfileDBAQueueSlaEntry ::=
			SEQUENCE { 
				fkEponOnuProfileDBAQueueIndex
					INTEGER,
				fkEponOnuProfileDBAQueueSlaDownMinShaBandwidth
					INTEGER,
				fkEponOnuProfileDBAQueueSlaDownMinShaBurstSize
					INTEGER,
				fkEponOnuProfileDBAQueueSlaDownMinShaSchedulerLevel
					INTEGER,
				fkEponOnuProfileDBAQueueSlaDownMinShaWeight
					INTEGER,
				fkEponOnuProfileDBAQueueSlaDownMaxShaBandwidth
					INTEGER,
				fkEponOnuProfileDBAQueueSlaDownMaxShaBurstSize
					INTEGER,
				fkEponOnuProfileDBAQueueSlaDownMaxShaSchedulerLevel
					INTEGER,
				fkEponOnuProfileDBAQueueSlaDownMaxShaWeight
					INTEGER,
				fkEponOnuProfileDBAQueueSlaUpMinShaBandwidth
					INTEGER,
				fkEponOnuProfileDBAQueueSlaUpMinShaBurstSize
					INTEGER,
				fkEponOnuProfileDBAQueueSlaUpMinShaSchedulerLevel
					INTEGER,
				fkEponOnuProfileDBAQueueSlaUpMinShaWeight
					INTEGER,
				fkEponOnuProfileDBAQueueSlaUpMaxShaBandwidth
					INTEGER,
				fkEponOnuProfileDBAQueueSlaUpMaxShaBurstSize
					INTEGER,
				fkEponOnuProfileDBAQueueSlaUpMaxShaSchedulerLevel
					INTEGER,
				fkEponOnuProfileDBAQueueSlaUpMaxShaWeight
					INTEGER
			 }

		-- 1.3.6.1.4.1.10428 9 1.101.20.14.2.2.1.1
		fkEponOnuProfileDBAQueueIndex OBJECT-TYPE
			SYNTAX INTEGER (0..3)
			MAX-ACCESS read-only
			STATUS current
			DESCRIPTION
				"Queue index."
			::= { fkEponOnuProfileDBAQueueSlaEntry 1 }

		
		-- 1.3.6.1.4.1.10428 9 1.101.20.14.2.2.1.2
		fkEponOnuProfileDBAQueueSlaDownMinShaBandwidth OBJECT-TYPE
			SYNTAX INTEGER (0 | 256..1000000)
			MAX-ACCESS read-only
			STATUS current
			DESCRIPTION
				"Queue sla downstream shaper minimum bandwidth.
				System default 0."
			DEFVAL { 0 }
			::= { fkEponOnuProfileDBAQueueSlaEntry 2 }

		
		-- 1.3.6.1.4.1.10428 9 1.101.20.14.2.2.1.3
		fkEponOnuProfileDBAQueueSlaDownMinShaBurstSize OBJECT-TYPE
			SYNTAX INTEGER (1..256 | 65535)
			MAX-ACCESS read-only
			STATUS current
			DESCRIPTION
				"Queue sla downstream shaper minimum burst size.
				System default 65535."
			DEFVAL { 65535 }
			::= { fkEponOnuProfileDBAQueueSlaEntry 3 }

		
		-- 1.3.6.1.4.1.10428 9 1.101.20.14.2.2.1.4
		fkEponOnuProfileDBAQueueSlaDownMinShaSchedulerLevel OBJECT-TYPE
			SYNTAX INTEGER (0..7 | 255)
			MAX-ACCESS read-only
			STATUS current
			DESCRIPTION
				"Queue sla downstream shaper minimum scheduer level.
				System default 255."
			DEFVAL { 255 }
			::= { fkEponOnuProfileDBAQueueSlaEntry 4 }

		
		-- 1.3.6.1.4.1.10428 9 1.101.20.14.2.2.1.5
		fkEponOnuProfileDBAQueueSlaDownMinShaWeight OBJECT-TYPE
			SYNTAX INTEGER (2..32 | 65535)
			MAX-ACCESS read-only
			STATUS current
			DESCRIPTION
				"Queue sla downstream shaper minimum weight.
				System default 65535."
			DEFVAL { 65535 }
			::= { fkEponOnuProfileDBAQueueSlaEntry 5 }

		
		-- 1.3.6.1.4.1.10428 9 1.101.20.14.2.2.1.6
		fkEponOnuProfileDBAQueueSlaDownMaxShaBandwidth OBJECT-TYPE
			SYNTAX INTEGER (256..1000000)
			MAX-ACCESS read-only
			STATUS current
			DESCRIPTION
				"Queue sla downstream shaper maximum bandwidth.
				System default 100000"
			DEFVAL { 100000 }
			::= { fkEponOnuProfileDBAQueueSlaEntry 6 }

		
		-- 1.3.6.1.4.1.10428 9 1.101.20.14.2.2.1.7
		fkEponOnuProfileDBAQueueSlaDownMaxShaBurstSize OBJECT-TYPE
			SYNTAX INTEGER (1..256)
			MAX-ACCESS read-only
			STATUS current
			DESCRIPTION
				"Queue sla downstream shaper maximum burst size.
				System default 255."
			DEFVAL { 255 }
			::= { fkEponOnuProfileDBAQueueSlaEntry 7 }

		
		-- 1.3.6.1.4.1.10428 9 1.101.20.14.2.2.1.8
		fkEponOnuProfileDBAQueueSlaDownMaxShaSchedulerLevel OBJECT-TYPE
			SYNTAX INTEGER (0..7)
			MAX-ACCESS read-only
			STATUS current
			DESCRIPTION
				"Queue sla downstream shaper maximum scheduler level.
				System default 2."
			DEFVAL { 2 }
			::= { fkEponOnuProfileDBAQueueSlaEntry 8 }

		
		-- 1.3.6.1.4.1.10428 9 1.101.20.14.2.2.1.9
		fkEponOnuProfileDBAQueueSlaDownMaxShaWeight OBJECT-TYPE
			SYNTAX INTEGER (2..32)
			MAX-ACCESS read-only
			STATUS current
			DESCRIPTION
				"Queue sla downstream shaper maximum weight.
				System default 24."
			DEFVAL { 24 }
			::= { fkEponOnuProfileDBAQueueSlaEntry 9 }

		
		-- 1.3.6.1.4.1.10428 9 1.101.20.14.2.2.1.10
		fkEponOnuProfileDBAQueueSlaUpMinShaBandwidth OBJECT-TYPE
			SYNTAX INTEGER (0 | 256..1000000)
			MAX-ACCESS read-only
			STATUS current
			DESCRIPTION
				"Queue sla upstream shaper minimum bandwidth.
				System default 0."
			DEFVAL { 0 }
			::= { fkEponOnuProfileDBAQueueSlaEntry 10 }

		
		-- 1.3.6.1.4.1.10428 9 1.101.20.14.2.2.1.11
		fkEponOnuProfileDBAQueueSlaUpMinShaBurstSize OBJECT-TYPE
			SYNTAX INTEGER (1..256 | 65535)
			MAX-ACCESS read-only
			STATUS current
			DESCRIPTION
				"Queue sla upstream shaper minimum bandwidth.
				System default 65535."
			DEFVAL { 65535 }
			::= { fkEponOnuProfileDBAQueueSlaEntry 11 }

		
		-- 1.3.6.1.4.1.10428 9 1.101.20.14.2.2.1.12
		fkEponOnuProfileDBAQueueSlaUpMinShaSchedulerLevel OBJECT-TYPE
			SYNTAX INTEGER (0..7 | 255)
			MAX-ACCESS read-write
			STATUS current
			DESCRIPTION
				"Queue sla upstream shaper minimum scheduler level.
				System default 255."
			DEFVAL { 255 }
			::= { fkEponOnuProfileDBAQueueSlaEntry 12 }

		
		-- 1.3.6.1.4.1.10428 9 1.101.20.14.2.2.1.13
		fkEponOnuProfileDBAQueueSlaUpMinShaWeight OBJECT-TYPE
			SYNTAX INTEGER (2..32 | 65535)
			MAX-ACCESS read-only
			STATUS current
			DESCRIPTION
				"Queue sla upstream shaper minimum weight.
				System default 65535."
			DEFVAL { 65535 }
			::= { fkEponOnuProfileDBAQueueSlaEntry 13 }

		
		-- 1.3.6.1.4.1.10428 9 1.101.20.14.2.2.1.14
		fkEponOnuProfileDBAQueueSlaUpMaxShaBandwidth OBJECT-TYPE
			SYNTAX INTEGER (256..1000000)
			MAX-ACCESS read-write
			STATUS current
			DESCRIPTION
				"Queue sla upstream shaper maximum bandwidth.
				System default 100000."
			DEFVAL { 100000 }
			::= { fkEponOnuProfileDBAQueueSlaEntry 14 }

		
		-- 1.3.6.1.4.1.10428 9 1.101.20.14.2.2.1.15
		fkEponOnuProfileDBAQueueSlaUpMaxShaBurstSize OBJECT-TYPE
			SYNTAX INTEGER (1..256)
			MAX-ACCESS read-only
			STATUS current
			DESCRIPTION
				"Queue sla upstream shaper maximum burst size.
				System default 255."
			DEFVAL { 255 }
			::= { fkEponOnuProfileDBAQueueSlaEntry 15 }

		
		-- 1.3.6.1.4.1.10428 9 1.101.20.14.2.2.1.16
		fkEponOnuProfileDBAQueueSlaUpMaxShaSchedulerLevel OBJECT-TYPE
			SYNTAX INTEGER (0..7)
			MAX-ACCESS read-write
			STATUS current
			DESCRIPTION
				"Queue sla upstream shaper maximum scheduler level.
				System default 2."
			DEFVAL { 2 }
			::= { fkEponOnuProfileDBAQueueSlaEntry 16 }

		
		-- 1.3.6.1.4.1.10428 9 1.101.20.14.2.2.1.17
		fkEponOnuProfileDBAQueueSlaUpMaxShaWeight OBJECT-TYPE
			SYNTAX INTEGER (2..32)
			MAX-ACCESS read-only
			STATUS current
			DESCRIPTION
				"Queue sla upstream shaper maximum weight.
				System default 24."
			DEFVAL { 24 }
			::= { fkEponOnuProfileDBAQueueSlaEntry 17 }

		
		-- 1.3.6.1.4.1.10428 9 1.101.20.14.2.3
		fkEponOnuProfileDBAControl OBJECT IDENTIFIER ::= { fkEponOnuProfileDBA 3 }

		
		-- 1.3.6.1.4.1.10428 9 1.101.20.14.2.3.1
		fkEponOnuProfileDBAControlRequest OBJECT-TYPE
			SYNTAX INTEGER
				{
				setPonOnuProfileDBALinkSla(1),
				noPonOnuProfileDBALinkSla(2),
				setPonOnuProfileDBAQueueSla(3),
				noPonOnuProfileDBAQueueSla(4),
				noPonOnuProfileDBAQueueSlaAll(5),
				setPonOnuProfileDBALinkOAMRate(6),
				noPonOnuProfileDBALinkOAMRate(7)
				}
			MAX-ACCESS read-write
			STATUS current
			DESCRIPTION
				"The request of a user command."
			::= { fkEponOnuProfileDBAControl 1 }

		
		-- 1.3.6.1.4.1.10428 9 1.101.20.14.2.3.2
		fkEponOnuProfileDBAControlStatus OBJECT-TYPE
			SYNTAX FkControlStatusType
			MAX-ACCESS read-write
			STATUS current
			DESCRIPTION
				"The status of user command."
			::= { fkEponOnuProfileDBAControl 2 }

		
		-- 1.3.6.1.4.1.10428 9 1.101.20.14.2.3.3
		fkEponOnuProfileDBAControlTimer OBJECT-TYPE
			SYNTAX Gauge32
			MAX-ACCESS read-write
			STATUS current
			DESCRIPTION
				"The maximum time for the manager for a long running user command."
			::= { fkEponOnuProfileDBAControl 3 }

		
		-- 1.3.6.1.4.1.10428 9 1.101.20.14.2.3.4
		fkEponOnuProfileDBAControlTimeStamp OBJECT-TYPE
			SYNTAX TimeTicks
			MAX-ACCESS read-write
			STATUS current
			DESCRIPTION
				"The time stamp of the last command(end of command)."
			::= { fkEponOnuProfileDBAControl 4 }

		
		-- 1.3.6.1.4.1.10428 9 1.101.20.14.2.3.5
		fkEponOnuProfileDBAControlReqResult OBJECT-TYPE
			SYNTAX FkControlRequestResultType
			MAX-ACCESS read-write
			STATUS current
			DESCRIPTION
				"The result of the last user command."
			::= { fkEponOnuProfileDBAControl 5 }

		
		-- 1.3.6.1.4.1.10428 9 1.101.20.14.2.3.6
		fkEponOnuProfileDBAControlProfileName OBJECT-TYPE
			SYNTAX OCTET STRING (SIZE (1..64))
			MAX-ACCESS read-write
			STATUS current
			DESCRIPTION
				"Profile name.
				'all' means configure all the onu profile."
			::= { fkEponOnuProfileDBAControl 6 }

		
		-- 1.3.6.1.4.1.10428 9 1.101.20.14.2.3.7
		fkEponOnuProfileDBAControlLinkSlaMinShaBandwidth OBJECT-TYPE
			SYNTAX INTEGER (0 | 256..1000000)
			MAX-ACCESS read-write
			STATUS current
			DESCRIPTION
				"Guaranteed Bandwidth(Kbps).
				0 means that we will use the default value."
			DEFVAL { 0 }
			::= { fkEponOnuProfileDBAControl 7 }

		
		-- 1.3.6.1.4.1.10428 9 1.101.20.14.2.3.8
		fkEponOnuProfileDBAControlLinkSlaMinShaBurstSize OBJECT-TYPE
			SYNTAX INTEGER (1..256 | 65535)
			MAX-ACCESS read-write
			STATUS current
			DESCRIPTION
				"Minimum Burst Size.
				Default 65535."
			DEFVAL { 65535 }
			::= { fkEponOnuProfileDBAControl 8 }

		
		-- 1.3.6.1.4.1.10428 9 1.101.20.14.2.3.9
		fkEponOnuProfileDBAControlLinkSlaMinShaSchedulerLevel OBJECT-TYPE
			SYNTAX INTEGER (0..7 | 255)
			MAX-ACCESS read-write
			STATUS current
			DESCRIPTION
				"Scheduler Level.
				Default 255."
			DEFVAL { 255 }
			::= { fkEponOnuProfileDBAControl 9 }

		
		-- 1.3.6.1.4.1.10428 9 1.101.20.14.2.3.10
		fkEponOnuProfileDBAControlLinkSlaMinShaWeight OBJECT-TYPE
			SYNTAX INTEGER (2..32 | 65535)
			MAX-ACCESS read-write
			STATUS current
			DESCRIPTION
				"Weight.
				Default 65535."
			DEFVAL { 0 }
			::= { fkEponOnuProfileDBAControl 10 }

		
		-- 1.3.6.1.4.1.10428 9 1.101.20.14.2.3.11
		fkEponOnuProfileDBAControlLinkSlaMaxShaBandwidth OBJECT-TYPE
			SYNTAX INTEGER (256..1000000)
			MAX-ACCESS read-write
			STATUS current
			DESCRIPTION
				"Guaranteed Bandwidth(Kbps)."
			::= { fkEponOnuProfileDBAControl 11 }

		
		-- 1.3.6.1.4.1.10428 9 1.101.20.14.2.3.12
		fkEponOnuProfileDBAControlLinkSlaMaxShaBurstSize OBJECT-TYPE
			SYNTAX INTEGER (1..256)
			MAX-ACCESS read-write
			STATUS current
			DESCRIPTION
				"Maximum burst size."
			::= { fkEponOnuProfileDBAControl 12 }

		
		-- 1.3.6.1.4.1.10428 9 1.101.20.14.2.3.13
		fkEponOnuProfileDBAControlLinkSlaMaxShaSchedulerLevel OBJECT-TYPE
			SYNTAX INTEGER (0..7)
			MAX-ACCESS read-write
			STATUS current
			DESCRIPTION
				"Scheduler Level."
			::= { fkEponOnuProfileDBAControl 13 }

		
		-- 1.3.6.1.4.1.10428 9 1.101.20.14.2.3.14
		fkEponOnuProfileDBAControlLinkSlaMaxShaWeight OBJECT-TYPE
			SYNTAX INTEGER (2..32)
			MAX-ACCESS read-write
			STATUS current
			DESCRIPTION
				"Weight."
			::= { fkEponOnuProfileDBAControl 14 }

		
		-- 1.3.6.1.4.1.10428 9 1.101.20.14.2.3.15
		fkEponOnuProfileDBAControlLinkSlaOperate OBJECT-TYPE
			SYNTAX INTEGER
				{
				none(1),
				forceReport(2),
				disableOAMUplift(3)
				}
			MAX-ACCESS read-write
			STATUS current
			DESCRIPTION
				"Onu profile DBA options."
			::= { fkEponOnuProfileDBAControl 15 }

		
		-- 1.3.6.1.4.1.10428 9 1.101.20.14.2.3.16
		fkEponOnuProfileDBAControlLinkSlaPollingLevel OBJECT-TYPE
			SYNTAX INTEGER (0..7)
			MAX-ACCESS read-write
			STATUS current
			DESCRIPTION
				"Polling Interval Select."
			::= { fkEponOnuProfileDBAControl 16 }

		
		-- 1.3.6.1.4.1.10428 9 1.101.20.14.2.3.17
		fkEponOnuProfileDBAControlLinkSlaTDMRate OBJECT-TYPE
			SYNTAX INTEGER (0 | 1..4000)
			MAX-ACCESS read-write
			STATUS current
			DESCRIPTION
				"TDM Rate.
				0 means that we will use the default value."
			DEFVAL { 0 }
			::= { fkEponOnuProfileDBAControl 17 }

		
		-- 1.3.6.1.4.1.10428 9 1.101.20.14.2.3.18
		fkEponOnuProfileDBAControlLinkSlaTDMGrantLength OBJECT-TYPE
			SYNTAX INTEGER (0 | 84..131072)
			MAX-ACCESS read-write
			STATUS current
			DESCRIPTION
				"TDM grant length.
				0 means that we will use the default value."
			DEFVAL { 0 }
			::= { fkEponOnuProfileDBAControl 18 }

		
		-- 1.3.6.1.4.1.10428 9 1.101.20.14.2.3.19
		fkEponOnuProfileDBAControlQueueIndex OBJECT-TYPE
			SYNTAX INTEGER (0..3)
			MAX-ACCESS read-write
			STATUS current
			DESCRIPTION
				"Queue index."
			::= { fkEponOnuProfileDBAControl 19 }

		
		-- 1.3.6.1.4.1.10428 9 1.101.20.14.2.3.20
		fkEponOnuProfileDBAControlQueueSlaMinShaBandwidth OBJECT-TYPE
			SYNTAX INTEGER (256..1000000)
			MAX-ACCESS read-write
			STATUS current
			DESCRIPTION
				"Guaranteed Bandwidth(Kbps)."
			::= { fkEponOnuProfileDBAControl 20 }

		
		-- 1.3.6.1.4.1.10428 9 1.101.20.14.2.3.21
		fkEponOnuProfileDBAControlQueueSlaMinShaBurstSize OBJECT-TYPE
			SYNTAX INTEGER (1..256)
			MAX-ACCESS read-write
			STATUS current
			DESCRIPTION
				"Minimum Burst Size."
			::= { fkEponOnuProfileDBAControl 21 }

		
		-- 1.3.6.1.4.1.10428 9 1.101.20.14.2.3.22
		fkEponOnuProfileDBAControlQueueSlaMinShaSchedulerLevel OBJECT-TYPE
			SYNTAX INTEGER (0..7)
			MAX-ACCESS read-write
			STATUS current
			DESCRIPTION
				"Scheduler Level."
			::= { fkEponOnuProfileDBAControl 22 }

		
		-- 1.3.6.1.4.1.10428 9 1.101.20.14.2.3.23
		fkEponOnuProfileDBAControlQueueSlaMinShaWeight OBJECT-TYPE
			SYNTAX INTEGER (2..32)
			MAX-ACCESS read-write
			STATUS current
			DESCRIPTION
				"Weight."
			::= { fkEponOnuProfileDBAControl 23 }

		
		-- 1.3.6.1.4.1.10428 9 1.101.20.14.2.3.24
		fkEponOnuProfileDBAControlQueueSlaMaxShaBandwidth OBJECT-TYPE
			SYNTAX INTEGER (256..1000000)
			MAX-ACCESS read-write
			STATUS current
			DESCRIPTION
				"Guaranteed Bandwidth(Kbps)."
			::= { fkEponOnuProfileDBAControl 24 }

		
		-- 1.3.6.1.4.1.10428 9 1.101.20.14.2.3.25
		fkEponOnuProfileDBAControlQueueSlaMaxShaBurstSize OBJECT-TYPE
			SYNTAX INTEGER (1..256)
			MAX-ACCESS read-write
			STATUS current
			DESCRIPTION
				"Maximum burst size."
			::= { fkEponOnuProfileDBAControl 25 }

		
		-- 1.3.6.1.4.1.10428 9 1.101.20.14.2.3.26
		fkEponOnuProfileDBAControlQueueSlaMaxShaSchedulerLevel OBJECT-TYPE
			SYNTAX INTEGER (0..7)
			MAX-ACCESS read-write
			STATUS current
			DESCRIPTION
				"Scheduler Level."
			::= { fkEponOnuProfileDBAControl 26 }

		
		-- 1.3.6.1.4.1.10428 9 1.101.20.14.2.3.27
		fkEponOnuProfileDBAControlQueueSlaMaxShaWeight OBJECT-TYPE
			SYNTAX INTEGER (2..32)
			MAX-ACCESS read-write
			STATUS current
			DESCRIPTION
				"Weight."
			::= { fkEponOnuProfileDBAControl 27 }

		
		-- 1.3.6.1.4.1.10428 9 1.101.20.14.2.3.28
		fkEponOnuProfileDBAControlQueueSlaOperate OBJECT-TYPE
			SYNTAX INTEGER
				{
				upstream(1),
				downstream(2)
				}
			MAX-ACCESS read-write
			STATUS current
			DESCRIPTION
				"Direction of Egress Shaping."
			::= { fkEponOnuProfileDBAControl 28 }

		
		-- 1.3.6.1.4.1.10428 9 1.101.20.14.2.3.29
		fkEponOnuProfileDBAControlLinkOAMMaxRate OBJECT-TYPE
			SYNTAX INTEGER (0..25)
			MAX-ACCESS read-write
			STATUS current
			DESCRIPTION
				"Maximum OAM rate."
			::= { fkEponOnuProfileDBAControl 29 }

		
		-- 1.3.6.1.4.1.10428 9 1.101.20.14.2.3.30
		fkEponOnuProfileDBAControlLinkOAMMinRate OBJECT-TYPE
			SYNTAX INTEGER (0..10)
			MAX-ACCESS read-write
			STATUS current
			DESCRIPTION
				"Minimum OAM rate."
			::= { fkEponOnuProfileDBAControl 30 }

		
		-- 1.3.6.1.4.1.10428 9 1.101.20.14.2.4
		fkEponOnuProfileDBANotification OBJECT IDENTIFIER ::= { fkEponOnuProfileDBA 4 }

		
		-- 1.3.6.1.4.1.10428 9 1.101.20.14.2.4.1
		fkEponOnuProfileDBALinkSlaChanged NOTIFICATION-TYPE
			OBJECTS { fkEponOnuProfileDBAControlRequest, fkEponOnuProfileDBAControlTimeStamp, fkEponOnuProfileDBAControlReqResult, fkEponOnuProfileDBAControlProfileName }
			STATUS current
			DESCRIPTION 
				"Set ONU profile DBA link sla trap."
			::= { fkEponOnuProfileDBANotification 1 }

		
		-- 1.3.6.1.4.1.10428 9 1.101.20.14.2.4.2
		fkEponOnuProfileDBAQueueSlaChanged NOTIFICATION-TYPE
			OBJECTS { fkEponOnuProfileDBAControlRequest, fkEponOnuProfileDBAControlTimeStamp, fkEponOnuProfileDBAControlReqResult, fkEponOnuProfileDBAControlProfileName, fkEponOnuProfileDBAControlQueueIndex
				 }
			STATUS current
			DESCRIPTION 
				"Onu profile DBA queue sla changed trap."
			::= { fkEponOnuProfileDBANotification 2 }

		
		-- 1.3.6.1.4.1.10428 9 1.101.20.14.2.4.3
		fkEponOnuProfileDBALinkOAMRateChanged NOTIFICATION-TYPE
			OBJECTS { fkEponOnuProfileDBAControlRequest, fkEponOnuProfileDBAControlTimeStamp, fkEponOnuProfileDBAControlReqResult, fkEponOnuProfileDBAControlProfileName, fkEponOnuProfileDBAControlLinkOAMMaxRate, 
				fkEponOnuProfileDBAControlLinkOAMMinRate }
			STATUS current
			DESCRIPTION 
				"Onu profile DBA link OAM changed trap."
			::= { fkEponOnuProfileDBANotification 3 }

		
		-- 1.3.6.1.4.1.10428 9 1.101.20.14.2.5
		fkEponOnuProfileDBAMutilLLidLinkTable OBJECT-TYPE
			SYNTAX SEQUENCE OF FkEponOnuProfileDBAMutilLLidLinkEntry
			MAX-ACCESS not-accessible
			STATUS current
			DESCRIPTION
				"Epon onu profile DBA link entry."
			::= { fkEponOnuProfileDBA 5 }

		
		-- 1.3.6.1.4.1.10428 9 1.101.20.14.2.5.1
		fkEponOnuProfileDBAMutilLLidLinkEntry OBJECT-TYPE
			SYNTAX FkEponOnuProfileDBAMutilLLidLinkEntry
			MAX-ACCESS not-accessible
			STATUS current
			DESCRIPTION
				"Description."
			INDEX { fkEponProfileIndex }
			::= { fkEponOnuProfileDBAMutilLLidLinkTable 1 }

		
		FkEponOnuProfileDBAMutilLLidLinkEntry ::=
			SEQUENCE { 
				fkEponOnuProfileDBAMultiLLidProfileName
					OCTET STRING,
				fkEponOnuProfileDBAMultiLLidLinkSlaMinShaBandwidth
					INTEGER,
				fkEponOnuProfileDBAMultiLLidLinkSlaMinShaBurstSize
					INTEGER,
				fkEponOnuProfileDBAMultiLLidLinkSlaMinShaSchedulerLevel
					INTEGER,
				fkEponOnuProfileDBAMultiLLidLinkSlaMinShaWeight
					INTEGER,
				fkEponOnuProfileDBAMultiLLidLinkSlaMaxShaBandwidth
					INTEGER,
				fkEponOnuProfileDBAMultiLLidLinkSlaMaxShaBurstSize
					INTEGER,
				fkEponOnuProfileDBAMultiLLidLinkSlaMaxShaSchedulerLevel
					INTEGER,
				fkEponOnuProfileDBAMultiLLidLinkSlaMaxShaWeight
					INTEGER,
				fkEponOnuProfileDBAMultiLLidLinkSlaOperate
					INTEGER,
				fkEponOnuProfileDBAMultiLLidLinkSlaPollingLevel
					INTEGER,
				fkEponOnuProfileDBAMultiLLidLinkSlaTDMRate
					INTEGER,
				fkEponOnuProfileDBAMultiLLidLinkSlaTDMGrantLength
					INTEGER,
				fkEponOnuProfileDBAMultiLLidLinkOAMMaxOAMRate
					INTEGER,
				fkEponOnuProfileDBAMultiLLidLinkOAMMinOAMRate
					INTEGER
			 }

		-- 1.3.6.1.4.1.10428 9 1.101.20.14.2.5.1.1
		fkEponOnuProfileDBAMultiLLidProfileName OBJECT-TYPE
			SYNTAX OCTET STRING (SIZE (1..64))
			MAX-ACCESS read-only
			STATUS current
			DESCRIPTION
				"Profile name.
				'all' means configure all the onu profile."
			::= { fkEponOnuProfileDBAMutilLLidLinkEntry 1 }

		
		-- 1.3.6.1.4.1.10428 9 1.101.20.14.2.5.1.2
		fkEponOnuProfileDBAMultiLLidLinkSlaMinShaBandwidth OBJECT-TYPE
			SYNTAX INTEGER (0 | 256..1000000)
			MAX-ACCESS read-only
			STATUS current
			DESCRIPTION
				"Guaranteed Bandwidth(Kbps).
				System default: 0
				"
			DEFVAL { 0 }
			::= { fkEponOnuProfileDBAMutilLLidLinkEntry 2 }

		
		-- 1.3.6.1.4.1.10428 9 1.101.20.14.2.5.1.3
		fkEponOnuProfileDBAMultiLLidLinkSlaMinShaBurstSize OBJECT-TYPE
			SYNTAX INTEGER (1..256 | 65535)
			MAX-ACCESS read-only
			STATUS current
			DESCRIPTION
				"Minimum Burst Size.
				System default: 65535"
			DEFVAL { 65535 }
			::= { fkEponOnuProfileDBAMutilLLidLinkEntry 3 }

		
		-- 1.3.6.1.4.1.10428 9 1.101.20.14.2.5.1.4
		fkEponOnuProfileDBAMultiLLidLinkSlaMinShaSchedulerLevel OBJECT-TYPE
			SYNTAX INTEGER (0..7 | 255)
			MAX-ACCESS read-only
			STATUS current
			DESCRIPTION
				"Scheduler Level.
				System default 255."
			DEFVAL { 255 }
			::= { fkEponOnuProfileDBAMutilLLidLinkEntry 4 }

		
		-- 1.3.6.1.4.1.10428 9 1.101.20.14.2.5.1.5
		fkEponOnuProfileDBAMultiLLidLinkSlaMinShaWeight OBJECT-TYPE
			SYNTAX INTEGER (2..32 | 65535)
			MAX-ACCESS read-only
			STATUS current
			DESCRIPTION
				"Weight
				System default: 65535."
			DEFVAL { 65535 }
			::= { fkEponOnuProfileDBAMutilLLidLinkEntry 5 }

		
		-- 1.3.6.1.4.1.10428 9 1.101.20.14.2.5.1.6
		fkEponOnuProfileDBAMultiLLidLinkSlaMaxShaBandwidth OBJECT-TYPE
			SYNTAX INTEGER (0 | 256..1000000)
			MAX-ACCESS read-only
			STATUS current
			DESCRIPTION
				"Guaranteed Bandwidth(Kbps).
				System default: 100000"
			DEFVAL { 100000 }
			::= { fkEponOnuProfileDBAMutilLLidLinkEntry 6 }

		
		-- 1.3.6.1.4.1.10428 9 1.101.20.14.2.5.1.7
		fkEponOnuProfileDBAMultiLLidLinkSlaMaxShaBurstSize OBJECT-TYPE
			SYNTAX INTEGER (1..256)
			MAX-ACCESS read-only
			STATUS current
			DESCRIPTION
				"Maximum Burst Size.
				System default: 255"
			DEFVAL { 255 }
			::= { fkEponOnuProfileDBAMutilLLidLinkEntry 7 }

		
		-- 1.3.6.1.4.1.10428 9 1.101.20.14.2.5.1.8
		fkEponOnuProfileDBAMultiLLidLinkSlaMaxShaSchedulerLevel OBJECT-TYPE
			SYNTAX INTEGER (0..7)
			MAX-ACCESS read-only
			STATUS current
			DESCRIPTION
				"Scheduler Level.
				System default 2."
			DEFVAL { 2 }
			::= { fkEponOnuProfileDBAMutilLLidLinkEntry 8 }

		
		-- 1.3.6.1.4.1.10428 9 1.101.20.14.2.5.1.9
		fkEponOnuProfileDBAMultiLLidLinkSlaMaxShaWeight OBJECT-TYPE
			SYNTAX INTEGER (2..32)
			MAX-ACCESS read-only
			STATUS current
			DESCRIPTION
				"Weight
				System default: 24."
			DEFVAL { 24 }
			::= { fkEponOnuProfileDBAMutilLLidLinkEntry 9 }

		
		-- 1.3.6.1.4.1.10428 9 1.101.20.14.2.5.1.10
		fkEponOnuProfileDBAMultiLLidLinkSlaOperate OBJECT-TYPE
			SYNTAX INTEGER
				{
				none(1),
				forceReport(2),
				disableOamUplift(3)
				}
			MAX-ACCESS read-only
			STATUS current
			DESCRIPTION
				"Onu profile DBA options."
			::= { fkEponOnuProfileDBAMutilLLidLinkEntry 10 }

		
		-- 1.3.6.1.4.1.10428 9 1.101.20.14.2.5.1.11
		fkEponOnuProfileDBAMultiLLidLinkSlaPollingLevel OBJECT-TYPE
			SYNTAX INTEGER (0..7)
			MAX-ACCESS read-only
			STATUS current
			DESCRIPTION
				"Polling Interval Select."
			::= { fkEponOnuProfileDBAMutilLLidLinkEntry 11 }

		
		-- 1.3.6.1.4.1.10428 9 1.101.20.14.2.5.1.12
		fkEponOnuProfileDBAMultiLLidLinkSlaTDMRate OBJECT-TYPE
			SYNTAX INTEGER (0 | 1..4000)
			MAX-ACCESS read-only
			STATUS current
			DESCRIPTION
				"TDM Rate.
				System default 0."
			DEFVAL { 0 }
			::= { fkEponOnuProfileDBAMutilLLidLinkEntry 12 }

		
		-- 1.3.6.1.4.1.10428 9 1.101.20.14.2.5.1.13
		fkEponOnuProfileDBAMultiLLidLinkSlaTDMGrantLength OBJECT-TYPE
			SYNTAX INTEGER (0 | 84..131072)
			MAX-ACCESS read-only
			STATUS current
			DESCRIPTION
				"TDM grant length.
				System default 0."
			DEFVAL { 0 }
			::= { fkEponOnuProfileDBAMutilLLidLinkEntry 13 }

		
		-- 1.3.6.1.4.1.10428 9 1.101.20.14.2.5.1.14
		fkEponOnuProfileDBAMultiLLidLinkOAMMaxOAMRate OBJECT-TYPE
			SYNTAX INTEGER (0..25)
			MAX-ACCESS read-only
			STATUS current
			DESCRIPTION
				"Maximum OAM rate.
				System default 3."
			DEFVAL { 3 }
			::= { fkEponOnuProfileDBAMutilLLidLinkEntry 14 }

		
		-- 1.3.6.1.4.1.10428 9 1.101.20.14.2.5.1.15
		fkEponOnuProfileDBAMultiLLidLinkOAMMinOAMRate OBJECT-TYPE
			SYNTAX INTEGER (0..10)
			MAX-ACCESS read-only
			STATUS current
			DESCRIPTION
				"Minimum OAM rate.
				System default 10."
			DEFVAL { 10 }
			::= { fkEponOnuProfileDBAMutilLLidLinkEntry 15 }

		
		-- 1.3.6.1.4.1.10428 9 1.101.20.14.2.6
		fkEponOnuProfileDBAMultiLLidQueueSlaTable OBJECT-TYPE
			SYNTAX SEQUENCE OF FkEponOnuProfileDBAMultiLLidQueueSlaEntry
			MAX-ACCESS not-accessible
			STATUS current
			DESCRIPTION
				"Description."
			::= { fkEponOnuProfileDBA 6 }

		
		-- 1.3.6.1.4.1.10428 9 1.101.20.14.2.6.1
		fkEponOnuProfileDBAMultiLLidQueueSlaEntry OBJECT-TYPE
			SYNTAX FkEponOnuProfileDBAMultiLLidQueueSlaEntry
			MAX-ACCESS not-accessible
			STATUS current
			DESCRIPTION
				"Epon onu profile DBA queue sla entry."
			INDEX { fkEponProfileIndex, fkEponOnuProfileDBAQueueIndex }
			::= { fkEponOnuProfileDBAMultiLLidQueueSlaTable 1 }

		
		FkEponOnuProfileDBAMultiLLidQueueSlaEntry ::=
			SEQUENCE { 
				fkEponOnuProfileDBAMultiLLidQueueIndex
					INTEGER,
				fkEponOnuProfileDBAMultiLLidQueueSlaDownMinShaBandwidth
					INTEGER,
				fkEponOnuProfileDBAMultiLLidQueueSlaDownMinShaBurstSize
					INTEGER,
				fkEponOnuProfileDBAMultiLLidQueueSlaDownMinShaSchedulerLevel
					INTEGER,
				fkEponOnuProfileDBAMultiLLidQueueSlaDownMinShaWeight
					INTEGER,
				fkEponOnuProfileDBAMutiLLidQueueSlaDownMaxShaBandwidth
					INTEGER,
				fkEponOnuProfileDBAMultiLLidQueueSlaDownMaxShaBurstSize
					INTEGER,
				fkEponOnuProfileDBAMultiLLidQueueSlaDownMaxShaSchedulerLevel
					INTEGER,
				fkEponOnuProfileDBAMultiLLidQueueSlaDownMaxShaWeight
					INTEGER,
				fkEponOnuProfileDBAMultiLLidQueueSlaUpMinShaBandwidth
					INTEGER,
				fkEponOnuProfileDBAMultiLLidQueueSlaUpMinShaBurstSize
					INTEGER,
				fkEponOnuProfileDBAMultiLLidQueueSlaUpMinShaSchedulerLevel
					INTEGER,
				fkEponOnuProfileDBAMultiLLidQueueSlaUpMinShaWeight
					INTEGER,
				fkEponOnuProfileDBAMultiLLidQueueSlaUpMaxShaBandwidth
					INTEGER,
				fkEponOnuProfileDBAMultiLLidQueueSlaUpMaxShaBurstSize
					INTEGER,
				fkEponOnuProfileDBAMultiLLidQueueSlaUpMaxShaSchedulerLevel
					INTEGER,
				fkEponOnuProfileDBAMultiLLidQueueSlaUpMaxShaWeight
					INTEGER
			 }

		-- 1.3.6.1.4.1.10428 9 1.101.20.14.2.6.1.1
		fkEponOnuProfileDBAMultiLLidQueueIndex OBJECT-TYPE
			SYNTAX INTEGER (0..3)
			MAX-ACCESS read-only
			STATUS current
			DESCRIPTION
				"Queue index."
			::= { fkEponOnuProfileDBAMultiLLidQueueSlaEntry 1 }

		
		-- 1.3.6.1.4.1.10428 9 1.101.20.14.2.6.1.2
		fkEponOnuProfileDBAMultiLLidQueueSlaDownMinShaBandwidth OBJECT-TYPE
			SYNTAX INTEGER (0 | 256..1000000)
			MAX-ACCESS read-only
			STATUS current
			DESCRIPTION
				"Queue sla downstream shaper minimum bandwidth.
				System default 0."
			DEFVAL { 0 }
			::= { fkEponOnuProfileDBAMultiLLidQueueSlaEntry 2 }

		
		-- 1.3.6.1.4.1.10428 9 1.101.20.14.2.6.1.3
		fkEponOnuProfileDBAMultiLLidQueueSlaDownMinShaBurstSize OBJECT-TYPE
			SYNTAX INTEGER (1..256 | 65535)
			MAX-ACCESS read-only
			STATUS current
			DESCRIPTION
				"Queue sla downstream shaper minimum burst size.
				System default 65535."
			DEFVAL { 65535 }
			::= { fkEponOnuProfileDBAMultiLLidQueueSlaEntry 3 }

		
		-- 1.3.6.1.4.1.10428 9 1.101.20.14.2.6.1.4
		fkEponOnuProfileDBAMultiLLidQueueSlaDownMinShaSchedulerLevel OBJECT-TYPE
			SYNTAX INTEGER (0..7 | 255)
			MAX-ACCESS read-only
			STATUS current
			DESCRIPTION
				"Queue sla downstream shaper minimum scheduer level.
				System default 255."
			DEFVAL { 255 }
			::= { fkEponOnuProfileDBAMultiLLidQueueSlaEntry 4 }

		
		-- 1.3.6.1.4.1.10428 9 1.101.20.14.2.6.1.5
		fkEponOnuProfileDBAMultiLLidQueueSlaDownMinShaWeight OBJECT-TYPE
			SYNTAX INTEGER (2..32 | 65535)
			MAX-ACCESS read-only
			STATUS current
			DESCRIPTION
				"Queue sla downstream shaper minimum weight.
				System default 65535."
			DEFVAL { 65535 }
			::= { fkEponOnuProfileDBAMultiLLidQueueSlaEntry 5 }

		
		-- 1.3.6.1.4.1.10428 9 1.101.20.14.2.6.1.6
		fkEponOnuProfileDBAMutiLLidQueueSlaDownMaxShaBandwidth OBJECT-TYPE
			SYNTAX INTEGER (256..1000000)
			MAX-ACCESS read-only
			STATUS current
			DESCRIPTION
				"Queue sla downstream shaper maximum bandwidth.
				System default 100000"
			DEFVAL { 100000 }
			::= { fkEponOnuProfileDBAMultiLLidQueueSlaEntry 6 }

		
		-- 1.3.6.1.4.1.10428 9 1.101.20.14.2.6.1.7
		fkEponOnuProfileDBAMultiLLidQueueSlaDownMaxShaBurstSize OBJECT-TYPE
			SYNTAX INTEGER (1..256)
			MAX-ACCESS read-only
			STATUS current
			DESCRIPTION
				"Queue sla downstream shaper maximum burst size.
				System default 255."
			DEFVAL { 255 }
			::= { fkEponOnuProfileDBAMultiLLidQueueSlaEntry 7 }

		
		-- 1.3.6.1.4.1.10428 9 1.101.20.14.2.6.1.8
		fkEponOnuProfileDBAMultiLLidQueueSlaDownMaxShaSchedulerLevel OBJECT-TYPE
			SYNTAX INTEGER (0..7)
			MAX-ACCESS read-only
			STATUS current
			DESCRIPTION
				"Queue sla downstream shaper maximum scheduler level.
				System default 2."
			DEFVAL { 2 }
			::= { fkEponOnuProfileDBAMultiLLidQueueSlaEntry 8 }

		
		-- 1.3.6.1.4.1.10428 9 1.101.20.14.2.6.1.9
		fkEponOnuProfileDBAMultiLLidQueueSlaDownMaxShaWeight OBJECT-TYPE
			SYNTAX INTEGER (2..32)
			MAX-ACCESS read-only
			STATUS current
			DESCRIPTION
				"Queue sla downstream shaper maximum weight.
				System default 24."
			DEFVAL { 24 }
			::= { fkEponOnuProfileDBAMultiLLidQueueSlaEntry 9 }

		
		-- 1.3.6.1.4.1.10428 9 1.101.20.14.2.6.1.10
		fkEponOnuProfileDBAMultiLLidQueueSlaUpMinShaBandwidth OBJECT-TYPE
			SYNTAX INTEGER (0 | 256..1000000)
			MAX-ACCESS read-only
			STATUS current
			DESCRIPTION
				"Queue sla upstream shaper minimum bandwidth.
				System default 0."
			DEFVAL { 0 }
			::= { fkEponOnuProfileDBAMultiLLidQueueSlaEntry 10 }

		
		-- 1.3.6.1.4.1.10428 9 1.101.20.14.2.6.1.11
		fkEponOnuProfileDBAMultiLLidQueueSlaUpMinShaBurstSize OBJECT-TYPE
			SYNTAX INTEGER (1..256 | 65535)
			MAX-ACCESS read-only
			STATUS current
			DESCRIPTION
				"Queue sla upstream shaper minimum bandwidth.
				System default 65535."
			DEFVAL { 65535 }
			::= { fkEponOnuProfileDBAMultiLLidQueueSlaEntry 11 }

		
		-- 1.3.6.1.4.1.10428 9 1.101.20.14.2.6.1.12
		fkEponOnuProfileDBAMultiLLidQueueSlaUpMinShaSchedulerLevel OBJECT-TYPE
			SYNTAX INTEGER (0..7 | 255)
			MAX-ACCESS read-write
			STATUS current
			DESCRIPTION
				"Queue sla upstream shaper minimum scheduler level.
				System default 255."
			DEFVAL { 255 }
			::= { fkEponOnuProfileDBAMultiLLidQueueSlaEntry 12 }

		
		-- 1.3.6.1.4.1.10428 9 1.101.20.14.2.6.1.13
		fkEponOnuProfileDBAMultiLLidQueueSlaUpMinShaWeight OBJECT-TYPE
			SYNTAX INTEGER (2..32 | 65535)
			MAX-ACCESS read-only
			STATUS current
			DESCRIPTION
				"Queue sla upstream shaper minimum weight.
				System default 65535."
			DEFVAL { 65535 }
			::= { fkEponOnuProfileDBAMultiLLidQueueSlaEntry 13 }

		
		-- 1.3.6.1.4.1.10428 9 1.101.20.14.2.6.1.14
		fkEponOnuProfileDBAMultiLLidQueueSlaUpMaxShaBandwidth OBJECT-TYPE
			SYNTAX INTEGER (256..1000000)
			MAX-ACCESS read-write
			STATUS current
			DESCRIPTION
				"Queue sla upstream shaper maximum bandwidth.
				System default 100000."
			DEFVAL { 100000 }
			::= { fkEponOnuProfileDBAMultiLLidQueueSlaEntry 14 }

		
		-- 1.3.6.1.4.1.10428 9 1.101.20.14.2.6.1.15
		fkEponOnuProfileDBAMultiLLidQueueSlaUpMaxShaBurstSize OBJECT-TYPE
			SYNTAX INTEGER (1..256)
			MAX-ACCESS read-only
			STATUS current
			DESCRIPTION
				"Queue sla upstream shaper maximum burst size.
				System default 255."
			DEFVAL { 255 }
			::= { fkEponOnuProfileDBAMultiLLidQueueSlaEntry 15 }

		
		-- 1.3.6.1.4.1.10428 9 1.101.20.14.2.6.1.16
		fkEponOnuProfileDBAMultiLLidQueueSlaUpMaxShaSchedulerLevel OBJECT-TYPE
			SYNTAX INTEGER (0..7)
			MAX-ACCESS read-write
			STATUS current
			DESCRIPTION
				"Queue sla upstream shaper maximum scheduler level.
				System default 2."
			DEFVAL { 2 }
			::= { fkEponOnuProfileDBAMultiLLidQueueSlaEntry 16 }

		
		-- 1.3.6.1.4.1.10428 9 1.101.20.14.2.6.1.17
		fkEponOnuProfileDBAMultiLLidQueueSlaUpMaxShaWeight OBJECT-TYPE
			SYNTAX INTEGER (2..32)
			MAX-ACCESS read-only
			STATUS current
			DESCRIPTION
				"Queue sla upstream shaper maximum weight.
				System default 24."
			DEFVAL { 24 }
			::= { fkEponOnuProfileDBAMultiLLidQueueSlaEntry 17 }

		
		-- 1.3.6.1.4.1.10428 9 1.101.20.14.2.7
		fkEponOnuProfileDBAMultiLLidControl OBJECT IDENTIFIER ::= { fkEponOnuProfileDBA 7 }

		
		-- 1.3.6.1.4.1.10428 9 1.101.20.14.2.7.1
		fkEponOnuProfileDBAMultiLLidControlRequest OBJECT-TYPE
			SYNTAX INTEGER
				{
				setPonOnuProfileDBAMultillidLinkSla(1),
				noPonOnuProfileDBAMultillidLinkSla(2),
				setPonOnuProfileDBAMultillidQueueSla(3),
				noPonOnuProfileDBAMultillidQueueSla(4),
				noPonOnuProfileDBAMultillidQueueSlaAll(5),
				setPonOnuProfileDBAMultillidLinkOAMRate(6),
				noPonOnuProfileDBAMultillidLinkOAMRate(7)
				}
			MAX-ACCESS read-write
			STATUS current
			DESCRIPTION
				"The request of a user command."
			::= { fkEponOnuProfileDBAMultiLLidControl 1 }

		
		-- 1.3.6.1.4.1.10428 9 1.101.20.14.2.7.2
		fkEponOnuProfileDBAMultiLLidControlStatus OBJECT-TYPE
			SYNTAX FkControlStatusType
			MAX-ACCESS read-write
			STATUS current
			DESCRIPTION
				"The status of user command."
			::= { fkEponOnuProfileDBAMultiLLidControl 2 }

		
		-- 1.3.6.1.4.1.10428 9 1.101.20.14.2.7.3
		fkEponOnuProfileDBAMultiLLidControlTimer OBJECT-TYPE
			SYNTAX Gauge32
			MAX-ACCESS read-write
			STATUS current
			DESCRIPTION
				"The maximum time for the manager for a long running user command."
			::= { fkEponOnuProfileDBAMultiLLidControl 3 }

		
		-- 1.3.6.1.4.1.10428 9 1.101.20.14.2.7.4
		fkEponOnuProfileDBAMultiLLidControlTimeStamp OBJECT-TYPE
			SYNTAX TimeTicks
			MAX-ACCESS read-write
			STATUS current
			DESCRIPTION
				"The time stamp of the last command(end of command)."
			::= { fkEponOnuProfileDBAMultiLLidControl 4 }

		
		-- 1.3.6.1.4.1.10428 9 1.101.20.14.2.7.5
		fkEponOnuProfileDBAMultiLLidControlReqResult OBJECT-TYPE
			SYNTAX FkControlRequestResultType
			MAX-ACCESS read-write
			STATUS current
			DESCRIPTION
				"The result of the last user command."
			::= { fkEponOnuProfileDBAMultiLLidControl 5 }

		
		-- 1.3.6.1.4.1.10428 9 1.101.20.14.2.7.6
		fkEponOnuProfileDBAMultiLLidControlProfileName OBJECT-TYPE
			SYNTAX OCTET STRING (SIZE (1..64))
			MAX-ACCESS read-write
			STATUS current
			DESCRIPTION
				"Profile name.
				'all' means configure all the onu profile."
			::= { fkEponOnuProfileDBAMultiLLidControl 6 }

		
		-- 1.3.6.1.4.1.10428 9 1.101.20.14.2.7.7
		fkEponOnuProfileDBAMultiLLidControlLinkSlaMinShaBandwidth OBJECT-TYPE
			SYNTAX INTEGER (0 | 256..1000000)
			MAX-ACCESS read-write
			STATUS current
			DESCRIPTION
				"Guaranteed Bandwidth(Kbps).
				0 means that we will use the default value."
			DEFVAL { 0 }
			::= { fkEponOnuProfileDBAMultiLLidControl 7 }

		
		-- 1.3.6.1.4.1.10428 9 1.101.20.14.2.7.8
		fkEponOnuProfileDBAMultiLLidControlLinkSlaMinShaBurstSize OBJECT-TYPE
			SYNTAX INTEGER (1..256 | 65535)
			MAX-ACCESS read-write
			STATUS current
			DESCRIPTION
				"Minimum Burst Size.
				Default 65535."
			DEFVAL { 65535 }
			::= { fkEponOnuProfileDBAMultiLLidControl 8 }

		
		-- 1.3.6.1.4.1.10428 9 1.101.20.14.2.7.9
		fkEponOnuProfileDBAMultiLLidControlLinkSlaMinShaSchedulerLevel OBJECT-TYPE
			SYNTAX INTEGER (0..7 | 255)
			MAX-ACCESS read-write
			STATUS current
			DESCRIPTION
				"Scheduler Level.
				Default 255."
			DEFVAL { 255 }
			::= { fkEponOnuProfileDBAMultiLLidControl 9 }

		
		-- 1.3.6.1.4.1.10428 9 1.101.20.14.2.7.10
		fkEponOnuProfileDBAMultiLLidControlLinkSlaMinShaWeight OBJECT-TYPE
			SYNTAX INTEGER (2..32 | 65535)
			MAX-ACCESS read-write
			STATUS current
			DESCRIPTION
				"Weight.
				Default 65535."
			DEFVAL { 0 }
			::= { fkEponOnuProfileDBAMultiLLidControl 10 }

		
		-- 1.3.6.1.4.1.10428 9 1.101.20.14.2.7.11
		fkEponOnuProfileDBAMultiLLidControlLinkSlaMaxShaBandwidth OBJECT-TYPE
			SYNTAX INTEGER (256..1000000)
			MAX-ACCESS read-write
			STATUS current
			DESCRIPTION
				"Guaranteed Bandwidth(Kbps)."
			::= { fkEponOnuProfileDBAMultiLLidControl 11 }

		
		-- 1.3.6.1.4.1.10428 9 1.101.20.14.2.7.12
		fkEponOnuProfileDBAMultiLLidControlLinkSlaMaxShaBurstSize OBJECT-TYPE
			SYNTAX INTEGER (1..256)
			MAX-ACCESS read-write
			STATUS current
			DESCRIPTION
				"Maximum burst size."
			::= { fkEponOnuProfileDBAMultiLLidControl 12 }

		
		-- 1.3.6.1.4.1.10428 9 1.101.20.14.2.7.13
		fkEponOnuProfileDBAMultiLLidControlLinkSlaMaxShaSchedulerLevel OBJECT-TYPE
			SYNTAX INTEGER (0..7)
			MAX-ACCESS read-write
			STATUS current
			DESCRIPTION
				"Scheduler Level."
			::= { fkEponOnuProfileDBAMultiLLidControl 13 }

		
		-- 1.3.6.1.4.1.10428 9 1.101.20.14.2.7.14
		fkEponOnuProfileDBAMultiLLidControlLinkSlaMaxShaWeight OBJECT-TYPE
			SYNTAX INTEGER (2..32)
			MAX-ACCESS read-write
			STATUS current
			DESCRIPTION
				"Weight."
			::= { fkEponOnuProfileDBAMultiLLidControl 14 }

		
		-- 1.3.6.1.4.1.10428 9 1.101.20.14.2.7.15
		fkEponOnuProfileDBAMultiLLidControlLinkSlaOperate OBJECT-TYPE
			SYNTAX INTEGER
				{
				none(1),
				forceReport(2),
				disableOAMUplift(3)
				}
			MAX-ACCESS read-write
			STATUS current
			DESCRIPTION
				"Onu profile DBA options."
			::= { fkEponOnuProfileDBAMultiLLidControl 15 }

		
		-- 1.3.6.1.4.1.10428 9 1.101.20.14.2.7.16
		fkEponOnuProfileDBAMultiLLIdControlLinkSlaPollingLevel OBJECT-TYPE
			SYNTAX INTEGER (0..7)
			MAX-ACCESS read-write
			STATUS current
			DESCRIPTION
				"Polling Interval Select."
			::= { fkEponOnuProfileDBAMultiLLidControl 16 }

		
		-- 1.3.6.1.4.1.10428 9 1.101.20.14.2.7.17
		fkEponOnuProfileDBAlMultiLLidControLinkSlaTDMRate OBJECT-TYPE
			SYNTAX INTEGER (0 | 1..4000)
			MAX-ACCESS read-write
			STATUS current
			DESCRIPTION
				"TDM Rate.
				0 means that we will use the default value."
			DEFVAL { 0 }
			::= { fkEponOnuProfileDBAMultiLLidControl 17 }

		
		-- 1.3.6.1.4.1.10428 9 1.101.20.14.2.7.18
		fkEponOnuProfileDBAMultiLLidControlLinkSlaTDMGrantLength OBJECT-TYPE
			SYNTAX INTEGER (0 | 84..131072)
			MAX-ACCESS read-write
			STATUS current
			DESCRIPTION
				"TDM grant length.
				0 means that we will use the default value."
			DEFVAL { 0 }
			::= { fkEponOnuProfileDBAMultiLLidControl 18 }

		
		-- 1.3.6.1.4.1.10428 9 1.101.20.14.2.7.19
		fkEponOnuProfileDBAMultiLLidControlQueueIndex OBJECT-TYPE
			SYNTAX INTEGER (0..3)
			MAX-ACCESS read-write
			STATUS current
			DESCRIPTION
				"Queue index."
			::= { fkEponOnuProfileDBAMultiLLidControl 19 }

		
		-- 1.3.6.1.4.1.10428 9 1.101.20.14.2.7.20
		fkEponOnuProfileDBAMultiLLidControlQueueSlaMinShaBandwidth OBJECT-TYPE
			SYNTAX INTEGER (256..1000000)
			MAX-ACCESS read-write
			STATUS current
			DESCRIPTION
				"Guaranteed Bandwidth(Kbps)."
			::= { fkEponOnuProfileDBAMultiLLidControl 20 }

		
		-- 1.3.6.1.4.1.10428 9 1.101.20.14.2.7.21
		fkEponOnuProfileDBAMultiLLidControlQueueSlaMinShaBurstSize OBJECT-TYPE
			SYNTAX INTEGER (1..256)
			MAX-ACCESS read-write
			STATUS current
			DESCRIPTION
				"Minimum Burst Size."
			::= { fkEponOnuProfileDBAMultiLLidControl 21 }

		
		-- 1.3.6.1.4.1.10428 9 1.101.20.14.2.7.22
		fkEponOnuProfileDBAMultiLLidControlQueueSlaMinShaSchedulerLevel OBJECT-TYPE
			SYNTAX INTEGER (0..7)
			MAX-ACCESS read-write
			STATUS current
			DESCRIPTION
				"Scheduler Level."
			::= { fkEponOnuProfileDBAMultiLLidControl 22 }

		
		-- 1.3.6.1.4.1.10428 9 1.101.20.14.2.7.23
		fkEponOnuProfileDBAMultiLLidControlQueueSlaMinShaWeight OBJECT-TYPE
			SYNTAX INTEGER (2..32)
			MAX-ACCESS read-write
			STATUS current
			DESCRIPTION
				"Weight."
			::= { fkEponOnuProfileDBAMultiLLidControl 23 }

		
		-- 1.3.6.1.4.1.10428 9 1.101.20.14.2.7.24
		fkEponOnuProfileDBAMultiLLidControlQueueSlaMaxShaBandwidth OBJECT-TYPE
			SYNTAX INTEGER (256..1000000)
			MAX-ACCESS read-write
			STATUS current
			DESCRIPTION
				"Guaranteed Bandwidth(Kbps)."
			::= { fkEponOnuProfileDBAMultiLLidControl 24 }

		
		-- 1.3.6.1.4.1.10428 9 1.101.20.14.2.7.25
		fkEponOnuProfileDBAMultiLLidControlQueueSlaMaxShaBurstSize OBJECT-TYPE
			SYNTAX INTEGER (1..256)
			MAX-ACCESS read-write
			STATUS current
			DESCRIPTION
				"Maximum burst size."
			::= { fkEponOnuProfileDBAMultiLLidControl 25 }

		
		-- 1.3.6.1.4.1.10428 9 1.101.20.14.2.7.26
		fkEponOnuProfileDBAMultiLLidControlQueueSlaMaxShaSchedulerLevel OBJECT-TYPE
			SYNTAX INTEGER (0..7)
			MAX-ACCESS read-write
			STATUS current
			DESCRIPTION
				"Scheduler Level."
			::= { fkEponOnuProfileDBAMultiLLidControl 26 }

		
		-- 1.3.6.1.4.1.10428 9 1.101.20.14.2.7.27
		fkEponOnuProfileDBAMultiLLidControlQueueSlaMaxShaWeight OBJECT-TYPE
			SYNTAX INTEGER (2..32)
			MAX-ACCESS read-write
			STATUS current
			DESCRIPTION
				"Weight."
			::= { fkEponOnuProfileDBAMultiLLidControl 27 }

		
		-- 1.3.6.1.4.1.10428 9 1.101.20.14.2.7.28
		fkEponOnuProfileDBAMultiLLIdControlQueueSlaOperate OBJECT-TYPE
			SYNTAX INTEGER
				{
				upstream(1),
				downstream(2)
				}
			MAX-ACCESS read-write
			STATUS current
			DESCRIPTION
				"Direction of Egress Shaping."
			::= { fkEponOnuProfileDBAMultiLLidControl 28 }

		
		-- 1.3.6.1.4.1.10428 9 1.101.20.14.2.7.29
		fkEponOnuProfileDBAMultiLLidControlLinkOAMMaxRate OBJECT-TYPE
			SYNTAX INTEGER (0..25)
			MAX-ACCESS read-write
			STATUS current
			DESCRIPTION
				"Maximum OAM rate."
			::= { fkEponOnuProfileDBAMultiLLidControl 29 }

		
		-- 1.3.6.1.4.1.10428 9 1.101.20.14.2.7.30
		fkEponOnuProfileDBAMultiLLidControlLinkOAMMinRate OBJECT-TYPE
			SYNTAX INTEGER (0..10)
			MAX-ACCESS read-write
			STATUS current
			DESCRIPTION
				"Minimum OAM rate."
			::= { fkEponOnuProfileDBAMultiLLidControl 30 }

		
		-- 1.3.6.1.4.1.10428 9 1.101.20.14.2.8
		fkEponOnuProfileDBAMultiLLidNotification OBJECT IDENTIFIER ::= { fkEponOnuProfileDBA 8 }

		
		-- 1.3.6.1.4.1.10428 9 1.101.20.14.2.8.1
		fkEponOnuProfileDBAMultiLLidLinkSlaChanged NOTIFICATION-TYPE
			OBJECTS { fkEponOnuProfileDBAMultiLLidControlRequest, fkEponOnuProfileDBAMultiLLidControlTimeStamp, fkEponOnuProfileDBAMultiLLidControlReqResult, fkEponOnuProfileDBAMultiLLidControlProfileName }
			STATUS current
			DESCRIPTION 
				"Set ONU profile DBA link sla trap."
			::= { fkEponOnuProfileDBAMultiLLidNotification 1 }

		
		-- 1.3.6.1.4.1.10428 9 1.101.20.14.2.8.2
		fkEponOnuProfileDBAMultiLLidQueueSlaChanged NOTIFICATION-TYPE
			OBJECTS { fkEponOnuProfileDBAMultiLLidControlRequest, fkEponOnuProfileDBAMultiLLidControlTimeStamp, fkEponOnuProfileDBAMultiLLidControlReqResult, fkEponOnuProfileDBAMultiLLidControlProfileName, fkEponOnuProfileDBAMultiLLidControlQueueIndex
				 }
			STATUS current
			DESCRIPTION 
				"Onu profile DBA queue sla changed trap."
			::= { fkEponOnuProfileDBAMultiLLidNotification 2 }

		
		-- 1.3.6.1.4.1.10428 9 1.101.20.14.2.8.3
		fkEponOnuProfileDBAMultiLLidLinkOAMRateChanged NOTIFICATION-TYPE
			OBJECTS { fkEponOnuProfileDBAMultiLLidControlRequest, fkEponOnuProfileDBAMultiLLidControlTimeStamp, fkEponOnuProfileDBAMultiLLidControlReqResult, fkEponOnuProfileDBAMultiLLidControlProfileName, fkEponOnuProfileDBAMultiLLidControlLinkOAMMaxRate, 
				fkEponOnuProfileDBAMultiLLidControlLinkOAMMinRate }
			STATUS current
			DESCRIPTION 
				"Onu profile DBA link OAM changed trap."
			::= { fkEponOnuProfileDBAMultiLLidNotification 3 }

		
		-- 1.3.6.1.4.1.10428 9 1.101.20.15
		fkEponDomain OBJECT IDENTIFIER ::= { fkEpon 15 }

		
		-- 1.3.6.1.4.1.10428 9 1.101.20.15.1
		fkEponDomainTable OBJECT-TYPE
			SYNTAX SEQUENCE OF FkEponDomainEntry
			MAX-ACCESS not-accessible
			STATUS current
			DESCRIPTION
				"Description."
			::= { fkEponDomain 1 }

		
		-- 1.3.6.1.4.1.10428 9 1.101.20.15.1.1
		fkEponDomainEntry OBJECT-TYPE
			SYNTAX FkEponDomainEntry
			MAX-ACCESS not-accessible
			STATUS current
			DESCRIPTION
				"Description."
			INDEX { fkEponOltIndex, fkEponDomainVlanID }
			::= { fkEponDomainTable 1 }

		
		FkEponDomainEntry ::=
			SEQUENCE { 
				fkEponDomainVlanID
					INTEGER,
				fkEponDomainUnTaggedPorts
					OCTET STRING,
				fkEponDomainMultiUnTaggedPorts
					OCTET STRING
			 }

		-- 1.3.6.1.4.1.10428 9 1.101.20.15.1.1.1
		fkEponDomainVlanID OBJECT-TYPE
			SYNTAX INTEGER (1..4094 | 4098)
			MAX-ACCESS read-only
			STATUS current
			DESCRIPTION
				"Pon olt/onu vlan index,4098 is the default vlanid."
			::= { fkEponDomainEntry 1 }

		
		-- 1.3.6.1.4.1.10428 9 1.101.20.15.1.1.2
		fkEponDomainUnTaggedPorts OBJECT-TYPE
			SYNTAX OCTET STRING
			MAX-ACCESS read-only
			STATUS current
			DESCRIPTION
				"the port map of vlan ,'.' is not add in vlan,'u' is untagged port,'t' is tagged port.
				"
			::= { fkEponDomainEntry 2 }

		
		-- 1.3.6.1.4.1.10428 9 1.101.20.15.1.1.3
		fkEponDomainMultiUnTaggedPorts OBJECT-TYPE
			SYNTAX OCTET STRING
			MAX-ACCESS read-only
			STATUS current
			DESCRIPTION
				"the port map of vlan ,'.' is not add in vlan,'u' is untagged port,'t' is tagged port.
				"
			::= { fkEponDomainEntry 3 }

		
		-- 1.3.6.1.4.1.10428 9 1.101.20.15.2
		fkEponDomainControl OBJECT IDENTIFIER ::= { fkEponDomain 2 }

		
		-- 1.3.6.1.4.1.10428 9 1.101.20.15.2.1
		fkEponDomainControlRequest OBJECT-TYPE
			SYNTAX INTEGER
				{
				setEponCreateVlan(1),
				setEponDestroyVlan(2),
				setEponVlanAdd(3),
				setEponDefaultVlanAdd(4),
				setEponVlanDel(5),
				setEponDefaultVlanDel(6),
				setEponVlanMultiAdd(7),
				setEponDefaultVlanMultiAdd(8),
				setEponVlanMultiDel(9),
				setEponDefaultVlanMultiDel(10)
				}
			MAX-ACCESS read-write
			STATUS current
			DESCRIPTION
				"The request of a user command."
			::= { fkEponDomainControl 1 }

		
		-- 1.3.6.1.4.1.10428 9 1.101.20.15.2.2
		fkEponDomainControlStatus OBJECT-TYPE
			SYNTAX FkControlStatusType
			MAX-ACCESS read-only
			STATUS current
			DESCRIPTION
				"The status of user command."
			::= { fkEponDomainControl 2 }

		
		-- 1.3.6.1.4.1.10428 9 1.101.20.15.2.3
		fkEponDomainControlTimer OBJECT-TYPE
			SYNTAX Gauge32
			MAX-ACCESS read-write
			STATUS current
			DESCRIPTION
				"The maximum time for the manager for a long running user command."
			::= { fkEponDomainControl 3 }

		
		-- 1.3.6.1.4.1.10428 9 1.101.20.15.2.4
		fkEponDomainControlTimeStamp OBJECT-TYPE
			SYNTAX TimeTicks
			MAX-ACCESS read-only
			STATUS current
			DESCRIPTION
				"The time stamp of the last command(end of command)."
			::= { fkEponDomainControl 4 }

		
		-- 1.3.6.1.4.1.10428 9 1.101.20.15.2.5
		fkEponDomainControlReqResult OBJECT-TYPE
			SYNTAX FkControlRequestResultType
			MAX-ACCESS read-only
			STATUS current
			DESCRIPTION
				"The result of the last user command."
			::= { fkEponDomainControl 5 }

		
		-- 1.3.6.1.4.1.10428 9 1.101.20.15.2.6
		fkEponDomainControlOltIndex OBJECT-TYPE
			SYNTAX INTEGER (1..64)
			MAX-ACCESS read-write
			STATUS current
			DESCRIPTION
				"OLT index."
			::= { fkEponDomainControl 6 }

		
		-- 1.3.6.1.4.1.10428 9 1.101.20.15.2.7
		fkEponDomainControlOnuIndex OBJECT-TYPE
			SYNTAX INTEGER (1..64)
			MAX-ACCESS read-write
			STATUS current
			DESCRIPTION
				"ONU index"
			::= { fkEponDomainControl 7 }

		
		-- 1.3.6.1.4.1.10428 9 1.101.20.15.2.8
		fkEponDomainControlVlanID OBJECT-TYPE
			SYNTAX INTEGER (1..4096)
			MAX-ACCESS read-write
			STATUS current
			DESCRIPTION
				"OLT vlan index,default vlan ID 4098."
			::= { fkEponDomainControl 8 }

		
		-- 1.3.6.1.4.1.10428 9 1.101.20.15.2.9
		fkEponDomainControlUnTaggedPorts OBJECT-TYPE
			SYNTAX INTEGER
				{
				tag(0),
				untag(1)
				}
			MAX-ACCESS read-write
			STATUS current
			DESCRIPTION
				"Portlist for members of this Vlan they will send only untagged frames.
				The octet string is a list of pairs of octets each identify
				an fkBridgePortIndex. The least significant byte is the second
				octet.
				"
			::= { fkEponDomainControl 9 }

		
		-- 1.3.6.1.4.1.10428 9 1.101.20.15.3
		fkEponDomainNotification OBJECT IDENTIFIER ::= { fkEponDomain 3 }

		
		-- 1.3.6.1.4.1.10428 9 1.101.20.15.3.1
		fkEponDomainVlanCreate NOTIFICATION-TYPE
			OBJECTS { fkEponDomainControlReqResult, fkEponDomainControlRequest, fkEponDomainControlTimeStamp, fkEponDomainControlVlanID }
			STATUS current
			DESCRIPTION 
				"Description."
			::= { fkEponDomainNotification 1 }

		
		-- 1.3.6.1.4.1.10428 9 1.101.20.15.3.2
		fkEponDomainDestroyVlan NOTIFICATION-TYPE
			OBJECTS { fkEponDomainControlReqResult, fkEponDomainControlRequest, fkEponDomainControlTimeStamp, fkEponDomainControlVlanID }
			STATUS current
			DESCRIPTION 
				"Description."
			::= { fkEponDomainNotification 2 }

		
		-- 1.3.6.1.4.1.10428 9 1.101.20.15.3.3
		fkEponDomainVlanAdd NOTIFICATION-TYPE
			OBJECTS { fkEponDomainControlReqResult, fkEponDomainControlRequest, fkEponDomainControlTimeStamp, fkEponDomainControlOnuIndex, fkEponDomainControlVlanID
				 }
			STATUS current
			DESCRIPTION 
				"Description."
			::= { fkEponDomainNotification 3 }

		
		-- 1.3.6.1.4.1.10428 9 1.101.20.15.3.4
		fkEponDomainDefaultVlanAdd NOTIFICATION-TYPE
			OBJECTS { fkEponDomainControlReqResult, fkEponDomainControlRequest, fkEponDomainControlTimeStamp, fkEponDomainControlOnuIndex, fkEponDomainControlVlanID
				 }
			STATUS current
			DESCRIPTION 
				"Description."
			::= { fkEponDomainNotification 4 }

		
		-- 1.3.6.1.4.1.10428 9 1.101.20.15.3.5
		fkEponDomainVlanDel NOTIFICATION-TYPE
			OBJECTS { fkEponDomainControlReqResult, fkEponDomainControlRequest, fkEponDomainControlTimeStamp, fkEponDomainControlOnuIndex, fkEponDomainControlVlanID
				 }
			STATUS current
			DESCRIPTION 
				"Description."
			::= { fkEponDomainNotification 5 }

		
		-- 1.3.6.1.4.1.10428 9 1.101.20.15.3.6
		fkEponDomainDefaultVlanDel NOTIFICATION-TYPE
			OBJECTS { fkEponDomainControlReqResult, fkEponDomainControlRequest, fkEponDomainControlTimeStamp, fkEponDomainControlOnuIndex, fkEponDomainControlVlanID
				 }
			STATUS current
			DESCRIPTION 
				"Description."
			::= { fkEponDomainNotification 6 }

		
		-- 1.3.6.1.4.1.10428 9 1.101.20.15.3.7
		fkEponDomainVlanMultiAdd NOTIFICATION-TYPE
			OBJECTS { fkEponDomainControlReqResult, fkEponDomainControlRequest, fkEponDomainControlTimeStamp, fkEponDomainControlOnuIndex, fkEponDomainControlVlanID
				 }
			STATUS current
			DESCRIPTION 
				"Description."
			::= { fkEponDomainNotification 7 }

		
		-- 1.3.6.1.4.1.10428 9 1.101.20.15.3.8
		fkEponDomainDefaultVlanMultiAdd NOTIFICATION-TYPE
			OBJECTS { fkEponDomainControlReqResult, fkEponDomainControlRequest, fkEponDomainControlTimeStamp, fkEponDomainControlOnuIndex, fkEponDomainControlVlanID
				 }
			STATUS current
			DESCRIPTION 
				"Description."
			::= { fkEponDomainNotification 8 }

		
		-- 1.3.6.1.4.1.10428 9 1.101.20.15.3.9
		fkEponDomainVlanMultiDel NOTIFICATION-TYPE
			OBJECTS { fkEponDomainControlReqResult, fkEponDomainControlRequest, fkEponDomainControlTimeStamp, fkEponDomainControlOnuIndex, fkEponDomainControlVlanID
				 }
			STATUS current
			DESCRIPTION 
				"Description."
			::= { fkEponDomainNotification 9 }

		
		-- 1.3.6.1.4.1.10428 9 1.101.20.15.3.10
		fkEponDomainDefaultVlanMultiDel NOTIFICATION-TYPE
			OBJECTS { fkEponDomainControlReqResult, fkEponDomainControlRequest, fkEponDomainControlTimeStamp, fkEponDomainControlOnuIndex, fkEponDomainControlVlanID
				 }
			STATUS current
			DESCRIPTION 
				"Description."
			::= { fkEponDomainNotification 10 }

		
		-- 1.3.6.1.4.1.10428 9 1.101.20.16
		fkEponOltRedundancy OBJECT IDENTIFIER ::= { fkEpon 16 }

		
		-- 1.3.6.1.4.1.10428 9 1.101.20.16.1
		fkEponOltRedundancyTable OBJECT-TYPE
			SYNTAX SEQUENCE OF FkEponOltRedundancyEntry
			MAX-ACCESS not-accessible
			STATUS current
			DESCRIPTION
				"Description."
			::= { fkEponOltRedundancy 1 }

		
		-- 1.3.6.1.4.1.10428 9 1.101.20.16.1.1
		fkEponOltRedundancyEntry OBJECT-TYPE
			SYNTAX FkEponOltRedundancyEntry
			MAX-ACCESS not-accessible
			STATUS current
			DESCRIPTION
				"Description."
			INDEX { fkEponOltRedundancyMaste }
			::= { fkEponOltRedundancyTable 1 }

		
		FkEponOltRedundancyEntry ::=
			SEQUENCE { 
				fkEponOltRedundancyMaste
					Integer32,
				fkEponOltRedundancyGroupID
					INTEGER,
				fkEponOltRedundancyTrunkID
					Integer32,
				fkEponOltRedundancyMasteStatus
					INTEGER,
				fkEponOltRedundancySlave
					Integer32,
				fkEponOltRedundancySlaveStatus
					INTEGER,
				fkEponOltRedundancyWtrValue
					Integer32,
				fkEponOltRedundancyRemainTime
					Integer32,
				fkEponOltRedundancyLastReason
					INTEGER,
				fkEponOltRedundancyHoldOffTime
					Integer32
			 }

		-- 1.3.6.1.4.1.10428 9 1.101.20.16.1.1.1
		fkEponOltRedundancyMaste OBJECT-TYPE
			SYNTAX Integer32 (1..24)
			MAX-ACCESS read-only
			STATUS current
			DESCRIPTION
				"Redundancy Master OLT_ID."
			::= { fkEponOltRedundancyEntry 1 }

		
		-- 1.3.6.1.4.1.10428 9 1.101.20.16.1.1.2
		fkEponOltRedundancyGroupID OBJECT-TYPE
			SYNTAX INTEGER (1..4)
			MAX-ACCESS read-only
			STATUS current
			DESCRIPTION
				"Redundancy Group ID (1-4)."
			::= { fkEponOltRedundancyEntry 2 }

		
		-- 1.3.6.1.4.1.10428 9 1.101.20.16.1.1.3
		fkEponOltRedundancyTrunkID OBJECT-TYPE
			SYNTAX Integer32 (0..13 | 255)
			MAX-ACCESS read-only
			STATUS current
			DESCRIPTION
				"Redundancy trunk ID 0-13,disable is 255."
			::= { fkEponOltRedundancyEntry 3 }

		
		-- 1.3.6.1.4.1.10428 9 1.101.20.16.1.1.4
		fkEponOltRedundancyMasteStatus OBJECT-TYPE
			SYNTAX INTEGER
				{
				none(0),
				active(1),
				standby(2),
				pending(3),
				unknown(4),
				active_los(5),
				standby_los(6)
				}
			MAX-ACCESS read-only
			STATUS current
			DESCRIPTION
				"Redundancy Master status."
			::= { fkEponOltRedundancyEntry 4 }

		
		-- 1.3.6.1.4.1.10428 9 1.101.20.16.1.1.5
		fkEponOltRedundancySlave OBJECT-TYPE
			SYNTAX Integer32
			MAX-ACCESS read-only
			STATUS current
			DESCRIPTION
				"Redundancy Slave OLT_ID."
			::= { fkEponOltRedundancyEntry 5 }

		
		-- 1.3.6.1.4.1.10428 9 1.101.20.16.1.1.6
		fkEponOltRedundancySlaveStatus OBJECT-TYPE
			SYNTAX INTEGER
				{
				none(0),
				active(1),
				standby(2),
				pending(3),
				unknown(4),
				active_los(5),
				standby_los(6)
				}
			MAX-ACCESS read-only
			STATUS current
			DESCRIPTION
				"Redundancy Slave status."
			::= { fkEponOltRedundancyEntry 6 }

		
		-- 1.3.6.1.4.1.10428 9 1.101.20.16.1.1.7
		fkEponOltRedundancyWtrValue OBJECT-TYPE
			SYNTAX Integer32 (1..60)
			MAX-ACCESS read-only
			STATUS current
			DESCRIPTION
				"WTR Value(Unit:min,1-60), -1 is invalid value."
			::= { fkEponOltRedundancyEntry 7 }

		
		-- 1.3.6.1.4.1.10428 9 1.101.20.16.1.1.8
		fkEponOltRedundancyRemainTime OBJECT-TYPE
			SYNTAX Integer32
			MAX-ACCESS read-write
			STATUS current
			DESCRIPTION
				"Remain time Value(Unit:sec)"
			::= { fkEponOltRedundancyEntry 8 }

		
		-- 1.3.6.1.4.1.10428 9 1.101.20.16.1.1.9
		fkEponOltRedundancyLastReason OBJECT-TYPE
			SYNTAX INTEGER
				{
				none(0),
				manualSwitch(1),
				losOfActive(2),
				slotRemoved(3),
				slotRestart(4),
				autoDetect(5),
				unknown(6)
				}
			MAX-ACCESS read-only
			STATUS current
			DESCRIPTION
				"Olt Redundancy Last Reason."
			::= { fkEponOltRedundancyEntry 9 }

		
		-- 1.3.6.1.4.1.10428 9 1.101.20.16.1.1.10
		fkEponOltRedundancyHoldOffTime OBJECT-TYPE
			SYNTAX Integer32 (0..10)
			MAX-ACCESS read-write
			STATUS current
			DESCRIPTION
				"Holdoff time range:0-10(default:0ms)."
			::= { fkEponOltRedundancyEntry 10 }

		
		-- 1.3.6.1.4.1.10428 9 1.101.20.16.2
		fkEponOltRedundancyControl OBJECT IDENTIFIER ::= { fkEponOltRedundancy 2 }

		
		-- 1.3.6.1.4.1.10428 9 1.101.20.16.2.1
		fkEponOltRedundancyControlRequest OBJECT-TYPE
			SYNTAX INTEGER
				{
				setEponOltRedundancy(1),
				noEponOltRedundancy(2),
				setEponOltSwitchoverForceGroup(3),
				setEponOltRedundancyHoldOffTime(4)
				}
			MAX-ACCESS read-write
			STATUS current
			DESCRIPTION
				"The request of a user command."
			::= { fkEponOltRedundancyControl 1 }

		
		-- 1.3.6.1.4.1.10428 9 1.101.20.16.2.2
		fkEponOltRedundancyControlStatus OBJECT-TYPE
			SYNTAX FkControlStatusType
			MAX-ACCESS read-only
			STATUS current
			DESCRIPTION
				"The status of user command."
			::= { fkEponOltRedundancyControl 2 }

		
		-- 1.3.6.1.4.1.10428 9 1.101.20.16.2.3
		fkEponOltRedundancyControlTimer OBJECT-TYPE
			SYNTAX Gauge32
			MAX-ACCESS read-write
			STATUS current
			DESCRIPTION
				"The maximum time for the manager for a long running user command."
			::= { fkEponOltRedundancyControl 3 }

		
		-- 1.3.6.1.4.1.10428 9 1.101.20.16.2.4
		fkEponOltRedundancyControlTimeStamp OBJECT-TYPE
			SYNTAX TimeTicks
			MAX-ACCESS read-only
			STATUS current
			DESCRIPTION
				"The time stamp of the last command(end of command)."
			::= { fkEponOltRedundancyControl 4 }

		
		-- 1.3.6.1.4.1.10428 9 1.101.20.16.2.5
		fkEponOltRedundancyControlReqResult OBJECT-TYPE
			SYNTAX FkControlRequestResultType
			MAX-ACCESS read-only
			STATUS current
			DESCRIPTION
				"The result of the last user command."
			::= { fkEponOltRedundancyControl 5 }

		
		-- 1.3.6.1.4.1.10428 9 1.101.20.16.2.6
		fkEponOltRedundancyControlGroupID OBJECT-TYPE
			SYNTAX INTEGER (1..4)
			MAX-ACCESS read-write
			STATUS current
			DESCRIPTION
				"Redundancy Group ID (1-4)."
			::= { fkEponOltRedundancyControl 6 }

		
		-- 1.3.6.1.4.1.10428 9 1.101.20.16.2.7
		fkEponOltRedundancyControlTrunkID OBJECT-TYPE
			SYNTAX INTEGER (0..13 | 255)
			MAX-ACCESS read-write
			STATUS current
			DESCRIPTION
				"Redundancy trunk ID 0-13,disable is 255."
			::= { fkEponOltRedundancyControl 7 }

		
		-- 1.3.6.1.4.1.10428 9 1.101.20.16.2.8
		fkEponOltRedundancyControlMaster OBJECT-TYPE
			SYNTAX INTEGER
			MAX-ACCESS read-write
			STATUS current
			DESCRIPTION
				"Redundancy Master OLT_ID."
			::= { fkEponOltRedundancyControl 8 }

		
		-- 1.3.6.1.4.1.10428 9 1.101.20.16.2.9
		fkEponOltRedundancyControlSlave OBJECT-TYPE
			SYNTAX INTEGER
			MAX-ACCESS read-write
			STATUS current
			DESCRIPTION
				"Redundancy Slave OLT_ID."
			::= { fkEponOltRedundancyControl 9 }

		
		-- 1.3.6.1.4.1.10428 9 1.101.20.16.2.10
		fkEponOltRedundancyControlWtrValue OBJECT-TYPE
			SYNTAX INTEGER (1..60)
			MAX-ACCESS read-write
			STATUS current
			DESCRIPTION
				"WTR value."
			::= { fkEponOltRedundancyControl 10 }

		
		-- 1.3.6.1.4.1.10428 9 1.101.20.16.2.11
		fkEponOltRedundancyControlHoldOffTime OBJECT-TYPE
			SYNTAX Integer32 (0..10)
			MAX-ACCESS read-write
			STATUS current
			DESCRIPTION
				"Holdoff time range:0-10(default:0ms)."
			::= { fkEponOltRedundancyControl 11 }

		
		-- 1.3.6.1.4.1.10428 9 1.101.20.16.3
		fkEponOltRedundancyNotification OBJECT IDENTIFIER ::= { fkEponOltRedundancy 3 }

		
		-- 1.3.6.1.4.1.10428 9 1.101.20.16.3.1
		fkEponOltRedundancyChanged NOTIFICATION-TYPE
			OBJECTS { fkEponOltRedundancyControlWtrValue, fkEponOltRedundancyControlSlave, fkEponOltRedundancyControlMaster, fkEponOltRedundancyControlTrunkID, fkEponOltRedundancyControlGroupID, 
				fkEponOltRedundancyReqResult, fkEponOltRedundancyTimeStamp, fkEponOltRedundancyRequest }
			STATUS current
			DESCRIPTION 
				"Description."
			::= { fkEponOltRedundancyNotification 1 }

		
		-- 1.3.6.1.4.1.10428 9 1.101.20.16.3.2
		fkEponOltRedundancySwitchoverForceGroup NOTIFICATION-TYPE
			OBJECTS { fkEponOltRedundancyRequest, fkEponOltRedundancyReqResult, fkEponOltRedundancyTimeStamp, fkEponOltRedundancyControlGroupID }
			STATUS current
			DESCRIPTION 
				"Description."
			::= { fkEponOltRedundancyNotification 2 }

		
		-- 1.3.6.1.4.1.10428 9 1.101.20.16.3.3
		fkEponOltRedundancyHoldOffTimeChanged NOTIFICATION-TYPE
			OBJECTS { fkEponOltRedundancyControlRequest, fkEponOltRedundancyControlTimeStamp, fkEponOltRedundancyControlReqResult, fkEponOltRedundancyControlGroupID, fkEponOltRedundancyControlHoldOffTime
				 }
			STATUS current
			DESCRIPTION 
				"Description."
			::= { fkEponOltRedundancyNotification 3 }

		
		-- 1.3.6.1.4.1.10428 9 1.101.20.17
		fkEponGroup OBJECT-GROUP
			OBJECTS { fkEponOltControlRequest, fkEponOltControlStatus, fkEponOltControlTimer, fkEponOltControlTimeStamp, fkEponOltControlReqResult, 
				fkEponOltControlOltIndex, fkEponOltControlRegMode, fkEponOltControlEncryptionPolicy, fkEponOltControlP2pAccessControl, fkEponOltControlDbaInternal, 
				fkEponOltControlDbaCycle, fkEponOltControlDbaDiscoveryFrequency, fkEponOltControlDbaDiscoveryLength, fkEponOnuControlRequest, fkEponOnuControlStatus, 
				fkEponOnuControlTimer, fkEponOnuControlTimeStamp, fkEponOnuControlReqResult, fkEponOnuControlOltIndex, fkEponOnuControlMacAddress, 
				fkEponOnuControlRegMode, fkEponOnuControlDescription, fkEponOnuControlProfile, fkEponProfileControlRequest, fkEponProfileControlStatus, 
				fkEponProfileControlTimer, fkEponProfileControlTimeStamp, fkEponProfileControlReqResult, fkEponProfileControlName, fkEponProfileControlDPDownMaxBandwidth, 
				fkEponProfileControlDPDownMaxBurstSize, fkEponProfileControlDPP2pMaxBandwidth, fkEponProfileControlDPP2pMaxBurstSize, fkEponProfileControlSlaGuaranteedBandwidth, fkEponProfileControlSlaPlatoClass, 
				fkEponProfileControlSlaPlatoGuaranteedBandwidth1m, fkEponProfileControlSlaPlatoGuaranteedBandwdith64k, fkEponProfileControlSlaPlatoBestEffortBandwidth1m, fkEponProfileControlSlaPlatoBestEffortBandwidth64k, fkEponProfileControlSlaPlatoDelayLevel, 
				fkEponAlarmControlRequest, fkEponAlarmControlStatus, fkEponAlarmControlTimer, fkEponAlarmControlTimeStamp, fkEponAlarmControlReqResult, 
				fkEponAlarmControlOltIndex, fkEponAlarmControlBadEncryption, fkEponAlarmControlDyingGasp, fkEponAlarmControlLlidMismatch, fkEponAlarmControlOnuRegistrationError, 
				fkEponOnuControlOnuIndex, fkEponOnuControlOnuStatus, fkEponStatsOltControlRequest, fkEponStatsOltControlStatus, fkEponStatsOltControlTimer, 
				fkEponStatsOltControlTimeStamp, fkEponStatsOltControlReqResult, fkEponStatsOltControlOltIndex, fkEponStatsOltControlChannelIndex, fkEponOnuControlLoopbackProvision, 
				fkEponOltControlOltStatus, fkEponAlarmControlTooManyOnuRegistration, fkEponProfileQueueControlRequest, fkEponProfileQueueControlStatus, fkEponProfileQueueControlTimer, 
				fkEponProfileQueueControlTimeStamp, fkEponProfileQueueControlReqResult, fkEponProfileQueueControlProfileIndex, fkEponProfileQueueControlQueueIndex, fkEponProfileQueueControlQPUpQueue, 
				fkEponProfileQueueControlQPUpMaxBandwidth, fkEponProfileQueueControlQPUpMAxBurstSize, fkEponProfileQueueControlQPDownQueue, fkEponProfileQueueControlQPDownMaxBandwidth, fkEponProfileQueueControlQPDownMAxBurstSize, 
				fkEponOltControlProfile, fkEponProfilePortControlRequest, fkEponProfilePortControlStatus, fkEponProfilePortControlTimer, fkEponProfilePortControlTimeStamp, 
				fkEponProfilePortControlReqResult, fkEponProfilePortControlAdminStatus, fkEponProfilePortControlNego, fkEponProfilePortControlSpeed, fkEponProfilePortControlMaxHost, 
				fkEponProfileVlanControlRequest, fkEponProfileVlanControlStatus, fkEponProfileVlanControlTimer, fkEponProfileVlanControlTimeStamp, fkEponProfileVlanControlReqResult, 
				fkEponProfileVlanControlVlanIndex, fkEponProfileVlanControlVlanEgressPorts, fkEponProfileVlanControlVlanUntaggedPorts, fkEponProfilePortControlPvid, fkEponProfilePortControlEgressRateLimit, 
				fkEponProfilePortControlIngressRateLimit, fkEponProfilePortControlIngressRateLimitMode, fkEponOnuPortControlReqResult, fkEponOnuPortControlOltIndex, fkEponOnuPortControlOnuIndex, 
				fkEponOnuPortControlPortIndex, fkEponOnuPortControlRequest, fkEponOnuPortControlStatus, fkEponOnuPortControlTimer, fkEponOnuPortControlTimeStamp, 
				fkEponOnuClassificationControlRequest, fkEponOnuClassificationControlStatus, fkEponOnuClassificationControlTimer, fkEponOnuClassificationControlTimeStamp, fkEponOnuClassificationControlProtoTypeNum, 
				fkEponOnuClassificationControlL3Addr, fkEponOnuClassificationControlReqResult, fkEponOnuClassificationControlName, fkEponOnuClassificationControlTrafficDirection, fkEponOnuClassificationControlLayer, 
				fkEponOnuClassificationControlEtherType, fkEponProfileVlanControlProfileIndex, fkEponProfileClassificationControlQueue, fkEponProfileClassificationControlReqResult, fkEponProfileClassificationControlProfileIndex, 
				fkEponProfileClassificationControlClassificationIndex, fkEponProfileClassificationControlMatchAction, fkEponProfileClassificationControlRequest, fkEponProfileClassificationControlStatus, fkEponProfileClassificationControlTimer, 
				fkEponProfileClassificationControlTimeStamp, fkEponOltIndex, fkEponOltRegMode, fkEponOltStatus, fkEponOltEncryptionPolicy, 
				fkEponOltP2pAccessControl, fkEponOltDbaInternal, fkEponOltDbaCycle, fkEponOltDbaDiscoveryFrequency, fkEponOltDbaDiscoveryLength, 
				fkEponOltProfile, fkEponOltTxFault, fkEponOltLossOfSignal, fkEponOltAdminRegMode, fkEponOltSC, 
				fkEponOltSCAutoOnuBlock, fkEponOltControlSC, fkEponOltControlSCAutoOnuBlock, fkEponOltControlUpgradeFilename, fkEponOnuIndex, 
				fkEponOnuLlid, fkEponOnuRegMode, fkEponOnuStatus, fkEponOnuMacAddress, fkEponOnuRtt, 
				fkEponOnuDescription, fkEponOnuProfile, fkEponOnuLoopbackProvision, fkEponOnuVendor, fkEponOnuFirmwareRev, 
				fkEponOnuControlTxPowerOffTimer, fkEponOnuVlanIndex, fkEponOnuVlanEgressPorts, fkEponOnuVlanUntaggedPorts, fkEponOnuPortIndex, 
				fkEponOnuPortAdminStatus, fkEponOnuPortOperStatus, fkEponOnuPortNego, fkEponOnuPortSpeed, fkEponOnuPortDuplex, 
				fkEponOnuPortMaxHost, fkEponOnuPortPvid, fkEponOnuPortIngressRateLimitMode, fkEponOnuPortIngressRateLimit, fkEponOnuPortEgressRateLimit, 
				fkEponOnuPortFlowControl, fkEponOnuFdbMacAddress, fkEponOnuFdbType, fkEponOnuFdbPermission, fkEponOnuFdbControlRequest, 
				fkEponOnuFdbControlStatus, fkEponOnuFdbControlTimer, fkEponOnuFdbControlTimeStamp, fkEponOnuFdbControlReqResult, fkEponOnuFdbControlOltIndex, 
				fkEponOnuFdbControlOnuIndex, fkEponOnuFdbControlType, fkEponOnuUserMacIndex, fkEponOnuUserMacMacAddress, fkEponOnuUserMacUsedTime, 
				fkEponProfileIndex, fkEponProfileName, fkEponProfileDPDownMaxBandwidth, fkEponProfileDPDownMaxBurstSize, fkEponProfileDPP2pMaxBandwidth, 
				fkEponProfileDPP2pMaxBurstSize, fkEponProfileSlaGuaranteedBandwidth, fkEponProfileSlaBestEffortBandwidth, fkEponProfileSlaPlatoClass, fkEponProfileSlaPlatoMinBandwidth1m, 
				fkEponProfileSlaPlatoMinBandwdith64k, fkEponProfileSlaPlatoMaxBandwidth1m, fkEponProfileSlaPlatoMaxBandwidth64k, fkEponProfileSlaPlatoDelayLevel, fkEponProfileIgmpFilter, 
				fkEponProfileIgmpSnooping, fkEponProfileSTPenable, fkEponProfileControlExtendMtu, fkEponProfileControlIgmpFilter, fkEponProfileControlSnooping, 
				fkEponProfileControlSTPenable, fkEponProfileQueueIndex, fkEponProfileQueueQPUpQueue, fkEponProfileQueueQPUpMaxBandwidth, fkEponProfileQueueQPUpMAxBurstSize, 
				fkEponProfileQueueQPDownQueue, fkEponProfileQueueQPDownMaxBandwidth, fkEponProfileQueueQPDownMAxBurstSize, fkEponProfileQueueQLimitUpBlockSize, fkEponProfileQueueQLimitDownBlockSize, 
				fkEponProfileQueueControlLimitFlag, fkEponProfileQueueControlBlockSize0, fkEponProfileQueueControlBlockSize1, fkEponProfileQueueControlBlockSize2, fkEponProfileQueueControlBlockSize3, 
				fkEponProfileVlanIndex, fkEponProfileVlanEgressPorts, fkEponProfileVlanUntaggedPorts, fkEponProfilePortIndex, fkEponProfilePortAdminStatus, 
				fkEponProfilePortNego, fkEponProfilePortSpeed, fkEponProfilePortduplex, fkEponProfilePortMaxHost, fkEponProfilePortPvid, 
				fkEponProfilePortIngressRateLimitMode, fkEponProfilePortIngressRateLimit, fkEponProfilePortEgressRateLimit, fkEponProfilePortFlowControl, fkEponProfilePortControlFlowControl, 
				fkEponProfileClassificationIndex, fkEponProfileClassificationMatchAction, fkEponProfileClassificationQueue, fkEponAlarmBadEncryption, fkEponAlarmDyingGasp, 
				fkEponAlarmLlidMismatch, fkEponAlarmOnuRegistrationError, fkEponAlarmTooManyOnuRegistration, fkEponStatsOltInOctets, fkEponStatsOltInPkts, 
				fkEponStatsOltInPause, fkEponStatsOltInErroredFrame, fkEponStatsOltInUnicastPkts, fkEponstatsOltInBroadcastPkts, fkEponStatsOltInMulticastPkts, 
				fkEponStatsOltOutOctets, fkEponStatsOltOutPkts, fkEponStatsOltOutPause, fkEponStatsOltOutDropped, fkEponStatsOltOutUnicastPkts, 
				fkEponstatsOltOutBroadcastPkts, fkEponStatsOltOutMulticastPkts, fkEponStatsOltPonInOctets, fkEponStatsOltPonInPkts, fkEponStatsOltPonInPause, 
				fkEponStatsOltPonInErroredFrame, fkEponStatsOltPonInUnicastPkts, fkEponstatsOltPonInBroadcastPkts, fkEponStatsOltPonInMulticastPkts, fkEponStatsOltPonOutOctets, 
				fkEponStatsOltPonOutPkts, fkEponStatsOltPonOutPause, fkEponStatsOltPonOutDropped, fkEponStatsOltPonOutUnicastPkts, fkEponstatsOltPonOutBroadcastPkts, 
				fkEponStatsOltPonOutMulticastPkts, fkEponStatsOltChannelInOctets, fkEponStatsOltChannelInDataOctets, fkEponStatsOltChannelInPkts, fkEponStatsOltChannelInMulticastPkts, 
				fkEponStatsOltChannelInBroadcastPkts, fkEponStatsOltChannelInErrorOctets, fkEponStatsOltChannelInErrorPkts, fkEponStatsOltChannelOutOctets, fkEponStatsOltChannelOutPkts, 
				fkEponStatsOltChannelOutPolicerDroppedPkts, fkEponStatsOltChannelOutMismatchDroppedPkts, fkEponStatsOltChannelOutMulticastPkts, fkEponStatsOltChannelOutBroadcastPkts, fkEponStatsOltChannelFCS, 
				fkEponStatsOltChannelInRangeLengthErrors, fkEponStatsOltChannelFrameTooLongErrors, fkEponStatsOltChannelInUnicastPkts, fkEponStatsOltChannelOutUnicastPkts, fkEponStatsOnuPortInOctets, 
				fkEponStatsOnuPortInPkts, fkEponStatsOnuPortInUcastPkts, fkEponStatsOnuPortInBcastPkts, fkEponStatsOnuPortInMcastPkts, fkEponStatsOnuPortOutOctets, 
				fkEponStatsOnuPortOutPkts, fkEponStatsOnuPortOutUcastPkts, fkEponStatsOnuPortOutBcastPkts, fkEponStatsOnuPortOutMcastPkts, fkEponOnuClassificationIndex, 
				fkEponOnuClassificationName, fkEponOnuClassificationTrafficDirection, fkEponOnuClassificationLayer, fkEponOnuClassificationEtherType, fkEponOnuClassificationProtoTypeNum, 
				fkEponOnuClassificationL3Addr, fkEponOnuClassificationL4Num, fkEponVlanOltVlanMode, fkEponVlanOltVlanNestedStack, fkEponVlanOltVlanPrefix, 
				fkEponVlanOltVlanSuffix, fkEponVlanOltVlanTag, fkEponVlanOltVlanEtherType, fkEponVlanOltVlanControlRequest, fkEponVlanOltVlanControlStatus, 
				fkEponVlanOltVlanControlTimer, fkEponVlanOltVlanControlTimeStamp, fkEponVlanOltVlanControlReqResult, fkEponVlanOltVlanControlOltIndex, fkEponVlanOltVlanControlOnuIndex, 
				fkEponVlanOltVlanControlMode, fkEponVlanOltVlanControlNestedStack, fkEponVlanOltVlanControlPrefix, fkEponVlanOltVlanControlSuffix, fkEponVlanOltVlanControlVlanTag, 
				fkEponVlanOltVlanControlEtherType, fkEponVlanOnuVlanUpVlanTag, fkEponVlanOnuVlanUpEtherType, fkEponVlanOnuVlanUpPriority, fkEponVlanOnuVlanDownVlanTag, 
				fkEponVlanOnuVlanDownPriority, fkEponVlanOnuVlanControlRequest, fkEponVlanOnuVlanControlStatus, fkEponVlanOnuVlanControlTimer, fkEponVlanOnuVlanControlTimeStamp, 
				fkEponVlanOnuVlanControlReqResult, fkEponVlanOnuVlanControlOltIndex, fkEponVlanOnuVlanControlOnuIndex, fkEponVlanOnuVlanControlUpVlanTag, fkEponVlanOnuVlanControlUpEtherType, 
				fkEponVlanOnuVlanControlUpPriority, fkEponVlanOnuVlanControlDownPriority, fkEponProfileControlIndex, fkEponOnuControlUpgradePath, fkEponProfileControlSlaBestEffortBandwidth, 
				fkEponProfilePortControlProfileIndex, fkEponProfilePortControlPortIndex, fkEponProfilePortControlDuplex, fkEponOnuClassificationControlL4Num, fkEponVlanOnuVlanControlDownVlanTag, 
				fkEponVlanOnuVlanUpMode, fkEponVlanOnuVlanDownMode, fkEponVlanOnuVlanControlUpMode, fkEponProfileQueueControlBlockSize4, fkEponProfileQueueControlBlockSize5, 
				fkEponProfileQueueControlBlockSize6, fkEponProfileQueueControlBlockSize7, fkEponVlanOnuVlanControlDownMode, fkEponProfileUNIQueueUpMaxBandwidth, fkEponProfileUNIQueueUpMaxBurstSize, 
				fkEponProfileUNIQueueDownMaxBandwidth, fkEponProfileUNIQueueDownMaxBurstSize, fkEponProfileUNIQueueControlRequest, fkEponProfileUNIQueueControlStatus, fkEponProfileUNIQueueControlTimer, 
				fkEponProfileUNIQueueControlTimeStamp, fkEponProfileUNIQueueControlReqResult, fkEponProfileUNIQueueControlProfileIndex, fkEponProfileUNIQueueControlUpMaxBandwidth, fkEponProfileUNIQueueControlUpMaxBurstSize, 
				fkEponProfileUNIQueueControlDownMaxBandwidth, fkEponProfileUNIQueueControlDownMaxBurstSize, fkEponPTimeStatsPortSaveTime, fkEponPTimeStatsPortHourInOctets, fkEponPTimeStatsPortHourOutOctets, 
				fkEponPTimeStatsPortDayInOctets, fkEponPTimeStatsPortDayOutOctets, fkEponPTimeStatsOltSaveTime, fkEponPTimeStatsOltHourInOctets, fkEponPTimeStatsOltHourOutOctets, 
				fkEponPTimeStatsOltDayInOctets, fkEponPTimeStatsOltDayOutOctets, fkEponPTimeStatsOnuSaveTime, fkEponPTimeStatsOnuHourInOctets, fkEponPTimeStatsOnuHourOutOctets, 
				fkEponPTimeStatsOnuDayInOctets, fkEponPTimeStatsOnuDayOutOctets, fkEponPTimeStatsControlRequest, fkEponPTimeStatsControlStatus, fkEponPTimeStatsControlTimer, 
				fkEponPTimeStatsControlTimeStamp, fkEponPTimeStatsControlReqResult, fkEponPTimeStatsServiceActivity, fkEponPTimeStatsControlServiceActivity, fkEponOnuSubscriberCurrentIpAddress, 
				fkEponOnuSubscriberCurrentMacAddress, fkEponOnuSubscriberControlRequest, fkEponOnuSubscriberControlStatus, fkEponOnuSubscriberControlTimer, fkEponOnuSubscriberControlTimeStamp, 
				fkEponOnuSubscriberControlReqResult, fkEponOnuSubscriberControlOltIndex, fkEponOnuSubscriberControlOnuIndex, fkEponOnuSubscriberCurrentPort, fkEponOnuSubscriberHistoryTime, 
				fkEponOnuSubscriberHistoryIpAddress, fkEponOnuSubscriberHistoryMacAddress, fkEponOnuSubscriberHistoryPort, fkEponProfileSubscriberInfoCollection, fkEponProfileControlSubscriberInfoCollection, 
				fkEponOnuSubscriberCurrentTime, fkEponOltOperStatus, fkEponProfileLoopDetectStatus, fkEponProfileLoopDetectBlockTimer, fkEponProfileLoopDetectSendingpacket, 
				fkEponProfileControlLoopDetectStatus, fkEponProfileControlLoopDetectBlockTimer, fkEponProfileControlLoopDetectSendingpacket, fkEponBaseSlaPlatoMaxBandwdith, fkEponBaseDPShapingMaxBandwidth, 
				fkEponBasePortMaxHost, fkEponBaseControlRequest, fkEponBaseControlStatus, fkEponBaseControlTimer, fkEponBaseControlTimeStamp, 
				fkEponBaseControlReqResult, fkEponBaseControlSlaPlatoMaxBandwdith, fkEponBaseControlDPShapingMaxBandwidth, fkEponBaseControlPortMaxHost, fkEponBaseOnuAutoUpgrade, 
				fkEponBaseOnuAutoUpgradeRebootTime, fkEponBaseControlOnuAutoUpgrade, fkEponBaseControlOnuAutoUpgradeRebootTime, fkEponOltFirmwareRev, fkEponFirmwareType, 
				fkEponFirmwareName, fkEponFirmwareControlRequest, fkEponFirmwareControlStatus, fkEponFirmwareControlTimer, fkEponFirmwareControlTimeStamp, 
				fkEponFirmwareControlReqResult, fkEponFirmwareControlName, fkEponFirmwareControlUpgradeMethod, fkEponFirmwareControlUpgradeMode, fkEponFirmwareControlServerAddress, 
				fkEponFirmwareControlUser, fkEponFirmwareControlPasswd, fkEponOnuSipGlobalConfigIp, fkEponOnuSipGlobalConfigNetmask, fkEponOnuSipGlobalConfigGateway, 
				fkEponOnuSipGlobalConfigVid, fkEponOnuControlSipGlobalConfigIp, fkEponOnuControlSipGlobalConfigNetmask, fkEponOnuControlSipGlobalConfigGateway, fkEponOnuControlSipGlobalConfigVid, 
				fkEponProfileSipMgPort, fkEponProfileSipProxyServer, fkEponProfileSipProxyServerPort, fkEponProfileSipBackupProxyServer, fkEponProfileSipBackupProxyServerPort, 
				fkEponProfileSipActiveServer, fkEponProfileSipRegisterServer, fkEponProfileSipRegisterServerPort, fkEponProfileSipBackupRegisterServer, fkEponProfileSipBackupRegisterServerPort, 
				fkEponProfileSipOutBindServer, fkEponProfileSipOutBindServerPort, fkEponProfileSipRegisterInterval, fkEponProfileSipHeartBeatSwitch, fkEponProfileSipHeartBeatCycle, 
				fkEponProfileSipHeartBeatCount, fkEponProfileVoiceT38enable, fkEponProfileModemControl, fkEponProfileControlSipMgPort, fkEponProfileControlSipProxyServer, 
				fkEponProfileControlSipProxyServerPort, fkEponProfileControlSipBackupProxyServer, fkEponProfileControlSipBackupProxyServerPort, fkEponProfileControlSipActiveServer, fkEponProfileControlSipRegisterServer, 
				fkEponProfileControlSipRegisterServerPort, fkEponProfileControlSipBackupRegisterServer, fkEponProfileControlSipBackupRegisterServerPort, fkEponProfileControlSipOutBindServer, fkEponProfileControlSipOutBindServerPort, 
				fkEponProfileControlSipRegisterInterval, fkEponProfileControlSipHeartBeatSwitch, fkEponProfileControlSipHeartBeatCycle, fkEponProfileControlSipHeartBeatCount, fkEponProfileControlVoiceT38enable, 
				fkEponProfileControlModemControl, fkEponOnuSipUserConfigControlTimer, fkEponOnuSipUserConfigPots, fkEponOnuSipUserConfigAccount, fkEponOnuSipUserConfigName, 
				fkEponOnuSipUserConfigPasswd, fkEponOnuSipUserConfigControlRequest, fkEponOnuSipUserConfigControlStatus, fkEponOnuSipUserConfigControlTimeStamp, fkEponOnuSipUserConfigControlReqResult, 
				fkEponOnuSipUserConfigControlOltIndex, fkEponOnuSipUserConfigControlOnuIndex, fkEponOnuSipUserConfigControlPots, fkEponOnuSipUserConfigControlAccount, fkEponOnuSipUserConfigControlName, 
				fkEponOnuSipUserConfigControlPasswd, sysDescr, ifIndex, fkEponBaseOnuAgingTime, fkEponBaseAlarmStatus, 
				fkEponBaseAlarmMode, fkEponBaseControlOnuAgingTime, fkEponBaseControlAlarmStatus, fkEponBaseControlAlarmMode, fkEponOltKeyExchangeTimeout, 
				fkEponOltRssiStatus, fkEponOltOnuRegisterCount, fkEponOltControlKeyExchangeTimeout, fkEponOltControlRssiStatus, fkEponOltP2PIndex, 
				fkEponOltP2PEnable, fkEponOltP2POnuID1, fkEponOltP2POnuID2, fkEponOltP2PControlRequest, fkEponOltP2PControlStatus, 
				fkEponOltP2PControlTimer, fkEponOltP2PControlTimeStamp, fkEponOltP2PControlReqResult, fkEponOltP2PControlOltIndex, fkEponOltP2PControlEnable, 
				fkEponOltP2PControlOnuID1, fkEponOltP2PControlOnuID2, fkEponOltDMITemper, fkEponOltDMIVoltage, fkEponOltDMITxBias, 
				fkEponOltDMITxPower, fkEponOltDMIRxPower, fkEponOnuLgPathStatus, fkEponOnuModelType, fkEponOnuSipGlobalConfigMode, 
				fkEponOnuSipGlobalUserName, fkEponOnuSipGlobalPasswd, fkEponOnuRxPower, fkEponOnuRxPowerAlarmStatus, fkEponOnuRssiInfo, 
				fkEponOnuLoopDetectUnblockStatus, fkEponOnuUpgradeStatus, fkEponOnuOltRssiStatus, fkEponOnuOltRssiInfo, fkEponOnuMultiLlid, 
				fkEponOnuMultiMacAddress, fkEponOltDBAMutilLLidLinkOperate, fkEponOnuControlSipGlobalConfigMode, fkEponOnuControlSipGlobalConfigUserName, fkEponOnuControlSipGlobalConfigUserPasswd, 
				fkEponOnuControlPingCount, fkEponOnuDMITemper, fkEponOnuDMIVoltage, fkEponOnuDMITxBias, fkEponOnuDMITxPower, 
				fkEponOnuDMIRxPower, fkEponOnuDMIThresholdWarnTemperLow, fkEponOnuDMIThresholdWarnTemperHigh, fkEponOnuDMIThresholdAlarmTemperLow, fkEponOnuDMIThresholdAlarmTemperHigh, 
				fkEponOnuDMIThresholdWarnVoltageLow, fkEponOnuDMIThresholdWarnVoltageHigh, fkEponOnuDMIThresholdAlarmVoltageLow, fkEponOnuDMIThresholdAlarmVoltageHigh, fkEponOnuDMIThresholdWarnTxbiasLow, 
				fkEponOnuDMIThresholdWarnTxbiasHigh, fkEponOnuDMIThresholdAlarmTxbiasLow, fkEponOnuDMIThresholdAlarmTxbiasHigh, fkEponOnuDMIThresholdWarnTxPowerLow, fkEponOnuDMIThresholdWarnTxPowerHigh, 
				fkEponOnuDMIThresholdAlarmTxPowerLow, fkEponOnuDMIThresholdAlarmTxPowerHigh, fkEponOnuDMIThresholdWarnRxPowerLow, fkEponOnuDMIThresholdWarnRxPowerHigh, fkEponOnuDMIThresholdAlarmRxPowerLow, 
				fkEponOnuDMIThresholdAlarmRxPowerHigh, fkEponOnuDMIThresholdControlRequest, fkEponOnuDMIThresholdControlStatus, fkEponOnuDMIThresholdControlTimer, fkEponOnuDMIThresholdControlTimeStamp, 
				fkEponOnuDMIThresholdControlReqResult, fkEponOnuDMIThresholdControlOltIndex, fkEponOnuDMIThresholdControlOnuIndex, fkEponOnuDMIThresholdControlMonitorType, fkEponOnuDMIThresholdControlMode, 
				fkEponOnuDMIThresholdControlLowThreshold, fkEponOnuDMIThresholdControlHighThreshold, fkEponOnuPortAgingTime, fkEponOnuPortForwardMode, fkEponOnuMacTableDynamicMacAddress, 
				fkEponOnuMacTableStaticMacAddress, fkEponProfileSipDNS1Server, fkEponProfileSipDNS2Server, fkEponProfileDHCPEnable, fkEponProfileMacLearnStatus, 
				fkEponProfileControlSipDNS1Server, fkEponProfileControlSipDNS2Server, fkEponProfileControlDHCPEnable, fkEponProfileControlMacLearnStatus, fkEponProfileIgmpSnoopingIndex, 
				fkEponProfileIgmpSnoopingState, fkEponProfileIgmpSnoopingMaxch, fkEponProfileIgmpSnoopingTagVlan, fkEponProfileIgmpSnoopingControlRequest, fkEponProfileIgmpSnoopingControlStatus, 
				fkEponProfileIgmpSnoopingControlTimer, fkEponProfileIgmpSnoopingControlTimeStamp, fkEponProfileIgmpSnoopingControlReqResult, fkEponProfileIgmpSnoopingControlProfileIndex, fkEponProfileIgmpSnoopingControlState, 
				fkEponProfileIgmpSnoopingControlMaxch, fkEponProfileIgmpSnoopingControlTagVlan, fkEponOnuProfileOnuRuleIndex, fkEponProfileOnuRuleName, fkEponProfileOnuRuleControlRequest, 
				fkEponProfileOnuRuleControlStatus, fkEponProfileOnuRuleControlTimer, fkEponProfileOnuRuleControlTimeStamp, fkEponProfleOnuRuleControlReqResult, fkEponProfileOnuRuleControlProfileIndex, 
				fkEponProfileOnuRuleControlName, fkEponProfilePortIsolationStatus, fkEponProfilePortMaxHostAgingTime, fkEponProfilePortControlIsolationStatus, fkEponProfilePortControlMaxHostAgingTime, 
				fkEponAlarmOpticSignalError, fkEponAlarmStandardLinkFault, fkEponAlarmLossOfSignal, fkEponAlarmTransmitFail, fkEponAlarmMacLearningOverflow, 
				fkEponAlarmLoopback, fkEponAlarmStandardDyingGasp, fkEponAlarmExternalDyingGasp, fkEponAlarmStandardCriticalEvent, fkEponAlarmExternalCriticalEvent, 
				fkEponAlarmEponStandbyLos, fkEponAlarmControlOpticSignalError, fkEponAlarmControlStandardLinkFault, fkEponAlarmControlLossOfSignal, fkEponAlarmControlTransmitFail, 
				fkEponAlarmControlMacLearningOverflow, fkEponAlarmControlLoopback, fkEponAlarmControlStandardDyingGasp, fkEponAlarmControlExternalDyingGasp, fkEponAlarmControlStandardCriticalevent, 
				fkEponAlarmControlExternalCriticalEvent, fkEponAlarmControlEponStandbyLos, fkEponStatsOltHostFrame, fkEponStatsOltInTooLongFrame, fkEponStatsOltHostFrameDropped, 
				fkEponStatsOltPonInHostFrame, fkEponStatsOltPonInTooLongFrame, fkEponStatsOltPonInHostFrameDropped, fkEponStatsOltPonInHECErrorFrame, fkEponStatsOltFromOnuInFrame, 
				fkEponStatsOltFromOnuInErrorFrame, fkEponStatsOltFromOnuInMulticastFrame, fkEponStatsOltFromOnuInBroadcastFrame, fkEponStatsOltFromOnuInReportFrame, fkEponStatsOltFromOnuInCheckSeqErrorFrame, 
				fkEponStatsOltFromOnuInRangeLenErrors, fkEponStatsOltFromOnuInTooLongFrame, fkEponStatsOltFromOnuOutFrame, fkEponStatsOltFromOnuOutFrameBytes, fkEponStatsOltFromOnuOutMulticastFrame, 
				fkEponStatsOltFromOnuOutBroadcastFrame, fkEponStatsOltFromOnuOutDBAGrantFrame, fkEponStatsOltFromOnuOutControlGrantFrame, fkEponStatsOnuPortInUndersize, fkEponStatsOnuPortInOversize, 
				fkEponStatsOnuPortInJabber, fkEponStatsOnuPortInRxError, fkEponStatsOnuPortInRxFcsError, fkEponStatsOnuUniInPkts, fkEponStatsOnuUniInBytes, 
				fkEponStatsOnuUniInErrPkts, fkEponStatsOnuUniInErrBytes, fkEponStatsOnuUniInPause, fkEponStatsOnuUniFrameLongError, fkEponStatsOnuUniOutPkts, 
				fkEponStatsOnuUniOutBytes, fkEponStatsOnuUniOutPause, fkEponStatsOnuUniOutDropPkts, fkEponStatsOnuUnInMcastPkts, fkEponStatsOnuUnInBcastPkts, 
				fkEponStatsOnuUniInDropPkts, fkEponStatsOnuUniOutMcastPkts, fkEponStatsOnuUniOutBcastPkts, fkEponStatsOnuPonInPkts, fkEponStatsOnuPonInBytes, 
				fkEponStatsOnuPonInMcastPkts, fkEponStatsOnuPonIntBcastPkts, fkEponStatsOnuPonInErrPkts, fkEponStatsOnuPonInErrBytes, fkEponStatsOnuPonInPause, 
				fkEponStatsOnuPonInHostPkts, fkEponStatsOnuPonInDropHostPkts, fkEponStatsOnuPonFrameLongError, fkEponStatsOnuPonOutPkts, fkEponStatsOnuPonOutBytes, 
				fkEponStatsOnuPonOutMcastPkts, fkEponStatsOnuPonOutBcastPkts, fkEponStatsOnuPonOutPause, fkEponStatsOnuPonOutDropPkts, fkEponStatsOnuPonOutHostPkts, 
				fkEponStatsOnuPonOutChipErrPkts, fkEponStatsOnuPonInDropPkts, fkEponOnuVoipPortStatus, fkEponOnuSipPortServiceState, fkEponOnuSipPortCodecMode, 
				fkEponRuleClauseQueue, fkEponRuleClauseQueueValue, fkEponRuleClauseLayerOperation, fkEponRuleClauseLayerValue, fkEponRuleClauseL2Mac, 
				fkEponRuleClauseL2EthertypeValue, fkEponRuleClauseNetmask, fkEponRuleClauseL3Addr, fkEponRuleClauseTcpUdpPort, fkEponRuleClauseTcpUdpPortNum, 
				fkEponRuleClauseProtoType, fkEponRuleClauseProtoTypeNum, fkEponRuleClauseVlanType, fkEponRuleClauseVlanValue, fkEponRuleClauseLinkIndexValue, 
				fkEponRuleClauseMatchMode, fkEponRuleClauseControlRequest, fkEponRuleClauseControlStatus, fkEponRuleClauseControlTimer, fkEponRuleClauseControlTimeStamp, 
				fkEponRuleClauseControlReqResult, fkEponRuleClauseControlClauseIndex, fkEponRuleClauseControlClauseMatch, fkEponRuleClauseControlQueue, fkEponRuleClauseControlQueueValue, 
				fkEponRuleClauseControlLayerOperation, fkEponRuleClauseControlLayerValue, fkEponRuleClauseControlL2Mac, fkEponRuleClauseControlL2EtherType, fkEponRuleClauseControlNetmask, 
				fkEponRuleClauseControlL3Addr, fkEponRuleClauseControlTcpUdpPort, fkEponRuleClauseControlTcpUdpPortNum, fkEponRuleClauseControlProtoType, fkEponRuleClauseControlProtoTypeNum, 
				fkEponRuleClauseControlVlanType, fkEponRuleClauseControlVlanValue, fkEponRuleClauseControlLinkIndexValue, fkEponRuleActionVlanOperate, fkEponRuleActionVlanMap, 
				fkEponRuleActionEtherType, fkEponRuleActionVlanID, fkEponRuleActionDiscardOperate, fkEponRuleActionDiscardOperateValue, fkEponRuleActionCaptureHostOperate, 
				fkEponRuleActionCaptureHostFlexibleOperate, fkEponRuleActionQueueId, fkEponRuleActionUnicastLinkDestID, fkEponRuleActionUnicastLinkDestOffset, fkEponRuleActionMulticastLinkDomID, 
				fkEponRuleActionMulticastLinkDomOffset, fkEponRuleActionCosOperate, fkEponRuleActionCosValue, fkEponRuleActionTosOperate, fkEponRuleActionTosValue, 
				fkEponRuleActionOutputOperate, fkEponRuleActionOutputValue, fkEponRuleActionOutputVlanContent, fkEponRuleActionOutputSourceFiledCopy, fkEponRuleActionQueuePendingOperate, 
				fkEponRuleActionControlRequest, fkEponRuleActionControlStatus, fkEponRuleActionControlTimer, fkEponRuleActionControlTimeStamp, fkEponRuleActionControlReqResult, 
				fkEponRuleActionControlIndex, fkEponRuleActionControlVlanOperate, fkEponRuleActionControlVlanMap, fkEponRuleActionControlEtherType, fkEponRuleActionControlVlanID, 
				fkEponRuleActionControlDiscardOperate, fkEponRuleActionControlDiscardOperateValue, fkEponRuleActionControlCaptureHostOperate, fkEponRuleActionControlCaptureHostFlexibleOperate, fkEponRuleActionControlQueueId, 
				fkEponRuleActionControlQueuependingOperate, fkEponRuleActionControlUnicastLinkDestID, fkEponRuleActionControlUnicastLinkDestOffset, fkEponRuleActionControlMulticastLinkDomID, fkEponRuleActionControlMulticastLinkDomOffset, 
				fkEponRuleActionControlCosOperate, fkEponRuleActionControlCosValue, fkEponRuleActionControlTosOperate, fkEponRuleActionControlTosValue, fkEponRuleActionControlOutputOperate, 
				fkEponRuleActionControlOutputValue, fkEponRuleActionControlOutputVlanContent, fkEponRuleActionControlOutputSourceFiledCopy, fkEponRuleModifyRuleName, fkEponRuleModifyTrafficDirection, 
				fkEponRuleModifyPriorityValue, fkEponRuleModifyCIndex, fkEponRuleModifyAIndex, fkEponRuleModifyControlRequest, fkEponRuleModifyControlStatus, 
				fkEponRuleModifyControlTimer, fkEponRuleModifyControlTimeStamp, fkEponRuleModifyControlReqResult, fkEponRuleModifyControlOltId, fkEponRuleModifyControlRuleName, 
				fkEponRuleModifyControlTrafficDirection, fkEponRuleModifyControlPriorityValue, fkEponRuleModifyControlCIndex, fkEponRuleModifyControlAIndex, fkEponOnuRuleName, 
				fkEponOnuRuleIndex, fkEponOnuRuleDirection, fkEponOnuRulePriority, fkEponOnuRuleDscp, fkEponOnuRuleLinkIndex, 
				fkEponOnuRuleQueueIndex, fkEponOnuRuleControlRequest, fkEponOnuRuleControlStatus, fkEponOnuRuleControlTimer, fkEponOnuRuleControlTimeStamp, 
				fkEponOnuRuleControlReqResult, fkEponOnuRuleControlRuleName, fkEponOnuRuleControlDscp, fkEponOnuRuleControlLinkIndex, fkEponOnuRuleControlQueueIndex, 
				fkEponOltDBAGlobalOltLinkOperate, fkEponOltDBAOverGrantMonConfMonitoringInterval, fkEponOltDBAOverGrantMonConfMaxDBAGrantSize, fkEponOltDBAOverGrantMonConfMinGrantUtilization, fkEponOltDBAOverGrantMonConfLeakyBucketCounterValue, 
				fkEponOltDBAMinShaperBandwidth, fkEponOltDBAMinShaperBurstSize, fkEponOltDBAMinShaperScheduleLevel, fkEponOltDBAMinShaperWeight, fkEponOltDBAMaxShaperBandwidth, 
				fkEponOltDBAMaxShaperBurstSize, fkEponOltDBAMaxShaperScheduleLevel, fkEponOltDBAMaxShaperWeight, fkEponOltDBADBAPollingRateLevel, fkEponOltDBADBAPollingRateRate, 
				eEponOltDBADropDownLevel, fkEponOltDBAShaDropDownWeights, fkEponOltDBADropDownWeights, fkEponOltDBAControlRequest, fkEponOltDBAControlStatus, 
				fkEponOltDBAControlTimer, fkEponOltDBAControlTimeStamp, fkEponOltDBAControlReqResult, fkEponOltDBAControlOltIndex, fkEponOltDBAControlOnuIndex, 
				fkEponOltDBAControlDBAPollingRateLevel, fkEponOltDBAControlDBAPollingRateRate, fkEponOltDBAControlShaDropDownWeightsLevel, fkEponOltDBAControlShaDropDownWeights, fkEponOltDBAControlDropDownWeightsLevel, 
				fkEponOltDBAControlDropDownWeightsl, fkEponOltDBAControlGlobalOltLinkOperate, fkEponOltDBAControlOverGrantMonConfMonitoringInterval, fkEponOltDBAControlOverGrantMonConfMaxDBAGrantSize, fkEponOltDBAControlOverGrantMonConfMinGrantUtilization, 
				fkEponOltDBAControlOverGrantMonConfLeakyBucketCounterValue, fkEponOltDBAControlMinShaperBandwidth, fkEponOltDBAControlMinShaperBurstSize, fkEponOltDBAControlMinShaperScheduleLevel, fkEponOltDBAControlMinShaperWeight, 
				fkEponOltDBAControlMaxShaperBandwidth, fkEponOltDBAControlMaxShaperBurstSize, fkEponOltDBAControlMaxShaperScheduleLevel, fkEponOltDBAControlMaxShaperWeight, fkEponOnuProfileDBAProfileName, 
				fkEponOnuProfileDBALinkSlaMinShaBandwidth, fkEponOnuProfileDBALinkSlaMinShaBurstSize, fkEponOnuProfileDBALinkSlaMinShaSchedulerLevel, fkEponOnuProfileDBALinkSlaMinShaWeight, fkEponOnuProfileDBALinkSlaMaxShaBandwidth, 
				fkEponOnuProfileDBALinkSlaMaxShaBurstSize, fkEponOnuProfileDBALinkSlaMaxShaSchedulerLevel, fkEponOnuProfileDBALinkSlaMaxShaWeight, fkEponOnuProfileDBALinkSlaOperate, fkEponOnuProfileDBALinkSlaPollingLevel, 
				fkEponOnuProfileDBALinkSlaTDMRate, fkEponOnuProfileDBALinkSlaTDMGrantLength, fkEponOnuProfileDBALinkOAMMaxOAMRate, fkEponOnuProfileDBALinkOAMMinOAMRate, fkEponOnuProfileDBAQueueIndex, 
				fkEponOnuProfileDBAQueueSlaDownMinShaBandwidth, fkEponOnuProfileDBAQueueSlaDownMinShaBurstSize, fkEponOnuProfileDBAQueueSlaDownMinShaSchedulerLevel, fkEponOnuProfileDBAQueueSlaDownMinShaWeight, fkEponOnuProfileDBAQueueSlaDownMaxShaBandwidth, 
				fkEponOnuProfileDBAQueueSlaDownMaxShaBurstSize, fkEponOnuProfileDBAQueueSlaDownMaxShaSchedulerLevel, fkEponOnuProfileDBAQueueSlaDownMaxShaWeight, fkEponOnuProfileDBAQueueSlaUpMinShaBandwidth, fkEponOnuProfileDBAQueueSlaUpMinShaBurstSize, 
				fkEponOnuProfileDBAQueueSlaUpMinShaSchedulerLevel, fkEponOnuProfileDBAQueueSlaUpMinShaWeight, fkEponOnuProfileDBAQueueSlaUpMaxShaBandwidth, fkEponOnuProfileDBAQueueSlaUpMaxShaBurstSize, fkEponOnuProfileDBAQueueSlaUpMaxShaSchedulerLevel, 
				fkEponOnuProfileDBAQueueSlaUpMaxShaWeight, fkEponOnuProfileDBAControlRequest, fkEponOnuProfileDBAControlStatus, fkEponOnuProfileDBAControlTimer, fkEponOnuProfileDBAControlTimeStamp, 
				fkEponOnuProfileDBAControlReqResult, fkEponOnuProfileDBAControlProfileName, fkEponOnuProfileDBAControlLinkSlaMinShaBandwidth, fkEponOnuProfileDBAControlLinkSlaMinShaBurstSize, fkEponOnuProfileDBAControlLinkSlaMinShaSchedulerLevel, 
				fkEponOnuProfileDBAControlLinkSlaMinShaWeight, fkEponOnuProfileDBAControlLinkSlaMaxShaBandwidth, fkEponOnuProfileDBAControlLinkSlaMaxShaBurstSize, fkEponOnuProfileDBAControlLinkSlaMaxShaSchedulerLevel, fkEponOnuProfileDBAControlLinkSlaMaxShaWeight, 
				fkEponOnuProfileDBAControlLinkSlaOperate, fkEponOnuProfileDBAControlLinkSlaPollingLevel, fkEponOnuProfileDBAControlLinkSlaTDMRate, fkEponOnuProfileDBAControlLinkSlaTDMGrantLength, fkEponOnuProfileDBAControlQueueIndex, 
				fkEponOnuProfileDBAControlQueueSlaMinShaBandwidth, fkEponOnuProfileDBAControlQueueSlaMinShaBurstSize, fkEponOnuProfileDBAControlQueueSlaMinShaSchedulerLevel, fkEponOnuProfileDBAControlQueueSlaMinShaWeight, fkEponOnuProfileDBAControlQueueSlaMaxShaBandwidth, 
				fkEponOnuProfileDBAControlQueueSlaMaxShaBurstSize, fkEponOnuProfileDBAControlQueueSlaMaxShaSchedulerLevel, fkEponOnuProfileDBAControlQueueSlaMaxShaWeight, fkEponOnuProfileDBAControlQueueSlaOperate, fkEponOnuProfileDBAControlLinkOAMMaxRate, 
				fkEponOnuProfileDBAControlLinkOAMMinRate, fkEponOnuProfileDBAMultiLLidProfileName, fkEponOnuProfileDBAMultiLLidLinkSlaMinShaBandwidth, fkEponOnuProfileDBAMultiLLidLinkSlaMinShaBurstSize, fkEponOnuProfileDBAMultiLLidLinkSlaMinShaSchedulerLevel, 
				fkEponOnuProfileDBAMultiLLidLinkSlaMinShaWeight, fkEponOnuProfileDBAMultiLLidLinkSlaMaxShaBandwidth, fkEponOnuProfileDBAMultiLLidLinkSlaMaxShaBurstSize, fkEponOnuProfileDBAMultiLLidLinkSlaMaxShaSchedulerLevel, fkEponOnuProfileDBAMultiLLidLinkSlaMaxShaWeight, 
				fkEponOnuProfileDBAMultiLLidLinkSlaOperate, fkEponOnuProfileDBAMultiLLidLinkSlaPollingLevel, fkEponOnuProfileDBAMultiLLidLinkSlaTDMRate, fkEponOnuProfileDBAMultiLLidLinkSlaTDMGrantLength, fkEponOnuProfileDBAMultiLLidLinkOAMMaxOAMRate, 
				fkEponOnuProfileDBAMultiLLidLinkOAMMinOAMRate, fkEponOnuProfileDBAMultiLLidQueueIndex, fkEponOnuProfileDBAMultiLLidQueueSlaDownMinShaBandwidth, fkEponOnuProfileDBAMultiLLidQueueSlaDownMinShaBurstSize, fkEponOnuProfileDBAMultiLLidQueueSlaDownMinShaSchedulerLevel, 
				fkEponOnuProfileDBAMultiLLidQueueSlaDownMinShaWeight, fkEponOnuProfileDBAMutiLLidQueueSlaDownMaxShaBandwidth, fkEponOnuProfileDBAMultiLLidQueueSlaDownMaxShaBurstSize, fkEponOnuProfileDBAMultiLLidQueueSlaDownMaxShaSchedulerLevel, fkEponOnuProfileDBAMultiLLidQueueSlaDownMaxShaWeight, 
				fkEponOnuProfileDBAMultiLLidQueueSlaUpMinShaBandwidth, fkEponOnuProfileDBAMultiLLidQueueSlaUpMinShaBurstSize, fkEponOnuProfileDBAMultiLLidQueueSlaUpMinShaSchedulerLevel, fkEponOnuProfileDBAMultiLLidQueueSlaUpMinShaWeight, fkEponOnuProfileDBAMultiLLidQueueSlaUpMaxShaBandwidth, 
				fkEponOnuProfileDBAMultiLLidQueueSlaUpMaxShaBurstSize, fkEponOnuProfileDBAMultiLLidQueueSlaUpMaxShaSchedulerLevel, fkEponOnuProfileDBAMultiLLidQueueSlaUpMaxShaWeight, fkEponOnuProfileDBAMultiLLidControlRequest, fkEponOnuProfileDBAMultiLLidControlStatus, 
				fkEponOnuProfileDBAMultiLLidControlTimer, fkEponOnuProfileDBAMultiLLidControlTimeStamp, fkEponOnuProfileDBAMultiLLidControlReqResult, fkEponOnuProfileDBAMultiLLidControlProfileName, fkEponOnuProfileDBAMultiLLidControlLinkSlaMinShaBandwidth, 
				fkEponOnuProfileDBAMultiLLidControlLinkSlaMinShaBurstSize, fkEponOnuProfileDBAMultiLLidControlLinkSlaMinShaSchedulerLevel, fkEponOnuProfileDBAMultiLLidControlLinkSlaMinShaWeight, fkEponOnuProfileDBAMultiLLidControlLinkSlaMaxShaBandwidth, fkEponOnuProfileDBAMultiLLidControlLinkSlaMaxShaBurstSize, 
				fkEponOnuProfileDBAMultiLLidControlLinkSlaMaxShaSchedulerLevel, fkEponOnuProfileDBAMultiLLidControlLinkSlaMaxShaWeight, fkEponOnuProfileDBAMultiLLidControlLinkSlaOperate, fkEponOnuProfileDBAMultiLLIdControlLinkSlaPollingLevel, fkEponOnuProfileDBAlMultiLLidControLinkSlaTDMRate, 
				fkEponOnuProfileDBAMultiLLidControlLinkSlaTDMGrantLength, fkEponOnuProfileDBAMultiLLidControlQueueIndex, fkEponOnuProfileDBAMultiLLidControlQueueSlaMinShaBandwidth, fkEponOnuProfileDBAMultiLLidControlQueueSlaMinShaBurstSize, fkEponOnuProfileDBAMultiLLidControlQueueSlaMinShaSchedulerLevel, 
				fkEponOnuProfileDBAMultiLLidControlQueueSlaMinShaWeight, fkEponOnuProfileDBAMultiLLidControlQueueSlaMaxShaBandwidth, fkEponOnuProfileDBAMultiLLidControlQueueSlaMaxShaBurstSize, fkEponOnuProfileDBAMultiLLidControlQueueSlaMaxShaSchedulerLevel, fkEponOnuProfileDBAMultiLLidControlQueueSlaMaxShaWeight, 
				fkEponOnuProfileDBAMultiLLIdControlQueueSlaOperate, fkEponOnuProfileDBAMultiLLidControlLinkOAMMaxRate, fkEponOnuProfileDBAMultiLLidControlLinkOAMMinRate, fkEponDomainVlanID, fkEponDomainUnTaggedPorts, 
				fkEponDomainMultiUnTaggedPorts, fkEponDomainControlRequest, fkEponDomainControlStatus, fkEponDomainControlTimer, fkEponDomainControlTimeStamp, 
				fkEponDomainControlReqResult, fkEponDomainControlOltIndex, fkEponDomainControlOnuIndex, fkEponDomainControlVlanID, fkEponDomainControlUnTaggedPorts, 
				fkEponOltRedundancyMaste, fkEponOltRedundancyGroupID, fkEponOltRedundancyTrunkID, fkEponOltRedundancyMasteStatus, fkEponOltRedundancySlave, 
				fkEponOltRedundancySlaveStatus, fkEponOltRedundancyWtrValue, fkEponOltRedundancyRemainTime, fkEponOltRedundancyLastReason, fkEponOltRedundancyHoldOffTime, 
				fkEponOltRedundancyControlRequest, fkEponOltRedundancyControlStatus, fkEponOltRedundancyControlTimer, fkEponOltRedundancyControlTimeStamp, fkEponOltRedundancyControlReqResult, 
				fkEponOltRedundancyControlGroupID, fkEponOltRedundancyControlTrunkID, fkEponOltRedundancyControlMaster, fkEponOltRedundancyControlSlave, fkEponOltRedundancyControlWtrValue, 
				fkEponOltRedundancyControlHoldOffTime, fkEponProfileExtendMtu, fkEponOnuTxPowerOffTimer }
			STATUS current
			DESCRIPTION 
				"Description."
			::= { fkEpon 17 }

		
		-- 1.3.6.1.4.1.10428 9 1.101.20.18
		fkEponNotificationGroup NOTIFICATION-GROUP
			NOTIFICATIONS { fkEponOltRegModeChanged, fkEponOltStatusChanged, fkEponOnuRegModeChanged, fkEponOnuStatusChanged, fkEponOnuRegistered, 
				fkEponOnuUpgraded, fkEponProfileCreated, fkEponProfileDestroyed, fkEponstatsOltCleared, fkEponStatsOltChannelCleared, 
				fkEponAlarmProfileChanged, fkEponOnuDeregistered, fkEponOnuProfileChanged, fkEponOnuLoopbackProvisioned, fkEponOltProfileChanged, 
				fkEponStatsAllCleared, fkEponProfileVlanCreated, fkEponProfileVlanDestroyed, fkEponProfileVlanProfileChanged, fkEponProfilePortAdminStatusChanged, 
				fkEponProfilePortNegoChanged, fkEponProfilePortSpeedChanged, fkEponProfilePortMaxHostChanged, fkEponProfilePortPvidChanged, fkEponProfilePortRateLimitChanged, 
				fkEponOnuPortReset, fkEponOnuClassificationCreated, fkEponOnuClassificationDestroyed, fkEponProfileClassificationCreated, fkEponProfileClassificationDestroyed, 
				fkEponOltSCChanged, fkEponOltUpgraded, fkEponOltReset, fkEponOnuTxPowerOffChanged, fkEponOnuFdbMacCleared, 
				fkEponProfileExtendMtuChanged, fkEponProfileIgmpChanged, fkEponProfileSTPChanged, fkEponProfileQueueModifyQueueLimit, fkEponProfilePortFlowControlChanged, 
				fkEponVlanOltVlanPrefixChanged, fkEponVlanOltVlanProfileChanged, fkEponProfileDefaultProfileCreated, fkEponProfileUNIQueueModifyQueuePolicy, fkEponPTimeStatsCleared, 
				fkEponPTimeStatsServiceActivityChanged, fkEponOnuSubscriberHistoryOltCleared, fkEponOnuSubscriberHistroyOnuCleared, fkEponProfileQueueModifyQueuePolicy, fkEponOltAttributesChanged, 
				fkEponOnuAttibutesChanged, fkEponProfileModified, fkEponProfilePortDuplexChanged, fkEponProfileLoopDetectChanged, fkEponBaseDefaultBandwidthChanged, 
				fkEponBaseDefaultMaxHost, fkEponVlanOnuVlanProfileChanged, fkEponFirmwareUpgradeProfileChanged, fkEponFirmwareDeleted, fkEponOnuSipGlobalConfigDestroyed, 
				fkEponProfileSipConfigChanged, fkEponProfileModemConfigChanged, fkEponOnuSipUserConfigDestroyed, fkEponBaseOnuAgingTimeChanged, fkEponBaseAlarmStatusChanged, 
				fkEponBaseAlarmModeChanged, fkEponOltRssiStatusChanged, fkEponOltP2PAccessControlChanged, fkEponOnuFristRegisteredOnAutoToManual, fkEponOnuProfileChangedByMac, 
				fkEponOnuDeregisteredByMac, fkEponOnuLgpauthStatusChanged, fkEponOnuSipGlobalConfigIpChanged, fkEponOnuSipGlobalConfigDhcpChanged, fkEponOnuSipGlobalConfigPPPoEChanged, 
				fkEponOnuPingTest, fkEponOnuLoopDectectUnblock, setEponOnuOltRssiOnuSingle, fkEponOnuDBAMultiLLidLink, fkEponOnuDMIMonitorThresholdChanged, 
				fkEponProfileDHCPChanged, fkEponProfileModemMacLearnChanged, fkEponProfileIgmpSnoopingChanged, fkEponProfileOnuRuleChanged, fkEponProfilePortIsolationChanged, 
				fkEponAlarmChanged, fkEponRuleClauseQueueChanged, fkEponRuleClauseLayer2Changed, fkEponRuleClauseVlanChanged, fkEponRuleClauseLayer3Changed, 
				fkEponRuleClauseTcpUdpChanged, fkEponRuleClauseProtocolChanged, fkEponRuleClauseLinkIndexChanged, fkEponRuleClauseDel, fkEponRuleActionVlanChanged, 
				fkEponRuleActionDiscardChanged, fkEponRuleActionCaptureHostChanged, fkEponRuleActionCaptureHostFlexibleChanged, fkEponRuleActionQueueChanged, fkEponRuleActionUnicastLinkChanged, 
				fkEponRuleActionMulticastLinkChanged, fkEponRuleActionNoOperation, fkEponRuleActionCosChanged, fkEponRuleActionTosChanged, fkEponRuleActionOutputChanged, 
				fkEponRuleActionQueuePendingChanged, fkEponRuleActionFkChanged, fkEponRuleActionNoRuleAction, fkEponRuleOltRuleCreate, fkEponRuleModifyPriorityChange, 
				fkEponRuleModifyTrafficDirChange, fkEponRuleModifyClauseAdd, fkEponRuleModifyActionAdd, fkEponRuleModifyClauseDel, fkEponRuleModifyActionDel, 
				fkEponRuleOltRuleDelete, fkEponRuleOltRuleAddApply, fkEponRuleOltRuleDelApply, fkEponOnuRuleChanged, fkEponOLtDBAShaperDropDownWeightsChanged, 
				fkEponOLtDBADropDownWeightsChanged, fkEponOltDBALinkChanged, fkEponOLtDBADGlobalOltLinkChanged, fkEponOLtDBADOverGrantMonConfChanged, fkEponOltDBAPollingRateChanged, 
				fkEponOltDBAMultiQueueSlaChanged, fkEponOnuProfileDBALinkSlaChanged, fkEponOnuProfileDBAQueueSlaChanged, fkEponOnuProfileDBALinkOAMRateChanged, fkEponOnuProfileDBAMultiLLidLinkSlaChanged, 
				fkEponOnuProfileDBAMultiLLidQueueSlaChanged, fkEponOnuProfileDBAMultiLLidLinkOAMRateChanged, fkEponDomainVlanCreate, fkEponDomainDestroyVlan, fkEponDomainVlanAdd, 
				fkEponDomainDefaultVlanAdd, fkEponDomainVlanDel, fkEponDomainDefaultVlanDel, fkEponDomainVlanMultiAdd, fkEponDomainDefaultVlanMultiAdd, 
				fkEponDomainVlanMultiDel, fkEponDomainDefaultVlanMultiDel, fkEponOltRedundancyChanged, fkEponOltRedundancySwitchoverForceGroup, fkEponOltRedundancyHoldOffTimeChanged, 
				fkEponProfileSubscriberChanged, fkEponBaseOnuAutoUpgradeChanged, fkEponOnuSipUserConfigChanged }
			STATUS current
			DESCRIPTION 
				"Description."
			::= { fkEpon 18 }

		
	
	END

--
-- fk-epon-mib.mib
--
