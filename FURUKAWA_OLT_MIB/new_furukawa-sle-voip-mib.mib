--
-- fk-voip-mib.mib
-- MIB generated by MG-SOFT Visual MIB Builder Version 6.0  Build 88
-- Tuesday, April 03, 2012 at 09:18:50
--

--  fk-voip-mib.mib
-- MIB generated by MG-SOFT Visual MIB Builder Version 6.0  Build 88
-- Friday, November 25, 2011 at 17:07:08
-- 
--  fk-voip-mib.mib
-- MIB generated by MG-SOFT Visual MIB Builder Version 6.0  Build 88
-- Thursday, November 24, 2011 at 23:01:34
-- 
--  fk-voip-mib.mib
-- MIB generated by MG-SOFT Visual MIB Builder Version 6.0  Build 88
-- Thursday, November 24, 2011 at 16:10:05
-- 
--  fk-voip-mib.mib
-- MIB generated by MG-SOFT Visual MIB Builder Version 6.0  Build 88
-- Wednesday, November 23, 2011 at 20:42:05
-- 
--  fk-voip2-mib.mib
-- MIB generated by MG-SOFT Visual MIB Builder Version 6.0  Build 88
-- Wednesday, November 23, 2011 at 20:39:44
-- 
--  FK-DEBUG-MIB.my
-- MIB generated by MG-SOFT Visual MIB Builder Version 3.0 Build 285
-- Monday, January 22, 2007 at 17:04:05
-- 

        FK-VOIP-MIB DEFINITIONS ::= BEGIN
 
                IMPORTS
                        fkMgmt                  
                                FROM FKOLTG1040-SMI                     
                        FkControlStatusType, FkControlRequestResultType                 
                                FROM FK-TC-MIB                  
                        OBJECT-GROUP, NOTIFICATION-GROUP                        
                                FROM SNMPv2-CONF                        
                        TimeTicks, IpAddress, Integer32, Unsigned32, Gauge32, 
                        OBJECT-TYPE, MODULE-IDENTITY, NOTIFICATION-TYPE                 
                                FROM SNMPv2-SMI;
        
        
                -- 1.3.6.1.4.1.10428 9 1.101.25
                fkVoip MODULE-IDENTITY 
                        LAST-UPDATED "201112141814Z"            -- December 14, 2011 at 18:14 GMT
                        ORGANIZATION 
                                "Furukawa Industrial S.A."
                        CONTACT-INFO 
                                "Furukawa Industrial S.A. Produtos Eletricos
        Rua Hasdrubal Bellegard, 820 - CIC
        CEP 81460-120 - Curitiba - Parana - Brasil
        CSC 0800-41-2100
        E-mail: fisa@furukawa.com.br"
                        DESCRIPTION 
                                "The MIB module for Furukawa GPON OLT FK-OLT-G1040."
                        ::= { fkMgmt 25 }

                
        
--
-- Type definitions
--
        
                OwnerString ::= OCTET STRING (SIZE (0..255))

                EnableDisableState ::= INTEGER
                        {
                        disable(0),
                        enable(1)
                        }

        
        
--
-- Node definitions
--
        
                -- 1.3.6.1.4.1.10428 9 1.101.25.1
                fkVoipBase OBJECT IDENTIFIER ::= { fkVoip 1 }

                
                -- 1.3.6.1.4.1.10428 9 1.101.25.1.1
                fkVoipBaseInfo OBJECT IDENTIFIER ::= { fkVoipBase 1 }

                
                -- 1.3.6.1.4.1.10428 9 1.101.25.1.1.1
                fkVoipInterface OBJECT-TYPE
                        SYNTAX OCTET STRING
                        MAX-ACCESS read-only
                        STATUS current
                        DESCRIPTION
                                "Display host interface name."
                        ::= { fkVoipBaseInfo 1 }

                
                -- 1.3.6.1.4.1.10428 9 1.101.25.1.1.2
                fkVoipProtocol OBJECT-TYPE
                        SYNTAX INTEGER
                                {
                                none(0),
                                sip(1),
                                mgcp(3)
                                }
                        MAX-ACCESS read-only
                        STATUS current
                        DESCRIPTION
                                "
                                Display protocol (none|sip|mgcp) is set."
                        ::= { fkVoipBaseInfo 2 }

                
                -- 1.3.6.1.4.1.10428 9 1.101.25.1.1.3
                fkVoipRtcp OBJECT-TYPE
                        SYNTAX INTEGER
                                {
                                voipRtcpDisable(0),
                                voipRtcpEnable(1)
                                }
                        MAX-ACCESS read-only
                        STATUS current
                        DESCRIPTION
                                "Description."
                        ::= { fkVoipBaseInfo 3 }

                
                -- 1.3.6.1.4.1.10428 9 1.101.25.1.1.4
                fkVoipFaxmode OBJECT-TYPE
                        SYNTAX INTEGER
                                {
                                voipFaxmodeT30(0),
                                voipFaxmodeT38(1)
                                }
                        MAX-ACCESS read-only
                        STATUS current
                        DESCRIPTION
                                "Description."
                        ::= { fkVoipBaseInfo 4 }

                
                -- 1.3.6.1.4.1.10428 9 1.101.25.1.2
                fkVoipBaseControl OBJECT IDENTIFIER ::= { fkVoipBase 2 }

                
                -- 1.3.6.1.4.1.10428 9 1.101.25.1.2.1
                fkVoipBaseControlRequest OBJECT-TYPE
                        SYNTAX INTEGER
                                {
                                setVoipInterface(1),
                                setVoipProtocol(2),
                                voipRestartStackOnly(3),
                                voipRestartAll(4),
                                setVoipRtcp(5),
                                setVoipFaxmode(6)
                                }
                        MAX-ACCESS read-write
                        STATUS current
                        DESCRIPTION
                                "Description."
                        ::= { fkVoipBaseControl 1 }

                
                -- 1.3.6.1.4.1.10428 9 1.101.25.1.2.2
                fkVoipBaseControlStatus OBJECT-TYPE
                        SYNTAX FkControlStatusType
                        MAX-ACCESS read-only
                        STATUS current
                        DESCRIPTION
                                "The status of a user command. 
                                "
                        ::= { fkVoipBaseControl 2 }

                
                -- 1.3.6.1.4.1.10428 9 1.101.25.1.2.3
                fkVoipBaseControlTimer OBJECT-TYPE
                        SYNTAX Gauge32
                        MAX-ACCESS read-write
                        STATUS current
                        DESCRIPTION
                                "The maximum wait time for the manager for a long running user command. 
                                "
                        ::= { fkVoipBaseControl 3 }

                
                -- 1.3.6.1.4.1.10428 9 1.101.25.1.2.4
                fkVoipBaseControlTimeStamp OBJECT-TYPE
                        SYNTAX TimeTicks
                        MAX-ACCESS read-only
                        STATUS current
                        DESCRIPTION
                                "The time stamp of the last command (end of command)."
                        ::= { fkVoipBaseControl 4 }

                
                -- 1.3.6.1.4.1.10428 9 1.101.25.1.2.5
                fkVoipBaseControlReqResult OBJECT-TYPE
                        SYNTAX FkControlRequestResultType
                        MAX-ACCESS read-only
                        STATUS current
                        DESCRIPTION
                                "Description"
                        ::= { fkVoipBaseControl 5 }

                
                -- 1.3.6.1.4.1.10428 9 1.101.25.1.2.6
                fkVoipBaseControlInterface OBJECT-TYPE
                        SYNTAX OCTET STRING
                        MAX-ACCESS read-write
                        STATUS current
                        DESCRIPTION
                                "
                                Host interface name. Explain each group,up to 32 characters string include Null character."
                        ::= { fkVoipBaseControl 6 }

                
                -- 1.3.6.1.4.1.10428 9 1.101.25.1.2.7
                fkVoipBaseControlProtocol OBJECT-TYPE
                        SYNTAX INTEGER
                                {
                                none(0),
                                sip(1),
                                mgcp(3)
                                }
                        MAX-ACCESS read-write
                        STATUS current
                        DESCRIPTION
                                "
                                Protocol(none|sip|mgcp).(Optional) to explain each group,up to 32 characters string include Null character."
                        ::= { fkVoipBaseControl 7 }

                
                -- 1.3.6.1.4.1.10428 9 1.101.25.1.2.8
                fkVoipBaseControlRtcp OBJECT-TYPE
                        SYNTAX INTEGER
                                {
                                voipRtcpDisable(0),
                                voipRtcpEnable(1)
                                }
                        MAX-ACCESS read-write
                        STATUS current
                        DESCRIPTION
                                "Description."
                        ::= { fkVoipBaseControl 8 }

                
                -- 1.3.6.1.4.1.10428 9 1.101.25.1.2.9
                fkVoipBaseControlFaxmode OBJECT-TYPE
                        SYNTAX INTEGER
                                {
                                voipFaxmodeT30(0),
                                voipFaxmodeT38(1)
                                }
                        MAX-ACCESS read-write
                        STATUS current
                        DESCRIPTION
                                "Description."
                        ::= { fkVoipBaseControl 9 }

                
                -- 1.3.6.1.4.1.10428 9 1.101.25.1.3
                fkVoipBaseNotification OBJECT IDENTIFIER ::= { fkVoipBase 3 }

                
                -- 1.3.6.1.4.1.10428 9 1.101.25.1.3.1
                fkVoipBaseInterfaceChanged NOTIFICATION-TYPE
                        OBJECTS { fkVoipBaseControlRequest, fkVoipBaseControlTimeStamp, fkVoipBaseControlReqResult, fkVoipBaseControlInterface }
                        STATUS current
                        DESCRIPTION 
                                "DESCRIPTION:"
                        ::= { fkVoipBaseNotification 1 }

                
                -- 1.3.6.1.4.1.10428 9 1.101.25.1.3.2
                fkVoipBaseProtocolChanged NOTIFICATION-TYPE
                        OBJECTS { fkVoipBaseControlRequest, fkVoipBaseControlTimeStamp, fkVoipBaseControlReqResult, fkVoipBaseControlProtocol }
                        STATUS current
                        DESCRIPTION 
                                "DESCRIPTION:"
                        ::= { fkVoipBaseNotification 2 }

                
                -- 1.3.6.1.4.1.10428 9 1.101.25.1.3.3
                fkVoipBaseRestartStackOnly NOTIFICATION-TYPE
                        OBJECTS { fkVoipBaseControlRequest, fkVoipBaseControlTimeStamp, fkVoipBaseControlReqResult }
                        STATUS current
                        DESCRIPTION 
                                "voipRestartStackOnly"
                        ::= { fkVoipBaseNotification 3 }

                
                -- 1.3.6.1.4.1.10428 9 1.101.25.1.3.4
                fkVoipBaseRestartAll NOTIFICATION-TYPE
                        OBJECTS { fkVoipBaseControlRequest, fkVoipBaseControlTimeStamp, fkVoipBaseControlReqResult }
                        STATUS current
                        DESCRIPTION 
                                "voipRestartAll"
                        ::= { fkVoipBaseNotification 4 }

                
                -- 1.3.6.1.4.1.10428 9 1.101.25.1.3.5
                fkVoipBaseRtcpChanged NOTIFICATION-TYPE
                        OBJECTS { fkVoipBaseControlRequest, fkVoipBaseControlTimeStamp, fkVoipBaseControlReqResult, fkVoipBaseControlRtcp }
                        STATUS current
                        DESCRIPTION 
                                "Description."
                        ::= { fkVoipBaseNotification 5 }

                
                -- 1.3.6.1.4.1.10428 9 1.101.25.1.3.6
                fkVoipBaseFaxmodeChanged NOTIFICATION-TYPE
                        OBJECTS { fkVoipBaseControlRequest, fkVoipBaseControlTimeStamp, fkVoipBaseControlReqResult, fkVoipBaseControlFaxmode }
                        STATUS current
                        DESCRIPTION 
                                "Description."
                        ::= { fkVoipBaseNotification 6 }

                
                -- 1.3.6.1.4.1.10428 9 1.101.25.2
                fkVoipVoice OBJECT IDENTIFIER ::= { fkVoip 2 }

                
                -- 1.3.6.1.4.1.10428 9 1.101.25.2.1
                fkVoipVoiceTable OBJECT-TYPE
                        SYNTAX SEQUENCE OF FkVoipVoiceEntry
                        MAX-ACCESS not-accessible
                        STATUS current
                        DESCRIPTION
                                "Description."
                        ::= { fkVoipVoice 1 }

                
                -- 1.3.6.1.4.1.10428 9 1.101.25.2.1.1
                fkVoipVoiceEntry OBJECT-TYPE
                        SYNTAX FkVoipVoiceEntry
                        MAX-ACCESS not-accessible
                        STATUS current
                        DESCRIPTION
                                "Description."
                        INDEX { fkVoipVoiceIndex }
                        ::= { fkVoipVoiceTable 1 }

                
                FkVoipVoiceEntry ::=
                        SEQUENCE { 
                                fkVoipVoiceIndex
                                        Integer32,
                                fkVoipVoiceEncoding
                                        INTEGER,
                                fkVoipVoiceUserEncoding
                                        INTEGER,
                                fkVoipVoiceComfortNoise
                                        INTEGER,
                                fkVoipVoiceEchoCancel
                                        INTEGER,
                                fkVoipVoicePacketLoss
                                        INTEGER,
                                fkVoipVoiceVad
                                        INTEGER,
                                fkVoipVoiceDSCP
                                        Unsigned32,
                                fkVoipVoiceJitter
                                        Unsigned32
                         }

                -- 1.3.6.1.4.1.10428 9 1.101.25.2.1.1.1
                fkVoipVoiceIndex OBJECT-TYPE
                        SYNTAX Integer32 (1..8)
                        MAX-ACCESS read-only
                        STATUS current
                        DESCRIPTION
                                "DESCRIPTION:
                                The index of the voice. <1-8>"
                        ::= { fkVoipVoiceEntry 1 }

                
                -- 1.3.6.1.4.1.10428 9 1.101.25.2.1.1.2
                fkVoipVoiceEncoding OBJECT-TYPE
                        SYNTAX INTEGER
                                {
                                a(0),
                                m(1)
                                }
                        MAX-ACCESS read-only
                        STATUS current
                        DESCRIPTION
                                "Line coding (0:a-law,1:mu-law)."
                        ::= { fkVoipVoiceEntry 2 }

                
                -- 1.3.6.1.4.1.10428 9 1.101.25.2.1.1.3
                fkVoipVoiceUserEncoding OBJECT-TYPE
                        SYNTAX INTEGER
                                {
                                a(0),
                                m(1)
                                }
                        MAX-ACCESS read-only
                        STATUS current
                        DESCRIPTION
                                "a-law telephony companding algorithm,mu-law telephony companding algorithm."
                        ::= { fkVoipVoiceEntry 3 }

                
                -- 1.3.6.1.4.1.10428 9 1.101.25.2.1.1.4
                fkVoipVoiceComfortNoise OBJECT-TYPE
                        SYNTAX INTEGER
                                {
                                on(0),
                                off(1)
                                }
                        MAX-ACCESS read-only
                        STATUS current
                        DESCRIPTION
                                "Comfort Noise (0: on;1: off)"
                        ::= { fkVoipVoiceEntry 4 }

                
                -- 1.3.6.1.4.1.10428 9 1.101.25.2.1.1.5
                fkVoipVoiceEchoCancel OBJECT-TYPE
                        SYNTAX INTEGER
                                {
                                off(0),
                                on(1)
                                }
                        MAX-ACCESS read-only
                        STATUS current
                        DESCRIPTION
                                " Echo cancellation,(on|off)."
                        ::= { fkVoipVoiceEntry 5 }

                
                -- 1.3.6.1.4.1.10428 9 1.101.25.2.1.1.6
                fkVoipVoicePacketLoss OBJECT-TYPE
                        SYNTAX INTEGER
                                {
                                off(0),
                                on(1)
                                }
                        MAX-ACCESS read-only
                        STATUS current
                        DESCRIPTION
                                "Packet Loss Concealment,(on|off). 
                                Index: Channel Index,Range is from 0 to 7.
                                Packetloss: Packet Loss Concealment, (1:on,0:off).
                                "
                        ::= { fkVoipVoiceEntry 6 }

                
                -- 1.3.6.1.4.1.10428 9 1.101.25.2.1.1.7
                fkVoipVoiceVad OBJECT-TYPE
                        SYNTAX INTEGER
                                {
                                off(0),
                                on(1)
                                }
                        MAX-ACCESS read-only
                        STATUS current
                        DESCRIPTION
                                " Voice Activity Detection (on(0)|off(1))."
                        ::= { fkVoipVoiceEntry 7 }

                
                -- 1.3.6.1.4.1.10428 9 1.101.25.2.1.1.8
                fkVoipVoiceDSCP OBJECT-TYPE
                        SYNTAX Unsigned32 (0..63)
                        MAX-ACCESS read-only
                        STATUS current
                        DESCRIPTION
                                " DSCP number, Range is from 0 to 63."
                        ::= { fkVoipVoiceEntry 8 }

                
                -- 1.3.6.1.4.1.10428 9 1.101.25.2.1.1.9
                fkVoipVoiceJitter OBJECT-TYPE
                        SYNTAX Unsigned32 (0..500)
                        MAX-ACCESS read-only
                        STATUS current
                        DESCRIPTION
                                "Jitter Buffer parameter (0-500ms).Default value is 500ms."
                        ::= { fkVoipVoiceEntry 9 }

                
                -- 1.3.6.1.4.1.10428 9 1.101.25.2.2
                fkVoipVoiceControl OBJECT IDENTIFIER ::= { fkVoipVoice 2 }

                
                -- 1.3.6.1.4.1.10428 9 1.101.25.2.2.1
                fkVoipVoiceControlRequest OBJECT-TYPE
                        SYNTAX INTEGER
                                {
                                enableVoiceVoip(1),
                                disableVoiceVoip(2)
                                }
                        MAX-ACCESS read-write
                        STATUS current
                        DESCRIPTION
                                "The request of a user command."
                        ::= { fkVoipVoiceControl 1 }

                
                -- 1.3.6.1.4.1.10428 9 1.101.25.2.2.2
                fkVoipVoiceControlStatus OBJECT-TYPE
                        SYNTAX FkControlStatusType
                        MAX-ACCESS read-only
                        STATUS current
                        DESCRIPTION
                                "The status of user command."
                        ::= { fkVoipVoiceControl 2 }

                
                -- 1.3.6.1.4.1.10428 9 1.101.25.2.2.3
                fkVoipVoiceControlTimer OBJECT-TYPE
                        SYNTAX Gauge32
                        MAX-ACCESS read-write
                        STATUS current
                        DESCRIPTION
                                "The maximum time for the manager for a long running user command.
                                Apply your setting."
                        ::= { fkVoipVoiceControl 3 }

                
                -- 1.3.6.1.4.1.10428 9 1.101.25.2.2.4
                fkVoipVoiceControlTimeStamp OBJECT-TYPE
                        SYNTAX TimeTicks
                        MAX-ACCESS read-only
                        STATUS current
                        DESCRIPTION
                                "The time stamp of the last command(end of command)."
                        ::= { fkVoipVoiceControl 4 }

                
                -- 1.3.6.1.4.1.10428 9 1.101.25.2.2.5
                fkVoipVoiceControlReqResult OBJECT-TYPE
                        SYNTAX FkControlRequestResultType
                        MAX-ACCESS read-only
                        STATUS current
                        DESCRIPTION
                                "The result of the last user command"
                        ::= { fkVoipVoiceControl 5 }

                
                -- 1.3.6.1.4.1.10428 9 1.101.25.2.2.6
                fkVoipVoiceControlIndex OBJECT-TYPE
                        SYNTAX Integer32 (1..8)
                        MAX-ACCESS read-write
                        STATUS current
                        DESCRIPTION
                                "The index of the voice. <1-8>"
                        ::= { fkVoipVoiceControl 6 }

                
                -- 1.3.6.1.4.1.10428 9 1.101.25.2.2.7
                fkVoipVoiceControlEncoding OBJECT-TYPE
                        SYNTAX INTEGER
                                {
                                alaw(0),
                                mulaw(1)
                                }
                        MAX-ACCESS read-write
                        STATUS current
                        DESCRIPTION
                                "Line coding (0:a-law,1:mu-law).(Optional) to explain each group,up to 32 characters string include Null character."
                        ::= { fkVoipVoiceControl 7 }

                
                -- 1.3.6.1.4.1.10428 9 1.101.25.2.2.8
                fkVoipVoiceControlUserEncoding OBJECT-TYPE
                        SYNTAX INTEGER
                                {
                                alaw(0),
                                mulaw(1)
                                }
                        MAX-ACCESS read-write
                        STATUS current
                        DESCRIPTION
                                "Description.
                                (Optional) to explain each group,up to 32 characters string include NULL character. a-law telephony companding algorithm,mu-law telephony companding algorithm."
                        ::= { fkVoipVoiceControl 8 }

                
                -- 1.3.6.1.4.1.10428 9 1.101.25.2.2.9
                fkVoipVoiceControlComfortNoise OBJECT-TYPE
                        SYNTAX INTEGER
                                {
                                on(0),
                                off(1)
                                }
                        MAX-ACCESS read-write
                        STATUS current
                        DESCRIPTION
                                "
                                (Optional) to explain each group,up to 32 characters string include NULL character.( on:turn on this function, off:turn off this function)"
                        ::= { fkVoipVoiceControl 9 }

                
                -- 1.3.6.1.4.1.10428 9 1.101.25.2.2.10
                fkVoipVoiceControlEchoCancel OBJECT-TYPE
                        SYNTAX INTEGER
                                {
                                off(0),
                                on(1)
                                }
                        MAX-ACCESS read-write
                        STATUS current
                        DESCRIPTION
                                "
                                (Optional) to explain each group,up to 32 characters string include NULL character. Echo cancellation,(on|off)."
                        ::= { fkVoipVoiceControl 10 }

                
                -- 1.3.6.1.4.1.10428 9 1.101.25.2.2.11
                fkVoipVoiceControlPacketLoss OBJECT-TYPE
                        SYNTAX INTEGER
                                {
                                off(0),
                                on(1)
                                }
                        MAX-ACCESS read-write
                        STATUS current
                        DESCRIPTION
                                "Description.
                                (Optional) to explain each group,up to 32 characters string include NULL character. Packet Loss Concealment,(on|off). 
                                Index: Channel Index,Range is from 0 to 7.
                                Packetloss: Packet Loss Concealment, (1:on,0:off).
                                "
                        ::= { fkVoipVoiceControl 11 }

                
                -- 1.3.6.1.4.1.10428 9 1.101.25.2.2.12
                fkVoipVoiceControlVad OBJECT-TYPE
                        SYNTAX INTEGER
                                {
                                off(0),
                                on(1)
                                }
                        MAX-ACCESS read-write
                        STATUS current
                        DESCRIPTION
                                "Description.
                                (Optional) to explain each group,up to 32 characters string include NULL character. Voice Activity Detection (on(1)|off(0)).
                                "
                        ::= { fkVoipVoiceControl 12 }

                
                -- 1.3.6.1.4.1.10428 9 1.101.25.2.2.13
                fkVoipVoiceControlDSCP OBJECT-TYPE
                        SYNTAX Unsigned32 (0..63)
                        MAX-ACCESS read-write
                        STATUS current
                        DESCRIPTION
                                "Description.
                                DSCP number, Range is from 0 to 63."
                        ::= { fkVoipVoiceControl 13 }

                
                -- 1.3.6.1.4.1.10428 9 1.101.25.2.2.14
                fkVoipVoiceControlJitter OBJECT-TYPE
                        SYNTAX Unsigned32 (0..500)
                        MAX-ACCESS read-write
                        STATUS current
                        DESCRIPTION
                                "Description.
                                (Optional) to explain each group,up to 32 characters string include NULL character. Jitter Buffer parameter (0-500ms).Default value is 500ms."
                        ::= { fkVoipVoiceControl 14 }

                
                -- 1.3.6.1.4.1.10428 9 1.101.25.2.3
                fkVoiceNotification OBJECT IDENTIFIER ::= { fkVoipVoice 3 }

                
                -- 1.3.6.1.4.1.10428 9 1.101.25.2.3.1
                fkVoipVoiceEnabled NOTIFICATION-TYPE
                        OBJECTS { fkVoipVoiceControlRequest, fkVoipVoiceControlTimeStamp, fkVoipVoiceControlReqResult, fkVoipVoiceControlIndex, fkVoipVoiceControlVad, 
                                fkVoipVoiceControlDSCP, fkVoipVoiceControlJitter, fkVoipVoiceControlPacketLoss, fkVoipVoiceControlEchoCancel, fkVoipVoiceControlComfortNoise, 
                                fkVoipVoiceControlUserEncoding, fkVoipVoiceControlEncoding }
                        STATUS current
                        DESCRIPTION 
                                "DESCRIPTION:"
                        ::= { fkVoiceNotification 1 }

                
                -- 1.3.6.1.4.1.10428 9 1.101.25.2.3.2
                fkVoipVoiceDisabled NOTIFICATION-TYPE
                        OBJECTS { fkVoipVoiceControlRequest, fkVoipVoiceControlTimeStamp, fkVoipVoiceControlReqResult, fkVoipVoiceControlIndex }
                        STATUS current
                        DESCRIPTION 
                                "DESCRIPTION:"
                        ::= { fkVoiceNotification 2 }

                
                -- 1.3.6.1.4.1.10428 9 1.101.25.3
                fkVoipSipUser OBJECT IDENTIFIER ::= { fkVoip 3 }

                
                -- 1.3.6.1.4.1.10428 9 1.101.25.3.1
                fkVoipSipUserTable OBJECT-TYPE
                        SYNTAX SEQUENCE OF FkVoipSipUserEntry
                        MAX-ACCESS not-accessible
                        STATUS current
                        DESCRIPTION
                                "Description."
                        ::= { fkVoipSipUser 1 }

                
                -- 1.3.6.1.4.1.10428 9 1.101.25.3.1.1
                fkVoipSipUserEntry OBJECT-TYPE
                        SYNTAX FkVoipSipUserEntry
                        MAX-ACCESS not-accessible
                        STATUS current
                        DESCRIPTION
                                "Description."
                        INDEX { fkVoipSipUserIndex }
                        ::= { fkVoipSipUserTable 1 }

                
                FkVoipSipUserEntry ::=
                        SEQUENCE { 
                                fkVoipSipUserIndex
                                        Unsigned32,
                                fkVoipSipUserAgent
                                        INTEGER,
                                fkVoipSipUserAOR
                                        OCTET STRING,
                                fkVoipSipUserDisplayName
                                        OCTET STRING,
                                fkVoipSipUserUserName
                                        OCTET STRING,
                                fkVoipSipUserPassword
                                        OCTET STRING
                         }

                -- 1.3.6.1.4.1.10428 9 1.101.25.3.1.1.1
                fkVoipSipUserIndex OBJECT-TYPE
                        SYNTAX Unsigned32 (1..8)
                        MAX-ACCESS read-only
                        STATUS current
                        DESCRIPTION
                                "The index of Sip user.(1..8)"
                        ::= { fkVoipSipUserEntry 1 }

                
                -- 1.3.6.1.4.1.10428 9 1.101.25.3.1.1.2
                fkVoipSipUserAgent OBJECT-TYPE
                        SYNTAX INTEGER (1..8)
                        MAX-ACCESS read-only
                        STATUS current
                        DESCRIPTION
                                "Display the reference to sip which agent.Range is from 1 to 8."
                        ::= { fkVoipSipUserEntry 2 }

                
                -- 1.3.6.1.4.1.10428 9 1.101.25.3.1.1.3
                fkVoipSipUserAOR OBJECT-TYPE
                        SYNTAX OCTET STRING
                        MAX-ACCESS read-only
                        STATUS current
                        DESCRIPTION
                                "Display address of record."
                        ::= { fkVoipSipUserEntry 3 }

                
                -- 1.3.6.1.4.1.10428 9 1.101.25.3.1.1.4
                fkVoipSipUserDisplayName OBJECT-TYPE
                        SYNTAX OCTET STRING
                        MAX-ACCESS read-only
                        STATUS current
                        DESCRIPTION
                                "The username for sip account."
                        ::= { fkVoipSipUserEntry 4 }

                
                -- 1.3.6.1.4.1.10428 9 1.101.25.3.1.1.5
                fkVoipSipUserUserName OBJECT-TYPE
                        SYNTAX OCTET STRING
                        MAX-ACCESS read-only
                        STATUS current
                        DESCRIPTION
                                "Display user name for sip account."
                        ::= { fkVoipSipUserEntry 5 }

                
                -- 1.3.6.1.4.1.10428 9 1.101.25.3.1.1.6
                fkVoipSipUserPassword OBJECT-TYPE
                        SYNTAX OCTET STRING
                        MAX-ACCESS read-only
                        STATUS current
                        DESCRIPTION
                                "The password for sip account."
                        ::= { fkVoipSipUserEntry 6 }

                
                -- 1.3.6.1.4.1.10428 9 1.101.25.3.2
                fkVoipSipUserControl OBJECT IDENTIFIER ::= { fkVoipSipUser 2 }

                
                -- 1.3.6.1.4.1.10428 9 1.101.25.3.2.1
                fkVoipSipUserControlRequest OBJECT-TYPE
                        SYNTAX INTEGER
                                {
                                enableVoipSipUser(1),
                                disableVoipSipUser(2)
                                }
                        MAX-ACCESS read-write
                        STATUS current
                        DESCRIPTION
                                "The request of a user command."
                        ::= { fkVoipSipUserControl 1 }

                
                -- 1.3.6.1.4.1.10428 9 1.101.25.3.2.2
                fkVoipSipUserControlStatus OBJECT-TYPE
                        SYNTAX FkControlStatusType
                        MAX-ACCESS read-only
                        STATUS current
                        DESCRIPTION
                                "The status of user command."
                        ::= { fkVoipSipUserControl 2 }

                
                -- 1.3.6.1.4.1.10428 9 1.101.25.3.2.3
                fkVoipSipUserControlTimer OBJECT-TYPE
                        SYNTAX Gauge32
                        MAX-ACCESS read-write
                        STATUS current
                        DESCRIPTION
                                "The maximum time for the manager for a long running user command"
                        ::= { fkVoipSipUserControl 3 }

                
                -- 1.3.6.1.4.1.10428 9 1.101.25.3.2.4
                fkVoipSipUserControlTimeStamp OBJECT-TYPE
                        SYNTAX TimeTicks
                        MAX-ACCESS read-only
                        STATUS current
                        DESCRIPTION
                                "Time stamp attribute set at the end of command"
                        ::= { fkVoipSipUserControl 4 }

                
                -- 1.3.6.1.4.1.10428 9 1.101.25.3.2.5
                fkVoipSipUserControlReqResult OBJECT-TYPE
                        SYNTAX FkControlRequestResultType
                        MAX-ACCESS read-only
                        STATUS current
                        DESCRIPTION
                                "Result of last command"
                        ::= { fkVoipSipUserControl 5 }

                
                -- 1.3.6.1.4.1.10428 9 1.101.25.3.2.6
                fkVoipSipUserControlIndex OBJECT-TYPE
                        SYNTAX Unsigned32 (1..8)
                        MAX-ACCESS read-write
                        STATUS current
                        DESCRIPTION
                                "Description.
                                Setting Sip user index <1-8>"
                        ::= { fkVoipSipUserControl 6 }

                
                -- 1.3.6.1.4.1.10428 9 1.101.25.3.2.7
                fkVoipSipUserControlAgent OBJECT-TYPE
                        SYNTAX INTEGER (1..8)
                        MAX-ACCESS read-write
                        STATUS current
                        DESCRIPTION
                                "
                                Setting the reference to sip which agent.Range is from 1 to 8. (Optional) to explain each group,up to 32 characters string include NULL character.
                                "
                        ::= { fkVoipSipUserControl 7 }

                
                -- 1.3.6.1.4.1.10428 9 1.101.25.3.2.8
                fkVoipSipUserControlAOR OBJECT-TYPE
                        SYNTAX OCTET STRING
                        MAX-ACCESS read-write
                        STATUS current
                        DESCRIPTION
                                "
                                Setting address of record."
                        ::= { fkVoipSipUserControl 8 }

                
                -- 1.3.6.1.4.1.10428 9 1.101.25.3.2.9
                fkVoipSipUserControlDisplayName OBJECT-TYPE
                        SYNTAX OCTET STRING
                        MAX-ACCESS read-write
                        STATUS current
                        DESCRIPTION
                                "Setting display-name."
                        ::= { fkVoipSipUserControl 9 }

                
                -- 1.3.6.1.4.1.10428 9 1.101.25.3.2.10
                fkVoipSipUserControlUserName OBJECT-TYPE
                        SYNTAX OCTET STRING
                        MAX-ACCESS read-write
                        STATUS current
                        DESCRIPTION
                                "Setting user name for sip account."
                        ::= { fkVoipSipUserControl 10 }

                
                -- 1.3.6.1.4.1.10428 9 1.101.25.3.2.11
                fkVoipSipUserControlPassword OBJECT-TYPE
                        SYNTAX OCTET STRING
                        MAX-ACCESS read-write
                        STATUS current
                        DESCRIPTION
                                "Setting password for sip account."
                        ::= { fkVoipSipUserControl 11 }

                
                -- 1.3.6.1.4.1.10428 9 1.101.25.3.3
                fkVoipSipUserNotification OBJECT IDENTIFIER ::= { fkVoipSipUser 3 }

                
                -- 1.3.6.1.4.1.10428 9 1.101.25.3.3.1
                fkVoipSipUserEnabled NOTIFICATION-TYPE
                        OBJECTS { fkVoipSipUserControlRequest, fkVoipSipUserControlTimeStamp, fkVoipSipUserControlReqResult, fkVoipSipUserControlIndex, fkVoipSipUserControlAgent, 
                                fkVoipSipUserControlAOR, fkVoipSipUserControlDisplayName, fkVoipSipUserControlUserName, fkVoipSipUserControlPassword }
                        STATUS current
                        DESCRIPTION 
                                "Description."
                        ::= { fkVoipSipUserNotification 1 }

                
                -- 1.3.6.1.4.1.10428 9 1.101.25.3.3.2
                fkVoipSipUserDisabled NOTIFICATION-TYPE
                        OBJECTS { fkVoipSipUserControlRequest, fkVoipSipUserControlTimeStamp, fkVoipSipUserControlReqResult, fkVoipSipUserControlIndex }
                        STATUS current
                        DESCRIPTION 
                                "Description."
                        ::= { fkVoipSipUserNotification 2 }

                
                -- 1.3.6.1.4.1.10428 9 1.101.25.4
                fkVoipSipAgent OBJECT IDENTIFIER ::= { fkVoip 4 }

                
                -- 1.3.6.1.4.1.10428 9 1.101.25.4.1
                fkVoipSipAgentTable OBJECT-TYPE
                        SYNTAX SEQUENCE OF FkVoipSipAgentEntry
                        MAX-ACCESS not-accessible
                        STATUS current
                        DESCRIPTION
                                "Description."
                        ::= { fkVoipSipAgent 1 }

                
                -- 1.3.6.1.4.1.10428 9 1.101.25.4.1.1
                fkVoipSipAgentEntry OBJECT-TYPE
                        SYNTAX FkVoipSipAgentEntry
                        MAX-ACCESS not-accessible
                        STATUS current
                        DESCRIPTION
                                "Description."
                        INDEX { fkVoipSipAgentIndex }
                        ::= { fkVoipSipAgentTable 1 }

                
                FkVoipSipAgentEntry ::=
                        SEQUENCE { 
                                fkVoipSipAgentIndex
                                        Integer32,
                                fkVoipSipAgentServer
                                        OCTET STRING,
                                fkVoipSipAgentPort
                                        Integer32,
                                fkVoipSipAgentTypeOfService
                                        Integer32,
                                fkVoipSipAgentTransport
                                        INTEGER,
                                fkVoipSipAgentRegistrar
                                        OCTET STRING,
                                fkVoipSipAgentPrimary
                                        OCTET STRING,
                                fkVoipSipAgentSecondary
                                        OCTET STRING,
                                fkVoipSipAgentProfileName
                                        OCTET STRING,
                                fkVoipSipAgentExpireTimer
                                        Integer32
                         }

                -- 1.3.6.1.4.1.10428 9 1.101.25.4.1.1.1
                fkVoipSipAgentIndex OBJECT-TYPE
                        SYNTAX Integer32 (1..8)
                        MAX-ACCESS read-only
                        STATUS current
                        DESCRIPTION
                                "The index of Sip agent. Range from 1 to 8."
                        ::= { fkVoipSipAgentEntry 1 }

                
                -- 1.3.6.1.4.1.10428 9 1.101.25.4.1.1.2
                fkVoipSipAgentServer OBJECT-TYPE
                        SYNTAX OCTET STRING
                        MAX-ACCESS read-only
                        STATUS current
                        DESCRIPTION
                                "Set Server for SIP service.IP destination prefix <A.B.C.D> or Domain name."
                        DEFVAL { "" }
                        ::= { fkVoipSipAgentEntry 2 }

                
                -- 1.3.6.1.4.1.10428 9 1.101.25.4.1.1.3
                fkVoipSipAgentPort OBJECT-TYPE
                        SYNTAX Integer32 (0..65535)
                        MAX-ACCESS read-only
                        STATUS current
                        DESCRIPTION
                                "Port number (0-65535)."
                        ::= { fkVoipSipAgentEntry 3 }

                
                -- 1.3.6.1.4.1.10428 9 1.101.25.4.1.1.4
                fkVoipSipAgentTypeOfService OBJECT-TYPE
                        SYNTAX Integer32 (0..63)
                        MAX-ACCESS read-only
                        STATUS current
                        DESCRIPTION
                                "Type of service, value is <0-63>."
                        ::= { fkVoipSipAgentEntry 4 }

                
                -- 1.3.6.1.4.1.10428 9 1.101.25.4.1.1.5
                fkVoipSipAgentTransport OBJECT-TYPE
                        SYNTAX INTEGER
                                {
                                tcp(6),
                                udp(17)
                                }
                        MAX-ACCESS read-only
                        STATUS current
                        DESCRIPTION
                                "Transport protocol (TCP(6)|UDP(17))"
                        ::= { fkVoipSipAgentEntry 5 }

                
                -- 1.3.6.1.4.1.10428 9 1.101.25.4.1.1.6
                fkVoipSipAgentRegistrar OBJECT-TYPE
                        SYNTAX OCTET STRING
                        MAX-ACCESS read-only
                        STATUS current
                        DESCRIPTION
                                "Register Domain name. <A.B.C.D> or DNS."
                        ::= { fkVoipSipAgentEntry 6 }

                
                -- 1.3.6.1.4.1.10428 9 1.101.25.4.1.1.7
                fkVoipSipAgentPrimary OBJECT-TYPE
                        SYNTAX OCTET STRING
                        MAX-ACCESS read-only
                        STATUS current
                        DESCRIPTION
                                "Set IPv4 destination prefix.<A.B.C.D> or primary domain name."
                        ::= { fkVoipSipAgentEntry 7 }

                
                -- 1.3.6.1.4.1.10428 9 1.101.25.4.1.1.8
                fkVoipSipAgentSecondary OBJECT-TYPE
                        SYNTAX OCTET STRING
                        MAX-ACCESS read-only
                        STATUS current
                        DESCRIPTION
                                "Set IPv4 destination prefix.<A.B.C.D> or secondary domain name."
                        ::= { fkVoipSipAgentEntry 8 }

                
                -- 1.3.6.1.4.1.10428 9 1.101.25.4.1.1.9
                fkVoipSipAgentProfileName OBJECT-TYPE
                        SYNTAX OCTET STRING
                        MAX-ACCESS read-only
                        STATUS current
                        DESCRIPTION
                                "Profile name."
                        ::= { fkVoipSipAgentEntry 9 }

                
                -- 1.3.6.1.4.1.10428 9 1.101.25.4.1.1.10
                fkVoipSipAgentExpireTimer OBJECT-TYPE
                        SYNTAX Integer32 (300..360)
                        MAX-ACCESS read-only
                        STATUS current
                        DESCRIPTION
                                "Register expire timer. Range from 300 to 360s."
                        ::= { fkVoipSipAgentEntry 10 }

                
                -- 1.3.6.1.4.1.10428 9 1.101.25.4.2
                fkVoipSipAgentControl OBJECT IDENTIFIER ::= { fkVoipSipAgent 2 }

                
                -- 1.3.6.1.4.1.10428 9 1.101.25.4.2.1
                fkVoipSipAgentControlRequest OBJECT-TYPE
                        SYNTAX INTEGER
                                {
                                enableSipAgent(1),
                                disableSipAgent(2)
                                }
                        MAX-ACCESS read-write
                        STATUS current
                        DESCRIPTION
                                "The request of a user command"
                        ::= { fkVoipSipAgentControl 1 }

                
                -- 1.3.6.1.4.1.10428 9 1.101.25.4.2.2
                fkVoipSipAgentControlStatus OBJECT-TYPE
                        SYNTAX FkControlStatusType
                        MAX-ACCESS read-only
                        STATUS current
                        DESCRIPTION
                                "The status of user command"
                        ::= { fkVoipSipAgentControl 2 }

                
                -- 1.3.6.1.4.1.10428 9 1.101.25.4.2.3
                fkVoipSipAgentControlTimer OBJECT-TYPE
                        SYNTAX Gauge32
                        MAX-ACCESS read-write
                        STATUS current
                        DESCRIPTION
                                "The maximum time for the manager for a long running user command"
                        ::= { fkVoipSipAgentControl 3 }

                
                -- 1.3.6.1.4.1.10428 9 1.101.25.4.2.4
                fkVoipSipAgentControlTimeStamp OBJECT-TYPE
                        SYNTAX TimeTicks
                        MAX-ACCESS read-only
                        STATUS current
                        DESCRIPTION
                                "Time stamp attribute set at the end of command"
                        ::= { fkVoipSipAgentControl 4 }

                
                -- 1.3.6.1.4.1.10428 9 1.101.25.4.2.5
                fkVoipSipAgentControlReqResult OBJECT-TYPE
                        SYNTAX FkControlRequestResultType
                        MAX-ACCESS read-only
                        STATUS current
                        DESCRIPTION
                                "Result of last command"
                        ::= { fkVoipSipAgentControl 5 }

                
                -- 1.3.6.1.4.1.10428 9 1.101.25.4.2.6
                fkVoipSipAgentControlIndex OBJECT-TYPE
                        SYNTAX Integer32 (1..8)
                        MAX-ACCESS read-write
                        STATUS current
                        DESCRIPTION
                                "The index of SIP agent.Range from 1 to 8."
                        ::= { fkVoipSipAgentControl 6 }

                
                -- 1.3.6.1.4.1.10428 9 1.101.25.4.2.7
                fkVoipSipAgentControlServer OBJECT-TYPE
                        SYNTAX OCTET STRING
                        MAX-ACCESS read-write
                        STATUS current
                        DESCRIPTION
                                "Description.
                                (Optional) to explain each group,up to 32 characters string include NULL character. Set IPv4 address destination prefix <A.B.C.D> or Domain name."
                        ::= { fkVoipSipAgentControl 7 }

                
                -- 1.3.6.1.4.1.10428 9 1.101.25.4.2.8
                fkVoipSipAgentControlPort OBJECT-TYPE
                        SYNTAX Integer32
                        MAX-ACCESS read-write
                        STATUS current
                        DESCRIPTION
                                "Description.
                                (Optional) to explain each group,up to 32 characters string include NULL character.Port number (0-65535)."
                        ::= { fkVoipSipAgentControl 8 }

                
                -- 1.3.6.1.4.1.10428 9 1.101.25.4.2.9
                fkVoipSipAgentControlTypeOfService OBJECT-TYPE
                        SYNTAX Integer32 (0..63)
                        MAX-ACCESS read-write
                        STATUS current
                        DESCRIPTION
                                "Description.
                                Type of service, value is Range from 0 to 63.."
                        ::= { fkVoipSipAgentControl 9 }

                
                -- 1.3.6.1.4.1.10428 9 1.101.25.4.2.10
                fkVoipSipAgentControlTransport OBJECT-TYPE
                        SYNTAX INTEGER
                                {
                                tcp(6),
                                udp(17)
                                }
                        MAX-ACCESS read-write
                        STATUS current
                        DESCRIPTION
                                "Description.
                                Transport protocol (TCP|UDP)."
                        ::= { fkVoipSipAgentControl 10 }

                
                -- 1.3.6.1.4.1.10428 9 1.101.25.4.2.11
                fkVoipSipAgentControlRegistrar OBJECT-TYPE
                        SYNTAX OCTET STRING
                        MAX-ACCESS read-write
                        STATUS current
                        DESCRIPTION
                                "Description.
                                Register Domain name. <A.B.C.D> or DNS..(Optional) to explain each group,up to 32 characters string include NULL character.
                                 "
                        ::= { fkVoipSipAgentControl 11 }

                
                -- 1.3.6.1.4.1.10428 9 1.101.25.4.2.12
                fkVoipSipAgentControlPrimary OBJECT-TYPE
                        SYNTAX OCTET STRING
                        MAX-ACCESS read-write
                        STATUS current
                        DESCRIPTION
                                "
                                (Optional) to explain each group,up to 32 characters string include NULL character. Set IPv4 address destination prefix <A.B.C.D> or primary Domain name."
                        ::= { fkVoipSipAgentControl 12 }

                
                -- 1.3.6.1.4.1.10428 9 1.101.25.4.2.13
                fkVoipSipAgentControlSecondary OBJECT-TYPE
                        SYNTAX OCTET STRING
                        MAX-ACCESS read-write
                        STATUS current
                        DESCRIPTION
                                "Description.
                                (Optional) to explain each group,up to 32 characters string include NULL character. Set IPv4 address destination prefix <A.B.C.D> or secondary Domain name."
                        ::= { fkVoipSipAgentControl 13 }

                
                -- 1.3.6.1.4.1.10428 9 1.101.25.4.2.14
                fkVoipSipAgentControlProfileName OBJECT-TYPE
                        SYNTAX OCTET STRING
                        MAX-ACCESS read-write
                        STATUS current
                        DESCRIPTION
                                "Profile name setting"
                        ::= { fkVoipSipAgentControl 14 }

                
                -- 1.3.6.1.4.1.10428 9 1.101.25.4.2.15
                fkVoipSipAgentControlExpireTimer OBJECT-TYPE
                        SYNTAX Integer32 (300..360)
                        MAX-ACCESS read-write
                        STATUS current
                        DESCRIPTION
                                "Register expire timer setting. Range from 300 to 360ms."
                        ::= { fkVoipSipAgentControl 15 }

                
                -- 1.3.6.1.4.1.10428 9 1.101.25.4.3
                fkVoipSipAgentNotification OBJECT IDENTIFIER ::= { fkVoipSipAgent 3 }

                
                -- 1.3.6.1.4.1.10428 9 1.101.25.4.3.1
                fkVoipSipAgentEnabled NOTIFICATION-TYPE
                        OBJECTS { fkVoipSipAgentControlRequest, fkVoipSipAgentControlTimeStamp, fkVoipSipAgentControlReqResult, fkVoipSipAgentControlIndex, fkVoipSipAgentControlServer, 
                                fkVoipSipAgentControlPort, fkVoipSipAgentControlTypeOfService, fkVoipSipAgentControlTransport, fkVoipSipAgentControlRegistrar, fkVoipSipAgentControlPrimary, 
                                fkVoipSipAgentControlSecondary, fkVoipSipAgentControlProfileName, fkVoipSipAgentControlExpireTimer }
                        STATUS current
                        DESCRIPTION 
                                "DESCRIPTION:"
                        ::= { fkVoipSipAgentNotification 1 }

                
                -- 1.3.6.1.4.1.10428 9 1.101.25.4.3.2
                fkVoipSipAgentDisabled NOTIFICATION-TYPE
                        OBJECTS { fkVoipSipAgentControlRequest, fkVoipSipAgentControlTimeStamp, fkVoipSipAgentControlReqResult, fkVoipSipAgentControlIndex }
                        STATUS current
                        DESCRIPTION 
                                "DESCRIPTION:"
                        ::= { fkVoipSipAgentNotification 2 }

                
                -- 1.3.6.1.4.1.10428 9 1.101.25.5
                fkVoipMgcpEndpoint OBJECT IDENTIFIER ::= { fkVoip 5 }

                
                -- 1.3.6.1.4.1.10428 9 1.101.25.5.1
                fkVoipMgcpEndpointTable OBJECT-TYPE
                        SYNTAX SEQUENCE OF FkVoipMgcpEndpointEntry
                        MAX-ACCESS not-accessible
                        STATUS current
                        DESCRIPTION
                                "Description."
                        ::= { fkVoipMgcpEndpoint 1 }

                
                -- 1.3.6.1.4.1.10428 9 1.101.25.5.1.1
                fkVoipMgcpEndpointEntry OBJECT-TYPE
                        SYNTAX FkVoipMgcpEndpointEntry
                        MAX-ACCESS not-accessible
                        STATUS current
                        DESCRIPTION
                                "Description."
                        INDEX { fkVoipMgcpEndpointIndex }
                        ::= { fkVoipMgcpEndpointTable 1 }

                
                FkVoipMgcpEndpointEntry ::=
                        SEQUENCE { 
                                fkVoipMgcpEndpointIndex
                                        Unsigned32,
                                fkVoipMgcpEndpointAgent
                                        Integer32,
                                fkVoipMgcpEndpointName
                                        OCTET STRING
                         }

                -- 1.3.6.1.4.1.10428 9 1.101.25.5.1.1.1
                fkVoipMgcpEndpointIndex OBJECT-TYPE
                        SYNTAX Unsigned32 (1..8)
                        MAX-ACCESS read-only
                        STATUS current
                        DESCRIPTION
                                "The index of mgcp endpoint Range from 1 to 8."
                        ::= { fkVoipMgcpEndpointEntry 1 }

                
                -- 1.3.6.1.4.1.10428 9 1.101.25.5.1.1.2
                fkVoipMgcpEndpointAgent OBJECT-TYPE
                        SYNTAX Integer32 (1..8)
                        MAX-ACCESS read-only
                        STATUS current
                        DESCRIPTION
                                "Setting the reference to sip which agent,default is 1
                                Range from 1 to 8."
                        ::= { fkVoipMgcpEndpointEntry 2 }

                
                -- 1.3.6.1.4.1.10428 9 1.101.25.5.1.1.3
                fkVoipMgcpEndpointName OBJECT-TYPE
                        SYNTAX OCTET STRING
                        MAX-ACCESS read-only
                        STATUS current
                        DESCRIPTION
                                "Setting endpoint name for mgcp."
                        ::= { fkVoipMgcpEndpointEntry 3 }

                
                -- 1.3.6.1.4.1.10428 9 1.101.25.5.2
                fkVoipMgcpEndpointControl OBJECT IDENTIFIER ::= { fkVoipMgcpEndpoint 2 }

                
                -- 1.3.6.1.4.1.10428 9 1.101.25.5.2.1
                fkVoipMgcpEndpointControlRequest OBJECT-TYPE
                        SYNTAX INTEGER
                                {
                                enableMgcpEndpoint(1),
                                disableMgcpEndpoint(2)
                                }
                        MAX-ACCESS read-write
                        STATUS current
                        DESCRIPTION
                                "The cpu-pkt-filter request.
                                
                                "
                        ::= { fkVoipMgcpEndpointControl 1 }

                
                -- 1.3.6.1.4.1.10428 9 1.101.25.5.2.2
                fkVoipMgcpEndpointControlStatus OBJECT-TYPE
                        SYNTAX FkControlStatusType
                        MAX-ACCESS read-only
                        STATUS current
                        DESCRIPTION
                                "The status of user command"
                        ::= { fkVoipMgcpEndpointControl 2 }

                
                -- 1.3.6.1.4.1.10428 9 1.101.25.5.2.3
                fkVoipMgcpEndpointControlTimer OBJECT-TYPE
                        SYNTAX Gauge32
                        MAX-ACCESS read-write
                        STATUS current
                        DESCRIPTION
                                "The maximum time for the manager for a long running user command"
                        ::= { fkVoipMgcpEndpointControl 3 }

                
                -- 1.3.6.1.4.1.10428 9 1.101.25.5.2.4
                fkVoipMgcpEndpointControlTimeStamp OBJECT-TYPE
                        SYNTAX TimeTicks
                        MAX-ACCESS read-only
                        STATUS current
                        DESCRIPTION
                                "Time stamp attribute set at the end of command"
                        ::= { fkVoipMgcpEndpointControl 4 }

                
                -- 1.3.6.1.4.1.10428 9 1.101.25.5.2.5
                fkVoipMgcpEndpointControlReqResult OBJECT-TYPE
                        SYNTAX FkControlRequestResultType
                        MAX-ACCESS read-only
                        STATUS current
                        DESCRIPTION
                                "Result of last command"
                        ::= { fkVoipMgcpEndpointControl 5 }

                
                -- 1.3.6.1.4.1.10428 9 1.101.25.5.2.6
                fkVoipMgcpEndpointControlIndex OBJECT-TYPE
                        SYNTAX Unsigned32 (1..8)
                        MAX-ACCESS read-write
                        STATUS current
                        DESCRIPTION
                                "The index of mgcp endpoint
                                Range from 1 to 8."
                        ::= { fkVoipMgcpEndpointControl 6 }

                
                -- 1.3.6.1.4.1.10428 9 1.101.25.5.2.7
                fkVoipMgcpEndpointControlAgent OBJECT-TYPE
                        SYNTAX Integer32 (1..8)
                        MAX-ACCESS read-write
                        STATUS current
                        DESCRIPTION
                                "Setting the reference to sip which agent,default is 1
                                Range from 1 to 8."
                        ::= { fkVoipMgcpEndpointControl 7 }

                
                -- 1.3.6.1.4.1.10428 9 1.101.25.5.2.8
                fkVoipMgcpEndpointControlName OBJECT-TYPE
                        SYNTAX OCTET STRING
                        MAX-ACCESS read-write
                        STATUS current
                        DESCRIPTION
                                "(Optional) to explain each group,up to 32 characters string include NULL character. Setting endpoint name for mgcp."
                        ::= { fkVoipMgcpEndpointControl 8 }

                
                -- 1.3.6.1.4.1.10428 9 1.101.25.5.3
                fkVoipMgcpEndpointNotification OBJECT IDENTIFIER ::= { fkVoipMgcpEndpoint 3 }

                
                -- 1.3.6.1.4.1.10428 9 1.101.25.5.3.1
                fkVoipMgcpEndpointEnabled NOTIFICATION-TYPE
                        OBJECTS { fkVoipMgcpEndpointControlRequest, fkVoipMgcpEndpointControlTimeStamp, fkVoipMgcpEndpointControlReqResult, fkVoipMgcpEndpointControlIndex, fkVoipMgcpEndpointControlAgent, 
                                fkVoipMgcpEndpointControlName }
                        STATUS current
                        DESCRIPTION 
                                "DESCRIPTION:"
                        ::= { fkVoipMgcpEndpointNotification 1 }

                
                -- 1.3.6.1.4.1.10428 9 1.101.25.5.3.2
                fkVoipMgcpEndpointDisabled NOTIFICATION-TYPE
                        OBJECTS { fkVoipMgcpEndpointControlRequest, fkVoipMgcpEndpointControlTimeStamp, fkVoipMgcpEndpointControlReqResult, fkVoipMgcpEndpointControlIndex }
                        STATUS current
                        DESCRIPTION 
                                "DESCRIPTION:"
                        ::= { fkVoipMgcpEndpointNotification 2 }

                
                -- 1.3.6.1.4.1.10428 9 1.101.25.6
                fkVoipMgcpAgent OBJECT IDENTIFIER ::= { fkVoip 6 }

                
                -- 1.3.6.1.4.1.10428 9 1.101.25.6.1
                fkVoipMgcpAgentTable OBJECT-TYPE
                        SYNTAX SEQUENCE OF FkVoipMgcpAgentEntry
                        MAX-ACCESS not-accessible
                        STATUS current
                        DESCRIPTION
                                "Description."
                        ::= { fkVoipMgcpAgent 1 }

                
                -- 1.3.6.1.4.1.10428 9 1.101.25.6.1.1
                fkVoipMgcpAgentEntry OBJECT-TYPE
                        SYNTAX FkVoipMgcpAgentEntry
                        MAX-ACCESS not-accessible
                        STATUS current
                        DESCRIPTION
                                "Description."
                        INDEX { fkVoipMgcpAgentIndex }
                        ::= { fkVoipMgcpAgentTable 1 }

                
                FkVoipMgcpAgentEntry ::=
                        SEQUENCE { 
                                fkVoipMgcpAgentIndex
                                        Integer32,
                                fkVoipMgcpCallAgent
                                        IpAddress,
                                fkVoipMgcpCallAgentPort
                                        Integer32,
                                fkVoipMgcpAgentPort
                                        Integer32,
                                fkVoipMgcpAgentTOS
                                        Integer32,
                                fkVoipMgcpAgentVendor
                                        INTEGER,
                                fkVoipMgcpAgentDNS
                                        OCTET STRING,
                                fkVoipMgcpAgentProfileName
                                        OCTET STRING
                         }

                -- 1.3.6.1.4.1.10428 9 1.101.25.6.1.1.1
                fkVoipMgcpAgentIndex OBJECT-TYPE
                        SYNTAX Integer32 (1..8)
                        MAX-ACCESS read-only
                        STATUS current
                        DESCRIPTION
                                "DESCRIPTION:
                                Display mgcp agent index .Range from 1 to 8."
                        ::= { fkVoipMgcpAgentEntry 1 }

                
                -- 1.3.6.1.4.1.10428 9 1.101.25.6.1.1.2
                fkVoipMgcpCallAgent OBJECT-TYPE
                        SYNTAX IpAddress
                        MAX-ACCESS read-only
                        STATUS current
                        DESCRIPTION
                                "IP address of destination prefix "
                        ::= { fkVoipMgcpAgentEntry 2 }

                
                -- 1.3.6.1.4.1.10428 9 1.101.25.6.1.1.3
                fkVoipMgcpCallAgentPort OBJECT-TYPE
                        SYNTAX Integer32 (1..65535)
                        MAX-ACCESS read-only
                        STATUS current
                        DESCRIPTION
                                "Description.
                                Agent-Port number, value is from 1-65535."
                        ::= { fkVoipMgcpAgentEntry 3 }

                
                -- 1.3.6.1.4.1.10428 9 1.101.25.6.1.1.4
                fkVoipMgcpAgentPort OBJECT-TYPE
                        SYNTAX Integer32 (1..65535)
                        MAX-ACCESS read-only
                        STATUS current
                        DESCRIPTION
                                "Local-Port number, value is from 1-65535."
                        ::= { fkVoipMgcpAgentEntry 4 }

                
                -- 1.3.6.1.4.1.10428 9 1.101.25.6.1.1.5
                fkVoipMgcpAgentTOS OBJECT-TYPE
                        SYNTAX Integer32 (0..63)
                        MAX-ACCESS read-only
                        STATUS current
                        DESCRIPTION
                                "Type of service .value is from 0-63."
                        ::= { fkVoipMgcpAgentEntry 5 }

                
                -- 1.3.6.1.4.1.10428 9 1.101.25.6.1.1.6
                fkVoipMgcpAgentVendor OBJECT-TYPE
                        SYNTAX INTEGER
                                {
                                unknown(0),
                                dssw(1),
                                mssw(2),
                                g6sw(3),
                                cssw(4)
                                }
                        MAX-ACCESS read-only
                        STATUS current
                        DESCRIPTION
                                "Type of vendor (DSSW:Fkoltg1040Switch,MSSW:MetaSwitch,G6SW:G6Switch,CSSW:C15Switch)"
                        ::= { fkVoipMgcpAgentEntry 6 }

                
                -- 1.3.6.1.4.1.10428 9 1.101.25.6.1.1.7
                fkVoipMgcpAgentDNS OBJECT-TYPE
                        SYNTAX OCTET STRING
                        MAX-ACCESS read-only
                        STATUS current
                        DESCRIPTION
                                "Set Domain name to MGCP agent."
                        ::= { fkVoipMgcpAgentEntry 7 }

                
                -- 1.3.6.1.4.1.10428 9 1.101.25.6.1.1.8
                fkVoipMgcpAgentProfileName OBJECT-TYPE
                        SYNTAX OCTET STRING
                        MAX-ACCESS read-only
                        STATUS current
                        DESCRIPTION
                                "The profile name"
                        ::= { fkVoipMgcpAgentEntry 8 }

                
                -- 1.3.6.1.4.1.10428 9 1.101.25.6.2
                fkVoipMgcpAgentControl OBJECT IDENTIFIER ::= { fkVoipMgcpAgent 2 }

                
                -- 1.3.6.1.4.1.10428 9 1.101.25.6.2.1
                fkVoipMgcpAgentControlRequest OBJECT-TYPE
                        SYNTAX INTEGER
                                {
                                enableVoipMgcpAgent(1),
                                disableVoipMgcpAgent(2)
                                }
                        MAX-ACCESS read-write
                        STATUS current
                        DESCRIPTION
                                "The request of a user command"
                        ::= { fkVoipMgcpAgentControl 1 }

                
                -- 1.3.6.1.4.1.10428 9 1.101.25.6.2.2
                fkVoipMgcpAgentControlStatus OBJECT-TYPE
                        SYNTAX FkControlStatusType
                        MAX-ACCESS read-only
                        STATUS current
                        DESCRIPTION
                                "The status of user command"
                        ::= { fkVoipMgcpAgentControl 2 }

                
                -- 1.3.6.1.4.1.10428 9 1.101.25.6.2.3
                fkVoipMgcpAgentControlTimer OBJECT-TYPE
                        SYNTAX Gauge32
                        MAX-ACCESS read-write
                        STATUS current
                        DESCRIPTION
                                "The maximum time for the manager for a long running user command"
                        ::= { fkVoipMgcpAgentControl 3 }

                
                -- 1.3.6.1.4.1.10428 9 1.101.25.6.2.4
                fkVoipMgcpAgentControlTimeStamp OBJECT-TYPE
                        SYNTAX TimeTicks
                        MAX-ACCESS read-only
                        STATUS current
                        DESCRIPTION
                                "The time stamp of the last command(end of command)"
                        ::= { fkVoipMgcpAgentControl 4 }

                
                -- 1.3.6.1.4.1.10428 9 1.101.25.6.2.5
                fkVoipMgcpAgentControlReqResult OBJECT-TYPE
                        SYNTAX FkControlRequestResultType
                        MAX-ACCESS read-only
                        STATUS current
                        DESCRIPTION
                                "The result of the last user command"
                        ::= { fkVoipMgcpAgentControl 5 }

                
                -- 1.3.6.1.4.1.10428 9 1.101.25.6.2.6
                fkVoipMgcpAgentControlIndex OBJECT-TYPE
                        SYNTAX Integer32 (1..8)
                        MAX-ACCESS read-write
                        STATUS current
                        DESCRIPTION
                                "The index of mgcp agent.
                                Setting mgcp agent index .Range from 1 to 8."
                        ::= { fkVoipMgcpAgentControl 6 }

                
                -- 1.3.6.1.4.1.10428 9 1.101.25.6.2.7
                fkVoipMgcpAgentControlCallAgent OBJECT-TYPE
                        SYNTAX OCTET STRING
                        MAX-ACCESS read-write
                        STATUS current
                        DESCRIPTION
                                "
                                Setting IP address of destination prefix "
                        ::= { fkVoipMgcpAgentControl 7 }

                
                -- 1.3.6.1.4.1.10428 9 1.101.25.6.2.8
                fkVoipMgcpAgentControlCallAgentPort OBJECT-TYPE
                        SYNTAX Integer32 (1..65535)
                        MAX-ACCESS read-write
                        STATUS current
                        DESCRIPTION
                                "Description.
                                Setting Agent-Port number, value is from 1-65535."
                        ::= { fkVoipMgcpAgentControl 8 }

                
                -- 1.3.6.1.4.1.10428 9 1.101.25.6.2.9
                fkVoipMgcpAgentControlPort OBJECT-TYPE
                        SYNTAX Integer32 (1..65535)
                        MAX-ACCESS read-write
                        STATUS current
                        DESCRIPTION
                                "Description.
                                Setting local-Port number, value is from 1-65535."
                        ::= { fkVoipMgcpAgentControl 9 }

                
                -- 1.3.6.1.4.1.10428 9 1.101.25.6.2.10
                fkVoipMgcpAgentControlTOS OBJECT-TYPE
                        SYNTAX Integer32 (0..63)
                        MAX-ACCESS read-write
                        STATUS current
                        DESCRIPTION
                                "Setting Type of service .value is from 0-63."
                        ::= { fkVoipMgcpAgentControl 10 }

                
                -- 1.3.6.1.4.1.10428 9 1.101.25.6.2.11
                fkVoipMgcpAgentControlVendor OBJECT-TYPE
                        SYNTAX INTEGER
                                {
                                dssw(1),
                                mssw(2),
                                g6sw(3),
                                cssw(4)
                                }
                        MAX-ACCESS read-write
                        STATUS current
                        DESCRIPTION
                                "
                                Setting Type of vendor (DSSW:Fkoltg1040Switch,MSSW:MetaSwitch,G6SW:G6Switch,CSSW:C15Switch)"
                        ::= { fkVoipMgcpAgentControl 11 }

                
                -- 1.3.6.1.4.1.10428 9 1.101.25.6.2.12
                fkVoipMgcpAgentControlDNS OBJECT-TYPE
                        SYNTAX OCTET STRING
                        MAX-ACCESS read-write
                        STATUS current
                        DESCRIPTION
                                "Set domain name to Mgcp Agent. (Optional) to explain each group, up to 32 characters string include Null character."
                        ::= { fkVoipMgcpAgentControl 12 }

                
                -- 1.3.6.1.4.1.10428 9 1.101.25.6.2.13
                fkVoipMgcpAgentControlProfileName OBJECT-TYPE
                        SYNTAX OCTET STRING
                        MAX-ACCESS read-write
                        STATUS current
                        DESCRIPTION
                                "The profile name"
                        ::= { fkVoipMgcpAgentControl 13 }

                
                -- 1.3.6.1.4.1.10428 9 1.101.25.6.3
                fkVoipMgcpAgentNotification OBJECT IDENTIFIER ::= { fkVoipMgcpAgent 3 }

                
                -- 1.3.6.1.4.1.10428 9 1.101.25.6.3.1
                fkVoipMgcpAgentEnabled NOTIFICATION-TYPE
                        OBJECTS { fkVoipMgcpAgentControlRequest, fkVoipMgcpAgentControlTimeStamp, fkVoipMgcpAgentControlReqResult, fkVoipMgcpAgentControlIndex, fkVoipMgcpAgentControlCallAgent, 
                                fkVoipMgcpAgentControlPort, fkVoipMgcpAgentControlTOS, fkVoipMgcpAgentControlVendor, fkVoipMgcpAgentControlProfileName, fkVoipMgcpAgentControlDNS, 
                                fkVoipMgcpAgentControlCallAgentPort }
                        STATUS current
                        DESCRIPTION 
                                "DESCRIPTION:"
                        ::= { fkVoipMgcpAgentNotification 1 }

                
                -- 1.3.6.1.4.1.10428 9 1.101.25.6.3.2
                fkVoipMgcpAgentDisabled NOTIFICATION-TYPE
                        OBJECTS { fkVoipMgcpAgentControlRequest, fkVoipMgcpAgentControlTimeStamp, fkVoipMgcpAgentControlReqResult, fkVoipMgcpAgentControlIndex }
                        STATUS current
                        DESCRIPTION 
                                "DESCRIPTION:"
                        ::= { fkVoipMgcpAgentNotification 2 }

                
                -- 1.3.6.1.4.1.10428 9 1.101.25.7
                fkVoipPots OBJECT IDENTIFIER ::= { fkVoip 7 }

                
                -- 1.3.6.1.4.1.10428 9 1.101.25.7.1
                fkVoipPotsStatusTable OBJECT-TYPE
                        SYNTAX SEQUENCE OF FkVoipPotsStatusEntry
                        MAX-ACCESS not-accessible
                        STATUS current
                        DESCRIPTION
                                "Description."
                        ::= { fkVoipPots 1 }

                
                -- 1.3.6.1.4.1.10428 9 1.101.25.7.1.1
                fkVoipPotsStatusEntry OBJECT-TYPE
                        SYNTAX FkVoipPotsStatusEntry
                        MAX-ACCESS not-accessible
                        STATUS current
                        DESCRIPTION
                                "Description."
                        INDEX { fkVoipSipAgentIndex }
                        ::= { fkVoipPotsStatusTable 1 }

                
                FkVoipPotsStatusEntry ::=
                        SEQUENCE { 
                                fkVoipPotsStatusIndex
                                        Unsigned32,
                                fkVoipPotsStatus
                                        INTEGER,
                                fkVoipPotsStatusHookState
                                        INTEGER,
                                fkVoipPotsStatusRegisterState
                                        INTEGER
                         }

                -- 1.3.6.1.4.1.10428 9 1.101.25.7.1.1.1
                fkVoipPotsStatusIndex OBJECT-TYPE
                        SYNTAX Unsigned32 (1..8)
                        MAX-ACCESS read-only
                        STATUS current
                        DESCRIPTION
                                "DESCRIPTION:
                                Display status of ports <1-8>"
                        ::= { fkVoipPotsStatusEntry 1 }

                
                -- 1.3.6.1.4.1.10428 9 1.101.25.7.1.1.2
                fkVoipPotsStatus OBJECT-TYPE
                        SYNTAX INTEGER
                                {
                                idle(0),
                                twoway(1),
                                threeway(2),
                                fax(3)
                                }
                        MAX-ACCESS read-only
                        STATUS current
                        DESCRIPTION
                                "
                                DESCRIPTION:
                                Setting pots status.Value is idle(0)|twoway(1)|threeway(2)|fax(3)"
                        ::= { fkVoipPotsStatusEntry 2 }

                
-- Register Status. Value is on(0)|off(1)
                -- 1.3.6.1.4.1.10428 9 1.101.25.7.1.1.3
                fkVoipPotsStatusHookState OBJECT-TYPE
                        SYNTAX INTEGER
                                {
                                on(0),
                                off(1)
                                }
                        MAX-ACCESS read-only
                        STATUS current
                        DESCRIPTION
                                "Hook status. Value is on(0)|off(1)"
                        ::= { fkVoipPotsStatusEntry 3 }

                
-- Register Status. Value is out(0)|in(1)
                -- 1.3.6.1.4.1.10428 9 1.101.25.7.1.1.4
                fkVoipPotsStatusRegisterState OBJECT-TYPE
                        SYNTAX INTEGER
                                {
                                out(0),
                                in(1)
                                }
                        MAX-ACCESS read-only
                        STATUS current
                        DESCRIPTION
                                "Register Status. Value is out(0)|in(1)"
                        ::= { fkVoipPotsStatusEntry 4 }

                
                -- 1.3.6.1.4.1.10428 9 1.101.25.8
                fkVoipMediaProfile OBJECT IDENTIFIER ::= { fkVoip 8 }

                
                -- 1.3.6.1.4.1.10428 9 1.101.25.8.1
                fkVoipMediaProfileTable OBJECT-TYPE
                        SYNTAX SEQUENCE OF FkVoipMediaProfileEntry
                        MAX-ACCESS not-accessible
                        STATUS current
                        DESCRIPTION
                                "Description."
                        ::= { fkVoipMediaProfile 1 }

                
                -- 1.3.6.1.4.1.10428 9 1.101.25.8.1.1
                fkVoipMediaProfileEntry OBJECT-TYPE
                        SYNTAX FkVoipMediaProfileEntry
                        MAX-ACCESS not-accessible
                        STATUS current
                        DESCRIPTION
                                "Description."
                        INDEX { fkVoipMediaProfileIndex }
                        ::= { fkVoipMediaProfileTable 1 }

                
                FkVoipMediaProfileEntry ::=
                        SEQUENCE { 
                                fkVoipMediaProfileIndex
                                        Integer32,
                                fkVoipMediaProfileCodecSelection
                                        INTEGER,
                                fkVoipMediaProfilePacketPeriod
                                        INTEGER,
                                fkVoipMediaProfileSilenceSuppression
                                        INTEGER
                         }

                -- 1.3.6.1.4.1.10428 9 1.101.25.8.1.1.1
                fkVoipMediaProfileIndex OBJECT-TYPE
                        SYNTAX Integer32 (1..8)
                        MAX-ACCESS read-only
                        STATUS current
                        DESCRIPTION
                                "The index of Media Profile (1..8)"
                        ::= { fkVoipMediaProfileEntry 1 }

                
                -- 1.3.6.1.4.1.10428 9 1.101.25.8.1.1.2
                fkVoipMediaProfileCodecSelection OBJECT-TYPE
                        SYNTAX INTEGER
                                {
                                pcmu(0),
                                g723(4),
                                pcma(8),
                                g729(18)
                                }
                        MAX-ACCESS read-only
                        STATUS current
                        DESCRIPTION
                                "Voice codec setting : G711 a-law codec, G711 mu-law codec, G.723 Codec standard, G.729 Codec standard."
                        ::= { fkVoipMediaProfileEntry 2 }

                
                -- 1.3.6.1.4.1.10428 9 1.101.25.8.1.1.3
                fkVoipMediaProfilePacketPeriod OBJECT-TYPE
                        SYNTAX INTEGER (10..30)
                        MAX-ACCESS read-only
                        STATUS current
                        DESCRIPTION
                                "Packet Period setting. Range value is from 10 to 30 ms. Default value is 10ms."
                        ::= { fkVoipMediaProfileEntry 3 }

                
                -- 1.3.6.1.4.1.10428 9 1.101.25.8.1.1.4
                fkVoipMediaProfileSilenceSuppression OBJECT-TYPE
                        SYNTAX INTEGER
                                {
                                off(0),
                                on(1)
                                }
                        MAX-ACCESS read-only
                        STATUS current
                        DESCRIPTION
                                "Silence suppression setting. Off(0), on(1)"
                        ::= { fkVoipMediaProfileEntry 4 }

                
                -- 1.3.6.1.4.1.10428 9 1.101.25.8.2
                fkVoipMediaProfileControl OBJECT IDENTIFIER ::= { fkVoipMediaProfile 2 }

                
                -- 1.3.6.1.4.1.10428 9 1.101.25.8.2.1
                fkVoipMediaProfileControlRequest OBJECT-TYPE
                        SYNTAX INTEGER
                                {
                                enableVoipMediaProfile(1),
                                disableVoipMediaProfile(2)
                                }
                        MAX-ACCESS read-write
                        STATUS current
                        DESCRIPTION
                                "Description.
                                The request of a user command"
                        ::= { fkVoipMediaProfileControl 1 }

                
                -- 1.3.6.1.4.1.10428 9 1.101.25.8.2.2
                fkVoipMediaProfileControlStatus OBJECT-TYPE
                        SYNTAX FkControlStatusType
                        MAX-ACCESS read-only
                        STATUS current
                        DESCRIPTION
                                "Description.
                                The status of user command"
                        ::= { fkVoipMediaProfileControl 2 }

                
                -- 1.3.6.1.4.1.10428 9 1.101.25.8.2.3
                fkVoipMediaProfileControlTimer OBJECT-TYPE
                        SYNTAX Gauge32
                        MAX-ACCESS read-write
                        STATUS current
                        DESCRIPTION
                                "Description.
                                The maximum time for the manager for a long running user command"
                        ::= { fkVoipMediaProfileControl 3 }

                
                -- 1.3.6.1.4.1.10428 9 1.101.25.8.2.4
                fkVoipMediaProfileControlTimeStamp OBJECT-TYPE
                        SYNTAX TimeTicks
                        MAX-ACCESS read-only
                        STATUS current
                        DESCRIPTION
                                "Description.
                                The time stamp of the last command(end of command)"
                        ::= { fkVoipMediaProfileControl 4 }

                
                -- 1.3.6.1.4.1.10428 9 1.101.25.8.2.5
                fkVoipMediaProfileControlReqResult OBJECT-TYPE
                        SYNTAX FkControlRequestResultType
                        MAX-ACCESS read-only
                        STATUS current
                        DESCRIPTION
                                "Description.
                                The result of the last user command"
                        ::= { fkVoipMediaProfileControl 5 }

                
                -- 1.3.6.1.4.1.10428 9 1.101.25.8.2.6
                fkVoipMediaProfileControlIndex OBJECT-TYPE
                        SYNTAX Integer32 (1..8)
                        MAX-ACCESS read-write
                        STATUS current
                        DESCRIPTION
                                "The index of Media Profile (1.8)"
                        ::= { fkVoipMediaProfileControl 6 }

                
                -- 1.3.6.1.4.1.10428 9 1.101.25.8.2.7
                fkVoipMediaProfileControlCodecSelection OBJECT-TYPE
                        SYNTAX INTEGER
                                {
                                pcmu(0),
                                g723(4),
                                pcma(8),
                                g729(18)
                                }
                        MAX-ACCESS read-write
                        STATUS current
                        DESCRIPTION
                                "Voice codec : G711 a-law codec, G711 mu-law codec, G.723 Codec standard, G.729 Codec standard."
                        ::= { fkVoipMediaProfileControl 7 }

                
                -- 1.3.6.1.4.1.10428 9 1.101.25.8.2.8
                fkVoipMediaProfileControlPacketPeriod OBJECT-TYPE
                        SYNTAX Integer32 (10..30)
                        MAX-ACCESS read-write
                        STATUS current
                        DESCRIPTION
                                "Packet Period setting. Range value is from 10 to 30 ms. Default value is 10ms."
                        ::= { fkVoipMediaProfileControl 8 }

                
                -- 1.3.6.1.4.1.10428 9 1.101.25.8.2.9
                fkVoipMediaProfileControlSilenceSuppression OBJECT-TYPE
                        SYNTAX INTEGER
                                {
                                off(0),
                                on(1)
                                }
                        MAX-ACCESS read-write
                        STATUS current
                        DESCRIPTION
                                "Silence suppression setting. Off(0), on(1)"
                        ::= { fkVoipMediaProfileControl 9 }

                
                -- 1.3.6.1.4.1.10428 9 1.101.25.8.3
                fkVoipMediaProfileNotification OBJECT IDENTIFIER ::= { fkVoipMediaProfile 3 }

                
                -- 1.3.6.1.4.1.10428 9 1.101.25.8.3.1
                fkVoipMediaProfileEnabled NOTIFICATION-TYPE
                        OBJECTS { fkVoipMediaProfileControlRequest, fkVoipMediaProfileControlTimeStamp, fkVoipMediaProfileControlReqResult, fkVoipMediaProfileControlIndex, fkVoipMediaProfileControlSilenceSuppression, 
                                fkVoipMediaProfileControlCodecSelection, fkVoipMediaProfileControlPacketPeriod }
                        STATUS current
                        DESCRIPTION 
                                "Description."
                        ::= { fkVoipMediaProfileNotification 1 }

                
                -- 1.3.6.1.4.1.10428 9 1.101.25.8.3.2
                fkVoipMediaProfileDisabled NOTIFICATION-TYPE
                        OBJECTS { fkVoipMediaProfileControlRequest, fkVoipMediaProfileControlTimeStamp, fkVoipMediaProfileControlReqResult, fkVoipMediaProfileControlIndex }
                        STATUS current
                        DESCRIPTION 
                                "Description."
                        ::= { fkVoipMediaProfileNotification 2 }

                
                -- 1.3.6.1.4.1.10428 9 1.101.25.9
                fkVoipRtpProfile OBJECT IDENTIFIER ::= { fkVoip 9 }

                
                -- 1.3.6.1.4.1.10428 9 1.101.25.9.1
                fkVoipRtpProfileInfo OBJECT IDENTIFIER ::= { fkVoipRtpProfile 1 }

                
                -- 1.3.6.1.4.1.10428 9 1.101.25.9.1.1
                fkVoipRtpProfilePortMin OBJECT-TYPE
                        SYNTAX Integer32 (30000..60000)
                        MAX-ACCESS read-only
                        STATUS current
                        DESCRIPTION
                                "Set the starting local port for RTP. Default value is 30000."
                        ::= { fkVoipRtpProfileInfo 1 }

                
                -- 1.3.6.1.4.1.10428 9 1.101.25.9.1.2
                fkVoipRtpProfileDscpMark OBJECT-TYPE
                        SYNTAX Integer32 (0..63)
                        MAX-ACCESS read-only
                        STATUS current
                        DESCRIPTION
                                "Marks the DSCP with the given number. Default value is 0."
                        ::= { fkVoipRtpProfileInfo 2 }

                
                -- 1.3.6.1.4.1.10428 9 1.101.25.9.1.3
                fkVoipRtpProfileOob OBJECT-TYPE
                        SYNTAX INTEGER
                                {
                                off(0),
                                on(1)
                                }
                        MAX-ACCESS read-only
                        STATUS current
                        DESCRIPTION
                                "Enable Out-of-band DTMF. When this option is enable, DTMF can be tranferred via RTP or signalling packet depending on the value of dtmf-event is enable or disable,respectively."
                        ::= { fkVoipRtpProfileInfo 3 }

                
                -- 1.3.6.1.4.1.10428 9 1.101.25.9.1.4
                fkVoipRtpProfileDtmfEvent OBJECT-TYPE
                        SYNTAX INTEGER
                                {
                                off(0),
                                on(1)
                                }
                        MAX-ACCESS read-only
                        STATUS current
                        DESCRIPTION
                                "Enable DTMF transfer via RTP. If oob-dtmf is disable, this value is ignored."
                        ::= { fkVoipRtpProfileInfo 4 }

                
                -- 1.3.6.1.4.1.10428 9 1.101.25.9.2
                fkVoipRtpProfileControl OBJECT IDENTIFIER ::= { fkVoipRtpProfile 2 }

                
                -- 1.3.6.1.4.1.10428 9 1.101.25.9.2.1
                fkVoipRtpProfileControlRequest OBJECT-TYPE
                        SYNTAX INTEGER
                                {
                                setVoipRtpPortMin(1),
                                setVoipRtpDscp(2),
                                setVoipRtpOob(3),
                                setVoipRtpDtmf(4)
                                }
                        MAX-ACCESS read-write
                        STATUS current
                        DESCRIPTION
                                "Description.
                                The request of a user command"
                        ::= { fkVoipRtpProfileControl 1 }

                
                -- 1.3.6.1.4.1.10428 9 1.101.25.9.2.2
                fkVoipRtpProfileControlStatus OBJECT-TYPE
                        SYNTAX FkControlStatusType
                        MAX-ACCESS read-only
                        STATUS current
                        DESCRIPTION
                                "Description.
                                The status of user command"
                        ::= { fkVoipRtpProfileControl 2 }

                
                -- 1.3.6.1.4.1.10428 9 1.101.25.9.2.3
                fkVoipRtpProfileControlTimer OBJECT-TYPE
                        SYNTAX Gauge32
                        MAX-ACCESS read-write
                        STATUS current
                        DESCRIPTION
                                "Description.
                                The maximum time for the manager for a long running user command"
                        ::= { fkVoipRtpProfileControl 3 }

                
                -- 1.3.6.1.4.1.10428 9 1.101.25.9.2.4
                fkVoipRtpProfileControlTimeStamp OBJECT-TYPE
                        SYNTAX TimeTicks
                        MAX-ACCESS read-only
                        STATUS current
                        DESCRIPTION
                                "Description.
                                The time stamp of the last command(end of command)"
                        ::= { fkVoipRtpProfileControl 4 }

                
                -- 1.3.6.1.4.1.10428 9 1.101.25.9.2.5
                fkVoipRtpProfileControlReqResult OBJECT-TYPE
                        SYNTAX FkControlRequestResultType
                        MAX-ACCESS read-only
                        STATUS current
                        DESCRIPTION
                                "Description.
                                The result of the last user command"
                        ::= { fkVoipRtpProfileControl 5 }

                
                -- 1.3.6.1.4.1.10428 9 1.101.25.9.2.6
                fkVoipRtpProfileControlPortMin OBJECT-TYPE
                        SYNTAX Integer32 (30000..60000)
                        MAX-ACCESS read-write
                        STATUS current
                        DESCRIPTION
                                "Set the starting local port for RTP. Default value is 30000."
                        ::= { fkVoipRtpProfileControl 6 }

                
                -- 1.3.6.1.4.1.10428 9 1.101.25.9.2.7
                fkVoipRtpProfileControlDscpMark OBJECT-TYPE
                        SYNTAX Integer32 (0..63)
                        MAX-ACCESS read-write
                        STATUS current
                        DESCRIPTION
                                "Marks the DSCP with the given number. Default value is 0."
                        ::= { fkVoipRtpProfileControl 7 }

                
                -- 1.3.6.1.4.1.10428 9 1.101.25.9.2.8
                fkVoipRtpProfileControlOob OBJECT-TYPE
                        SYNTAX INTEGER
                                {
                                off(0),
                                on(1)
                                }
                        MAX-ACCESS read-write
                        STATUS current
                        DESCRIPTION
                                "Enable Out-of-band DTMF. When this option is enable, DTMF can be tranferred via RTP or signalling packet depending on the value of dtmf-event is enable or disable,respectively."
                        ::= { fkVoipRtpProfileControl 8 }

                
                -- 1.3.6.1.4.1.10428 9 1.101.25.9.2.9
                fkVoipRtpProfileControlDtmfEvent OBJECT-TYPE
                        SYNTAX INTEGER
                                {
                                off(0),
                                on(1)
                                }
                        MAX-ACCESS read-write
                        STATUS current
                        DESCRIPTION
                                "Enable DTMF transfer via RTP. If oob-dtmf is disable, this value is ignored."
                        ::= { fkVoipRtpProfileControl 9 }

                
                -- 1.3.6.1.4.1.10428 9 1.101.25.9.3
                fkVoipRtpProfileNotification OBJECT IDENTIFIER ::= { fkVoipRtpProfile 3 }

                
                -- 1.3.6.1.4.1.10428 9 1.101.25.9.3.1
                fkVoipRtpProfilePortMinChanged NOTIFICATION-TYPE
                        OBJECTS { fkVoipRtpProfileControlRequest, fkVoipRtpProfileControlTimeStamp, fkVoipRtpProfileControlReqResult, fkVoipRtpProfileControlPortMin }
                        STATUS current
                        DESCRIPTION 
                                "Description."
                        ::= { fkVoipRtpProfileNotification 1 }

                
                -- 1.3.6.1.4.1.10428 9 1.101.25.9.3.2
                fkVoipRtpProfileDscpMarkChanged NOTIFICATION-TYPE
                        OBJECTS { fkVoipRtpProfileControlRequest, fkVoipRtpProfileControlTimeStamp, fkVoipRtpProfileControlReqResult, fkVoipRtpProfileControlDscpMark }
                        STATUS current
                        DESCRIPTION 
                                "Description."
                        ::= { fkVoipRtpProfileNotification 2 }

                
                -- 1.3.6.1.4.1.10428 9 1.101.25.9.3.3
                fkVoipRtpProfileOobChanged NOTIFICATION-TYPE
                        OBJECTS { fkVoipRtpProfileControlRequest, fkVoipRtpProfileControlTimeStamp, fkVoipRtpProfileControlReqResult, fkVoipRtpProfileControlOob }
                        STATUS current
                        DESCRIPTION 
                                "Description."
                        ::= { fkVoipRtpProfileNotification 3 }

                
                -- 1.3.6.1.4.1.10428 9 1.101.25.9.3.4
                fkVoipRtpProfileDtmfEventChanged NOTIFICATION-TYPE
                        OBJECTS { fkVoipRtpProfileControlRequest, fkVoipRtpProfileControlTimeStamp, fkVoipRtpProfileControlReqResult, fkVoipRtpProfileControlDtmfEvent }
                        STATUS current
                        DESCRIPTION 
                                "Description."
                        ::= { fkVoipRtpProfileNotification 4 }

                
                -- 1.3.6.1.4.1.10428 9 1.101.25.10
                fkVoipTimer OBJECT IDENTIFIER ::= { fkVoip 10 }

                
                -- 1.3.6.1.4.1.10428 9 1.101.25.10.1
                fkVoipTimerTable OBJECT-TYPE
                        SYNTAX SEQUENCE OF FkVoipTimerEntry
                        MAX-ACCESS not-accessible
                        STATUS current
                        DESCRIPTION
                                "Description."
                        ::= { fkVoipTimer 1 }

                
                -- 1.3.6.1.4.1.10428 9 1.101.25.10.1.1
                fkVoipTimerEntry OBJECT-TYPE
                        SYNTAX FkVoipTimerEntry
                        MAX-ACCESS not-accessible
                        STATUS current
                        DESCRIPTION
                                "Description."
                        INDEX { fkVoipTimerIndex }
                        ::= { fkVoipTimerTable 1 }

                
                FkVoipTimerEntry ::=
                        SEQUENCE { 
                                fkVoipTimerIndex
                                        Integer32,
                                fkVoipTimerCriticalTimeout
                                        Integer32,
                                fkVoipTimerFirstDigit
                                        Integer32,
                                fkVoipTimerIntraDigit
                                        Integer32
                         }

                -- 1.3.6.1.4.1.10428 9 1.101.25.10.1.1.1
                fkVoipTimerIndex OBJECT-TYPE
                        SYNTAX Integer32 (1..8)
                        MAX-ACCESS read-only
                        STATUS current
                        DESCRIPTION
                                "Description.
                                Display Timer index. Value is range from 1 to 8"
                        ::= { fkVoipTimerEntry 1 }

                
                -- 1.3.6.1.4.1.10428 9 1.101.25.10.1.1.2
                fkVoipTimerCriticalTimeout OBJECT-TYPE
                        SYNTAX Integer32 (0..15000)
                        MAX-ACCESS read-only
                        STATUS current
                        DESCRIPTION
                                "Critical timeout value (default 0ms)"
                        ::= { fkVoipTimerEntry 2 }

                
                -- 1.3.6.1.4.1.10428 9 1.101.25.10.1.1.3
                fkVoipTimerFirstDigit OBJECT-TYPE
                        SYNTAX Integer32 (10000..30000)
                        MAX-ACCESS read-only
                        STATUS current
                        DESCRIPTION
                                "First Digit Value (default 15000ms)"
                        ::= { fkVoipTimerEntry 3 }

                
                -- 1.3.6.1.4.1.10428 9 1.101.25.10.1.1.4
                fkVoipTimerIntraDigit OBJECT-TYPE
                        SYNTAX Integer32 (5000..15000)
                        MAX-ACCESS read-only
                        STATUS current
                        DESCRIPTION
                                "Intra Digit value(Default 5000ms)"
                        ::= { fkVoipTimerEntry 4 }

                
                -- 1.3.6.1.4.1.10428 9 1.101.25.10.2
                fkVoipTimerControl OBJECT IDENTIFIER ::= { fkVoipTimer 2 }

                
                -- 1.3.6.1.4.1.10428 9 1.101.25.10.2.1
                fkVoipTimerControlRequest OBJECT-TYPE
                        SYNTAX INTEGER
                                {
                                enableVoipTimer(1),
                                disableVoipTimer(2)
                                }
                        MAX-ACCESS read-write
                        STATUS current
                        DESCRIPTION
                                "Description.
                                The request of a user command"
                        ::= { fkVoipTimerControl 1 }

                
                -- 1.3.6.1.4.1.10428 9 1.101.25.10.2.2
                fkVoipTimerControlStatus OBJECT-TYPE
                        SYNTAX FkControlStatusType
                        MAX-ACCESS read-only
                        STATUS current
                        DESCRIPTION
                                "Description.
                                The status of user command"
                        ::= { fkVoipTimerControl 2 }

                
                -- 1.3.6.1.4.1.10428 9 1.101.25.10.2.3
                fkVoipTimerControlTimer OBJECT-TYPE
                        SYNTAX Gauge32
                        MAX-ACCESS read-write
                        STATUS current
                        DESCRIPTION
                                "Description.
                                The maximum time for the manager for a long running user command"
                        ::= { fkVoipTimerControl 3 }

                
                -- 1.3.6.1.4.1.10428 9 1.101.25.10.2.4
                fkVoipTimerControlTimeStamp OBJECT-TYPE
                        SYNTAX TimeTicks
                        MAX-ACCESS read-only
                        STATUS current
                        DESCRIPTION
                                "Description.
                                The time stamp of the last command(end of command)"
                        ::= { fkVoipTimerControl 4 }

                
                -- 1.3.6.1.4.1.10428 9 1.101.25.10.2.5
                fkVoipTimerControlReqResult OBJECT-TYPE
                        SYNTAX FkControlRequestResultType
                        MAX-ACCESS read-only
                        STATUS current
                        DESCRIPTION
                                "Description.
                                The result of the last user command"
                        ::= { fkVoipTimerControl 5 }

                
                -- 1.3.6.1.4.1.10428 9 1.101.25.10.2.6
                fkVoipTimerControlIndex OBJECT-TYPE
                        SYNTAX Integer32 (1..8)
                        MAX-ACCESS read-write
                        STATUS current
                        DESCRIPTION
                                "Description.
                                Setting Timer index. Value is range from 1 to 8"
                        ::= { fkVoipTimerControl 6 }

                
                -- 1.3.6.1.4.1.10428 9 1.101.25.10.2.7
                fkVoipTimerControlCriticalTimeout OBJECT-TYPE
                        SYNTAX Integer32 (0..15000)
                        MAX-ACCESS read-write
                        STATUS current
                        DESCRIPTION
                                "Description.
                                Critical timeout value (default 0ms)"
                        ::= { fkVoipTimerControl 7 }

                
                -- 1.3.6.1.4.1.10428 9 1.101.25.10.2.8
                fkVoipTimerControlFirstDigit OBJECT-TYPE
                        SYNTAX Integer32 (10000..30000)
                        MAX-ACCESS read-write
                        STATUS current
                        DESCRIPTION
                                "Description.
                                First Digit Value (default 15000ms)"
                        ::= { fkVoipTimerControl 8 }

                
                -- 1.3.6.1.4.1.10428 9 1.101.25.10.2.9
                fkVoipTimerControlIntraDigit OBJECT-TYPE
                        SYNTAX Integer32 (5000..15000)
                        MAX-ACCESS read-write
                        STATUS current
                        DESCRIPTION
                                "Description.
                                Intra Digit value(Default 5000ms)"
                        ::= { fkVoipTimerControl 9 }

                
                -- 1.3.6.1.4.1.10428 9 1.101.25.10.3
                fkVoipTimerNotification OBJECT IDENTIFIER ::= { fkVoipTimer 3 }

                
                -- 1.3.6.1.4.1.10428 9 1.101.25.10.3.1
                fkVoipTimerEnabled NOTIFICATION-TYPE
                        OBJECTS { fkVoipTimerControlRequest, fkVoipTimerControlTimeStamp, fkVoipTimerControlReqResult, fkVoipTimerControlIndex, fkVoipTimerControlCriticalTimeout, 
                                fkVoipTimerControlFirstDigit, fkVoipTimerControlIntraDigit }
                        STATUS current
                        DESCRIPTION 
                                "Description."
                        ::= { fkVoipTimerNotification 1 }

                
                -- 1.3.6.1.4.1.10428 9 1.101.25.10.3.2
                fkVoipTimerDisabled NOTIFICATION-TYPE
                        OBJECTS { fkVoipTimerControlRequest, fkVoipTimerControlTimeStamp, fkVoipTimerControlReqResult, fkVoipTimerControlIndex }
                        STATUS current
                        DESCRIPTION 
                                "Description."
                        ::= { fkVoipTimerNotification 2 }

                
                -- 1.3.6.1.4.1.10428 9 1.101.25.11
                fkVoipDialPlan OBJECT IDENTIFIER ::= { fkVoip 11 }

                
                -- 1.3.6.1.4.1.10428 9 1.101.25.11.1
                fkVoipDialPlanTable OBJECT-TYPE
                        SYNTAX SEQUENCE OF FkVoipDialPlanEntry
                        MAX-ACCESS not-accessible
                        STATUS current
                        DESCRIPTION
                                "Description."
                        ::= { fkVoipDialPlan 1 }

                
                -- 1.3.6.1.4.1.10428 9 1.101.25.11.1.1
                fkVoipDialPlanEntry OBJECT-TYPE
                        SYNTAX FkVoipDialPlanEntry
                        MAX-ACCESS not-accessible
                        STATUS current
                        DESCRIPTION
                                "Description."
                        INDEX { fkVoipDialPlanIndex }
                        ::= { fkVoipDialPlanTable 1 }

                
                FkVoipDialPlanEntry ::=
                        SEQUENCE { 
                                fkVoipDialPlanPotStatusIndex
                                        Integer32,
                                fkVoipDialPlanIndex
                                        Integer32,
                                fkVoipDialPlanDigitMap
                                        OCTET STRING
                         }

                -- 1.3.6.1.4.1.10428 9 1.101.25.11.1.1.1
                fkVoipDialPlanPotStatusIndex OBJECT-TYPE
                        SYNTAX Integer32 (1..8)
                        MAX-ACCESS read-only
                        STATUS current
                        DESCRIPTION
                                "Description.
                                Display pots status index. Value is range from 1 to 8"
                        ::= { fkVoipDialPlanEntry 1 }

                
                -- 1.3.6.1.4.1.10428 9 1.101.25.11.1.1.2
                fkVoipDialPlanIndex OBJECT-TYPE
                        SYNTAX Integer32 (1..16)
                        MAX-ACCESS read-only
                        STATUS current
                        DESCRIPTION
                                "Description.
                                Dial-plan index. Value is range from 1 to 16"
                        ::= { fkVoipDialPlanEntry 2 }

                
                -- 1.3.6.1.4.1.10428 9 1.101.25.11.1.1.3
                fkVoipDialPlanDigitMap OBJECT-TYPE
                        SYNTAX OCTET STRING
                        MAX-ACCESS read-only
                        STATUS current
                        DESCRIPTION
                                "Description.
                                Digit Map string. The format is 0123456789.x"
                        ::= { fkVoipDialPlanEntry 3 }

                
                -- 1.3.6.1.4.1.10428 9 1.101.25.11.2
                fkVoipDialPlanControl OBJECT IDENTIFIER ::= { fkVoipDialPlan 2 }

                
                -- 1.3.6.1.4.1.10428 9 1.101.25.11.2.1
                fkVoipDialPlanControlRequest OBJECT-TYPE
                        SYNTAX INTEGER
                                {
                                enableVoipDialPlan(1),
                                disableVoipDialPlan(2)
                                }
                        MAX-ACCESS read-write
                        STATUS current
                        DESCRIPTION
                                "Description.
                                The request of a user command"
                        ::= { fkVoipDialPlanControl 1 }

                
                -- 1.3.6.1.4.1.10428 9 1.101.25.11.2.2
                fkVoipDialPlanControlStatus OBJECT-TYPE
                        SYNTAX FkControlStatusType
                        MAX-ACCESS read-only
                        STATUS current
                        DESCRIPTION
                                "Description.
                                The status of user command"
                        ::= { fkVoipDialPlanControl 2 }

                
                -- 1.3.6.1.4.1.10428 9 1.101.25.11.2.3
                fkVoipDialPlanControlTimer OBJECT-TYPE
                        SYNTAX Gauge32
                        MAX-ACCESS read-write
                        STATUS current
                        DESCRIPTION
                                "Description.
                                The maximum time for the manager for a long running user command"
                        ::= { fkVoipDialPlanControl 3 }

                
                -- 1.3.6.1.4.1.10428 9 1.101.25.11.2.4
                fkVoipDialPlanControlTimeStamp OBJECT-TYPE
                        SYNTAX TimeTicks
                        MAX-ACCESS read-only
                        STATUS current
                        DESCRIPTION
                                "Description.
                                The time stamp of the last command(end of command)"
                        ::= { fkVoipDialPlanControl 4 }

                
                -- 1.3.6.1.4.1.10428 9 1.101.25.11.2.5
                fkVoipDialPlanControlReqResult OBJECT-TYPE
                        SYNTAX FkControlRequestResultType
                        MAX-ACCESS read-write
                        STATUS current
                        DESCRIPTION
                                "Description.
                                The result of the last user command"
                        ::= { fkVoipDialPlanControl 5 }

                
                -- 1.3.6.1.4.1.10428 9 1.101.25.11.2.6
                fkVoipDialPlanControlPotStatusIndex OBJECT-TYPE
                        SYNTAX Integer32 (1..8)
                        MAX-ACCESS read-write
                        STATUS current
                        DESCRIPTION
                                "Description.
                                Pots status index. Value is range from 1 to 8"
                        ::= { fkVoipDialPlanControl 6 }

                
                -- 1.3.6.1.4.1.10428 9 1.101.25.11.2.7
                fkVoipDialPlanControlIndex OBJECT-TYPE
                        SYNTAX Integer32 (1..16)
                        MAX-ACCESS read-write
                        STATUS current
                        DESCRIPTION
                                "Description.
                                Dial-plan index. Value is range from 1 to 16"
                        ::= { fkVoipDialPlanControl 7 }

                
                -- 1.3.6.1.4.1.10428 9 1.101.25.11.2.8
                fkVoipDialPlanControlDigitMap OBJECT-TYPE
                        SYNTAX OCTET STRING
                        MAX-ACCESS read-write
                        STATUS current
                        DESCRIPTION
                                "Description.
                                Digit Map string. The format is 0123456789.x. Characters can be 0123456789.x-[]T"
                        ::= { fkVoipDialPlanControl 8 }

                
                -- 1.3.6.1.4.1.10428 9 1.101.25.11.3
                fkVoipDialPlanNotification OBJECT IDENTIFIER ::= { fkVoipDialPlan 3 }

                
                -- 1.3.6.1.4.1.10428 9 1.101.25.11.3.1
                fkVoipDialPlanEnabled NOTIFICATION-TYPE
                        OBJECTS { fkVoipDialPlanControlRequest, fkVoipDialPlanControlTimeStamp, fkVoipDialPlanControlReqResult, fkVoipDialPlanControlPotStatusIndex, fkVoipDialPlanControlIndex, 
                                fkVoipDialPlanControlDigitMap }
                        STATUS current
                        DESCRIPTION 
                                "Description."
                        ::= { fkVoipDialPlanNotification 1 }

                
                -- 1.3.6.1.4.1.10428 9 1.101.25.11.3.2
                fkVoipDialPlanDisabled NOTIFICATION-TYPE
                        OBJECTS { fkVoipDialPlanControlRequest, fkVoipDialPlanControlTimeStamp, fkVoipDialPlanControlReqResult, fkVoipDialPlanControlIndex }
                        STATUS current
                        DESCRIPTION 
                                "Description."
                        ::= { fkVoipDialPlanNotification 2 }

                
                -- 1.3.6.1.4.1.10428 9 1.101.25.12
                fkVoipStatistics OBJECT IDENTIFIER ::= { fkVoip 12 }

                
                -- 1.3.6.1.4.1.10428 9 1.101.25.12.1
                fkVoipStatisticsTable OBJECT-TYPE
                        SYNTAX SEQUENCE OF FkVoipStatisticsEntry
                        MAX-ACCESS not-accessible
                        STATUS current
                        DESCRIPTION
                                "Description."
                        ::= { fkVoipStatistics 1 }

                
                -- 1.3.6.1.4.1.10428 9 1.101.25.12.1.1
                fkVoipStatisticsEntry OBJECT-TYPE
                        SYNTAX FkVoipStatisticsEntry
                        MAX-ACCESS not-accessible
                        STATUS current
                        DESCRIPTION
                                "Description."
                        INDEX { fkVoipStatisticsIndex }
                        ::= { fkVoipStatisticsTable 1 }

                
                FkVoipStatisticsEntry ::=
                        SEQUENCE { 
                                fkVoipStatisticsIndex
                                        Integer32,
                                fkVoipStatisticsFormat
                                        Unsigned32,
                                fkVoipStatisticsCallTimer
                                        Unsigned32,
                                fkVoipStatisticsCurrentPlayoutDelay
                                        Unsigned32,
                                fkVoipStatisticsMinPlayoutDelay
                                        Unsigned32,
                                fkVoipStatisticsMaxPlayoutDelay
                                        Unsigned32,
                                fkVoipStatisticsClockOffset
                                        Unsigned32,
                                fkVoipStatisticsPeakJitter
                                        Unsigned32,
                                fkVoipStatisticsInterpolativeConcealment
                                        Unsigned32,
                                fkVoipStatisticsSilenceConcealment
                                        Unsigned32,
                                fkVoipStatisticsOverflowDiscard
                                        Unsigned32,
                                fkVoipStatisticsEndpointDetectionErrors
                                        Unsigned32,
                                fkVoipStatisticsTxVoicePackets
                                        Unsigned32,
                                fkVoipStatisticsTxSignalingPackets
                                        Unsigned32,
                                fkVoipStatisticsTxComfortNoisePackets
                                        Unsigned32,
                                fkVoipStatisticsTotalTransmitDuration
                                        Unsigned32,
                                fkVoipStatisticsVoiceTransmitDuration
                                        Unsigned32,
                                fkVoipStatisticsRxVoicePackets
                                        Unsigned32,
                                fkVoipStatisticsRxSignalingPackets
                                        Unsigned32,
                                fkVoipStatisticsRxComfortNoisePackets
                                        Unsigned32,
                                fkVoipStatisticsTotalReceiveDuration
                                        Unsigned32,
                                fkVoipStatisticsVoiceReceiveDuration
                                        Unsigned32,
                                fkVoipStatisticsPacketsOutSequence
                                        Unsigned32,
                                fkVoipStatisticsBadProtocolHeaders
                                        Unsigned32,
                                fkVoipStatisticsLatePackets
                                        Unsigned32,
                                fkVoipStatisticsEarlyPackets
                                        Unsigned32,
                                fkVoipStatisticsRxVoiceOctets
                                        Unsigned32,
                                fkVoipStatisticsLostPackets
                                        Unsigned32,
                                fkVoipStatisticsCurrentTransmitPower
                                        Unsigned32,
                                fkVoipStatisticsMeanTransmitPower
                                        Unsigned32,
                                fkVoipStatisticsCurrentReceivePower
                                        Unsigned32,
                                fkVoipStatisticsMeanReceivePower
                                        Unsigned32,
                                fkVoipStatisticsBackgroundNoise
                                        Unsigned32,
                                fkVoipStatisticsErlLevel
                                        Unsigned32,
                                fkVoipStatisticsAcomLevel
                                        Unsigned32,
                                fkVoipStatisticsCurrentTransmitActivity
                                        Unsigned32,
                                fkVoipStatisticsCurrentReceiveActivity
                                        Unsigned32
                         }

                -- 1.3.6.1.4.1.10428 9 1.101.25.12.1.1.1
                fkVoipStatisticsIndex OBJECT-TYPE
                        SYNTAX Integer32 (1..8)
                        MAX-ACCESS read-only
                        STATUS current
                        DESCRIPTION
                                "Index of voip pots. Value is range from 1 to 8"
                        ::= { fkVoipStatisticsEntry 1 }

                
                -- 1.3.6.1.4.1.10428 9 1.101.25.12.1.1.2
                fkVoipStatisticsFormat OBJECT-TYPE
                        SYNTAX Unsigned32
                        MAX-ACCESS read-only
                        STATUS current
                        DESCRIPTION
                                "Format revision"
                        ::= { fkVoipStatisticsEntry 2 }

                
                -- 1.3.6.1.4.1.10428 9 1.101.25.12.1.1.3
                fkVoipStatisticsCallTimer OBJECT-TYPE
                        SYNTAX Unsigned32
                        MAX-ACCESS read-only
                        STATUS current
                        DESCRIPTION
                                "Call Timer is number of Rx Voice bytes"
                        ::= { fkVoipStatisticsEntry 3 }

                
                -- 1.3.6.1.4.1.10428 9 1.101.25.12.1.1.4
                fkVoipStatisticsCurrentPlayoutDelay OBJECT-TYPE
                        SYNTAX Unsigned32
                        MAX-ACCESS read-only
                        STATUS current
                        DESCRIPTION
                                "Current delay, measured in milliseconds"
                        ::= { fkVoipStatisticsEntry 4 }

                
                -- 1.3.6.1.4.1.10428 9 1.101.25.12.1.1.5
                fkVoipStatisticsMinPlayoutDelay OBJECT-TYPE
                        SYNTAX Unsigned32
                        MAX-ACCESS read-only
                        STATUS current
                        DESCRIPTION
                                "The minimum playout delay observed during the current voice session"
                        ::= { fkVoipStatisticsEntry 5 }

                
                -- 1.3.6.1.4.1.10428 9 1.101.25.12.1.1.6
                fkVoipStatisticsMaxPlayoutDelay OBJECT-TYPE
                        SYNTAX Unsigned32
                        MAX-ACCESS read-only
                        STATUS current
                        DESCRIPTION
                                "The maximum playout delay observed during the current voice session"
                        ::= { fkVoipStatisticsEntry 6 }

                
                -- 1.3.6.1.4.1.10428 9 1.101.25.12.1.1.7
                fkVoipStatisticsClockOffset OBJECT-TYPE
                        SYNTAX Unsigned32
                        MAX-ACCESS read-only
                        STATUS current
                        DESCRIPTION
                                "Description.
                                The time offset between the remote source and the current source"
                        ::= { fkVoipStatisticsEntry 7 }

                
                -- 1.3.6.1.4.1.10428 9 1.101.25.12.1.1.8
                fkVoipStatisticsPeakJitter OBJECT-TYPE
                        SYNTAX Unsigned32
                        MAX-ACCESS read-only
                        STATUS current
                        DESCRIPTION
                                "Description."
                        ::= { fkVoipStatisticsEntry 8 }

                
                -- 1.3.6.1.4.1.10428 9 1.101.25.12.1.1.9
                fkVoipStatisticsInterpolativeConcealment OBJECT-TYPE
                        SYNTAX Unsigned32
                        MAX-ACCESS read-only
                        STATUS current
                        DESCRIPTION
                                "Description.
                                The duration of voice interpolation to PCM is incremented when the voice decoder 
                                interpolates the missing frames to preserve audio continuity.
                                "
                        ::= { fkVoipStatisticsEntry 9 }

                
                -- 1.3.6.1.4.1.10428 9 1.101.25.12.1.1.10
                fkVoipStatisticsSilenceConcealment OBJECT-TYPE
                        SYNTAX Unsigned32
                        MAX-ACCESS read-only
                        STATUS current
                        DESCRIPTION
                                "Description.
                                The duration of silence interpolation to PCM is incremented when the voice decoder 
                                performs silence concealment of a missing frame.
                                "
                        ::= { fkVoipStatisticsEntry 10 }

                
                -- 1.3.6.1.4.1.10428 9 1.101.25.12.1.1.11
                fkVoipStatisticsOverflowDiscard OBJECT-TYPE
                        SYNTAX Unsigned32
                        MAX-ACCESS read-only
                        STATUS current
                        DESCRIPTION
                                "Description.
                                The duration of Jitter Buffer Overflow Discard"
                        ::= { fkVoipStatisticsEntry 11 }

                
                -- 1.3.6.1.4.1.10428 9 1.101.25.12.1.1.12
                fkVoipStatisticsEndpointDetectionErrors OBJECT-TYPE
                        SYNTAX Unsigned32
                        MAX-ACCESS read-only
                        STATUS current
                        DESCRIPTION
                                "The number of End-point Detection errors "
                        ::= { fkVoipStatisticsEntry 12 }

                
                -- 1.3.6.1.4.1.10428 9 1.101.25.12.1.1.13
                fkVoipStatisticsTxVoicePackets OBJECT-TYPE
                        SYNTAX Unsigned32
                        MAX-ACCESS read-only
                        STATUS current
                        DESCRIPTION
                                "Description.
                                The number of voice packets sent to IP."
                        ::= { fkVoipStatisticsEntry 13 }

                
                -- 1.3.6.1.4.1.10428 9 1.101.25.12.1.1.14
                fkVoipStatisticsTxSignalingPackets OBJECT-TYPE
                        SYNTAX Unsigned32
                        MAX-ACCESS read-only
                        STATUS current
                        DESCRIPTION
                                "Description.
                                The number of packets with payload type Redundant, DTMF or NTE 
                                packets sent to IP.
                                "
                        ::= { fkVoipStatisticsEntry 14 }

                
                -- 1.3.6.1.4.1.10428 9 1.101.25.12.1.1.15
                fkVoipStatisticsTxComfortNoisePackets OBJECT-TYPE
                        SYNTAX Unsigned32
                        MAX-ACCESS read-only
                        STATUS current
                        DESCRIPTION
                                "Description.
                                Transmit Comfort Noise Packets. The number of SID packets sent to IP."
                        ::= { fkVoipStatisticsEntry 15 }

                
                -- 1.3.6.1.4.1.10428 9 1.101.25.12.1.1.16
                fkVoipStatisticsTotalTransmitDuration OBJECT-TYPE
                        SYNTAX Unsigned32
                        MAX-ACCESS read-only
                        STATUS current
                        DESCRIPTION
                                "Description.
                                The total duration of the voice transmission."
                        ::= { fkVoipStatisticsEntry 16 }

                
                -- 1.3.6.1.4.1.10428 9 1.101.25.12.1.1.17
                fkVoipStatisticsVoiceTransmitDuration OBJECT-TYPE
                        SYNTAX Unsigned32
                        MAX-ACCESS read-only
                        STATUS current
                        DESCRIPTION
                                "Description.
                                The duration of voice transmission when voice is active."
                        ::= { fkVoipStatisticsEntry 17 }

                
                -- 1.3.6.1.4.1.10428 9 1.101.25.12.1.1.18
                fkVoipStatisticsRxVoicePackets OBJECT-TYPE
                        SYNTAX Unsigned32
                        MAX-ACCESS read-only
                        STATUS current
                        DESCRIPTION
                                "Description.
                                The number of voice packets received from IP."
                        ::= { fkVoipStatisticsEntry 18 }

                
                -- 1.3.6.1.4.1.10428 9 1.101.25.12.1.1.19
                fkVoipStatisticsRxSignalingPackets OBJECT-TYPE
                        SYNTAX Unsigned32
                        MAX-ACCESS read-only
                        STATUS current
                        DESCRIPTION
                                "Description.
                                The number of packets with payload type Redundant or DTMF or NTE packets received from IP."
                        ::= { fkVoipStatisticsEntry 19 }

                
                -- 1.3.6.1.4.1.10428 9 1.101.25.12.1.1.20
                fkVoipStatisticsRxComfortNoisePackets OBJECT-TYPE
                        SYNTAX Unsigned32
                        MAX-ACCESS read-only
                        STATUS current
                        DESCRIPTION
                                "Description.
                                Receive Comfort Noise Packets. The number of SID packets received from IP."
                        ::= { fkVoipStatisticsEntry 20 }

                
                -- 1.3.6.1.4.1.10428 9 1.101.25.12.1.1.21
                fkVoipStatisticsTotalReceiveDuration OBJECT-TYPE
                        SYNTAX Unsigned32
                        MAX-ACCESS read-only
                        STATUS current
                        DESCRIPTION
                                "Description.
                                The total duration of the voice transmission."
                        ::= { fkVoipStatisticsEntry 21 }

                
                -- 1.3.6.1.4.1.10428 9 1.101.25.12.1.1.22
                fkVoipStatisticsVoiceReceiveDuration OBJECT-TYPE
                        SYNTAX Unsigned32
                        MAX-ACCESS read-only
                        STATUS current
                        DESCRIPTION
                                "Description.
                                The total duration of the voice receive."
                        ::= { fkVoipStatisticsEntry 22 }

                
                -- 1.3.6.1.4.1.10428 9 1.101.25.12.1.1.23
                fkVoipStatisticsPacketsOutSequence OBJECT-TYPE
                        SYNTAX Unsigned32
                        MAX-ACCESS read-only
                        STATUS current
                        DESCRIPTION
                                "Description.
                                The number of out of sequence packets received from IP."
                        ::= { fkVoipStatisticsEntry 23 }

                
                -- 1.3.6.1.4.1.10428 9 1.101.25.12.1.1.24
                fkVoipStatisticsBadProtocolHeaders OBJECT-TYPE
                        SYNTAX Unsigned32
                        MAX-ACCESS read-only
                        STATUS current
                        DESCRIPTION
                                "Description.
                                Bad Protocol headers. Following packets will be rejected because of a bad protocol header"
                        ::= { fkVoipStatisticsEntry 24 }

                
                -- 1.3.6.1.4.1.10428 9 1.101.25.12.1.1.25
                fkVoipStatisticsLatePackets OBJECT-TYPE
                        SYNTAX Unsigned32
                        MAX-ACCESS read-only
                        STATUS current
                        DESCRIPTION
                                "Description.
                                Real Late Packets are defined as packets with sequence numbers that are received after having been declared late."
                        ::= { fkVoipStatisticsEntry 25 }

                
                -- 1.3.6.1.4.1.10428 9 1.101.25.12.1.1.26
                fkVoipStatisticsEarlyPackets OBJECT-TYPE
                        SYNTAX Unsigned32
                        MAX-ACCESS read-only
                        STATUS current
                        DESCRIPTION
                                "Description.
                                Early Packets"
                        ::= { fkVoipStatisticsEntry 26 }

                
                -- 1.3.6.1.4.1.10428 9 1.101.25.12.1.1.27
                fkVoipStatisticsRxVoiceOctets OBJECT-TYPE
                        SYNTAX Unsigned32
                        MAX-ACCESS read-only
                        STATUS current
                        DESCRIPTION
                                "Description.
                                Total number of bytes in the received voice packets."
                        ::= { fkVoipStatisticsEntry 27 }

                
                -- 1.3.6.1.4.1.10428 9 1.101.25.12.1.1.28
                fkVoipStatisticsLostPackets OBJECT-TYPE
                        SYNTAX Unsigned32
                        MAX-ACCESS read-only
                        STATUS current
                        DESCRIPTION
                                "Description.
                                The Lost Packet Count is calculated as: Declared Late Packets - Real Late Packets"
                        ::= { fkVoipStatisticsEntry 28 }

                
                -- 1.3.6.1.4.1.10428 9 1.101.25.12.1.1.29
                fkVoipStatisticsCurrentTransmitPower OBJECT-TYPE
                        SYNTAX Unsigned32
                        MAX-ACCESS read-only
                        STATUS current
                        DESCRIPTION
                                "Description.
                                Measured power (in dBov) of the signal being sent by the Mindspeed Comcerto Device over the circuit switched network."
                        ::= { fkVoipStatisticsEntry 29 }

                
                -- 1.3.6.1.4.1.10428 9 1.101.25.12.1.1.30
                fkVoipStatisticsMeanTransmitPower OBJECT-TYPE
                        SYNTAX Unsigned32
                        MAX-ACCESS read-only
                        STATUS current
                        DESCRIPTION
                                "Description.
                                Mean Transmit Power. Running mean (average) of measured Tx Powers."
                        ::= { fkVoipStatisticsEntry 30 }

                
                -- 1.3.6.1.4.1.10428 9 1.101.25.12.1.1.31
                fkVoipStatisticsCurrentReceivePower OBJECT-TYPE
                        SYNTAX Unsigned32
                        MAX-ACCESS read-only
                        STATUS current
                        DESCRIPTION
                                "Description.
                                Current Receive Power. Measured power (in dBov) of the signal being received by the Mindspeed Comcerto Device from the circuit switched network."
                        ::= { fkVoipStatisticsEntry 31 }

                
                -- 1.3.6.1.4.1.10428 9 1.101.25.12.1.1.32
                fkVoipStatisticsMeanReceivePower OBJECT-TYPE
                        SYNTAX Unsigned32
                        MAX-ACCESS read-only
                        STATUS current
                        DESCRIPTION
                                "Description.
                                Mean Receive Power .Running mean (average) of measured Rx Powers."
                        ::= { fkVoipStatisticsEntry 32 }

                
                -- 1.3.6.1.4.1.10428 9 1.101.25.12.1.1.33
                fkVoipStatisticsBackgroundNoise OBJECT-TYPE
                        SYNTAX Unsigned32
                        MAX-ACCESS read-only
                        STATUS current
                        DESCRIPTION
                                "Description.
                                Measured power (in dBov) of the estimated background noise level sent by the Comcerto 
                                Device over the circuit switched network.
                                "
                        ::= { fkVoipStatisticsEntry 33 }

                
                -- 1.3.6.1.4.1.10428 9 1.101.25.12.1.1.34
                fkVoipStatisticsErlLevel OBJECT-TYPE
                        SYNTAX Unsigned32
                        MAX-ACCESS read-only
                        STATUS current
                        DESCRIPTION
                                "Description.
                                The ERL is the attenuation of a signal from the receive-out port to the send-in port of an 
                                echo canceller, due to transmission and hybrid loss.
                                "
                        ::= { fkVoipStatisticsEntry 34 }

                
                -- 1.3.6.1.4.1.10428 9 1.101.25.12.1.1.35
                fkVoipStatisticsAcomLevel OBJECT-TYPE
                        SYNTAX Unsigned32
                        MAX-ACCESS read-only
                        STATUS current
                        DESCRIPTION
                                "Description.
                                The ACOM is the attenuation of a signal from the receive-out port to the send-out port of an echo canceller, "
                        ::= { fkVoipStatisticsEntry 35 }

                
                -- 1.3.6.1.4.1.10428 9 1.101.25.12.1.1.36
                fkVoipStatisticsCurrentTransmitActivity OBJECT-TYPE
                        SYNTAX Unsigned32
                        MAX-ACCESS read-only
                        STATUS current
                        DESCRIPTION
                                "Description.
                                Binary decision indicating whether the signal currently being sent by the Mindspeed 
                                Comcerto Device over the circuit switched network is voice (1) or silence (0).
                                "
                        ::= { fkVoipStatisticsEntry 36 }

                
                -- 1.3.6.1.4.1.10428 9 1.101.25.12.1.1.37
                fkVoipStatisticsCurrentReceiveActivity OBJECT-TYPE
                        SYNTAX Unsigned32
                        MAX-ACCESS read-only
                        STATUS current
                        DESCRIPTION
                                "Description.
                                Binary decision indicating whether the signal currently being received by the Mindspeed Comcerto Device from the circuit switched network is voice (1) or silence (0)."
                        ::= { fkVoipStatisticsEntry 37 }

                
                -- 1.3.6.1.4.1.10428 9 1.101.25.13
                fkVoipGroup OBJECT-GROUP
                        OBJECTS { fkVoipBaseControlRequest, fkVoipBaseControlStatus, fkVoipBaseControlTimer, fkVoipProtocol, fkVoipBaseControlTimeStamp, 
                                fkVoipBaseControlReqResult, fkVoipVoiceDSCP, fkVoipVoiceJitter, fkVoipVoiceControlRequest, fkVoipVoiceControlStatus, 
                                fkVoipVoiceControlTimer, fkVoipVoiceControlTimeStamp, fkVoipVoiceControlReqResult, fkVoipVoiceControlIndex, fkVoipVoiceControlEncoding, 
                                fkVoipVoiceControlUserEncoding, fkVoipVoiceControlComfortNoise, fkVoipVoiceControlEchoCancel, fkVoipVoiceControlPacketLoss, fkVoipVoiceControlVad, 
                                fkVoipVoiceControlDSCP, fkVoipVoiceControlJitter, fkVoipSipUserIndex, fkVoipSipUserAgent, fkVoipSipUserAOR, 
                                fkVoipSipUserDisplayName, fkVoipSipUserUserName, fkVoipSipUserPassword, fkVoipSipUserControlRequest, fkVoipSipUserControlStatus, 
                                fkVoipSipUserControlTimer, fkVoipSipUserControlTimeStamp, fkVoipSipUserControlReqResult, fkVoipSipUserControlIndex, fkVoipSipUserControlAgent, 
                                fkVoipSipUserControlAOR, fkVoipSipUserControlDisplayName, fkVoipSipUserControlUserName, fkVoipSipUserControlPassword, fkVoipSipAgentIndex, 
                                fkVoipSipAgentServer, fkVoipSipAgentPort, fkVoipSipAgentTypeOfService, fkVoipSipAgentTransport, fkVoipSipAgentRegistrar, 
                                fkVoipSipAgentPrimary, fkVoipSipAgentSecondary, fkVoipSipAgentProfileName, fkVoipSipAgentExpireTimer, fkVoipSipAgentControlRequest, 
                                fkVoipSipAgentControlStatus, fkVoipSipAgentControlTimer, fkVoipSipAgentControlTimeStamp, fkVoipSipAgentControlReqResult, fkVoipSipAgentControlIndex, 
                                fkVoipSipAgentControlServer, fkVoipSipAgentControlPort, fkVoipSipAgentControlTypeOfService, fkVoipSipAgentControlTransport, fkVoipSipAgentControlRegistrar, 
                                fkVoipSipAgentControlPrimary, fkVoipSipAgentControlSecondary, fkVoipSipAgentControlProfileName, fkVoipSipAgentControlExpireTimer, fkVoipVoiceIndex, 
                                fkVoipVoiceEncoding, fkVoipVoiceUserEncoding, fkVoipVoiceComfortNoise, fkVoipVoiceEchoCancel, fkVoipVoicePacketLoss, 
                                fkVoipVoiceVad, fkVoipMgcpEndpointIndex, fkVoipMgcpEndpointAgent, fkVoipMgcpEndpointName, fkVoipMgcpEndpointControlRequest, 
                                fkVoipMgcpEndpointControlStatus, fkVoipMgcpEndpointControlTimer, fkVoipMgcpEndpointControlTimeStamp, fkVoipMgcpEndpointControlReqResult, fkVoipMgcpEndpointControlIndex, 
                                fkVoipMgcpEndpointControlAgent, fkVoipMgcpEndpointControlName, fkVoipMgcpAgentIndex, fkVoipMgcpCallAgent, fkVoipMgcpAgentPort, 
                                fkVoipMgcpAgentTOS, fkVoipMgcpAgentVendor, fkVoipMgcpAgentDNS, fkVoipMgcpAgentControlRequest, fkVoipMgcpAgentControlStatus, 
                                fkVoipMgcpAgentControlTimer, fkVoipMgcpAgentControlTimeStamp, fkVoipMgcpAgentControlReqResult, fkVoipMgcpAgentControlIndex, fkVoipMgcpAgentControlCallAgent, 
                                fkVoipMgcpAgentControlPort, fkVoipMgcpAgentControlTOS, fkVoipMgcpAgentControlVendor, fkVoipMgcpAgentControlDNS, fkVoipPotsStatusIndex, 
                                fkVoipInterface, fkVoipMediaProfileIndex, fkVoipMediaProfileCodecSelection, fkVoipMediaProfilePacketPeriod, fkVoipMediaProfileSilenceSuppression, 
                                fkVoipMediaProfileControlRequest, fkVoipMediaProfileControlStatus, fkVoipMediaProfileControlTimer, fkVoipMediaProfileControlTimeStamp, fkVoipMediaProfileControlIndex, 
                                fkVoipMediaProfileControlCodecSelection, fkVoipMediaProfileControlPacketPeriod, fkVoipMediaProfileControlSilenceSuppression, fkVoipRtpProfilePortMin, fkVoipRtpProfileDscpMark, 
                                fkVoipRtpProfileOob, fkVoipRtpProfileDtmfEvent, fkVoipRtpProfileControlRequest, fkVoipRtpProfileControlStatus, fkVoipRtpProfileControlTimer, 
                                fkVoipRtpProfileControlTimeStamp, fkVoipRtpProfileControlReqResult, fkVoipRtpProfileControlPortMin, fkVoipRtpProfileControlDscpMark, fkVoipRtpProfileControlOob, 
                                fkVoipRtpProfileControlDtmfEvent, fkVoipMgcpCallAgentPort, fkVoipMgcpAgentControlCallAgentPort, fkVoipMgcpAgentProfileName, fkVoipMgcpAgentControlProfileName, 
                                fkVoipTimerIndex, fkVoipTimerCriticalTimeout, fkVoipTimerFirstDigit, fkVoipTimerIntraDigit, fkVoipTimerControlRequest, 
                                fkVoipTimerControlStatus, fkVoipTimerControlTimer, fkVoipTimerControlTimeStamp, fkVoipTimerControlReqResult, fkVoipTimerControlIndex, 
                                fkVoipTimerControlCriticalTimeout, fkVoipTimerControlFirstDigit, fkVoipTimerControlIntraDigit, fkVoipStatisticsIndex, fkVoipStatisticsFormat, 
                                fkVoipStatisticsCallTimer, fkVoipStatisticsCurrentPlayoutDelay, fkVoipStatisticsMinPlayoutDelay, fkVoipStatisticsMaxPlayoutDelay, fkVoipStatisticsClockOffset, 
                                fkVoipStatisticsPeakJitter, fkVoipStatisticsInterpolativeConcealment, fkVoipStatisticsSilenceConcealment, fkVoipStatisticsOverflowDiscard, fkVoipStatisticsEndpointDetectionErrors, 
                                fkVoipStatisticsTxVoicePackets, fkVoipStatisticsTxSignalingPackets, fkVoipStatisticsTxComfortNoisePackets, fkVoipStatisticsTotalTransmitDuration, fkVoipStatisticsVoiceTransmitDuration, 
                                fkVoipStatisticsRxVoicePackets, fkVoipStatisticsRxSignalingPackets, fkVoipStatisticsRxComfortNoisePackets, fkVoipStatisticsTotalReceiveDuration, fkVoipStatisticsVoiceReceiveDuration, 
                                fkVoipStatisticsPacketsOutSequence, fkVoipStatisticsBadProtocolHeaders, fkVoipStatisticsLatePackets, fkVoipStatisticsEarlyPackets, fkVoipStatisticsRxVoiceOctets, 
                                fkVoipStatisticsLostPackets, fkVoipStatisticsCurrentTransmitPower, fkVoipStatisticsMeanTransmitPower, fkVoipStatisticsCurrentReceivePower, fkVoipStatisticsMeanReceivePower, 
                                fkVoipStatisticsBackgroundNoise, fkVoipStatisticsErlLevel, fkVoipStatisticsAcomLevel, fkVoipStatisticsCurrentTransmitActivity, fkVoipStatisticsCurrentReceiveActivity, 
                                fkVoipDialPlanIndex, fkVoipDialPlanDigitMap, fkVoipDialPlanControlRequest, fkVoipDialPlanControlStatus, fkVoipDialPlanControlTimer, 
                                fkVoipDialPlanControlReqResult, fkVoipDialPlanControlIndex, fkVoipDialPlanControlDigitMap, fkVoipDialPlanPotStatusIndex, fkVoipDialPlanControlPotStatusIndex, 
                                fkVoipPotsStatusHookState, fkVoipPotsStatusRegisterState, fkVoipRtcp, fkVoipPotsStatus, fkVoipBaseControlInterface, 
                                fkVoipBaseControlProtocol, fkVoipMediaProfileControlReqResult, fkVoipBaseControlFaxmode, fkVoipFaxmode, fkVoipDialPlanControlTimeStamp, 
                                fkVoipBaseControlRtcp }
                        STATUS current
                        DESCRIPTION 
                                "Description."
                        ::= { fkVoip 13 }

                
                -- 1.3.6.1.4.1.10428 9 1.101.25.14
                fkVoipNotificationGroup NOTIFICATION-GROUP
                        NOTIFICATIONS { fkVoipBaseInterfaceChanged, fkVoipBaseProtocolChanged, fkVoipVoiceEnabled, fkVoipVoiceDisabled, fkVoipSipUserEnabled, 
                                fkVoipSipUserDisabled, fkVoipSipAgentEnabled, fkVoipSipAgentDisabled, fkVoipMgcpEndpointEnabled, fkVoipMgcpEndpointDisabled, 
                                fkVoipMgcpAgentEnabled, fkVoipMgcpAgentDisabled, fkVoipMediaProfileEnabled, fkVoipMediaProfileDisabled, fkVoipRtpProfilePortMinChanged, 
                                fkVoipRtpProfileDscpMarkChanged, fkVoipRtpProfileOobChanged, fkVoipRtpProfileDtmfEventChanged, fkVoipTimerEnabled, fkVoipTimerDisabled, 
                                fkVoipDialPlanEnabled, fkVoipBaseRtcpChanged, fkVoipBaseFaxmodeChanged, fkVoipDialPlanDisabled, fkVoipBaseRestartStackOnly, 
                                fkVoipBaseRestartAll }
                        STATUS current
                        DESCRIPTION 
                                "Description."
                        ::= { fkVoip 14 }

                
        
        END

--
-- fk-voip-mib.mib
--
