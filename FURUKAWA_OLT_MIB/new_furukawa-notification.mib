--
-- fkoltg1040-notification.mib

-- *****************************************************************
-- 

FKOLTG1040-NOTIFICATION DEFINITIONS ::= BEGIN

IMPORTS
    TRAP-TYPE
        FROM RFC-1215
    sysDescr, sysUpTime
        FROM SNMPv2-MIB
    ifIndex, ifDescr, ifAdminStatus
        FROM IF-MIB
    ipAdEntAddr
        FROM IP-MIB
    fkoltg1040Events
        FROM FKOLTG1040-SMI
    dsSubnetConfName
        FROM FKOLTG1040-DHCP-MIB
    dsPonOltIndex, dsPonOnuIndex, dsPonOnuMacAddress, dsPonTaggedLabel, dsPonPortIndex, dsPonDirection, dsPonState, dsPonCount, dsPonQueueIndex
        FROM FKOLTG1040-GEPON-MIB
    dsFreeMem, dsSystemUpgradePath, dsSystemUpgradeStorage, dsPortModuleIndex, dsPortPortIndex, dsPortInstallStatus, dsTemperatureStatus, dsPowerIndex, dsPowerstatus, dsFanIndex, dsFanstatus, dsUserMacAddress1, dsUserMacAddress2, dsUserMacAddress3, dsUserMacAddress4, dsSwitchAtNetAddress, dsSwitchAtMacAddress, dsSwitchAtVID, dsVdslPortIndex, dsSerialNumber
        FROM FKOLTG1040-SWITCH-MIB
    dsUserLoginName, dsUserLoginIpAddress
        FROM FKOLTG1040-USER-MANAGEMENT-MIB
    fkGponOltId, fkGponOltTransceiverPort, fkGponRedGroupIndex, fkGponRedGroupOltAIndex, fkGponRedGroupOltAStatus, fkGponRedGroupOltBIndex, fkGponRedGroupOltBStatus, fkGponRedLastReason, fkGponOnuAuthenticationStatus, fkGponOnuPortSlotId, fkGponOnuId, fkGponAntiSpoofingOltId, fkGponAntiSpoofingOnuId, fkGponOntFirmwareOltId, fkGponOnuPortControlUniDescription, fkGponAntiSpoofingMac, fkGponAntiSpoofingVlanId, fkGponOnuPortId, fkGponOltFixedTcontCount, fkGponOnuIsFirst, fkGponOltPortCount, fkGponOnuBatteryStatus, fkGponOntFirmwareOntOsStatus, fkGponOntFirmwareOntBLStatus, fkGponOnuSerial, fkGponOntFirmwareOntId, fkGponOltDynamicTcontCount, fkGponOnuPortOperStatus, fkGponOnuDescription
        FROM FK-GPON-MIB
    fkSlotSystemIndex, fkSlotStatusCurrentInstallCardType, fkSlotStatusActionEvent, fkClockModuleInitStatus, fkEthernetPortSlotIndex, fkClockModuleInstallStatus, fkClockInfoInSrcLoSStatus, fkClockInfoInSrcLDSCStatus, fkClockInfoInSrcStatus, fkClockModuleIndex, fkClockModuleOPMode, fkClockInfoInSrcNtrClockType, fkFanUnitIndex, fkClockInfoInSrcAISStatus, fkEthernetPortSlotPortIndex, fkSlotStatusState, fkSlotPowerMonStatus, fkSlotPowerMonIndex, fkClockInfoInSrcType, fkClockModuleBoardId, fkFanUnitSpeed
        FROM FK-DEVICE-MIB
    fkArpInspectInvalidLogSrcIpAddr, fkArpInspectInvalidLogPortNumber, fkArpInspectInvalidLogVlanId, fkArpInspectInvalidLogReason, fkArpInspectInvalidLogOpcode, fkArpInspectInvalidLogLastRecvTime, fkArpInspectInvalidLogDstMacAddr, fkArpInspectInvalidLogSamePktCnt, fkArpInspectInvalidLogDstIpAddr, fkArpInspectInvalidLogSrcMacAddr
        FROM FK-SECURITY-MIB
    fkY1731MegIndex, fkY1731MegRapsEastPortStatus, fkY1731MegRapsWestPortStatus, fkEMLogGPIURavenLinkDown, fkEMLogFanFail, fkEMLogDaemonHealthBad, fkY1731URMegIndex, fkEMLogMemLow, fkY1731URNodeConfPortStatus, fkEMLogSFUMateInitFail, fkEMLogTemperLow, fkY1731URNodeConfPortNum, fkEMLogPhyDetectFail, fkEMLogPhyCRCFail, fkEMLogDefectCPUHigh, fkEMLogTemperHigh
        FROM FK-FAULTMGMT-MIB
    fkPerformanceBaseCpuPpsThreshold, fkPerformanceBaseCpuPpsStatus, fkPerformanceBaseCpuPpsAvg
        FROM FK-PERFORMANCEMGMT-MIB
    fkBFDSessionStatus, fkBFDSessionNeighAddrType, fkBFDSessionNeighAddrValue
        FROM FK-NETWORK-MIB
    fkRedActiveCurrState, fkRedActivePrevState, fkRedActiveBoard
        FROM FK-RED-MIB
    fkSnmpConnectionType, fkAgentAddress
        FROM FK-SNMP-MIB    
    fkNTPServerName, fkSwWatchdogType, fkAutoResetBootReason
        FROM FK-SYSTEMMAINTENANCE-MIB
    fkBridgePortIndex
        FROM FK-BRIDGE-MIB
    dsIgmpSnoopingEnabled
        FROM FKOLTG1040-MCAST-MIB;

--
-- Node definitions
--

--  Node definitions
-- 
-- Node definitions
-- 
       
        -- 1.3.6.1.4.1.10428 9 1.0.1
        portInstalled TRAP-TYPE
                ENTERPRISE  fkoltg1040Events
                VARIABLES { ifIndex, dsPortInstallStatus }
                DESCRIPTION 
                        "portI0nstalled trap send when portInstallStatus is enabled."
                ::= 1
        
        -- 1.3.6.1.4.1.10428 9 1.0.2
        portRemoved TRAP-TYPE
                ENTERPRISE  fkoltg1040Events
                VARIABLES { ifIndex, dsPortInstallStatus }
                DESCRIPTION 
                        "portInstalled trap send when portInstallStatus is disabled."
                ::= 2
        
        -- 1.3.6.1.4.1.10428 9 1.0.3
        powerOk TRAP-TYPE
                ENTERPRISE  fkoltg1040Events
                VARIABLES { dsPowerIndex, dsPowerstatus }
                DESCRIPTION 
                        "Power status OK trap when powerStatus change from disable to enable."
                ::= 3
        
        -- 1.3.6.1.4.1.10428 9 1.0.4
        powerFail TRAP-TYPE
                ENTERPRISE  fkoltg1040Events
                VARIABLES { dsPowerIndex, dsPowerstatus }
                DESCRIPTION 
                        "Power status fail trap when powerStatus change from enable to disable."
                ::= 4
        
        -- 1.3.6.1.4.1.10428 9 1.0.5
        fanOk TRAP-TYPE
                ENTERPRISE  fkoltg1040Events
                VARIABLES { dsFanIndex, dsFanstatus }
                DESCRIPTION 
                        "Fan status OK trap when fanStatus change from disable to enable."
                ::= 5
        
        -- 1.3.6.1.4.1.10428 9 1.0.6
        fanFail TRAP-TYPE
                ENTERPRISE  fkoltg1040Events
                VARIABLES { dsFanIndex, dsFanstatus }
                DESCRIPTION 
                        "Fan status fail trap when fanStatus change from enable to disable."
                ::= 6
        
        -- 1.3.6.1.4.1.10428 9 1.0.7
        powerInstalled TRAP-TYPE
                ENTERPRISE  fkoltg1040Events
                VARIABLES { dsPowerIndex }
                DESCRIPTION 
                        "Power Installed trap when power was installed."
                ::= 7
        
        -- 1.3.6.1.4.1.10428 9 1.0.8
        powerRemoved TRAP-TYPE
                ENTERPRISE  fkoltg1040Events
                VARIABLES { dsPowerIndex }
                DESCRIPTION 
                        "Power removed trap when power was removed."
                ::= 8
        
        -- 1.3.6.1.4.1.10428 9 1.0.9
        fanInstalled TRAP-TYPE
                ENTERPRISE  fkoltg1040Events
                DESCRIPTION 
                        "Fan Installed trap when fan was installed."
                ::= 9
        
        -- 1.3.6.1.4.1.10428 9 1.0.10
        fanRemoved TRAP-TYPE
                ENTERPRISE  fkoltg1040Events
                DESCRIPTION 
                        "Fan removed trap when fan was removed."
                ::= 10
        
        -- 1.3.6.1.4.1.10428 9 1.0.11
        bcastOver TRAP-TYPE
                ENTERPRISE  fkoltg1040Events
                VARIABLES { sysDescr }
                DESCRIPTION 
                        "Broadcast packet over trap when Rx broadcast packet is over the given limit."
                ::= 11
        
        -- 1.3.6.1.4.1.10428 9 1.0.12
        cpuLoadOverThreshold TRAP-TYPE
                ENTERPRISE  fkoltg1040Events
                VARIABLES { sysDescr }
                DESCRIPTION 
                        "The cpuLoadOverThreshold trap is sent when cpuLoad is over the given limit."
                ::= 12
        
        -- 1.3.6.1.4.1.10428 9 1.0.13
        cpuLoadFallThreshold TRAP-TYPE
                ENTERPRISE  fkoltg1040Events
                VARIABLES { sysDescr }
                DESCRIPTION 
                        "The cpuLoadfallThreshold trap is sent when cpuLoad fall under the given limit."
                ::= 13
        
        -- 1.3.6.1.4.1.10428 9 1.0.14
        dhcpLeaseShortage TRAP-TYPE
                ENTERPRISE  fkoltg1040Events
                VARIABLES { sysDescr, dsSubnetConfName }
                DESCRIPTION 
                        "DHCP User IP pool shortage when User's DHCPDISCOVER message arrive."
                ::= 14
        
        -- 1.3.6.1.4.1.10428 9 1.0.15
        portOverThreshold TRAP-TYPE
                ENTERPRISE  fkoltg1040Events
                VARIABLES { ifIndex }
                DESCRIPTION 
                        "Port traffic over HighThreshold trap when port traffic is over the given limit."
                ::= 15
        
        -- 1.3.6.1.4.1.10428 9 1.0.16
        portFallThreshold TRAP-TYPE
                ENTERPRISE  fkoltg1040Events
                VARIABLES { ifIndex }
                DESCRIPTION 
                        "Port traffic fall under HighThreshold trap when port traffic falls below the given limit."
                ::= 16
        
        -- 1.3.6.1.4.1.10428 9 1.0.17
        temperatureOverThreshold TRAP-TYPE
                ENTERPRISE  fkoltg1040Events
                VARIABLES { dsTemperatureStatus }
                DESCRIPTION 
                        "TemperatureOverThreshold Trap is sent when temperature is over the certain threshold."
                ::= 17
        
        -- 1.3.6.1.4.1.10428 9 1.0.18
        systemRestart TRAP-TYPE
                ENTERPRISE  fkoltg1040Events
                VARIABLES { sysDescr, fkAutoResetBootReason }
                DESCRIPTION 
                        "SystemRestart Trap is sent when system is restarted by
                        user. fkAutoResetBootReason is only used for auto-reset"
                ::= 18
        
        -- 1.3.6.1.4.1.10428 9 1.0.19
        mfgdBlocked TRAP-TYPE
                ENTERPRISE  fkoltg1040Events
                VARIABLES { dsSwitchAtMacAddress, dsSwitchAtNetAddress, dsSwitchAtVID }
                DESCRIPTION 
                        "mfgdblocked Trap is sent when a certain mac address is denied by mac-flood-guard mechanism."
                ::= 19
        
        -- 1.3.6.1.4.1.10428 9 1.0.20
        mfgdReleased TRAP-TYPE
                ENTERPRISE  fkoltg1040Events
                VARIABLES { dsSwitchAtMacAddress, dsSwitchAtNetAddress, dsSwitchAtVID }
                DESCRIPTION 
                        "mfgdReleased Trap is sent when a certain mac address is permitted again by mac-flood-guard mechanism."
                ::= 20
        
        -- 1.3.6.1.4.1.10428 9 1.0.21
        ipConflict TRAP-TYPE
                ENTERPRISE  fkoltg1040Events
                VARIABLES { dsSwitchAtNetAddress, dsSwitchAtMacAddress }
                DESCRIPTION 
                        "ipConflict Trap is sent when a certain IP address is shared among different users."
                ::= 21
        
        -- 1.3.6.1.4.1.10428 9 1.0.22
        dhcpIllegalEntry TRAP-TYPE
                ENTERPRISE  fkoltg1040Events
                VARIABLES { dsSwitchAtNetAddress, dsSwitchAtMacAddress, ifIndex }
                DESCRIPTION 
                        "dhcpIllegalEntry trap is sent when illegal dhcp user is found."
                ::= 22
        
        -- 1.3.6.1.4.1.10428 9 1.0.23
        optionModuleInstalled TRAP-TYPE
                ENTERPRISE  fkoltg1040Events
                VARIABLES { ifIndex }
                DESCRIPTION 
                        "optionModuleInstalled Trap is sent when option Module was installed."
                ::= 23
        
        -- 1.3.6.1.4.1.10428 9 1.0.24
        optionModuleRemoved TRAP-TYPE
                ENTERPRISE  fkoltg1040Events
                VARIABLES { ifIndex }
                DESCRIPTION 
                        "optionModuleRemoved Trap is sent when option Module was removed."
                ::= 24
        
        -- 1.3.6.1.4.1.10428 9 1.0.25
        memoryOverThreshold TRAP-TYPE
                ENTERPRISE  fkoltg1040Events
                VARIABLES { sysDescr, dsFreeMem }
                DESCRIPTION 
                        "MemoryOverThreshold trap is sent when used memory size is over the given limit 
                        and free memory size falls below the given limit."
                ::= 25
        
        -- 1.3.6.1.4.1.10428 9 1.0.26
        memoryFallThreshold TRAP-TYPE
                ENTERPRISE  fkoltg1040Events
                VARIABLES { sysDescr, dsFreeMem }
                DESCRIPTION 
                        "MemoryFallThreshold trap is sent when free memory size is over the given limit."
                ::= 26
        
        -- 1.3.6.1.4.1.10428 9 1.0.27
        slotInstalled TRAP-TYPE
                ENTERPRISE  fkoltg1040Events
                VARIABLES { ifIndex }
                DESCRIPTION 
                        "slotInstalled Trap is sent when Board was installed."
                ::= 27
        
        -- 1.3.6.1.4.1.10428 9 1.0.28
        slotRemoved TRAP-TYPE
                ENTERPRISE  fkoltg1040Events
                VARIABLES { ifIndex }
                DESCRIPTION 
                        "slotRemoved Trap is sent when Board was removed."
                ::= 28
        
        -- 1.3.6.1.4.1.10428 9 1.0.29
        slotStateChange TRAP-TYPE
                ENTERPRISE  fkoltg1040Events
                VARIABLES { ifIndex }
                DESCRIPTION 
                        "slotStateChangeTrap Trap is sent when Board State change."
                ::= 29
        
        -- 1.3.6.1.4.1.10428 9 1.0.30
        portCRCOverThreshold TRAP-TYPE
                ENTERPRISE  fkoltg1040Events
                VARIABLES { ifIndex }
                DESCRIPTION 
                        "portCRCOverThreshold Trap is sent when the CRC count of
                        port over threshold."
                ::= 30
        
        -- 1.3.6.1.4.1.10428 9 1.0.31
        portCRCFallThreshold TRAP-TYPE
                ENTERPRISE  fkoltg1040Events
                VARIABLES { ifIndex }
                DESCRIPTION 
                        "portCRCOverThreshold Trap is sent when the CRC count of
                        port fall threshold."
                ::= 31
        
--     Newly Add traps related to temperature.
-- 
        -- 1.3.6.1.4.1.10428 9 1.0.32
        temperatureHighOverThreshold TRAP-TYPE
                ENTERPRISE  fkoltg1040Events
                VARIABLES { dsTemperatureStatus }
                DESCRIPTION 
                        "The temperatureHighOverThreshold Trap is sent when temperature is over the high-threshold."
                ::= 32
        
        -- 1.3.6.1.4.1.10428 9 1.0.33
        temperatureHighFallThreshold TRAP-TYPE
                ENTERPRISE  fkoltg1040Events
                VARIABLES { dsTemperatureStatus }
                DESCRIPTION 
                        "The temperatureHighFallThreshold Trap is sent when temperature fall the high-threshold."
                ::= 33
        
        -- 1.3.6.1.4.1.10428 9 1.0.34
        temperatureLowOverThreshold TRAP-TYPE
                ENTERPRISE  fkoltg1040Events
                VARIABLES { dsTemperatureStatus }
                DESCRIPTION 
                        "The temperatureLowOverThreshold Trap is sent when 1st temperature is over the low-threshold."
                ::= 34
        
        -- 1.3.6.1.4.1.10428 9 1.0.35
        temperatureLowFallThreshold TRAP-TYPE
                ENTERPRISE  fkoltg1040Events
                VARIABLES { dsTemperatureStatus }
                DESCRIPTION 
                        "The temperatureLowFallThreshold Trap is sent when temperature fall under the low-threshold."
                ::= 35
        
        -- 1.3.6.1.4.1.10428 9 1.0.36
        userLogIn TRAP-TYPE
                ENTERPRISE  fkoltg1040Events
                VARIABLES { dsUserLoginName, dsUserLoginIpAddress }
                DESCRIPTION 
                        "The user-login trap is sent when user login."
                ::= 36
        
        -- 1.3.6.1.4.1.10428 9 1.0.37
        userLogOut TRAP-TYPE
                ENTERPRISE  fkoltg1040Events
                VARIABLES { dsUserLoginName, dsUserLoginIpAddress }
                DESCRIPTION 
                        "The user-logout trap is sent when user logout."
                ::= 37
        
        -- 1.3.6.1.4.1.10428 9 1.0.38
        restoreFactory TRAP-TYPE
                ENTERPRISE  fkoltg1040Events
                VARIABLES { sysDescr }
                DESCRIPTION 
                        "The restoreFactory trap is sent when user initialize as factory defaults."
                ::= 38
        
        -- 1.3.6.1.4.1.10428 9 1.0.39
        cpuLoadHighOverThreshold TRAP-TYPE
                ENTERPRISE  fkoltg1040Events
                VARIABLES { sysDescr }
                DESCRIPTION 
                        "The cpuloadHighOverThreshold Trap is sent when temperature is over the high-threshold."
                ::= 39
        
        -- 1.3.6.1.4.1.10428 9 1.0.40
        cpuLoadHighFallThreshold TRAP-TYPE
                ENTERPRISE  fkoltg1040Events
                VARIABLES { sysDescr }
                DESCRIPTION 
                        "The cpuloadHighFallThreshold Trap is sent when temperature fall the high-threshold."
                ::= 40
        
        -- 1.3.6.1.4.1.10428 9 1.0.41
        cpuLoadLowOverThreshold TRAP-TYPE
                ENTERPRISE  fkoltg1040Events
                VARIABLES { sysDescr }
                DESCRIPTION 
                        "The cpuloadLowOverThreshold Trap is sent when 1st temperature is over the low-threshold."
                ::= 41
        
        -- 1.3.6.1.4.1.10428 9 1.0.42
        cpuLoadLowFallThreshold TRAP-TYPE
                ENTERPRISE  fkoltg1040Events
                VARIABLES { sysDescr }
                DESCRIPTION 
                        "The cpuloadLowFallThreshold Trap is sent when temperature fall under the low-threshold."
                ::= 42
        
        igmpSnoopingChanged TRAP-TYPE
                ENTERPRISE fkoltg1040Events
                VARIABLES { dsIgmpSnoopingEnabled }
                DESCRIPTION 
                            " "
                ::= 43
        
        -- 1.3.6.1.4.1.10428 9 1.0.44
        dsSystemUpgradeChanged TRAP-TYPE
                ENTERPRISE  fkoltg1040Events
                VARIABLES { sysDescr }
                DESCRIPTION 
                        "System NOS Upgrade status"
                ::= 44
        
        -- 1.3.6.1.4.1.10428 9 1.0.51
        adslAtucPerfLofsThresh TRAP-TYPE
                ENTERPRISE  fkoltg1040Events
                VARIABLES { sysUpTime }
                DESCRIPTION 
                        "Loss of Framing threshold reached(ATUC)."
                ::= 51
        
        -- 1.3.6.1.4.1.10428 9 1.0.52
        adslAtucPerfLossThresh TRAP-TYPE
                ENTERPRISE  fkoltg1040Events
                VARIABLES { sysUpTime }
                DESCRIPTION 
                        "Loss of signal threshold reached(ATUC)."
                ::= 52
        
        -- 1.3.6.1.4.1.10428 9 1.0.53
        adslAtucPerfLprsThresh TRAP-TYPE
                ENTERPRISE  fkoltg1040Events
                VARIABLES { sysUpTime }
                DESCRIPTION 
                        "Loss of power threshold reached (ATUC)."
                ::= 53
        
        -- 1.3.6.1.4.1.10428 9 1.0.54
        adslAtucPerfESsThresh TRAP-TYPE
                ENTERPRISE  fkoltg1040Events
                VARIABLES { sysUpTime }
                DESCRIPTION 
                        "Errored Seconds threshold reached (ATUC)."
                ::= 54
        
        -- 1.3.6.1.4.1.10428 9 1.0.55
        adslAtucRateChange TRAP-TYPE
                ENTERPRISE  fkoltg1040Events
                VARIABLES { sysUpTime }
                DESCRIPTION 
                        "Changed atuc rate."
                ::= 55
        
        -- 1.3.6.1.4.1.10428 9 1.0.56
        adslAtucPerfLolsThresh TRAP-TYPE
                ENTERPRISE  fkoltg1040Events
                VARIABLES { sysUpTime }
                DESCRIPTION 
                        "Loss of Link threshold reached (ATUC)."
                ::= 56
        
        -- 1.3.6.1.4.1.10428 9 1.0.61
        adslAturPerfLofsThresh TRAP-TYPE
                ENTERPRISE  fkoltg1040Events
                VARIABLES { sysUpTime }
                DESCRIPTION 
                        "Loss of Framing threshold reached(ATUR)."
                ::= 61
        
        -- 1.3.6.1.4.1.10428 9 1.0.62
        adslAturPerfLossThresh TRAP-TYPE
                ENTERPRISE  fkoltg1040Events
                VARIABLES { sysUpTime }
                DESCRIPTION 
                        "Loss of signal threshold reached(ATUR)."
                ::= 62
        
        -- 1.3.6.1.4.1.10428 9 1.0.63
        adslAturPerfLprsThresh TRAP-TYPE
                ENTERPRISE  fkoltg1040Events
                VARIABLES { sysUpTime }
                DESCRIPTION 
                        "Loss of power threshold reached (ATUR)."
                ::= 63
        
        -- 1.3.6.1.4.1.10428 9 1.0.64
        adslAturPerfESsThresh TRAP-TYPE
                ENTERPRISE  fkoltg1040Events
                VARIABLES { sysUpTime }
                DESCRIPTION 
                        "Errored Seconds threshold reached (ATUR)."
                ::= 64
        
        -- 1.3.6.1.4.1.10428 9 1.0.65
        vdslCPEChangeInfo TRAP-TYPE
                ENTERPRISE  fkoltg1040Events
                VARIABLES { sysDescr, ipAdEntAddr, dsVdslPortIndex, dsSerialNumber, dsUserMacAddress1, 
                        dsUserMacAddress2, dsUserMacAddress3, dsUserMacAddress4 }
                DESCRIPTION 
                        "Trap is sent with CPE Serial No., Mac Address of CPE, after CPE serial change.  "
                ::= 65
        
        -- 1.3.6.1.4.1.10428 9 1.0.66
        vdslArulePacketDrop TRAP-TYPE
                ENTERPRISE  fkoltg1040Events
                VARIABLES { sysUpTime }
                DESCRIPTION 
                        "Packet Dropped by arule .  "
                ::= 66
        
--    flood-guard (CPU|SYSTEM) 
-- 
        -- 1.3.6.1.4.1.10428 9 1.0.71
        cfgdBlocked TRAP-TYPE
                ENTERPRISE  fkoltg1040Events
                VARIABLES { ifIndex }
                DESCRIPTION 
                        "Cfgdblocked Trap is sent when a certain port is blocked by cpu-flood-guard mechanism."
                ::= 71
        
        -- 1.3.6.1.4.1.10428 9 1.0.72
        cfgdReleased TRAP-TYPE
                ENTERPRISE  fkoltg1040Events
                VARIABLES { ifIndex }
                DESCRIPTION 
                        "CfgdReleased Trap is sent when a certain port is non-blocked by cpu-flood-guard mechanism."
                ::= 72
        
        -- 1.3.6.1.4.1.10428 9 1.0.73
        cfgdOverThreshold TRAP-TYPE
                ENTERPRISE  fkoltg1040Events
                VARIABLES { ifIndex }
                DESCRIPTION 
                        "CfgdReleased Trap is sent when a certain port is over threshold by cpu-flood-guard mechanism."
                ::= 73
        
        -- 1.3.6.1.4.1.10428 9 1.0.74
        cfgdUnderThreshold TRAP-TYPE
                ENTERPRISE  fkoltg1040Events
                VARIABLES { ifIndex }
                DESCRIPTION 
                        "CfgdReleased Trap is sent when a certain port is under threshold by cpu-flood-guard mechanism."
                ::= 74
        
        -- 1.3.6.1.4.1.10428 9 1.0.75
        sfgdBlocked TRAP-TYPE
                ENTERPRISE  fkoltg1040Events
                VARIABLES { ifIndex }
                DESCRIPTION 
                        "Sfgdblocked Trap is sent when a certain port is blocked by system-flood-guard mechanism."
                ::= 75
        
        -- 1.3.6.1.4.1.10428 9 1.0.76
        sfgdReleased TRAP-TYPE
                ENTERPRISE  fkoltg1040Events
                VARIABLES { ifIndex }
                DESCRIPTION 
                        "SfgdReleased Trap is sent when a certain port is non-blocked by system-flood-guard mechanism."
                ::= 76
        
        -- 1.3.6.1.4.1.10428 9 1.0.77
        sfgdOverThreshold TRAP-TYPE
                ENTERPRISE  fkoltg1040Events
                VARIABLES { ifIndex }
                DESCRIPTION 
                        "SfgdReleased Trap is sent when a certain port is over threshold by system-flood-guard mechanism."
                ::= 77
        
        -- 1.3.6.1.4.1.10428 9 1.0.78
        sfgdUnderThreshold TRAP-TYPE
                ENTERPRISE  fkoltg1040Events
                VARIABLES { ifIndex }
                DESCRIPTION 
                        "SfgdReleased Trap is sent when a certain port is under threshold by system-flood-guard mechanism."
                ::= 78
        
        -- 1.3.6.1.4.1.10428 9 1.0.79
        ppsControlBlocked TRAP-TYPE
                ENTERPRISE  fkoltg1040Events
                VARIABLES { ifIndex }
                DESCRIPTION 
                        "PpsControlblocked Trap is sent when a certain port is blocked by PPS-Control mechanism."
                ::= 79
        
        -- 1.3.6.1.4.1.10428 9 1.0.80
        ppsControlReleased TRAP-TYPE
                ENTERPRISE  fkoltg1040Events
                VARIABLES { ifIndex }
                DESCRIPTION 
                        "PpsControlReleased Trap is sent when a certain port is non-blocked by PPS-Control mechanism."
                ::= 80
        
        -- 1.3.6.1.4.1.10428 9 1.0.81
        ppsControlOverThreshold TRAP-TYPE
                ENTERPRISE  fkoltg1040Events
                VARIABLES { ifIndex }
                DESCRIPTION
                        "PpsControlReleased Trap is sent when a certain port is over threshold by PPS-Control mechanism."
                ::= 81
        
        -- 1.3.6.1.4.1.10428 9 1.0.82
        ppsControlUnderThreshold TRAP-TYPE
                ENTERPRISE  fkoltg1040Events
                VARIABLES { ifIndex }
                DESCRIPTION
                        "PpsControlReleased Trap is sent when a certain port is under threshold by PPS-Control mechanism."
                ::= 82
        
--    remote upgrade
-- 
        -- 1.3.6.1.4.1.10428 9 1.0.83
        nosRemoteUpgradeRequest TRAP-TYPE
                ENTERPRISE  fkoltg1040Events
                VARIABLES { sysDescr, dsSystemUpgradePath, dsSystemUpgradeStorage }
                DESCRIPTION 
                        "This trap indicates that the system received nos-remote-upgrade command."
                ::= 83
        
        -- 1.3.6.1.4.1.10428 9 1.0.84
        nosRemoteUpgradeSuccess TRAP-TYPE
                ENTERPRISE  fkoltg1040Events
                VARIABLES { sysDescr, dsSystemUpgradePath, dsSystemUpgradeStorage }
                DESCRIPTION 
                        "This trap indicates that the NOS succeeded to upgrade NOS."
                ::= 84
        
        -- 1.3.6.1.4.1.10428 9 1.0.85
        nosRemoteUpgradeFailAbort TRAP-TYPE
                ENTERPRISE  fkoltg1040Events
                VARIABLES { sysDescr, dsSystemUpgradePath, dsSystemUpgradeStorage }
                DESCRIPTION 
                        "This trap indicates that the system failed to upgrade NOS by user interrupt"
                ::= 85
        
        -- 1.3.6.1.4.1.10428 9 1.0.86
        nosRemoteUpgradeFailHeaderError TRAP-TYPE
                ENTERPRISE  fkoltg1040Events
                VARIABLES { sysDescr, dsSystemUpgradePath, dsSystemUpgradeStorage }
                DESCRIPTION 
                        "This trap indicates that the system failed to upgrade NOS, for NOS header-error."
                ::= 86
        
        -- 1.3.6.1.4.1.10428 9 1.0.87
        nosRemoteUpgradeFailDownloadError TRAP-TYPE
                ENTERPRISE  fkoltg1040Events
                VARIABLES { sysDescr, dsSystemUpgradePath, dsSystemUpgradeStorage }
                DESCRIPTION 
                        "This trap indicates that the system failed to upgrade NOS, for NOS checksum-error"
                ::= 87
        
        -- 1.3.6.1.4.1.10428 9 1.0.88
        nosRemoteUpgradeFailFlashError TRAP-TYPE
                ENTERPRISE  fkoltg1040Events
                VARIABLES { sysDescr, dsSystemUpgradePath, dsSystemUpgradeStorage }
                DESCRIPTION 
                        "This trap indicates that the system failed to upgrade NOS, for flash operation"
                ::= 88
        
        -- 1.3.6.1.4.1.10428 9 1.0.89
        nosRemoteUpgradeStart TRAP-TYPE
                ENTERPRISE  fkoltg1040Events
                VARIABLES { sysDescr, dsSystemUpgradePath, dsSystemUpgradeStorage }
                DESCRIPTION 
                        "This trap indicates that the upgrade NOS process was started."
                ::= 89
        
--    Dying gasp for power fault 
        -- 1.3.6.1.4.1.10428 9 1.0.90
        systemDyingGasp TRAP-TYPE
                ENTERPRISE  fkoltg1040Events
                VARIABLES { sysDescr }
                DESCRIPTION 
                        "This trap indicates that Dying-gasp for power fault."
                ::= 90
        
--    Attack-Guard 
        -- 1.3.6.1.4.1.10428 9 1.0.91
        attackGuardBlock TRAP-TYPE
                ENTERPRISE  fkoltg1040Events
                VARIABLES { dsPortModuleIndex, dsPortPortIndex }
                DESCRIPTION 
                        "This trap indicates that some port is blocked by attack-guard."
                ::= 91
        
        -- 1.3.6.1.4.1.10428 9 1.0.92
        attackGuardUnBlock TRAP-TYPE
                ENTERPRISE  fkoltg1040Events
                VARIABLES { dsPortModuleIndex, dsPortPortIndex }
                DESCRIPTION 
                        "This trap indicates that some port is unblocked by attack-guard."
                ::= 92
        
        -- 1.3.6.1.4.1.10428 9 1.0.93
        fanPeriodicFault TRAP-TYPE
                ENTERPRISE  fkoltg1040Events
                VARIABLES { dsFanIndex, dsFanstatus }
                DESCRIPTION 
                        "This trap indicates the fan status is fault in some period."
                ::= 93
        
        -- 1.3.6.1.4.1.10428 9 1.0.94
        remoteOamDyingGasp TRAP-TYPE
                ENTERPRISE  fkoltg1040Events
                VARIABLES { ifIndex }
                DESCRIPTION 
                        "This trap indicates the remote oam entity is in dying-gasp ."
                ::= 94
        
        -- 1.3.6.1.4.1.10428 9 1.0.95
        remoteOamDyingGaspRestoration TRAP-TYPE
                ENTERPRISE  fkoltg1040Events
                VARIABLES { ifIndex }
                DESCRIPTION 
                        "This trap indicates the remote oam entity is restored."
                ::= 95
        
        -- 1.3.6.1.4.1.10428 9 1.0.96
        arpInspectInvalid TRAP-TYPE
                ENTERPRISE  fkoltg1040Events
                VARIABLES { fkArpInspectInvalidLogReason, fkArpInspectInvalidLogSamePktCnt, fkArpInspectInvalidLogOpcode, fkArpInspectInvalidLogPortNumber, fkArpInspectInvalidLogVlanId, 
                        fkArpInspectInvalidLogSrcMacAddr, fkArpInspectInvalidLogSrcIpAddr, fkArpInspectInvalidLogDstMacAddr, fkArpInspectInvalidLogDstIpAddr, fkArpInspectInvalidLogLastRecvTime
                         }
                DESCRIPTION 
                        "This trap indicates the ARP inspection is invalided."
                ::= 96
        
        -- 1.3.6.1.4.1.10428 9 1.0.97
        systemSwitchover TRAP-TYPE
                ENTERPRISE  fkoltg1040Events
                VARIABLES { sysDescr }
                DESCRIPTION 
                        "This trap indicates the system is switchover."
                ::= 97
        
        -- 1.3.6.1.4.1.10428 9 1.0.98
        boardChangeState TRAP-TYPE
                ENTERPRISE  fkoltg1040Events
                VARIABLES { fkRedActiveBoard, fkRedActivePrevState, fkRedActiveCurrState }
                DESCRIPTION 
                        "This trap indicates the board state is changed."
                ::= 98
        -- 1.3.6.1.4.1.10428 9 1.0.99
        redConfigurationMisMatch TRAP-TYPE
                ENTERPRISE  fkoltg1040Events
                VARIABLES {sysDescr}
                DESCRIPTION
                "Configurations of Active and Standby SFU are different."
                ::= 99


--    100, 101 reserved as FK
-- 
        -- 1.3.6.1.4.1.10428 9 1.0.105
        clockModuleInstalled TRAP-TYPE
                ENTERPRISE  fkoltg1040Events
                VARIABLES { fkClockModuleIndex, fkClockModuleBoardId, fkClockModuleInstallStatus }
                DESCRIPTION 
                        "clockModuleInstalled trap send when fkClockModuleInstallStatus is installed."
                ::= 105
        
        -- 1.3.6.1.4.1.10428 9 1.0.106
        clockModuleRemoved TRAP-TYPE
                ENTERPRISE  fkoltg1040Events
                VARIABLES { fkClockModuleIndex, fkClockModuleBoardId, fkClockModuleInstallStatus }
                DESCRIPTION 
                        "clockModuleRemoved trap send when fkClockModuleInstallStatus is removed."
                ::= 106
        
        -- 1.3.6.1.4.1.10428 9 1.0.107
        clockModuleInitOk TRAP-TYPE
                ENTERPRISE  fkoltg1040Events
                VARIABLES { fkClockModuleIndex, fkClockModuleBoardId, fkClockModuleInitStatus }
                DESCRIPTION 
                        "clockModuleInitOk trap send when fkClockModuleInitStatus is ok."
                ::= 107
        
        -- 1.3.6.1.4.1.10428 9 1.0.108
        clockModuleInitFail TRAP-TYPE
                ENTERPRISE  fkoltg1040Events
                VARIABLES { fkClockModuleIndex, fkClockModuleBoardId, fkClockModuleInitStatus }
                DESCRIPTION 
                        "clockModuleInitFail trap send when fkClockModuleInitStatus is failure."
                ::= 108
        
        -- 1.3.6.1.4.1.10428 9 1.0.109
        interfaceAdminUp TRAP-TYPE
                ENTERPRISE  fkoltg1040Events
                VARIABLES { ifIndex, ifDescr, ifAdminStatus }
                DESCRIPTION 
                        "This trap indicates the interface admin up."
                ::= 109
        
        -- 1.3.6.1.4.1.10428 9 1.0.110
        interfaceAdminDown TRAP-TYPE
                ENTERPRISE  fkoltg1040Events
                VARIABLES { ifIndex, ifDescr, ifAdminStatus }
                DESCRIPTION 
                        "This trap indicates the interface admin down."
                ::= 110
        
        -- 1.3.6.1.4.1.10428 9 1.0.111
        powerMonEventDetected TRAP-TYPE
                ENTERPRISE  fkoltg1040Events
                VARIABLES { fkSlotPowerMonIndex, fkSlotPowerMonStatus }
                DESCRIPTION 
                        "This trap indicates the power monitoring detects voltage change of slot."
                ::= 111
        
        -- 1.3.6.1.4.1.10428 9 1.0.112
        ntpConnectionFail TRAP-TYPE
                ENTERPRISE  fkoltg1040Events
                VARIABLES { fkNTPServerName }
                DESCRIPTION 
                        "This trap indicates the ntp connection is lost."
                ::= 112
        
        -- 1.3.6.1.4.1.10428 9 1.0.113
        fanSpeedFallUnderThreshold TRAP-TYPE
                ENTERPRISE  fkoltg1040Events
                VARIABLES { fkFanUnitIndex, fkFanUnitSpeed }
                DESCRIPTION 
                        "This trap indicates the fan speed is under the threshold."
                ::= 113
        
        -- 1.3.6.1.4.1.10428 9 1.0.114
        fanSpeedRisingOverThreshold TRAP-TYPE
                ENTERPRISE  fkoltg1040Events
                VARIABLES { fkFanUnitIndex, fkFanUnitSpeed }
                DESCRIPTION 
                        "This trap indicates the fan speed is over the threshold."
                ::= 114
        
        -- 1.3.6.1.4.1.10428 9 1.0.115
        userLoginFail TRAP-TYPE
                ENTERPRISE  fkoltg1040Events
                VARIABLES { dsUserLoginName, dsUserLoginIpAddress }
                DESCRIPTION 
                        "This trap indicates the user fail to login."
                ::= 115
        
        -- 1.3.6.1.4.1.10428 9 1.0.116
        bfdSessionStateChanged TRAP-TYPE
                ENTERPRISE  fkoltg1040Events
                VARIABLES { ifIndex, fkBFDSessionNeighAddrType, fkBFDSessionNeighAddrValue, fkBFDSessionStatus }
                DESCRIPTION 
                        "This trap indicates that BFD session state is changed."
                ::= 116

        clockModuleOPModeChanged TRAP-TYPE
                ENTERPRISE  fkoltg1040Events
            VARIABLES {
                fkClockModuleIndex, fkClockModuleOPMode, fkSlotSystemIndex
            }
            DESCRIPTION
                     "This trap indicate that slot Operation mode is changed."
            ::= 117
        clockModuleRefrencesChanged TRAP-TYPE
                ENTERPRISE  fkoltg1040Events
            VARIABLES {
                fkClockModuleIndex, fkSlotSystemIndex
            }
            DESCRIPTION
                     "This trap indicate that slot reference ntr is changed."
            ::= 118
        -- 1.3.6.1.4.1.10428 9 1.0.119
        portOperUp TRAP-TYPE
                ENTERPRISE  fkoltg1040Events
            VARIABLES {
                fkEthernetPortSlotIndex,fkEthernetPortSlotPortIndex 
            }
            DESCRIPTION
                     "This trap indicate that port operation
                     is up."
            ::= 119
        -- 1.3.6.1.4.1.10428 9 1.0.120
        portOperDown TRAP-TYPE
                ENTERPRISE  fkoltg1040Events
            VARIABLES {
                fkEthernetPortSlotIndex,fkEthernetPortSlotPortIndex 
            }
            DESCRIPTION
                     "This trap indicate that port operation
                     is down"
            ::= 120

        -- 1.3.6.1.4.1.10428 9 1.0.121
        portRxOverThreshold TRAP-TYPE
                ENTERPRISE  fkoltg1040Events
                VARIABLES { ifIndex }
                DESCRIPTION 
                        "Port Rx traffic over HighThreshold trap when port traffic is over the given limit."
                ::= 121

        -- 1.3.6.1.4.1.10428 9 1.0.122
        portRxFallThreshold TRAP-TYPE
                ENTERPRISE  fkoltg1040Events
                VARIABLES { ifIndex }
                DESCRIPTION 
                        "Port Rx traffic fall under HighThreshold trap when port traffic falls below the given limit."
                ::= 122

        -- 1.3.6.1.4.1.10428 9 1.0.123
        portTxOverThreshold TRAP-TYPE
                ENTERPRISE  fkoltg1040Events
                VARIABLES { ifIndex }
                DESCRIPTION 
                        "Port Tx traffic over HighThreshold trap when port traffic is over the given limit."
                ::= 123

        -- 1.3.6.1.4.1.10428 9 1.0.124
        portTxFallThreshold TRAP-TYPE
                ENTERPRISE  fkoltg1040Events
                VARIABLES { ifIndex }
                DESCRIPTION 
                        "Port Tx traffic fall under HighThreshold trap when port traffic falls below the given limit."
                ::= 124

        clockModuleInSrcStatusChanged TRAP-TYPE
                ENTERPRISE  fkoltg1040Events
            VARIABLES {
                fkClockModuleIndex, fkClockInfoInSrcType, fkClockInfoInSrcStatus
            }
            DESCRIPTION
                     "This trap indicate that module status is changed."
            ::= 125
        clockModuleInSrcAISStatusChanged TRAP-TYPE
                ENTERPRISE  fkoltg1040Events
            VARIABLES {
                fkClockModuleIndex, fkClockInfoInSrcType, fkClockInfoInSrcAISStatus
            }
            DESCRIPTION
                     "This trap indicate that AIS status is changed."
            ::= 126
        clockModuleInSrcLoSStatusChanged TRAP-TYPE
                ENTERPRISE  fkoltg1040Events
            VARIABLES {
                fkClockModuleIndex, fkClockInfoInSrcType, fkClockInfoInSrcLoSStatus
            }
            DESCRIPTION
                     "This trap indicate that LOS status is changed."
            ::= 127
        clockModuleInSrcLDSCStatus TRAP-TYPE
                ENTERPRISE  fkoltg1040Events
            VARIABLES {
                fkClockModuleIndex, fkClockInfoInSrcType, fkClockInfoInSrcLDSCStatus
            }
            DESCRIPTION
                     "This trap indicate that LDSC status is changed."
            ::= 128
        clockModuleInSrcNtrClockChanged TRAP-TYPE
                ENTERPRISE  fkoltg1040Events
            VARIABLES {
                fkClockModuleIndex, fkClockInfoInSrcType, fkClockInfoInSrcNtrClockType
            }
            DESCRIPTION
                     "This trap indicate that NTR is changed."
            ::= 129

        -- 1.3.6.1.4.1.10428 9 1.0.145
        cpuPpsOverThreshold TRAP-TYPE
                ENTERPRISE  fkoltg1040Events
                VARIABLES { fkPerformanceBaseCpuPpsStatus, fkPerformanceBaseCpuPpsThreshold, fkPerformanceBaseCpuPpsAvg}
                DESCRIPTION
                "The PPS of cpu is over the threshold."
                ::= 145

        -- 1.3.6.1.4.1.10428 9 1.0.146
        cpuPpsUnderThreshold TRAP-TYPE
                ENTERPRISE  fkoltg1040Events
                VARIABLES { fkPerformanceBaseCpuPpsStatus, fkPerformanceBaseCpuPpsThreshold, fkPerformanceBaseCpuPpsAvg}
                DESCRIPTION
                "The PPS of cpu is under the threshold."
                ::= 146


--   GE-PON
        -- 1.3.6.1.4.1.10428 9 1.0.151
        ponLinkFault TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "ONU reports a Link Fault via the flag in the 802.3ah OAM header. No further information about the fault is available."
                ::= 151
        
        -- 1.3.6.1.4.1.10428 9 1.0.152
        ponLos TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Loss of Signal is detected by the PHY device for OLT Network  interface, and PON interfaces on  the OLT and ONU."
                ::= 152
        
        -- 1.3.6.1.4.1.10428 9 1.0.153
        ponTransmitFail TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Transmitted output does not match input, as reported by EPON optics."
                ::= 153
        
        -- 1.3.6.1.4.1.10428 9 1.0.154
        ponTransmitDegrade TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Transmitted output has a high error level, but not so high as to cause - Failure. Optionallyreported by EPON optical module."
                ::= 154
        
        -- 1.3.6.1.4.1.10428 9 1.0.155
        ponQueueOverflow TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "One of the queues for the link has dropped frames due to becoming full."
                ::= 155
        
        -- 1.3.6.1.4.1.10428 9 1.0.156
        ponMacLearningTableOverflow TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "MAC address learning table is full, not in overwrite mode, and a new MAC address wasencountered."
                ::= 156
        
        -- 1.3.6.1.4.1.10428 9 1.0.157
        ponDuplicateMacRegistration TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "MPCP register request received for MAC that is registered and in-service."
                ::= 157
        
        -- 1.3.6.1.4.1.10428 9 1.0.158
        ponReportTimeout TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "ONU does not respond to grants from the OLT."
                ::= 158
        
        -- 1.3.6.1.4.1.10428 9 1.0.159
        ponGateTimeout TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Excessive interval between MPCP gates."
                ::= 159
        
        -- 1.3.6.1.4.1.10428 9 1.0.160
        ponOAMKeepaliveTimeout TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "OAM KeepaliveTimeout - OAM layer does not receive periodic messages from its peer."
                ::= 160
        
        -- 1.3.6.1.4.1.10428 9 1.0.161
        ponKeyExchangeFailure TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "The link peer has failed to generate a new key message, or to switch to the new key, in the timeallotted by the key exchange timer for this link. Encryption remains in force using the old key, and the key exchange process continues.The alarm will clear when a new key is established."
                ::= 161
        
        -- 1.3.6.1.4.1.10428 9 1.0.162
        ponAutoNegotiation TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "OLT Network port fails to auto-negotiate with the peer (if auto-negotiation feature is enabled)."
                ::= 162
        
        -- 1.3.6.1.4.1.10428 9 1.0.163
        ponLinkLoopback TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "The link is currently in the loopback state."
                ::= 163
        
        -- 1.3.6.1.4.1.10428 9 1.0.164
        ponStandardDyingGasp TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "ONU reports Dying Gasp via that bit in 802.3ah OAM header."
                ::= 164
        
        -- 1.3.6.1.4.1.10428 9 1.0.165
        ponPowerFail TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Power supply failure."
                ::= 165
        
        -- 1.3.6.1.4.1.10428 9 1.0.166
        ponTemperature TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Operating temperature range exceeded."
                ::= 166
        
        -- 1.3.6.1.4.1.10428 9 1.0.167
        ponAuthenticationInformationUnavailable TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "ONU is configured to use external authentication device, and that device is not present."
                ::= 167
        
        -- 1.3.6.1.4.1.10428 9 1.0.171
        ponOctetsTransferred TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Octets Transferred."
                ::= 171
        
        -- 1.3.6.1.4.1.10428 9 1.0.172
        ponTotalFramesTransferred TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Total frames transferred."
                ::= 172
        
        -- 1.3.6.1.4.1.10428 9 1.0.173
        ponUnicastFramesTransferred TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Unicast frames transferred."
                ::= 173
        
        -- 1.3.6.1.4.1.10428 9 1.0.174
        ponBroadcastFramesTransferred TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Broadcast frames transferred."
                ::= 174
        
        -- 1.3.6.1.4.1.10428 9 1.0.175
        ponMulticastFramesTransferred TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Multicast frames transferred."
                ::= 175
        
        -- 1.3.6.1.4.1.10428 9 1.0.176
        ponCRC32Errors TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "CRC-32 Errors."
                ::= 176
        
        -- 1.3.6.1.4.1.10428 9 1.0.177
        ponUndersizeFrames TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Undersize Frames."
                ::= 177
        
        -- 1.3.6.1.4.1.10428 9 1.0.178
        ponOversizeFrames TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Oversize Frames."
                ::= 178
        
        -- 1.3.6.1.4.1.10428 9 1.0.179
        ponCollisions TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Collisions."
                ::= 179
        
        -- 1.3.6.1.4.1.10428 9 1.0.180
        pon64OctetFrames TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "64 Octet Frames."
                ::= 180
        
        -- 1.3.6.1.4.1.10428 9 1.0.181
        pon127OctetFrames TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "65-127 Octet Frames."
                ::= 181
        
        -- 1.3.6.1.4.1.10428 9 1.0.182
        pon255OctetFrames TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "128-255 Octet Frames."
                ::= 182
        
        -- 1.3.6.1.4.1.10428 9 1.0.183
        pon511OctetFrames TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "256-511 Octet Frames."
                ::= 183
        
        -- 1.3.6.1.4.1.10428 9 1.0.184
        pon1023OctetFrames TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "512-1023 Octet Frames."
                ::= 184
        
        -- 1.3.6.1.4.1.10428 9 1.0.185
        pon1518OctetFrames TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "1024-1518 Octet Frames."
                ::= 185
        
        -- 1.3.6.1.4.1.10428 9 1.0.186
        pon1519OverOctetFrames TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "1519+ Octet Frames."
                ::= 186
        
        -- 1.3.6.1.4.1.10428 9 1.0.187
        ponFramesDropped TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Frames dropped."
                ::= 187
        
        -- 1.3.6.1.4.1.10428 9 1.0.188
        ponOctetsDropped TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Octets dropped."
                ::= 188
        
        -- 1.3.6.1.4.1.10428 9 1.0.189
        ponOctetsDelayed TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Octets delayed."
                ::= 189
        
        -- 1.3.6.1.4.1.10428 9 1.0.190
        ponOctetsGranted TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Octets granted."
                ::= 190
        
        -- 1.3.6.1.4.1.10428 9 1.0.191
        ponOctetsGrantedButUnused TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Octets granted but unused."
                ::= 191
        
        -- 1.3.6.1.4.1.10428 9 1.0.192
        ponMaximumDelay TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "Maximum Delay (units of 100usec)."
                ::= 192
        
        -- 1.3.6.1.4.1.10428 9 1.0.193
        ponCRC8Errors TRAP-TYPE
                ENTERPRISE  fkoltg1040Events
                VARIABLES { dsPonOltIndex, dsPonOnuIndex, dsPonOnuMacAddress, dsPonTaggedLabel, dsPonQueueIndex, 
                        dsPonDirection, dsPonState, dsPonCount }
                DESCRIPTION 
                        "CRC-8 (preamble) Errors."
                ::= 193
        
        -- 1.3.6.1.4.1.10428 9 1.0.194
        ponLineCodeErrors TRAP-TYPE
                ENTERPRISE  fkoltg1040Events
                VARIABLES { dsPonOltIndex, dsPonOnuIndex, dsPonOnuMacAddress, dsPonTaggedLabel, dsPonPortIndex, 
                        dsPonQueueIndex, dsPonDirection, dsPonState, dsPonCount }
                DESCRIPTION 
                        " Line code errors "
                ::= 194
        
        -- 1.3.6.1.4.1.10428 9 1.0.195
        ponPauseFrames TRAP-TYPE
                ENTERPRISE  fkoltg1040Events
                VARIABLES { dsPonOltIndex, dsPonOnuIndex, dsPonOnuMacAddress, dsPonTaggedLabel, dsPonPortIndex, 
                        dsPonQueueIndex, dsPonDirection, dsPonState, dsPonCount }
                DESCRIPTION 
                        " Pause Frames "
                ::= 195
        
        -- 1.3.6.1.4.1.10428 9 1.0.196
        ponErroredFrameSeconds TRAP-TYPE
                ENTERPRISE  fkoltg1040Events
                VARIABLES { dsPonOltIndex, dsPonOnuIndex, dsPonOnuMacAddress, dsPonTaggedLabel, dsPonPortIndex, 
                        dsPonQueueIndex, dsPonDirection, dsPonState, dsPonCount }
                DESCRIPTION 
                        " Errored Frame Seconds "
                ::= 196
        
        -- 1.3.6.1.4.1.10428 9 1.0.197
        ponErroredFramePeriod TRAP-TYPE
                ENTERPRISE  fkoltg1040Events
                VARIABLES { dsPonOltIndex, dsPonOnuIndex, dsPonOnuMacAddress, dsPonTaggedLabel, dsPonPortIndex, 
                        dsPonQueueIndex, dsPonDirection, dsPonState, dsPonCount }
                DESCRIPTION 
                        " Errored Frame Period "
                ::= 197
        
        -- 1.3.6.1.4.1.10428 9 1.0.198
        ponErroredFrameSecondsSummary TRAP-TYPE
                ENTERPRISE  fkoltg1040Events
                VARIABLES { dsPonOltIndex, dsPonOnuIndex, dsPonOnuMacAddress, dsPonTaggedLabel, dsPonPortIndex, 
                        dsPonQueueIndex, dsPonDirection, dsPonState, dsPonCount }
                DESCRIPTION 
                        " Errored Frame Seconds Summary "
                ::= 198
        
        -- 1.3.6.1.4.1.10428 9 1.0.200
        gponOnuRegistered TRAP-TYPE
                ENTERPRISE  fkoltg1040Events
                VARIABLES { sysDescr, fkAgentAddress, fkGponOltId, fkGponOnuId, fkGponOnuSerial, 
                        fkGponOnuIsFirst }
                DESCRIPTION 
                        " Registered Onu Informations "
                ::= 200
        
        -- 1.3.6.1.4.1.10428 9 1.0.201
        gponOnuDeregistered TRAP-TYPE
                ENTERPRISE  fkoltg1040Events
                VARIABLES { sysDescr, fkAgentAddress, fkGponOltId, fkGponOnuId, fkGponOnuSerial
                         }
                DESCRIPTION 
                        " Deregistered Onu Informations "
                ::= 201
        
        -- 1.3.6.1.4.1.10428 9 1.0.202
        swWatchdogDetectError TRAP-TYPE
                ENTERPRISE  fkoltg1040Events
                VARIABLES { fkSwWatchdogType }
                DESCRIPTION 
                        " S/W Watchdog Detect Error "
                ::= 202
        
        -- 1.3.6.1.4.1.10428 9 1.0.203
        swWatchdogClearError TRAP-TYPE
                ENTERPRISE  fkoltg1040Events
                VARIABLES { fkSwWatchdogType }
                DESCRIPTION 
                        " S/W Watchdog Clear Error "
                ::= 203
        
        -- 1.3.6.1.4.1.10428 9 1.0.204
        swWatchdogNormalState TRAP-TYPE
                ENTERPRISE  fkoltg1040Events
                VARIABLES { fkSwWatchdogType }
                DESCRIPTION 
                        " S/W Watchdog Normal State "
                ::= 204
        
        -- 1.3.6.1.4.1.10428 9 1.0.205
        swWatchdogAbnormalState TRAP-TYPE
                ENTERPRISE  fkoltg1040Events
                VARIABLES { fkSwWatchdogType }
                DESCRIPTION 
                        " S/W Watchdog Abnormal State "
                ::= 205
        
        -- 1.3.6.1.4.1.10428 9 1.0.206
        gponOnuUpgradeCompleted TRAP-TYPE
                ENTERPRISE  fkoltg1040Events
                VARIABLES { fkGponOltId, fkGponOnuId, fkGponOnuSerial }
                DESCRIPTION 
                        " Upgrade Completed Onu Informations "
                ::= 206
        
        -- 1.3.6.1.4.1.10428 9 1.0.207
        gponOltCableDown TRAP-TYPE
                ENTERPRISE  fkoltg1040Events
                VARIABLES { fkGponOltId }
                DESCRIPTION 
                        " GPON Cable down event is detected.(This is not used for
                        any product)"
                ::= 207
        
        -- 1.3.6.1.4.1.10428 9 1.0.208
        gponOnuAutoToManual TRAP-TYPE
                ENTERPRISE  fkoltg1040Events
                VARIABLES { fkGponOltId, fkGponOnuId, fkGponOnuSerial }
                DESCRIPTION 
                        " GPON Onu is auto-to-manual "
                ::= 208
        
        -- 1.3.6.1.4.1.10428 9 1.0.209
        slotActionEvent TRAP-TYPE
                ENTERPRISE  fkoltg1040Events
                VARIABLES { fkSlotSystemIndex, fkSlotStatusCurrentInstallCardType, fkSlotStatusActionEvent }
                DESCRIPTION 
                        " This trap indicates the slot action event "
                ::= 209
        
        -- 1.3.6.1.4.1.10428 9 1.0.210
        slotStateChanged TRAP-TYPE
                ENTERPRISE  fkoltg1040Events
                VARIABLES { fkSlotSystemIndex, fkSlotStatusCurrentInstallCardType, fkSlotStatusState }
                DESCRIPTION 
                        " This trap indicates the slot state is changed "
                ::= 210
        
        -- 1.3.6.1.4.1.10428 9 1.0.211
        gponNoAuthONU TRAP-TYPE
                ENTERPRISE  fkoltg1040Events
                VARIABLES { fkGponOltId, fkGponOnuId, fkGponOnuAuthenticationStatus }
                DESCRIPTION 
                        " No autheticated ONU "
                ::= 211
        
        -- 1.3.6.1.4.1.10428 9 1.0.212
        gponDuplicateONU TRAP-TYPE
                ENTERPRISE  fkoltg1040Events
                VARIABLES { fkGponOltId, fkGponOnuId, fkGponOnuSerial }
                DESCRIPTION 
                        " Duplicated ONU "
                ::= 212
        
        -- 1.3.6.1.4.1.10428 9 1.0.213
        gponDyingGasp TRAP-TYPE
                ENTERPRISE  fkoltg1040Events
                VARIABLES { fkGponOltId, fkGponOnuId, fkGponOnuSerial }
                DESCRIPTION 
                        "Dying Gasp of GPON ONU "
                ::= 213
        
        -- 1.3.6.1.4.1.10428 9 1.0.214
        gponRogueOnu TRAP-TYPE
                ENTERPRISE  fkoltg1040Events
                VARIABLES { fkGponOltId, fkGponOnuId, fkGponOnuSerial }
                DESCRIPTION 
                        "Found Rogue ONU. "
                ::= 214
        
        -- 1.3.6.1.4.1.10428 9 1.0.215
        gponOnuBatteryEvent TRAP-TYPE
                ENTERPRISE  fkoltg1040Events
                VARIABLES { fkGponOltId, fkGponOnuId, fkGponOnuBatteryStatus }
                DESCRIPTION 
                        "Battery Event. "
                ::= 215
        
        -- 1.3.6.1.4.1.10428 9 1.0.216
        gponOnuBatteryEventCleared TRAP-TYPE
                ENTERPRISE  fkoltg1040Events
                VARIABLES { fkGponOltId, fkGponOnuId, fkGponOnuBatteryStatus }
                DESCRIPTION 
                        "Battery Event is cleared. "
                ::= 216
        
        -- 1.3.6.1.4.1.10428 9 1.0.217
        gponOnuPortOperStatus TRAP-TYPE
                ENTERPRISE  fkoltg1040Events
                VARIABLES { fkGponOltId, fkGponOnuId, fkGponOnuSerial,
                    fkGponOnuPortId, fkGponOnuDescription, fkGponOnuPortSlotId,
                    fkGponOnuPortControlUniDescription, fkGponOnuPortOperStatus
                         }
                DESCRIPTION 
                        " This trap indicates state of ONU Port Operation. "
                ::= 217
        
        -- 1.3.6.1.4.1.10428 9 1.0.218
        gponTransceiverChanged TRAP-TYPE
                ENTERPRISE  fkoltg1040Events
                VARIABLES { fkGponOltId, fkGponOltTransceiverPort }
                DESCRIPTION 
                        " This trap indicates GPON transceiver changed. "
                ::= 218
        
        -- 1.3.6.1.4.1.10428 9 1.0.219
        gponOltLosOn TRAP-TYPE
                ENTERPRISE  fkoltg1040Events
                VARIABLES { fkGponOltId }
                DESCRIPTION 
                        " This trap indicates state of OLT Loss Of Signal (on). "
                ::= 219
        
        -- 1.3.6.1.4.1.10428 9 1.0.220
        gponOltLosOff TRAP-TYPE
                ENTERPRISE  fkoltg1040Events
                VARIABLES { fkGponOltId }
                DESCRIPTION 
                        " This trap indicates state of OLT Loss Of Signal (off). "
                ::= 220
        
        -- 1.3.6.1.4.1.10428 9 1.0.221
        gponOltLosiOn TRAP-TYPE
                ENTERPRISE  fkoltg1040Events
                VARIABLES { fkGponOltId, fkGponOnuId }
                DESCRIPTION 
                        " This trap indicates state of OLT Loss Of Signal for ONUi (on). "
                ::= 221
        
        -- 1.3.6.1.4.1.10428 9 1.0.222
        gponOltLosiOff TRAP-TYPE
                ENTERPRISE  fkoltg1040Events
                VARIABLES { fkGponOltId, fkGponOnuId }
                DESCRIPTION 
                        " This trap indicates state of OLT Loss Of Signal for ONUi (off). "
                ::= 222
        
        -- 1.3.6.1.4.1.10428 9 1.0.223
        gponDyingGaspOn TRAP-TYPE
                ENTERPRISE  fkoltg1040Events
                VARIABLES { fkGponOltId, fkGponOnuId, fkGponOnuSerial }
                DESCRIPTION 
                        "This trap indicates Dying Gasp of GPON ONU (on). "
                ::= 223
        
        -- 1.3.6.1.4.1.10428 9 1.0.224
        gponDyingGaspOff TRAP-TYPE
                ENTERPRISE  fkoltg1040Events
                VARIABLES { fkGponOltId, fkGponOnuId, fkGponOnuSerial }
                DESCRIPTION 
                        "This trap indicates Dying Gasp of GPON ONU (off). "
                ::= 224
        
        -- 1.3.6.1.4.1.10428 9 1.0.225
        slotErrorLEDChanged TRAP-TYPE
                ENTERPRISE  fkoltg1040Events
                VARIABLES { fkSlotSystemIndex }
                DESCRIPTION 
                        "This trap indicates slot error LED changed. "
                ::= 225
        
        -- 1.3.6.1.4.1.10428 9 1.0.226
        nmsConnectionTypeChanged TRAP-TYPE
                ENTERPRISE  fkoltg1040Events
                VARIABLES { fkSnmpConnectionType }
                DESCRIPTION 
                        "This trap indicates NMS connection type changed. "
                ::= 226
        
        -- 1.3.6.1.4.1.10428 9 1.0.227
        gponOntOSUpgradeStatus TRAP-TYPE
                ENTERPRISE  fkoltg1040Events
                VARIABLES { fkGponOntFirmwareOltId, fkGponOntFirmwareOntId, fkGponOntFirmwareOntOsStatus }
                DESCRIPTION 
                        "This trap indicates ONT OS upgrade status changes. "
                ::= 227
        
        -- 1.3.6.1.4.1.10428 9 1.0.228
        gponOntBLUpgradeStatus TRAP-TYPE
                ENTERPRISE  fkoltg1040Events
                VARIABLES { fkGponOntFirmwareOltId, fkGponOntFirmwareOntId, fkGponOntFirmwareOntBLStatus }
                DESCRIPTION 
                        "This trap indicates ONT BL upgrade status changes. "
                ::= 228
        
        -- 1.3.6.1.4.1.10428 9 1.0.229
        gponOntRxPowerLoss TRAP-TYPE
                ENTERPRISE  fkoltg1040Events
                VARIABLES { fkGponOltId }
                DESCRIPTION 
                        "This trap indicates ONT port failed to detect Rx Power. "
                ::= 229
        
        -- 1.3.6.1.4.1.10428 9 1.0.230
        gponOntRxPowerDetected TRAP-TYPE
                ENTERPRISE  fkoltg1040Events
                VARIABLES { fkGponOltId }
                DESCRIPTION 
                        "This trap indicates ONT port detected Rx Power. "
                ::= 230
        
        -- 1.3.6.1.4.1.10428 9 1.0.231
        gponOnuTemperatureHighOverThreshold TRAP-TYPE
                ENTERPRISE  fkoltg1040Events
                VARIABLES { fkGponOltId, fkGponOnuId }
                DESCRIPTION 
                        "This trap indicates the temperature of ONU is over high threshold. "
                ::= 231
        
        -- 1.3.6.1.4.1.10428 9 1.0.232
        gponOnuTemperatureHighFallThreshold TRAP-TYPE
                ENTERPRISE  fkoltg1040Events
                VARIABLES { fkGponOltId, fkGponOnuId }
                DESCRIPTION 
                        "This trap indicates the temperature of ONU falls under high threshold. "
                ::= 232
        
        -- 1.3.6.1.4.1.10428 9 1.0.233
        gponOnuTemperatureLowOverThreshold TRAP-TYPE
                ENTERPRISE  fkoltg1040Events
                VARIABLES { fkGponOltId, fkGponOnuId }
                DESCRIPTION 
                        "This trap indicates the temperature of ONU is over low threshold. "
                ::= 233
        
        -- 1.3.6.1.4.1.10428 9 1.0.234
        gponOnuTemperatureLowFallThreshold TRAP-TYPE
                ENTERPRISE  fkoltg1040Events
                VARIABLES { fkGponOltId, fkGponOnuId }
                DESCRIPTION 
                        "This trap indicates the temperature of ONU falls under low threshold. "
                ::= 234
        
        -- 1.3.6.1.4.1.10428 9 1.0.235
        gponOnuCpuOverThreshold TRAP-TYPE
                ENTERPRISE  fkoltg1040Events
                VARIABLES { fkGponOltId, fkGponOnuId }
                DESCRIPTION 
                        "This trap indicates the CPU-load of ONU is over threshold. "
                ::= 235
        
        -- 1.3.6.1.4.1.10428 9 1.0.236
        gponOnuCpuFallThreshold TRAP-TYPE
                ENTERPRISE  fkoltg1040Events
                VARIABLES { fkGponOltId, fkGponOnuId }
                DESCRIPTION 
                        "This trap indicates the CPU-load of ONU falls under threshold. "
                ::= 236
        
        -- 1.3.6.1.4.1.10428 9 1.0.237
        gponOnuMemoryOverThreshold TRAP-TYPE
                ENTERPRISE  fkoltg1040Events
                VARIABLES { fkGponOltId, fkGponOnuId }
                DESCRIPTION 
                        "This trap indicates the memory-utilization of ONU is over threshold. "
                ::= 237
        
        -- 1.3.6.1.4.1.10428 9 1.0.238
        gponOnuMemoryFallThreshold TRAP-TYPE
                ENTERPRISE  fkoltg1040Events
                VARIABLES { fkGponOltId, fkGponOnuId }
                DESCRIPTION 
                        "This trap indicates the memory-utilization of ONU falls under threshold. "
                ::= 238
        
        -- 1.3.6.1.4.1.10428 9 1.0.239
        gponOnuI2cFail TRAP-TYPE
                ENTERPRISE  fkoltg1040Events
                VARIABLES { fkGponOltId, fkGponOnuId }
                DESCRIPTION 
                        "This trap indicates that detect ONU's i2c fail."
                ::= 239
        -- 1.3.6.1.4.1.10428 9 1.0.240
        gponOnuRxOpticPowerLowThreshAlarmOn TRAP-TYPE
                ENTERPRISE  fkoltg1040Events
                VARIABLES { fkGponOltId, fkGponOnuId }
                DESCRIPTION 
                        "RX optic low power alarm is detected"
                ::= 240
        
        -- 1.3.6.1.4.1.10428 9 1.0.241
        gponOnuRxOpticPowerLowThreshAlarmOff TRAP-TYPE
                ENTERPRISE  fkoltg1040Events
                VARIABLES { fkGponOltId, fkGponOnuId }
                DESCRIPTION 
                        "RX optic low power alarm is cleared"
                ::= 241
        
        -- 1.3.6.1.4.1.10428 9 1.0.242
        gponOnuRxOpticPowerHighThreshAlarmOn TRAP-TYPE
                ENTERPRISE  fkoltg1040Events
                VARIABLES { fkGponOltId, fkGponOnuId }
                DESCRIPTION 
                        "RX Optic over power alarm is detected"
                ::= 242
        
        -- 1.3.6.1.4.1.10428 9 1.0.243
        gponOnuRxOpticPowerHighThreshAlarmOff TRAP-TYPE
                ENTERPRISE  fkoltg1040Events
                VARIABLES { fkGponOltId, fkGponOnuId }
                DESCRIPTION 
                        "RX Optic over power alarm is cleared."
                ::= 243
        
        -- 1.3.6.1.4.1.10428 9 1.0.244
        gponOltLOFIOn TRAP-TYPE
                ENTERPRISE  fkoltg1040Events
                VARIABLES { fkGponOltId, fkGponOnuId }
                DESCRIPTION 
                        "OLT LOFI alarm is detected"
                ::= 244
        
        -- 1.3.6.1.4.1.10428 9 1.0.245
        gponOltLOFIOff TRAP-TYPE
                ENTERPRISE  fkoltg1040Events
                VARIABLES { fkGponOltId, fkGponOnuId }
                DESCRIPTION 
                        "OLT LOFI alarm is cleared"
                ::= 245
        
        -- 1.3.6.1.4.1.10428 9 1.0.246
        gponOltDOWOn TRAP-TYPE
                ENTERPRISE  fkoltg1040Events
                VARIABLES { fkGponOltId, fkGponOnuId }
                DESCRIPTION 
                        "OLT DOW alarm is detected"
                ::= 246
        
        -- 1.3.6.1.4.1.10428 9 1.0.247
        gponOltDOWOff TRAP-TYPE
                ENTERPRISE  fkoltg1040Events
                VARIABLES { fkGponOltId, fkGponOnuId }
                DESCRIPTION 
                        "OLT DOW alarm is cleared"
                ::= 247
        
        -- 1.3.6.1.4.1.10428 9 1.0.248
        gponOltSFOn TRAP-TYPE
                ENTERPRISE  fkoltg1040Events
                VARIABLES { fkGponOltId, fkGponOnuId }
                DESCRIPTION 
                        "OLT SF alarm is detected"
                ::= 248
        
        -- 1.3.6.1.4.1.10428 9 1.0.249
        gponOltSFOff TRAP-TYPE
                ENTERPRISE  fkoltg1040Events
                VARIABLES { fkGponOltId, fkGponOnuId }
                DESCRIPTION 
                        "OLT SF alarm is cleared"
                ::= 249
        
        -- 1.3.6.1.4.1.10428 9 1.0.250
        gponOltSDOn TRAP-TYPE
                ENTERPRISE  fkoltg1040Events
                VARIABLES { fkGponOltId, fkGponOnuId }
                DESCRIPTION 
                        "OLT SD alarm is detected"
                ::= 250
        
        -- 1.3.6.1.4.1.10428 9 1.0.251
        gponOltSDOff TRAP-TYPE
                ENTERPRISE  fkoltg1040Events
                VARIABLES { fkGponOltId, fkGponOnuId }
                DESCRIPTION 
                        "OLT SD alarm is cleared"
                ::= 251
        
        -- 1.3.6.1.4.1.10428 9 1.0.252
        gponOltLCDGIOn TRAP-TYPE
                ENTERPRISE  fkoltg1040Events
                VARIABLES { fkGponOltId, fkGponOnuId }
                DESCRIPTION 
                        "OLT LCDGI alarm is detected"
                ::= 252
        
        -- 1.3.6.1.4.1.10428 9 1.0.253
        gponOltLCDGIOff TRAP-TYPE
                ENTERPRISE  fkoltg1040Events
                VARIABLES { fkGponOltId, fkGponOnuId }
                DESCRIPTION 
                        "OLT LCDGI alarm is cleared"
                ::= 253
        
        -- 1.3.6.1.4.1.10428 9 1.0.254
        gponOltRDOn TRAP-TYPE
                ENTERPRISE  fkoltg1040Events
                VARIABLES { fkGponOltId, fkGponOnuId }
                DESCRIPTION 
                        "OLT RD alarm is detected"
                ::= 254
        
        -- 1.3.6.1.4.1.10428 9 1.0.255
        gponOltRDOff TRAP-TYPE
                ENTERPRISE  fkoltg1040Events
                VARIABLES { fkGponOltId, fkGponOnuId }
                DESCRIPTION 
                        "OLT RD alarm is cleared"
                ::= 255
        
        -- 1.3.6.1.4.1.10428 9 1.0.256
        gponOltSUFOn TRAP-TYPE
                ENTERPRISE  fkoltg1040Events
                VARIABLES { fkGponOltId, fkGponOnuId }
                DESCRIPTION 
                        "OLT SUF alarm is detected"
                ::= 256
        
        -- 1.3.6.1.4.1.10428 9 1.0.257
        gponOltSUFOff TRAP-TYPE
                ENTERPRISE  fkoltg1040Events
                VARIABLES { fkGponOltId, fkGponOnuId }
                DESCRIPTION 
                        "OLT SUF alarm is cleared"
                ::= 257
        
        -- 1.3.6.1.4.1.10428 9 1.0.258
        gponOltLOAOn TRAP-TYPE
                ENTERPRISE  fkoltg1040Events
                VARIABLES { fkGponOltId, fkGponOnuId }
                DESCRIPTION 
                        "OLT LOA alarm is detected"
                ::= 258
        
        -- 1.3.6.1.4.1.10428 9 1.0.259
        gponOltLOAOff TRAP-TYPE
                ENTERPRISE  fkoltg1040Events
                VARIABLES { fkGponOltId, fkGponOnuId }
                DESCRIPTION 
                        "OLT LOA alarm is cleared"
                ::= 259
        
        -- 1.3.6.1.4.1.10428 9 1.0.260
        gponOltLOAMIOn TRAP-TYPE
                ENTERPRISE  fkoltg1040Events
                VARIABLES { fkGponOltId, fkGponOnuId }
                DESCRIPTION 
                        "OLT LOAMI alarm is detected"
                ::= 260
        
        -- 1.3.6.1.4.1.10428 9 1.0.261
        gponOltLOAMIOff TRAP-TYPE
                ENTERPRISE  fkoltg1040Events
                VARIABLES { fkGponOltId, fkGponOnuId }
                DESCRIPTION 
                        "OLT LOAMI alarm is cleared"
                ::= 261
        
        -- 1.3.6.1.4.1.10428 9 1.0.262
        gponOltMEMOn TRAP-TYPE
                ENTERPRISE  fkoltg1040Events
                VARIABLES { fkGponOltId, fkGponOnuId }
                DESCRIPTION 
                        "OLT MEM alarm is detected"
                ::= 262
        
        -- 1.3.6.1.4.1.10428 9 1.0.263
        gponOltMEMOff TRAP-TYPE
                ENTERPRISE  fkoltg1040Events
                VARIABLES { fkGponOltId, fkGponOnuId }
                DESCRIPTION 
                        "OLT MEM alarm is cleared"
                ::= 263
        
        -- 1.3.6.1.4.1.10428 9 1.0.264
        gponOltPEEOn TRAP-TYPE
                ENTERPRISE  fkoltg1040Events
                VARIABLES { fkGponOltId, fkGponOnuId }
                DESCRIPTION 
                        "OLT PEE alarm is detected"
                ::= 264
        
        -- 1.3.6.1.4.1.10428 9 1.0.265
        gponOltPEEOff TRAP-TYPE
                ENTERPRISE  fkoltg1040Events
                VARIABLES { fkGponOltId, fkGponOnuId }
                DESCRIPTION 
                        "OLT PEE alarm is cleared"
                ::= 265
        
        -- 1.3.6.1.4.1.10428 9 1.0.266
        gponOltPSTOn TRAP-TYPE
                ENTERPRISE  fkoltg1040Events
                VARIABLES { fkGponOltId, fkGponOnuId }
                DESCRIPTION 
                        "OLT PST alarm is detected"
                ::= 266
        
        -- 1.3.6.1.4.1.10428 9 1.0.267
        gponOltPSTOff TRAP-TYPE
                ENTERPRISE  fkoltg1040Events
                VARIABLES { fkGponOltId, fkGponOnuId }
                DESCRIPTION 
                        "OLT PST alarm is cleared"
                ::= 267
        
        -- 1.3.6.1.4.1.10428 9 1.0.268
        gponOltERROn TRAP-TYPE
                ENTERPRISE  fkoltg1040Events
                VARIABLES { fkGponOltId, fkGponOnuId }
                DESCRIPTION 
                        "OLT alarm error is detected"
                ::= 268
        
        -- 1.3.6.1.4.1.10428 9 1.0.269
        gponOltERROff TRAP-TYPE
                ENTERPRISE  fkoltg1040Events
                VARIABLES { fkGponOltId, fkGponOnuId }
                DESCRIPTION 
                        "OLT alarm error is cleared"
                ::= 269
        
        -- 1.3.6.1.4.1.10428 9 1.0.270
        gponOltREIOn TRAP-TYPE
                ENTERPRISE  fkoltg1040Events
                VARIABLES { fkGponOltId, fkGponOnuId }
                DESCRIPTION 
                        "OLT REI alarm is detected"
                ::= 270
        
        -- 1.3.6.1.4.1.10428 9 1.0.271
        gponOltREIOff TRAP-TYPE
                ENTERPRISE  fkoltg1040Events
                VARIABLES { fkGponOltId, fkGponOnuId }
                DESCRIPTION 
                        "OLT REI alarm is cleared."
                ::= 271

        -- 1.3.6.1.4.1.10428 9 1.0.272
        gponAntiSpoofingDupPortOn TRAP-TYPE
                ENTERPRISE  fkoltg1040Events
                VARIABLES { fkGponAntiSpoofingOltId,
                    fkGponAntiSpoofingOnuId, fkGponAntiSpoofingVlanId,
                    fkGponAntiSpoofingMac } 
                DESCRIPTION 
                        "Anti spoofing duplication port alarm is detected"
                ::= 272
        -- 1.3.6.1.4.1.10428 9 1.0.273
        gponAntiSpoofingDupPortOff TRAP-TYPE
                ENTERPRISE  fkoltg1040Events
                VARIABLES { fkGponAntiSpoofingOltId,
                    fkGponAntiSpoofingOnuId, fkGponAntiSpoofingVlanId,
                    fkGponAntiSpoofingMac } 
                DESCRIPTION 
                        "Anti spoofing duplication port alarm is cleared"
                ::= 273
        -- 1.3.6.1.4.1.10428 9 1.0.274
        gponRedundancySwitchOver TRAP-TYPE
                ENTERPRISE  fkoltg1040Events
                VARIABLES {fkGponRedGroupIndex,
                    fkGponRedGroupOltAIndex,
                    fkGponRedGroupOltAStatus,
                    fkGponRedGroupOltBIndex,
                    fkGponRedGroupOltBStatus,
                    fkGponRedLastReason }
                DESCRIPTION 
                        "Redundancy switch over"
                ::= 274
        -- 1.3.6.1.4.1.10428 9 1.0.275
        gponDuplicatedRangingResponse TRAP-TYPE
                ENTERPRISE  fkoltg1040Events
                VARIABLES {fkGponOltId,
                    fkGponOnuId}
                DESCRIPTION 
                        "Duplicated ranging response detection."
                ::= 275
  

        -- 1.3.6.1.4.1.10428 9 1.0.276
        gponOnuPortOpticModuleInstall TRAP-TYPE
                ENTERPRISE  fkoltg1040Events
                VARIABLES {fkGponOltId, fkGponOnuId,
                    fkGponOnuPortSlotId, fkGponOnuPortId }
                DESCRIPTION 
                        "ONU port optic module install detection."
                ::= 276
        -- 1.3.6.1.4.1.10428 9 1.0.277
        gponOnuPortOpticModuleRemove TRAP-TYPE
                ENTERPRISE  fkoltg1040Events
                VARIABLES {fkGponOltId, fkGponOnuId,
                    fkGponOnuPortSlotId, fkGponOnuPortId }
                DESCRIPTION 
                        "ONU port optic module removal detection."
                ::= 277
       -- 1.3.6.1.4.1.10428 9 1.0.278
        gponOnuOMCCProblemDetected TRAP-TYPE
                ENTERPRISE  fkoltg1040Events
                VARIABLES {fkGponOltId, fkGponOnuId }
                DESCRIPTION 
                        "ONU OMCC Problem is detected."
                ::= 278
       -- 1.3.6.1.4.1.10428 9 1.0.279
        gponOnuOMCCProblemCleared TRAP-TYPE
                ENTERPRISE  fkoltg1040Events
                VARIABLES {fkGponOltId, fkGponOnuId }
                DESCRIPTION 
                        "ONU OMCC Problem is cleared."
                ::= 279
       -- 1.3.6.1.4.1.10428 9 1.0.280
        gponOltFixedTcontAlarmOn TRAP-TYPE
                ENTERPRISE  fkoltg1040Events
                VARIABLES {fkGponOltId, fkGponOltFixedTcontCount}
                DESCRIPTION 
                        "OLT fixed tcont alarm is detected"
                ::= 280
       -- 1.3.6.1.4.1.10428 9 1.0.281
        gponOltFixedTcontAlarmOff TRAP-TYPE
                ENTERPRISE  fkoltg1040Events
                VARIABLES {fkGponOltId, fkGponOltFixedTcontCount}
                DESCRIPTION 
                        "OLT fixed tcont alarm is cleared"
                ::= 281
       -- 1.3.6.1.4.1.10428 9 1.0.282
        gponOltDynamicTcontAlarmOn TRAP-TYPE
                ENTERPRISE  fkoltg1040Events
                VARIABLES {fkGponOltId, fkGponOltDynamicTcontCount}
                DESCRIPTION 
                        "OLT dynamic tcont alarm is detected."
                ::= 282
        -- 1.3.6.1.4.1.10428 9 1.0.283
        gponOltDynamicTcontAlarmOff TRAP-TYPE
                ENTERPRISE  fkoltg1040Events
                VARIABLES {fkGponOltId, fkGponOltDynamicTcontCount}
                DESCRIPTION 
                        "OLT dynamic tcont alarm is cleared."
                ::= 283
        -- 1.3.6.1.4.1.10428 9 1.0.284
        gponOltPortCountAlarmOn TRAP-TYPE
                ENTERPRISE  fkoltg1040Events
                VARIABLES {fkGponOltId, fkGponOltPortCount}
                DESCRIPTION 
                        "OLT port count alarm is detected."
                ::= 284
        -- 1.3.6.1.4.1.10428 9 1.0.285
        gponOltPortCountAlarmOff TRAP-TYPE
                ENTERPRISE  fkoltg1040Events
                VARIABLES {fkGponOltId, fkGponOltPortCount}
                DESCRIPTION 
                        "OLT port count alarm is cleared."
                ::= 285
        -- 1.3.6.1.4.1.10428 9 1.0.286
        gponOltCableDownAlarmOn TRAP-TYPE
                ENTERPRISE  fkoltg1040Events
                VARIABLES {fkGponOltId}
                DESCRIPTION 
                        "GPON Cable down event is detected"
                ::= 286
        -- 1.3.6.1.4.1.10428 9 1.0.287
        gponOltCableDownAlarmOff TRAP-TYPE
                ENTERPRISE  fkoltg1040Events
                VARIABLES {fkGponOltId}
                DESCRIPTION 
                        "GPON Cable down event is cleared"
                ::= 287
        -- 1.3.6.1.4.1.10428 9 1.0.288
        gponOltDeactiveMonitorAlarmOn TRAP-TYPE
                ENTERPRISE  fkoltg1040Events
                VARIABLES {fkGponOltId}
                DESCRIPTION 
                        "GPON deactive monitor alarm is on"
                ::= 288
        -- 1.3.6.1.4.1.10428 9 1.0.289
        gponOltDeactiveMonitorAlarmOff TRAP-TYPE
                ENTERPRISE  fkoltg1040Events
                VARIABLES {fkGponOltId}
                DESCRIPTION 
                        "GPON deactive monitor alarm is off"
                ::= 289
        -- 1.3.6.1.4.1.10428 9 1.0.290
        gponOltDFION TRAP-TYPE
                ENTERPRISE  fkoltg1040Events
                VARIABLES {fkGponOltId, fkGponOnuId}
                DESCRIPTION 
                        "GPON OLT DFI is on"
                ::= 290
        -- 1.3.6.1.4.1.10428 9 1.0.291
        gponOltDFIOFF TRAP-TYPE
                ENTERPRISE  fkoltg1040Events
                VARIABLES {fkGponOltId, fkGponOnuId}
                DESCRIPTION 
                        "GPON OLT DFI is off"
                ::= 291
        -- 1.3.6.1.4.1.10428 9 1.0.294
        gponOltTransceiverPortChanged TRAP-TYPE
                ENTERPRISE  fkoltg1040Events
                VARIABLES {fkGponOltId, fkGponOltTransceiverPort}
                DESCRIPTION 
                        "GPON OLT Transceiver alarm is changed"
                ::= 294
        -- 1.3.6.1.4.1.10428 9 1.0.301
        oamRapsEastPortStatusChanged TRAP-TYPE
                ENTERPRISE  fkoltg1040Events
                VARIABLES {fkY1731MegIndex,
                    fkY1731MegRapsEastPortStatus}
                    DESCRIPTION
                    "The east port status changed"
                    ::= 301
        -- 1.3.6.1.4.1.10428 9 1.0.302
        oamRapsWestPortStatusChanged TRAP-TYPE
                ENTERPRISE  fkoltg1040Events
                VARIABLES {fkY1731MegIndex,
                    fkY1731MegRapsWestPortStatus}
                    DESCRIPTION
                    "The west port status changed"
                    ::= 302
        -- 1.3.6.1.4.1.10428 9 1.0.303
        oamURNodePortStatusChanged TRAP-TYPE
                ENTERPRISE  fkoltg1040Events
                VARIABLES {fkY1731URMegIndex,
                    fkY1731URNodeConfPortNum,
                    fkY1731URNodeConfPortStatus}
                    DESCRIPTION
                    "OAM uplink redundancy node's port status changed"
                    ::= 303
        -- 1.3.6.1.4.1.10428 9 1.0.320
        loopDetectBlocked TRAP-TYPE
                ENTERPRISE  fkoltg1040Events
                VARIABLES {fkBridgePortIndex}
                DESCRIPTION
                "This trap indicate the Port is blocked by loop-detect."
                ::= 320

        -- 1.3.6.1.4.1.10428 9 1.0.321
        loopDetectUnBlockedbyExpireTimer TRAP-TYPE
                ENTERPRISE  fkoltg1040Events
                VARIABLES {fkBridgePortIndex}
                DESCRIPTION
                "This trap indicate the Port is unblocked by loop-detect's expire timer."
                ::= 321

        -- 1.3.6.1.4.1.10428 9 1.0.322
        loopDetectUnBlockedbyLinkDown TRAP-TYPE
                ENTERPRISE  fkoltg1040Events
                VARIABLES {fkBridgePortIndex}
                DESCRIPTION
                "This trap indicate the Port is unblocked by loop-detect's link down."
                ::= 322


--   EM Log
        emLogDefectCPUHighOver TRAP-TYPE
                ENTERPRISE  fkoltg1040Events
            VARIABLES {fkEMLogDefectCPUHigh}
            DESCRIPTION
                     "EM log about CPU load high over."
            ::= 351
        emLogDefectCPUHighUnder TRAP-TYPE
                ENTERPRISE  fkoltg1040Events
            VARIABLES {fkEMLogDefectCPUHigh}
            DESCRIPTION
                     "EM log about CPU load high under."
            ::= 352

        emLogTemperHighOver TRAP-TYPE
                ENTERPRISE  fkoltg1040Events
            VARIABLES {fkEMLogTemperHigh}
            DESCRIPTION
                     "EM log about temperature high over."
            ::= 353
        emLogTemperHighUnder TRAP-TYPE
                ENTERPRISE  fkoltg1040Events
            VARIABLES {fkEMLogTemperHigh}
            DESCRIPTION
                     "EM log about temperature high under."
            ::= 354
            
        emLogTemperLowUnder TRAP-TYPE
                ENTERPRISE  fkoltg1040Events
            VARIABLES {fkEMLogTemperLow}
            DESCRIPTION
                     "EM log about temperature low under (occured)."
            ::= 355
        emLogTemperLowOver TRAP-TYPE
                ENTERPRISE  fkoltg1040Events
            VARIABLES {fkEMLogTemperLow}
            DESCRIPTION
                     "EM log about temperature low under (cleared)."
            ::= 356

        emLogMemLowUnder TRAP-TYPE
                ENTERPRISE  fkoltg1040Events
            VARIABLES {fkEMLogMemLow}
            DESCRIPTION
                     "EM log about memory low over (occured)."
            ::= 357
        emLogMemLowOver TRAP-TYPE
                ENTERPRISE  fkoltg1040Events
            VARIABLES {fkEMLogMemLow}
            DESCRIPTION
                     "EM log about memory low over (cleared)."
            ::= 358

        emLogFanFail TRAP-TYPE
                ENTERPRISE  fkoltg1040Events
            VARIABLES {fkEMLogFanFail}
            DESCRIPTION
                     "EM log about fan fail."
            ::= 359
        emLogFanFailCleared TRAP-TYPE
                ENTERPRISE  fkoltg1040Events
            VARIABLES {fkEMLogFanFail}
            DESCRIPTION
                     "EM log about fan fail cleared."
            ::= 360

        emLogPhyCRCFail TRAP-TYPE
                ENTERPRISE  fkoltg1040Events
            VARIABLES {fkEMLogPhyCRCFail}
            DESCRIPTION
                     "EM log about PHY CRC fail."
            ::= 361
        emLogPhyCRCFailCleared TRAP-TYPE
                ENTERPRISE  fkoltg1040Events
            VARIABLES {fkEMLogPhyCRCFail}
            DESCRIPTION
                     "EM log about PHY CRC fail cleared."
            ::= 362
        emLogPhyDetectFail TRAP-TYPE
                ENTERPRISE  fkoltg1040Events
            VARIABLES {fkEMLogPhyDetectFail}
            DESCRIPTION
                     "EM log about PHY detect fail."
            ::= 363
        emLogPhyDetectFailCleared TRAP-TYPE
                ENTERPRISE  fkoltg1040Events
            VARIABLES {fkEMLogPhyDetectFail}
            DESCRIPTION
                     "EM log about PHY detect fail cleared."
            ::= 364

        emLogSFUMateInitFail TRAP-TYPE
                ENTERPRISE  fkoltg1040Events
            VARIABLES {fkEMLogSFUMateInitFail}
            DESCRIPTION
                     "EM log about SFU mate init fail"
            ::= 365
        emLogSFUMateInitFailCleared TRAP-TYPE
                ENTERPRISE  fkoltg1040Events
            VARIABLES {fkEMLogSFUMateInitFail}
            DESCRIPTION
                     "EM log about SFU mate init fail cleared"
            ::= 366
        emLogDaemonHealthBad TRAP-TYPE
                ENTERPRISE  fkoltg1040Events
            VARIABLES {fkEMLogDaemonHealthBad}
            DESCRIPTION
                     "EM log about daemon health bad"
            ::= 367
        emLogDaemonHealthBadCleared TRAP-TYPE
                ENTERPRISE  fkoltg1040Events
            VARIABLES {fkEMLogDaemonHealthBad}
            DESCRIPTION
                     "EM log about daemon health bad cleared"
            ::= 368

        emLogGPIURavenLinkDown TRAP-TYPE
                ENTERPRISE  fkoltg1040Events
            VARIABLES {fkEMLogGPIURavenLinkDown}
            DESCRIPTION
                     "EM log about GPIU raven link down"
            ::= 369
        emLogGPIURavenLinkDownCleared TRAP-TYPE
                ENTERPRISE  fkoltg1040Events
                VARIABLES {fkEMLogGPIURavenLinkDown}
                DESCRIPTION
                     "EM log about GPIU raven link down cleared"
                ::= 370
        bootSequenceConfigFile TRAP-TYPE
                ENTERPRISE  fkoltg1040Events
                DESCRIPTION 
                        "Boot Sequence Config File failed"
                ::= 371
                
        topologyChanged TRAP-TYPE
                ENTERPRISE  fkoltg1040Events
                DESCRIPTION 
                        "Topolgy changed"
                ::= 372
                
        configLoadFail TRAP-TYPE
                ENTERPRISE  fkoltg1040Events
                DESCRIPTION 
                        "Config load failed"
                ::= 373
                
        gponOnuAniVoltageLowThreshAlarmOn TRAP-TYPE
                ENTERPRISE  fkoltg1040Events
                VARIABLES {fkGponOltId, fkGponOnuId}
                DESCRIPTION 
                        "Voltage low threshold alarm on"
                ::= 381
        gponOnuAniVoltageLowThreshAlarmOff TRAP-TYPE
                ENTERPRISE  fkoltg1040Events
                VARIABLES {fkGponOltId, fkGponOnuId}
                DESCRIPTION 
                        "Voltage low threshold alarm off"
                ::= 382
         gponOnuAniVoltageHighThreshAlarmOn TRAP-TYPE
                ENTERPRISE  fkoltg1040Events
                VARIABLES {fkGponOltId, fkGponOnuId}
                DESCRIPTION 
                        "Voltage high threshold alarm on"
                ::= 383
         gponOnuAniVoltageHighThreshAlarmOff TRAP-TYPE
                ENTERPRISE  fkoltg1040Events
                VARIABLES {fkGponOltId, fkGponOnuId}
                DESCRIPTION 
                        "Voltage high threshold alarm off"
                ::= 384
         gponOnuAniTemperatureLowThreshAlarmOn TRAP-TYPE
                ENTERPRISE  fkoltg1040Events
                VARIABLES {fkGponOltId, fkGponOnuId}
                DESCRIPTION 
                        "Temperature low threshold alarm on"
                ::= 385
         gponOnuAniTemperatureLowThreshAlarmOff TRAP-TYPE
                ENTERPRISE  fkoltg1040Events
                VARIABLES {fkGponOltId, fkGponOnuId}
                DESCRIPTION 
                        "Temperature high threshold alarm off"
                ::= 386
         gponOnuAniTemperatureHighThreshAlarmOn TRAP-TYPE
                ENTERPRISE  fkoltg1040Events
                VARIABLES {fkGponOltId, fkGponOnuId}
                DESCRIPTION 
                        "Temperature high threshold alarm on"
                ::= 387
         gponOnuAniTemperatureHighThreshAlarmOff TRAP-TYPE
                ENTERPRISE  fkoltg1040Events
                VARIABLES {fkGponOltId, fkGponOnuId}
                DESCRIPTION 
                        "Temperature high threshold alarm off"
                ::= 388

         gponOnuAniTxBiasLowThreshAlarmOn TRAP-TYPE
                ENTERPRISE  fkoltg1040Events
                VARIABLES {fkGponOltId, fkGponOnuId}
                DESCRIPTION 
                        "TX-bias low threshold alarm on"
                ::= 389
         gponOnuAniTxBiasLowThreshAlarmOff TRAP-TYPE
                ENTERPRISE  fkoltg1040Events
                VARIABLES {fkGponOltId, fkGponOnuId}
                DESCRIPTION 
                        "TX-bias low threshold alarm off"
                ::= 390

         gponOnuAniTxBiasHighThreshAlarmOn TRAP-TYPE
                ENTERPRISE  fkoltg1040Events
                VARIABLES {fkGponOltId, fkGponOnuId}
                DESCRIPTION 
                        "TX-bias high threshold alarm on"
                ::= 391
         gponOnuAniTxBiasHighThreshAlarmOff TRAP-TYPE
                ENTERPRISE  fkoltg1040Events
                VARIABLES {fkGponOltId, fkGponOnuId}
                DESCRIPTION 
                        "TX-bias high threshold alarm off"
                ::= 392

         gponOnuAniTxpowerLowThreshAlarmOn TRAP-TYPE
                ENTERPRISE  fkoltg1040Events
                VARIABLES {fkGponOltId, fkGponOnuId}
                DESCRIPTION 
                        "TX-power low threshold alarm on"
                ::= 393
         gponOnuAniTxpowerLowThreshAlarmOff TRAP-TYPE
                ENTERPRISE  fkoltg1040Events
                VARIABLES {fkGponOltId, fkGponOnuId}
                DESCRIPTION 
                        "TX-power low threshold alarm off"
                ::= 394
         gponOnuAniTxpowerHighThreshAlarmOn TRAP-TYPE
                ENTERPRISE  fkoltg1040Events
                VARIABLES {fkGponOltId, fkGponOnuId}
                DESCRIPTION 
                        "TX-power high threshold alarm on"
                ::= 395
         gponOnuAniTxpowerHighThreshAlarmOff TRAP-TYPE
                ENTERPRISE  fkoltg1040Events
                VARIABLES {fkGponOltId, fkGponOnuId}
                DESCRIPTION 
                        "TX-power high threshold alarm off"
                ::= 396


END

--
-- fkoltg1040-notification.mib
--
