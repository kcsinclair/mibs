--
-- FKOLTG1040-THRESHOLD-MIB.my
-- MIB generated by MG-SOFT Visual MIB Builder Version 6.0  Build 88
-- Wednesday, June 04, 2008 at 10:28:24
--

	FKOLTG1040-THRESHOLD-MIB DEFINITIONS ::= BEGIN
 
		IMPORTS
			dsSwitchModules			
				FROM FKOLTG1040-SWITCH-MIB			
			ifIndex			
				FROM IF-MIB			
			OBJECT-GROUP			
				FROM SNMPv2-CONF			
			Integer32, Counter64, OBJECT-TYPE, MODULE-IDENTITY			
				FROM SNMPv2-SMI;
	
	
		-- 1.3.6.1.4.1.10428 9 1.9.1.1.2.16
		dsSwitchThreshold MODULE-IDENTITY 
			LAST-UPDATED "200602121527Z"		-- February 12, 2006 at 15:27 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { dsSwitchModules 16 }

		
	
--
-- Node definitions
--
	
		-- 1.3.6.1.4.1.10428 9 1.9.1.1.2.16.1
		dsPortThresholdTable OBJECT-TYPE
			SYNTAX SEQUENCE OF DsPortThresholdEntry
			MAX-ACCESS not-accessible
			STATUS current
			DESCRIPTION
				"Description."
			::= { dsSwitchThreshold 1 }

		
		-- 1.3.6.1.4.1.10428 9 1.9.1.1.2.16.1.1
		dsPortThresholdEntry OBJECT-TYPE
			SYNTAX DsPortThresholdEntry
			MAX-ACCESS not-accessible
			STATUS current
			DESCRIPTION
				"Description."
			INDEX { ifIndex, dsPortThresholdIndex }
			::= { dsPortThresholdTable 1 }

		
		DsPortThresholdEntry ::=
			SEQUENCE { 
				dsPortThresholdIndex
					INTEGER,
				dsPortThresholdDuration
					Integer32,
				dsPortThresholdInterval
					Integer32,
				dsPortThresholdValue
					Counter64,
				dsPortThresholdDirection
					INTEGER
			 }

		-- 1.3.6.1.4.1.10428 9 1.9.1.1.2.16.1.1.1
		dsPortThresholdIndex OBJECT-TYPE
			SYNTAX INTEGER (1..128)
			MAX-ACCESS read-only
			STATUS current
			DESCRIPTION
				"Port number"
			::= { dsPortThresholdEntry 1 }

		
		-- 1.3.6.1.4.1.10428 9 1.9.1.1.2.16.1.1.2
		dsPortThresholdDuration OBJECT-TYPE
			SYNTAX Integer32
			UNITS "10minute"
			MAX-ACCESS read-write
			STATUS current
			DESCRIPTION
				"ThresholdDuration describes amonunt of time which is USER 
				want to monitor traffic for the time.
				"
			::= { dsPortThresholdEntry 2 }

		
		-- 1.3.6.1.4.1.10428 9 1.9.1.1.2.16.1.1.3
		dsPortThresholdInterval OBJECT-TYPE
			SYNTAX Integer32
			UNITS "10minute"
			MAX-ACCESS read-write
			STATUS current
			DESCRIPTION
				"ThresholdInverval describes amonunt of time which is USER 
				want to monitor traffic for the time after the duration time.
				"
			::= { dsPortThresholdEntry 3 }

		
		-- 1.3.6.1.4.1.10428 9 1.9.1.1.2.16.1.1.4
		dsPortThresholdValue OBJECT-TYPE
			SYNTAX Counter64
			UNITS "Mbps"
			MAX-ACCESS read-write
			STATUS current
			DESCRIPTION
				"The value of traffic threshold.
				"
			::= { dsPortThresholdEntry 4 }

		
		-- 1.3.6.1.4.1.10428 9 1.9.1.1.2.16.1.1.5
		dsPortThresholdDirection OBJECT-TYPE
			SYNTAX INTEGER
				{
				rx(1),
				tx(2)
				}
			MAX-ACCESS read-write
			STATUS current
			DESCRIPTION
				"Traffic direction(rx/tx)"
			::= { dsPortThresholdEntry 5 }

		
		-- 1.3.6.1.4.1.10428 9 1.9.1.1.2.16.2
		dsPortThresholdGroup OBJECT-GROUP
			OBJECTS { dsPortThresholdDirection, dsPortThresholdInterval, dsPortThresholdDuration, dsPortThresholdIndex, dsPortThresholdValue
				 }
			STATUS current
			DESCRIPTION 
				"Description."
			::= { dsSwitchThreshold 2 }

		
	
	END

--
-- FKOLTG1040-THRESHOLD-MIB.my
--
