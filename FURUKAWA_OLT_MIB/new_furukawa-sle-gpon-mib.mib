--
-- fk-gpon-mib.mib
-- MIB generated by MG-SOFT Visual MIB Builder Version 6.0  Build 88
-- Monday, April 08, 2013 at 20:49:23
--

--  fk-gpon-mib.mib
-- MIB generated by MG-SOFT Visual MIB Builder Version 6.0  Build 88
-- Friday, December 24, 2010 at 11:42:45
-- 

        FK-GPON-MIB DEFINITIONS ::= BEGIN
 
                IMPORTS
                        fkMgmt                  
                                FROM FKOLTG1040-SMI                     
                        EnableFlag
				FROM FKOLTG1040-TC
			FkControlStatusType, FkControlRequestResultType                 
                                FROM FK-TC-MIB                  
                        OBJECT-GROUP, NOTIFICATION-GROUP                        
                                FROM SNMPv2-CONF                        
                        TimeTicks, IpAddress, Integer32, Gauge32, Counter32, 
                        Counter64, OBJECT-TYPE, MODULE-IDENTITY, NOTIFICATION-TYPE                        
                                FROM SNMPv2-SMI                 
                        TEXTUAL-CONVENTION
                                FROM SNMPv2-TC;
        
        
--  1.3.6.1.4.1.10428 9 1.101.23
-- January 25, 2006 at 17:53 GMT
                -- 1.3.6.1.4.1.10428 9 1.101.23
                fkGpon MODULE-IDENTITY 
                        LAST-UPDATED "200601251753Z"            -- January 25, 2006 at 17:53 GMT
                        ORGANIZATION 
                                "Furukawa Industrial S.A."
                        CONTACT-INFO 
                                "Furukawa Industrial S.A. Produtos Eletricos
        Rua Hasdrubal Bellegard, 820 - CIC
        CEP 81460-120 - Curitiba - Parana - Brasil
        CSC 0800-41-2100
        E-mail: fisa@furukawa.com.br"
                        DESCRIPTION 
                                "The MIB module for Furukawa GPON OLT FK-OLT-G1040."
                        ::= { fkMgmt 23 }
       
--  Node definitions
-- 
-- Node definitions
-- 
-- 1.3.6.1.4.1.10428 9 1.101.23.1
                -- 1.3.6.1.4.1.10428 9 1.101.23.1
                fkGponBase OBJECT IDENTIFIER ::= { fkGpon 1 }

                
--   1.3.6.1.4.1.10428 9 1.101.23.1.1
-- 1.3.6.1.4.1.10428 9 1.101.23.1.1
                -- 1.3.6.1.4.1.10428 9 1.101.23.1.1
                fkGponBaseInfo OBJECT IDENTIFIER ::= { fkGponBase 1 }

                
--   1.3.6.1.4.1.10428 9 1.101.23.1.1.1
-- 1.3.6.1.4.1.10428 9 1.101.23.1.1.1
                -- 1.3.6.1.4.1.10428 9 1.101.23.1.1.1
                fkGponCableDownStatus OBJECT-TYPE
                        SYNTAX EnableFlag
                        MAX-ACCESS read-only
                        STATUS current
                        DESCRIPTION
                                "cable-down admin status"
                        ::= { fkGponBaseInfo 1 }

                
--   1.3.6.1.4.1.10428 9 1.101.23.1.1.2
-- 1.3.6.1.4.1.10428 9 1.101.23.1.1.2
                -- 1.3.6.1.4.1.10428 9 1.101.23.1.1.2
                fkGponCableDownRefCount OBJECT-TYPE
                        SYNTAX Integer32
                        MAX-ACCESS read-only
                        STATUS current
                        DESCRIPTION
                                "cable-down reference count"
                        ::= { fkGponBaseInfo 2 }

                
--   1.3.6.1.4.1.10428 9 1.101.23.1.1.3
-- 1.3.6.1.4.1.10428 9 1.101.23.1.1.3
                -- 1.3.6.1.4.1.10428 9 1.101.23.1.1.3
                fkGponDefaultServiceProfile OBJECT-TYPE
                        SYNTAX OCTET STRING
                        MAX-ACCESS read-only
                        STATUS current
                        DESCRIPTION
                                "The default service profile."
                        ::= { fkGponBaseInfo 3 }

                
--  1.3.6.1.4.1.10428 9 1.101.23.1.1.4
                -- 1.3.6.1.4.1.10428 9 1.101.23.1.1.4
                fkGponSystemOltVendorId OBJECT-TYPE
                        SYNTAX OCTET STRING (SIZE (1..4))
                        MAX-ACCESS read-only
                        STATUS current
                        DESCRIPTION
                                "The OLT Vendor ID. 
                                Only valid in case that this equipment is used as ONT."
                        ::= { fkGponBaseInfo 4 }

                
--  1.3.6.1.4.1.10428 9 1.101.23.1.1.5
-- fkGponSystemOltEquipId OBJECT-TYPE
--      SYNTAX OCTET STRING (SIZE (1..20))
--      MAX-ACCESS read-only
--      STATUS current
--      DESCRIPTION
--              "The OLT Equipment ID. 
--              Only valid in case that this equipment is used as ONT."
--      ::= { fkGponBaseInfo 5 }
-- 1.3.6.1.4.1.10428 9 1.101.23.1.1.5
                -- 1.3.6.1.4.1.10428 9 1.101.23.1.1.5
                fkGponSystemOltVersion OBJECT-TYPE
                        SYNTAX OCTET STRING (SIZE (1..14))
                        MAX-ACCESS read-only
                        STATUS current
                        DESCRIPTION
                                "The OLT Version Info.
                                Only valid in case that this equipment is used as ONT."
                        ::= { fkGponBaseInfo 5 }

                
                -- 1.3.6.1.4.1.10428 9 1.101.23.1.1.6
                fkGponSystemOltModel OBJECT-TYPE
                        SYNTAX OCTET STRING
                        MAX-ACCESS read-only
                        STATUS current
                        DESCRIPTION
                                "The OLT Model.
                                Only valid in case that this equipment is used as ONT."
                        ::= { fkGponBaseInfo 6 }

                
                -- 1.3.6.1.4.1.10428 9 1.101.23.1.1.7
                fkGponSystemOltMac OBJECT-TYPE
                        SYNTAX OCTET STRING (SIZE (0..6))
                        MAX-ACCESS read-only
                        STATUS current
                        DESCRIPTION
                                "The OLT Mac address.
                                Only valid in case that this equipment is used as ONT."
                        ::= { fkGponBaseInfo 7 }

                
                -- 1.3.6.1.4.1.10428 9 1.101.23.1.1.8
                fkGponSystemOltSlot OBJECT-TYPE
                        SYNTAX Integer32
                        MAX-ACCESS read-only
                        STATUS current
                        DESCRIPTION
                                "The OLT Slot index.
                                Only valid in case that this equipment is used as ONT."
                        ::= { fkGponBaseInfo 8 }

                
                -- 1.3.6.1.4.1.10428 9 1.101.23.1.1.9
                fkGponSystemOltPort OBJECT-TYPE
                        SYNTAX Integer32
                        MAX-ACCESS read-only
                        STATUS current
                        DESCRIPTION
                                "The OLT Port index.
                                Only valid in case that this equipment is used as ONT."
                        ::= { fkGponBaseInfo 9 }

                
                -- 1.3.6.1.4.1.10428 9 1.101.23.1.1.10
                fkGponSystemOltOnuId OBJECT-TYPE
                        SYNTAX Integer32
                        MAX-ACCESS read-only
                        STATUS current
                        DESCRIPTION
                                "The OLT ONU index.
                                Only valid in case that this equipment is used as ONT."
                        ::= { fkGponBaseInfo 10 }

                
                -- 1.3.6.1.4.1.10428 9 1.101.23.1.1.11
                fkGponOnuPasswordType OBJECT-TYPE
                        SYNTAX INTEGER
                                {
                                hex(0),
                                ascii(1)
                                }
                        MAX-ACCESS read-only
                        STATUS current
                        DESCRIPTION
                                "The Password Type."
                        ::= { fkGponBaseInfo 11 }

                
                -- 1.3.6.1.4.1.10428 9 1.101.23.1.1.12
                fkGponOnuRxPowerUpdateTime OBJECT-TYPE
                        SYNTAX Integer32 (0..1440)
                        MAX-ACCESS read-only
                        STATUS current
                        DESCRIPTION
                                "The ONU rx-power update Time
                                0: disable
                                1~1440: available values"
                        ::= { fkGponBaseInfo 12 }

                
                -- 1.3.6.1.4.1.10428 9 1.101.23.1.1.13
                fkGponOltMulticastGem OBJECT-TYPE
                        SYNTAX Integer32 (4094..4095)
                        MAX-ACCESS read-only
                        STATUS current
                        DESCRIPTION
                                "The OLT multicast Gem."
                        ::= { fkGponBaseInfo 13 }

                
                -- 1.3.6.1.4.1.10428 9 1.101.23.1.1.14
                fkGponOltInterworkIgmpSnooping OBJECT-TYPE
                        SYNTAX INTEGER
                                {
                                disable(0),
                                enable(1)
                                }
                        MAX-ACCESS read-only
                        STATUS current
                        DESCRIPTION
                                "The OLT interwork igmp-snooping"
                        ::= { fkGponBaseInfo 14 }

                
                -- 1.3.6.1.4.1.10428 9 1.101.23.1.1.15
                fkGponOnuRFPseudowireMode OBJECT-TYPE
                        SYNTAX INTEGER
                                {
                                disable(0),
                                enable(1)
                                }
                        MAX-ACCESS read-only
                        STATUS current
                        DESCRIPTION
                                "The ONU RF Pseudowire Mode"
                        ::= { fkGponBaseInfo 15 }

                
                -- 1.3.6.1.4.1.10428 9 1.101.23.1.1.16
                fkGponOnuRFPseudowireDstMac OBJECT-TYPE
                        SYNTAX OCTET STRING
                        MAX-ACCESS read-only
                        STATUS current
                        DESCRIPTION
                                "The Destination MAC address by ONU RF Pseudowire.
                                This is valid when only fkGponOnuRFPseudowireMode is enable."
                        ::= { fkGponBaseInfo 16 }

                
                -- 1.3.6.1.4.1.10428 9 1.101.23.1.1.17
                fkGponOnuActiveMode OBJECT-TYPE
                        SYNTAX INTEGER
                                {
                                serialNumber(1),
                                registerationId(2)
                                }
                        MAX-ACCESS read-only
                        STATUS current
                        DESCRIPTION
                                "The GPON ONU active mode"
                        ::= { fkGponBaseInfo 17 }

                
                -- 1.3.6.1.4.1.10428 9 1.101.23.1.1.18
                fkGponOnuRFPseudowireEthType OBJECT-TYPE
                        SYNTAX Integer32 (0..65535)
                        MAX-ACCESS read-only
                        STATUS current
                        DESCRIPTION
                                "The RF Pseudowire Ethernet Type"
                        ::= { fkGponBaseInfo 18 }

                
                -- 1.3.6.1.4.1.10428 9 1.101.23.1.1.19
                fkGponOnuRFPseudowireVlanId OBJECT-TYPE
                        SYNTAX Integer32 (0..4094)
                        MAX-ACCESS read-only
                        STATUS current
                        DESCRIPTION
                                "The RF Pseudowire vlan index"
                        ::= { fkGponBaseInfo 19 }

                
--  
-- 
-- 1.3.6.1.4.1.10428 9 1.101.23.1.2
                -- 1.3.6.1.4.1.10428 9 1.101.23.1.2
                fkGponBaseControl OBJECT IDENTIFIER ::= { fkGponBase 2 }

                
--  
-- 
-- 1.3.6.1.4.1.10428 9 1.101.23.1.2.1
                -- 1.3.6.1.4.1.10428 9 1.101.23.1.2.1
                fkGponBaseControlRequest OBJECT-TYPE
                        SYNTAX INTEGER
                                {
                                setCableDownStatus(1),
                                setCableDownRefCnt(2),
                                setDefaultServiceProfile(3),
                                setOnuPasswordType(4),
                                setOnuRxPowerUpdateTime(5),
                                setMulticastGem(6),
                                setInterworkIgmpSnooping(7),
                                setOnuRFPseudowireDstMac(8),
                                setOnuActiveMode(9),
                                setOnuRFPseudowireEthType(10),
                                setOnuRFPseudowireVlanId(11)
                                }
                        MAX-ACCESS read-write
                        STATUS current
                        DESCRIPTION
                                "The request of a user command"
                        ::= { fkGponBaseControl 1 }

                
--  
-- 
-- 1.3.6.1.4.1.10428 9 1.101.23.1.2.2
                -- 1.3.6.1.4.1.10428 9 1.101.23.1.2.2
                fkGponBaseControlStatus OBJECT-TYPE
                        SYNTAX FkControlStatusType
                        MAX-ACCESS read-only
                        STATUS current
                        DESCRIPTION
                                "The status of user command"
                        ::= { fkGponBaseControl 2 }

                
--  1.3.6.1.4.1.10428 9 1.101.23.1.2.3
                -- 1.3.6.1.4.1.10428 9 1.101.23.1.2.3
                fkGponBaseControlTimer OBJECT-TYPE
                        SYNTAX Gauge32
                        MAX-ACCESS read-write
                        STATUS current
                        DESCRIPTION
                                "The maximum time for the manager for a long running user command"
                        ::= { fkGponBaseControl 3 }

                
--  1.3.6.1.4.1.10428 9 1.101.23.1.2.4
                -- 1.3.6.1.4.1.10428 9 1.101.23.1.2.4
                fkGponBaseControlTimeStamp OBJECT-TYPE
                        SYNTAX TimeTicks
                        MAX-ACCESS read-only
                        STATUS current
                        DESCRIPTION
                                "The time stamp of the last command(end of command)"
                        ::= { fkGponBaseControl 4 }

                
--  1.3.6.1.4.1.10428 9 1.101.23.1.2.5
                -- 1.3.6.1.4.1.10428 9 1.101.23.1.2.5
                fkGponBaseControlReqResult OBJECT-TYPE
                        SYNTAX FkControlRequestResultType
                        MAX-ACCESS read-only
                        STATUS current
                        DESCRIPTION
                                "The result of the last user command"
                        ::= { fkGponBaseControl 5 }

                
--  1.3.6.1.4.1.10428 9 1.101.23.1.2.6
                -- 1.3.6.1.4.1.10428 9 1.101.23.1.2.6
                fkGponBaseControlCableDownStatus OBJECT-TYPE
                        SYNTAX EnableFlag
                        MAX-ACCESS read-write
                        STATUS current
                        DESCRIPTION
                                "cable-down admin status"
                        ::= { fkGponBaseControl 6 }

                
--  1.3.6.1.4.1.10428 9 1.101.23.1.2.7
                -- 1.3.6.1.4.1.10428 9 1.101.23.1.2.7
                fkGponBaseControlCableDwonRefCnt OBJECT-TYPE
                        SYNTAX Integer32
                        MAX-ACCESS read-write
                        STATUS current
                        DESCRIPTION
                                "cable-down reference count"
                        ::= { fkGponBaseControl 7 }

                
--  1.3.6.1.4.1.10428 9 1.101.23.1.2.8
                -- 1.3.6.1.4.1.10428 9 1.101.23.1.2.8
                fkGponBaseControlDeaultServiceProfile OBJECT-TYPE
                        SYNTAX OCTET STRING
                        MAX-ACCESS read-write
                        STATUS current
                        DESCRIPTION
                                "The default service profile."
                        ::= { fkGponBaseControl 8 }

                
                -- 1.3.6.1.4.1.10428 9 1.101.23.1.2.9
                fkGponBaseControlOnuPasswordType OBJECT-TYPE
                        SYNTAX INTEGER
                                {
                                hex(0),
                                ascii(1)
                                }
                        MAX-ACCESS read-write
                        STATUS current
                        DESCRIPTION
                                "The Password Type."
                        ::= { fkGponBaseControl 9 }

                
                -- 1.3.6.1.4.1.10428 9 1.101.23.1.2.10
                fkGponBaseControlOnuRxPowerUpdateTime OBJECT-TYPE
                        SYNTAX Integer32 (0..1440)
                        MAX-ACCESS read-write
                        STATUS current
                        DESCRIPTION
                                "The ONU rx-power update time
                                0: disable
                                1~1440: available values"
                        ::= { fkGponBaseControl 10 }

                
                -- 1.3.6.1.4.1.10428 9 1.101.23.1.2.11
                fkGponBaseControlOltMulticastGem OBJECT-TYPE
                        SYNTAX Integer32 (4094..4095)
                        MAX-ACCESS read-write
                        STATUS current
                        DESCRIPTION
                                "The OLT multicast Gem."
                        ::= { fkGponBaseControl 11 }

                
                -- 1.3.6.1.4.1.10428 9 1.101.23.1.2.12
                fkGponBaseControlOltInterworkIgmpSnooping OBJECT-TYPE
                        SYNTAX INTEGER
                                {
                                disable(0),
                                enable(1)
                                }
                        MAX-ACCESS read-only
                        STATUS current
                        DESCRIPTION
                                "The OLT interwork igmp-snooping"
                        ::= { fkGponBaseControl 12 }

                
                -- 1.3.6.1.4.1.10428 9 1.101.23.1.2.13
                fkGponBaseControlOnuRFPseudowireMode OBJECT-TYPE
                        SYNTAX INTEGER
                                {
                                disable(0),
                                enable(1)
                                }
                        MAX-ACCESS read-write
                        STATUS current
                        DESCRIPTION
                                "The ONU RF Pseudowire Mode"
                        ::= { fkGponBaseControl 13 }

                
                -- 1.3.6.1.4.1.10428 9 1.101.23.1.2.14
                fkGponBaseControlOnuRFPseudowireDstMac OBJECT-TYPE
                        SYNTAX OCTET STRING
                        MAX-ACCESS read-write
                        STATUS current
                        DESCRIPTION
                                "The Destination MAC address by ONU RF Pseudowire.
                                This is valid when only fkGponOnuRFPseudowireMode is enable."
                        ::= { fkGponBaseControl 14 }

                
                -- 1.3.6.1.4.1.10428 9 1.101.23.1.2.15
                fkGponbaseControlOnuActiveMode OBJECT-TYPE
                        SYNTAX INTEGER
                                {
                                serialNumber(1),
                                registerationId(2)
                                }
                        MAX-ACCESS read-write
                        STATUS current
                        DESCRIPTION
                                "The GPON ONU active mode"
                        ::= { fkGponBaseControl 15 }

                
                -- 1.3.6.1.4.1.10428 9 1.101.23.1.2.16
                fkGponBaseControlOnuRFPseudowireEthType OBJECT-TYPE
                        SYNTAX Integer32 (0..65535)
                        MAX-ACCESS read-write
                        STATUS current
                        DESCRIPTION
                                "The RF Pseudowire Ethernet Type (0:del)"
                        ::= { fkGponBaseControl 16 }

                
                -- 1.3.6.1.4.1.10428 9 1.101.23.1.2.17
                fkGponBaseControlOnuRFPseudowireVlanId OBJECT-TYPE
                        SYNTAX Integer32 (0..4094)
                        MAX-ACCESS read-write
                        STATUS current
                        DESCRIPTION
                                "The RF Pseudowire vlan index (0:del)"
                        ::= { fkGponBaseControl 17 }

                
--  1.3.6.1.4.1.10428 9 1.101.23.1.3
                -- 1.3.6.1.4.1.10428 9 1.101.23.1.3
                fkGponBaseNotification OBJECT IDENTIFIER ::= { fkGponBase 3 }

                
--  1.3.6.1.4.1.10428 9 1.101.23.1.3.1
                -- 1.3.6.1.4.1.10428 9 1.101.23.1.3.1
                fkGponBaseCableDownStatusChanged NOTIFICATION-TYPE
                        OBJECTS { fkGponBaseControlRequest, fkGponBaseControlTimeStamp, fkGponBaseControlReqResult, fkGponBaseControlCableDownStatus }
                        STATUS current
                        DESCRIPTION 
                                "Description."
                        ::= { fkGponBaseNotification 1 }

                
--  1.3.6.1.4.1.10428 9 1.101.23.1.3.2
                -- 1.3.6.1.4.1.10428 9 1.101.23.1.3.2
                fkGponBaseCableDownRefCntChanged NOTIFICATION-TYPE
                        OBJECTS { fkGponBaseControlRequest, fkGponBaseControlTimeStamp, fkGponBaseControlReqResult, fkGponBaseControlCableDwonRefCnt }
                        STATUS current
                        DESCRIPTION 
                                "Description."
                        ::= { fkGponBaseNotification 2 }

                
--  1.3.6.1.4.1.10428 9 1.101.23.1.3.3
                -- 1.3.6.1.4.1.10428 9 1.101.23.1.3.3
                fkGponBaseDefaultServiceProfileChanged NOTIFICATION-TYPE
                        OBJECTS { fkGponBaseControlRequest, fkGponBaseControlTimeStamp, fkGponBaseControlReqResult, fkGponBaseControlDeaultServiceProfile }
                        STATUS current
                        DESCRIPTION 
                                "Description."
                        ::= { fkGponBaseNotification 3 }

                
                -- 1.3.6.1.4.1.10428 9 1.101.23.1.3.4
                fkGponBasePasswordTypeChanged NOTIFICATION-TYPE
                        OBJECTS { fkGponBaseControlRequest, fkGponBaseControlTimeStamp, fkGponBaseControlReqResult, fkGponBaseControlOnuPasswordType }
                        STATUS current
                        DESCRIPTION 
                                "setOnuPasswordType"
                        ::= { fkGponBaseNotification 4 }

                
                -- 1.3.6.1.4.1.10428 9 1.101.23.1.3.5
                fkGponBaseOnuRxPowerUpdateTimeChanged NOTIFICATION-TYPE
                        OBJECTS { fkGponBaseControlRequest, fkGponBaseControlTimeStamp, fkGponBaseControlReqResult, fkGponBaseControlOnuRxPowerUpdateTime }
                        STATUS current
                        DESCRIPTION 
                                "setOnuRxPowerUpdateTime"
                        ::= { fkGponBaseNotification 5 }

                
                -- 1.3.6.1.4.1.10428 9 1.101.23.1.3.6
                fkGponBaseOltMulticastGemChanged NOTIFICATION-TYPE
                        OBJECTS { fkGponBaseControlRequest, fkGponBaseControlTimeStamp, fkGponBaseControlReqResult, fkGponBaseControlOltMulticastGem }
                        STATUS current
                        DESCRIPTION 
                                "setMulticastGem "
                        ::= { fkGponBaseNotification 6 }

                
                -- 1.3.6.1.4.1.10428 9 1.101.23.1.3.7
                fkGponBaseOltInterworkIgmpSnoopingChanged NOTIFICATION-TYPE
                        OBJECTS { fkGponBaseControlRequest, fkGponBaseControlTimeStamp, fkGponBaseControlReqResult, fkGponBaseControlOltInterworkIgmpSnooping }
                        STATUS current
                        DESCRIPTION 
                                "setInterworkIgmpSnooping "
                        ::= { fkGponBaseNotification 7 }

                
                -- 1.3.6.1.4.1.10428 9 1.101.23.1.3.8
                fkGponBaseOnuRFPseudowireDstMacChanged NOTIFICATION-TYPE
                        OBJECTS { fkGponBaseControlRequest, fkGponBaseControlTimeStamp, fkGponBaseControlReqResult, fkGponBaseControlOnuRFPseudowireMode, fkGponBaseControlOnuRFPseudowireDstMac
                                 }
                        STATUS current
                        DESCRIPTION 
                                "setOnuRFPseudowireDstMac"
                        ::= { fkGponBaseNotification 8 }

                
                -- 1.3.6.1.4.1.10428 9 1.101.23.1.3.9
                fkGponBaseOnuActiveModeChanged NOTIFICATION-TYPE
                        OBJECTS { fkGponBaseControlRequest, fkGponBaseControlTimeStamp, fkGponBaseControlReqResult, fkGponbaseControlOnuActiveMode }
                        STATUS current
                        DESCRIPTION 
                                "setOnuActiveMode"
                        ::= { fkGponBaseNotification 9 }

                
                -- 1.3.6.1.4.1.10428 9 1.101.23.1.3.10
                fkGponBaseOnuRFPseudowireEthTypeChanged NOTIFICATION-TYPE
                        OBJECTS { fkGponBaseControlRequest, fkGponBaseControlTimeStamp, fkGponBaseControlReqResult, fkGponBaseControlOnuRFPseudowireEthType }
                        STATUS current
                        DESCRIPTION 
                                "setOnuRFPseudowireEthType"
                        ::= { fkGponBaseNotification 10 }

                
                -- 1.3.6.1.4.1.10428 9 1.101.23.1.3.11
                fkGponBaseOnuRFPseudowireVlanIdChanged NOTIFICATION-TYPE
                        OBJECTS { fkGponBaseControlRequest, fkGponBaseControlTimeStamp, fkGponBaseControlReqResult, fkGponBaseControlOnuRFPseudowireVlanId }
                        STATUS current
                        DESCRIPTION 
                                "setOnuRFPseudowireVlanId"
                        ::= { fkGponBaseNotification 11 }

                
--  1.3.6.1.4.1.10428 9 1.101.23.2
                -- 1.3.6.1.4.1.10428 9 1.101.23.2
                fkGponOlt OBJECT IDENTIFIER ::= { fkGpon 2 }

                
--  1.3.6.1.4.1.10428 9 1.101.23.2.1
                -- 1.3.6.1.4.1.10428 9 1.101.23.2.1
                fkGponOltTable OBJECT-TYPE
                        SYNTAX SEQUENCE OF FkGponOltEntry
                        MAX-ACCESS not-accessible
                        STATUS current
                        DESCRIPTION
                                "fkGponOltTable"
                        ::= { fkGponOlt 1 }

                
--  1.3.6.1.4.1.10428 9 1.101.23.2.1.1
                -- 1.3.6.1.4.1.10428 9 1.101.23.2.1.1
                fkGponOltEntry OBJECT-TYPE
                        SYNTAX FkGponOltEntry
                        MAX-ACCESS not-accessible
                        STATUS current
                        DESCRIPTION
                                "key: fkGponOltId"
                        INDEX { fkGponOltId }
                        ::= { fkGponOltTable 1 }

                
                FkGponOltEntry ::=
                        SEQUENCE { 
                                fkGponOltId
                                        INTEGER,
                                fkGponOltStatus
                                        INTEGER,
                                fkGponOltDiscoverySerialStart
                                        INTEGER,
                                fkGponOltLinkMaxDistance
                                        INTEGER,
                                fkGponOltKeyExchange
                                        INTEGER,
                                fkGponOltSignalCheck
                                        INTEGER,
                                fkGponOltSignalCheckAutoOnuBlock
                                        INTEGER,
                                fkGponOltDescription
                                        OCTET STRING,
                                fkGponOltAutoToManual
                                        INTEGER,
                                fkGponOltDefaultTcontDBAMode
                                        INTEGER,
                                fkGponOltDefaultTcontFixedBw
                                        INTEGER,
                                fkGponOltDefaultTcontAssuredBw
                                        INTEGER,
                                fkGponOltDefaultTcontMaxBw
                                        INTEGER,
                                fkGponOltDefaultProfileName
                                        OCTET STRING,
                                fkGponOltFecModeUS
                                        INTEGER,
                                fkGponOltFecModeDS
                                        INTEGER,
                                fkGponOltMacAgingTime
                                        INTEGER,
                                fkGponOltTransceiverPort
                                        INTEGER,
                                fkGponOltActivateStatus
                                        INTEGER,
                                fkGponOltProtection
                                        INTEGER,
                                fkGponOltActiveOnuCount
                                        Integer32,
                                fkGponOltInactiveOnuCount
                                        Integer32,
                                fkGponOltLinkUpCount
                                        Counter32,
                                fkGponOltLinkDownCount
                                        Counter32,
                                fkGponOltAuthenCount
                                        Counter32,
                                fkGponOltElapsedTimeAfterClearAuthStats
                                        Counter64,
                                fkGponOltUpElapsedTime
                                        Counter64,
                                fkGponOltDownElapsedTime
                                        Counter64,
                                fkGponOltOpticParam
                                        INTEGER,
                                fkGponOltSrcMacMonitorStatus
                                        EnableFlag,
                                fkGponOltSrcMacMonitorAutoBlock
                                        EnableFlag,
                                fkGponOltSrcMacMonitoEexpireTimeout
                                        INTEGER,
                                fkGponOltTotalUsBw
                                        INTEGER,
                                fkGponOltMaxOnuCount
                                        INTEGER,
                                fkGponOltAntiSpoofingFilter
                                        INTEGER,
                                fkGponOltAntiSpoofingExpireTime
                                        INTEGER,
                                fkGponOltBwBEMethod
                                        INTEGER,
                                fkGponOltDsGemMapping
                                        INTEGER,
                                fkGponOltFixedTcontCount
                                        Integer32,
                                fkGponOltDynamicTcontCount
                                        Integer32,
                                fkGponOltPortCount
                                        Integer32,
                                fkGponOltDeactiveMonitorStatus
                                        INTEGER,
                                fkGponOltDeactiveMonitorRaisePercent
                                        Integer32,
                                fkGponOltDeactiveMonitorClearPercent
                                        Integer32,
                                fkGponOltDeactiveMonitorPeriod
                                        Integer32,
                                fkGponOltDeactiveMonitorActiveOnuCount
                                        Integer32,
                                fkGponOltDeactiveMonitorCurrentPercent
                                        Integer32,
                                fkGponOltDeactiveMonitorInAlamStatus
                                        INTEGER,
                                fkGponOltBerUpInterval
                                        Integer32,
                                fkGponOltBerDownInterval
                                        Integer32,
                                fkGponOltBerSfThreshold
                                        Integer32,
                                fkGponOltBerSdThreshold
                                        Integer32,
                                fkGponOltUsFlowMapping
                                        INTEGER,
                                fkGponOltDsQosMappingQueueCount
                                        Integer32,
                                fkGponOltDsQosMappingCos0Queue
                                        Integer32,
                                fkGponOltDsQosMappingCos1Queue
                                        Integer32,
                                fkGponOltDsQosMappingCos2Queue
                                        Integer32,
                                fkGponOltDsQosMappingCos3Queue
                                        Integer32,
                                fkGponOltDsQosMappingCos4Queue
                                        Integer32,
                                fkGponOltDsQosMappingCos5Queue
                                        Integer32,
                                fkGponOltDsQosMappingCos6Queue
                                        Integer32,
                                fkGponOltDsQosMappingCos7Queue
                                        Integer32,
                                fkGponOltDsQosMappingMode
                                        INTEGER,
                                fkGponOltPortServiceStatus
                                        INTEGER
                         }

--  1.3.6.1.4.1.10428 9 1.101.23.2.1.1.1
                -- 1.3.6.1.4.1.10428 9 1.101.23.2.1.1.1
                fkGponOltId OBJECT-TYPE
                        SYNTAX INTEGER (1..512)
                        MAX-ACCESS read-only
                        STATUS current
                        DESCRIPTION
                                "Gpon Olt Index"
                        ::= { fkGponOltEntry 1 }

                
--  1.3.6.1.4.1.10428 9 1.101.23.2.1.1.2
                -- 1.3.6.1.4.1.10428 9 1.101.23.2.1.1.2
                fkGponOltStatus OBJECT-TYPE
                        SYNTAX INTEGER
                                {
                                disable(0),
                                notReady(1),
                                inactive(2),
                                active(3),
                                activePending(4),
                                deactivePending(5),
                                switchOverPending(6),
                                unknown(255)
                                }
                        MAX-ACCESS read-only
                        STATUS current
                        DESCRIPTION
                                "Gpon Olt Status"
                        ::= { fkGponOltEntry 2 }

                
--  1.3.6.1.4.1.10428 9 1.101.23.2.1.1.3
                -- 1.3.6.1.4.1.10428 9 1.101.23.2.1.1.3
                fkGponOltDiscoverySerialStart OBJECT-TYPE
                        SYNTAX INTEGER (1..65535)
                        UNITS "seconds"
                        MAX-ACCESS read-only
                        STATUS current
                        DESCRIPTION
                                "Serial number acquisition Interval Time (seconds)"
                        ::= { fkGponOltEntry 3 }

                
--  1.3.6.1.4.1.10428 9 1.101.23.2.1.1.4
                -- 1.3.6.1.4.1.10428 9 1.101.23.2.1.1.4
                fkGponOltLinkMaxDistance OBJECT-TYPE
                        SYNTAX INTEGER (1..65535)
                        MAX-ACCESS read-only
                        STATUS current
                        DESCRIPTION
                                "Optical link  distance configuration.
                                30       10 ~ 30 Km
                                40       20 ~ 40 Km
                                50       30 ~ 50 Km
                                60       40 ~ 60 Km
                                default  default distance (0~20Km)"
                        ::= { fkGponOltEntry 4 }

                
--  1.3.6.1.4.1.10428 9 1.101.23.2.1.1.5
                -- 1.3.6.1.4.1.10428 9 1.101.23.2.1.1.5
                fkGponOltKeyExchange OBJECT-TYPE
                        SYNTAX INTEGER (1..65535)
                        UNITS "seconds"
                        MAX-ACCESS read-only
                        STATUS current
                        DESCRIPTION
                                "Units:seconds, Encryption key exchange configuration."
                        ::= { fkGponOltEntry 5 }

                
--  1.3.6.1.4.1.10428 9 1.101.23.2.1.1.6
                -- 1.3.6.1.4.1.10428 9 1.101.23.2.1.1.6
                fkGponOltSignalCheck OBJECT-TYPE
                        SYNTAX INTEGER
                                {
                                enable(1),
                                disable(2)
                                }
                        MAX-ACCESS read-only
                        STATUS current
                        DESCRIPTION
                                "Optic signal check."
                        ::= { fkGponOltEntry 6 }

                
--  1.3.6.1.4.1.10428 9 1.101.23.2.1.1.7
                -- 1.3.6.1.4.1.10428 9 1.101.23.2.1.1.7
                fkGponOltSignalCheckAutoOnuBlock OBJECT-TYPE
                        SYNTAX INTEGER
                                {
                                enable(1),
                                disable(2)
                                }
                        MAX-ACCESS read-only
                        STATUS current
                        DESCRIPTION
                                "block ONU automatically using optic power off."
                        ::= { fkGponOltEntry 7 }

                
--  1.3.6.1.4.1.10428 9 1.101.23.2.1.1.8
                -- 1.3.6.1.4.1.10428 9 1.101.23.2.1.1.8
                fkGponOltDescription OBJECT-TYPE
                        SYNTAX OCTET STRING
                        MAX-ACCESS read-only
                        STATUS current
                        DESCRIPTION
                                "OLT description."
                        ::= { fkGponOltEntry 8 }

                
--  1.3.6.1.4.1.10428 9 1.101.23.2.1.1.9
                -- 1.3.6.1.4.1.10428 9 1.101.23.2.1.1.9
                fkGponOltAutoToManual OBJECT-TYPE
                        SYNTAX INTEGER
                                {
                                enable(1),
                                disable(2)
                                }
                        MAX-ACCESS read-only
                        STATUS current
                        DESCRIPTION
                                "Automatically changes to manual register"
                        ::= { fkGponOltEntry 9 }

                
--  1.3.6.1.4.1.10428 9 1.101.23.2.1.1.10
                -- 1.3.6.1.4.1.10428 9 1.101.23.2.1.1.10
                fkGponOltDefaultTcontDBAMode OBJECT-TYPE
                        SYNTAX INTEGER
                                {
                                none(0),
                                nsr(1),
                                sr(2),
                                fixed(3)
                                }
                        MAX-ACCESS read-only
                        STATUS current
                        DESCRIPTION
                                "Default status reports received from ONUs"
                        ::= { fkGponOltEntry 10 }

                
--  1.3.6.1.4.1.10428 9 1.101.23.2.1.1.11
                -- 1.3.6.1.4.1.10428 9 1.101.23.2.1.1.11
                fkGponOltDefaultTcontFixedBw OBJECT-TYPE
                        SYNTAX INTEGER (1..65535)
                        UNITS "64kbps"
                        MAX-ACCESS read-only
                        STATUS current
                        DESCRIPTION
                                "Default upstream fixed bandwidth.<128-1031616>"
                        ::= { fkGponOltEntry 11 }

                
--  1.3.6.1.4.1.10428 9 1.101.23.2.1.1.12
                -- 1.3.6.1.4.1.10428 9 1.101.23.2.1.1.12
                fkGponOltDefaultTcontAssuredBw OBJECT-TYPE
                        SYNTAX INTEGER (1..65535)
                        UNITS "64kbps"
                        MAX-ACCESS read-only
                        STATUS current
                        DESCRIPTION
                                "Default upstream assured bandwidth.<0-1031616>"
                        ::= { fkGponOltEntry 12 }

                
--  1.3.6.1.4.1.10428 9 1.101.23.2.1.1.13
                -- 1.3.6.1.4.1.10428 9 1.101.23.2.1.1.13
                fkGponOltDefaultTcontMaxBw OBJECT-TYPE
                        SYNTAX INTEGER (1..65535)
                        UNITS "64kbps"
                        MAX-ACCESS read-only
                        STATUS current
                        DESCRIPTION
                                "Default upstream max bandwidth.<128-1031616>"
                        ::= { fkGponOltEntry 13 }

                
--  1.3.6.1.4.1.10428 9 1.101.23.2.1.1.14
                -- 1.3.6.1.4.1.10428 9 1.101.23.2.1.1.14
                fkGponOltDefaultProfileName OBJECT-TYPE
                        SYNTAX OCTET STRING
                        MAX-ACCESS read-only
                        STATUS current
                        DESCRIPTION
                                "Default Profile Name"
                        ::= { fkGponOltEntry 14 }

                
--  1.3.6.1.4.1.10428 9 1.101.23.2.1.1.15
                -- 1.3.6.1.4.1.10428 9 1.101.23.2.1.1.15
                fkGponOltFecModeUS OBJECT-TYPE
                        SYNTAX INTEGER
                                {
                                enable(1),
                                disable(2)
                                }
                        MAX-ACCESS read-only
                        STATUS current
                        DESCRIPTION
                                "UpStream FEC mode"
                        ::= { fkGponOltEntry 15 }

                
--  1.3.6.1.4.1.10428 9 1.101.23.2.1.1.16
                -- 1.3.6.1.4.1.10428 9 1.101.23.2.1.1.16
                fkGponOltFecModeDS OBJECT-TYPE
                        SYNTAX INTEGER
                                {
                                enable(1),
                                disable(2)
                                }
                        MAX-ACCESS read-only
                        STATUS current
                        DESCRIPTION
                                "DownStream FEC mode"
                        ::= { fkGponOltEntry 16 }

                
--  1.3.6.1.4.1.10428 9 1.101.23.2.1.1.17
                -- 1.3.6.1.4.1.10428 9 1.101.23.2.1.1.17
                fkGponOltMacAgingTime OBJECT-TYPE
                        SYNTAX INTEGER (30..2147480)
                        MAX-ACCESS read-only
                        STATUS current
                        DESCRIPTION
                                "Mac Aging Time"
                        ::= { fkGponOltEntry 17 }

                
--  1.3.6.1.4.1.10428 9 1.101.23.2.1.1.18
                -- 1.3.6.1.4.1.10428 9 1.101.23.2.1.1.18
                fkGponOltTransceiverPort OBJECT-TYPE
                        SYNTAX INTEGER
                                {
                                portA(1),
                                portB(2)
                                }
                        MAX-ACCESS read-only
                        STATUS current
                        DESCRIPTION
                                "Transceiver Port"
                        ::= { fkGponOltEntry 18 }

                
--  1.3.6.1.4.1.10428 9 1.101.23.2.1.1.19
                -- 1.3.6.1.4.1.10428 9 1.101.23.2.1.1.19
                fkGponOltActivateStatus OBJECT-TYPE
                        SYNTAX INTEGER
                                {
                                activate(1),
                                deActivate(2)
                                }
                        MAX-ACCESS read-only
                        STATUS current
                        DESCRIPTION
                                "OLT activation status."
                        ::= { fkGponOltEntry 19 }

                
--  1.3.6.1.4.1.10428 9 1.101.23.2.1.1.20
                -- 1.3.6.1.4.1.10428 9 1.101.23.2.1.1.20
                fkGponOltProtection OBJECT-TYPE
                        SYNTAX INTEGER
                                {
                                enable(1),
                                disable(2)
                                }
                        MAX-ACCESS read-only
                        STATUS current
                        DESCRIPTION
                                "OLT protection status."
                        ::= { fkGponOltEntry 20 }

                
--  1.3.6.1.4.1.10428 9 1.101.23.2.1.1.21
                -- 1.3.6.1.4.1.10428 9 1.101.23.2.1.1.21
                fkGponOltActiveOnuCount OBJECT-TYPE
                        SYNTAX Integer32
                        MAX-ACCESS read-only
                        STATUS current
                        DESCRIPTION
                                "The active ONU count."
                        ::= { fkGponOltEntry 21 }

                
--  1.3.6.1.4.1.10428 9 1.101.23.2.1.1.22
                -- 1.3.6.1.4.1.10428 9 1.101.23.2.1.1.22
                fkGponOltInactiveOnuCount OBJECT-TYPE
                        SYNTAX Integer32
                        MAX-ACCESS read-only
                        STATUS current
                        DESCRIPTION
                                "The inactive ONU count."
                        ::= { fkGponOltEntry 22 }

                
--  1.3.6.1.4.1.10428 9 1.101.23.2.1.1.23
                -- 1.3.6.1.4.1.10428 9 1.101.23.2.1.1.23
                fkGponOltLinkUpCount OBJECT-TYPE
                        SYNTAX Counter32
                        MAX-ACCESS read-only
                        STATUS current
                        DESCRIPTION
                                "The link up count"
                        ::= { fkGponOltEntry 23 }

                
--  1.3.6.1.4.1.10428 9 1.101.23.2.1.1.24
                -- 1.3.6.1.4.1.10428 9 1.101.23.2.1.1.24
                fkGponOltLinkDownCount OBJECT-TYPE
                        SYNTAX Counter32
                        MAX-ACCESS read-only
                        STATUS current
                        DESCRIPTION
                                "The link down count
                                "
                        ::= { fkGponOltEntry 24 }

                
--  1.3.6.1.4.1.10428 9 1.101.23.2.1.1.25
                -- 1.3.6.1.4.1.10428 9 1.101.23.2.1.1.25
                fkGponOltAuthenCount OBJECT-TYPE
                        SYNTAX Counter32
                        MAX-ACCESS read-only
                        STATUS current
                        DESCRIPTION
                                "The number of password-authed onu."
                        ::= { fkGponOltEntry 25 }

                
--  1.3.6.1.4.1.10428 9 1.101.23.2.1.1.26
                -- 1.3.6.1.4.1.10428 9 1.101.23.2.1.1.26
                fkGponOltElapsedTimeAfterClearAuthStats OBJECT-TYPE
                        SYNTAX Counter64
                        UNITS "1 sec"
                        MAX-ACCESS read-only
                        STATUS current
                        DESCRIPTION
                                "The elapsed time after clearing auth-related statistics"
                        ::= { fkGponOltEntry 26 }

                
--  1.3.6.1.4.1.10428 9 1.101.23.2.1.1.27
                -- 1.3.6.1.4.1.10428 9 1.101.23.2.1.1.27
                fkGponOltUpElapsedTime OBJECT-TYPE
                        SYNTAX Counter64
                        UNITS "1 sec"
                        MAX-ACCESS read-only
                        STATUS current
                        DESCRIPTION
                                "The elapsed time from link is up."
                        ::= { fkGponOltEntry 27 }

                
--  1.3.6.1.4.1.10428 9 1.101.23.2.1.1.28
                -- 1.3.6.1.4.1.10428 9 1.101.23.2.1.1.28
                fkGponOltDownElapsedTime OBJECT-TYPE
                        SYNTAX Counter64
                        UNITS "1 sec"
                        MAX-ACCESS read-only
                        STATUS current
                        DESCRIPTION
                                "The elapsed time from link is down."
                        ::= { fkGponOltEntry 28 }

                
--  1.3.6.1.4.1.10428 9 1.101.23.2.1.1.29
                -- 1.3.6.1.4.1.10428 9 1.101.23.2.1.1.29
                fkGponOltOpticParam OBJECT-TYPE
                        SYNTAX INTEGER
                                {
                                default(1),
                                user1(2),
                                unknown(255)
                                }
                        MAX-ACCESS read-only
                        STATUS current
                        DESCRIPTION
                                "The optic-module parmater.
                                default : Default optic configuration - FUJITSU relaxy configuration.
                                user1   : User1 optic configuration - Broadlight suggested."
                        ::= { fkGponOltEntry 29 }

                
--  1.3.6.1.4.1.10428 9 1.101.23.2.1.1.30
                -- 1.3.6.1.4.1.10428 9 1.101.23.2.1.1.30
                fkGponOltSrcMacMonitorStatus OBJECT-TYPE
                        SYNTAX EnableFlag
                        MAX-ACCESS read-only
                        STATUS current
                        DESCRIPTION
                                "The Source Mac Monitor status."
                        ::= { fkGponOltEntry 30 }

                
--  1.3.6.1.4.1.10428 9 1.101.23.2.1.1.31
                -- 1.3.6.1.4.1.10428 9 1.101.23.2.1.1.31
                fkGponOltSrcMacMonitorAutoBlock OBJECT-TYPE
                        SYNTAX EnableFlag
                        MAX-ACCESS read-only
                        STATUS current
                        DESCRIPTION
                                "The Source Mac Monitor Auto block status"
                        ::= { fkGponOltEntry 31 }

                
--  1.3.6.1.4.1.10428 9 1.101.23.2.1.1.32
                -- 1.3.6.1.4.1.10428 9 1.101.23.2.1.1.32
                fkGponOltSrcMacMonitoEexpireTimeout OBJECT-TYPE
                        SYNTAX INTEGER (0 | 60..65535)
                        MAX-ACCESS read-only
                        STATUS current
                        DESCRIPTION
                                "The Source Mac Monitor Expire time."
                        ::= { fkGponOltEntry 32 }

                
--  1.3.6.1.4.1.10428 9 1.101.23.2.1.1.33
                -- 1.3.6.1.4.1.10428 9 1.101.23.2.1.1.33
                fkGponOltTotalUsBw OBJECT-TYPE
                        SYNTAX INTEGER (1031616..1244160 | 140000000)
                        MAX-ACCESS read-only
                        STATUS current
                        DESCRIPTION
                                "The OLT Total US bandwidth."
                        ::= { fkGponOltEntry 33 }

                
                -- 1.3.6.1.4.1.10428 9 1.101.23.2.1.1.34
                fkGponOltMaxOnuCount OBJECT-TYPE
                        SYNTAX INTEGER (1..65535)
                        MAX-ACCESS read-only
                        STATUS current
                        DESCRIPTION
                                "The max ONU count"
                        ::= { fkGponOltEntry 34 }

                
                -- 1.3.6.1.4.1.10428 9 1.101.23.2.1.1.35
                fkGponOltAntiSpoofingFilter OBJECT-TYPE
                        SYNTAX INTEGER
                                {
                                enable(1),
                                disable(2)
                                }
                        MAX-ACCESS read-only
                        STATUS current
                        DESCRIPTION
                                "The Anti-Spoofing Configuration"
                        ::= { fkGponOltEntry 35 }

                
                -- 1.3.6.1.4.1.10428 9 1.101.23.2.1.1.36
                fkGponOltAntiSpoofingExpireTime OBJECT-TYPE
                        SYNTAX INTEGER (0 | 60..65535)
                        MAX-ACCESS read-only
                        STATUS current
                        DESCRIPTION
                                "The Expire Timeout Configuration.
                                Timeout Seconds (Default : 300 sec)
                                "
                        ::= { fkGponOltEntry 36 }

                
                -- 1.3.6.1.4.1.10428 9 1.101.23.2.1.1.37
                fkGponOltBwBEMethod OBJECT-TYPE
                        SYNTAX INTEGER
                                {
                                guaranteed(0),
                                maximum(1)
                                }
                        MAX-ACCESS read-only
                        STATUS current
                        DESCRIPTION
                                "The OLT band-width scheduler."
                        ::= { fkGponOltEntry 37 }

                
                -- 1.3.6.1.4.1.10428 9 1.101.23.2.1.1.38
                fkGponOltDsGemMapping OBJECT-TYPE
                        SYNTAX INTEGER
                                {
                                mac(0),
                                macVid(1),
                                vid(2),
                                perFlowByMac(3),
                                perFlowByMacVid(4)
                                }
                        MAX-ACCESS read-only
                        STATUS current
                        DESCRIPTION
                                "The OLT ds gem mapping."
                        ::= { fkGponOltEntry 38 }

                
                -- 1.3.6.1.4.1.10428 9 1.101.23.2.1.1.39
                fkGponOltFixedTcontCount OBJECT-TYPE
                        SYNTAX Integer32 (0..384)
                        MAX-ACCESS read-only
                        STATUS current
                        DESCRIPTION
                                "The fixed tcont count. (0 is disable)."
                        ::= { fkGponOltEntry 39 }

                
                -- 1.3.6.1.4.1.10428 9 1.101.23.2.1.1.40
                fkGponOltDynamicTcontCount OBJECT-TYPE
                        SYNTAX Integer32 (0..384)
                        MAX-ACCESS read-only
                        STATUS current
                        DESCRIPTION
                                "The dynamic tcont count. (0 is disable)."
                        ::= { fkGponOltEntry 40 }

                
                -- 1.3.6.1.4.1.10428 9 1.101.23.2.1.1.41
                fkGponOltPortCount OBJECT-TYPE
                        SYNTAX Integer32 (0..3966)
                        MAX-ACCESS read-only
                        STATUS current
                        DESCRIPTION
                                "The port count. (0 is disable)."
                        ::= { fkGponOltEntry 41 }

                
                -- 1.3.6.1.4.1.10428 9 1.101.23.2.1.1.42
                fkGponOltDeactiveMonitorStatus OBJECT-TYPE
                        SYNTAX INTEGER
                                {
                                disable(0),
                                enable(1)
                                }
                        MAX-ACCESS read-only
                        STATUS current
                        DESCRIPTION
                                "The deactive monitor status."
                        ::= { fkGponOltEntry 42 }

                
                -- 1.3.6.1.4.1.10428 9 1.101.23.2.1.1.43
                fkGponOltDeactiveMonitorRaisePercent OBJECT-TYPE
                        SYNTAX Integer32 (1..100)
                        MAX-ACCESS read-only
                        STATUS current
                        DESCRIPTION
                                "The deactive monitor raise percent."
                        ::= { fkGponOltEntry 43 }

                
                -- 1.3.6.1.4.1.10428 9 1.101.23.2.1.1.44
                fkGponOltDeactiveMonitorClearPercent OBJECT-TYPE
                        SYNTAX Integer32 (1..100)
                        MAX-ACCESS read-only
                        STATUS current
                        DESCRIPTION
                                "The deactive monitor clear percent."
                        ::= { fkGponOltEntry 44 }

                
                -- 1.3.6.1.4.1.10428 9 1.101.23.2.1.1.45
                fkGponOltDeactiveMonitorPeriod OBJECT-TYPE
                        SYNTAX Integer32 (10..86400)
                        MAX-ACCESS read-only
                        STATUS current
                        DESCRIPTION
                                "The deactive monitor period. (per 10 multiple)"
                        ::= { fkGponOltEntry 45 }

                
                -- 1.3.6.1.4.1.10428 9 1.101.23.2.1.1.46
                fkGponOltDeactiveMonitorActiveOnuCount OBJECT-TYPE
                        SYNTAX Integer32
                        MAX-ACCESS read-only
                        STATUS current
                        DESCRIPTION
                                "the OLT deactive monitor active ONU count."
                        ::= { fkGponOltEntry 46 }

                
                -- 1.3.6.1.4.1.10428 9 1.101.23.2.1.1.47
                fkGponOltDeactiveMonitorCurrentPercent OBJECT-TYPE
                        SYNTAX Integer32 (0..100)
                        MAX-ACCESS read-only
                        STATUS current
                        DESCRIPTION
                                "The OLT deactive monitor current percent.(%)"
                        ::= { fkGponOltEntry 47 }

                
                -- 1.3.6.1.4.1.10428 9 1.101.23.2.1.1.48
                fkGponOltDeactiveMonitorInAlamStatus OBJECT-TYPE
                        SYNTAX INTEGER
                                {
                                off(0),
                                on(1)
                                }
                        MAX-ACCESS read-only
                        STATUS current
                        DESCRIPTION
                                "The OLT deactive monitor alarm status."
                        ::= { fkGponOltEntry 48 }

                
                -- 1.3.6.1.4.1.10428 9 1.101.23.2.1.1.49
                fkGponOltBerUpInterval OBJECT-TYPE
                        SYNTAX Integer32 (1000..10000)
                        MAX-ACCESS read-only
                        STATUS current
                        DESCRIPTION
                                "The OLT BER up interval"
                        ::= { fkGponOltEntry 49 }

                
                -- 1.3.6.1.4.1.10428 9 1.101.23.2.1.1.50
                fkGponOltBerDownInterval OBJECT-TYPE
                        SYNTAX Integer32 (1000..10000)
                        MAX-ACCESS read-only
                        STATUS current
                        DESCRIPTION
                                "The OLT BER down interval"
                        ::= { fkGponOltEntry 50 }

                
                -- 1.3.6.1.4.1.10428 9 1.101.23.2.1.1.51
                fkGponOltBerSfThreshold OBJECT-TYPE
                        SYNTAX Integer32 (3..8)
                        MAX-ACCESS read-only
                        STATUS current
                        DESCRIPTION
                                "The OLT BER SF threshold"
                        ::= { fkGponOltEntry 51 }

                
                -- 1.3.6.1.4.1.10428 9 1.101.23.2.1.1.52
                fkGponOltBerSdThreshold OBJECT-TYPE
                        SYNTAX Integer32 (4..9)
                        MAX-ACCESS read-only
                        STATUS current
                        DESCRIPTION
                                "The OLT BER SD threshold"
                        ::= { fkGponOltEntry 52 }

                
                -- 1.3.6.1.4.1.10428 9 1.101.23.2.1.1.53
                fkGponOltUsFlowMapping OBJECT-TYPE
                        SYNTAX INTEGER
                                {
                                perMapper(0),
                                perGem(1)
                                }
                        MAX-ACCESS read-only
                        STATUS current
                        DESCRIPTION
                                "The OLT us flow mapping"
                        ::= { fkGponOltEntry 53 }

                
--  1.3.6.1.4.1.10428 9 1.101.23.2.1.1.54
                -- 1.3.6.1.4.1.10428 9 1.101.23.2.1.1.54
                fkGponOltDsQosMappingQueueCount OBJECT-TYPE
                        SYNTAX Integer32 (0..8)
                        MAX-ACCESS read-only
                        STATUS current
                        DESCRIPTION
                                "The OLT ds Qos mapping Queue Count"
                        ::= { fkGponOltEntry 54 }

                
--  1.3.6.1.4.1.10428 9 1.101.23.2.1.1.55
                -- 1.3.6.1.4.1.10428 9 1.101.23.2.1.1.55
                fkGponOltDsQosMappingCos0Queue OBJECT-TYPE
                        SYNTAX Integer32 (0..7)
                        MAX-ACCESS read-only
                        STATUS current
                        DESCRIPTION
                                "The OLT ds Qos mapping Cos 0 to Priority Queue"
                        ::= { fkGponOltEntry 55 }

                
--  1.3.6.1.4.1.10428 9 1.101.23.2.1.1.56
                -- 1.3.6.1.4.1.10428 9 1.101.23.2.1.1.56
                fkGponOltDsQosMappingCos1Queue OBJECT-TYPE
                        SYNTAX Integer32 (0..7)
                        MAX-ACCESS read-only
                        STATUS current
                        DESCRIPTION
                                "The OLT ds Qos mapping Cos 1 to Priority Queue"
                        ::= { fkGponOltEntry 56 }

                
--  1.3.6.1.4.1.10428 9 1.101.23.2.1.1.57
                -- 1.3.6.1.4.1.10428 9 1.101.23.2.1.1.57
                fkGponOltDsQosMappingCos2Queue OBJECT-TYPE
                        SYNTAX Integer32 (0..7)
                        MAX-ACCESS read-only
                        STATUS current
                        DESCRIPTION
                                "The OLT ds Qos mapping Cos 2 to Priority Queue"
                        ::= { fkGponOltEntry 57 }

                
--  1.3.6.1.4.1.10428 9 1.101.23.2.1.1.58
                -- 1.3.6.1.4.1.10428 9 1.101.23.2.1.1.58
                fkGponOltDsQosMappingCos3Queue OBJECT-TYPE
                        SYNTAX Integer32 (0..7)
                        MAX-ACCESS read-only
                        STATUS current
                        DESCRIPTION
                                "The OLT ds Qos mapping Cos 3 to Priority Queue"
                        ::= { fkGponOltEntry 58 }

                
--  1.3.6.1.4.1.10428 9 1.101.23.2.1.1.59
                -- 1.3.6.1.4.1.10428 9 1.101.23.2.1.1.59
                fkGponOltDsQosMappingCos4Queue OBJECT-TYPE
                        SYNTAX Integer32 (0..7)
                        MAX-ACCESS read-only
                        STATUS current
                        DESCRIPTION
                                "The OLT ds Qos mapping Cos 4 to Priority Queue"
                        ::= { fkGponOltEntry 59 }

                
--  1.3.6.1.4.1.10428 9 1.101.23.2.1.1.60
                -- 1.3.6.1.4.1.10428 9 1.101.23.2.1.1.60
                fkGponOltDsQosMappingCos5Queue OBJECT-TYPE
                        SYNTAX Integer32 (0..7)
                        MAX-ACCESS read-only
                        STATUS current
                        DESCRIPTION
                                "The OLT ds Qos mapping Cos 5 to Priority Queue"
                        ::= { fkGponOltEntry 60 }

                
--  1.3.6.1.4.1.10428 9 1.101.23.2.1.1.61
                -- 1.3.6.1.4.1.10428 9 1.101.23.2.1.1.61
                fkGponOltDsQosMappingCos6Queue OBJECT-TYPE
                        SYNTAX Integer32 (0..7)
                        MAX-ACCESS read-only
                        STATUS current
                        DESCRIPTION
                                "The OLT ds Qos mapping Cos 6 to Priority Queue"
                        ::= { fkGponOltEntry 61 }

                
--  1.3.6.1.4.1.10428 9 1.101.23.2.1.1.62
                -- 1.3.6.1.4.1.10428 9 1.101.23.2.1.1.62
                fkGponOltDsQosMappingCos7Queue OBJECT-TYPE
                        SYNTAX Integer32 (0..7)
                        MAX-ACCESS read-only
                        STATUS current
                        DESCRIPTION
                                "The OLT ds Qos mapping Cos 7 to Priority Queue"
                        ::= { fkGponOltEntry 62 }

                
--  1.3.6.1.4.1.10428 9 1.101.23.2.1.1.63
                -- 1.3.6.1.4.1.10428 9 1.101.23.2.1.1.63
                fkGponOltDsQosMappingMode OBJECT-TYPE
                        SYNTAX INTEGER
                                {
                                none(0),
                                mac(1),
                                macVid(2),
                                vid(3)
                                }
                        MAX-ACCESS read-only
                        STATUS current
                        DESCRIPTION
                                "The OLT us flow mapping"
                        ::= { fkGponOltEntry 63 }

                
                -- 1.3.6.1.4.1.10428 9 1.101.23.2.1.1.64
                fkGponOltPortServiceStatus OBJECT-TYPE
                        SYNTAX INTEGER
                                {
                                disable(0),
                                enable(1)
                                }
                        MAX-ACCESS read-only
                        STATUS current
                        DESCRIPTION
                                "The GPON port service status."
                        ::= { fkGponOltEntry 64 }

                
--  1.3.6.1.4.1.10428 9 1.101.23.2.2
                -- 1.3.6.1.4.1.10428 9 1.101.23.2.2
                fkGponOltControl OBJECT IDENTIFIER ::= { fkGponOlt 2 }

                
--  1.3.6.1.4.1.10428 9 1.101.23.2.2.1
                -- 1.3.6.1.4.1.10428 9 1.101.23.2.2.1
                fkGponOltControlRequest OBJECT-TYPE
                        SYNTAX INTEGER
                                {
                                setDiscoverySerialStart(1),
                                setDiscoverySerialStop(2),
                                setLinkMaxDistance(3),
                                setKeyExchangeStart(4),
                                setKeyExchangeStop(5),
                                setSignalCheck(6),
                                setSignalCheckAutoOnuBlock(7),
                                setDescription(8),
                                setAutoToManual(9),
                                setDefaultTcont(10),
                                setDefaultTcontRemove(11),
                                setDefaultProfile(12),
                                setDefaultProfileRemove(13),
                                setOltFecModeUS(14),
                                setOltFecModeDs(15),
                                setOltMacAgingTime(16),
                                setOltTransceiverPort(17),
                                setOltActivateStatus(18),
                                setOltProtection(19),
                                clearOltAuthStats(20),
                                setOltOpticParam(21),
                                setOltSrcMacMonitor(22),
                                setOltTotalUsBw(23),
                                setMaxOnuCount(24),
                                setAntiSpoofingFilter(25),
                                setBwBEMethod(26),
                                setDsGemMapping(27),
                                setFixedTcontCount(28),
                                setDynamicTcontCount(29),
                                setPortCount(30),
                                setDeactiveMonitorStatus(31),
                                setDeactiveMonitorRaisePercent(32),
                                setDeactiveMonitorClearPercent(33),
                                setDeactiveMonitorPeriod(34),
                                clearDeactiveMonitorAlarm(35),
                                setOltRegister(36),
                                setOltBerUsInterval(37),
                                setOltBerDsInterval(38),
                                setOltBerSfThreshold(39),
                                setOltBerSdThreshold(40),
                                setUsFlowMapping(41),
                                setDsQosMapping(42),
                                clearDsQosMapping(43),
                                setDsQosMappingMode(44)
                                }
                        MAX-ACCESS read-write
                        STATUS current
                        DESCRIPTION
                                "The request of a user command"
                        ::= { fkGponOltControl 1 }

                
--  1.3.6.1.4.1.10428 9 1.101.23.2.2.2
                -- 1.3.6.1.4.1.10428 9 1.101.23.2.2.2
                fkGponOltControlStatus OBJECT-TYPE
                        SYNTAX FkControlStatusType
                        MAX-ACCESS read-only
                        STATUS current
                        DESCRIPTION
                                "The status of user command"
                        ::= { fkGponOltControl 2 }

                
--  1.3.6.1.4.1.10428 9 1.101.23.2.2.3
                -- 1.3.6.1.4.1.10428 9 1.101.23.2.2.3
                fkGponOltControlTimer OBJECT-TYPE
                        SYNTAX Gauge32
                        MAX-ACCESS read-write
                        STATUS current
                        DESCRIPTION
                                "The maximum time for the manager for a long running user command"
                        ::= { fkGponOltControl 3 }

                
--  1.3.6.1.4.1.10428 9 1.101.23.2.2.4
                -- 1.3.6.1.4.1.10428 9 1.101.23.2.2.4
                fkGponOltControlTimeStamp OBJECT-TYPE
                        SYNTAX TimeTicks
                        MAX-ACCESS read-only
                        STATUS current
                        DESCRIPTION
                                "The time stamp of the last command(end of command)"
                        ::= { fkGponOltControl 4 }

                
--  1.3.6.1.4.1.10428 9 1.101.23.2.2.5
                -- 1.3.6.1.4.1.10428 9 1.101.23.2.2.5
                fkGponOltControlReqResult OBJECT-TYPE
                        SYNTAX FkControlRequestResultType
                        MAX-ACCESS read-only
                        STATUS current
                        DESCRIPTION
                                "The result of the last user command"
                        ::= { fkGponOltControl 5 }

                
--  1.3.6.1.4.1.10428 9 1.101.23.2.2.6
                -- 1.3.6.1.4.1.10428 9 1.101.23.2.2.6
                fkGponOltControllndex OBJECT-TYPE
                        SYNTAX INTEGER (1..65535)
                        MAX-ACCESS read-write
                        STATUS current
                        DESCRIPTION
                                "Gpon Olt Index"
                        ::= { fkGponOltControl 6 }

                
--  1.3.6.1.4.1.10428 9 1.101.23.2.2.7
                -- 1.3.6.1.4.1.10428 9 1.101.23.2.2.7
                fkGponOltControlDiscoverySerialStart OBJECT-TYPE
                        SYNTAX INTEGER (1..65535)
                        MAX-ACCESS read-write
                        STATUS current
                        DESCRIPTION
                                "Serial number acquisition Interval Time (seconds) <1-1200>"
                        ::= { fkGponOltControl 7 }

                
--  1.3.6.1.4.1.10428 9 1.101.23.2.2.8
                -- 1.3.6.1.4.1.10428 9 1.101.23.2.2.8
                fkGponOltControlLinkMaxDistance OBJECT-TYPE
                        SYNTAX INTEGER (1..65535)
                        MAX-ACCESS read-write
                        STATUS current
                        DESCRIPTION
                                "Optical link  distance configuration.
                                  30       10 ~ 30 Km
                                  40       20 ~ 40 Km
                                  50       30 ~ 50 Km
                                  60       40 ~ 60 Km
                                  default  default distance (0~20Km)
                                "
                        ::= { fkGponOltControl 8 }

                
--  1.3.6.1.4.1.10428 9 1.101.23.2.2.9
                -- 1.3.6.1.4.1.10428 9 1.101.23.2.2.9
                fkGponOltControlKeyExchange OBJECT-TYPE
                        SYNTAX INTEGER (1..65535)
                        MAX-ACCESS read-only
                        STATUS current
                        DESCRIPTION
                                "Units:seconds, Encryption key exchange configuration. <10-86400>"
                        ::= { fkGponOltControl 9 }

                
--  1.3.6.1.4.1.10428 9 1.101.23.2.2.10
                -- 1.3.6.1.4.1.10428 9 1.101.23.2.2.10
                fkGponOltControlSignalCheck OBJECT-TYPE
                        SYNTAX INTEGER
                                {
                                enable(1),
                                disable(2)
                                }
                        MAX-ACCESS read-only
                        STATUS current
                        DESCRIPTION
                                "Optic signal check."
                        ::= { fkGponOltControl 10 }

                
--  1.3.6.1.4.1.10428 9 1.101.23.2.2.11
                -- 1.3.6.1.4.1.10428 9 1.101.23.2.2.11
                fkGponOltControlSignalCheckAutoOnuBlock OBJECT-TYPE
                        SYNTAX INTEGER
                                {
                                enable(1),
                                disable(2)
                                }
                        MAX-ACCESS read-only
                        STATUS current
                        DESCRIPTION
                                "block ONU automatically using optic power off."
                        ::= { fkGponOltControl 11 }

                
--  1.3.6.1.4.1.10428 9 1.101.23.2.2.12
                -- 1.3.6.1.4.1.10428 9 1.101.23.2.2.12
                fkGponOltControlDescription OBJECT-TYPE
                        SYNTAX OCTET STRING
                        MAX-ACCESS read-write
                        STATUS current
                        DESCRIPTION
                                "OLT Description."
                        ::= { fkGponOltControl 12 }

                
--  1.3.6.1.4.1.10428 9 1.101.23.2.2.13
                -- 1.3.6.1.4.1.10428 9 1.101.23.2.2.13
                fkGponOltControlAutoToManual OBJECT-TYPE
                        SYNTAX INTEGER
                                {
                                enable(1),
                                disable(2)
                                }
                        MAX-ACCESS read-write
                        STATUS current
                        DESCRIPTION
                                "Automatically changes to manual register"
                        ::= { fkGponOltControl 13 }

                
--  1.3.6.1.4.1.10428 9 1.101.23.2.2.14
                -- 1.3.6.1.4.1.10428 9 1.101.23.2.2.14
                fkGponOltControlDefaultTcontDBAMode OBJECT-TYPE
                        SYNTAX INTEGER
                                {
                                nsr(1),
                                sr(2),
                                fixed(3)
                                }
                        MAX-ACCESS read-write
                        STATUS current
                        DESCRIPTION
                                "Default status reports received from ONUs"
                        ::= { fkGponOltControl 14 }

                
--  1.3.6.1.4.1.10428 9 1.101.23.2.2.15
                -- 1.3.6.1.4.1.10428 9 1.101.23.2.2.15
                fkGponOltControlDefaultTcontFixedBw OBJECT-TYPE
                        SYNTAX INTEGER (1..65535)
                        MAX-ACCESS read-write
                        STATUS current
                        DESCRIPTION
                                "Default upstream fixed bandwidth.<128-1031616>"
                        ::= { fkGponOltControl 15 }

                
--  1.3.6.1.4.1.10428 9 1.101.23.2.2.16
                -- 1.3.6.1.4.1.10428 9 1.101.23.2.2.16
                fkGponOltControlDefaultTcontAssuredBw OBJECT-TYPE
                        SYNTAX INTEGER (1..65535)
                        MAX-ACCESS read-write
                        STATUS current
                        DESCRIPTION
                                "Default upstream assured bandwidth.<0-1031616>"
                        ::= { fkGponOltControl 16 }

                
--  1.3.6.1.4.1.10428 9 1.101.23.2.2.17
                -- 1.3.6.1.4.1.10428 9 1.101.23.2.2.17
                fkGponOltControlDefaultTcontMaxBw OBJECT-TYPE
                        SYNTAX INTEGER (1..65535)
                        MAX-ACCESS read-write
                        STATUS current
                        DESCRIPTION
                                "Default upstream max bandwidth.<128-1031616>"
                        ::= { fkGponOltControl 17 }

                
--  1.3.6.1.4.1.10428 9 1.101.23.2.2.18
                -- 1.3.6.1.4.1.10428 9 1.101.23.2.2.18
                fkGponOltControlDefaultProfileName OBJECT-TYPE
                        SYNTAX OCTET STRING
                        MAX-ACCESS read-write
                        STATUS current
                        DESCRIPTION
                                "Default Profile Name"
                        ::= { fkGponOltControl 18 }

                
--  1.3.6.1.4.1.10428 9 1.101.23.2.2.19
                -- 1.3.6.1.4.1.10428 9 1.101.23.2.2.19
                fkGponOltControlFecModeUS OBJECT-TYPE
                        SYNTAX INTEGER
                                {
                                enable(1),
                                disable(2)
                                }
                        MAX-ACCESS read-write
                        STATUS current
                        DESCRIPTION
                                "UpStream FEC mode"
                        ::= { fkGponOltControl 19 }

                
--  1.3.6.1.4.1.10428 9 1.101.23.2.2.20
                -- 1.3.6.1.4.1.10428 9 1.101.23.2.2.20
                fkGponOltControlFecModeDS OBJECT-TYPE
                        SYNTAX INTEGER
                                {
                                enable(1),
                                disable(2)
                                }
                        MAX-ACCESS read-write
                        STATUS current
                        DESCRIPTION
                                "DownStream FEC mode"
                        ::= { fkGponOltControl 20 }

                
--  1.3.6.1.4.1.10428 9 1.101.23.2.2.21
                -- 1.3.6.1.4.1.10428 9 1.101.23.2.2.21
                fkGponOltControlMacAgingTime OBJECT-TYPE
                        SYNTAX INTEGER (30..2147480)
                        MAX-ACCESS read-write
                        STATUS current
                        DESCRIPTION
                                "Mac Aging Time"
                        ::= { fkGponOltControl 21 }

                
--  1.3.6.1.4.1.10428 9 1.101.23.2.2.22
                -- 1.3.6.1.4.1.10428 9 1.101.23.2.2.22
                fkGponOltControlTransceiverPort OBJECT-TYPE
                        SYNTAX INTEGER
                                {
                                portA(1),
                                portB(2)
                                }
                        MAX-ACCESS read-write
                        STATUS current
                        DESCRIPTION
                                "Transceiver Port"
                        ::= { fkGponOltControl 22 }

                
--  1.3.6.1.4.1.10428 9 1.101.23.2.2.23
                -- 1.3.6.1.4.1.10428 9 1.101.23.2.2.23
                fkGponOltControlActivateStatus OBJECT-TYPE
                        SYNTAX INTEGER
                                {
                                activate(1),
                                deActivate(2)
                                }
                        MAX-ACCESS read-write
                        STATUS current
                        DESCRIPTION
                                "OLT activation status."
                        ::= { fkGponOltControl 23 }

                
--  1.3.6.1.4.1.10428 9 1.101.23.2.2.24
                -- 1.3.6.1.4.1.10428 9 1.101.23.2.2.24
                fkGponOltControlProtection OBJECT-TYPE
                        SYNTAX INTEGER
                                {
                                enable(1),
                                disable(2)
                                }
                        MAX-ACCESS read-write
                        STATUS current
                        DESCRIPTION
                                "OLT protection status."
                        ::= { fkGponOltControl 24 }

                
--  1.3.6.1.4.1.10428 9 1.101.23.2.2.25
                -- 1.3.6.1.4.1.10428 9 1.101.23.2.2.25
                fkGponOltControlOpticParam OBJECT-TYPE
                        SYNTAX INTEGER
                                {
                                default(1),
                                user1(2)
                                }
                        MAX-ACCESS read-write
                        STATUS current
                        DESCRIPTION
                                "The optic-module parmater.
                                default : Default optic configuration - FUJITSU relaxy configuration.
                                user1   : User1 optic configuration - Broadlight suggested.
                                "
                        ::= { fkGponOltControl 25 }

                
--  1.3.6.1.4.1.10428 9 1.101.23.2.2.26
                -- 1.3.6.1.4.1.10428 9 1.101.23.2.2.26
                fkGponOltControlSrcMacMonitorStatus OBJECT-TYPE
                        SYNTAX EnableFlag
                        MAX-ACCESS read-write
                        STATUS current
                        DESCRIPTION
                                "The Source Mac Monitor status."
                        ::= { fkGponOltControl 26 }

                
--  1.3.6.1.4.1.10428 9 1.101.23.2.2.27
                -- 1.3.6.1.4.1.10428 9 1.101.23.2.2.27
                fkGponOltControlSrcMacMonitorAutoBlock OBJECT-TYPE
                        SYNTAX EnableFlag
                        MAX-ACCESS read-write
                        STATUS current
                        DESCRIPTION
                                "The Source Mac Monitor Auto block status"
                        ::= { fkGponOltControl 27 }

                
--  1.3.6.1.4.1.10428 9 1.101.23.2.2.28
                -- 1.3.6.1.4.1.10428 9 1.101.23.2.2.28
                fkGponOltControlSrcMacMonitoEexpireTimeout OBJECT-TYPE
                        SYNTAX INTEGER (0 | 60..65535)
                        MAX-ACCESS read-write
                        STATUS current
                        DESCRIPTION
                                "The Source Mac Monitor Expire time."
                        ::= { fkGponOltControl 28 }

                
--  1.3.6.1.4.1.10428 9 1.101.23.2.2.29
                -- 1.3.6.1.4.1.10428 9 1.101.23.2.2.29
                fkGponOltControlTotalUsBw OBJECT-TYPE
                        SYNTAX INTEGER (1031616..1244160 | 140000000)
                        MAX-ACCESS read-write
                        STATUS current
                        DESCRIPTION
                                "The OLT Total US bandwidth."
                        ::= { fkGponOltControl 29 }

                
                -- 1.3.6.1.4.1.10428 9 1.101.23.2.2.30
                fkGponOltControlMaxOnuCount OBJECT-TYPE
                        SYNTAX INTEGER (1..65535)
                        MAX-ACCESS read-write
                        STATUS current
                        DESCRIPTION
                                "The max ONU count"
                        ::= { fkGponOltControl 30 }

                
                -- 1.3.6.1.4.1.10428 9 1.101.23.2.2.31
                fkGponOltControlAntiSpoofingFilter OBJECT-TYPE
                        SYNTAX INTEGER
                                {
                                enable(1),
                                disable(2)
                                }
                        MAX-ACCESS read-write
                        STATUS current
                        DESCRIPTION
                                "The Anti-Spoofing Configuration"
                        ::= { fkGponOltControl 31 }

                
                -- 1.3.6.1.4.1.10428 9 1.101.23.2.2.32
                fkGponOltControlAntiSpoofingExpireTime OBJECT-TYPE
                        SYNTAX INTEGER (0 | 60..65535)
                        MAX-ACCESS read-write
                        STATUS current
                        DESCRIPTION
                                "The Expire Timeout Configuration.
                                Timeout Seconds (Default : 300 sec)"
                        ::= { fkGponOltControl 32 }

                
                -- 1.3.6.1.4.1.10428 9 1.101.23.2.2.33
                fkGponOltControlBwBEMethod OBJECT-TYPE
                        SYNTAX INTEGER
                                {
                                guaranteed(0),
                                maximum(1)
                                }
                        MAX-ACCESS read-write
                        STATUS current
                        DESCRIPTION
                                "The OLT band-width scheduler."
                        ::= { fkGponOltControl 33 }

                
                -- 1.3.6.1.4.1.10428 9 1.101.23.2.2.34
                fkGponOltControlDsGemMapping OBJECT-TYPE
                        SYNTAX INTEGER
                                {
                                mac(0),
                                macVid(1),
                                vid(2),
                                perFlowByMac(3),
                                perFlowByMacVid(4)
                                }
                        MAX-ACCESS read-write
                        STATUS current
                        DESCRIPTION
                                "The OLT ds gem mapping."
                        ::= { fkGponOltControl 34 }

                
                -- 1.3.6.1.4.1.10428 9 1.101.23.2.2.35
                fkGponOltControlFixedTcontCount OBJECT-TYPE
                        SYNTAX Integer32 (0..384)
                        MAX-ACCESS read-write
                        STATUS current
                        DESCRIPTION
                                "The fixed tcont count"
                        ::= { fkGponOltControl 35 }

                
                -- 1.3.6.1.4.1.10428 9 1.101.23.2.2.36
                fkGponOltControlDynamicTcontCount OBJECT-TYPE
                        SYNTAX Integer32 (0..384)
                        MAX-ACCESS read-write
                        STATUS current
                        DESCRIPTION
                                "The dynamic tcont count"
                        ::= { fkGponOltControl 36 }

                
                -- 1.3.6.1.4.1.10428 9 1.101.23.2.2.37
                fkGponOltControlPortCount OBJECT-TYPE
                        SYNTAX Integer32 (0..3966)
                        MAX-ACCESS read-write
                        STATUS current
                        DESCRIPTION
                                "The port count"
                        ::= { fkGponOltControl 37 }

                
                -- 1.3.6.1.4.1.10428 9 1.101.23.2.2.38
                fkGponOltControlDeactiveMonitorStatus OBJECT-TYPE
                        SYNTAX INTEGER
                                {
                                disable(0),
                                enable(1)
                                }
                        MAX-ACCESS read-write
                        STATUS current
                        DESCRIPTION
                                "The deactive monitor status."
                        ::= { fkGponOltControl 38 }

                
                -- 1.3.6.1.4.1.10428 9 1.101.23.2.2.39
                fkGponOltControlDeactiveMonitorRaisePercent OBJECT-TYPE
                        SYNTAX Integer32 (1..100)
                        MAX-ACCESS read-write
                        STATUS current
                        DESCRIPTION
                                "The deactive monitor raise percent."
                        ::= { fkGponOltControl 39 }

                
                -- 1.3.6.1.4.1.10428 9 1.101.23.2.2.40
                fkGponOltControlDeactiveMonitorClearPercent OBJECT-TYPE
                        SYNTAX Integer32 (1..100)
                        MAX-ACCESS read-write
                        STATUS current
                        DESCRIPTION
                                "The deactive monitor clear percent."
                        ::= { fkGponOltControl 40 }

                
                -- 1.3.6.1.4.1.10428 9 1.101.23.2.2.41
                fkGponOltControlDeactiveMonitorPeriod OBJECT-TYPE
                        SYNTAX Integer32 (10..86400)
                        MAX-ACCESS read-write
                        STATUS current
                        DESCRIPTION
                                "The deactive monitor period. (per 10 multiple)"
                        ::= { fkGponOltControl 41 }

                
                -- 1.3.6.1.4.1.10428 9 1.101.23.2.2.42
                fkGponOltControlBerUpInterval OBJECT-TYPE
                        SYNTAX Integer32 (1000..10000)
                        MAX-ACCESS read-write
                        STATUS current
                        DESCRIPTION
                                "The OLT BER up interval"
                        ::= { fkGponOltControl 42 }

                
                -- 1.3.6.1.4.1.10428 9 1.101.23.2.2.43
                fkGponOltControlBerDownInterval OBJECT-TYPE
                        SYNTAX Integer32 (1000..10000)
                        MAX-ACCESS read-write
                        STATUS current
                        DESCRIPTION
                                "The OLT BER down interval"
                        ::= { fkGponOltControl 43 }

                
                -- 1.3.6.1.4.1.10428 9 1.101.23.2.2.44
                fkGponOltControlBerSfThreshold OBJECT-TYPE
                        SYNTAX Integer32 (3..8)
                        MAX-ACCESS read-write
                        STATUS current
                        DESCRIPTION
                                "The OLT BER SF threshold"
                        ::= { fkGponOltControl 44 }

                
                -- 1.3.6.1.4.1.10428 9 1.101.23.2.2.45
                fkGponOltControlBerSdThreshold OBJECT-TYPE
                        SYNTAX Integer32 (4..9)
                        MAX-ACCESS read-write
                        STATUS current
                        DESCRIPTION
                                "The OLT BER SD threshold"
                        ::= { fkGponOltControl 45 }

                
                -- 1.3.6.1.4.1.10428 9 1.101.23.2.2.46
                fkGponOltControlUsFlowMapping OBJECT-TYPE
                        SYNTAX INTEGER
                                {
                                perMapper(0),
                                perGem(1)
                                }
                        MAX-ACCESS read-write
                        STATUS current
                        DESCRIPTION
                                "The OLT us flow mapping"
                        ::= { fkGponOltControl 46 }

                
--  1.3.6.1.4.1.10428 9 1.101.23.2.2.47
                -- 1.3.6.1.4.1.10428 9 1.101.23.2.2.47
                fkGponOltControlDsQosMappingQueueCount OBJECT-TYPE
                        SYNTAX Integer32 (0..8)
                        MAX-ACCESS read-write
                        STATUS current
                        DESCRIPTION
                                "The OLT ds Qos mapping Queue Count"
                        ::= { fkGponOltControl 47 }

                
--  1.3.6.1.4.1.10428 9 1.101.23.2.2.48
                -- 1.3.6.1.4.1.10428 9 1.101.23.2.2.48
                fkGponOltControlDsQosMappingCos0Queue OBJECT-TYPE
                        SYNTAX Integer32 (0..7)
                        MAX-ACCESS read-write
                        STATUS current
                        DESCRIPTION
                                "The OLT ds Qos mapping Cos 0 to Priority Queue"
                        ::= { fkGponOltControl 48 }

                
--  1.3.6.1.4.1.10428 9 1.101.23.2.2.49
                -- 1.3.6.1.4.1.10428 9 1.101.23.2.2.49
                fkGponOltControlDsQosMappingCos1Queue OBJECT-TYPE
                        SYNTAX Integer32 (0..7)
                        MAX-ACCESS read-write
                        STATUS current
                        DESCRIPTION
                                "The OLT ds Qos mapping Cos 1 to Priority Queue"
                        ::= { fkGponOltControl 49 }

                
--  1.3.6.1.4.1.10428 9 1.101.23.2.2.50
                -- 1.3.6.1.4.1.10428 9 1.101.23.2.2.50
                fkGponOltControlDsQosMappingCos2Queue OBJECT-TYPE
                        SYNTAX Integer32 (0..7)
                        MAX-ACCESS read-write
                        STATUS current
                        DESCRIPTION
                                "The OLT ds Qos mapping Cos 2 to Priority Queue"
                        ::= { fkGponOltControl 50 }

                
--  1.3.6.1.4.1.10428 9 1.101.23.2.2.51
                -- 1.3.6.1.4.1.10428 9 1.101.23.2.2.51
                fkGponOltControlDsQosMappingCos3Queue OBJECT-TYPE
                        SYNTAX Integer32 (0..7)
                        MAX-ACCESS read-write
                        STATUS current
                        DESCRIPTION
                                "The OLT ds Qos mapping Cos 3 to Priority Queue"
                        ::= { fkGponOltControl 51 }

                
--  1.3.6.1.4.1.10428 9 1.101.23.2.2.52
                -- 1.3.6.1.4.1.10428 9 1.101.23.2.2.52
                fkGponOltControlDsQosMappingCos4Queue OBJECT-TYPE
                        SYNTAX Integer32 (0..7)
                        MAX-ACCESS read-write
                        STATUS current
                        DESCRIPTION
                                "The OLT ds Qos mapping Cos 4 to Priority Queue"
                        ::= { fkGponOltControl 52 }

                
--  1.3.6.1.4.1.10428 9 1.101.23.2.2.53
                -- 1.3.6.1.4.1.10428 9 1.101.23.2.2.53
                fkGponOltControlDsQosMappingCos5Queue OBJECT-TYPE
                        SYNTAX Integer32 (0..7)
                        MAX-ACCESS read-write
                        STATUS current
                        DESCRIPTION
                                "The OLT ds Qos mapping Cos 5 to Priority Queue"
                        ::= { fkGponOltControl 53 }

                
--  1.3.6.1.4.1.10428 9 1.101.23.2.2.54
                -- 1.3.6.1.4.1.10428 9 1.101.23.2.2.54
                fkGponOltControlDsQosMappingCos6Queue OBJECT-TYPE
                        SYNTAX Integer32 (0..7)
                        MAX-ACCESS read-write
                        STATUS current
                        DESCRIPTION
                                "The OLT ds Qos mapping Cos 6 to Priority Queue"
                        ::= { fkGponOltControl 54 }

                
--  1.3.6.1.4.1.10428 9 1.101.23.2.2.55
                -- 1.3.6.1.4.1.10428 9 1.101.23.2.2.55
                fkGponOltControlDsQosMappingCos7Queue OBJECT-TYPE
                        SYNTAX Integer32 (0..7)
                        MAX-ACCESS read-write
                        STATUS current
                        DESCRIPTION
                                "The OLT ds Qos mapping Cos 7 to Priority Queue"
                        ::= { fkGponOltControl 55 }

                
--  1.3.6.1.4.1.10428 9 1.101.23.2.2.56
                -- 1.3.6.1.4.1.10428 9 1.101.23.2.2.56
                fkGponOltControlDsQosMappingMode OBJECT-TYPE
                        SYNTAX INTEGER
                                {
                                none(0),
                                mac(1),
                                macVid(2),
                                vid(3)
                                }
                        MAX-ACCESS read-write
                        STATUS current
                        DESCRIPTION
                                "The OLT us flow mapping"
                        ::= { fkGponOltControl 56 }

                
--  1.3.6.1.4.1.10428 9 1.101.23.2.3
                -- 1.3.6.1.4.1.10428 9 1.101.23.2.3
                fkGponOltNotification OBJECT IDENTIFIER ::= { fkGponOlt 3 }

                
--  1.3.6.1.4.1.10428 9 1.101.23.2.3.1
                -- 1.3.6.1.4.1.10428 9 1.101.23.2.3.1
                fkGponOltDiscoverySerialStarted NOTIFICATION-TYPE
                        OBJECTS { fkGponOltControlRequest, fkGponOltControlTimeStamp, fkGponOltControlReqResult, fkGponOltControllndex, fkGponOltControlDiscoverySerialStart
                                 }
                        STATUS current
                        DESCRIPTION 
                                "Description."
                        ::= { fkGponOltNotification 1 }

                
--  1.3.6.1.4.1.10428 9 1.101.23.2.3.2
                -- 1.3.6.1.4.1.10428 9 1.101.23.2.3.2
                fkGponOltDiscoverySerialStopped NOTIFICATION-TYPE
                        OBJECTS { fkGponOltControlRequest, fkGponOltControlTimeStamp, fkGponOltControlReqResult, fkGponOltControllndex }
                        STATUS current
                        DESCRIPTION 
                                "Description."
                        ::= { fkGponOltNotification 2 }

                
--  1.3.6.1.4.1.10428 9 1.101.23.2.3.3
                -- 1.3.6.1.4.1.10428 9 1.101.23.2.3.3
                fkGponOltLinkMaxDistanceChanged NOTIFICATION-TYPE
                        OBJECTS { fkGponOltControlRequest, fkGponOltControlTimeStamp, fkGponOltControlReqResult, fkGponOltControllndex, fkGponOltControlLinkMaxDistance
                                 }
                        STATUS current
                        DESCRIPTION 
                                "Description."
                        ::= { fkGponOltNotification 3 }

                
--  1.3.6.1.4.1.10428 9 1.101.23.2.3.4
                -- 1.3.6.1.4.1.10428 9 1.101.23.2.3.4
                fkGponOltKeyExchangeStarted NOTIFICATION-TYPE
                        OBJECTS { fkGponOltControlRequest, fkGponOltControlTimeStamp, fkGponOltControlReqResult, fkGponOltControllndex, fkGponOltControlKeyExchange
                                 }
                        STATUS current
                        DESCRIPTION 
                                "Description."
                        ::= { fkGponOltNotification 4 }

                
--  1.3.6.1.4.1.10428 9 1.101.23.2.3.5
                -- 1.3.6.1.4.1.10428 9 1.101.23.2.3.5
                fkGponOltKeyExchangeStopped NOTIFICATION-TYPE
                        OBJECTS { fkGponOltControlRequest, fkGponOltControlTimeStamp, fkGponOltControlReqResult, fkGponOltControllndex }
                        STATUS current
                        DESCRIPTION 
                                "Description."
                        ::= { fkGponOltNotification 5 }

                
--  1.3.6.1.4.1.10428 9 1.101.23.2.3.6
                -- 1.3.6.1.4.1.10428 9 1.101.23.2.3.6
                fkGponOltSignalCheckChanged NOTIFICATION-TYPE
                        OBJECTS { fkGponOltControlRequest, fkGponOltControlTimeStamp, fkGponOltControlReqResult, fkGponOltControllndex, fkGponOltControlSignalCheck
                                 }
                        STATUS current
                        DESCRIPTION 
                                "Description."
                        ::= { fkGponOltNotification 6 }

                
--  1.3.6.1.4.1.10428 9 1.101.23.2.3.7
                -- 1.3.6.1.4.1.10428 9 1.101.23.2.3.7
                fkGponOltSignalCheckAutoOnuBlockChanged NOTIFICATION-TYPE
                        OBJECTS { fkGponOltControlRequest, fkGponOltControlTimeStamp, fkGponOltControlReqResult, fkGponOltControllndex, fkGponOltControlSignalCheckAutoOnuBlock
                                 }
                        STATUS current
                        DESCRIPTION 
                                "Description."
                        ::= { fkGponOltNotification 7 }

                
--  1.3.6.1.4.1.10428 9 1.101.23.2.3.8
                -- 1.3.6.1.4.1.10428 9 1.101.23.2.3.8
                fkGponOltDescriptionChanged NOTIFICATION-TYPE
                        OBJECTS { fkGponOltControlRequest, fkGponOltControlTimeStamp, fkGponOltControlReqResult, fkGponOltControllndex, fkGponOltControlDescription
                                 }
                        STATUS current
                        DESCRIPTION 
                                "Description."
                        ::= { fkGponOltNotification 8 }

                
--   
-- 1.3.6.1.4.1.10428 9 1.101.23.2.3.9
                -- 1.3.6.1.4.1.10428 9 1.101.23.2.3.9
                fkGponOltAutoToManualChanged NOTIFICATION-TYPE
                        OBJECTS { fkGponOltControlRequest, fkGponOltControlTimeStamp, fkGponOltControlReqResult, fkGponOltControllndex, fkGponOltControlAutoToManual
                                 }
                        STATUS current
                        DESCRIPTION 
                                "Description."
                        ::= { fkGponOltNotification 9 }

                
--  1.3.6.1.4.1.10428 9 1.101.23.2.3.10
                -- 1.3.6.1.4.1.10428 9 1.101.23.2.3.10
                fkGponOltDefaultTcontChanged NOTIFICATION-TYPE
                        OBJECTS { fkGponOltControlRequest, fkGponOltControlTimeStamp, fkGponOltControlReqResult, fkGponOltControllndex, fkGponOltControlDefaultTcontDBAMode, 
                                fkGponOltControlDefaultTcontFixedBw, fkGponOltControlDefaultTcontAssuredBw, fkGponOltControlDefaultTcontMaxBw }
                        STATUS current
                        DESCRIPTION 
                                "Description."
                        ::= { fkGponOltNotification 10 }

                
--  1.3.6.1.4.1.10428 9 1.101.23.2.3.11
                -- 1.3.6.1.4.1.10428 9 1.101.23.2.3.11
                fkGponOltDefaultTcontRemoved NOTIFICATION-TYPE
                        OBJECTS { fkGponOltControlRequest, fkGponOltControlTimeStamp, fkGponOltControlReqResult, fkGponOltControllndex }
                        STATUS current
                        DESCRIPTION 
                                "Description."
                        ::= { fkGponOltNotification 11 }

                
--  1.3.6.1.4.1.10428 9 1.101.23.2.3.12
                -- 1.3.6.1.4.1.10428 9 1.101.23.2.3.12
                fkGponOltDefaultProfileChanged NOTIFICATION-TYPE
                        OBJECTS { fkGponOltControlRequest, fkGponOltControlTimeStamp, fkGponOltControlReqResult, fkGponOltControllndex, fkGponOltControlDefaultProfileName
                                 }
                        STATUS current
                        DESCRIPTION 
                                "Description."
                        ::= { fkGponOltNotification 12 }

                
--  1.3.6.1.4.1.10428 9 1.101.23.2.3.13
                -- 1.3.6.1.4.1.10428 9 1.101.23.2.3.13
                fkGponOltDefaultProfileRemoved NOTIFICATION-TYPE
                        OBJECTS { fkGponOltControlRequest, fkGponOltControlTimeStamp, fkGponOltControlReqResult, fkGponOltControllndex }
                        STATUS current
                        DESCRIPTION 
                                "Description."
                        ::= { fkGponOltNotification 13 }

                
--  1.3.6.1.4.1.10428 9 1.101.23.2.3.14
                -- 1.3.6.1.4.1.10428 9 1.101.23.2.3.14
                fkGponOltFecModeUSChanged NOTIFICATION-TYPE
                        OBJECTS { fkGponOltControlRequest, fkGponOltControlTimeStamp, fkGponOltControlReqResult, fkGponOltControllndex, fkGponOltControlFecModeUS
                                 }
                        STATUS current
                        DESCRIPTION 
                                "Description."
                        ::= { fkGponOltNotification 14 }

                
--  1.3.6.1.4.1.10428 9 1.101.23.2.3.15
                -- 1.3.6.1.4.1.10428 9 1.101.23.2.3.15
                fkGponOltFecModeDSChanged NOTIFICATION-TYPE
                        OBJECTS { fkGponOltControlRequest, fkGponOltControlTimeStamp, fkGponOltControlReqResult, fkGponOltControllndex, fkGponOltControlFecModeDS
                                 }
                        STATUS current
                        DESCRIPTION 
                                "Description."
                        ::= { fkGponOltNotification 15 }

                
--  1.3.6.1.4.1.10428 9 1.101.23.2.3.16
                -- 1.3.6.1.4.1.10428 9 1.101.23.2.3.16
                fkGponOltMacAgingTimeChanged NOTIFICATION-TYPE
                        OBJECTS { fkGponOltControlRequest, fkGponOltControlTimeStamp, fkGponOltControlReqResult, fkGponOltControllndex, fkGponOltControlMacAgingTime
                                 }
                        STATUS current
                        DESCRIPTION 
                                "Description."
                        ::= { fkGponOltNotification 16 }

                
--  1.3.6.1.4.1.10428 9 1.101.23.2.3.17
                -- 1.3.6.1.4.1.10428 9 1.101.23.2.3.17
                fkGponOltTransceiverPortChanged NOTIFICATION-TYPE
                        OBJECTS { fkGponOltControlRequest, fkGponOltControlTimeStamp, fkGponOltControlReqResult, fkGponOltControllndex, fkGponOltControlTransceiverPort
                                 }
                        STATUS current
                        DESCRIPTION 
                                "Description."
                        ::= { fkGponOltNotification 17 }

                
--  1.3.6.1.4.1.10428 9 1.101.23.2.3.18
                -- 1.3.6.1.4.1.10428 9 1.101.23.2.3.18
                fkGponOltActivateStatusChanged NOTIFICATION-TYPE
                        OBJECTS { fkGponOltControlRequest, fkGponOltControlTimeStamp, fkGponOltControlReqResult, fkGponOltControllndex, fkGponOltControlActivateStatus
                                 }
                        STATUS current
                        DESCRIPTION 
                                "Description."
                        ::= { fkGponOltNotification 18 }

                
--  1.3.6.1.4.1.10428 9 1.101.23.2.3.19
                -- 1.3.6.1.4.1.10428 9 1.101.23.2.3.19
                fkGponOltProtectionChanged NOTIFICATION-TYPE
                        OBJECTS { fkGponOltControlRequest, fkGponOltControlTimeStamp, fkGponOltControlReqResult, fkGponOltControllndex, fkGponOltControlProtection
                                 }
                        STATUS current
                        DESCRIPTION 
                                "Description."
                        ::= { fkGponOltNotification 19 }

                
--  1.3.6.1.4.1.10428 9 1.101.23.2.3.20
                -- 1.3.6.1.4.1.10428 9 1.101.23.2.3.20
                fkGponOltAuthStatsCleared NOTIFICATION-TYPE
                        OBJECTS { fkGponOltControlRequest, fkGponOltControlTimeStamp, fkGponOltControlReqResult, fkGponOltControllndex }
                        STATUS current
                        DESCRIPTION 
                                "Description."
                        ::= { fkGponOltNotification 20 }

                
--  1.3.6.1.4.1.10428 9 1.101.23.2.3.21
                -- 1.3.6.1.4.1.10428 9 1.101.23.2.3.21
                fkGponOltOpticParamChanged NOTIFICATION-TYPE
                        OBJECTS { fkGponOltControlRequest, fkGponOltControlTimeStamp, fkGponOltControlReqResult, fkGponOltControllndex, fkGponOltControlOpticParam
                                 }
                        STATUS current
                        DESCRIPTION 
                                "Description."
                        ::= { fkGponOltNotification 21 }

                
--  1.3.6.1.4.1.10428 9 1.101.23.2.3.22
                -- 1.3.6.1.4.1.10428 9 1.101.23.2.3.22
                fkGponOltSrcMacMonitorChanged NOTIFICATION-TYPE
                        OBJECTS { fkGponOltControlRequest, fkGponOltControlTimeStamp, fkGponOltControlReqResult, fkGponOltControlSrcMacMonitorAutoBlock, fkGponOltControlSrcMacMonitoEexpireTimeout, 
                                fkGponOltControlSrcMacMonitorStatus, fkGponOltControllndex }
                        STATUS current
                        DESCRIPTION 
                                "Description."
                        ::= { fkGponOltNotification 22 }

                
--  1.3.6.1.4.1.10428 9 1.101.23.2.3.23
                -- 1.3.6.1.4.1.10428 9 1.101.23.2.3.23
                fkGponOltTotalUsBwChanged NOTIFICATION-TYPE
                        OBJECTS { fkGponOltControlRequest, fkGponOltControlTimeStamp, fkGponOltControlReqResult, fkGponOltControllndex, fkGponOltControlTotalUsBw
                                 }
                        STATUS current
                        DESCRIPTION 
                                "Description."
                        ::= { fkGponOltNotification 23 }

                
                -- 1.3.6.1.4.1.10428 9 1.101.23.2.3.24
                fkGponOltMaxOnuCountChanged NOTIFICATION-TYPE
                        OBJECTS { fkGponOltControlRequest, fkGponOltControlTimeStamp, fkGponOltControlReqResult, fkGponOltControllndex, fkGponOltControlMaxOnuCount
                                 }
                        STATUS current
                        DESCRIPTION 
                                "Description."
                        ::= { fkGponOltNotification 24 }

                
                -- 1.3.6.1.4.1.10428 9 1.101.23.2.3.25
                fkGponOltAntiSpoofingFilterChanged NOTIFICATION-TYPE
                        OBJECTS { fkGponOltControlRequest, fkGponOltControlTimeStamp, fkGponOltControlReqResult, fkGponOltControllndex, fkGponOltControlAntiSpoofingFilter, 
                                fkGponOltControlAntiSpoofingExpireTime }
                        STATUS current
                        DESCRIPTION 
                                "Description."
                        ::= { fkGponOltNotification 25 }

                
                -- 1.3.6.1.4.1.10428 9 1.101.23.2.3.26
                fkGponOltBwBEMethodChanged NOTIFICATION-TYPE
                        OBJECTS { fkGponOltControlRequest, fkGponOltControlTimeStamp, fkGponOltControlReqResult, fkGponOltControllndex, fkGponOltControlBwBEMethod
                                 }
                        STATUS current
                        DESCRIPTION 
                                "setBwBEMethod"
                        ::= { fkGponOltNotification 26 }

                
                -- 1.3.6.1.4.1.10428 9 1.101.23.2.3.27
                fkGponOltDsGemMappingChanged NOTIFICATION-TYPE
                        OBJECTS { fkGponOltControlRequest, fkGponOltControlTimeStamp, fkGponOltControlReqResult, fkGponOltControllndex, fkGponOltControlDsGemMapping
                                 }
                        STATUS current
                        DESCRIPTION 
                                "setDsGemMapping"
                        ::= { fkGponOltNotification 27 }

                
                -- 1.3.6.1.4.1.10428 9 1.101.23.2.3.28
                fkGponOltFixedTcontCountChanged NOTIFICATION-TYPE
                        OBJECTS { fkGponOltControlRequest, fkGponOltControlTimeStamp, fkGponOltControlReqResult, fkGponOltControllndex, fkGponOltControlFixedTcontCount
                                 }
                        STATUS current
                        DESCRIPTION 
                                "setFixedTcontCount"
                        ::= { fkGponOltNotification 28 }

                
                -- 1.3.6.1.4.1.10428 9 1.101.23.2.3.29
                fkGponOltDynamicTcontCountChanged NOTIFICATION-TYPE
                        OBJECTS { fkGponOltControlRequest, fkGponOltControlTimeStamp, fkGponOltControlReqResult, fkGponOltControllndex, fkGponOltControlDynamicTcontCount
                                 }
                        STATUS current
                        DESCRIPTION 
                                "setDynamicTcontCount"
                        ::= { fkGponOltNotification 29 }

                
                -- 1.3.6.1.4.1.10428 9 1.101.23.2.3.30
                fkGponOltPortCountChanged NOTIFICATION-TYPE
                        OBJECTS { fkGponOltControlRequest, fkGponOltControlTimeStamp, fkGponOltControlReqResult, fkGponOltControllndex, fkGponOltControlPortCount
                                 }
                        STATUS current
                        DESCRIPTION 
                                "setPortCount"
                        ::= { fkGponOltNotification 30 }

                
                -- 1.3.6.1.4.1.10428 9 1.101.23.2.3.31
                fkGponOltDeactiveMonitorStatusChanged NOTIFICATION-TYPE
                        OBJECTS { fkGponOltControlRequest, fkGponOltControlTimeStamp, fkGponOltControlReqResult, fkGponOltControllndex, fkGponOltControlDeactiveMonitorStatus
                                 }
                        STATUS current
                        DESCRIPTION 
                                "setDeactiveMonitorStatus "
                        ::= { fkGponOltNotification 31 }

                
                -- 1.3.6.1.4.1.10428 9 1.101.23.2.3.32
                fkGponOltDeactiveMonitorRaisePercentChanged NOTIFICATION-TYPE
                        OBJECTS { fkGponOltControlRequest, fkGponOltControlTimeStamp, fkGponOltControlReqResult, fkGponOltControllndex, fkGponOltControlDeactiveMonitorRaisePercent
                                 }
                        STATUS current
                        DESCRIPTION 
                                "setDeactiveMonitorRaisePercent "
                        ::= { fkGponOltNotification 32 }

                
                -- 1.3.6.1.4.1.10428 9 1.101.23.2.3.33
                fkGponOltDeactiveMonitorClearPercentChanged NOTIFICATION-TYPE
                        OBJECTS { fkGponOltControlRequest, fkGponOltControlTimeStamp, fkGponOltControlReqResult, fkGponOltControllndex, fkGponOltControlDeactiveMonitorClearPercent
                                 }
                        STATUS current
                        DESCRIPTION 
                                "setDeactiveMonitorClearPercent "
                        ::= { fkGponOltNotification 33 }

                
                -- 1.3.6.1.4.1.10428 9 1.101.23.2.3.34
                fkGponOltDeactiveMonitorPeriodChanged NOTIFICATION-TYPE
                        OBJECTS { fkGponOltControlRequest, fkGponOltControlTimeStamp, fkGponOltControlReqResult, fkGponOltControllndex, fkGponOltControlDeactiveMonitorPeriod
                                 }
                        STATUS current
                        DESCRIPTION 
                                "setDeactiveMonitorPeriod "
                        ::= { fkGponOltNotification 34 }

                
                -- 1.3.6.1.4.1.10428 9 1.101.23.2.3.35
                fkGponOltDeactiveMonitorAlarmCleared NOTIFICATION-TYPE
                        OBJECTS { fkGponOltControlRequest, fkGponOltControlTimeStamp, fkGponOltControlReqResult }
                        STATUS current
                        DESCRIPTION 
                                "clearDeactiveMonitorAlarm "
                        ::= { fkGponOltNotification 35 }

                
                -- 1.3.6.1.4.1.10428 9 1.101.23.2.3.36
                fkGponOltRegisterd NOTIFICATION-TYPE
                        OBJECTS { fkGponOltControlRequest, fkGponOltControlTimeStamp, fkGponOltControlReqResult, fkGponOltControllndex }
                        STATUS current
                        DESCRIPTION 
                                "setOltRegister"
                        ::= { fkGponOltNotification 36 }

                
                -- 1.3.6.1.4.1.10428 9 1.101.23.2.3.37
                fkGponOltBerUsIntervalChanged NOTIFICATION-TYPE
                        OBJECTS { fkGponOltControlRequest, fkGponOltControlTimeStamp, fkGponOltControlReqResult, fkGponOltControllndex, fkGponOltControlBerUpInterval
                                 }
                        STATUS current
                        DESCRIPTION 
                                "setOltBer"
                        ::= { fkGponOltNotification 37 }

                
                -- 1.3.6.1.4.1.10428 9 1.101.23.2.3.38
                fkGponOltBerDsIntervalChanged NOTIFICATION-TYPE
                        OBJECTS { fkGponOltControlRequest, fkGponOltControlTimeStamp, fkGponOltControlReqResult, fkGponOltControllndex, fkGponOltControlBerDownInterval
                                 }
                        STATUS current
                        DESCRIPTION 
                                "setOltBer"
                        ::= { fkGponOltNotification 38 }

                
                -- 1.3.6.1.4.1.10428 9 1.101.23.2.3.39
                fkGponOltBerSfThresholdChanged NOTIFICATION-TYPE
                        OBJECTS { fkGponOltControlRequest, fkGponOltControlTimeStamp, fkGponOltControlReqResult, fkGponOltControllndex, fkGponOltControlBerSfThreshold
                                 }
                        STATUS current
                        DESCRIPTION 
                                "setOltBer"
                        ::= { fkGponOltNotification 39 }

                
                -- 1.3.6.1.4.1.10428 9 1.101.23.2.3.40
                fkGponOltBerSdThresholdChanged NOTIFICATION-TYPE
                        OBJECTS { fkGponOltControlRequest, fkGponOltControlTimeStamp, fkGponOltControlReqResult, fkGponOltControllndex, fkGponOltControlBerSdThreshold
                                 }
                        STATUS current
                        DESCRIPTION 
                                "setOltBer"
                        ::= { fkGponOltNotification 40 }

                
                -- 1.3.6.1.4.1.10428 9 1.101.23.2.3.41
                fkGponOltUsFlowMappingChanged NOTIFICATION-TYPE
                        OBJECTS { fkGponOltControlRequest, fkGponOltControlTimeStamp, fkGponOltControlReqResult, fkGponOltControllndex, fkGponOltControlUsFlowMapping
                                 }
                        STATUS current
                        DESCRIPTION 
                                "setUsFlowMapping"
                        ::= { fkGponOltNotification 41 }

                
--  1.3.6.1.4.1.10428 9 1.101.23.2.3.42
                -- 1.3.6.1.4.1.10428 9 1.101.23.2.3.42
                fkGponOltDsQosMappingChanged NOTIFICATION-TYPE
                        OBJECTS { fkGponOltControlRequest, fkGponOltControlTimeStamp, fkGponOltControlReqResult, fkGponOltControllndex, fkGponOltControlDsQosMappingQueueCount, 
                                fkGponOltControlDsQosMappingCos0Queue, fkGponOltControlDsQosMappingCos1Queue, fkGponOltControlDsQosMappingCos2Queue, fkGponOltControlDsQosMappingCos3Queue, fkGponOltControlDsQosMappingCos4Queue, 
                                fkGponOltControlDsQosMappingCos5Queue, fkGponOltControlDsQosMappingCos6Queue, fkGponOltControlDsQosMappingCos7Queue }
                        STATUS current
                        DESCRIPTION 
                                "setDsQosMapping"
                        ::= { fkGponOltNotification 42 }

                
--  1.3.6.1.4.1.10428 9 1.101.23.2.3.43
                -- 1.3.6.1.4.1.10428 9 1.101.23.2.3.43
                fkGponOltDsQosMappingCleared NOTIFICATION-TYPE
                        OBJECTS { fkGponOltControlRequest, fkGponOltControlTimeStamp, fkGponOltControlReqResult, fkGponOltControllndex }
                        STATUS current
                        DESCRIPTION 
                                "clearDsQosMapping"
                        ::= { fkGponOltNotification 43 }

                
--  1.3.6.1.4.1.10428 9 1.101.23.2.3.44
                -- 1.3.6.1.4.1.10428 9 1.101.23.2.3.44
                fkGponOltDsQosMappingModeChanged NOTIFICATION-TYPE
                        OBJECTS { fkGponOltControlRequest, fkGponOltControlTimeStamp, fkGponOltControlReqResult, fkGponOltControllndex, fkGponOltControlDsQosMappingMode
                                 }
                        STATUS current
                        DESCRIPTION 
                                "setDsQosMappingMode"
                        ::= { fkGponOltNotification 44 }

                
--  1.3.6.1.4.1.10428 9 1.101.23.3
                -- 1.3.6.1.4.1.10428 9 1.101.23.3
                fkGponOnu OBJECT IDENTIFIER ::= { fkGpon 3 }

                
--  1.3.6.1.4.1.10428 9 1.101.23.3.1
                -- 1.3.6.1.4.1.10428 9 1.101.23.3.1
                fkGponOnuTable OBJECT-TYPE
                        SYNTAX SEQUENCE OF FkGponOnuEntry
                        MAX-ACCESS not-accessible
                        STATUS current
                        DESCRIPTION
                                "fkGponOnuTable"
                        ::= { fkGponOnu 1 }

                
--  1.3.6.1.4.1.10428 9 1.101.23.3.1.1
                -- 1.3.6.1.4.1.10428 9 1.101.23.3.1.1
                fkGponOnuEntry OBJECT-TYPE
                        SYNTAX FkGponOnuEntry
                        MAX-ACCESS not-accessible
                        STATUS current
                        DESCRIPTION
                                "key: fkGponOltId, fkGponOnuId"
                        INDEX { fkGponOltId, fkGponOnuId }
                        ::= { fkGponOnuTable 1 }

                
                FkGponOnuEntry ::=
                        SEQUENCE { 
                                fkGponOnuId
                                        INTEGER,
                                fkGponOnuStatus
                                        INTEGER,
                                fkGponOnuMode
                                        INTEGER,
                                fkGponOnuSerial
                                        OCTET STRING,
                                fkGponOnuPasswd
                                        OCTET STRING,
                                fkGponOnuPasswdMode
                                        INTEGER,
                                fkGponOnuEncMode
                                        INTEGER,
                                fkGponOnuProfile
                                        OCTET STRING,
                                fkGponOnuHostname
                                        OCTET STRING,
                                fkGponOnuDistance
                                        INTEGER,
                                fkGponOnuHwAddress
                                        OCTET STRING,
                                fkGponOnuNosActiveVersion
                                        OCTET STRING,
                                fkGponOnuNosStandbyVersion
                                        OCTET STRING,
                                fkGponOnuNosUpgradeStatus
                                        INTEGER,
                                fkGponOnuIsFirst
                                        INTEGER,
                                fkGponOnuRxPower
                                        INTEGER,
                                fkGponOnuModelName
                                        OCTET STRING,
                                fkGponOnuDescription
                                        OCTET STRING,
                                fkGponOnuNosAutoUpgradeWaitStatus
                                        INTEGER,
                                fkGponOnuNosAutoUpgradeFailCount
                                        INTEGER,
                                fkGponOnuOltRxPower
                                        INTEGER,
                                fkGponOnuRTD
                                        Integer32,
                                fkGponOnuLinkUpTime
                                        Counter64,
                                fkGponOnuAuthenticationStatus
                                        INTEGER,
                                fkGponOnuVlanID
                                        INTEGER,
                                fkGponOnuIpAddress
                                        IpAddress,
                                fkGponOnuNetmask
                                        IpAddress,
                                fkGponOnuHWType
                                        INTEGER,
                                fkGponOnuRegistrationCnt
                                        Integer32,
                                fkGponOnuAuthAcceptedCnt
                                        Integer32,
                                fkGponOnuAuthRejectedCnt
                                        Integer32,
                                fkGponOnuAuthChallengedCnt
                                        Integer32,
                                fkGponOnuFecModeUS
                                        INTEGER,
                                fkGponOnuIPMode
                                        INTEGER,
                                fkGponOnuIPAddr
                                        IpAddress,
                                fkGponOnuIPMask
                                        IpAddress,
                                fkGponOnuIPGw
                                        IpAddress,
                                fkGponOnuIPDns1
                                        IpAddress,
                                fkGponOnuIPDns2
                                        IpAddress,
                                fkGponOnuBatteryStatus
                                        INTEGER,
                                fkGponOnuMgmtSerialNo
                                        OCTET STRING,
                                fkGponOnuUserMacCnt
                                        Integer32,
                                fkGponOnuOmciPingTestResult
                                        OCTET STRING,
                                fkGponOnuOmciPingTestResultAvg
                                        OCTET STRING,
                                fkGponOnuDeactiveReason
                                        INTEGER,
                                fkGponOnuControlPathIpAddr
                                        IpAddress,
                                fkGponOnuControlPathMacAddr
                                        OCTET STRING,
                                fkGponOnuControlPathStatus
                                        Integer32,
                                fkGponOnuControlPathUptime
                                        TimeTicks,
                                fkGponOnuPMProfile
                                        OCTET STRING,
                                fkGponOnuUpCount
                                        Integer32,
                                fkGponOnuDownCount
                                        Integer32,
                                fkGponOnuNosDefaultPartition
                                        INTEGER,
                                fkGponOnuNosActivePartition
                                        INTEGER,
                                fkGponOnuBlockStatus
                                        INTEGER,
                                fkGponOnuBlockReason
                                        INTEGER,
                                fkGponOnuLastActiveFailReason
                                        INTEGER,
                                fkGponOnuEqD
                                        INTEGER,
                                fkGponOnuMaxTcont
                                        INTEGER,
                                fkGponOnuMaxUsQueuePerTcont
                                        INTEGER,
                                fkGponOnuSysUpTime
                                        Counter64,
                                fkGponOnuVenderProduct
                                        INTEGER,
                                fkGponOnuSlotId
                                        INTEGER,
                                fkGponOnuPortsID
                                        INTEGER,
                                fkGponOnuOperStatus
                                        Integer32,
                                fkGponOnuMapperID
                                        Integer32,
                                fkGponOnuVoipAvailSignalProtocol
                                        BITS,
                                fkGponOnuVoipAvailConfigMethod
                                        BITS,
                                fkGponOnuSupplierSerial
                                        OCTET STRING,
                                fkGponOnuHWRevision
                                        OCTET STRING,
                                fkGponOnuCPULoad
                                        INTEGER,
                                fkGponOnuCPULoadThreshold
                                        INTEGER,
                                fkGponOnuMemoryUsage
                                        INTEGER,
                                fkGponOnuMemoryThreshold
                                        INTEGER,
                                fkGponOnuTemperature
                                        INTEGER,
                                fkGponOnuTemperatureHighThreshold
                                        INTEGER,
                                fkGponOnuTemperatureLowThreshold
                                        INTEGER,
                                fkGponOnuLoopDetectStateSupport
                                        INTEGER,
                                fkGponOnuLoopDetectStateDetect
                                        INTEGER,
                                fkGponOnuLoopDetectStateBlock
                                        INTEGER,
                                fkGponOnuLoopDetectUnblockReason
                                        INTEGER,
                                fkGponOnuSupportFunction
                                        BITS,
                                fkGponOnuAccountUserName
                                        OCTET STRING,
                                fkGponOnuAccountPassword
                                        OCTET STRING
                         }

--  1.3.6.1.4.1.10428 9 1.101.23.3.1.1.1
                -- 1.3.6.1.4.1.10428 9 1.101.23.3.1.1.1
                fkGponOnuId OBJECT-TYPE
                        SYNTAX INTEGER (1..256)
                        MAX-ACCESS read-only
                        STATUS current
                        DESCRIPTION
                                "Gpon Onu Index"
                        ::= { fkGponOnuEntry 1 }

                
--  1.3.6.1.4.1.10428 9 1.101.23.3.1.1.2
                -- 1.3.6.1.4.1.10428 9 1.101.23.3.1.1.2
                fkGponOnuStatus OBJECT-TYPE
                        SYNTAX INTEGER
                                {
                                invalid(0),
                                inactive(1),
                                active(2),
                                running(3),
                                activePending(4),
                                deactivePending(5),
                                disablePending(6),
                                disable(7),
                                unknown(255)
                                }
                        MAX-ACCESS read-only
                        STATUS current
                        DESCRIPTION
                                "Gpon Onu Status"
                        ::= { fkGponOnuEntry 2 }

                
--  1.3.6.1.4.1.10428 9 1.101.23.3.1.1.3
                -- 1.3.6.1.4.1.10428 9 1.101.23.3.1.1.3
                fkGponOnuMode OBJECT-TYPE
                        SYNTAX INTEGER
                                {
                                notlearned(0),
                                manual(1),
                                auto(2)
                                }
                        MAX-ACCESS read-only
                        STATUS current
                        DESCRIPTION
                                "Gpon Onu register-mode"
                        ::= { fkGponOnuEntry 3 }

                
--  1.3.6.1.4.1.10428 9 1.101.23.3.1.1.4
                -- 1.3.6.1.4.1.10428 9 1.101.23.3.1.1.4
                fkGponOnuSerial OBJECT-TYPE
                        SYNTAX OCTET STRING (SIZE (1..64))
                        MAX-ACCESS read-only
                        STATUS current
                        DESCRIPTION
                                "ONU Serial Number"
                        ::= { fkGponOnuEntry 4 }

                
--  1.3.6.1.4.1.10428 9 1.101.23.3.1.1.5
                -- 1.3.6.1.4.1.10428 9 1.101.23.3.1.1.5
                fkGponOnuPasswd OBJECT-TYPE
                        SYNTAX OCTET STRING (SIZE (1..64))
                        MAX-ACCESS read-only
                        STATUS current
                        DESCRIPTION
                                "ONU Password"
                        ::= { fkGponOnuEntry 5 }

                
--  1.3.6.1.4.1.10428 9 1.101.23.3.1.1.6
                -- 1.3.6.1.4.1.10428 9 1.101.23.3.1.1.6
                fkGponOnuPasswdMode OBJECT-TYPE
                        SYNTAX INTEGER
                                {
                                enable(1),
                                disable(2)
                                }
                        MAX-ACCESS read-only
                        STATUS current
                        DESCRIPTION
                                "Password auto-learning "
                        ::= { fkGponOnuEntry 6 }

                
--  1.3.6.1.4.1.10428 9 1.101.23.3.1.1.7
                -- 1.3.6.1.4.1.10428 9 1.101.23.3.1.1.7
                fkGponOnuEncMode OBJECT-TYPE
                        SYNTAX INTEGER
                                {
                                enable(1),
                                disable(2)
                                }
                        MAX-ACCESS read-only
                        STATUS current
                        DESCRIPTION
                                "Encryption mode"
                        ::= { fkGponOnuEntry 7 }

                
--  1.3.6.1.4.1.10428 9 1.101.23.3.1.1.8
                -- 1.3.6.1.4.1.10428 9 1.101.23.3.1.1.8
                fkGponOnuProfile OBJECT-TYPE
                        SYNTAX OCTET STRING
                        MAX-ACCESS read-only
                        STATUS current
                        DESCRIPTION
                                "Onu assigned Profile."
                        ::= { fkGponOnuEntry 8 }

                
--  1.3.6.1.4.1.10428 9 1.101.23.3.1.1.9
                -- 1.3.6.1.4.1.10428 9 1.101.23.3.1.1.9
                fkGponOnuHostname OBJECT-TYPE
                        SYNTAX OCTET STRING
                        MAX-ACCESS read-only
                        STATUS current
                        DESCRIPTION
                                "ONU Hostname."
                        ::= { fkGponOnuEntry 9 }

                
--  1.3.6.1.4.1.10428 9 1.101.23.3.1.1.10
                -- 1.3.6.1.4.1.10428 9 1.101.23.3.1.1.10
                fkGponOnuDistance OBJECT-TYPE
                        SYNTAX INTEGER (1..65535)
                        UNITS "1m"
                        MAX-ACCESS read-only
                        STATUS current
                        DESCRIPTION
                                "ONU Distance information."
                        ::= { fkGponOnuEntry 10 }

                
--  1.3.6.1.4.1.10428 9 1.101.23.3.1.1.11
                -- 1.3.6.1.4.1.10428 9 1.101.23.3.1.1.11
                fkGponOnuHwAddress OBJECT-TYPE
                        SYNTAX OCTET STRING (SIZE (0..6))
                        MAX-ACCESS read-only
                        STATUS current
                        DESCRIPTION
                                "Onu System H/W address."
                        ::= { fkGponOnuEntry 11 }

                
--  1.3.6.1.4.1.10428 9 1.101.23.3.1.1.12
                -- 1.3.6.1.4.1.10428 9 1.101.23.3.1.1.12
                fkGponOnuNosActiveVersion OBJECT-TYPE
                        SYNTAX OCTET STRING
                        MAX-ACCESS read-only
                        STATUS current
                        DESCRIPTION
                                "ONU Firmware Version of Active"
                        ::= { fkGponOnuEntry 12 }

                
--  1.3.6.1.4.1.10428 9 1.101.23.3.1.1.13
                -- 1.3.6.1.4.1.10428 9 1.101.23.3.1.1.13
                fkGponOnuNosStandbyVersion OBJECT-TYPE
                        SYNTAX OCTET STRING
                        MAX-ACCESS read-only
                        STATUS current
                        DESCRIPTION
                                "ONU Firmware Version of Standby"
                        ::= { fkGponOnuEntry 13 }

                
--  1.3.6.1.4.1.10428 9 1.101.23.3.1.1.14
                -- 1.3.6.1.4.1.10428 9 1.101.23.3.1.1.14
                fkGponOnuNosUpgradeStatus OBJECT-TYPE
                        SYNTAX INTEGER
                                {
                                none(0),
                                downloadProgress(1),
                                downloadProgressforDevBusy(2),
                                endDownloadForDevBusy(3),
                                downloadComplete(4),
                                downloadFail(5),
                                commitWaitValid(6),
                                commitProgress(7),
                                commitProgressforDevBusy(8),
                                commitFailForDevBusy(9),
                                commitComplete(10),
                                commitFail(11),
                                changeActiveComplete(12),
                                changeActiveFailforDevBusy(13),
                                changeActiveFail(14),
                                autoUpgradeResetWaiting(15),
                                autoUpgradeFail(16),
                                endDownloadSend(17),
                                endDownloadComplete(18),
                                unknown(255)
                                }
                        MAX-ACCESS read-only
                        STATUS current
                        DESCRIPTION
                                "Onu firmware upgrade status."
                        ::= { fkGponOnuEntry 14 }

                
--  1.3.6.1.4.1.10428 9 1.101.23.3.1.1.15
                -- 1.3.6.1.4.1.10428 9 1.101.23.3.1.1.15
                fkGponOnuIsFirst OBJECT-TYPE
                        SYNTAX INTEGER
                                {
                                true(1),
                                false(2)
                                }
                        MAX-ACCESS accessible-for-notify
                        STATUS current
                        DESCRIPTION
                                "Whether it is first registration or not."
                        ::= { fkGponOnuEntry 15 }

                
--  1.3.6.1.4.1.10428 9 1.101.23.3.1.1.16
                -- 1.3.6.1.4.1.10428 9 1.101.23.3.1.1.16
                fkGponOnuRxPower OBJECT-TYPE
                        SYNTAX INTEGER (1..65535)
                        UNITS "0.1dBm"
                        MAX-ACCESS read-only
                        STATUS current
                        DESCRIPTION
                                "Rx Optical power."
                        ::= { fkGponOnuEntry 16 }

                
--  1.3.6.1.4.1.10428 9 1.101.23.3.1.1.17
                -- 1.3.6.1.4.1.10428 9 1.101.23.3.1.1.17
                fkGponOnuModelName OBJECT-TYPE
                        SYNTAX OCTET STRING
                        MAX-ACCESS read-only
                        STATUS current
                        DESCRIPTION
                                "ONU Model name."
                        ::= { fkGponOnuEntry 17 }

                
--  1.3.6.1.4.1.10428 9 1.101.23.3.1.1.18
                -- 1.3.6.1.4.1.10428 9 1.101.23.3.1.1.18
                fkGponOnuDescription OBJECT-TYPE
                        SYNTAX OCTET STRING
                        MAX-ACCESS read-only
                        STATUS current
                        DESCRIPTION
                                "ONU description."
                        ::= { fkGponOnuEntry 18 }

                
--  1.3.6.1.4.1.10428 9 1.101.23.3.1.1.19
                -- 1.3.6.1.4.1.10428 9 1.101.23.3.1.1.19
                fkGponOnuNosAutoUpgradeWaitStatus OBJECT-TYPE
                        SYNTAX INTEGER
                                {
                                waiting(1),
                                nowaiting(2)
                                }
                        MAX-ACCESS read-only
                        STATUS current
                        DESCRIPTION
                                "Onu firmware auto-upgrade wait status."
                        ::= { fkGponOnuEntry 19 }

                
--  1.3.6.1.4.1.10428 9 1.101.23.3.1.1.20
                -- 1.3.6.1.4.1.10428 9 1.101.23.3.1.1.20
                fkGponOnuNosAutoUpgradeFailCount OBJECT-TYPE
                        SYNTAX INTEGER (1..65535)
                        MAX-ACCESS read-only
                        STATUS current
                        DESCRIPTION
                                "Onu firmware upgrade fail count."
                        ::= { fkGponOnuEntry 20 }

                
--  1.3.6.1.4.1.10428 9 1.101.23.3.1.1.21
                -- 1.3.6.1.4.1.10428 9 1.101.23.3.1.1.21
                fkGponOnuOltRxPower OBJECT-TYPE
                        SYNTAX INTEGER (1..65535)
                        UNITS "0.1dBm"
                        MAX-ACCESS read-only
                        STATUS current
                        DESCRIPTION
                                "Rx Optical power of olt-side."
                        ::= { fkGponOnuEntry 21 }

                
--  1.3.6.1.4.1.10428 9 1.101.23.3.1.1.22
                -- 1.3.6.1.4.1.10428 9 1.101.23.3.1.1.22
                fkGponOnuRTD OBJECT-TYPE
                        SYNTAX Integer32
                        UNITS "bit"
                        MAX-ACCESS read-only
                        STATUS current
                        DESCRIPTION
                                "The RTD."
                        ::= { fkGponOnuEntry 22 }

                
--  1.3.6.1.4.1.10428 9 1.101.23.3.1.1.23
                -- 1.3.6.1.4.1.10428 9 1.101.23.3.1.1.23
                fkGponOnuLinkUpTime OBJECT-TYPE
                        SYNTAX Counter64
                        UNITS "1 sec"
                        MAX-ACCESS read-only
                        STATUS current
                        DESCRIPTION
                                "The elapsed time after ont is up."
                        ::= { fkGponOnuEntry 23 }

                
--  1.3.6.1.4.1.10428 9 1.101.23.3.1.1.24
                -- 1.3.6.1.4.1.10428 9 1.101.23.3.1.1.24
                fkGponOnuAuthenticationStatus OBJECT-TYPE
                        SYNTAX INTEGER
                                {
                                normal(1),
                                rangingFail(2),
                                passwdInconsistencyFail(3),
                                passwdMismatchFail(4),
                                passwdTimeoutFail(5),
                                passwdONUAlarmFail(6),
                                passwdDisableEventFail(7),
                                passwdLosFail(8),
                                unknown(255)
                                }
                        MAX-ACCESS read-only
                        STATUS current
                        DESCRIPTION
                                "The authentication status."
                        ::= { fkGponOnuEntry 24 }

                
--  1.3.6.1.4.1.10428 9 1.101.23.3.1.1.25
                -- 1.3.6.1.4.1.10428 9 1.101.23.3.1.1.25
                fkGponOnuVlanID OBJECT-TYPE
                        SYNTAX INTEGER (1..65535)
                        MAX-ACCESS read-only
                        STATUS current
                        DESCRIPTION
                                "The ont's vlan id."
                        ::= { fkGponOnuEntry 25 }

                
--  1.3.6.1.4.1.10428 9 1.101.23.3.1.1.26
                -- 1.3.6.1.4.1.10428 9 1.101.23.3.1.1.26
                fkGponOnuIpAddress OBJECT-TYPE
                        SYNTAX IpAddress
                        MAX-ACCESS read-only
                        STATUS current
                        DESCRIPTION
                                "The ont's ip address."
                        ::= { fkGponOnuEntry 26 }

                
--  1.3.6.1.4.1.10428 9 1.101.23.3.1.1.27
                -- 1.3.6.1.4.1.10428 9 1.101.23.3.1.1.27
                fkGponOnuNetmask OBJECT-TYPE
                        SYNTAX IpAddress
                        MAX-ACCESS read-only
                        STATUS current
                        DESCRIPTION
                                "The ont's netmask."
                        ::= { fkGponOnuEntry 27 }

                
--  1.3.6.1.4.1.10428 9 1.101.23.3.1.1.28
                -- 1.3.6.1.4.1.10428 9 1.101.23.3.1.1.28
                fkGponOnuHWType OBJECT-TYPE
                        SYNTAX INTEGER (1..65535)
                        MAX-ACCESS read-only
                        STATUS current
                        DESCRIPTION
                                "The ont's HW type."
                        ::= { fkGponOnuEntry 28 }

                
--  1.3.6.1.4.1.10428 9 1.101.23.3.1.1.29
                -- 1.3.6.1.4.1.10428 9 1.101.23.3.1.1.29
                fkGponOnuRegistrationCnt OBJECT-TYPE
                        SYNTAX Integer32
                        MAX-ACCESS read-only
                        STATUS current
                        DESCRIPTION
                                "The times of registration."
                        ::= { fkGponOnuEntry 29 }

                
--  1.3.6.1.4.1.10428 9 1.101.23.3.1.1.30
                -- 1.3.6.1.4.1.10428 9 1.101.23.3.1.1.30
                fkGponOnuAuthAcceptedCnt OBJECT-TYPE
                        SYNTAX Integer32
                        MAX-ACCESS read-only
                        STATUS current
                        DESCRIPTION
                                "The times of acception."
                        ::= { fkGponOnuEntry 30 }

                
--  1.3.6.1.4.1.10428 9 1.101.23.3.1.1.31
                -- 1.3.6.1.4.1.10428 9 1.101.23.3.1.1.31
                fkGponOnuAuthRejectedCnt OBJECT-TYPE
                        SYNTAX Integer32
                        MAX-ACCESS read-only
                        STATUS current
                        DESCRIPTION
                                "The times of rejection."
                        ::= { fkGponOnuEntry 31 }

                
--  1.3.6.1.4.1.10428 9 1.101.23.3.1.1.32
                -- 1.3.6.1.4.1.10428 9 1.101.23.3.1.1.32
                fkGponOnuAuthChallengedCnt OBJECT-TYPE
                        SYNTAX Integer32
                        MAX-ACCESS read-only
                        STATUS current
                        DESCRIPTION
                                "The times of challenge."
                        ::= { fkGponOnuEntry 32 }

                
--  1.3.6.1.4.1.10428 9 1.101.23.3.1.1.33
                -- 1.3.6.1.4.1.10428 9 1.101.23.3.1.1.33
                fkGponOnuFecModeUS OBJECT-TYPE
                        SYNTAX INTEGER
                                {
                                enable(1),
                                disable(2)
                                }
                        MAX-ACCESS read-only
                        STATUS current
                        DESCRIPTION
                                "UpStream FEC mode"
                        ::= { fkGponOnuEntry 33 }

                
--  1.3.6.1.4.1.10428 9 1.101.23.3.1.1.34
                -- 1.3.6.1.4.1.10428 9 1.101.23.3.1.1.34
                fkGponOnuIPMode OBJECT-TYPE
                        SYNTAX INTEGER
                                {
                                dhcp(1),
                                manual(2)
                                }
                        MAX-ACCESS read-only
                        STATUS current
                        DESCRIPTION
                                "Ip Addressing mode
                                DHCP or Manual (UnUsed)"
                        ::= { fkGponOnuEntry 34 }

                
--  1.3.6.1.4.1.10428 9 1.101.23.3.1.1.35
                -- 1.3.6.1.4.1.10428 9 1.101.23.3.1.1.35
                fkGponOnuIPAddr OBJECT-TYPE
                        SYNTAX IpAddress
                        MAX-ACCESS read-only
                        STATUS current
                        DESCRIPTION
                                "Onu IP address(UnUsed)"
                        ::= { fkGponOnuEntry 35 }

                
--  1.3.6.1.4.1.10428 9 1.101.23.3.1.1.36
                -- 1.3.6.1.4.1.10428 9 1.101.23.3.1.1.36
                fkGponOnuIPMask OBJECT-TYPE
                        SYNTAX IpAddress
                        MAX-ACCESS read-only
                        STATUS current
                        DESCRIPTION
                                "Onu IP Netmask(UnUsed)"
                        ::= { fkGponOnuEntry 36 }

                
--  1.3.6.1.4.1.10428 9 1.101.23.3.1.1.37
                -- 1.3.6.1.4.1.10428 9 1.101.23.3.1.1.37
                fkGponOnuIPGw OBJECT-TYPE
                        SYNTAX IpAddress
                        MAX-ACCESS read-only
                        STATUS current
                        DESCRIPTION
                                "Onu Gateway(UnUsed)"
                        ::= { fkGponOnuEntry 37 }

                
--  1.3.6.1.4.1.10428 9 1.101.23.3.1.1.38
                -- 1.3.6.1.4.1.10428 9 1.101.23.3.1.1.38
                fkGponOnuIPDns1 OBJECT-TYPE
                        SYNTAX IpAddress
                        MAX-ACCESS read-only
                        STATUS current
                        DESCRIPTION
                                "Onu DNS primary(UnUsed)"
                        ::= { fkGponOnuEntry 38 }

                
--  1.3.6.1.4.1.10428 9 1.101.23.3.1.1.39
                -- 1.3.6.1.4.1.10428 9 1.101.23.3.1.1.39
                fkGponOnuIPDns2 OBJECT-TYPE
                        SYNTAX IpAddress
                        MAX-ACCESS read-only
                        STATUS current
                        DESCRIPTION
                                "Onu DNS secondary(Unused)"
                        ::= { fkGponOnuEntry 39 }

                
--  1.3.6.1.4.1.10428 9 1.101.23.3.1.1.40
                -- 1.3.6.1.4.1.10428 9 1.101.23.3.1.1.40
                fkGponOnuBatteryStatus OBJECT-TYPE
                        SYNTAX INTEGER
                                {
                                powering(1),
                                missing(2),
                                failure(3),
                                low(4)
                                }
                        MAX-ACCESS read-only
                        STATUS current
                        DESCRIPTION
                                "Onu battery status."
                        ::= { fkGponOnuEntry 40 }

                
--  1.3.6.1.4.1.10428 9 1.101.23.3.1.1.41
                -- 1.3.6.1.4.1.10428 9 1.101.23.3.1.1.41
                fkGponOnuMgmtSerialNo OBJECT-TYPE
                        SYNTAX OCTET STRING
                        MAX-ACCESS read-only
                        STATUS current
                        DESCRIPTION
                                "The ONU management serial number"
                        ::= { fkGponOnuEntry 41 }

                
--  1.3.6.1.4.1.10428 9 1.101.23.3.1.1.42
                -- 1.3.6.1.4.1.10428 9 1.101.23.3.1.1.42
                fkGponOnuUserMacCnt OBJECT-TYPE
                        SYNTAX Integer32
                        MAX-ACCESS read-only
                        STATUS current
                        DESCRIPTION
                                "The count of MAC addresses that are leant at the running ONU."
                        ::= { fkGponOnuEntry 42 }

                
--  1.3.6.1.4.1.10428 9 1.101.23.3.1.1.43
                -- 1.3.6.1.4.1.10428 9 1.101.23.3.1.1.43
                fkGponOnuOmciPingTestResult OBJECT-TYPE
                        SYNTAX OCTET STRING
                        MAX-ACCESS read-only
                        STATUS current
                        DESCRIPTION
                                "OMCI ping test result.
                                Result Format : Sent Packets/Received Packets/Lost Packets"
                        ::= { fkGponOnuEntry 43 }

                
--  1.3.6.1.4.1.10428 9 1.101.23.3.1.1.44
                -- 1.3.6.1.4.1.10428 9 1.101.23.3.1.1.44
                fkGponOnuOmciPingTestResultAvg OBJECT-TYPE
                        SYNTAX OCTET STRING
                        MAX-ACCESS read-only
                        STATUS current
                        DESCRIPTION
                                "OMCI ping test result average.
                                Result Average Format : minimum/maximum/averge"
                        ::= { fkGponOnuEntry 44 }

                
--  1.3.6.1.4.1.10428 9 1.101.23.3.1.1.45
                -- 1.3.6.1.4.1.10428 9 1.101.23.3.1.1.45
                fkGponOnuDeactiveReason OBJECT-TYPE
                        SYNTAX INTEGER
                                {
                                none(1),
                                dgi(2),
                                losi(3),
                                lofi(4),
                                sfi(5),
                                sufi(6),
                                loai(7),
                                loami(8),
                                loki(9),
                                adminReset(10),
                                adminActiveChange(11),
                                adminOltConfiguration(12),
                                adminSlotRestart(13),
                                adminSlotRemove(14),
                                adminRogueOnuCandidate(15),
                                adminRogueOnu(16),
                                adminRogueOnuSelfDetectBlock(17),
                                adminTxOffOptic(18),
                                adminDeactivate(19),
                                adminOltDeactivate(20),
                                adminOmccDown(21),
                                adminSetRedundancy(22),
                                adminRemoveOnu(23),
                                los(100),
                                onuDeactReasonRanging(101),
                                onuDeactReasonPasswdAuthentication(102),
                                onuDeactReasonPasswdInconsistency(103),
                                onuDeactReasonPasswdMismatch(104),
                                onuDeactReasonPasswdTimeout(105),
                                onuDeactReasonPasswdOnuAlarm(106),
                                onuDeactReasonPasswdDisableEvent(107),
                                unknown(255)
                                }
                        MAX-ACCESS read-only
                        STATUS current
                        DESCRIPTION
                                "Onu inactive reason."
                        ::= { fkGponOnuEntry 45 }

                
--  1.3.6.1.4.1.10428 9 1.101.23.3.1.1.46
                -- 1.3.6.1.4.1.10428 9 1.101.23.3.1.1.46
                fkGponOnuControlPathIpAddr OBJECT-TYPE
                        SYNTAX IpAddress
                        MAX-ACCESS read-only
                        STATUS current
                        DESCRIPTION
                                "IP Address for ONU Control plane"
                        ::= { fkGponOnuEntry 46 }

                
--  1.3.6.1.4.1.10428 9 1.101.23.3.1.1.47
                -- 1.3.6.1.4.1.10428 9 1.101.23.3.1.1.47
                fkGponOnuControlPathMacAddr OBJECT-TYPE
                        SYNTAX OCTET STRING
                        MAX-ACCESS read-only
                        STATUS current
                        DESCRIPTION
                                "MAC Address for ONU Control plane"
                        ::= { fkGponOnuEntry 47 }

                
--  1.3.6.1.4.1.10428 9 1.101.23.3.1.1.48
                -- 1.3.6.1.4.1.10428 9 1.101.23.3.1.1.48
                fkGponOnuControlPathStatus OBJECT-TYPE
                        SYNTAX Integer32
                        MAX-ACCESS read-only
                        STATUS current
                        DESCRIPTION
                                "The status about ONU's control path."
                        ::= { fkGponOnuEntry 48 }

                
--  1.3.6.1.4.1.10428 9 1.101.23.3.1.1.49
                -- 1.3.6.1.4.1.10428 9 1.101.23.3.1.1.49
                fkGponOnuControlPathUptime OBJECT-TYPE
                        SYNTAX TimeTicks
                        MAX-ACCESS read-only
                        STATUS current
                        DESCRIPTION
                                "The elapsed time that control path has been connect."
                        ::= { fkGponOnuEntry 49 }

                
--  1.3.6.1.4.1.10428 9 1.101.23.3.1.1.50
                -- 1.3.6.1.4.1.10428 9 1.101.23.3.1.1.50
                fkGponOnuPMProfile OBJECT-TYPE
                        SYNTAX OCTET STRING
                        MAX-ACCESS read-only
                        STATUS current
                        DESCRIPTION
                                "The assigned PM-profile
                                "
                        ::= { fkGponOnuEntry 50 }

                
--  1.3.6.1.4.1.10428 9 1.101.23.3.1.1.51
                -- 1.3.6.1.4.1.10428 9 1.101.23.3.1.1.51
                fkGponOnuUpCount OBJECT-TYPE
                        SYNTAX Integer32
                        MAX-ACCESS read-only
                        STATUS current
                        DESCRIPTION
                                "The link up count"
                        ::= { fkGponOnuEntry 51 }

                
--  1.3.6.1.4.1.10428 9 1.101.23.3.1.1.52
                -- 1.3.6.1.4.1.10428 9 1.101.23.3.1.1.52
                fkGponOnuDownCount OBJECT-TYPE
                        SYNTAX Integer32
                        MAX-ACCESS read-only
                        STATUS current
                        DESCRIPTION
                                "The link up count"
                        ::= { fkGponOnuEntry 52 }

                
--  1.3.6.1.4.1.10428 9 1.101.23.3.1.1.53
                -- 1.3.6.1.4.1.10428 9 1.101.23.3.1.1.53
                fkGponOnuNosDefaultPartition OBJECT-TYPE
                        SYNTAX INTEGER
                                {
                                os1(1),
                                os2(2),
                                unknown(255)
                                }
                        MAX-ACCESS read-only
                        STATUS current
                        DESCRIPTION
                                "The default NOS partition."
                        ::= { fkGponOnuEntry 53 }

                
--  1.3.6.1.4.1.10428 9 1.101.23.3.1.1.54
                -- 1.3.6.1.4.1.10428 9 1.101.23.3.1.1.54
                fkGponOnuNosActivePartition OBJECT-TYPE
                        SYNTAX INTEGER
                                {
                                os1(1),
                                os2(2),
                                unknown(255)
                                }
                        MAX-ACCESS read-only
                        STATUS current
                        DESCRIPTION
                                "The current active NOS partition.."
                        ::= { fkGponOnuEntry 54 }

                
--  1.3.6.1.4.1.10428 9 1.101.23.3.1.1.55
                -- 1.3.6.1.4.1.10428 9 1.101.23.3.1.1.55
                fkGponOnuBlockStatus OBJECT-TYPE
                        SYNTAX INTEGER
                                {
                                autoblock(1),
                                manualblock(2),
                                unblock(255)
                                }
                        MAX-ACCESS read-only
                        STATUS current
                        DESCRIPTION
                                "The ONU block status."
                        ::= { fkGponOnuEntry 55 }

                
--  1.3.6.1.4.1.10428 9 1.101.23.3.1.1.56
                -- 1.3.6.1.4.1.10428 9 1.101.23.3.1.1.56
                fkGponOnuBlockReason OBJECT-TYPE
                        SYNTAX INTEGER
                                {
                                mnanualblock(1),
                                sourcemac(2),
                                none(255)
                                }
                        MAX-ACCESS read-only
                        STATUS current
                        DESCRIPTION
                                "The ONU Block reason."
                        ::= { fkGponOnuEntry 56 }

                
--  1.3.6.1.4.1.10428 9 1.101.23.3.1.1.57
                -- 1.3.6.1.4.1.10428 9 1.101.23.3.1.1.57
                fkGponOnuLastActiveFailReason OBJECT-TYPE
                        SYNTAX INTEGER
                                {
                                ranging(1),
                                passwdInconsistency(2),
                                passwdMismatch(3),
                                passwdTimeout(4),
                                passwdONUAlarm(5),
                                passwdDisableEvent(6),
                                passwdLosl(7),
                                unknown(255)
                                }
                        MAX-ACCESS read-only
                        STATUS current
                        DESCRIPTION
                                "The ONU Last active fail  Reason."
                        ::= { fkGponOnuEntry 57 }

                
--  1.3.6.1.4.1.10428 9 1.101.23.3.1.1.58
                -- 1.3.6.1.4.1.10428 9 1.101.23.3.1.1.58
                fkGponOnuEqD OBJECT-TYPE
                        SYNTAX INTEGER (1..65535)
                        MAX-ACCESS read-only
                        STATUS current
                        DESCRIPTION
                                "The ONU EqD."
                        ::= { fkGponOnuEntry 58 }

                
--  1.3.6.1.4.1.10428 9 1.101.23.3.1.1.59
                -- 1.3.6.1.4.1.10428 9 1.101.23.3.1.1.59
                fkGponOnuMaxTcont OBJECT-TYPE
                        SYNTAX INTEGER (1..65535)
                        MAX-ACCESS read-only
                        STATUS current
                        DESCRIPTION
                                "The ONU Max tcont"
                        ::= { fkGponOnuEntry 59 }

                
--  1.3.6.1.4.1.10428 9 1.101.23.3.1.1.60
                -- 1.3.6.1.4.1.10428 9 1.101.23.3.1.1.60
                fkGponOnuMaxUsQueuePerTcont OBJECT-TYPE
                        SYNTAX INTEGER (1..65535)
                        MAX-ACCESS read-only
                        STATUS current
                        DESCRIPTION
                                "The ONU Max US queue per Tcont"
                        ::= { fkGponOnuEntry 60 }

                
--  1.3.6.1.4.1.10428 9 1.101.23.3.1.1.61
                -- 1.3.6.1.4.1.10428 9 1.101.23.3.1.1.61
                fkGponOnuSysUpTime OBJECT-TYPE
                        SYNTAX Counter64
                        MAX-ACCESS read-only
                        STATUS current
                        DESCRIPTION
                                "The ONU sysUptime"
                        ::= { fkGponOnuEntry 61 }

                
--  1.3.6.1.4.1.10428 9 1.101.23.3.1.1.62
                -- 1.3.6.1.4.1.10428 9 1.101.23.3.1.1.62
                fkGponOnuVenderProduct OBJECT-TYPE
                        SYNTAX INTEGER (1..65535)
                        MAX-ACCESS read-only
                        STATUS current
                        DESCRIPTION
                                "The ONU Vendor"
                        ::= { fkGponOnuEntry 62 }

                
--  1.3.6.1.4.1.10428 9 1.101.23.3.1.1.63
                -- 1.3.6.1.4.1.10428 9 1.101.23.3.1.1.63
                fkGponOnuSlotId OBJECT-TYPE
                        SYNTAX INTEGER (1..65535)
                        MAX-ACCESS read-only
                        STATUS current
                        DESCRIPTION
                                "The ONU slotId"
                        ::= { fkGponOnuEntry 63 }

                
--  1.3.6.1.4.1.10428 9 1.101.23.3.1.1.64
                -- 1.3.6.1.4.1.10428 9 1.101.23.3.1.1.64
                fkGponOnuPortsID OBJECT-TYPE
                        SYNTAX INTEGER (1..65535)
                        MAX-ACCESS read-only
                        STATUS current
                        DESCRIPTION
                                "The ONU Port ID"
                        ::= { fkGponOnuEntry 64 }

                
--  1.3.6.1.4.1.10428 9 1.101.23.3.1.1.65
                -- 1.3.6.1.4.1.10428 9 1.101.23.3.1.1.65
                fkGponOnuOperStatus OBJECT-TYPE
                        SYNTAX Integer32
                        MAX-ACCESS read-only
                        STATUS current
                        DESCRIPTION
                                "The ONU Oper status"
                        ::= { fkGponOnuEntry 65 }

                
--  1.3.6.1.4.1.10428 9 1.101.23.3.1.1.66
                -- 1.3.6.1.4.1.10428 9 1.101.23.3.1.1.66
                fkGponOnuMapperID OBJECT-TYPE
                        SYNTAX Integer32
                        MAX-ACCESS read-only
                        STATUS current
                        DESCRIPTION
                                "The ONU MapperID"
                        ::= { fkGponOnuEntry 66 }

                
                -- 1.3.6.1.4.1.10428 9 1.101.23.3.1.1.67
                fkGponOnuVoipAvailSignalProtocol OBJECT-TYPE
                        SYNTAX BITS
                                {
                                sip(0),
                                h248(1),
                                mgcp(2)
                                }
                        MAX-ACCESS read-only
                        STATUS current
                        DESCRIPTION
                                "The Signal protocol"
                        ::= { fkGponOnuEntry 67 }

                
                -- 1.3.6.1.4.1.10428 9 1.101.23.3.1.1.68
                fkGponOnuVoipAvailConfigMethod OBJECT-TYPE
                        SYNTAX BITS
                                {
                                omci(0),
                                configrationFile(1),
                                tr69(2),
                                ietf(3)
                                }
                        MAX-ACCESS read-only
                        STATUS current
                        DESCRIPTION
                                "The Configuration method"
                        ::= { fkGponOnuEntry 68 }

                
                -- 1.3.6.1.4.1.10428 9 1.101.23.3.1.1.69
                fkGponOnuSupplierSerial OBJECT-TYPE
                        SYNTAX OCTET STRING
                        MAX-ACCESS read-only
                        STATUS current
                        DESCRIPTION
                                "The supplier serial."
                        ::= { fkGponOnuEntry 69 }

                
                -- 1.3.6.1.4.1.10428 9 1.101.23.3.1.1.70
                fkGponOnuHWRevision OBJECT-TYPE
                        SYNTAX OCTET STRING
                        MAX-ACCESS read-only
                        STATUS current
                        DESCRIPTION
                                "The H/W revision."
                        ::= { fkGponOnuEntry 70 }

                
                -- 1.3.6.1.4.1.10428 9 1.101.23.3.1.1.71
                fkGponOnuCPULoad OBJECT-TYPE
                        SYNTAX INTEGER (1..65535)
                        MAX-ACCESS read-only
                        STATUS current
                        DESCRIPTION
                                "The cpu load (%)."
                        ::= { fkGponOnuEntry 71 }

                
                -- 1.3.6.1.4.1.10428 9 1.101.23.3.1.1.72
                fkGponOnuCPULoadThreshold OBJECT-TYPE
                        SYNTAX INTEGER (1..65535)
                        MAX-ACCESS read-only
                        STATUS current
                        DESCRIPTION
                                "The CPU load threshold(%)."
                        ::= { fkGponOnuEntry 72 }

                
                -- 1.3.6.1.4.1.10428 9 1.101.23.3.1.1.73
                fkGponOnuMemoryUsage OBJECT-TYPE
                        SYNTAX INTEGER (1..65535)
                        MAX-ACCESS read-only
                        STATUS current
                        DESCRIPTION
                                "The memory usage(%)."
                        ::= { fkGponOnuEntry 73 }

                
                -- 1.3.6.1.4.1.10428 9 1.101.23.3.1.1.74
                fkGponOnuMemoryThreshold OBJECT-TYPE
                        SYNTAX INTEGER (1..65535)
                        MAX-ACCESS read-only
                        STATUS current
                        DESCRIPTION
                                "The memory threshold(%)."
                        ::= { fkGponOnuEntry 74 }

                
                -- 1.3.6.1.4.1.10428 9 1.101.23.3.1.1.75
                fkGponOnuTemperature OBJECT-TYPE
                        SYNTAX INTEGER (1..65535)
                        MAX-ACCESS read-only
                        STATUS current
                        DESCRIPTION
                                "The temperature(C)."
                        ::= { fkGponOnuEntry 75 }

                
                -- 1.3.6.1.4.1.10428 9 1.101.23.3.1.1.76
                fkGponOnuTemperatureHighThreshold OBJECT-TYPE
                        SYNTAX INTEGER (1..65535)
                        MAX-ACCESS read-only
                        STATUS current
                        DESCRIPTION
                                "The temperature high threshold(C)."
                        ::= { fkGponOnuEntry 76 }

                
                -- 1.3.6.1.4.1.10428 9 1.101.23.3.1.1.77
                fkGponOnuTemperatureLowThreshold OBJECT-TYPE
                        SYNTAX INTEGER (1..65535)
                        MAX-ACCESS read-write
                        STATUS current
                        DESCRIPTION
                                "The temperature low threshold(C)."
                        ::= { fkGponOnuEntry 77 }

                
                -- 1.3.6.1.4.1.10428 9 1.101.23.3.1.1.78
                fkGponOnuLoopDetectStateSupport OBJECT-TYPE
                        SYNTAX INTEGER
                                {
                                unSupported(0),
                                supported(1)
                                }
                        MAX-ACCESS read-only
                        STATUS current
                        DESCRIPTION
                                "The supported state."
                        ::= { fkGponOnuEntry 78 }

                
                -- 1.3.6.1.4.1.10428 9 1.101.23.3.1.1.79
                fkGponOnuLoopDetectStateDetect OBJECT-TYPE
                        SYNTAX INTEGER
                                {
                                unDetected(0),
                                detected(1)
                                }
                        MAX-ACCESS read-only
                        STATUS current
                        DESCRIPTION
                                "The detect state."
                        ::= { fkGponOnuEntry 79 }

                
                -- 1.3.6.1.4.1.10428 9 1.101.23.3.1.1.80
                fkGponOnuLoopDetectStateBlock OBJECT-TYPE
                        SYNTAX INTEGER
                                {
                                unBlocked(0),
                                blocked(1)
                                }
                        MAX-ACCESS read-only
                        STATUS current
                        DESCRIPTION
                                "The block state."
                        ::= { fkGponOnuEntry 80 }

                
                -- 1.3.6.1.4.1.10428 9 1.101.23.3.1.1.81
                fkGponOnuLoopDetectUnblockReason OBJECT-TYPE
                        SYNTAX INTEGER
                                {
                                unBlockByInit(0),
                                unBlockByCommand(1),
                                unBlockByTimerExpire(2),
                                unBlockByDisable(3),
                                unknown(255)
                                }
                        MAX-ACCESS read-only
                        STATUS current
                        DESCRIPTION
                                "The unblock reason.
                                0: Unblock by init
                                1: Unblock by command
                                2: Unblock by timer expire
                                3: Unblock by disable
                                255: Unknown"
                        ::= { fkGponOnuEntry 81 }

                
                -- 1.3.6.1.4.1.10428 9 1.101.23.3.1.1.82
                fkGponOnuSupportFunction OBJECT-TYPE
                        SYNTAX BITS { systemStatus(0) }
                        MAX-ACCESS read-only
                        STATUS current
                        DESCRIPTION
                                "The support function."
                        ::= { fkGponOnuEntry 82 }

                
                -- 1.3.6.1.4.1.10428 9 1.101.23.3.1.1.83
                fkGponOnuAccountUserName OBJECT-TYPE
                        SYNTAX OCTET STRING
                        MAX-ACCESS read-only
                        STATUS current
                        DESCRIPTION
                                "The account user name."
                        ::= { fkGponOnuEntry 83 }

                
                -- 1.3.6.1.4.1.10428 9 1.101.23.3.1.1.84
                fkGponOnuAccountPassword OBJECT-TYPE
                        SYNTAX OCTET STRING
                        MAX-ACCESS read-only
                        STATUS current
                        DESCRIPTION
                                "The account password."
                        ::= { fkGponOnuEntry 84 }

                
--  1.3.6.1.4.1.10428 9 1.101.23.3.2
                -- 1.3.6.1.4.1.10428 9 1.101.23.3.2
                fkGponOnuControl OBJECT IDENTIFIER ::= { fkGponOnu 2 }

                
--  1.3.6.1.4.1.10428 9 1.101.23.3.2.1
                -- 1.3.6.1.4.1.10428 9 1.101.23.3.2.1
                fkGponOnuControlRequest OBJECT-TYPE
                        SYNTAX INTEGER
                                {
                                setOnuRegister(1),
                                setOnuDeregister(2),
                                setOnuProfile(3),
                                setOnuFix(4),
                                setOnuUpgradeNos(5),
                                setOnuNosActiveChange(6),
                                setOnuEncMode(7),
                                setOnuReset(8),
                                setOnuTxOffOptic(9),
                                setOnuDescription(10),
                                setOnuFecModeUS(11),
                                setOnuIpInfo(12),
                                setOnuOmciPingTest(13),
                                setOnuActiveStatus(14),
                                setOnuPMProfile(15),
                                setOnuUpgradeNosPartition(16),
                                setOnuUpgradeNosCommit(17),
                                setOnuUpgradeNosActiveChange(18),
                                setOnuBlock(19),
                                updateOltRxPower(20),
                                updateOnuSystemInfo(21),
                                setOnuTxOnOptic(22),
                                setOnuLoopDetectUnblock(23),
                                updateOnuUserMacCnt(24),
                                updateOnuAccount(25),
                                setOnuAccount(26)
                                }
                        MAX-ACCESS read-write
                        STATUS current
                        DESCRIPTION
                                "The request of a user command"
                        ::= { fkGponOnuControl 1 }

                
--  1.3.6.1.4.1.10428 9 1.101.23.3.2.2
                -- 1.3.6.1.4.1.10428 9 1.101.23.3.2.2
                fkGponOnuControlStatus OBJECT-TYPE
                        SYNTAX FkControlStatusType
                        MAX-ACCESS read-only
                        STATUS current
                        DESCRIPTION
                                "The status of user command"
                        ::= { fkGponOnuControl 2 }

                
--  1.3.6.1.4.1.10428 9 1.101.23.3.2.3
                -- 1.3.6.1.4.1.10428 9 1.101.23.3.2.3
                fkGponOnuControlTimer OBJECT-TYPE
                        SYNTAX Gauge32
                        MAX-ACCESS read-write
                        STATUS current
                        DESCRIPTION
                                "The maximum time for the manager for a long running user command"
                        ::= { fkGponOnuControl 3 }

                
--  1.3.6.1.4.1.10428 9 1.101.23.3.2.4
                -- 1.3.6.1.4.1.10428 9 1.101.23.3.2.4
                fkGponOnuControlTimeStamp OBJECT-TYPE
                        SYNTAX TimeTicks
                        MAX-ACCESS read-only
                        STATUS current
                        DESCRIPTION
                                "The time stamp of the last command(end of command)"
                        ::= { fkGponOnuControl 4 }

                
--  1.3.6.1.4.1.10428 9 1.101.23.3.2.5
                -- 1.3.6.1.4.1.10428 9 1.101.23.3.2.5
                fkGponOnuControlReqResult OBJECT-TYPE
                        SYNTAX FkControlRequestResultType
                        MAX-ACCESS read-only
                        STATUS current
                        DESCRIPTION
                                "The result of the last user command"
                        ::= { fkGponOnuControl 5 }

                
--  1.3.6.1.4.1.10428 9 1.101.23.3.2.6
                -- 1.3.6.1.4.1.10428 9 1.101.23.3.2.6
                fkGponOnuControlOltId OBJECT-TYPE
                        SYNTAX INTEGER (1..65535)
                        MAX-ACCESS read-write
                        STATUS current
                        DESCRIPTION
                                "Gpon Olt Index"
                        ::= { fkGponOnuControl 6 }

                
--  1.3.6.1.4.1.10428 9 1.101.23.3.2.7
                -- 1.3.6.1.4.1.10428 9 1.101.23.3.2.7
                fkGponOnuControlId OBJECT-TYPE
                        SYNTAX INTEGER (1..65535)
                        MAX-ACCESS read-write
                        STATUS current
                        DESCRIPTION
                                "Gpon Onu Index. (0xFF is all onu)"
                        ::= { fkGponOnuControl 7 }

                
--  1.3.6.1.4.1.10428 9 1.101.23.3.2.8
                -- 1.3.6.1.4.1.10428 9 1.101.23.3.2.8
                fkGponOnuControlSerial OBJECT-TYPE
                        SYNTAX OCTET STRING
                        MAX-ACCESS read-write
                        STATUS current
                        DESCRIPTION
                                "ONU Serial Number"
                        ::= { fkGponOnuControl 8 }

                
--  1.3.6.1.4.1.10428 9 1.101.23.3.2.9
                -- 1.3.6.1.4.1.10428 9 1.101.23.3.2.9
                fkGponOnuControlPasswd OBJECT-TYPE
                        SYNTAX OCTET STRING
                        MAX-ACCESS read-write
                        STATUS current
                        DESCRIPTION
                                "ONU Password"
                        ::= { fkGponOnuControl 9 }

                
--  1.3.6.1.4.1.10428 9 1.101.23.3.2.10
                -- 1.3.6.1.4.1.10428 9 1.101.23.3.2.10
                fkGponOnuControlPasswdMode OBJECT-TYPE
                        SYNTAX INTEGER
                                {
                                enable(1),
                                disable(2)
                                }
                        MAX-ACCESS read-write
                        STATUS current
                        DESCRIPTION
                                "Password auto-learning"
                        ::= { fkGponOnuControl 10 }

                
--  1.3.6.1.4.1.10428 9 1.101.23.3.2.11
                -- 1.3.6.1.4.1.10428 9 1.101.23.3.2.11
                fkGponOnuControlEncMode OBJECT-TYPE
                        SYNTAX INTEGER
                                {
                                enable(1),
                                disable(2)
                                }
                        MAX-ACCESS read-write
                        STATUS current
                        DESCRIPTION
                                "Encryption mode"
                        ::= { fkGponOnuControl 11 }

                
--  1.3.6.1.4.1.10428 9 1.101.23.3.2.12
                -- 1.3.6.1.4.1.10428 9 1.101.23.3.2.12
                fkGponOnuControlProfile OBJECT-TYPE
                        SYNTAX OCTET STRING
                        MAX-ACCESS read-write
                        STATUS current
                        DESCRIPTION
                                "Onu assigned Profile"
                        ::= { fkGponOnuControl 12 }

                
--  1.3.6.1.4.1.10428 9 1.101.23.3.2.13
                -- 1.3.6.1.4.1.10428 9 1.101.23.3.2.13
                fkGponOnuControlNosUpgradePath OBJECT-TYPE
                        SYNTAX OCTET STRING
                        MAX-ACCESS read-write
                        STATUS current
                        DESCRIPTION
                                "Onu Firmware Path."
                        ::= { fkGponOnuControl 13 }

                
--  1.3.6.1.4.1.10428 9 1.101.23.3.2.14
                -- 1.3.6.1.4.1.10428 9 1.101.23.3.2.14
                fkGponOnuControlHwAddr OBJECT-TYPE
                        SYNTAX OCTET STRING
                        MAX-ACCESS read-write
                        STATUS current
                        DESCRIPTION
                                "Onu H/W address. (0 is unused)"
                        ::= { fkGponOnuControl 14 }

                
--  1.3.6.1.4.1.10428 9 1.101.23.3.2.15
                -- 1.3.6.1.4.1.10428 9 1.101.23.3.2.15
                fkGponOnuControlTxOffOptic OBJECT-TYPE
                        SYNTAX INTEGER (0..65525)
                        UNITS "seconds"
                        MAX-ACCESS read-write
                        STATUS current
                        DESCRIPTION
                                "Tx power disable of the tranceiver"
                        ::= { fkGponOnuControl 15 }

                
--  1.3.6.1.4.1.10428 9 1.101.23.3.2.16
                -- 1.3.6.1.4.1.10428 9 1.101.23.3.2.16
                fkGponOnuControlDescription OBJECT-TYPE
                        SYNTAX OCTET STRING
                        MAX-ACCESS read-write
                        STATUS current
                        DESCRIPTION
                                "ONU description."
                        ::= { fkGponOnuControl 16 }

                
--  1.3.6.1.4.1.10428 9 1.101.23.3.2.17
                -- 1.3.6.1.4.1.10428 9 1.101.23.3.2.17
                fkGponOnuControlFecModeUS OBJECT-TYPE
                        SYNTAX INTEGER
                                {
                                enable(1),
                                disable(2)
                                }
                        MAX-ACCESS read-write
                        STATUS current
                        DESCRIPTION
                                "UpStream FEC mode"
                        ::= { fkGponOnuControl 17 }

                
--  1.3.6.1.4.1.10428 9 1.101.23.3.2.18
                -- 1.3.6.1.4.1.10428 9 1.101.23.3.2.18
                fkGponOnuControlIPMode OBJECT-TYPE
                        SYNTAX INTEGER
                                {
                                dhcp(1),
                                manual(2)
                                }
                        MAX-ACCESS read-write
                        STATUS current
                        DESCRIPTION
                                "Ip Addressing mode
                                DHCP or Manual"
                        ::= { fkGponOnuControl 18 }

                
--  1.3.6.1.4.1.10428 9 1.101.23.3.2.19
                -- 1.3.6.1.4.1.10428 9 1.101.23.3.2.19
                fkGponOnuControlIPAddr OBJECT-TYPE
                        SYNTAX IpAddress
                        MAX-ACCESS read-write
                        STATUS current
                        DESCRIPTION
                                "Onu IP address"
                        ::= { fkGponOnuControl 19 }

                
--  1.3.6.1.4.1.10428 9 1.101.23.3.2.20
                -- 1.3.6.1.4.1.10428 9 1.101.23.3.2.20
                fkGponOnuControlIPMask OBJECT-TYPE
                        SYNTAX IpAddress
                        MAX-ACCESS read-write
                        STATUS current
                        DESCRIPTION
                                "Onu IP Netmask"
                        ::= { fkGponOnuControl 20 }

                
--  1.3.6.1.4.1.10428 9 1.101.23.3.2.21
                -- 1.3.6.1.4.1.10428 9 1.101.23.3.2.21
                fkGponOnuControlIPGw OBJECT-TYPE
                        SYNTAX IpAddress
                        MAX-ACCESS read-write
                        STATUS current
                        DESCRIPTION
                                "Onu Gateway"
                        ::= { fkGponOnuControl 21 }

                
--  1.3.6.1.4.1.10428 9 1.101.23.3.2.22
                -- 1.3.6.1.4.1.10428 9 1.101.23.3.2.22
                fkGponOnuControlIPDns1 OBJECT-TYPE
                        SYNTAX IpAddress
                        MAX-ACCESS read-write
                        STATUS current
                        DESCRIPTION
                                "Onu DNS primary"
                        ::= { fkGponOnuControl 22 }

                
--  1.3.6.1.4.1.10428 9 1.101.23.3.2.23
                -- 1.3.6.1.4.1.10428 9 1.101.23.3.2.23
                fkGponOnuControlIPDns2 OBJECT-TYPE
                        SYNTAX IpAddress
                        MAX-ACCESS read-write
                        STATUS current
                        DESCRIPTION
                                "Onu DNS secondary"
                        ::= { fkGponOnuControl 23 }

                
--  1.3.6.1.4.1.10428 9 1.101.23.3.2.24
                -- 1.3.6.1.4.1.10428 9 1.101.23.3.2.24
                fkGponOnuControlOmciPingTestTimeout OBJECT-TYPE
                        SYNTAX Integer32 (1..1000)
                        UNITS "msec"
                        MAX-ACCESS read-write
                        STATUS current
                        DESCRIPTION
                                "OMCI ping test timeout. <1-1000> (msec)"
                        ::= { fkGponOnuControl 24 }

                
--  1.3.6.1.4.1.10428 9 1.101.23.3.2.25
                -- 1.3.6.1.4.1.10428 9 1.101.23.3.2.25
                fkGponOnuControlActiveStatus OBJECT-TYPE
                        SYNTAX INTEGER
                                {
                                activate(1),
                                deactivate(2)
                                }
                        MAX-ACCESS read-write
                        STATUS current
                        DESCRIPTION
                                "ONU activation/deactivation."
                        ::= { fkGponOnuControl 25 }

                
--  1.3.6.1.4.1.10428 9 1.101.23.3.2.26
                -- 1.3.6.1.4.1.10428 9 1.101.23.3.2.26
                fkGponOnuControlPMProfile OBJECT-TYPE
                        SYNTAX OCTET STRING
                        MAX-ACCESS read-write
                        STATUS current
                        DESCRIPTION
                                "The assigned PM-profile"
                        ::= { fkGponOnuControl 26 }

                
--  1.3.6.1.4.1.10428 9 1.101.23.3.2.27
                -- 1.3.6.1.4.1.10428 9 1.101.23.3.2.27
                fkGponOnuControlNosPartition OBJECT-TYPE
                        SYNTAX INTEGER
                                {
                                os1(1),
                                os2(2),
                                unknown(255)
                                }
                        MAX-ACCESS read-write
                        STATUS current
                        DESCRIPTION
                                "The partition of ONU OS."
                        ::= { fkGponOnuControl 27 }

                
--  1.3.6.1.4.1.10428 9 1.101.23.3.2.28
                -- 1.3.6.1.4.1.10428 9 1.101.23.3.2.28
                fkGponOnuControlBlock OBJECT-TYPE
                        SYNTAX INTEGER
                                {
                                block(1),
                                unblock(2)
                                }
                        MAX-ACCESS read-write
                        STATUS current
                        DESCRIPTION
                                "The Onu Block status."
                        ::= { fkGponOnuControl 28 }

                
                -- 1.3.6.1.4.1.10428 9 1.101.23.3.2.29
                fkGponOnuControlAccountUserName OBJECT-TYPE
                        SYNTAX OCTET STRING
                        MAX-ACCESS read-write
                        STATUS current
                        DESCRIPTION
                                "The account user name."
                        ::= { fkGponOnuControl 29 }

                
                -- 1.3.6.1.4.1.10428 9 1.101.23.3.2.30
                fkGponOnuControlAccountPassword OBJECT-TYPE
                        SYNTAX OCTET STRING
                        MAX-ACCESS read-write
                        STATUS current
                        DESCRIPTION
                                "The account password."
                        ::= { fkGponOnuControl 30 }

                
--  1.3.6.1.4.1.10428 9 1.101.23.3.3
                -- 1.3.6.1.4.1.10428 9 1.101.23.3.3
                fkGponOnuNotification OBJECT IDENTIFIER ::= { fkGponOnu 3 }

                
--  1.3.6.1.4.1.10428 9 1.101.23.3.3.1
                -- 1.3.6.1.4.1.10428 9 1.101.23.3.3.1
                fkGponOnuRegistered NOTIFICATION-TYPE
                        OBJECTS { fkGponOnuControlRequest, fkGponOnuControlTimeStamp, fkGponOnuControlReqResult, fkGponOnuControlOltId, fkGponOnuControlId, 
                                fkGponOnuControlSerial, fkGponOnuControlPasswd, fkGponOnuControlPasswdMode, fkGponOnuControlHwAddr }
                        STATUS current
                        DESCRIPTION 
                                "Description."
                        ::= { fkGponOnuNotification 1 }

                
--  1.3.6.1.4.1.10428 9 1.101.23.3.3.2
                -- 1.3.6.1.4.1.10428 9 1.101.23.3.3.2
                fkGponOnuDeregistered NOTIFICATION-TYPE
                        OBJECTS { fkGponOnuControlRequest, fkGponOnuControlTimeStamp, fkGponOnuControlReqResult, fkGponOnuControlOltId, fkGponOnuControlId, 
                                fkGponOnuControlSerial }
                        STATUS current
                        DESCRIPTION 
                                "Description."
                        ::= { fkGponOnuNotification 2 }

                
--  1.3.6.1.4.1.10428 9 1.101.23.3.3.3
                -- 1.3.6.1.4.1.10428 9 1.101.23.3.3.3
                fkGponOnuProfileChanged NOTIFICATION-TYPE
                        OBJECTS { fkGponOnuControlRequest, fkGponOnuControlTimeStamp, fkGponOnuControlReqResult, fkGponOnuControlOltId, fkGponOnuControlId, 
                                fkGponOnuControlSerial, fkGponOnuControlProfile }
                        STATUS current
                        DESCRIPTION 
                                "Description."
                        ::= { fkGponOnuNotification 3 }

                
--  1.3.6.1.4.1.10428 9 1.101.23.3.3.4
                -- 1.3.6.1.4.1.10428 9 1.101.23.3.3.4
                fkGponOnuFixed NOTIFICATION-TYPE
                        OBJECTS { fkGponOnuControlRequest, fkGponOnuControlTimeStamp, fkGponOnuControlReqResult, fkGponOnuControlOltId, fkGponOnuControlId, 
                                fkGponOnuControlSerial }
                        STATUS current
                        DESCRIPTION 
                                "Description."
                        ::= { fkGponOnuNotification 4 }

                
--  1.3.6.1.4.1.10428 9 1.101.23.3.3.5
                -- 1.3.6.1.4.1.10428 9 1.101.23.3.3.5
                fkGponOnuUpgradeNosChanged NOTIFICATION-TYPE
                        OBJECTS { fkGponOnuControlRequest, fkGponOnuControlTimeStamp, fkGponOnuControlReqResult, fkGponOnuControlOltId, fkGponOnuControlId, 
                                fkGponOnuControlSerial, fkGponOnuControlNosUpgradePath }
                        STATUS current
                        DESCRIPTION 
                                "Description."
                        ::= { fkGponOnuNotification 5 }

                
--  1.3.6.1.4.1.10428 9 1.101.23.3.3.6
                -- 1.3.6.1.4.1.10428 9 1.101.23.3.3.6
                fkGponOnuNosActiveChanged NOTIFICATION-TYPE
                        OBJECTS { fkGponOnuControlRequest, fkGponOnuControlTimeStamp, fkGponOnuControlReqResult, fkGponOnuControlOltId, fkGponOnuControlId, 
                                fkGponOnuControlSerial }
                        STATUS current
                        DESCRIPTION 
                                "Description."
                        ::= { fkGponOnuNotification 6 }

                
--  1.3.6.1.4.1.10428 9 1.101.23.3.3.7
                -- 1.3.6.1.4.1.10428 9 1.101.23.3.3.7
                fkGponOnuEncModeChanged NOTIFICATION-TYPE
                        OBJECTS { fkGponOnuControlRequest, fkGponOnuControlTimeStamp, fkGponOnuControlReqResult, fkGponOnuControlOltId, fkGponOnuControlId, 
                                fkGponOnuControlSerial, fkGponOnuControlEncMode }
                        STATUS current
                        DESCRIPTION 
                                "Description."
                        ::= { fkGponOnuNotification 7 }

                
--  1.3.6.1.4.1.10428 9 1.101.23.3.3.8
                -- 1.3.6.1.4.1.10428 9 1.101.23.3.3.8
                fkGponOnuReset NOTIFICATION-TYPE
                        OBJECTS { fkGponOnuControlRequest, fkGponOnuControlTimeStamp, fkGponOnuControlReqResult, fkGponOnuControlOltId, fkGponOnuControlId, 
                                fkGponOnuControlSerial }
                        STATUS current
                        DESCRIPTION 
                                "Description."
                        ::= { fkGponOnuNotification 8 }

                
--  1.3.6.1.4.1.10428 9 1.101.23.3.3.9
                -- 1.3.6.1.4.1.10428 9 1.101.23.3.3.9
                fkGponOnuTxOffOpticChanged NOTIFICATION-TYPE
                        OBJECTS { fkGponOnuControlRequest, fkGponOnuControlTimeStamp, fkGponOnuControlReqResult, fkGponOnuControlOltId, fkGponOnuControlId, 
                                fkGponOnuControlSerial, fkGponOnuControlTxOffOptic }
                        STATUS current
                        DESCRIPTION 
                                "Description."
                        ::= { fkGponOnuNotification 9 }

                
--  1.3.6.1.4.1.10428 9 1.101.23.3.3.10
                -- 1.3.6.1.4.1.10428 9 1.101.23.3.3.10
                fkGponOnuDescriptionChanged NOTIFICATION-TYPE
                        OBJECTS { fkGponOnuControlRequest, fkGponOnuControlTimeStamp, fkGponOnuControlReqResult, fkGponOnuControlOltId, fkGponOnuControlId, 
                                fkGponOnuControlSerial, fkGponOnuControlDescription }
                        STATUS current
                        DESCRIPTION 
                                "Description."
                        ::= { fkGponOnuNotification 10 }

                
--  1.3.6.1.4.1.10428 9 1.101.23.3.3.11
                -- 1.3.6.1.4.1.10428 9 1.101.23.3.3.11
                fkGponOnuFecModeChanged NOTIFICATION-TYPE
                        OBJECTS { fkGponOnuControlRequest, fkGponOnuControlTimeStamp, fkGponOnuControlReqResult, fkGponOnuControlOltId, fkGponOnuControlId, 
                                fkGponOnuControlFecModeUS }
                        STATUS current
                        DESCRIPTION 
                                "Description."
                        ::= { fkGponOnuNotification 11 }

                
--  1.3.6.1.4.1.10428 9 1.101.23.3.3.12
                -- 1.3.6.1.4.1.10428 9 1.101.23.3.3.12
                fkGponOnuIPInfoChanged NOTIFICATION-TYPE
                        OBJECTS { fkGponOnuControlRequest, fkGponOnuControlTimeStamp, fkGponOnuControlReqResult, fkGponOnuControlOltId, fkGponOnuControlId, 
                                fkGponOnuControlIPMode, fkGponOnuControlIPAddr, fkGponOnuControlIPMask, fkGponOnuControlIPGw, fkGponOnuControlIPDns1, 
                                fkGponOnuControlIPDns2 }
                        STATUS current
                        DESCRIPTION 
                                "Description."
                        ::= { fkGponOnuNotification 12 }

                
--  1.3.6.1.4.1.10428 9 1.101.23.3.3.13
                -- 1.3.6.1.4.1.10428 9 1.101.23.3.3.13
                fkGponOnuOmciPingTest NOTIFICATION-TYPE
                        OBJECTS { fkGponOnuControlRequest, fkGponOnuControlTimeStamp, fkGponOnuControlReqResult, fkGponOnuControlOltId, fkGponOnuControlId, 
                                fkGponOnuControlOmciPingTestTimeout }
                        STATUS current
                        DESCRIPTION 
                                "Description."
                        ::= { fkGponOnuNotification 13 }

                
--  1.3.6.1.4.1.10428 9 1.101.23.3.3.14
                -- 1.3.6.1.4.1.10428 9 1.101.23.3.3.14
                fkGponOnuActivationChanged NOTIFICATION-TYPE
                        OBJECTS { fkGponOnuControlRequest, fkGponOnuControlTimeStamp, fkGponOnuControlReqResult, fkGponOnuControlOltId, fkGponOnuControlId, 
                                fkGponOnuControlActiveStatus }
                        STATUS current
                        DESCRIPTION 
                                "Description."
                        ::= { fkGponOnuNotification 14 }

                
--  1.3.6.1.4.1.10428 9 1.101.23.3.3.15
                -- 1.3.6.1.4.1.10428 9 1.101.23.3.3.15
                fkGponOnuPMProfileChanged NOTIFICATION-TYPE
                        OBJECTS { fkGponOnuControlRequest, fkGponOnuControlTimeStamp, fkGponOnuControlReqResult, fkGponOnuControlOltId, fkGponOnuControlId, 
                                fkGponOnuControlPMProfile }
                        STATUS current
                        DESCRIPTION 
                                "Description."
                        ::= { fkGponOnuNotification 15 }

                
--  1.3.6.1.4.1.10428 9 1.101.23.3.3.16
                -- 1.3.6.1.4.1.10428 9 1.101.23.3.3.16
                fkGponOnuUpgradeNosPartitionChanged NOTIFICATION-TYPE
                        OBJECTS { fkGponOnuControlRequest, fkGponOnuControlTimeStamp, fkGponOnuControlReqResult, fkGponOnuControlOltId, fkGponOnuControlId, 
                                fkGponOnuControlSerial, fkGponOnuControlNosUpgradePath, fkGponOnuControlNosPartition }
                        STATUS current
                        DESCRIPTION 
                                "Description."
                        ::= { fkGponOnuNotification 16 }

                
--  1.3.6.1.4.1.10428 9 1.101.23.3.3.17
                -- 1.3.6.1.4.1.10428 9 1.101.23.3.3.17
                fkGponOnuUpgradeNosCommited NOTIFICATION-TYPE
                        OBJECTS { fkGponOnuControlRequest, fkGponOnuControlTimeStamp, fkGponOnuControlReqResult, fkGponOnuControlOltId, fkGponOnuControlId, 
                                fkGponOnuControlSerial, fkGponOnuControlNosPartition }
                        STATUS current
                        DESCRIPTION 
                                "Description."
                        ::= { fkGponOnuNotification 17 }

                
--  1.3.6.1.4.1.10428 9 1.101.23.3.3.18
                -- 1.3.6.1.4.1.10428 9 1.101.23.3.3.18
                fkGponOnuUpgradeNosActiveChanged NOTIFICATION-TYPE
                        OBJECTS { fkGponOnuControlRequest, fkGponOnuControlTimeStamp, fkGponOnuControlReqResult, fkGponOnuControlOltId, fkGponOnuControlId, 
                                fkGponOnuControlSerial }
                        STATUS current
                        DESCRIPTION 
                                "Description."
                        ::= { fkGponOnuNotification 18 }

                
--  1.3.6.1.4.1.10428 9 1.101.23.3.3.19
                -- 1.3.6.1.4.1.10428 9 1.101.23.3.3.19
                fkGponOnuBlockChanged NOTIFICATION-TYPE
                        OBJECTS { fkGponOnuControlRequest, fkGponOnuControlTimeStamp, fkGponOnuControlReqResult, fkGponOnuControlBlock, fkGponOnuControlSerial, 
                                fkGponOnuControlId, fkGponOnuControlOltId }
                        STATUS current
                        DESCRIPTION 
                                "Description."
                        ::= { fkGponOnuNotification 19 }

                
                -- 1.3.6.1.4.1.10428 9 1.101.23.3.3.20
                fkGponOnuUpdateOltRxPowerChanged NOTIFICATION-TYPE
                        OBJECTS { fkGponOnuControlRequest, fkGponOnuControlTimeStamp, fkGponOnuControlReqResult, fkGponOnuControlOltId, fkGponOnuControlId
                                 }
                        STATUS current
                        DESCRIPTION 
                                "fkGponOnuUpdateOltRxPowerChanged"
                        ::= { fkGponOnuNotification 20 }

                
                -- 1.3.6.1.4.1.10428 9 1.101.23.3.3.21
                fkGponOnuSystemInfoUpdated NOTIFICATION-TYPE
                        OBJECTS { fkGponOnuControlRequest, fkGponOnuControlTimeStamp, fkGponOnuControlReqResult, fkGponOnuControlOltId, fkGponOnuControlId
                                 }
                        STATUS current
                        DESCRIPTION 
                                "Description."
                        ::= { fkGponOnuNotification 21 }

                
                -- 1.3.6.1.4.1.10428 9 1.101.23.3.3.22
                fkGponOnuTxOnOptic NOTIFICATION-TYPE
                        OBJECTS { fkGponOnuControlRequest, fkGponOnuControlTimeStamp, fkGponOnuControlReqResult, fkGponOnuControlOltId, fkGponOnuControlId
                                 }
                        STATUS current
                        DESCRIPTION 
                                "Description."
                        ::= { fkGponOnuNotification 22 }

                
                -- 1.3.6.1.4.1.10428 9 1.101.23.3.3.23
                fkGponOnuLoopDetectUnblockChanged NOTIFICATION-TYPE
                        OBJECTS { fkGponOnuControlRequest, fkGponOnuControlTimeStamp, fkGponOnuControlReqResult, fkGponOnuControlOltId, fkGponOnuControlId
                                 }
                        STATUS current
                        DESCRIPTION 
                                "setOnuLoopDetectUnblock"
                        ::= { fkGponOnuNotification 23 }

                
                -- 1.3.6.1.4.1.10428 9 1.101.23.3.3.24
                fkGponOnuUserMacCntUpdated NOTIFICATION-TYPE
                        OBJECTS { fkGponOnuControlRequest, fkGponOnuControlTimeStamp, fkGponOnuControlReqResult, fkGponOltId, fkGponOnuId
                                 }
                        STATUS current
                        DESCRIPTION 
                                "updateOnuUserMacCnt"
                        ::= { fkGponOnuNotification 24 }

                
                -- 1.3.6.1.4.1.10428 9 1.101.23.3.3.25
                fkGponOnuAccountUpdated NOTIFICATION-TYPE
                        OBJECTS { fkGponOnuControlRequest, fkGponOnuControlTimeStamp, fkGponOnuControlReqResult, fkGponOnuControlOltId, fkGponOnuControlId
                                 }
                        STATUS current
                        DESCRIPTION 
                                "updateOnuAccount "
                        ::= { fkGponOnuNotification 25 }

                
                -- 1.3.6.1.4.1.10428 9 1.101.23.3.3.26
                fkGponOnuAccountChanged NOTIFICATION-TYPE
                        OBJECTS { fkGponOnuControlRequest, fkGponOnuControlTimeStamp, fkGponOnuControlReqResult, fkGponOnuControlOltId, fkGponOnuControlId
                                 }
                        STATUS current
                        DESCRIPTION 
                                "setOnuAccount "
                        ::= { fkGponOnuNotification 26 }

                
--  1.3.6.1.4.1.10428 9 1.101.23.4
                -- 1.3.6.1.4.1.10428 9 1.101.23.4
                fkGponTcont OBJECT IDENTIFIER ::= { fkGpon 4 }

                
--  1.3.6.1.4.1.10428 9 1.101.23.4.1
                -- 1.3.6.1.4.1.10428 9 1.101.23.4.1
                fkGponTcontTable OBJECT-TYPE
                        SYNTAX SEQUENCE OF FkGponTcontEntry
                        MAX-ACCESS not-accessible
                        STATUS current
                        DESCRIPTION
                                "fkGponTcontTable"
                        ::= { fkGponTcont 1 }

                
--  1.3.6.1.4.1.10428 9 1.101.23.4.1.1
                -- 1.3.6.1.4.1.10428 9 1.101.23.4.1.1
                fkGponTcontEntry OBJECT-TYPE
                        SYNTAX FkGponTcontEntry
                        MAX-ACCESS not-accessible
                        STATUS current
                        DESCRIPTION
                                "key: fkGponOltId, fkGponTcontId"
                        INDEX { fkGponOltId, fkGponTcontId }
                        ::= { fkGponTcontTable 1 }

                
                FkGponTcontEntry ::=
                        SEQUENCE { 
                                fkGponTcontId
                                        INTEGER,
                                fkGponTcontOnuId
                                        INTEGER,
                                fkGponTcontDBAMode
                                        INTEGER,
                                fkGponTcontFixedBw
                                        INTEGER,
                                fkGponTcontAssuredBw
                                        INTEGER,
                                fkGponTcontMaxBw
                                        INTEGER
                         }

--  1.3.6.1.4.1.10428 9 1.101.23.4.1.1.1
                -- 1.3.6.1.4.1.10428 9 1.101.23.4.1.1.1
                fkGponTcontId OBJECT-TYPE
                        SYNTAX INTEGER (1..512)
                        MAX-ACCESS read-only
                        STATUS current
                        DESCRIPTION
                                "Tcon Id"
                        ::= { fkGponTcontEntry 1 }

                
--  1.3.6.1.4.1.10428 9 1.101.23.4.1.1.2
                -- 1.3.6.1.4.1.10428 9 1.101.23.4.1.1.2
                fkGponTcontOnuId OBJECT-TYPE
                        SYNTAX INTEGER (1..65535)
                        MAX-ACCESS read-only
                        STATUS current
                        DESCRIPTION
                                "Tcont assigned ONU Id"
                        ::= { fkGponTcontEntry 2 }

                
--  1.3.6.1.4.1.10428 9 1.101.23.4.1.1.3
                -- 1.3.6.1.4.1.10428 9 1.101.23.4.1.1.3
                fkGponTcontDBAMode OBJECT-TYPE
                        SYNTAX INTEGER
                                {
                                nsr(1),
                                sr(2),
                                fixed(3)
                                }
                        MAX-ACCESS read-only
                        STATUS current
                        DESCRIPTION
                                "Status reports received from ONUs"
                        ::= { fkGponTcontEntry 3 }

                
--  1.3.6.1.4.1.10428 9 1.101.23.4.1.1.4
                -- 1.3.6.1.4.1.10428 9 1.101.23.4.1.1.4
                fkGponTcontFixedBw OBJECT-TYPE
                        SYNTAX INTEGER (1..65535)
                        UNITS "64kbps"
                        MAX-ACCESS read-only
                        STATUS current
                        DESCRIPTION
                                "Upstream fixed bandwidth.<128-1031616>"
                        ::= { fkGponTcontEntry 4 }

                
--  1.3.6.1.4.1.10428 9 1.101.23.4.1.1.5
                -- 1.3.6.1.4.1.10428 9 1.101.23.4.1.1.5
                fkGponTcontAssuredBw OBJECT-TYPE
                        SYNTAX INTEGER (1..65535)
                        UNITS "64kbps"
                        MAX-ACCESS read-only
                        STATUS current
                        DESCRIPTION
                                "Upstream assured bandwidth.<0-1031616>"
                        ::= { fkGponTcontEntry 5 }

                
--  1.3.6.1.4.1.10428 9 1.101.23.4.1.1.6
                -- 1.3.6.1.4.1.10428 9 1.101.23.4.1.1.6
                fkGponTcontMaxBw OBJECT-TYPE
                        SYNTAX INTEGER (1..65535)
                        UNITS "64kbps"
                        MAX-ACCESS read-only
                        STATUS current
                        DESCRIPTION
                                "Upstream max bandwidth.<128-1031616>"
                        ::= { fkGponTcontEntry 6 }

                
--  1.3.6.1.4.1.10428 9 1.101.23.4.2
                -- 1.3.6.1.4.1.10428 9 1.101.23.4.2
                fkGponTcontControl OBJECT IDENTIFIER ::= { fkGponTcont 2 }

                
--  1.3.6.1.4.1.10428 9 1.101.23.4.2.1
                -- 1.3.6.1.4.1.10428 9 1.101.23.4.2.1
                fkGponTcontControlRequest OBJECT-TYPE
                        SYNTAX INTEGER
                                {
                                createTcon(1),
                                destroyTcon(2)
                                }
                        MAX-ACCESS read-write
                        STATUS current
                        DESCRIPTION
                                "The request of a user command"
                        ::= { fkGponTcontControl 1 }

                
--  1.3.6.1.4.1.10428 9 1.101.23.4.2.2
                -- 1.3.6.1.4.1.10428 9 1.101.23.4.2.2
                fkGponTcontControlStatus OBJECT-TYPE
                        SYNTAX FkControlStatusType
                        MAX-ACCESS read-only
                        STATUS current
                        DESCRIPTION
                                "The status of user command"
                        ::= { fkGponTcontControl 2 }

                
--  1.3.6.1.4.1.10428 9 1.101.23.4.2.3
                -- 1.3.6.1.4.1.10428 9 1.101.23.4.2.3
                fkGponTcontControlTimer OBJECT-TYPE
                        SYNTAX Gauge32
                        MAX-ACCESS read-write
                        STATUS current
                        DESCRIPTION
                                "The maximum time for the manager for a long running user command"
                        ::= { fkGponTcontControl 3 }

                
--  1.3.6.1.4.1.10428 9 1.101.23.4.2.4
                -- 1.3.6.1.4.1.10428 9 1.101.23.4.2.4
                fkGponTcontControlTimeStamp OBJECT-TYPE
                        SYNTAX TimeTicks
                        MAX-ACCESS read-only
                        STATUS current
                        DESCRIPTION
                                "The time stamp of the last command(end of command)"
                        ::= { fkGponTcontControl 4 }

                
--  1.3.6.1.4.1.10428 9 1.101.23.4.2.5
                -- 1.3.6.1.4.1.10428 9 1.101.23.4.2.5
                fkGponTcontControlReqResult OBJECT-TYPE
                        SYNTAX FkControlRequestResultType
                        MAX-ACCESS read-only
                        STATUS current
                        DESCRIPTION
                                "The result of the last user command"
                        ::= { fkGponTcontControl 5 }

                
--  1.3.6.1.4.1.10428 9 1.101.23.4.2.6
                -- 1.3.6.1.4.1.10428 9 1.101.23.4.2.6
                fkGponTcontControlId OBJECT-TYPE
                        SYNTAX INTEGER (1..65535)
                        MAX-ACCESS read-write
                        STATUS current
                        DESCRIPTION
                                "Tcon Id.<256-1023>"
                        ::= { fkGponTcontControl 6 }

                
--  1.3.6.1.4.1.10428 9 1.101.23.4.2.7
                -- 1.3.6.1.4.1.10428 9 1.101.23.4.2.7
                fkGponTcontControlOltId OBJECT-TYPE
                        SYNTAX INTEGER (1..65535)
                        MAX-ACCESS read-write
                        STATUS current
                        DESCRIPTION
                                "Gpon Olt Id"
                        ::= { fkGponTcontControl 7 }

                
--  1.3.6.1.4.1.10428 9 1.101.23.4.2.8
                -- 1.3.6.1.4.1.10428 9 1.101.23.4.2.8
                fkGponTcontControlOnuId OBJECT-TYPE
                        SYNTAX INTEGER (1..65535)
                        MAX-ACCESS read-write
                        STATUS current
                        DESCRIPTION
                                "Gpon Onu Id"
                        ::= { fkGponTcontControl 8 }

                
--  1.3.6.1.4.1.10428 9 1.101.23.4.2.9
                -- 1.3.6.1.4.1.10428 9 1.101.23.4.2.9
                fkGponTcontControlDBAMode OBJECT-TYPE
                        SYNTAX INTEGER
                                {
                                nsr(1),
                                sr(2),
                                fixed(3)
                                }
                        MAX-ACCESS read-write
                        STATUS current
                        DESCRIPTION
                                "Status reports received from ONUs"
                        ::= { fkGponTcontControl 9 }

                
--  1.3.6.1.4.1.10428 9 1.101.23.4.2.10
                -- 1.3.6.1.4.1.10428 9 1.101.23.4.2.10
                fkGponTcontControlFixedBw OBJECT-TYPE
                        SYNTAX INTEGER (1..65535)
                        MAX-ACCESS read-write
                        STATUS current
                        DESCRIPTION
                                "Upstream fixed bandwidth.<128-1031616>"
                        ::= { fkGponTcontControl 10 }

                
--  1.3.6.1.4.1.10428 9 1.101.23.4.2.11
                -- 1.3.6.1.4.1.10428 9 1.101.23.4.2.11
                fkGponTcontControlAssuredBw OBJECT-TYPE
                        SYNTAX INTEGER (1..65535)
                        MAX-ACCESS read-write
                        STATUS current
                        DESCRIPTION
                                "Upstream assured bandwidth.<0-1031616>"
                        ::= { fkGponTcontControl 11 }

                
--  1.3.6.1.4.1.10428 9 1.101.23.4.2.12
                -- 1.3.6.1.4.1.10428 9 1.101.23.4.2.12
                fkGponTcontControlMaxBw OBJECT-TYPE
                        SYNTAX INTEGER (1..65535)
                        MAX-ACCESS read-write
                        STATUS current
                        DESCRIPTION
                                "Upstream max bandwidth.<128-1031616>"
                        ::= { fkGponTcontControl 12 }

                
--  1.3.6.1.4.1.10428 9 1.101.23.4.2.13
                -- 1.3.6.1.4.1.10428 9 1.101.23.4.2.13
                fkGponTcontControlOnuSerial OBJECT-TYPE
                        SYNTAX OCTET STRING
                        MAX-ACCESS read-write
                        STATUS current
                        DESCRIPTION
                                "ONU Serial Number"
                        ::= { fkGponTcontControl 13 }

                
--  1.3.6.1.4.1.10428 9 1.101.23.4.3
                -- 1.3.6.1.4.1.10428 9 1.101.23.4.3
                fkGponTcontNotification OBJECT IDENTIFIER ::= { fkGponTcont 3 }

                
--  1.3.6.1.4.1.10428 9 1.101.23.4.3.1
                -- 1.3.6.1.4.1.10428 9 1.101.23.4.3.1
                fkGponTcontCreated NOTIFICATION-TYPE
                        OBJECTS { fkGponTcontControlRequest, fkGponTcontControlTimeStamp, fkGponTcontControlReqResult, fkGponTcontControlId, fkGponTcontControlOltId, 
                                fkGponTcontControlOnuId, fkGponTcontControlDBAMode, fkGponTcontControlFixedBw, fkGponTcontControlAssuredBw, fkGponTcontControlMaxBw, 
                                fkGponTcontControlOnuSerial }
                        STATUS current
                        DESCRIPTION 
                                "Description."
                        ::= { fkGponTcontNotification 1 }

                
--  1.3.6.1.4.1.10428 9 1.101.23.4.3.2
                -- 1.3.6.1.4.1.10428 9 1.101.23.4.3.2
                fkGponTcontDestroyed NOTIFICATION-TYPE
                        OBJECTS { fkGponTcontControlRequest, fkGponTcontControlTimeStamp, fkGponTcontControlReqResult, fkGponTcontControlId, fkGponTcontControlOltId, 
                                fkGponTcontControlOnuId, fkGponTcontControlOnuSerial }
                        STATUS current
                        DESCRIPTION 
                                "Description."
                        ::= { fkGponTcontNotification 2 }

                
--  1.3.6.1.4.1.10428 9 1.101.23.5
                -- 1.3.6.1.4.1.10428 9 1.101.23.5
                fkGponProfile OBJECT IDENTIFIER ::= { fkGpon 5 }

                
--  1.3.6.1.4.1.10428 9 1.101.23.5.1
                -- 1.3.6.1.4.1.10428 9 1.101.23.5.1
                fkGponProfileBase OBJECT IDENTIFIER ::= { fkGponProfile 1 }

                
--  1.3.6.1.4.1.10428 9 1.101.23.5.1.1
                -- 1.3.6.1.4.1.10428 9 1.101.23.5.1.1
                fkGponProfileBaseTable OBJECT-TYPE
                        SYNTAX SEQUENCE OF FkGponProfileBaseEntry
                        MAX-ACCESS not-accessible
                        STATUS current
                        DESCRIPTION
                                "fkGponProfileBaseTable"
                        ::= { fkGponProfileBase 1 }

                
--  1.3.6.1.4.1.10428 9 1.101.23.5.1.1.1
                -- 1.3.6.1.4.1.10428 9 1.101.23.5.1.1.1
                fkGponProfileBaseEntry OBJECT-TYPE
                        SYNTAX FkGponProfileBaseEntry
                        MAX-ACCESS not-accessible
                        STATUS current
                        DESCRIPTION
                                "key: fkGponProfileId"
                        INDEX { fkGponProfileId }
                        ::= { fkGponProfileBaseTable 1 }

                
                FkGponProfileBaseEntry ::=
                        SEQUENCE { 
                                fkGponProfileId
                                        INTEGER,
                                fkGponProfileName
                                        OCTET STRING,
                                fkGponProfileDscpToPbit
                                        INTEGER,
                                fkGponProfileTcontProfileCnt
                                        INTEGER,
                                fkGponProfileTcontProfile
                                        OCTET STRING,
                                fkGponProfileVoIPProfileCnt
                                        INTEGER,
                                fkGponProfileVoIPProfile
                                        OCTET STRING
                         }

--  1.3.6.1.4.1.10428 9 1.101.23.5.1.1.1.1
                -- 1.3.6.1.4.1.10428 9 1.101.23.5.1.1.1.1
                fkGponProfileId OBJECT-TYPE
                        SYNTAX INTEGER (1..512)
                        MAX-ACCESS read-only
                        STATUS current
                        DESCRIPTION
                                "Profile Id"
                        ::= { fkGponProfileBaseEntry 1 }

                
--  1.3.6.1.4.1.10428 9 1.101.23.5.1.1.1.2
                -- 1.3.6.1.4.1.10428 9 1.101.23.5.1.1.1.2
                fkGponProfileName OBJECT-TYPE
                        SYNTAX OCTET STRING
                        MAX-ACCESS read-only
                        STATUS current
                        DESCRIPTION
                                "Profile Name"
                        ::= { fkGponProfileBaseEntry 2 }

                
--  1.3.6.1.4.1.10428 9 1.101.23.5.1.1.1.3
                -- 1.3.6.1.4.1.10428 9 1.101.23.5.1.1.1.3
                fkGponProfileDscpToPbit OBJECT-TYPE
                        SYNTAX INTEGER
                                {
                                enable(1),
                                disable(2)
                                }
                        MAX-ACCESS read-only
                        STATUS current
                        DESCRIPTION
                                "DSCP to P bit marking"
                        ::= { fkGponProfileBaseEntry 3 }

                
--  1.3.6.1.4.1.10428 9 1.101.23.5.1.1.1.4
                -- 1.3.6.1.4.1.10428 9 1.101.23.5.1.1.1.4
                fkGponProfileTcontProfileCnt OBJECT-TYPE
                        SYNTAX INTEGER (1..65535)
                        MAX-ACCESS read-only
                        STATUS current
                        DESCRIPTION
                                "Assgined Tcont Profile count
                                Indicate how many tcont profile assigned"
                        ::= { fkGponProfileBaseEntry 4 }

                
--  1.3.6.1.4.1.10428 9 1.101.23.5.1.1.1.5
                -- 1.3.6.1.4.1.10428 9 1.101.23.5.1.1.1.5
                fkGponProfileTcontProfile OBJECT-TYPE
                        SYNTAX OCTET STRING
                        MAX-ACCESS read-only
                        STATUS current
                        DESCRIPTION
                                "Assigned TconT Profile Map
                                2bytes indicate TconT Profile Index.
                                # 0001 0003 0004 ....."
                        ::= { fkGponProfileBaseEntry 5 }

                
--  1.3.6.1.4.1.10428 9 1.101.23.5.1.1.1.6
                -- 1.3.6.1.4.1.10428 9 1.101.23.5.1.1.1.6
                fkGponProfileVoIPProfileCnt OBJECT-TYPE
                        SYNTAX INTEGER (1..65535)
                        MAX-ACCESS read-only
                        STATUS current
                        DESCRIPTION
                                "Assgined VoIP Profile count
                                Indicate how many VoIP profile assigned(UnUsed)"
                        ::= { fkGponProfileBaseEntry 6 }

                
--  1.3.6.1.4.1.10428 9 1.101.23.5.1.1.1.7
                -- 1.3.6.1.4.1.10428 9 1.101.23.5.1.1.1.7
                fkGponProfileVoIPProfile OBJECT-TYPE
                        SYNTAX OCTET STRING
                        MAX-ACCESS read-only
                        STATUS current
                        DESCRIPTION
                                "Assigned VoIP Profile Map
                                2bytes indicate VoIP Profile Index(UnUsed)"
                        ::= { fkGponProfileBaseEntry 7 }

                
--  1.3.6.1.4.1.10428 9 1.101.23.5.1.2
                -- 1.3.6.1.4.1.10428 9 1.101.23.5.1.2
                fkGponProfileBaseControl OBJECT IDENTIFIER ::= { fkGponProfileBase 2 }

                
--  1.3.6.1.4.1.10428 9 1.101.23.5.1.2.1
                -- 1.3.6.1.4.1.10428 9 1.101.23.5.1.2.1
                fkGponProfileBaseControlRequest OBJECT-TYPE
                        SYNTAX INTEGER
                                {
                                createProfile(1),
                                modifyProfile(2),
                                destroyProfile(3),
                                updateTcontProfile(4),
                                updateVoipProfile(5)
                                }
                        MAX-ACCESS read-write
                        STATUS current
                        DESCRIPTION
                                "The request of a user command"
                        ::= { fkGponProfileBaseControl 1 }

                
--  1.3.6.1.4.1.10428 9 1.101.23.5.1.2.2
                -- 1.3.6.1.4.1.10428 9 1.101.23.5.1.2.2
                fkGponProfileBaseControlStatus OBJECT-TYPE
                        SYNTAX FkControlStatusType
                        MAX-ACCESS read-only
                        STATUS current
                        DESCRIPTION
                                "The status of user command"
                        ::= { fkGponProfileBaseControl 2 }

                
--  1.3.6.1.4.1.10428 9 1.101.23.5.1.2.3
                -- 1.3.6.1.4.1.10428 9 1.101.23.5.1.2.3
                fkGponProfileBaseControlTimer OBJECT-TYPE
                        SYNTAX Gauge32
                        MAX-ACCESS read-write
                        STATUS current
                        DESCRIPTION
                                "The maximum time for the manager for a long running user command"
                        ::= { fkGponProfileBaseControl 3 }

                
--  1.3.6.1.4.1.10428 9 1.101.23.5.1.2.4
                -- 1.3.6.1.4.1.10428 9 1.101.23.5.1.2.4
                fkGponProfileBaseControlTimeStamp OBJECT-TYPE
                        SYNTAX TimeTicks
                        MAX-ACCESS read-only
                        STATUS current
                        DESCRIPTION
                                "The time stamp of the last command(end of command)"
                        ::= { fkGponProfileBaseControl 4 }

                
--  1.3.6.1.4.1.10428 9 1.101.23.5.1.2.5
                -- 1.3.6.1.4.1.10428 9 1.101.23.5.1.2.5
                fkGponProfileBaseControlReqResult OBJECT-TYPE
                        SYNTAX FkControlRequestResultType
                        MAX-ACCESS read-only
                        STATUS current
                        DESCRIPTION
                                "The result of the last user command"
                        ::= { fkGponProfileBaseControl 5 }

                
--  1.3.6.1.4.1.10428 9 1.101.23.5.1.2.6
                -- 1.3.6.1.4.1.10428 9 1.101.23.5.1.2.6
                fkGponProfileBaseControlName OBJECT-TYPE
                        SYNTAX OCTET STRING
                        MAX-ACCESS read-write
                        STATUS current
                        DESCRIPTION
                                "Profile Name"
                        ::= { fkGponProfileBaseControl 6 }

                
--  1.3.6.1.4.1.10428 9 1.101.23.5.1.2.7
                -- 1.3.6.1.4.1.10428 9 1.101.23.5.1.2.7
                fkGponProfileBaseControlDscpToPbit OBJECT-TYPE
                        SYNTAX INTEGER
                                {
                                enable(1),
                                disable(2)
                                }
                        MAX-ACCESS read-write
                        STATUS current
                        DESCRIPTION
                                "DSCP to P bit marking"
                        ::= { fkGponProfileBaseControl 7 }

                
--  1.3.6.1.4.1.10428 9 1.101.23.5.1.2.8
                -- 1.3.6.1.4.1.10428 9 1.101.23.5.1.2.8
                fkGponProfileControlTcontProfileCnt OBJECT-TYPE
                        SYNTAX INTEGER (1..65535)
                        MAX-ACCESS read-write
                        STATUS current
                        DESCRIPTION
                                "Assgined Tcont Profile count"
                        ::= { fkGponProfileBaseControl 8 }

                
--  1.3.6.1.4.1.10428 9 1.101.23.5.1.2.9
                -- 1.3.6.1.4.1.10428 9 1.101.23.5.1.2.9
                fkGponProfileControlTcontProfile OBJECT-TYPE
                        SYNTAX OCTET STRING
                        MAX-ACCESS read-write
                        STATUS current
                        DESCRIPTION
                                "Assigned TconT Profile Map"
                        ::= { fkGponProfileBaseControl 9 }

                
--  1.3.6.1.4.1.10428 9 1.101.23.5.1.2.10
                -- 1.3.6.1.4.1.10428 9 1.101.23.5.1.2.10
                fkGponProfileControlVoipProfileCnt OBJECT-TYPE
                        SYNTAX INTEGER (1..65535)
                        MAX-ACCESS read-write
                        STATUS current
                        DESCRIPTION
                                "Assgined VoIP Profile count"
                        ::= { fkGponProfileBaseControl 10 }

                
--  1.3.6.1.4.1.10428 9 1.101.23.5.1.2.11
                -- 1.3.6.1.4.1.10428 9 1.101.23.5.1.2.11
                fkGponProfileControlVoipProfile OBJECT-TYPE
                        SYNTAX OCTET STRING
                        MAX-ACCESS read-write
                        STATUS current
                        DESCRIPTION
                                "Assigned VoIP Profile Map"
                        ::= { fkGponProfileBaseControl 11 }

                
--  1.3.6.1.4.1.10428 9 1.101.23.5.1.3
                -- 1.3.6.1.4.1.10428 9 1.101.23.5.1.3
                fkGponProfileBaseNotification OBJECT IDENTIFIER ::= { fkGponProfileBase 3 }

                
--  1.3.6.1.4.1.10428 9 1.101.23.5.1.3.1
                -- 1.3.6.1.4.1.10428 9 1.101.23.5.1.3.1
                fkGponProfileBaseCreated NOTIFICATION-TYPE
                        OBJECTS { fkGponProfileBaseControlRequest, fkGponProfileBaseControlTimeStamp, fkGponProfileBaseControlReqResult, fkGponProfileBaseControlName, fkGponProfileBaseControlDscpToPbit
                                 }
                        STATUS current
                        DESCRIPTION 
                                "Description."
                        ::= { fkGponProfileBaseNotification 1 }

                
--  1.3.6.1.4.1.10428 9 1.101.23.5.1.3.2
                -- 1.3.6.1.4.1.10428 9 1.101.23.5.1.3.2
                fkGponProfileBaseModified NOTIFICATION-TYPE
                        OBJECTS { fkGponProfileBaseControlRequest, fkGponProfileBaseControlTimeStamp, fkGponProfileBaseControlReqResult, fkGponProfileBaseControlName, fkGponProfileBaseControlDscpToPbit
                                 }
                        STATUS current
                        DESCRIPTION 
                                "Description."
                        ::= { fkGponProfileBaseNotification 2 }

                
--  1.3.6.1.4.1.10428 9 1.101.23.5.1.3.3
                -- 1.3.6.1.4.1.10428 9 1.101.23.5.1.3.3
                fkGponProfileBaseDestroyed NOTIFICATION-TYPE
                        OBJECTS { fkGponProfileBaseControlRequest, fkGponProfileBaseControlTimeStamp, fkGponProfileBaseControlReqResult, fkGponProfileBaseControlName }
                        STATUS current
                        DESCRIPTION 
                                "Description."
                        ::= { fkGponProfileBaseNotification 3 }

                
--  1.3.6.1.4.1.10428 9 1.101.23.5.1.3.4
                -- 1.3.6.1.4.1.10428 9 1.101.23.5.1.3.4
                fkGponProfileTcontProfileChanged NOTIFICATION-TYPE
                        OBJECTS { fkGponProfileBaseControlRequest, fkGponProfileBaseControlTimeStamp, fkGponProfileBaseControlReqResult, fkGponProfileBaseControlName, fkGponProfileControlTcontProfileCnt, 
                                fkGponProfileControlTcontProfile }
                        STATUS current
                        DESCRIPTION 
                                "Description."
                        ::= { fkGponProfileBaseNotification 4 }

                
--  1.3.6.1.4.1.10428 9 1.101.23.5.1.3.5
                -- 1.3.6.1.4.1.10428 9 1.101.23.5.1.3.5
                fkGponProfileBaseVoIPProfileChanged NOTIFICATION-TYPE
                        OBJECTS { fkGponProfileBaseControlRequest, fkGponProfileBaseControlTimeStamp, fkGponProfileBaseControlReqResult, fkGponProfileBaseControlName, fkGponProfileControlVoipProfileCnt, 
                                fkGponProfileControlVoipProfile }
                        STATUS current
                        DESCRIPTION 
                                "Description."
                        ::= { fkGponProfileBaseNotification 5 }

                
--  1.3.6.1.4.1.10428 9 1.101.23.5.2
                -- 1.3.6.1.4.1.10428 9 1.101.23.5.2
                fkGponProfilePort OBJECT IDENTIFIER ::= { fkGponProfile 2 }

                
--  1.3.6.1.4.1.10428 9 1.101.23.5.2.1
                -- 1.3.6.1.4.1.10428 9 1.101.23.5.2.1
                fkGponProfilePortTable OBJECT-TYPE
                        SYNTAX SEQUENCE OF FkGponProfilePortEntry
                        MAX-ACCESS not-accessible
                        STATUS current
                        DESCRIPTION
                                "fkGponProfilePortTable"
                        ::= { fkGponProfilePort 1 }

                
--  1.3.6.1.4.1.10428 9 1.101.23.5.2.1.1
                -- 1.3.6.1.4.1.10428 9 1.101.23.5.2.1.1
                fkGponProfilePortEntry OBJECT-TYPE
                        SYNTAX FkGponProfilePortEntry
                        MAX-ACCESS not-accessible
                        STATUS current
                        DESCRIPTION
                                "key: fkGponProfileId, fkGponProfilePortId"
                        INDEX { fkGponProfileId, fkGponProfilePortId }
                        ::= { fkGponProfilePortTable 1 }

                
                FkGponProfilePortEntry ::=
                        SEQUENCE { 
                                fkGponProfilePortId
                                        Integer32,
                                fkGponProfilePortRateLimit
                                        INTEGER,
                                fkGponProfilePortMaxHost
                                        INTEGER,
                                fkGponProfilePortVlan
                                        INTEGER,
                                fkGponProfilePortCosValue
                                        INTEGER,
                                fkGponProfilePortVlanMode
                                        INTEGER,
                                fkGponProfilePortVlanFilter
                                        OCTET STRING,
                                fkGponProfilePortAdmin
                                        INTEGER,
                                fkGponProfilePortDuplex
                                        INTEGER,
                                fkGponProfilePortSpeed
                                        INTEGER,
                                fkGponProfilePortPause
                                        Integer32
                         }

--  1.3.6.1.4.1.10428 9 1.101.23.5.2.1.1.1
                -- 1.3.6.1.4.1.10428 9 1.101.23.5.2.1.1.1
                fkGponProfilePortId OBJECT-TYPE
                        SYNTAX Integer32 (1..65535)
                        MAX-ACCESS read-only
                        STATUS current
                        DESCRIPTION
                                "UNI Port number."
                        ::= { fkGponProfilePortEntry 1 }

                
--  1.3.6.1.4.1.10428 9 1.101.23.5.2.1.1.2
                -- 1.3.6.1.4.1.10428 9 1.101.23.5.2.1.1.2
                fkGponProfilePortRateLimit OBJECT-TYPE
                        SYNTAX INTEGER (1..65535)
                        MAX-ACCESS read-only
                        STATUS current
                        DESCRIPTION
                                "port through which packets are incoming. Bandwidth in steps of 64Kbps."
                        ::= { fkGponProfilePortEntry 2 }

                
--  1.3.6.1.4.1.10428 9 1.101.23.5.2.1.1.3
                -- 1.3.6.1.4.1.10428 9 1.101.23.5.2.1.1.3
                fkGponProfilePortMaxHost OBJECT-TYPE
                        SYNTAX INTEGER (1..65535)
                        MAX-ACCESS read-only
                        STATUS current
                        DESCRIPTION
                                "Maximum Mac learning number."
                        ::= { fkGponProfilePortEntry 3 }

                
--  1.3.6.1.4.1.10428 9 1.101.23.5.2.1.1.4
                -- 1.3.6.1.4.1.10428 9 1.101.23.5.2.1.1.4
                fkGponProfilePortVlan OBJECT-TYPE
                        SYNTAX INTEGER (1..65535)
                        MAX-ACCESS read-only
                        STATUS current
                        DESCRIPTION
                                "Port VLAN tagging operation."
                        ::= { fkGponProfilePortEntry 4 }

                
--  1.3.6.1.4.1.10428 9 1.101.23.5.2.1.1.5
                -- 1.3.6.1.4.1.10428 9 1.101.23.5.2.1.1.5
                fkGponProfilePortCosValue OBJECT-TYPE
                        SYNTAX INTEGER (1..65535)
                        MAX-ACCESS read-only
                        STATUS current
                        DESCRIPTION
                                "COS Value."
                        ::= { fkGponProfilePortEntry 5 }

                
--  1.3.6.1.4.1.10428 9 1.101.23.5.2.1.1.6
                -- 1.3.6.1.4.1.10428 9 1.101.23.5.2.1.1.6
                fkGponProfilePortVlanMode OBJECT-TYPE
                        SYNTAX INTEGER
                                {
                                keep(1),
                                remove(2)
                                }
                        MAX-ACCESS read-only
                        STATUS current
                        DESCRIPTION
                                "Port VLAN tagging operation mode."
                        ::= { fkGponProfilePortEntry 6 }

                
--  1.3.6.1.4.1.10428 9 1.101.23.5.2.1.1.7
                -- 1.3.6.1.4.1.10428 9 1.101.23.5.2.1.1.7
                fkGponProfilePortVlanFilter OBJECT-TYPE
                        SYNTAX OCTET STRING
                        MAX-ACCESS read-only
                        STATUS current
                        DESCRIPTION
                                "VLAN tagging filter configuration."
                        ::= { fkGponProfilePortEntry 7 }

                
--  1.3.6.1.4.1.10428 9 1.101.23.5.2.1.1.8
                -- 1.3.6.1.4.1.10428 9 1.101.23.5.2.1.1.8
                fkGponProfilePortAdmin OBJECT-TYPE
                        SYNTAX INTEGER
                                {
                                enable(1),
                                disable(2)
                                }
                        MAX-ACCESS read-only
                        STATUS current
                        DESCRIPTION
                                "Port Admin status"
                        ::= { fkGponProfilePortEntry 8 }

                
--  1.3.6.1.4.1.10428 9 1.101.23.5.2.1.1.9
                -- 1.3.6.1.4.1.10428 9 1.101.23.5.2.1.1.9
                fkGponProfilePortDuplex OBJECT-TYPE
                        SYNTAX INTEGER
                                {
                                auto(1),
                                full(2),
                                half(3)
                                }
                        MAX-ACCESS read-only
                        STATUS current
                        DESCRIPTION
                                "Port Duplex configuration"
                        ::= { fkGponProfilePortEntry 9 }

                
--  1.3.6.1.4.1.10428 9 1.101.23.5.2.1.1.10
                -- 1.3.6.1.4.1.10428 9 1.101.23.5.2.1.1.10
                fkGponProfilePortSpeed OBJECT-TYPE
                        SYNTAX INTEGER
                                {
                                auto(1),
                                speed10M(2),
                                speed100M(3),
                                speed1000M(4)
                                }
                        MAX-ACCESS read-only
                        STATUS current
                        DESCRIPTION
                                "Port Speed configuration"
                        ::= { fkGponProfilePortEntry 10 }

                
--  1.3.6.1.4.1.10428 9 1.101.23.5.2.1.1.11
                -- 1.3.6.1.4.1.10428 9 1.101.23.5.2.1.1.11
                fkGponProfilePortPause OBJECT-TYPE
                        SYNTAX Integer32
                        MAX-ACCESS read-only
                        STATUS current
                        DESCRIPTION
                                "Port Pause-time configuration"
                        ::= { fkGponProfilePortEntry 11 }

                
--  1.3.6.1.4.1.10428 9 1.101.23.5.2.2
                -- 1.3.6.1.4.1.10428 9 1.101.23.5.2.2
                fkGponProfilePortControl OBJECT IDENTIFIER ::= { fkGponProfilePort 2 }

                
--  1.3.6.1.4.1.10428 9 1.101.23.5.2.2.1
                -- 1.3.6.1.4.1.10428 9 1.101.23.5.2.2.1
                fkGponProfilePortControlRequest OBJECT-TYPE
                        SYNTAX INTEGER
                                {
                                setPortRateLimit(1),
                                setPortMaxHost(2),
                                setPortVlanOper(3),
                                setPortVlanFilter(4),
                                setPortAdmin(5),
                                setPortDuplex(6),
                                setPortSpeed(7),
                                setPortPause(8)
                                }
                        MAX-ACCESS read-write
                        STATUS current
                        DESCRIPTION
                                "The request of a user command"
                        ::= { fkGponProfilePortControl 1 }

                
--  1.3.6.1.4.1.10428 9 1.101.23.5.2.2.2
                -- 1.3.6.1.4.1.10428 9 1.101.23.5.2.2.2
                fkGponProfilePortControlStatus OBJECT-TYPE
                        SYNTAX FkControlStatusType
                        MAX-ACCESS read-only
                        STATUS current
                        DESCRIPTION
                                "The status of user command"
                        ::= { fkGponProfilePortControl 2 }

                
--  1.3.6.1.4.1.10428 9 1.101.23.5.2.2.3
                -- 1.3.6.1.4.1.10428 9 1.101.23.5.2.2.3
                fkGponProfilePortControlTimer OBJECT-TYPE
                        SYNTAX Gauge32
                        MAX-ACCESS read-write
                        STATUS current
                        DESCRIPTION
                                "The maximum time for the manager for a long running user command"
                        ::= { fkGponProfilePortControl 3 }

                
--  1.3.6.1.4.1.10428 9 1.101.23.5.2.2.4
                -- 1.3.6.1.4.1.10428 9 1.101.23.5.2.2.4
                fkGponProfilePortControlTimeStamp OBJECT-TYPE
                        SYNTAX TimeTicks
                        MAX-ACCESS read-only
                        STATUS current
                        DESCRIPTION
                                "The time stamp of the last command(end of command)"
                        ::= { fkGponProfilePortControl 4 }

                
--  1.3.6.1.4.1.10428 9 1.101.23.5.2.2.5
                -- 1.3.6.1.4.1.10428 9 1.101.23.5.2.2.5
                fkGponProfilePortControlReqResult OBJECT-TYPE
                        SYNTAX FkControlRequestResultType
                        MAX-ACCESS read-only
                        STATUS current
                        DESCRIPTION
                                "The result of the last user command"
                        ::= { fkGponProfilePortControl 5 }

                
--  1.3.6.1.4.1.10428 9 1.101.23.5.2.2.6
                -- 1.3.6.1.4.1.10428 9 1.101.23.5.2.2.6
                fkGponProfilePortControlId OBJECT-TYPE
                        SYNTAX INTEGER (1..65535)
                        MAX-ACCESS read-write
                        STATUS current
                        DESCRIPTION
                                "Profile Index"
                        ::= { fkGponProfilePortControl 6 }

                
--  1.3.6.1.4.1.10428 9 1.101.23.5.2.2.7
                -- 1.3.6.1.4.1.10428 9 1.101.23.5.2.2.7
                fkGponProfilePortControlPortId OBJECT-TYPE
                        SYNTAX INTEGER (1..65535)
                        MAX-ACCESS read-write
                        STATUS current
                        DESCRIPTION
                                "UNI Port number"
                        ::= { fkGponProfilePortControl 7 }

                
--  1.3.6.1.4.1.10428 9 1.101.23.5.2.2.8
                -- 1.3.6.1.4.1.10428 9 1.101.23.5.2.2.8
                fkGponProfilePortControlRateLimit OBJECT-TYPE
                        SYNTAX INTEGER (1..65535)
                        MAX-ACCESS read-write
                        STATUS current
                        DESCRIPTION
                                "port through which packets are incoming. Bandwidth in steps of 64Kbps"
                        ::= { fkGponProfilePortControl 8 }

                
--  1.3.6.1.4.1.10428 9 1.101.23.5.2.2.9
                -- 1.3.6.1.4.1.10428 9 1.101.23.5.2.2.9
                fkGponProfilePortControlMaxHost OBJECT-TYPE
                        SYNTAX INTEGER (1..65535)
                        MAX-ACCESS read-write
                        STATUS current
                        DESCRIPTION
                                "Maximum Mac learning number"
                        ::= { fkGponProfilePortControl 9 }

                
--  1.3.6.1.4.1.10428 9 1.101.23.5.2.2.10
                -- 1.3.6.1.4.1.10428 9 1.101.23.5.2.2.10
                fkGponProfilePortControlVlan OBJECT-TYPE
                        SYNTAX INTEGER (1..65535)
                        MAX-ACCESS read-write
                        STATUS current
                        DESCRIPTION
                                "Port VLAN tagging operation"
                        ::= { fkGponProfilePortControl 10 }

                
--  1.3.6.1.4.1.10428 9 1.101.23.5.2.2.11
                -- 1.3.6.1.4.1.10428 9 1.101.23.5.2.2.11
                fkGponProfilePortControlCosValue OBJECT-TYPE
                        SYNTAX INTEGER (1..65535)
                        MAX-ACCESS read-write
                        STATUS current
                        DESCRIPTION
                                "COS Value"
                        ::= { fkGponProfilePortControl 11 }

                
--  1.3.6.1.4.1.10428 9 1.101.23.5.2.2.12
                -- 1.3.6.1.4.1.10428 9 1.101.23.5.2.2.12
                fkGponProfilePortControlVlanMode OBJECT-TYPE
                        SYNTAX INTEGER
                                {
                                keep(1),
                                remove(2)
                                }
                        MAX-ACCESS read-write
                        STATUS current
                        DESCRIPTION
                                "Port VLAN tagging operation mode."
                        ::= { fkGponProfilePortControl 12 }

                
--  1.3.6.1.4.1.10428 9 1.101.23.5.2.2.13
                -- 1.3.6.1.4.1.10428 9 1.101.23.5.2.2.13
                fkGponProfilePortControlVlanFilter OBJECT-TYPE
                        SYNTAX OCTET STRING
                        MAX-ACCESS read-write
                        STATUS current
                        DESCRIPTION
                                "VLAN tagging filter configuration."
                        ::= { fkGponProfilePortControl 13 }

                
--  1.3.6.1.4.1.10428 9 1.101.23.5.2.2.14
                -- 1.3.6.1.4.1.10428 9 1.101.23.5.2.2.14
                fkGponProfilePortControlPortAdmin OBJECT-TYPE
                        SYNTAX INTEGER
                                {
                                enable(1),
                                disable(2)
                                }
                        MAX-ACCESS read-write
                        STATUS current
                        DESCRIPTION
                                "Port Admin status"
                        ::= { fkGponProfilePortControl 14 }

                
--  1.3.6.1.4.1.10428 9 1.101.23.5.2.2.15
                -- 1.3.6.1.4.1.10428 9 1.101.23.5.2.2.15
                fkGponProfilePortControlPortDuplex OBJECT-TYPE
                        SYNTAX INTEGER
                                {
                                auto(1),
                                full(2),
                                half(3)
                                }
                        MAX-ACCESS read-write
                        STATUS current
                        DESCRIPTION
                                "Port Duplex configuration"
                        ::= { fkGponProfilePortControl 15 }

                
--  1.3.6.1.4.1.10428 9 1.101.23.5.2.2.16
                -- 1.3.6.1.4.1.10428 9 1.101.23.5.2.2.16
                fkGponProfilePortControlPortSpeed OBJECT-TYPE
                        SYNTAX INTEGER
                                {
                                auto(1),
                                speed10M(2),
                                speed100M(3),
                                speed1000M(4)
                                }
                        MAX-ACCESS read-write
                        STATUS current
                        DESCRIPTION
                                "Port Speed configuration"
                        ::= { fkGponProfilePortControl 16 }

                
--  1.3.6.1.4.1.10428 9 1.101.23.5.2.2.17
                -- 1.3.6.1.4.1.10428 9 1.101.23.5.2.2.17
                fkGponProfilePortControlPortPause OBJECT-TYPE
                        SYNTAX Integer32
                        MAX-ACCESS read-write
                        STATUS current
                        DESCRIPTION
                                "Port Pause-time configuration"
                        ::= { fkGponProfilePortControl 17 }

                
--  1.3.6.1.4.1.10428 9 1.101.23.5.2.3
                -- 1.3.6.1.4.1.10428 9 1.101.23.5.2.3
                fkGponProfilePortNotification OBJECT IDENTIFIER ::= { fkGponProfilePort 3 }

                
--  1.3.6.1.4.1.10428 9 1.101.23.5.2.3.1
                -- 1.3.6.1.4.1.10428 9 1.101.23.5.2.3.1
                fkGponProfilePortRateLimitChanged NOTIFICATION-TYPE
                        OBJECTS { fkGponProfilePortControlRequest, fkGponProfilePortControlTimeStamp, fkGponProfilePortControlReqResult, fkGponProfilePortControlId, fkGponProfilePortControlPortId, 
                                fkGponProfilePortControlRateLimit }
                        STATUS current
                        DESCRIPTION 
                                "Description."
                        ::= { fkGponProfilePortNotification 1 }

                
--  1.3.6.1.4.1.10428 9 1.101.23.5.2.3.2
                -- 1.3.6.1.4.1.10428 9 1.101.23.5.2.3.2
                fkGponProfilePortMaxHostChanged NOTIFICATION-TYPE
                        OBJECTS { fkGponProfilePortControlRequest, fkGponProfilePortControlTimeStamp, fkGponProfilePortControlReqResult, fkGponProfilePortControlId, fkGponProfilePortControlPortId, 
                                fkGponProfilePortControlMaxHost }
                        STATUS current
                        DESCRIPTION 
                                "Description."
                        ::= { fkGponProfilePortNotification 2 }

                
--  1.3.6.1.4.1.10428 9 1.101.23.5.2.3.3
                -- 1.3.6.1.4.1.10428 9 1.101.23.5.2.3.3
                fkGponProfilePortVlanOperChanged NOTIFICATION-TYPE
                        OBJECTS { fkGponProfilePortControlRequest, fkGponProfilePortControlTimeStamp, fkGponProfilePortControlReqResult, fkGponProfilePortControlId, fkGponProfilePortControlPortId, 
                                fkGponProfilePortControlVlan, fkGponProfilePortControlCosValue, fkGponProfilePortControlVlanMode }
                        STATUS current
                        DESCRIPTION 
                                "Description."
                        ::= { fkGponProfilePortNotification 3 }

                
--  1.3.6.1.4.1.10428 9 1.101.23.5.2.3.4
                -- 1.3.6.1.4.1.10428 9 1.101.23.5.2.3.4
                fkGponProfilePortVlanFilterChanged NOTIFICATION-TYPE
                        OBJECTS { fkGponProfilePortControlRequest, fkGponProfilePortControlTimeStamp, fkGponProfilePortControlReqResult, fkGponProfilePortControlId, fkGponProfilePortControlPortId, 
                                fkGponProfilePortControlVlanFilter }
                        STATUS current
                        DESCRIPTION 
                                "Description."
                        ::= { fkGponProfilePortNotification 4 }

                
--  1.3.6.1.4.1.10428 9 1.101.23.5.2.3.5
                -- 1.3.6.1.4.1.10428 9 1.101.23.5.2.3.5
                fkGponProfilePortAdminChanged NOTIFICATION-TYPE
                        OBJECTS { fkGponProfilePortControlRequest, fkGponProfilePortControlTimeStamp, fkGponProfilePortControlReqResult, fkGponProfilePortControlId, fkGponProfilePortControlPortId, 
                                fkGponProfilePortControlPortAdmin }
                        STATUS current
                        DESCRIPTION 
                                "Description."
                        ::= { fkGponProfilePortNotification 5 }

                
--  1.3.6.1.4.1.10428 9 1.101.23.5.2.3.6
                -- 1.3.6.1.4.1.10428 9 1.101.23.5.2.3.6
                fkGponProfilePortDuplexChanged NOTIFICATION-TYPE
                        OBJECTS { fkGponProfilePortControlRequest, fkGponProfilePortControlTimeStamp, fkGponProfilePortControlReqResult, fkGponProfilePortControlId, fkGponProfilePortControlPortId, 
                                fkGponProfilePortControlPortDuplex }
                        STATUS current
                        DESCRIPTION 
                                "Description."
                        ::= { fkGponProfilePortNotification 6 }

                
--  1.3.6.1.4.1.10428 9 1.101.23.5.2.3.7
                -- 1.3.6.1.4.1.10428 9 1.101.23.5.2.3.7
                fkGponProfilePortSpeedChanged NOTIFICATION-TYPE
                        OBJECTS { fkGponProfilePortControlRequest, fkGponProfilePortControlTimeStamp, fkGponProfilePortControlReqResult, fkGponProfilePortControlId, fkGponProfilePortControlPortId, 
                                fkGponProfilePortControlPortSpeed }
                        STATUS current
                        DESCRIPTION 
                                "Description."
                        ::= { fkGponProfilePortNotification 7 }

                
--  1.3.6.1.4.1.10428 9 1.101.23.5.2.3.8
                -- 1.3.6.1.4.1.10428 9 1.101.23.5.2.3.8
                fkGponProfilePorPauseChanged NOTIFICATION-TYPE
                        OBJECTS { fkGponProfilePortControlRequest, fkGponProfilePortControlTimeStamp, fkGponProfilePortControlReqResult, fkGponProfilePortControlId, fkGponProfilePortControlPortId, 
                                fkGponProfilePortControlPortPause }
                        STATUS current
                        DESCRIPTION 
                                "Description."
                        ::= { fkGponProfilePortNotification 8 }

                
--  1.3.6.1.4.1.10428 9 1.101.23.5.3
                -- 1.3.6.1.4.1.10428 9 1.101.23.5.3
                fkGponProfileDba OBJECT IDENTIFIER ::= { fkGponProfile 3 }

                
--  1.3.6.1.4.1.10428 9 1.101.23.5.3.1
                -- 1.3.6.1.4.1.10428 9 1.101.23.5.3.1
                fkGponProfileDbaTable OBJECT-TYPE
                        SYNTAX SEQUENCE OF FkGponProfileDbaEntry
                        MAX-ACCESS not-accessible
                        STATUS current
                        DESCRIPTION
                                "fkGponProfileDbaTable"
                        ::= { fkGponProfileDba 1 }

                
--  1.3.6.1.4.1.10428 9 1.101.23.5.3.1.1
                -- 1.3.6.1.4.1.10428 9 1.101.23.5.3.1.1
                fkGponProfileDbaEntry OBJECT-TYPE
                        SYNTAX FkGponProfileDbaEntry
                        MAX-ACCESS not-accessible
                        STATUS current
                        DESCRIPTION
                                "key: fkGponProfileDbaId"
                        INDEX { fkGponProfileDbaId }
                        ::= { fkGponProfileDbaTable 1 }

                
                FkGponProfileDbaEntry ::=
                        SEQUENCE { 
                                fkGponProfileDbaId
                                        Integer32,
                                fkGponProfileDbaName
                                        OCTET STRING,
                                fkGponProfileDbaMode
                                        INTEGER,
                                fkGponProfileDbaSlaFixedBw
                                        Integer32,
                                fkGponProfileDbaSlaAssuredBw
                                        Integer32,
                                fkGponProfileDbaSlaMaxBw
                                        Integer32
                         }

--  1.3.6.1.4.1.10428 9 1.101.23.5.3.1.1.1
                -- 1.3.6.1.4.1.10428 9 1.101.23.5.3.1.1.1
                fkGponProfileDbaId OBJECT-TYPE
                        SYNTAX Integer32 (1..65535)
                        MAX-ACCESS read-only
                        STATUS current
                        DESCRIPTION
                                "DBA Profile Id"
                        ::= { fkGponProfileDbaEntry 1 }

                
--  1.3.6.1.4.1.10428 9 1.101.23.5.3.1.1.2
                -- 1.3.6.1.4.1.10428 9 1.101.23.5.3.1.1.2
                fkGponProfileDbaName OBJECT-TYPE
                        SYNTAX OCTET STRING
                        MAX-ACCESS read-only
                        STATUS current
                        DESCRIPTION
                                "DBA Profile Name"
                        ::= { fkGponProfileDbaEntry 2 }

                
--  1.3.6.1.4.1.10428 9 1.101.23.5.3.1.1.3
                -- 1.3.6.1.4.1.10428 9 1.101.23.5.3.1.1.3
                fkGponProfileDbaMode OBJECT-TYPE
                        SYNTAX INTEGER
                                {
                                fixed(1),
                                sr(2),
                                nsr(3),
                                unknown(255)
                                }
                        MAX-ACCESS read-only
                        STATUS current
                        DESCRIPTION
                                "DBA mode"
                        ::= { fkGponProfileDbaEntry 3 }

                
--  1.3.6.1.4.1.10428 9 1.101.23.5.3.1.1.4
                -- 1.3.6.1.4.1.10428 9 1.101.23.5.3.1.1.4
                fkGponProfileDbaSlaFixedBw OBJECT-TYPE
                        SYNTAX Integer32
                        UNITS "64 kbps"
                        MAX-ACCESS read-only
                        STATUS current
                        DESCRIPTION
                                "128-1031616, unit : 64kbps"
                        ::= { fkGponProfileDbaEntry 4 }

                
--  1.3.6.1.4.1.10428 9 1.101.23.5.3.1.1.5
                -- 1.3.6.1.4.1.10428 9 1.101.23.5.3.1.1.5
                fkGponProfileDbaSlaAssuredBw OBJECT-TYPE
                        SYNTAX Integer32
                        UNITS "64 kbps"
                        MAX-ACCESS read-only
                        STATUS current
                        DESCRIPTION
                                "0-1031616, unit : 64kbps"
                        ::= { fkGponProfileDbaEntry 5 }

                
--  1.3.6.1.4.1.10428 9 1.101.23.5.3.1.1.6
                -- 1.3.6.1.4.1.10428 9 1.101.23.5.3.1.1.6
                fkGponProfileDbaSlaMaxBw OBJECT-TYPE
                        SYNTAX Integer32
                        UNITS "64 kbps"
                        MAX-ACCESS read-only
                        STATUS current
                        DESCRIPTION
                                "128-1031616, unit : 64kbps"
                        ::= { fkGponProfileDbaEntry 6 }

                
--  1.3.6.1.4.1.10428 9 1.101.23.5.3.2
                -- 1.3.6.1.4.1.10428 9 1.101.23.5.3.2
                fkGponProfileDbaControl OBJECT IDENTIFIER ::= { fkGponProfileDba 2 }

                
--  1.3.6.1.4.1.10428 9 1.101.23.5.3.2.1
                -- 1.3.6.1.4.1.10428 9 1.101.23.5.3.2.1
                fkGponProfileDbaControlRequest OBJECT-TYPE
                        SYNTAX INTEGER
                                {
                                createProfile(1),
                                destroyProfile(2),
                                updateProfile(3)
                                }
                        MAX-ACCESS read-write
                        STATUS current
                        DESCRIPTION
                                "The request of a user command"
                        ::= { fkGponProfileDbaControl 1 }

                
--  1.3.6.1.4.1.10428 9 1.101.23.5.3.2.2
                -- 1.3.6.1.4.1.10428 9 1.101.23.5.3.2.2
                fkGponProfileDbaControlStatus OBJECT-TYPE
                        SYNTAX FkControlStatusType
                        MAX-ACCESS read-only
                        STATUS current
                        DESCRIPTION
                                "The status of user command"
                        ::= { fkGponProfileDbaControl 2 }

                
--  1.3.6.1.4.1.10428 9 1.101.23.5.3.2.3
                -- 1.3.6.1.4.1.10428 9 1.101.23.5.3.2.3
                fkGponProfileDbaControlTimer OBJECT-TYPE
                        SYNTAX Gauge32
                        MAX-ACCESS read-write
                        STATUS current
                        DESCRIPTION
                                "The maximum time for the manager for a long running user command"
                        ::= { fkGponProfileDbaControl 3 }

                
--  1.3.6.1.4.1.10428 9 1.101.23.5.3.2.4
                -- 1.3.6.1.4.1.10428 9 1.101.23.5.3.2.4
                fkGponProfileDbaControlTimeStamp OBJECT-TYPE
                        SYNTAX TimeTicks
                        MAX-ACCESS read-only
                        STATUS current
                        DESCRIPTION
                                "The time stamp of the last command(end of command)"
                        ::= { fkGponProfileDbaControl 4 }

                
--  1.3.6.1.4.1.10428 9 1.101.23.5.3.2.5
                -- 1.3.6.1.4.1.10428 9 1.101.23.5.3.2.5
                fkGponProfileDbaControlReqResult OBJECT-TYPE
                        SYNTAX FkControlRequestResultType
                        MAX-ACCESS read-only
                        STATUS current
                        DESCRIPTION
                                "The result of the last user command"
                        ::= { fkGponProfileDbaControl 5 }

                
--  1.3.6.1.4.1.10428 9 1.101.23.5.3.2.6
                -- 1.3.6.1.4.1.10428 9 1.101.23.5.3.2.6
                fkGponProfileDbaControlId OBJECT-TYPE
                        SYNTAX INTEGER (1..65535)
                        MAX-ACCESS read-write
                        STATUS current
                        DESCRIPTION
                                "DBA profile Index"
                        ::= { fkGponProfileDbaControl 6 }

                
--  1.3.6.1.4.1.10428 9 1.101.23.5.3.2.7
                -- 1.3.6.1.4.1.10428 9 1.101.23.5.3.2.7
                fkGponProfileDbaControlName OBJECT-TYPE
                        SYNTAX OCTET STRING
                        MAX-ACCESS read-write
                        STATUS current
                        DESCRIPTION
                                "DBA Profile Name"
                        ::= { fkGponProfileDbaControl 7 }

                
--  1.3.6.1.4.1.10428 9 1.101.23.5.3.2.8
                -- 1.3.6.1.4.1.10428 9 1.101.23.5.3.2.8
                fkGponProfileDbaControlMode OBJECT-TYPE
                        SYNTAX INTEGER
                                {
                                fixed(1),
                                sr(2),
                                nsr(3),
                                unknown(255)
                                }
                        MAX-ACCESS read-write
                        STATUS current
                        DESCRIPTION
                                "DBA mode"
                        ::= { fkGponProfileDbaControl 8 }

                
--  1.3.6.1.4.1.10428 9 1.101.23.5.3.2.9
                -- 1.3.6.1.4.1.10428 9 1.101.23.5.3.2.9
                fkGponProfileDbaControlSlaFixedBw OBJECT-TYPE
                        SYNTAX Integer32
                        UNITS "64 kbps"
                        MAX-ACCESS read-write
                        STATUS current
                        DESCRIPTION
                                "128-1031616, unit : 64kbps"
                        ::= { fkGponProfileDbaControl 9 }

                
--  1.3.6.1.4.1.10428 9 1.101.23.5.3.2.10
                -- 1.3.6.1.4.1.10428 9 1.101.23.5.3.2.10
                fkGponProfileDbaControlSlaAssuredBw OBJECT-TYPE
                        SYNTAX Integer32
                        UNITS "64 kbps"
                        MAX-ACCESS read-write
                        STATUS current
                        DESCRIPTION
                                "0-1031616, unit : 64kbps"
                        ::= { fkGponProfileDbaControl 10 }

                
--  1.3.6.1.4.1.10428 9 1.101.23.5.3.2.11
                -- 1.3.6.1.4.1.10428 9 1.101.23.5.3.2.11
                fkGponProfileDbaControlSlaMaxBw OBJECT-TYPE
                        SYNTAX Integer32
                        UNITS "64 kbps"
                        MAX-ACCESS read-write
                        STATUS current
                        DESCRIPTION
                                "128-1031616, unit : 64kbps"
                        ::= { fkGponProfileDbaControl 11 }

                
--  1.3.6.1.4.1.10428 9 1.101.23.5.3.3
                -- 1.3.6.1.4.1.10428 9 1.101.23.5.3.3
                fkGponProfileDbaNotification OBJECT IDENTIFIER ::= { fkGponProfileDba 3 }

                
--  1.3.6.1.4.1.10428 9 1.101.23.5.3.3.1
                -- 1.3.6.1.4.1.10428 9 1.101.23.5.3.3.1
                fkGponProfileDbaCreated NOTIFICATION-TYPE
                        OBJECTS { fkGponProfileDbaControlRequest, fkGponProfileDbaControlTimeStamp, fkGponProfileDbaControlReqResult, fkGponProfileDbaControlName, fkGponProfileDbaControlMode, 
                                fkGponProfileDbaControlSlaFixedBw, fkGponProfileDbaControlSlaAssuredBw, fkGponProfileDbaControlSlaMaxBw }
                        STATUS current
                        DESCRIPTION 
                                "Description."
                        ::= { fkGponProfileDbaNotification 1 }

                
--  1.3.6.1.4.1.10428 9 1.101.23.5.3.3.2
                -- 1.3.6.1.4.1.10428 9 1.101.23.5.3.3.2
                fkGponProfileDbaDestroyed NOTIFICATION-TYPE
                        OBJECTS { fkGponProfileDbaControlRequest, fkGponProfileDbaControlTimeStamp, fkGponProfileDbaControlReqResult, fkGponProfileDbaControlId, fkGponProfileDbaControlName
                                 }
                        STATUS current
                        DESCRIPTION 
                                "Description."
                        ::= { fkGponProfileDbaNotification 2 }

                
--  1.3.6.1.4.1.10428 9 1.101.23.5.3.3.3
                -- 1.3.6.1.4.1.10428 9 1.101.23.5.3.3.3
                fkGponProfileDbaChanged NOTIFICATION-TYPE
                        OBJECTS { fkGponProfileDbaControlRequest, fkGponProfileDbaControlTimeStamp, fkGponProfileDbaControlReqResult, fkGponProfileDbaControlId, fkGponProfileDbaControlMode, 
                                fkGponProfileDbaControlSlaFixedBw, fkGponProfileDbaControlSlaAssuredBw, fkGponProfileDbaControlSlaMaxBw }
                        STATUS current
                        DESCRIPTION 
                                "Description."
                        ::= { fkGponProfileDbaNotification 3 }

                
--  1.3.6.1.4.1.10428 9 1.101.23.5.4
                -- 1.3.6.1.4.1.10428 9 1.101.23.5.4
                fkGponProfileMultiTcont OBJECT IDENTIFIER ::= { fkGponProfile 4 }

                
--  1.3.6.1.4.1.10428 9 1.101.23.5.4.1
                -- 1.3.6.1.4.1.10428 9 1.101.23.5.4.1
                fkGponProfileMultiTcontTable OBJECT-TYPE
                        SYNTAX SEQUENCE OF FkGponProfileMultiTcontEntry
                        MAX-ACCESS not-accessible
                        STATUS current
                        DESCRIPTION
                                "fkGponProfileMultiTcontTable"
                        ::= { fkGponProfileMultiTcont 1 }

                
--  1.3.6.1.4.1.10428 9 1.101.23.5.4.1.1
                -- 1.3.6.1.4.1.10428 9 1.101.23.5.4.1.1
                fkGponProfileMultiTcontEntry OBJECT-TYPE
                        SYNTAX FkGponProfileMultiTcontEntry
                        MAX-ACCESS not-accessible
                        STATUS current
                        DESCRIPTION
                                "key: fkGponProfileMultiTcontIndex"
                        INDEX { fkGponProfileMultiTcontIndex }
                        ::= { fkGponProfileMultiTcontTable 1 }

                
                FkGponProfileMultiTcontEntry ::=
                        SEQUENCE { 
                                fkGponProfileMultiTcontIndex
                                        Integer32,
                                fkGponProfileMultiTcontName
                                        OCTET STRING,
                                fkGponProfileMultiTconTDscp2Pbit
                                        INTEGER,
                                fkGponProfileMultiTconTPriQWeightCnt
                                        INTEGER,
                                fkGponProfileMultiTconTPriQWeight
                                        OCTET STRING,
                                fkGponProfileMultiTcontGemPortType
                                        INTEGER,
                                fkGponProfileMultiTcontGemportUniPortList
                                        BITS,
                                fkGponProfileMultiTcontGemPortVlanCnt
                                        INTEGER,
                                fkGponProfileMultiTcontGemPortVlanList
                                        OCTET STRING,
                                fkGponProfileMultiTcontGemPortCount
                                        Integer32,
                                fkGponProfileMultiTcontGemPortDbaProfileName1
                                        OCTET STRING,
                                fkGponProfileMultiTcontGemPortDbaProfileMask1
                                        BITS,
                                fkGponProfileMultiTcontGemPortDbaProfileName2
                                        OCTET STRING,
                                fkGponProfileMultiTcontGemPortDbaProfileMask2
                                        BITS,
                                fkGponProfileMultiTcontGemPortDbaProfileName3
                                        OCTET STRING,
                                fkGponProfileMultiTcontGemPortDbaProfileMask3
                                        BITS,
                                fkGponProfileMultiTcontGemPortDbaProfileName4
                                        OCTET STRING,
                                fkGponProfileMultiTcontGemPortDbaProfileMask4
                                        BITS,
                                fkGponProfileMultiTcontGemPortDbaProfileName5
                                        OCTET STRING,
                                fkGponProfileMultiTcontGemPortDbaProfileMask5
                                        BITS,
                                fkGponProfileMultiTcontGemPortDbaProfileName6
                                        OCTET STRING,
                                fkGponProfileMultiTcontGemPortDbaProfileMask6
                                        BITS,
                                fkGponProfileMultiTcontGemPortDbaProfileName7
                                        OCTET STRING,
                                fkGponProfileMultiTcontGemPortDbaProfileMask7
                                        BITS,
                                fkGponProfileMultiTcontGemPortDbaProfileName8
                                        OCTET STRING,
                                fkGponProfileMultiTcontGemPortDbaProfileMask8
                                        BITS
                         }

--  1.3.6.1.4.1.10428 9 1.101.23.5.4.1.1.1
                -- 1.3.6.1.4.1.10428 9 1.101.23.5.4.1.1.1
                fkGponProfileMultiTcontIndex OBJECT-TYPE
                        SYNTAX Integer32 (1..65535)
                        MAX-ACCESS read-only
                        STATUS current
                        DESCRIPTION
                                "MultiTconT Profile Id"
                        ::= { fkGponProfileMultiTcontEntry 1 }

                
--  1.3.6.1.4.1.10428 9 1.101.23.5.4.1.1.2
                -- 1.3.6.1.4.1.10428 9 1.101.23.5.4.1.1.2
                fkGponProfileMultiTcontName OBJECT-TYPE
                        SYNTAX OCTET STRING
                        MAX-ACCESS read-only
                        STATUS current
                        DESCRIPTION
                                "MultiTconT Profile Name"
                        ::= { fkGponProfileMultiTcontEntry 2 }

                
--  1.3.6.1.4.1.10428 9 1.101.23.5.4.1.1.3
                -- 1.3.6.1.4.1.10428 9 1.101.23.5.4.1.1.3
                fkGponProfileMultiTconTDscp2Pbit OBJECT-TYPE
                        SYNTAX INTEGER
                                {
                                enable(1),
                                disable(2),
                                unknown(255)
                                }
                        MAX-ACCESS read-only
                        STATUS current
                        DESCRIPTION
                                "Multi-Tcont DSCP2Pbit."
                        ::= { fkGponProfileMultiTcontEntry 3 }

                
--  1.3.6.1.4.1.10428 9 1.101.23.5.4.1.1.4
                -- 1.3.6.1.4.1.10428 9 1.101.23.5.4.1.1.4
                fkGponProfileMultiTconTPriQWeightCnt OBJECT-TYPE
                        SYNTAX INTEGER (1..65535)
                        MAX-ACCESS read-only
                        STATUS current
                        DESCRIPTION
                                "Priority Q & Weight mapping count"
                        ::= { fkGponProfileMultiTcontEntry 4 }

                
--  1.3.6.1.4.1.10428 9 1.101.23.5.4.1.1.5
                -- 1.3.6.1.4.1.10428 9 1.101.23.5.4.1.1.5
                fkGponProfileMultiTconTPriQWeight OBJECT-TYPE
                        SYNTAX OCTET STRING
                        MAX-ACCESS read-only
                        STATUS current
                        DESCRIPTION
                                "Priority Q & Weight MAP
                                2bytes per each Q-ID,   
                                Example)
                                queue-weight 1-2,5 63 / queue-weight 8 22
                                 -->  # 003f 003f 0000 0000 003f 0000 0000 0016"
                        ::= { fkGponProfileMultiTcontEntry 5 }

                
--  1.3.6.1.4.1.10428 9 1.101.23.5.4.1.1.6
                -- 1.3.6.1.4.1.10428 9 1.101.23.5.4.1.1.6
                fkGponProfileMultiTcontGemPortType OBJECT-TYPE
                        SYNTAX INTEGER
                                {
                                eth(1),
                                voip(2),
                                unknown(255)
                                }
                        MAX-ACCESS read-only
                        STATUS current
                        DESCRIPTION
                                "Multi Tcon Gem port type"
                        ::= { fkGponProfileMultiTcontEntry 6 }

                
--  1.3.6.1.4.1.10428 9 1.101.23.5.4.1.1.7
                -- 1.3.6.1.4.1.10428 9 1.101.23.5.4.1.1.7
                fkGponProfileMultiTcontGemportUniPortList OBJECT-TYPE
                        SYNTAX BITS
                                {
                                uni1(0),
                                uni2(1),
                                uni3(2),
                                uni4(3),
                                uni5(4),
                                uni6(5),
                                uni7(6),
                                uni8(7)
                                }
                        MAX-ACCESS read-only
                        STATUS current
                        DESCRIPTION
                                "Multi Tcon Gem port Uni port list"
                        ::= { fkGponProfileMultiTcontEntry 7 }

                
--  1.3.6.1.4.1.10428 9 1.101.23.5.4.1.1.8
                -- 1.3.6.1.4.1.10428 9 1.101.23.5.4.1.1.8
                fkGponProfileMultiTcontGemPortVlanCnt OBJECT-TYPE
                        SYNTAX INTEGER (1..65535)
                        MAX-ACCESS read-only
                        STATUS current
                        DESCRIPTION
                                "VLAN ID counter"
                        ::= { fkGponProfileMultiTcontEntry 8 }

                
--  1.3.6.1.4.1.10428 9 1.101.23.5.4.1.1.9
                -- 1.3.6.1.4.1.10428 9 1.101.23.5.4.1.1.9
                fkGponProfileMultiTcontGemPortVlanList OBJECT-TYPE
                        SYNTAX OCTET STRING
                        MAX-ACCESS read-only
                        STATUS current
                        DESCRIPTION
                                "bitmap, Vlan ID List,  2 bytes per each VLAN.
                                Exampel)
                                gemport eth 1 vid 1-8,10 count 1
                                 -->  # 0001 0002 0003 0004 0005 0006 0007 0008 000a"
                        ::= { fkGponProfileMultiTcontEntry 9 }

                
--  1.3.6.1.4.1.10428 9 1.101.23.5.4.1.1.10
                -- 1.3.6.1.4.1.10428 9 1.101.23.5.4.1.1.10
                fkGponProfileMultiTcontGemPortCount OBJECT-TYPE
                        SYNTAX Integer32
                        MAX-ACCESS read-only
                        STATUS current
                        DESCRIPTION
                                "Gem port count"
                        ::= { fkGponProfileMultiTcontEntry 10 }

                
--  1.3.6.1.4.1.10428 9 1.101.23.5.4.1.1.11
                -- 1.3.6.1.4.1.10428 9 1.101.23.5.4.1.1.11
                fkGponProfileMultiTcontGemPortDbaProfileName1 OBJECT-TYPE
                        SYNTAX OCTET STRING
                        MAX-ACCESS read-only
                        STATUS current
                        DESCRIPTION
                                "Dba Profile name"
                        ::= { fkGponProfileMultiTcontEntry 11 }

                
--  1.3.6.1.4.1.10428 9 1.101.23.5.4.1.1.12
                -- 1.3.6.1.4.1.10428 9 1.101.23.5.4.1.1.12
                fkGponProfileMultiTcontGemPortDbaProfileMask1 OBJECT-TYPE
                        SYNTAX BITS
                                {
                                port1(0),
                                port2(1),
                                port3(2),
                                port4(3),
                                port5(4),
                                port6(5),
                                port7(6),
                                port8(7)
                                }
                        MAX-ACCESS read-only
                        STATUS current
                        DESCRIPTION
                                "Dba Profile Mask (gemport List)"
                        ::= { fkGponProfileMultiTcontEntry 12 }

                
--  1.3.6.1.4.1.10428 9 1.101.23.5.4.1.1.13
                -- 1.3.6.1.4.1.10428 9 1.101.23.5.4.1.1.13
                fkGponProfileMultiTcontGemPortDbaProfileName2 OBJECT-TYPE
                        SYNTAX OCTET STRING
                        MAX-ACCESS read-only
                        STATUS current
                        DESCRIPTION
                                "Multi-Tcont Gemport DBA profile Mask"
                        ::= { fkGponProfileMultiTcontEntry 13 }

                
--  1.3.6.1.4.1.10428 9 1.101.23.5.4.1.1.14
                -- 1.3.6.1.4.1.10428 9 1.101.23.5.4.1.1.14
                fkGponProfileMultiTcontGemPortDbaProfileMask2 OBJECT-TYPE
                        SYNTAX BITS
                                {
                                port1(0),
                                port2(1),
                                port3(2),
                                port4(3),
                                port5(4),
                                port6(5),
                                port7(6),
                                port8(7)
                                }
                        MAX-ACCESS read-only
                        STATUS current
                        DESCRIPTION
                                "Dba Profile Mask (gemport List)"
                        ::= { fkGponProfileMultiTcontEntry 14 }

                
--  1.3.6.1.4.1.10428 9 1.101.23.5.4.1.1.15
                -- 1.3.6.1.4.1.10428 9 1.101.23.5.4.1.1.15
                fkGponProfileMultiTcontGemPortDbaProfileName3 OBJECT-TYPE
                        SYNTAX OCTET STRING
                        MAX-ACCESS read-only
                        STATUS current
                        DESCRIPTION
                                "Dba Profile name"
                        ::= { fkGponProfileMultiTcontEntry 15 }

                
--  1.3.6.1.4.1.10428 9 1.101.23.5.4.1.1.16
                -- 1.3.6.1.4.1.10428 9 1.101.23.5.4.1.1.16
                fkGponProfileMultiTcontGemPortDbaProfileMask3 OBJECT-TYPE
                        SYNTAX BITS
                                {
                                port1(0),
                                port2(1),
                                port3(2),
                                port4(3),
                                port5(4),
                                port6(5),
                                port7(6),
                                port8(7)
                                }
                        MAX-ACCESS read-only
                        STATUS current
                        DESCRIPTION
                                "Dba Profile Mask (gemport List)"
                        ::= { fkGponProfileMultiTcontEntry 16 }

                
--  1.3.6.1.4.1.10428 9 1.101.23.5.4.1.1.17
                -- 1.3.6.1.4.1.10428 9 1.101.23.5.4.1.1.17
                fkGponProfileMultiTcontGemPortDbaProfileName4 OBJECT-TYPE
                        SYNTAX OCTET STRING
                        MAX-ACCESS read-only
                        STATUS current
                        DESCRIPTION
                                "Dba Profile name"
                        ::= { fkGponProfileMultiTcontEntry 17 }

                
--  1.3.6.1.4.1.10428 9 1.101.23.5.4.1.1.18
                -- 1.3.6.1.4.1.10428 9 1.101.23.5.4.1.1.18
                fkGponProfileMultiTcontGemPortDbaProfileMask4 OBJECT-TYPE
                        SYNTAX BITS
                                {
                                port1(0),
                                port2(1),
                                port3(2),
                                port4(3),
                                port5(4),
                                port6(5),
                                port7(6),
                                port8(7)
                                }
                        MAX-ACCESS read-only
                        STATUS current
                        DESCRIPTION
                                "Dba Profile Mask (gemport List)"
                        ::= { fkGponProfileMultiTcontEntry 18 }

                
--  1.3.6.1.4.1.10428 9 1.101.23.5.4.1.1.19
                -- 1.3.6.1.4.1.10428 9 1.101.23.5.4.1.1.19
                fkGponProfileMultiTcontGemPortDbaProfileName5 OBJECT-TYPE
                        SYNTAX OCTET STRING
                        MAX-ACCESS read-only
                        STATUS current
                        DESCRIPTION
                                "Dba Profile name"
                        ::= { fkGponProfileMultiTcontEntry 19 }

                
--  1.3.6.1.4.1.10428 9 1.101.23.5.4.1.1.20
                -- 1.3.6.1.4.1.10428 9 1.101.23.5.4.1.1.20
                fkGponProfileMultiTcontGemPortDbaProfileMask5 OBJECT-TYPE
                        SYNTAX BITS
                                {
                                port1(0),
                                port2(1),
                                port3(2),
                                port4(3),
                                port5(4),
                                port6(5),
                                port7(6),
                                port8(7)
                                }
                        MAX-ACCESS read-only
                        STATUS current
                        DESCRIPTION
                                "Dba Profile Mask (gemport List)"
                        ::= { fkGponProfileMultiTcontEntry 20 }

                
--  1.3.6.1.4.1.10428 9 1.101.23.5.4.1.1.21
                -- 1.3.6.1.4.1.10428 9 1.101.23.5.4.1.1.21
                fkGponProfileMultiTcontGemPortDbaProfileName6 OBJECT-TYPE
                        SYNTAX OCTET STRING
                        MAX-ACCESS read-only
                        STATUS current
                        DESCRIPTION
                                "Dba Profile name"
                        ::= { fkGponProfileMultiTcontEntry 21 }

                
--  1.3.6.1.4.1.10428 9 1.101.23.5.4.1.1.22
                -- 1.3.6.1.4.1.10428 9 1.101.23.5.4.1.1.22
                fkGponProfileMultiTcontGemPortDbaProfileMask6 OBJECT-TYPE
                        SYNTAX BITS
                                {
                                port1(0),
                                port2(1),
                                port3(2),
                                port4(3),
                                port5(4),
                                port6(5),
                                port7(6),
                                port8(7)
                                }
                        MAX-ACCESS read-only
                        STATUS current
                        DESCRIPTION
                                "Dba Profile Mask (gemport List)"
                        ::= { fkGponProfileMultiTcontEntry 22 }

                
--  1.3.6.1.4.1.10428 9 1.101.23.5.4.1.1.23
                -- 1.3.6.1.4.1.10428 9 1.101.23.5.4.1.1.23
                fkGponProfileMultiTcontGemPortDbaProfileName7 OBJECT-TYPE
                        SYNTAX OCTET STRING
                        MAX-ACCESS read-only
                        STATUS current
                        DESCRIPTION
                                "Dba Profile name"
                        ::= { fkGponProfileMultiTcontEntry 23 }

                
--  1.3.6.1.4.1.10428 9 1.101.23.5.4.1.1.24
                -- 1.3.6.1.4.1.10428 9 1.101.23.5.4.1.1.24
                fkGponProfileMultiTcontGemPortDbaProfileMask7 OBJECT-TYPE
                        SYNTAX BITS
                                {
                                port1(0),
                                port2(1),
                                port3(2),
                                port4(3),
                                port5(4),
                                port6(5),
                                port7(6),
                                port8(7)
                                }
                        MAX-ACCESS read-only
                        STATUS current
                        DESCRIPTION
                                "Dba Profile Mask (gemport List)"
                        ::= { fkGponProfileMultiTcontEntry 24 }

                
--  1.3.6.1.4.1.10428 9 1.101.23.5.4.1.1.25
                -- 1.3.6.1.4.1.10428 9 1.101.23.5.4.1.1.25
                fkGponProfileMultiTcontGemPortDbaProfileName8 OBJECT-TYPE
                        SYNTAX OCTET STRING
                        MAX-ACCESS read-only
                        STATUS current
                        DESCRIPTION
                                "Dba Profile name"
                        ::= { fkGponProfileMultiTcontEntry 25 }

                
--  1.3.6.1.4.1.10428 9 1.101.23.5.4.1.1.26
                -- 1.3.6.1.4.1.10428 9 1.101.23.5.4.1.1.26
                fkGponProfileMultiTcontGemPortDbaProfileMask8 OBJECT-TYPE
                        SYNTAX BITS
                                {
                                port1(0),
                                port2(1),
                                port3(2),
                                port4(3),
                                port5(4),
                                port6(5),
                                port7(6),
                                port8(7)
                                }
                        MAX-ACCESS read-only
                        STATUS current
                        DESCRIPTION
                                "Dba Profile Mask (gemport List)"
                        ::= { fkGponProfileMultiTcontEntry 26 }

                
--  1.3.6.1.4.1.10428 9 1.101.23.5.4.2
                -- 1.3.6.1.4.1.10428 9 1.101.23.5.4.2
                fkGponProfileMultiTcontControl OBJECT IDENTIFIER ::= { fkGponProfileMultiTcont 2 }

                
--  1.3.6.1.4.1.10428 9 1.101.23.5.4.2.1
                -- 1.3.6.1.4.1.10428 9 1.101.23.5.4.2.1
                fkGponProfileMultiTcontControllRequest OBJECT-TYPE
                        SYNTAX INTEGER
                                {
                                createProfile(1),
                                destroyProfile(2),
                                updateDscp2Pbit(3),
                                updatePriQWeight(4),
                                updateGemport(5)
                                }
                        MAX-ACCESS read-write
                        STATUS current
                        DESCRIPTION
                                "The request of a user command"
                        ::= { fkGponProfileMultiTcontControl 1 }

                
--  1.3.6.1.4.1.10428 9 1.101.23.5.4.2.2
                -- 1.3.6.1.4.1.10428 9 1.101.23.5.4.2.2
                fkGponProfileMultiTcontControlStatus OBJECT-TYPE
                        SYNTAX FkControlStatusType
                        MAX-ACCESS read-only
                        STATUS current
                        DESCRIPTION
                                "The status of user command"
                        ::= { fkGponProfileMultiTcontControl 2 }

                
--  1.3.6.1.4.1.10428 9 1.101.23.5.4.2.3
                -- 1.3.6.1.4.1.10428 9 1.101.23.5.4.2.3
                fkGponProfileMultiTcontControlTimer OBJECT-TYPE
                        SYNTAX Gauge32
                        MAX-ACCESS read-write
                        STATUS current
                        DESCRIPTION
                                "The maximum time for the manager for a long running user command"
                        ::= { fkGponProfileMultiTcontControl 3 }

                
--  1.3.6.1.4.1.10428 9 1.101.23.5.4.2.4
                -- 1.3.6.1.4.1.10428 9 1.101.23.5.4.2.4
                fkGponProfileMultiTcontControlTimeStamp OBJECT-TYPE
                        SYNTAX TimeTicks
                        MAX-ACCESS read-only
                        STATUS current
                        DESCRIPTION
                                "The time stamp of the last command(end of command)"
                        ::= { fkGponProfileMultiTcontControl 4 }

                
--  1.3.6.1.4.1.10428 9 1.101.23.5.4.2.5
                -- 1.3.6.1.4.1.10428 9 1.101.23.5.4.2.5
                fkGponProfileMultiTcontControlReqResult OBJECT-TYPE
                        SYNTAX FkControlRequestResultType
                        MAX-ACCESS read-only
                        STATUS current
                        DESCRIPTION
                                "The result of the last user command"
                        ::= { fkGponProfileMultiTcontControl 5 }

                
--  1.3.6.1.4.1.10428 9 1.101.23.5.4.2.6
                -- 1.3.6.1.4.1.10428 9 1.101.23.5.4.2.6
                fkGponProfileMultiTcontControlIndex OBJECT-TYPE
                        SYNTAX INTEGER (1..65535)
                        MAX-ACCESS read-write
                        STATUS current
                        DESCRIPTION
                                "Multi Tcont profile Index"
                        ::= { fkGponProfileMultiTcontControl 6 }

                
--  1.3.6.1.4.1.10428 9 1.101.23.5.4.2.7
                -- 1.3.6.1.4.1.10428 9 1.101.23.5.4.2.7
                fkGponProfileMultiTcontControlName OBJECT-TYPE
                        SYNTAX OCTET STRING
                        MAX-ACCESS read-write
                        STATUS current
                        DESCRIPTION
                                "Profile Name"
                        ::= { fkGponProfileMultiTcontControl 7 }

                
--  1.3.6.1.4.1.10428 9 1.101.23.5.4.2.8
                -- 1.3.6.1.4.1.10428 9 1.101.23.5.4.2.8
                fkGponProfileMultiTcontControlDscp2Pbit OBJECT-TYPE
                        SYNTAX INTEGER
                                {
                                enable(1),
                                disable(2),
                                unknown(255)
                                }
                        MAX-ACCESS read-write
                        STATUS current
                        DESCRIPTION
                                "DSCP to P bit marking"
                        ::= { fkGponProfileMultiTcontControl 8 }

                
--  1.3.6.1.4.1.10428 9 1.101.23.5.4.2.9
                -- 1.3.6.1.4.1.10428 9 1.101.23.5.4.2.9
                fkGponProfileMultiTcontControlPriQWeightCnt OBJECT-TYPE
                        SYNTAX Integer32
                        MAX-ACCESS read-write
                        STATUS current
                        DESCRIPTION
                                "TconT PrioQ mapping count"
                        ::= { fkGponProfileMultiTcontControl 9 }

                
--  1.3.6.1.4.1.10428 9 1.101.23.5.4.2.10
                -- 1.3.6.1.4.1.10428 9 1.101.23.5.4.2.10
                fkGponProfileMultiTcontControlPriQWeight OBJECT-TYPE
                        SYNTAX OCTET STRING
                        MAX-ACCESS read-write
                        STATUS current
                        DESCRIPTION
                                "Tcont PriQ weight MAP."
                        ::= { fkGponProfileMultiTcontControl 10 }

                
--  1.3.6.1.4.1.10428 9 1.101.23.5.4.2.11
                -- 1.3.6.1.4.1.10428 9 1.101.23.5.4.2.11
                fkGponProfileMultiTcontControlGemPortType OBJECT-TYPE
                        SYNTAX INTEGER
                                {
                                eth(1),
                                voip(2),
                                unknown(255)
                                }
                        MAX-ACCESS read-write
                        STATUS current
                        DESCRIPTION
                                "Multi Tcon Gem port type"
                        ::= { fkGponProfileMultiTcontControl 11 }

                
--  1.3.6.1.4.1.10428 9 1.101.23.5.4.2.12
                -- 1.3.6.1.4.1.10428 9 1.101.23.5.4.2.12
                fkGponProfileMultiTcontControlGemportUniPortList OBJECT-TYPE
                        SYNTAX BITS
                                {
                                uni1(0),
                                uni2(1),
                                uni3(2),
                                uni4(3),
                                uni5(4),
                                uni6(5),
                                uni7(6),
                                uni8(7)
                                }
                        MAX-ACCESS read-write
                        STATUS current
                        DESCRIPTION
                                "Multi Tcon Gem port Uni port list"
                        ::= { fkGponProfileMultiTcontControl 12 }

                
--  1.3.6.1.4.1.10428 9 1.101.23.5.4.2.13
                -- 1.3.6.1.4.1.10428 9 1.101.23.5.4.2.13
                fkGponProfileMultiTcontControlGemPortVlanCnt OBJECT-TYPE
                        SYNTAX Integer32
                        MAX-ACCESS read-write
                        STATUS current
                        DESCRIPTION
                                "VLAN list mappling  count"
                        ::= { fkGponProfileMultiTcontControl 13 }

                
--  1.3.6.1.4.1.10428 9 1.101.23.5.4.2.14
                -- 1.3.6.1.4.1.10428 9 1.101.23.5.4.2.14
                fkGponProfileMultiTcontControlGemPortVlanList OBJECT-TYPE
                        SYNTAX OCTET STRING
                        MAX-ACCESS read-write
                        STATUS current
                        DESCRIPTION
                                "VLAN MAP."
                        ::= { fkGponProfileMultiTcontControl 14 }

                
--  1.3.6.1.4.1.10428 9 1.101.23.5.4.2.15
                -- 1.3.6.1.4.1.10428 9 1.101.23.5.4.2.15
                fkGponProfileMultiTcontControlGemPortCount OBJECT-TYPE
                        SYNTAX Integer32
                        MAX-ACCESS read-write
                        STATUS current
                        DESCRIPTION
                                "Gemport count"
                        ::= { fkGponProfileMultiTcontControl 15 }

                
--  1.3.6.1.4.1.10428 9 1.101.23.5.4.2.16
                -- 1.3.6.1.4.1.10428 9 1.101.23.5.4.2.16
                fkGponProfileMultiTcontControlGemPortDbaProfileName1 OBJECT-TYPE
                        SYNTAX OCTET STRING
                        MAX-ACCESS read-write
                        STATUS current
                        DESCRIPTION
                                "Dba Profile name"
                        ::= { fkGponProfileMultiTcontControl 16 }

                
--  1.3.6.1.4.1.10428 9 1.101.23.5.4.2.17
                -- 1.3.6.1.4.1.10428 9 1.101.23.5.4.2.17
                fkGponProfileMultiTcontControlGemPortDbaProfileMask1 OBJECT-TYPE
                        SYNTAX BITS
                                {
                                port1(0),
                                port2(1),
                                port3(2),
                                port4(3),
                                port5(4),
                                port6(5),
                                port7(6),
                                port8(7)
                                }
                        MAX-ACCESS read-write
                        STATUS current
                        DESCRIPTION
                                "Dba Profile Mask (gemport List)"
                        ::= { fkGponProfileMultiTcontControl 17 }

                
--  1.3.6.1.4.1.10428 9 1.101.23.5.4.2.18
                -- 1.3.6.1.4.1.10428 9 1.101.23.5.4.2.18
                fkGponProfileMultiTcontControlGemPortDbaProfileName2 OBJECT-TYPE
                        SYNTAX OCTET STRING
                        MAX-ACCESS read-write
                        STATUS current
                        DESCRIPTION
                                "Dba Profile name"
                        ::= { fkGponProfileMultiTcontControl 18 }

                
--  1.3.6.1.4.1.10428 9 1.101.23.5.4.2.19
                -- 1.3.6.1.4.1.10428 9 1.101.23.5.4.2.19
                fkGponProfileMultiTcontControlGemPortDbaProfileMask2 OBJECT-TYPE
                        SYNTAX BITS
                                {
                                port1(0),
                                port2(1),
                                port3(2),
                                port4(3),
                                port5(4),
                                port6(5),
                                port7(6),
                                port8(7)
                                }
                        MAX-ACCESS read-write
                        STATUS current
                        DESCRIPTION
                                "Dba Profile Mask (gemport List)"
                        ::= { fkGponProfileMultiTcontControl 19 }

                
--  1.3.6.1.4.1.10428 9 1.101.23.5.4.2.20
                -- 1.3.6.1.4.1.10428 9 1.101.23.5.4.2.20
                fkGponProfileMultiTcontControlGemPortDbaProfileName3 OBJECT-TYPE
                        SYNTAX OCTET STRING
                        MAX-ACCESS read-write
                        STATUS current
                        DESCRIPTION
                                "Dba Profile name"
                        ::= { fkGponProfileMultiTcontControl 20 }

                
--  1.3.6.1.4.1.10428 9 1.101.23.5.4.2.21
                -- 1.3.6.1.4.1.10428 9 1.101.23.5.4.2.21
                fkGponProfileMultiTcontControlGemPortDbaProfileMask3 OBJECT-TYPE
                        SYNTAX BITS
                                {
                                port1(0),
                                port2(1),
                                port3(2),
                                port4(3),
                                port5(4),
                                port6(5),
                                port7(6),
                                port8(7)
                                }
                        MAX-ACCESS read-write
                        STATUS current
                        DESCRIPTION
                                "Dba Profile Mask (gemport List)"
                        ::= { fkGponProfileMultiTcontControl 21 }

                
--  1.3.6.1.4.1.10428 9 1.101.23.5.4.2.22
                -- 1.3.6.1.4.1.10428 9 1.101.23.5.4.2.22
                fkGponProfileMultiTcontControlGemPortDbaProfileName4 OBJECT-TYPE
                        SYNTAX OCTET STRING
                        MAX-ACCESS read-write
                        STATUS current
                        DESCRIPTION
                                "Dba Profile name"
                        ::= { fkGponProfileMultiTcontControl 22 }

                
--  1.3.6.1.4.1.10428 9 1.101.23.5.4.2.23
                -- 1.3.6.1.4.1.10428 9 1.101.23.5.4.2.23
                fkGponProfileMultiTcontControlGemPortDbaProfileMask4 OBJECT-TYPE
                        SYNTAX BITS
                                {
                                port1(0),
                                port2(1),
                                port3(2),
                                port4(3),
                                port5(4),
                                port6(5),
                                port7(6),
                                port8(7)
                                }
                        MAX-ACCESS read-write
                        STATUS current
                        DESCRIPTION
                                "Dba Profile Mask (gemport List)"
                        ::= { fkGponProfileMultiTcontControl 23 }

                
--  1.3.6.1.4.1.10428 9 1.101.23.5.4.2.24
                -- 1.3.6.1.4.1.10428 9 1.101.23.5.4.2.24
                fkGponProfileMultiTcontControlGemPortDbaProfileName5 OBJECT-TYPE
                        SYNTAX OCTET STRING
                        MAX-ACCESS read-write
                        STATUS current
                        DESCRIPTION
                                "Dba Profile name"
                        ::= { fkGponProfileMultiTcontControl 24 }

                
--  1.3.6.1.4.1.10428 9 1.101.23.5.4.2.25
                -- 1.3.6.1.4.1.10428 9 1.101.23.5.4.2.25
                fkGponProfileMultiTcontControlGemPortDbaProfileMask5 OBJECT-TYPE
                        SYNTAX BITS
                                {
                                port1(0),
                                port2(1),
                                port3(2),
                                port4(3),
                                port5(4),
                                port6(5),
                                port7(6),
                                port8(7)
                                }
                        MAX-ACCESS read-write
                        STATUS current
                        DESCRIPTION
                                "Dba Profile Mask (gemport List)"
                        ::= { fkGponProfileMultiTcontControl 25 }

                
--  1.3.6.1.4.1.10428 9 1.101.23.5.4.2.26
                -- 1.3.6.1.4.1.10428 9 1.101.23.5.4.2.26
                fkGponProfileMultiTcontControlGemPortDbaProfileName6 OBJECT-TYPE
                        SYNTAX OCTET STRING
                        MAX-ACCESS read-write
                        STATUS current
                        DESCRIPTION
                                "Dba Profile name"
                        ::= { fkGponProfileMultiTcontControl 26 }

                
--  1.3.6.1.4.1.10428 9 1.101.23.5.4.2.27
                -- 1.3.6.1.4.1.10428 9 1.101.23.5.4.2.27
                fkGponProfileMultiTcontControlGemPortDbaProfileMask6 OBJECT-TYPE
                        SYNTAX BITS
                                {
                                port1(0),
                                port2(1),
                                port3(2),
                                port4(3),
                                port5(4),
                                port6(5),
                                port7(6),
                                port8(7)
                                }
                        MAX-ACCESS read-write
                        STATUS current
                        DESCRIPTION
                                "Dba Profile Mask (gemport List)"
                        ::= { fkGponProfileMultiTcontControl 27 }

                
--  1.3.6.1.4.1.10428 9 1.101.23.5.4.2.28
                -- 1.3.6.1.4.1.10428 9 1.101.23.5.4.2.28
                fkGponProfileMultiTcontControlGemPortDbaProfileName7 OBJECT-TYPE
                        SYNTAX OCTET STRING
                        MAX-ACCESS read-write
                        STATUS current
                        DESCRIPTION
                                "Dba Profile name"
                        ::= { fkGponProfileMultiTcontControl 28 }

                
--  1.3.6.1.4.1.10428 9 1.101.23.5.4.2.29
                -- 1.3.6.1.4.1.10428 9 1.101.23.5.4.2.29
                fkGponProfileMultiTcontControlGemPortDbaProfileMask7 OBJECT-TYPE
                        SYNTAX BITS
                                {
                                port1(0),
                                port2(1),
                                port3(2),
                                port4(3),
                                port5(4),
                                port6(5),
                                port7(6),
                                port8(7)
                                }
                        MAX-ACCESS read-write
                        STATUS current
                        DESCRIPTION
                                "Dba Profile Mask (gemport List)"
                        ::= { fkGponProfileMultiTcontControl 29 }

                
--  1.3.6.1.4.1.10428 9 1.101.23.5.4.2.30
                -- 1.3.6.1.4.1.10428 9 1.101.23.5.4.2.30
                fkGponProfileMultiTcontControlGemPortDbaProfileName8 OBJECT-TYPE
                        SYNTAX OCTET STRING
                        MAX-ACCESS read-write
                        STATUS current
                        DESCRIPTION
                                "Dba Profile name"
                        ::= { fkGponProfileMultiTcontControl 30 }

                
--  1.3.6.1.4.1.10428 9 1.101.23.5.4.2.31
                -- 1.3.6.1.4.1.10428 9 1.101.23.5.4.2.31
                fkGponProfileMultiTcontControlGemPortDbaProfileMask8 OBJECT-TYPE
                        SYNTAX BITS
                                {
                                port1(0),
                                port2(1),
                                port3(2),
                                port4(3),
                                port5(4),
                                port6(5),
                                port7(6),
                                port8(7)
                                }
                        MAX-ACCESS read-write
                        STATUS current
                        DESCRIPTION
                                "Dba Profile Mask (gemport List)"
                        ::= { fkGponProfileMultiTcontControl 31 }

                
--  1.3.6.1.4.1.10428 9 1.101.23.5.4.3
                -- 1.3.6.1.4.1.10428 9 1.101.23.5.4.3
                fkGponProfileMultiTcontNotification OBJECT IDENTIFIER ::= { fkGponProfileMultiTcont 3 }

                
--  1.3.6.1.4.1.10428 9 1.101.23.5.4.3.1
                -- 1.3.6.1.4.1.10428 9 1.101.23.5.4.3.1
                fkGponProfileMultiTcontProfileCreated NOTIFICATION-TYPE
                        OBJECTS { fkGponProfileMultiTcontControllRequest, fkGponProfileMultiTcontControlTimeStamp, fkGponProfileMultiTcontControlReqResult, fkGponProfileMultiTcontControlName, fkGponProfileMultiTcontControlDscp2Pbit, 
                                fkGponProfileMultiTcontControlPriQWeightCnt, fkGponProfileMultiTcontControlPriQWeight, fkGponProfileMultiTcontControlGemPortType, fkGponProfileMultiTcontControlGemportUniPortList, fkGponProfileMultiTcontControlGemPortVlanCnt, 
                                fkGponProfileMultiTcontControlGemPortVlanList, fkGponProfileMultiTcontControlGemPortCount, fkGponProfileMultiTcontControlGemPortDbaProfileName1, fkGponProfileMultiTcontControlGemPortDbaProfileMask1, fkGponProfileMultiTcontControlGemPortDbaProfileName2, 
                                fkGponProfileMultiTcontControlGemPortDbaProfileMask2, fkGponProfileMultiTcontControlGemPortDbaProfileName3, fkGponProfileMultiTcontControlGemPortDbaProfileMask3, fkGponProfileMultiTcontControlGemPortDbaProfileName4, fkGponProfileMultiTcontControlGemPortDbaProfileMask4, 
                                fkGponProfileMultiTcontControlGemPortDbaProfileName5, fkGponProfileMultiTcontControlGemPortDbaProfileMask5, fkGponProfileMultiTcontControlGemPortDbaProfileName6, fkGponProfileMultiTcontControlGemPortDbaProfileMask6, fkGponProfileMultiTcontControlGemPortDbaProfileName7, 
                                fkGponProfileMultiTcontControlGemPortDbaProfileMask7, fkGponProfileMultiTcontControlGemPortDbaProfileName8, fkGponProfileMultiTcontControlGemPortDbaProfileMask8 }
                        STATUS current
                        DESCRIPTION 
                                "Description."
                        ::= { fkGponProfileMultiTcontNotification 1 }

                
--  1.3.6.1.4.1.10428 9 1.101.23.5.4.3.2
                -- 1.3.6.1.4.1.10428 9 1.101.23.5.4.3.2
                fkGponProfileMultiTcontProfileDestroyed NOTIFICATION-TYPE
                        OBJECTS { fkGponProfileMultiTcontControllRequest, fkGponProfileMultiTcontControlTimeStamp, fkGponProfileMultiTcontControlReqResult, fkGponProfileMultiTcontControlIndex }
                        STATUS current
                        DESCRIPTION 
                                "Description."
                        ::= { fkGponProfileMultiTcontNotification 2 }

                
--  1.3.6.1.4.1.10428 9 1.101.23.5.4.3.3
                -- 1.3.6.1.4.1.10428 9 1.101.23.5.4.3.3
                fkGponProfileMultiTcontProfileDscp2PbitChanged NOTIFICATION-TYPE
                        OBJECTS { fkGponProfileMultiTcontControllRequest, fkGponProfileMultiTcontControlTimeStamp, fkGponProfileMultiTcontControlReqResult, fkGponProfileMultiTcontControlIndex, fkGponProfileMultiTcontControlDscp2Pbit
                                 }
                        STATUS current
                        DESCRIPTION 
                                "Description."
                        ::= { fkGponProfileMultiTcontNotification 3 }

                
--  1.3.6.1.4.1.10428 9 1.101.23.5.4.3.4
                -- 1.3.6.1.4.1.10428 9 1.101.23.5.4.3.4
                fkGponProfileMultiTcontProfilePriQWeightChanged NOTIFICATION-TYPE
                        OBJECTS { fkGponProfileMultiTcontControllRequest, fkGponProfileMultiTcontControlTimeStamp, fkGponProfileMultiTcontControlReqResult, fkGponProfileMultiTcontControlIndex, fkGponProfileMultiTcontControlPriQWeightCnt, 
                                fkGponProfileMultiTcontControlPriQWeight }
                        STATUS current
                        DESCRIPTION 
                                "Description."
                        ::= { fkGponProfileMultiTcontNotification 4 }

                
--  1.3.6.1.4.1.10428 9 1.101.23.5.4.3.5
                -- 1.3.6.1.4.1.10428 9 1.101.23.5.4.3.5
                fkGponProfileMultiTcontProfileGemportChanged NOTIFICATION-TYPE
                        OBJECTS { fkGponProfileMultiTcontControllRequest, fkGponProfileMultiTcontControlTimeStamp, fkGponProfileMultiTcontControlReqResult, fkGponProfileMultiTcontControlIndex, fkGponProfileMultiTcontControlGemPortType, 
                                fkGponProfileMultiTcontControlGemportUniPortList, fkGponProfileMultiTcontControlGemPortVlanCnt, fkGponProfileMultiTcontControlGemPortVlanList, fkGponProfileMultiTcontControlGemPortCount, fkGponProfileMultiTcontControlGemPortDbaProfileName1, 
                                fkGponProfileMultiTcontControlGemPortDbaProfileMask1, fkGponProfileMultiTcontControlGemPortDbaProfileName2, fkGponProfileMultiTcontControlGemPortDbaProfileMask2, fkGponProfileMultiTcontControlGemPortDbaProfileName3, fkGponProfileMultiTcontControlGemPortDbaProfileMask3, 
                                fkGponProfileMultiTcontControlGemPortDbaProfileName4, fkGponProfileMultiTcontControlGemPortDbaProfileMask4, fkGponProfileMultiTcontControlGemPortDbaProfileName5, fkGponProfileMultiTcontControlGemPortDbaProfileMask5, fkGponProfileMultiTcontControlGemPortDbaProfileName6, 
                                fkGponProfileMultiTcontControlGemPortDbaProfileMask6, fkGponProfileMultiTcontControlGemPortDbaProfileName7, fkGponProfileMultiTcontControlGemPortDbaProfileMask7, fkGponProfileMultiTcontControlGemPortDbaProfileName8, fkGponProfileMultiTcontControlGemPortDbaProfileMask8
                                 }
                        STATUS current
                        DESCRIPTION 
                                "Description."
                        ::= { fkGponProfileMultiTcontNotification 5 }

                
--  1.3.6.1.4.1.10428 9 1.101.23.5.5
                -- 1.3.6.1.4.1.10428 9 1.101.23.5.5
                fkGponVoIP OBJECT IDENTIFIER ::= { fkGponProfile 5 }

                
--  1.3.6.1.4.1.10428 9 1.101.23.5.5.1
                -- 1.3.6.1.4.1.10428 9 1.101.23.5.5.1
                fkGponProfileVoIP OBJECT IDENTIFIER ::= { fkGponVoIP 1 }

                
--  1.3.6.1.4.1.10428 9 1.101.23.5.5.1.1
                -- 1.3.6.1.4.1.10428 9 1.101.23.5.5.1.1
                fkGponProfileVoIPTable OBJECT-TYPE
                        SYNTAX SEQUENCE OF FkGponProfileVoIPEntry
                        MAX-ACCESS not-accessible
                        STATUS current
                        DESCRIPTION
                                "fkGponProfileVoIPTable"
                        ::= { fkGponProfileVoIP 1 }

                
--  1.3.6.1.4.1.10428 9 1.101.23.5.5.1.1.1
                -- 1.3.6.1.4.1.10428 9 1.101.23.5.5.1.1.1
                fkGponProfileVoIPEntry OBJECT-TYPE
                        SYNTAX FkGponProfileVoIPEntry
                        MAX-ACCESS not-accessible
                        STATUS current
                        DESCRIPTION
                                "fkGponProfileVoIPIndex"
                        INDEX { fkGponProfileVoIPIndex }
                        ::= { fkGponProfileVoIPTable 1 }

                
                FkGponProfileVoIPEntry ::=
                        SEQUENCE { 
                                fkGponProfileVoIPIndex
                                        Integer32,
                                fkGponProfileVoIPName
                                        OCTET STRING,
                                fkGponProfileVoIPServiceMode
                                        INTEGER,
                                fkGponProfileVoIPServiceProtocol
                                        INTEGER,
                                fkGponProfileVoIPOmciAgentURL
                                        OCTET STRING,
                                fkGponProfileVoIPOmciAgentProxy
                                        OCTET STRING,
                                fkGponProfileVoIPOmciAgentDns1
                                        IpAddress,
                                fkGponProfileVoIPOmciAgentDns2
                                        IpAddress,
                                fkGponProfileVoIPIpwayAuthName
                                        OCTET STRING,
                                fkGponProfileVoIPIpwayAuthPasswd
                                        OCTET STRING,
                                fkGponProfileVoIPIpwayURL
                                        OCTET STRING
                         }

--  1.3.6.1.4.1.10428 9 1.101.23.5.5.1.1.1.1
                -- 1.3.6.1.4.1.10428 9 1.101.23.5.5.1.1.1.1
                fkGponProfileVoIPIndex OBJECT-TYPE
                        SYNTAX Integer32 (1..65535)
                        MAX-ACCESS read-only
                        STATUS current
                        DESCRIPTION
                                "VoIP Profile Index."
                        ::= { fkGponProfileVoIPEntry 1 }

                
--  1.3.6.1.4.1.10428 9 1.101.23.5.5.1.1.1.2
                -- 1.3.6.1.4.1.10428 9 1.101.23.5.5.1.1.1.2
                fkGponProfileVoIPName OBJECT-TYPE
                        SYNTAX OCTET STRING
                        MAX-ACCESS read-only
                        STATUS current
                        DESCRIPTION
                                "VoIP profile name."
                        ::= { fkGponProfileVoIPEntry 2 }

                
--  1.3.6.1.4.1.10428 9 1.101.23.5.5.1.1.1.3
                -- 1.3.6.1.4.1.10428 9 1.101.23.5.5.1.1.1.3
                fkGponProfileVoIPServiceMode OBJECT-TYPE
                        SYNTAX INTEGER
                                {
                                ipPath(1),
                                omci(2),
                                unknown(3)
                                }
                        MAX-ACCESS read-only
                        STATUS current
                        DESCRIPTION
                                "VoIP service mode."
                        ::= { fkGponProfileVoIPEntry 3 }

                
--  1.3.6.1.4.1.10428 9 1.101.23.5.5.1.1.1.4
                -- 1.3.6.1.4.1.10428 9 1.101.23.5.5.1.1.1.4
                fkGponProfileVoIPServiceProtocol OBJECT-TYPE
                        SYNTAX INTEGER
                                {
                                h248(1),
                                mgcp(2),
                                sip(3),
                                unknown(4)
                                }
                        MAX-ACCESS read-only
                        STATUS current
                        DESCRIPTION
                                "VoIP service Protocol."
                        ::= { fkGponProfileVoIPEntry 4 }

                
--  1.3.6.1.4.1.10428 9 1.101.23.5.5.1.1.1.5
                -- 1.3.6.1.4.1.10428 9 1.101.23.5.5.1.1.1.5
                fkGponProfileVoIPOmciAgentURL OBJECT-TYPE
                        SYNTAX OCTET STRING
                        MAX-ACCESS read-only
                        STATUS current
                        DESCRIPTION
                                "OMCI agent URL."
                        ::= { fkGponProfileVoIPEntry 5 }

                
--  1.3.6.1.4.1.10428 9 1.101.23.5.5.1.1.1.6
                -- 1.3.6.1.4.1.10428 9 1.101.23.5.5.1.1.1.6
                fkGponProfileVoIPOmciAgentProxy OBJECT-TYPE
                        SYNTAX OCTET STRING
                        MAX-ACCESS read-only
                        STATUS current
                        DESCRIPTION
                                "OMCI agent proxy."
                        ::= { fkGponProfileVoIPEntry 6 }

                
--  1.3.6.1.4.1.10428 9 1.101.23.5.5.1.1.1.7
                -- 1.3.6.1.4.1.10428 9 1.101.23.5.5.1.1.1.7
                fkGponProfileVoIPOmciAgentDns1 OBJECT-TYPE
                        SYNTAX IpAddress
                        MAX-ACCESS read-only
                        STATUS current
                        DESCRIPTION
                                "OCMI agent DNS primary"
                        ::= { fkGponProfileVoIPEntry 7 }

                
--  1.3.6.1.4.1.10428 9 1.101.23.5.5.1.1.1.8
                -- 1.3.6.1.4.1.10428 9 1.101.23.5.5.1.1.1.8
                fkGponProfileVoIPOmciAgentDns2 OBJECT-TYPE
                        SYNTAX IpAddress
                        MAX-ACCESS read-only
                        STATUS current
                        DESCRIPTION
                                "OMCI agent DNS secondary"
                        ::= { fkGponProfileVoIPEntry 8 }

                
--  1.3.6.1.4.1.10428 9 1.101.23.5.5.1.1.1.9
                -- 1.3.6.1.4.1.10428 9 1.101.23.5.5.1.1.1.9
                fkGponProfileVoIPIpwayAuthName OBJECT-TYPE
                        SYNTAX OCTET STRING
                        MAX-ACCESS read-only
                        STATUS current
                        DESCRIPTION
                                "IP PATH AUTH name"
                        ::= { fkGponProfileVoIPEntry 9 }

                
--  1.3.6.1.4.1.10428 9 1.101.23.5.5.1.1.1.10
                -- 1.3.6.1.4.1.10428 9 1.101.23.5.5.1.1.1.10
                fkGponProfileVoIPIpwayAuthPasswd OBJECT-TYPE
                        SYNTAX OCTET STRING
                        MAX-ACCESS read-only
                        STATUS current
                        DESCRIPTION
                                "IP PATH AUTH Password(UnUsed)"
                        ::= { fkGponProfileVoIPEntry 10 }

                
--  1.3.6.1.4.1.10428 9 1.101.23.5.5.1.1.1.11
                -- 1.3.6.1.4.1.10428 9 1.101.23.5.5.1.1.1.11
                fkGponProfileVoIPIpwayURL OBJECT-TYPE
                        SYNTAX OCTET STRING
                        MAX-ACCESS read-only
                        STATUS current
                        DESCRIPTION
                                "IP PATH AUTH URL"
                        ::= { fkGponProfileVoIPEntry 11 }

                
--  1.3.6.1.4.1.10428 9 1.101.23.5.5.1.2
                -- 1.3.6.1.4.1.10428 9 1.101.23.5.5.1.2
                fkGponProfileVoIPControl OBJECT IDENTIFIER ::= { fkGponProfileVoIP 2 }

                
--  1.3.6.1.4.1.10428 9 1.101.23.5.5.1.2.1
                -- 1.3.6.1.4.1.10428 9 1.101.23.5.5.1.2.1
                fkGponProfileVoIPControlRequest OBJECT-TYPE
                        SYNTAX INTEGER
                                {
                                createProfile(1),
                                destroyProfile(2),
                                updateService(3),
                                updateOmci(4),
                                updateIpWay(5)
                                }
                        MAX-ACCESS read-write
                        STATUS current
                        DESCRIPTION
                                "The request of a user command"
                        ::= { fkGponProfileVoIPControl 1 }

                
--  1.3.6.1.4.1.10428 9 1.101.23.5.5.1.2.2
                -- 1.3.6.1.4.1.10428 9 1.101.23.5.5.1.2.2
                fkGponProfileVoIPControlStatus OBJECT-TYPE
                        SYNTAX FkControlStatusType
                        MAX-ACCESS read-only
                        STATUS current
                        DESCRIPTION
                                "The status of user command"
                        ::= { fkGponProfileVoIPControl 2 }

                
--  1.3.6.1.4.1.10428 9 1.101.23.5.5.1.2.3
                -- 1.3.6.1.4.1.10428 9 1.101.23.5.5.1.2.3
                fkGponProfileVoIPControlTimer OBJECT-TYPE
                        SYNTAX Gauge32
                        MAX-ACCESS read-write
                        STATUS current
                        DESCRIPTION
                                "The maximum time for the manager for a long running user command"
                        ::= { fkGponProfileVoIPControl 3 }

                
--  1.3.6.1.4.1.10428 9 1.101.23.5.5.1.2.4
                -- 1.3.6.1.4.1.10428 9 1.101.23.5.5.1.2.4
                fkGponProfileVoIPControlTimeStamp OBJECT-TYPE
                        SYNTAX TimeTicks
                        MAX-ACCESS read-only
                        STATUS current
                        DESCRIPTION
                                "The time stamp of the last command(end of command)"
                        ::= { fkGponProfileVoIPControl 4 }

                
--  1.3.6.1.4.1.10428 9 1.101.23.5.5.1.2.5
                -- 1.3.6.1.4.1.10428 9 1.101.23.5.5.1.2.5
                fkGponProfileVoIPControlReqResult OBJECT-TYPE
                        SYNTAX FkControlRequestResultType
                        MAX-ACCESS read-only
                        STATUS current
                        DESCRIPTION
                                "The result of the last user command"
                        ::= { fkGponProfileVoIPControl 5 }

                
--  1.3.6.1.4.1.10428 9 1.101.23.5.5.1.2.6
                -- 1.3.6.1.4.1.10428 9 1.101.23.5.5.1.2.6
                fkGponProfileVoIPControlIndex OBJECT-TYPE
                        SYNTAX INTEGER (1..65535)
                        MAX-ACCESS read-write
                        STATUS current
                        DESCRIPTION
                                "Multi Tcont profile Index"
                        ::= { fkGponProfileVoIPControl 6 }

                
--  1.3.6.1.4.1.10428 9 1.101.23.5.5.1.2.7
                -- 1.3.6.1.4.1.10428 9 1.101.23.5.5.1.2.7
                fkGponProfileVoIPControlName OBJECT-TYPE
                        SYNTAX OCTET STRING
                        MAX-ACCESS read-write
                        STATUS current
                        DESCRIPTION
                                "Profile Name"
                        ::= { fkGponProfileVoIPControl 7 }

                
--  1.3.6.1.4.1.10428 9 1.101.23.5.5.1.2.8
                -- 1.3.6.1.4.1.10428 9 1.101.23.5.5.1.2.8
                fkGponProfileVoIPControlServiceMode OBJECT-TYPE
                        SYNTAX INTEGER
                                {
                                ipPath(1),
                                omci(2),
                                unknown(3)
                                }
                        MAX-ACCESS read-write
                        STATUS current
                        DESCRIPTION
                                "VoIP service mode"
                        ::= { fkGponProfileVoIPControl 8 }

                
--  1.3.6.1.4.1.10428 9 1.101.23.5.5.1.2.9
                -- 1.3.6.1.4.1.10428 9 1.101.23.5.5.1.2.9
                fkGponProfileVoIPControlServiceProtocol OBJECT-TYPE
                        SYNTAX INTEGER
                                {
                                h248(1),
                                mgcp(2),
                                sip(3),
                                unknown(4)
                                }
                        MAX-ACCESS read-write
                        STATUS current
                        DESCRIPTION
                                "VoIP service Protocol."
                        ::= { fkGponProfileVoIPControl 9 }

                
--  1.3.6.1.4.1.10428 9 1.101.23.5.5.1.2.10
                -- 1.3.6.1.4.1.10428 9 1.101.23.5.5.1.2.10
                fkGponProfileVoIPControlOmciAgentURL OBJECT-TYPE
                        SYNTAX OCTET STRING
                        MAX-ACCESS read-write
                        STATUS current
                        DESCRIPTION
                                "OMCI agent URL."
                        ::= { fkGponProfileVoIPControl 10 }

                
--  1.3.6.1.4.1.10428 9 1.101.23.5.5.1.2.11
                -- 1.3.6.1.4.1.10428 9 1.101.23.5.5.1.2.11
                fkGponProfileVoIPControlOmciAgentProxy OBJECT-TYPE
                        SYNTAX OCTET STRING
                        MAX-ACCESS read-write
                        STATUS current
                        DESCRIPTION
                                "OMCI agent proxy."
                        ::= { fkGponProfileVoIPControl 11 }

                
--  1.3.6.1.4.1.10428 9 1.101.23.5.5.1.2.12
                -- 1.3.6.1.4.1.10428 9 1.101.23.5.5.1.2.12
                fkGponProfileVoIPControlOmciAgentDns1 OBJECT-TYPE
                        SYNTAX IpAddress
                        MAX-ACCESS read-write
                        STATUS current
                        DESCRIPTION
                                "OCMI agent DNS primary"
                        ::= { fkGponProfileVoIPControl 12 }

                
--  1.3.6.1.4.1.10428 9 1.101.23.5.5.1.2.13
                -- 1.3.6.1.4.1.10428 9 1.101.23.5.5.1.2.13
                fkGponProfileVoIPControlOmciAgentDns2 OBJECT-TYPE
                        SYNTAX IpAddress
                        MAX-ACCESS read-write
                        STATUS current
                        DESCRIPTION
                                "OMCI agent DNS secondary"
                        ::= { fkGponProfileVoIPControl 13 }

                
--  1.3.6.1.4.1.10428 9 1.101.23.5.5.1.2.14
                -- 1.3.6.1.4.1.10428 9 1.101.23.5.5.1.2.14
                fkGponProfileVoIPControlIpwayAuthName OBJECT-TYPE
                        SYNTAX OCTET STRING
                        MAX-ACCESS read-write
                        STATUS current
                        DESCRIPTION
                                "IP PATH AUTH name"
                        ::= { fkGponProfileVoIPControl 14 }

                
--  1.3.6.1.4.1.10428 9 1.101.23.5.5.1.2.15
                -- 1.3.6.1.4.1.10428 9 1.101.23.5.5.1.2.15
                fkGponProfileVoIPControlIpwayAuthPasswd OBJECT-TYPE
                        SYNTAX OCTET STRING
                        MAX-ACCESS read-write
                        STATUS current
                        DESCRIPTION
                                "IP PATH AUTH Password(UnUsed)"
                        ::= { fkGponProfileVoIPControl 15 }

                
--  1.3.6.1.4.1.10428 9 1.101.23.5.5.1.2.16
                -- 1.3.6.1.4.1.10428 9 1.101.23.5.5.1.2.16
                fkGponProfileVoIPControlIpwayURL OBJECT-TYPE
                        SYNTAX OCTET STRING
                        MAX-ACCESS read-write
                        STATUS current
                        DESCRIPTION
                                "IP PATH AUTH URL"
                        ::= { fkGponProfileVoIPControl 16 }

                
--  1.3.6.1.4.1.10428 9 1.101.23.5.5.1.3
                -- 1.3.6.1.4.1.10428 9 1.101.23.5.5.1.3
                fkGponProfileVoIPNotification OBJECT IDENTIFIER ::= { fkGponProfileVoIP 3 }

                
--  1.3.6.1.4.1.10428 9 1.101.23.5.5.1.3.1
                -- 1.3.6.1.4.1.10428 9 1.101.23.5.5.1.3.1
                fkGponProfileVoIPProfileCreated NOTIFICATION-TYPE
                        OBJECTS { fkGponProfileVoIPControlRequest, fkGponProfileVoIPControlTimeStamp, fkGponProfileVoIPControlReqResult, fkGponProfileVoIPControlName }
                        STATUS current
                        DESCRIPTION 
                                "Description."
                        ::= { fkGponProfileVoIPNotification 1 }

                
--  1.3.6.1.4.1.10428 9 1.101.23.5.5.1.3.2
                -- 1.3.6.1.4.1.10428 9 1.101.23.5.5.1.3.2
                fkGponProfileVoIPProfileDestroyed NOTIFICATION-TYPE
                        OBJECTS { fkGponProfileVoIPControlRequest, fkGponProfileVoIPControlTimeStamp, fkGponProfileVoIPControlReqResult, fkGponProfileVoIPControlIndex }
                        STATUS current
                        DESCRIPTION 
                                "Description."
                        ::= { fkGponProfileVoIPNotification 2 }

                
--  1.3.6.1.4.1.10428 9 1.101.23.5.5.1.3.3
                -- 1.3.6.1.4.1.10428 9 1.101.23.5.5.1.3.3
                fkGponProfilVoIPProfileServiceChanged NOTIFICATION-TYPE
                        OBJECTS { fkGponProfileVoIPControlRequest, fkGponProfileVoIPControlTimeStamp, fkGponProfileVoIPControlReqResult, fkGponProfileVoIPControlIndex, fkGponProfileVoIPControlServiceMode, 
                                fkGponProfileVoIPControlServiceProtocol }
                        STATUS current
                        DESCRIPTION 
                                "Description."
                        ::= { fkGponProfileVoIPNotification 3 }

                
--  1.3.6.1.4.1.10428 9 1.101.23.5.5.1.3.4
                -- 1.3.6.1.4.1.10428 9 1.101.23.5.5.1.3.4
                fkGponProfileVoIPProfileOmciChanged NOTIFICATION-TYPE
                        OBJECTS { fkGponProfileVoIPControlRequest, fkGponProfileVoIPControlTimeStamp, fkGponProfileVoIPControlReqResult, fkGponProfileVoIPControlIndex, fkGponProfileVoIPControlOmciAgentURL, 
                                fkGponProfileVoIPControlOmciAgentProxy, fkGponProfileVoIPControlOmciAgentDns1, fkGponProfileVoIPControlOmciAgentDns2 }
                        STATUS current
                        DESCRIPTION 
                                "Description."
                        ::= { fkGponProfileVoIPNotification 4 }

                
--  1.3.6.1.4.1.10428 9 1.101.23.5.5.1.3.5
                -- 1.3.6.1.4.1.10428 9 1.101.23.5.5.1.3.5
                fkGponProfileVoIPProfileIpwayChanged NOTIFICATION-TYPE
                        OBJECTS { fkGponProfileVoIPControlRequest, fkGponProfileVoIPControlTimer, fkGponProfileVoIPControlReqResult, fkGponProfileVoIPControlIndex, fkGponProfileVoIPControlIpwayAuthName, 
                                fkGponProfileVoIPControlIpwayAuthPasswd, fkGponProfileVoIPControlIpwayURL }
                        STATUS current
                        DESCRIPTION 
                                "Description."
                        ::= { fkGponProfileVoIPNotification 5 }

                
--  1.3.6.1.4.1.10428 9 1.101.23.5.5.2
                -- 1.3.6.1.4.1.10428 9 1.101.23.5.5.2
                fkGponProfileVoIPOmci OBJECT IDENTIFIER ::= { fkGponVoIP 2 }

                
--  1.3.6.1.4.1.10428 9 1.101.23.5.5.2.1
                -- 1.3.6.1.4.1.10428 9 1.101.23.5.5.2.1
                fkGponProfileVoIPOmciTable OBJECT-TYPE
                        SYNTAX SEQUENCE OF FkGponProfileVoIPOmciEntry
                        MAX-ACCESS not-accessible
                        STATUS current
                        DESCRIPTION
                                "fkGponProfileVoIPOmciTable"
                        ::= { fkGponProfileVoIPOmci 1 }

                
--  1.3.6.1.4.1.10428 9 1.101.23.5.5.2.1.1
                -- 1.3.6.1.4.1.10428 9 1.101.23.5.5.2.1.1
                fkGponProfileVoIPOmciEntry OBJECT-TYPE
                        SYNTAX FkGponProfileVoIPOmciEntry
                        MAX-ACCESS not-accessible
                        STATUS current
                        DESCRIPTION
                                "key: fkGponOltId, fkGponOnuId, fkGponProfileVoIPOmciUniPortId"
                        INDEX { fkGponOltId, fkGponOnuId, fkGponProfileVoIPOmciUniPortId }
                        ::= { fkGponProfileVoIPOmciTable 1 }

                
                FkGponProfileVoIPOmciEntry ::=
                        SEQUENCE { 
                                fkGponProfileVoIPOmciUniPortId
                                        Integer32,
                                fkGponProfileVoIPOmciAuthName
                                        OCTET STRING,
                                fkGponProfileVoIPOmciAuthPasswd
                                        OCTET STRING,
                                fkGponProfileVoIPOmciPhoneNumber
                                        OCTET STRING,
                                fkGponProfileVoIPOmciDisplay
                                        OCTET STRING,
                                fkGponProfileVoIPOmciMgcTerminationId
                                        OCTET STRING
                         }

--  1.3.6.1.4.1.10428 9 1.101.23.5.5.2.1.1.1
                -- 1.3.6.1.4.1.10428 9 1.101.23.5.5.2.1.1.1
                fkGponProfileVoIPOmciUniPortId OBJECT-TYPE
                        SYNTAX Integer32 (1..65535)
                        MAX-ACCESS read-only
                        STATUS current
                        DESCRIPTION
                                "OMCI UNI port Id"
                        ::= { fkGponProfileVoIPOmciEntry 1 }

                
--  1.3.6.1.4.1.10428 9 1.101.23.5.5.2.1.1.2
                -- 1.3.6.1.4.1.10428 9 1.101.23.5.5.2.1.1.2
                fkGponProfileVoIPOmciAuthName OBJECT-TYPE
                        SYNTAX OCTET STRING
                        MAX-ACCESS read-only
                        STATUS current
                        DESCRIPTION
                                "OMCI AUTH name"
                        ::= { fkGponProfileVoIPOmciEntry 2 }

                
--  1.3.6.1.4.1.10428 9 1.101.23.5.5.2.1.1.3
                -- 1.3.6.1.4.1.10428 9 1.101.23.5.5.2.1.1.3
                fkGponProfileVoIPOmciAuthPasswd OBJECT-TYPE
                        SYNTAX OCTET STRING
                        MAX-ACCESS read-only
                        STATUS current
                        DESCRIPTION
                                "OMCI AUTH Password"
                        ::= { fkGponProfileVoIPOmciEntry 3 }

                
--  1.3.6.1.4.1.10428 9 1.101.23.5.5.2.1.1.4
                -- 1.3.6.1.4.1.10428 9 1.101.23.5.5.2.1.1.4
                fkGponProfileVoIPOmciPhoneNumber OBJECT-TYPE
                        SYNTAX OCTET STRING
                        MAX-ACCESS read-only
                        STATUS current
                        DESCRIPTION
                                "OMCI Phone number"
                        ::= { fkGponProfileVoIPOmciEntry 4 }

                
--  1.3.6.1.4.1.10428 9 1.101.23.5.5.2.1.1.5
                -- 1.3.6.1.4.1.10428 9 1.101.23.5.5.2.1.1.5
                fkGponProfileVoIPOmciDisplay OBJECT-TYPE
                        SYNTAX OCTET STRING
                        MAX-ACCESS read-only
                        STATUS current
                        DESCRIPTION
                                "OMCI Phone Display"
                        ::= { fkGponProfileVoIPOmciEntry 5 }

                
--  1.3.6.1.4.1.10428 9 1.101.23.5.5.2.1.1.5
                -- 1.3.6.1.4.1.10428 9 1.101.23.5.5.2.1.1.6
                fkGponProfileVoIPOmciMgcTerminationId OBJECT-TYPE
                        SYNTAX OCTET STRING
                        MAX-ACCESS read-only
                        STATUS current
                        DESCRIPTION
                                "The MGC termination ID"
                        ::= { fkGponProfileVoIPOmciEntry 6 }

                
--  1.3.6.1.4.1.10428 9 1.101.23.5.5.2.2
                -- 1.3.6.1.4.1.10428 9 1.101.23.5.5.2.2
                fkGponProfileVoIPOmciControl OBJECT IDENTIFIER ::= { fkGponProfileVoIPOmci 2 }

                
--  1.3.6.1.4.1.10428 9 1.101.23.5.5.2.2.1
                -- 1.3.6.1.4.1.10428 9 1.101.23.5.5.2.2.1
                fkGponProfileVoIPOmciControlRequest OBJECT-TYPE
                        SYNTAX INTEGER
                                {
                                setSIPAuth(1),
                                setSIPPhone(2),
                                setMGCTermination(3)
                                }
                        MAX-ACCESS read-write
                        STATUS current
                        DESCRIPTION
                                "The request of a user command"
                        ::= { fkGponProfileVoIPOmciControl 1 }

                
--  1.3.6.1.4.1.10428 9 1.101.23.5.5.2.2.2
                -- 1.3.6.1.4.1.10428 9 1.101.23.5.5.2.2.2
                fkGponProfileVoIPOmciControlStatus OBJECT-TYPE
                        SYNTAX FkControlStatusType
                        MAX-ACCESS read-only
                        STATUS current
                        DESCRIPTION
                                "The status of user command"
                        ::= { fkGponProfileVoIPOmciControl 2 }

                
--  1.3.6.1.4.1.10428 9 1.101.23.5.5.2.2.3
                -- 1.3.6.1.4.1.10428 9 1.101.23.5.5.2.2.3
                fkGponProfileVoIPOmciControlTimer OBJECT-TYPE
                        SYNTAX Gauge32
                        MAX-ACCESS read-write
                        STATUS current
                        DESCRIPTION
                                "The maximum time for the manager for a long running user command"
                        ::= { fkGponProfileVoIPOmciControl 3 }

                
--  1.3.6.1.4.1.10428 9 1.101.23.5.5.2.2.4
                -- 1.3.6.1.4.1.10428 9 1.101.23.5.5.2.2.4
                fkGponProfileVoIPOmciControlTimeStamp OBJECT-TYPE
                        SYNTAX TimeTicks
                        MAX-ACCESS read-only
                        STATUS current
                        DESCRIPTION
                                "The time stamp of the last command(end of command)"
                        ::= { fkGponProfileVoIPOmciControl 4 }

                
--  1.3.6.1.4.1.10428 9 1.101.23.5.5.2.2.5
                -- 1.3.6.1.4.1.10428 9 1.101.23.5.5.2.2.5
                fkGponProfileVoIPOmciControlReqResult OBJECT-TYPE
                        SYNTAX FkControlRequestResultType
                        MAX-ACCESS read-only
                        STATUS current
                        DESCRIPTION
                                "The result of the last user command"
                        ::= { fkGponProfileVoIPOmciControl 5 }

                
--  1.3.6.1.4.1.10428 9 1.101.23.5.5.2.2.6
                -- 1.3.6.1.4.1.10428 9 1.101.23.5.5.2.2.6
                fkGponProfileVoIPOmciControlOltIndex OBJECT-TYPE
                        SYNTAX INTEGER (1..65535)
                        MAX-ACCESS read-write
                        STATUS current
                        DESCRIPTION
                                "OLT Index"
                        ::= { fkGponProfileVoIPOmciControl 6 }

                
--  1.3.6.1.4.1.10428 9 1.101.23.5.5.2.2.7
                -- 1.3.6.1.4.1.10428 9 1.101.23.5.5.2.2.7
                fkGponProfileVoIPOmciControlOnuIndex OBJECT-TYPE
                        SYNTAX INTEGER (1..65535)
                        MAX-ACCESS read-write
                        STATUS current
                        DESCRIPTION
                                "ONU Index"
                        ::= { fkGponProfileVoIPOmciControl 7 }

                
--  1.3.6.1.4.1.10428 9 1.101.23.5.5.2.2.8
                -- 1.3.6.1.4.1.10428 9 1.101.23.5.5.2.2.8
                fkGponProfileVoIPOmciControlUniId OBJECT-TYPE
                        SYNTAX INTEGER (1..65535)
                        MAX-ACCESS read-write
                        STATUS current
                        DESCRIPTION
                                "UNI port Index"
                        ::= { fkGponProfileVoIPOmciControl 8 }

                
--  1.3.6.1.4.1.10428 9 1.101.23.5.5.2.2.9
                -- 1.3.6.1.4.1.10428 9 1.101.23.5.5.2.2.9
                fkGponProfileVoIPOmciControlAuthName OBJECT-TYPE
                        SYNTAX OCTET STRING
                        MAX-ACCESS read-write
                        STATUS current
                        DESCRIPTION
                                "OMCI AUTH name"
                        ::= { fkGponProfileVoIPOmciControl 9 }

                
--  1.3.6.1.4.1.10428 9 1.101.23.5.5.2.2.10
                -- 1.3.6.1.4.1.10428 9 1.101.23.5.5.2.2.10
                fkGponProfileVoIPOmciControlAuthPasswd OBJECT-TYPE
                        SYNTAX OCTET STRING
                        MAX-ACCESS read-write
                        STATUS current
                        DESCRIPTION
                                "OMCI AUTH Password"
                        ::= { fkGponProfileVoIPOmciControl 10 }

                
--  1.3.6.1.4.1.10428 9 1.101.23.5.5.2.2.11
                -- 1.3.6.1.4.1.10428 9 1.101.23.5.5.2.2.11
                fkGponProfileVoIPOmciControlPhoneNumber OBJECT-TYPE
                        SYNTAX OCTET STRING
                        MAX-ACCESS read-write
                        STATUS current
                        DESCRIPTION
                                "OMCI Phone number"
                        ::= { fkGponProfileVoIPOmciControl 11 }

                
--  1.3.6.1.4.1.10428 9 1.101.23.5.5.2.2.12
                -- 1.3.6.1.4.1.10428 9 1.101.23.5.5.2.2.12
                fkGponProfileVoIPOmciControlDisplay OBJECT-TYPE
                        SYNTAX OCTET STRING
                        MAX-ACCESS read-write
                        STATUS current
                        DESCRIPTION
                                "OMCI Phone Display"
                        ::= { fkGponProfileVoIPOmciControl 12 }

                
                -- 1.3.6.1.4.1.10428 9 1.101.23.5.5.2.2.13
                fkGponProfileVoIPOmciControlMgcTerminationId OBJECT-TYPE
                        SYNTAX OCTET STRING
                        MAX-ACCESS read-write
                        STATUS current
                        DESCRIPTION
                                "The MGC termination ID"
                        ::= { fkGponProfileVoIPOmciControl 13 }

                
--  1.3.6.1.4.1.10428 9 1.101.23.5.5.2.3
                -- 1.3.6.1.4.1.10428 9 1.101.23.5.5.2.3
                fkGponProfileVoIPOmciNotification OBJECT IDENTIFIER ::= { fkGponProfileVoIPOmci 3 }

                
--  1.3.6.1.4.1.10428 9 1.101.23.5.5.2.3.1
                -- 1.3.6.1.4.1.10428 9 1.101.23.5.5.2.3.1
                fkGponProfileVoIPOmciSIPAuthChanged NOTIFICATION-TYPE
                        OBJECTS { fkGponProfileVoIPOmciControlRequest, fkGponProfileVoIPOmciControlTimeStamp, fkGponProfileVoIPOmciControlReqResult, fkGponProfileVoIPOmciControlOltIndex, fkGponProfileVoIPOmciControlOnuIndex, 
                                fkGponProfileVoIPOmciControlUniId, fkGponProfileVoIPOmciControlAuthName, fkGponProfileVoIPOmciControlAuthPasswd }
                        STATUS current
                        DESCRIPTION 
                                "Description."
                        ::= { fkGponProfileVoIPOmciNotification 1 }

                
--  1.3.6.1.4.1.10428 9 1.101.23.5.5.2.3.2
                -- 1.3.6.1.4.1.10428 9 1.101.23.5.5.2.3.2
                fkGponProfileVoIPOmciSIPPhoneChnaged NOTIFICATION-TYPE
                        OBJECTS { fkGponProfileVoIPOmciControlRequest, fkGponProfileVoIPOmciControlTimeStamp, fkGponProfileVoIPOmciControlReqResult, fkGponProfileVoIPOmciControlOltIndex, fkGponProfileVoIPOmciControlOnuIndex, 
                                fkGponProfileVoIPOmciControlUniId, fkGponProfileVoIPOmciControlPhoneNumber, fkGponProfileVoIPOmciControlDisplay }
                        STATUS current
                        DESCRIPTION 
                                "Description."
                        ::= { fkGponProfileVoIPOmciNotification 2 }

                
--  1.3.6.1.4.1.10428 9 1.101.23.5.5.2.3.1
                -- 1.3.6.1.4.1.10428 9 1.101.23.5.5.2.3.3
                fkGponProfileVoIPOmciMGCTerminationChanged NOTIFICATION-TYPE
                        OBJECTS { fkGponProfileVoIPOmciControlRequest, fkGponProfileVoIPOmciControlTimeStamp, fkGponProfileVoIPOmciControlReqResult, fkGponProfileVoIPOmciControlOltIndex, fkGponProfileVoIPOmciControlOnuIndex, 
                                fkGponProfileVoIPOmciControlUniId, fkGponProfileVoIPOmciControlMgcTerminationId }
                        STATUS current
                        DESCRIPTION 
                                "setMGCTermination"
                        ::= { fkGponProfileVoIPOmciNotification 3 }

                
--  1.3.6.1.4.1.10428 9 1.101.23.5.5.3
                -- 1.3.6.1.4.1.10428 9 1.101.23.5.5.3
                fkGponProfileVoIPIpPath OBJECT IDENTIFIER ::= { fkGponVoIP 3 }

                
--  1.3.6.1.4.1.10428 9 1.101.23.5.5.3.1
                -- 1.3.6.1.4.1.10428 9 1.101.23.5.5.3.1
                fkGponProfileVoIPIpPathTable OBJECT-TYPE
                        SYNTAX SEQUENCE OF FkGponProfileVoIPIpPathEntry
                        MAX-ACCESS not-accessible
                        STATUS current
                        DESCRIPTION
                                "Description."
                        ::= { fkGponProfileVoIPIpPath 1 }

                
--  1.3.6.1.4.1.10428 9 1.101.23.5.5.3.1.1
                -- 1.3.6.1.4.1.10428 9 1.101.23.5.5.3.1.1
                fkGponProfileVoIPIpPathEntry OBJECT-TYPE
                        SYNTAX FkGponProfileVoIPIpPathEntry
                        MAX-ACCESS not-accessible
                        STATUS current
                        DESCRIPTION
                                "Description."
                        INDEX { fkGponOltId, fkGponOnuId }
                        ::= { fkGponProfileVoIPIpPathTable 1 }

                
                FkGponProfileVoIPIpPathEntry ::=
                        SEQUENCE { 
                                fkGponProfileVoIPIpPathAuthName
                                        OCTET STRING,
                                fkGponProfileVoIPIpPathAuthPasswd
                                        OCTET STRING,
                                fkGponProfileVoIPIpPathURL
                                        OCTET STRING
                         }

--  1.3.6.1.4.1.10428 9 1.101.23.5.5.3.1.1.1
                -- 1.3.6.1.4.1.10428 9 1.101.23.5.5.3.1.1.1
                fkGponProfileVoIPIpPathAuthName OBJECT-TYPE
                        SYNTAX OCTET STRING
                        MAX-ACCESS read-only
                        STATUS current
                        DESCRIPTION
                                "IP PATH AUTH name(UnUsed)"
                        ::= { fkGponProfileVoIPIpPathEntry 1 }

                
--  1.3.6.1.4.1.10428 9 1.101.23.5.5.3.1.1.2
                -- 1.3.6.1.4.1.10428 9 1.101.23.5.5.3.1.1.2
                fkGponProfileVoIPIpPathAuthPasswd OBJECT-TYPE
                        SYNTAX OCTET STRING
                        MAX-ACCESS read-only
                        STATUS current
                        DESCRIPTION
                                "IP PATH AUTH Password(UnUsed)"
                        ::= { fkGponProfileVoIPIpPathEntry 2 }

                
--  1.3.6.1.4.1.10428 9 1.101.23.5.5.3.1.1.3
                -- 1.3.6.1.4.1.10428 9 1.101.23.5.5.3.1.1.3
                fkGponProfileVoIPIpPathURL OBJECT-TYPE
                        SYNTAX OCTET STRING
                        MAX-ACCESS read-only
                        STATUS current
                        DESCRIPTION
                                "IP PATH AUTH URL(UnUsed)"
                        ::= { fkGponProfileVoIPIpPathEntry 3 }

                
--  1.3.6.1.4.1.10428 9 1.101.23.5.5.3.2
                -- 1.3.6.1.4.1.10428 9 1.101.23.5.5.3.2
                fkGponProfileVoIPIpPathControl OBJECT IDENTIFIER ::= { fkGponProfileVoIPIpPath 2 }

                
--  1.3.6.1.4.1.10428 9 1.101.23.5.5.3.2.1
                -- 1.3.6.1.4.1.10428 9 1.101.23.5.5.3.2.1
                fkGponProfileVoIPIpPathControlRequest OBJECT-TYPE
                        SYNTAX INTEGER { setVoIPIPPathControlInfo(1) }
                        MAX-ACCESS read-write
                        STATUS current
                        DESCRIPTION
                                "The request of a user command"
                        ::= { fkGponProfileVoIPIpPathControl 1 }

                
--  1.3.6.1.4.1.10428 9 1.101.23.5.5.3.2.2
                -- 1.3.6.1.4.1.10428 9 1.101.23.5.5.3.2.2
                fkGponProfileVoIPIpPathControlStatus OBJECT-TYPE
                        SYNTAX FkControlStatusType
                        MAX-ACCESS read-only
                        STATUS current
                        DESCRIPTION
                                "The status of user command"
                        ::= { fkGponProfileVoIPIpPathControl 2 }

                
--  1.3.6.1.4.1.10428 9 1.101.23.5.5.3.2.3
                -- 1.3.6.1.4.1.10428 9 1.101.23.5.5.3.2.3
                fkGponProfileVoIPIpPathControlTimer OBJECT-TYPE
                        SYNTAX Gauge32
                        MAX-ACCESS read-write
                        STATUS current
                        DESCRIPTION
                                "The maximum time for the manager for a long running user command"
                        ::= { fkGponProfileVoIPIpPathControl 3 }

                
--  1.3.6.1.4.1.10428 9 1.101.23.5.5.3.2.4
                -- 1.3.6.1.4.1.10428 9 1.101.23.5.5.3.2.4
                fkGponProfileVoIPIpPathControlTimeStamp OBJECT-TYPE
                        SYNTAX TimeTicks
                        MAX-ACCESS read-only
                        STATUS current
                        DESCRIPTION
                                "The time stamp of the last command(end of command)"
                        ::= { fkGponProfileVoIPIpPathControl 4 }

                
--  1.3.6.1.4.1.10428 9 1.101.23.5.5.3.2.5
                -- 1.3.6.1.4.1.10428 9 1.101.23.5.5.3.2.5
                fkGponProfileVoIPIpPathControlReqResult OBJECT-TYPE
                        SYNTAX FkControlRequestResultType
                        MAX-ACCESS read-only
                        STATUS current
                        DESCRIPTION
                                "The result of the last user command"
                        ::= { fkGponProfileVoIPIpPathControl 5 }

                
--  1.3.6.1.4.1.10428 9 1.101.23.5.5.3.2.6
                -- 1.3.6.1.4.1.10428 9 1.101.23.5.5.3.2.6
                fkGponProfileVoIPIpPathControlOltIndex OBJECT-TYPE
                        SYNTAX INTEGER (1..65535)
                        MAX-ACCESS read-write
                        STATUS current
                        DESCRIPTION
                                "OLT Index"
                        ::= { fkGponProfileVoIPIpPathControl 6 }

                
--  1.3.6.1.4.1.10428 9 1.101.23.5.5.3.2.7
                -- 1.3.6.1.4.1.10428 9 1.101.23.5.5.3.2.7
                fkGponProfileVoIPIpPathControlOnuIndex OBJECT-TYPE
                        SYNTAX INTEGER (1..65535)
                        MAX-ACCESS read-write
                        STATUS current
                        DESCRIPTION
                                "ONU Index"
                        ::= { fkGponProfileVoIPIpPathControl 7 }

                
--  1.3.6.1.4.1.10428 9 1.101.23.5.5.3.2.8
                -- 1.3.6.1.4.1.10428 9 1.101.23.5.5.3.2.8
                fkGponProfileVoIPIpPathControlAuthName OBJECT-TYPE
                        SYNTAX OCTET STRING
                        MAX-ACCESS read-write
                        STATUS current
                        DESCRIPTION
                                "IP PATH AUTH name"
                        ::= { fkGponProfileVoIPIpPathControl 8 }

                
--  1.3.6.1.4.1.10428 9 1.101.23.5.5.3.2.9
                -- 1.3.6.1.4.1.10428 9 1.101.23.5.5.3.2.9
                fkGponProfileVoIPIpPathControlAuthPasswd OBJECT-TYPE
                        SYNTAX OCTET STRING
                        MAX-ACCESS read-write
                        STATUS current
                        DESCRIPTION
                                "IP PATH AUTH Password"
                        ::= { fkGponProfileVoIPIpPathControl 9 }

                
--  1.3.6.1.4.1.10428 9 1.101.23.5.5.3.3
                -- 1.3.6.1.4.1.10428 9 1.101.23.5.5.3.3
                fkGponProfileVoIPIpPathNotification OBJECT IDENTIFIER ::= { fkGponProfileVoIPIpPath 3 }

                
--  1.3.6.1.4.1.10428 9 1.101.23.5.5.3.3.1
                -- 1.3.6.1.4.1.10428 9 1.101.23.5.5.3.3.1
                fkGponProfileVoIPIpPathInfoChanged NOTIFICATION-TYPE
                        OBJECTS { fkGponProfileVoIPIpPathControlRequest, fkGponProfileVoIPIpPathControlTimeStamp, fkGponProfileVoIPIpPathControlReqResult, fkGponProfileVoIPIpPathControlOltIndex, fkGponProfileVoIPIpPathControlOnuIndex, 
                                fkGponProfileVoIPIpPathControlAuthName, fkGponProfileVoIPIpPathControlAuthPasswd }
                        STATUS current
                        DESCRIPTION 
                                "Description."
                        ::= { fkGponProfileVoIPIpPathNotification 1 }

                
--  1.3.6.1.4.1.10428 9 1.101.23.5.5.4
                -- 1.3.6.1.4.1.10428 9 1.101.23.5.5.4
                fkGponProfileVoIPPots OBJECT IDENTIFIER ::= { fkGponVoIP 4 }

                
--  1.3.6.1.4.1.10428 9 1.101.23.5.5.4.1
                -- 1.3.6.1.4.1.10428 9 1.101.23.5.5.4.1
                fkGponProfileVoIPPotsTable OBJECT-TYPE
                        SYNTAX SEQUENCE OF FkGponProfileVoIPPotsEntry
                        MAX-ACCESS not-accessible
                        STATUS current
                        DESCRIPTION
                                "fkGponProfileVoIPPotsTable"
                        ::= { fkGponProfileVoIPPots 1 }

                
--  1.3.6.1.4.1.10428 9 1.101.23.5.5.4.1.1
                -- 1.3.6.1.4.1.10428 9 1.101.23.5.5.4.1.1
                fkGponProfileVoIPPotsEntry OBJECT-TYPE
                        SYNTAX FkGponProfileVoIPPotsEntry
                        MAX-ACCESS not-accessible
                        STATUS current
                        DESCRIPTION
                                "key: fkGponProfileVoIPPotsPIndex, fkGponProfileVoIPPotsIndex"
                        INDEX { fkGponProfileVoIPPotsPIndex, fkGponProfileVoIPPotsIndex }
                        ::= { fkGponProfileVoIPPotsTable 1 }

                
                FkGponProfileVoIPPotsEntry ::=
                        SEQUENCE { 
                                fkGponProfileVoIPPotsPIndex
                                        Integer32,
                                fkGponProfileVoIPPotsIndex
                                        Integer32,
                                fkGponProfileVoIPPotsAdmin
                                        EnableFlag
                         }

--  1.3.6.1.4.1.10428 9 1.101.23.5.5.4.1.1.1
                -- 1.3.6.1.4.1.10428 9 1.101.23.5.5.4.1.1.1
                fkGponProfileVoIPPotsPIndex OBJECT-TYPE
                        SYNTAX Integer32 (1..65535)
                        MAX-ACCESS read-only
                        STATUS current
                        DESCRIPTION
                                "VoIP Profile Index"
                        ::= { fkGponProfileVoIPPotsEntry 1 }

                
--  1.3.6.1.4.1.10428 9 1.101.23.5.5.4.1.1.2
                -- 1.3.6.1.4.1.10428 9 1.101.23.5.5.4.1.1.2
                fkGponProfileVoIPPotsIndex OBJECT-TYPE
                        SYNTAX Integer32 (1..65535)
                        MAX-ACCESS read-only
                        STATUS current
                        DESCRIPTION
                                "Pptp Pots Index"
                        ::= { fkGponProfileVoIPPotsEntry 2 }

                
--  1.3.6.1.4.1.10428 9 1.101.23.5.5.4.1.1.3
                -- 1.3.6.1.4.1.10428 9 1.101.23.5.5.4.1.1.3
                fkGponProfileVoIPPotsAdmin OBJECT-TYPE
                        SYNTAX EnableFlag
                        MAX-ACCESS read-only
                        STATUS current
                        DESCRIPTION
                                "State of ONU Pots Administratoration"
                        ::= { fkGponProfileVoIPPotsEntry 3 }

                
--  1.3.6.1.4.1.10428 9 1.101.23.5.5.4.2
                -- 1.3.6.1.4.1.10428 9 1.101.23.5.5.4.2
                fkGponProfileVoIPPotsControl OBJECT IDENTIFIER ::= { fkGponProfileVoIPPots 2 }

                
--  1.3.6.1.4.1.10428 9 1.101.23.5.5.4.2.1
                -- 1.3.6.1.4.1.10428 9 1.101.23.5.5.4.2.1
                fkGponProfileVoIPPotsControlRequest OBJECT-TYPE
                        SYNTAX INTEGER
                                {
                                addPots(1),
                                delPots(2)
                                }
                        MAX-ACCESS read-write
                        STATUS current
                        DESCRIPTION
                                "The request of a user command"
                        ::= { fkGponProfileVoIPPotsControl 1 }

                
--  1.3.6.1.4.1.10428 9 1.101.23.5.5.4.2.2
                -- 1.3.6.1.4.1.10428 9 1.101.23.5.5.4.2.2
                fkGponProfileVoIPPotsControlStatus OBJECT-TYPE
                        SYNTAX FkControlStatusType
                        MAX-ACCESS read-only
                        STATUS current
                        DESCRIPTION
                                "The status of user command"
                        ::= { fkGponProfileVoIPPotsControl 2 }

                
--  1.3.6.1.4.1.10428 9 1.101.23.5.5.4.2.3
                -- 1.3.6.1.4.1.10428 9 1.101.23.5.5.4.2.3
                fkGponProfileVoIPPotsControlTimer OBJECT-TYPE
                        SYNTAX Gauge32
                        MAX-ACCESS read-write
                        STATUS current
                        DESCRIPTION
                                "The maximum time for the manager for a long running user command"
                        ::= { fkGponProfileVoIPPotsControl 3 }

                
--  1.3.6.1.4.1.10428 9 1.101.23.5.5.4.2.4
                -- 1.3.6.1.4.1.10428 9 1.101.23.5.5.4.2.4
                fkGponProfileVoIPPotsControlTimeStamp OBJECT-TYPE
                        SYNTAX TimeTicks
                        MAX-ACCESS read-only
                        STATUS current
                        DESCRIPTION
                                "The time stamp of the last command(end of command)"
                        ::= { fkGponProfileVoIPPotsControl 4 }

                
--  1.3.6.1.4.1.10428 9 1.101.23.5.5.4.2.5
                -- 1.3.6.1.4.1.10428 9 1.101.23.5.5.4.2.5
                fkGponProfileVoIPPotsControlReqResult OBJECT-TYPE
                        SYNTAX FkControlRequestResultType
                        MAX-ACCESS read-only
                        STATUS current
                        DESCRIPTION
                                "The result of the last user command"
                        ::= { fkGponProfileVoIPPotsControl 5 }

                
--  1.3.6.1.4.1.10428 9 1.101.23.5.5.4.2.6
                -- 1.3.6.1.4.1.10428 9 1.101.23.5.5.4.2.6
                fkGponProfileVoIPPotsControlProfileIndex OBJECT-TYPE
                        SYNTAX Integer32
                        MAX-ACCESS read-write
                        STATUS current
                        DESCRIPTION
                                "VoIP Profile Index"
                        ::= { fkGponProfileVoIPPotsControl 6 }

                
--  1.3.6.1.4.1.10428 9 1.101.23.5.5.4.2.7
                -- 1.3.6.1.4.1.10428 9 1.101.23.5.5.4.2.7
                fkGponProfileVoIPPotsControlPotsIndex OBJECT-TYPE
                        SYNTAX Integer32
                        MAX-ACCESS read-write
                        STATUS current
                        DESCRIPTION
                                "Pptp Pots Index"
                        ::= { fkGponProfileVoIPPotsControl 7 }

                
--  1.3.6.1.4.1.10428 9 1.101.23.5.5.4.2.8
                -- 1.3.6.1.4.1.10428 9 1.101.23.5.5.4.2.8
                fkGponProfileVoIPPotsControlAdmin OBJECT-TYPE
                        SYNTAX EnableFlag
                        MAX-ACCESS read-write
                        STATUS current
                        DESCRIPTION
                                "State of ONU Pots Administratoration"
                        ::= { fkGponProfileVoIPPotsControl 8 }

                
--  1.3.6.1.4.1.10428 9 1.101.23.5.5.4.3
                -- 1.3.6.1.4.1.10428 9 1.101.23.5.5.4.3
                fkGponProfileVoIPPotsNotification OBJECT IDENTIFIER ::= { fkGponProfileVoIPPots 3 }

                
--  1.3.6.1.4.1.10428 9 1.101.23.5.5.4.3.1
                -- 1.3.6.1.4.1.10428 9 1.101.23.5.5.4.3.1
                fkGponProfileVoIPPotsAdded NOTIFICATION-TYPE
                        OBJECTS { fkGponProfileVoIPPotsControlReqResult, fkGponProfileVoIPPotsControlTimeStamp, fkGponProfileVoIPPotsControlProfileIndex, fkGponProfileVoIPPotsControlPotsIndex, fkGponProfileVoIPPotsControlAdmin
                                 }
                        STATUS current
                        DESCRIPTION 
                                "Description."
                        ::= { fkGponProfileVoIPPotsNotification 1 }

                
--  1.3.6.1.4.1.10428 9 1.101.23.5.5.4.3.2
                -- 1.3.6.1.4.1.10428 9 1.101.23.5.5.4.3.2
                fkGponProfileVoIPPotsDeleted NOTIFICATION-TYPE
                        OBJECTS { fkGponProfileVoIPPotsControlRequest, fkGponProfileVoIPPotsControlTimeStamp, fkGponProfileVoIPPotsControlReqResult, fkGponProfileVoIPPotsControlProfileIndex, fkGponProfileVoIPPotsControlPotsIndex
                                 }
                        STATUS current
                        DESCRIPTION 
                                "Description."
                        ::= { fkGponProfileVoIPPotsNotification 2 }

                
--  1.3.6.1.4.1.10428 9 1.101.23.5.5.1
                -- 1.3.6.1.4.1.10428 9 1.101.23.5.5.5
                fkGponProfileVoIPDetail OBJECT IDENTIFIER ::= { fkGponVoIP 5 }

                
--  1.3.6.1.4.1.10428 9 1.101.23.5.5.1.1
                -- 1.3.6.1.4.1.10428 9 1.101.23.5.5.5.1
                fkGponProfileVoIPDetailTable OBJECT-TYPE
                        SYNTAX SEQUENCE OF FkGponProfileVoIPDetailEntry
                        MAX-ACCESS not-accessible
                        STATUS current
                        DESCRIPTION
                                "fkGponProfileVoIPDetailTable"
                        ::= { fkGponProfileVoIPDetail 1 }

                
--  1.3.6.1.4.1.10428 9 1.101.23.5.5.1.1.1
                -- 1.3.6.1.4.1.10428 9 1.101.23.5.5.5.1.1
                fkGponProfileVoIPDetailEntry OBJECT-TYPE
                        SYNTAX FkGponProfileVoIPDetailEntry
                        MAX-ACCESS not-accessible
                        STATUS current
                        DESCRIPTION
                                "key: fkGponProfileVoIPDetailIndex"
                        INDEX { fkGponProfileVoIPDetailIndex }
                        ::= { fkGponProfileVoIPDetailTable 1 }

                
                FkGponProfileVoIPDetailEntry ::=
                        SEQUENCE { 
                                fkGponProfileVoIPDetailIndex
                                        INTEGER,
                                fkGponProfileVoIPDetailName
                                        OCTET STRING,
                                fkGponProfileVoIPDetailFaxMode
                                        INTEGER,
                                fkGponProfileVoIPDetailCodecType1st
                                        INTEGER,
                                fkGponProfileVoIPDetailCodecPeriod1st
                                        INTEGER,
                                fkGponProfileVoIPDetailCodecSilenceSuppression1st
                                        INTEGER,
                                fkGponProfileVoIPDetailCodecType2nd
                                        INTEGER,
                                fkGponProfileVoIPDetailCodecPeriod2nd
                                        INTEGER,
                                fkGponProfileVoIPDetailCodecSilenceSuppression2nd
                                        INTEGER,
                                fkGponProfileVoIPDetailCodecType3rd
                                        INTEGER,
                                fkGponProfileVoIPDetailCodecPeriod3rd
                                        INTEGER,
                                fkGponProfileVoIPDetailCodecSilenceSuppression3rd
                                        INTEGER,
                                fkGponProfileVoIPDetailCodecType4th
                                        INTEGER,
                                fkGponProfileVoIPDetailCodecPeriod4th
                                        INTEGER,
                                fkGponProfileVoIPDetailCodecSilenceSuppression4th
                                        INTEGER,
                                fkGponProfileVoIPDetailOobdtmf
                                        INTEGER,
                                fkGponProfileVoIPDetailAnnouncementType
                                        INTEGER,
                                fkGponProfileVoIPDetailJitterTarget
                                        INTEGER,
                                fkGponProfileVoIPDetailJitterBuffMax
                                        INTEGER,
                                fkGponProfileVoIPDetailEchoCancel
                                        INTEGER,
                                fkGponProfileVoIPDetailPstnProtoVariant
                                        INTEGER,
                                fkGponProfileVoIPDetailDtmfDigitLevels
                                        INTEGER,
                                fkGponProfileVoIPDetailDtmfDigitDuration
                                        INTEGER,
                                fkGponProfileVoIPDetailHookFlashTimeMin
                                        INTEGER,
                                fkGponProfileVoIPDetailHookFlashTimeMax
                                        INTEGER,
                                fkGponProfileVoIPDetailSignalingCode
                                        INTEGER,
                                fkGponProfileVoIPDetailRtpLocalPortMin
                                        INTEGER,
                                fkGponProfileVoIPDetailRtpLocalPortMax
                                        INTEGER,
                                fkGponProfileVoIPDetailRtpDscpMark
                                        INTEGER,
                                fkGponProfileVoIPDetailRtpPiggybackEvent
                                        INTEGER,
                                fkGponProfileVoIPDetailRtpToneEvent
                                        INTEGER,
                                fkGponProfileVoIPDetailRtpDtmfEvent
                                        INTEGER,
                                fkGponProfileVoIPDetailRtpCasEvent
                                        INTEGER,
                                fkGponProfileVoIPDetailProtocol
                                        INTEGER,
                                fkGponProfileVoIPDetailMgcPriServer
                                        OCTET STRING,
                                fkGponProfileVoIPDetailMgcSecServer
                                        OCTET STRING,
                                fkGponProfileVoIPDetailMgcMsgVersion
                                        INTEGER,
                                fkGponProfileVoIPDetailMgcMsgFormat
                                        INTEGER,
                                fkGponProfileVoIPDetailMgcMaxRetryTime
                                        INTEGER,
                                fkGponProfileVoIPDetailMgcMaxRetryAttempts
                                        INTEGER,
                                fkGponProfileVoIPDetailMgcSvcChangeDelay
                                        INTEGER,
                                fkGponProfileVoIPDetailMgcTerminationId
                                        OCTET STRING,
                                fkGponProfileVoIPDetailMgcSoftswitch
                                        OCTET STRING,
                                fkGponProfileVoIPDetailVoicemailServer
                                        OCTET STRING,
                                fkGponProfileVoIPDetailVoicemmailExpireTime
                                        INTEGER,
                                fkGponProfileVoIPDetailReleaseTime
                                        INTEGER,
                                fkGponProfileVoIPDetailRohTimer
                                        INTEGER,
                                fkGponProfileVoIPDetailProxyServer
                                        OCTET STRING,
                                fkGponProfileVoIPDetailOutboundProxyServer
                                        OCTET STRING,
                                fkGponProfileVoIPDetailRegisterServer
                                        OCTET STRING,
                                fkGponProfileVoIPDetailHostPartServer
                                        OCTET STRING,
                                fkGponProfileVoIPDetailPriDns
                                        IpAddress,
                                fkGponProfileVoIPDetailSecDns
                                        IpAddress,
                                fkGponProfileVoIPDetailRegExpTime
                                        INTEGER,
                                fkGponProfileVoIPDetailReregHeadStartTime
                                        INTEGER,
                                fkGponProfileVoIPDetailSoftSwitchVendor
                                        OCTET STRING,
                                fkGponProfileVoIPDetailSipOptionTransmitCtl
                                        INTEGER,
                                fkGponProfileVoIPDetailSipUriFormat
                                        INTEGER,
                                fkGponProfileVoIPDetailCallerId
                                        BITS,
                                fkGponProfileVoIPDetailCallWaiting
                                        BITS,
                                fkGponProfileVoIPDetailCallProgressTransfer
                                        BITS,
                                fkGponProfileVoIPDetailCallPresent
                                        BITS,
                                fkGponProfileVoIPDetailDirectConnect
                                        INTEGER,
                                fkGponProfileVoIPDetailDirectConnectUri
                                        OCTET STRING,
                                fkGponProfileVoIPDetailBridgedLineAgentUri
                                        OCTET STRING,
                                fkGponProfileVoIPDetailConferenceFactoryUri
                                        OCTET STRING,
                                fkGponProfileVoIPDetailCancelCallWait
                                        OCTET STRING,
                                fkGponProfileVoIPDetailCallHold
                                        OCTET STRING,
                                fkGponProfileVoIPDetailCallPark
                                        OCTET STRING,
                                fkGponProfileVoIPDetailCallerIdAct
                                        OCTET STRING,
                                fkGponProfileVoIPDetailCallerIdDeact
                                        OCTET STRING,
                                fkGponProfileVoIPDetailDoNotDisturbAct
                                        OCTET STRING,
                                fkGponProfileVoIPDetailDoNotDisturbDeact
                                        OCTET STRING,
                                fkGponProfileVoIPDetailDoNotDisturbPinChange
                                        OCTET STRING,
                                fkGponProfileVoIPDetailEmergServiceNumber
                                        OCTET STRING,
                                fkGponProfileVoIPDetailIntercomService
                                        OCTET STRING,
                                fkGponProfileVoIPDetailDialplanCritTimeout
                                        INTEGER,
                                fkGponProfileVoIPDetailDialplanPartTimeout
                                        INTEGER,
                                fkGponProfileVoIPDetailDialplanFormat
                                        INTEGER,
                                fkGponProfileVoIPDetailSpecialLineService
                                        INTEGER,
                                fkGponProfileVoIPDetailWarmLineTimeout
                                        Integer32,
                                fkGponProfileVoIPDetailLineNumber
                                        OCTET STRING,
                                fkGponProfileVoIPDetailThreeWaySSWMixing
                                        INTEGER,
                                fkGponProfileVoIPDetailSIPDNSCache
                                        INTEGER,
                                fkGponProfileVoIPDetailSIPTimerT1
                                        Integer32,
                                fkGponProfileVoIPDetailSIPTimerT2
                                        Integer32,
                                fkGponProfileVoIPDetailSIPTimerTd
                                        Integer32,
                                fkGponProfileVoIPDetailSIPSessionTimer
                                        INTEGER,
                                fkGponProfileVoIPDetailSIPSessionTimeout
                                        Integer32,
                                fkGponProfileVoIPDetailSIPEndOfDigit
                                        INTEGER,
                                fkGponProfileVoIPDetailSIPEndSharpToken
                                        INTEGER
                         }

--  1.3.6.1.4.1.10428 9 1.101.23.5.5.1.1.1.1
                -- 1.3.6.1.4.1.10428 9 1.101.23.5.5.5.1.1.1
                fkGponProfileVoIPDetailIndex OBJECT-TYPE
                        SYNTAX INTEGER (1..65535)
                        MAX-ACCESS read-only
                        STATUS current
                        DESCRIPTION
                                "VoIP Profile Index."
                        ::= { fkGponProfileVoIPDetailEntry 1 }

                
--  1.3.6.1.4.1.10428 9 1.101.23.5.5.1.1.1.2
                -- 1.3.6.1.4.1.10428 9 1.101.23.5.5.5.1.1.2
                fkGponProfileVoIPDetailName OBJECT-TYPE
                        SYNTAX OCTET STRING
                        MAX-ACCESS read-only
                        STATUS current
                        DESCRIPTION
                                "VoIP profile name."
                        ::= { fkGponProfileVoIPDetailEntry 2 }

                
--  1.3.6.1.4.1.10428 9 1.101.23.5.5.1.1.1.3
                -- 1.3.6.1.4.1.10428 9 1.101.23.5.5.5.1.1.3
                fkGponProfileVoIPDetailFaxMode OBJECT-TYPE
                        SYNTAX INTEGER
                                {
                                passthru(0),
                                t38(1)
                                }
                        MAX-ACCESS read-only
                        STATUS current
                        DESCRIPTION
                                "VoIP fax mode."
                        ::= { fkGponProfileVoIPDetailEntry 3 }

                
--  1.3.6.1.4.1.10428 9 1.101.23.5.5.1.1.1.4
                -- 1.3.6.1.4.1.10428 9 1.101.23.5.5.5.1.1.4
                fkGponProfileVoIPDetailCodecType1st OBJECT-TYPE
                        SYNTAX INTEGER
                                {
                                pcmu(0),
                                gsm(3),
                                g723(4),
                                dvi4and8k(5),
                                dvi4and16k(6),
                                lpc(7),
                                pcma(8),
                                g722(9),
                                l16and2ch(10),
                                l16and1h(11),
                                qcelp(12),
                                cn(13),
                                mpa(14),
                                g728(15),
                                dvi4and11k(16),
                                dvi4and22k(17),
                                g729(18)
                                }
                        MAX-ACCESS read-only
                        STATUS current
                        DESCRIPTION
                                "VoIP codec type 1st."
                        ::= { fkGponProfileVoIPDetailEntry 4 }

                
--  1.3.6.1.4.1.10428 9 1.101.23.5.5.1.1.1.5
                -- 1.3.6.1.4.1.10428 9 1.101.23.5.5.5.1.1.5
                fkGponProfileVoIPDetailCodecPeriod1st OBJECT-TYPE
                        SYNTAX INTEGER (1..65535)
                        MAX-ACCESS read-only
                        STATUS current
                        DESCRIPTION
                                "Codec sampling period1st"
                        ::= { fkGponProfileVoIPDetailEntry 5 }

                
--  1.3.6.1.4.1.10428 9 1.101.23.5.5.1.1.1.5
                -- 1.3.6.1.4.1.10428 9 1.101.23.5.5.5.1.1.6
                fkGponProfileVoIPDetailCodecSilenceSuppression1st OBJECT-TYPE
                        SYNTAX INTEGER (1..65535)
                        MAX-ACCESS read-only
                        STATUS current
                        DESCRIPTION
                                "VoIP codec silence suppression 1st"
                        ::= { fkGponProfileVoIPDetailEntry 6 }

                
--  1.3.6.1.4.1.10428 9 1.101.23.5.5.1.1.1.5
                -- 1.3.6.1.4.1.10428 9 1.101.23.5.5.5.1.1.7
                fkGponProfileVoIPDetailCodecType2nd OBJECT-TYPE
                        SYNTAX INTEGER
                                {
                                pcmu(0),
                                gsm(3),
                                g723(4),
                                dvi4and8k(5),
                                dvi4and16k(6),
                                lpc(7),
                                pcma(8),
                                g722(9),
                                l16and2ch(10),
                                l16and1h(11),
                                qcelp(12),
                                cn(13),
                                mpa(14),
                                g728(15),
                                dvi4and11k(16),
                                dvi4and22k(17),
                                g729(18)
                                }
                        MAX-ACCESS read-only
                        STATUS current
                        DESCRIPTION
                                "VoIP codec type 2nd"
                        ::= { fkGponProfileVoIPDetailEntry 7 }

                
--  1.3.6.1.4.1.10428 9 1.101.23.5.5.1.1.1.5
                -- 1.3.6.1.4.1.10428 9 1.101.23.5.5.5.1.1.8
                fkGponProfileVoIPDetailCodecPeriod2nd OBJECT-TYPE
                        SYNTAX INTEGER (1..65535)
                        MAX-ACCESS read-only
                        STATUS current
                        DESCRIPTION
                                "Codec sampling period 2nd"
                        ::= { fkGponProfileVoIPDetailEntry 8 }

                
--  1.3.6.1.4.1.10428 9 1.101.23.5.5.1.1.1.5
                -- 1.3.6.1.4.1.10428 9 1.101.23.5.5.5.1.1.9
                fkGponProfileVoIPDetailCodecSilenceSuppression2nd OBJECT-TYPE
                        SYNTAX INTEGER (1..65535)
                        MAX-ACCESS read-only
                        STATUS current
                        DESCRIPTION
                                "VoIP codec silence suppression 2nd"
                        ::= { fkGponProfileVoIPDetailEntry 9 }

                
--  1.3.6.1.4.1.10428 9 1.101.23.5.5.1.1.1.5
                -- 1.3.6.1.4.1.10428 9 1.101.23.5.5.5.1.1.10
                fkGponProfileVoIPDetailCodecType3rd OBJECT-TYPE
                        SYNTAX INTEGER
                                {
                                pcmu(0),
                                gsm(3),
                                g723(4),
                                dvi4and8k(5),
                                dvi4and16k(6),
                                lpc(7),
                                pcma(8),
                                g722(9),
                                l16and2ch(10),
                                l16and1h(11),
                                qcelp(12),
                                cn(13),
                                mpa(14),
                                g728(15),
                                dvi4and11k(16),
                                dvi4and22k(17),
                                g729(18)
                                }
                        MAX-ACCESS read-only
                        STATUS current
                        DESCRIPTION
                                "VoIP codec type 3rd"
                        ::= { fkGponProfileVoIPDetailEntry 10 }

                
--  1.3.6.1.4.1.10428 9 1.101.23.5.5.1.1.1.5
                -- 1.3.6.1.4.1.10428 9 1.101.23.5.5.5.1.1.11
                fkGponProfileVoIPDetailCodecPeriod3rd OBJECT-TYPE
                        SYNTAX INTEGER (1..65535)
                        MAX-ACCESS read-only
                        STATUS current
                        DESCRIPTION
                                "Codec sampling period 3rd"
                        ::= { fkGponProfileVoIPDetailEntry 11 }

                
--  1.3.6.1.4.1.10428 9 1.101.23.5.5.1.1.1.5
                -- 1.3.6.1.4.1.10428 9 1.101.23.5.5.5.1.1.12
                fkGponProfileVoIPDetailCodecSilenceSuppression3rd OBJECT-TYPE
                        SYNTAX INTEGER (1..65535)
                        MAX-ACCESS read-only
                        STATUS current
                        DESCRIPTION
                                "VoIP codec silence suppression 3rd."
                        ::= { fkGponProfileVoIPDetailEntry 12 }

                
--  1.3.6.1.4.1.10428 9 1.101.23.5.5.1.1.1.5
                -- 1.3.6.1.4.1.10428 9 1.101.23.5.5.5.1.1.13
                fkGponProfileVoIPDetailCodecType4th OBJECT-TYPE
                        SYNTAX INTEGER
                                {
                                pcmu(0),
                                gsm(3),
                                g723(4),
                                dvi4and8k(5),
                                dvi4and16k(6),
                                lpc(7),
                                pcma(8),
                                g722(9),
                                l16and2ch(10),
                                l16and1h(11),
                                qcelp(12),
                                cn(13),
                                mpa(14),
                                g728(15),
                                dvi4and11k(16),
                                dvi4and22k(17),
                                g729(18)
                                }
                        MAX-ACCESS read-only
                        STATUS current
                        DESCRIPTION
                                "VoIP codec type 4th"
                        ::= { fkGponProfileVoIPDetailEntry 13 }

                
--  1.3.6.1.4.1.10428 9 1.101.23.5.5.1.1.1.5
                -- 1.3.6.1.4.1.10428 9 1.101.23.5.5.5.1.1.14
                fkGponProfileVoIPDetailCodecPeriod4th OBJECT-TYPE
                        SYNTAX INTEGER (1..65535)
                        MAX-ACCESS read-only
                        STATUS current
                        DESCRIPTION
                                "Codec sampling period 4th"
                        ::= { fkGponProfileVoIPDetailEntry 14 }

                
--  1.3.6.1.4.1.10428 9 1.101.23.5.5.1.1.1.5
                -- 1.3.6.1.4.1.10428 9 1.101.23.5.5.5.1.1.15
                fkGponProfileVoIPDetailCodecSilenceSuppression4th OBJECT-TYPE
                        SYNTAX INTEGER (1..65535)
                        MAX-ACCESS read-only
                        STATUS current
                        DESCRIPTION
                                "VoIP codec silence suppression 4th."
                        ::= { fkGponProfileVoIPDetailEntry 15 }

                
--  1.3.6.1.4.1.10428 9 1.101.23.5.5.1.1.1.5
                -- 1.3.6.1.4.1.10428 9 1.101.23.5.5.5.1.1.16
                fkGponProfileVoIPDetailOobdtmf OBJECT-TYPE
                        SYNTAX INTEGER
                                {
                                disable(0),
                                enable(1)
                                }
                        MAX-ACCESS read-only
                        STATUS current
                        DESCRIPTION
                                "Control DTMF(Dual Tone Multi-Frequency)"
                        ::= { fkGponProfileVoIPDetailEntry 16 }

                
--  1.3.6.1.4.1.10428 9 1.101.23.5.5.1.1.1.5
                -- 1.3.6.1.4.1.10428 9 1.101.23.5.5.5.1.1.17
                fkGponProfileVoIPDetailAnnouncementType OBJECT-TYPE
                        SYNTAX INTEGER
                                {
                                silence(1),
                                reorderTone(2),
                                fastBusy(3),
                                voiceAnnouncement(4)
                                }
                        MAX-ACCESS read-only
                        STATUS current
                        DESCRIPTION
                                "VoIp announcement type"
                        ::= { fkGponProfileVoIPDetailEntry 17 }

                
--  1.3.6.1.4.1.10428 9 1.101.23.5.5.1.1.1.5
                -- 1.3.6.1.4.1.10428 9 1.101.23.5.5.5.1.1.18
                fkGponProfileVoIPDetailJitterTarget OBJECT-TYPE
                        SYNTAX INTEGER (1..65535)
                        MAX-ACCESS read-only
                        STATUS current
                        DESCRIPTION
                                "Jitter target (milliseconds)"
                        ::= { fkGponProfileVoIPDetailEntry 18 }

                
--  1.3.6.1.4.1.10428 9 1.101.23.5.5.1.1.1.5
                -- 1.3.6.1.4.1.10428 9 1.101.23.5.5.5.1.1.19
                fkGponProfileVoIPDetailJitterBuffMax OBJECT-TYPE
                        SYNTAX INTEGER (0..65535)
                        MAX-ACCESS read-only
                        STATUS current
                        DESCRIPTION
                                "VoIP jitter buffer max."
                        ::= { fkGponProfileVoIPDetailEntry 19 }

                
--  1.3.6.1.4.1.10428 9 1.101.23.5.5.1.1.1.5
                -- 1.3.6.1.4.1.10428 9 1.101.23.5.5.5.1.1.20
                fkGponProfileVoIPDetailEchoCancel OBJECT-TYPE
                        SYNTAX INTEGER
                                {
                                false(0),
                                true(1)
                                }
                        MAX-ACCESS read-only
                        STATUS current
                        DESCRIPTION
                                "VoIP echo cancel"
                        ::= { fkGponProfileVoIPDetailEntry 20 }

                
--  1.3.6.1.4.1.10428 9 1.101.23.5.5.1.1.1.5
                -- 1.3.6.1.4.1.10428 9 1.101.23.5.5.5.1.1.21
                fkGponProfileVoIPDetailPstnProtoVariant OBJECT-TYPE
                        SYNTAX INTEGER (1..65535)
                        MAX-ACCESS read-only
                        STATUS current
                        DESCRIPTION
                                "PSTN Protocol Variant"
                        ::= { fkGponProfileVoIPDetailEntry 21 }

                
--  1.3.6.1.4.1.10428 9 1.101.23.5.5.1.1.1.5
                -- 1.3.6.1.4.1.10428 9 1.101.23.5.5.5.1.1.22
                fkGponProfileVoIPDetailDtmfDigitLevels OBJECT-TYPE
                        SYNTAX INTEGER (0..65535)
                        MAX-ACCESS read-only
                        STATUS current
                        DESCRIPTION
                                "DTMF digit Power Level configuration "
                        ::= { fkGponProfileVoIPDetailEntry 22 }

                
--  1.3.6.1.4.1.10428 9 1.101.23.5.5.1.1.1.5
                -- 1.3.6.1.4.1.10428 9 1.101.23.5.5.5.1.1.23
                fkGponProfileVoIPDetailDtmfDigitDuration OBJECT-TYPE
                        SYNTAX INTEGER (0..65535)
                        MAX-ACCESS read-only
                        STATUS current
                        DESCRIPTION
                                "DTMF digit Power Duration configuration"
                        ::= { fkGponProfileVoIPDetailEntry 23 }

                
--  1.3.6.1.4.1.10428 9 1.101.23.5.5.1.1.1.5
                -- 1.3.6.1.4.1.10428 9 1.101.23.5.5.5.1.1.24
                fkGponProfileVoIPDetailHookFlashTimeMin OBJECT-TYPE
                        SYNTAX INTEGER (0..65535)
                        MAX-ACCESS read-only
                        STATUS current
                        DESCRIPTION
                                "VoIP hook Flash Time Minimum"
                        ::= { fkGponProfileVoIPDetailEntry 24 }

                
--  1.3.6.1.4.1.10428 9 1.101.23.5.5.1.1.1.5
                -- 1.3.6.1.4.1.10428 9 1.101.23.5.5.5.1.1.25
                fkGponProfileVoIPDetailHookFlashTimeMax OBJECT-TYPE
                        SYNTAX INTEGER (0..65535)
                        MAX-ACCESS read-only
                        STATUS current
                        DESCRIPTION
                                "VoIP hook Flash Time Maximum"
                        ::= { fkGponProfileVoIPDetailEntry 25 }

                
--  1.3.6.1.4.1.10428 9 1.101.23.5.5.1.1.1.5
                -- 1.3.6.1.4.1.10428 9 1.101.23.5.5.5.1.1.26
                fkGponProfileVoIPDetailSignalingCode OBJECT-TYPE
                        SYNTAX INTEGER
                                {
                                loopStart(1),
                                groundStart(2),
                                loopReverseBattery(3),
                                coinFirst(4),
                                dialToneFirst(5),
                                multiParty(6)
                                }
                        MAX-ACCESS read-only
                        STATUS current
                        DESCRIPTION
                                "VoIP signaling code."
                        ::= { fkGponProfileVoIPDetailEntry 26 }

                
--  1.3.6.1.4.1.10428 9 1.101.23.5.5.1.1.1.5
                -- 1.3.6.1.4.1.10428 9 1.101.23.5.5.5.1.1.27
                fkGponProfileVoIPDetailRtpLocalPortMin OBJECT-TYPE
                        SYNTAX INTEGER (1..65535)
                        MAX-ACCESS read-only
                        STATUS current
                        DESCRIPTION
                                "RTP Local Port Min"
                        ::= { fkGponProfileVoIPDetailEntry 27 }

                
--  1.3.6.1.4.1.10428 9 1.101.23.5.5.1.1.1.5
                -- 1.3.6.1.4.1.10428 9 1.101.23.5.5.5.1.1.28
                fkGponProfileVoIPDetailRtpLocalPortMax OBJECT-TYPE
                        SYNTAX INTEGER (1..65535)
                        MAX-ACCESS read-only
                        STATUS current
                        DESCRIPTION
                                "RTP Local Port Max"
                        ::= { fkGponProfileVoIPDetailEntry 28 }

                
                -- 1.3.6.1.4.1.10428 9 1.101.23.5.5.5.1.1.29
                fkGponProfileVoIPDetailRtpDscpMark OBJECT-TYPE
                        SYNTAX INTEGER (1..65535)
                        MAX-ACCESS read-only
                        STATUS current
                        DESCRIPTION
                                "RTP DSCP Mark"
                        ::= { fkGponProfileVoIPDetailEntry 29 }

                
                -- 1.3.6.1.4.1.10428 9 1.101.23.5.5.5.1.1.30
                fkGponProfileVoIPDetailRtpPiggybackEvent OBJECT-TYPE
                        SYNTAX INTEGER
                                {
                                disable(0),
                                enable(1)
                                }
                        MAX-ACCESS read-only
                        STATUS current
                        DESCRIPTION
                                "RTP Piggyback event"
                        ::= { fkGponProfileVoIPDetailEntry 30 }

                
                -- 1.3.6.1.4.1.10428 9 1.101.23.5.5.5.1.1.31
                fkGponProfileVoIPDetailRtpToneEvent OBJECT-TYPE
                        SYNTAX INTEGER
                                {
                                disable(0),
                                enable(1)
                                }
                        MAX-ACCESS read-only
                        STATUS current
                        DESCRIPTION
                                "RTP Tone event"
                        ::= { fkGponProfileVoIPDetailEntry 31 }

                
                -- 1.3.6.1.4.1.10428 9 1.101.23.5.5.5.1.1.32
                fkGponProfileVoIPDetailRtpDtmfEvent OBJECT-TYPE
                        SYNTAX INTEGER
                                {
                                disable(0),
                                enable(1)
                                }
                        MAX-ACCESS read-only
                        STATUS current
                        DESCRIPTION
                                "RTP DTMF event"
                        ::= { fkGponProfileVoIPDetailEntry 32 }

                
                -- 1.3.6.1.4.1.10428 9 1.101.23.5.5.5.1.1.33
                fkGponProfileVoIPDetailRtpCasEvent OBJECT-TYPE
                        SYNTAX INTEGER
                                {
                                disable(0),
                                enable(1)
                                }
                        MAX-ACCESS read-only
                        STATUS current
                        DESCRIPTION
                                "RTP CAS events"
                        ::= { fkGponProfileVoIPDetailEntry 33 }

                
                -- 1.3.6.1.4.1.10428 9 1.101.23.5.5.5.1.1.34
                fkGponProfileVoIPDetailProtocol OBJECT-TYPE
                        SYNTAX INTEGER
                                {
                                none(0),
                                sip(1),
                                h248(2),
                                mgcp(3)
                                }
                        MAX-ACCESS read-only
                        STATUS current
                        DESCRIPTION
                                "VoIP Protocol configuration"
                        ::= { fkGponProfileVoIPDetailEntry 34 }

                
                -- 1.3.6.1.4.1.10428 9 1.101.23.5.5.5.1.1.35
                fkGponProfileVoIPDetailMgcPriServer OBJECT-TYPE
                        SYNTAX OCTET STRING
                        MAX-ACCESS read-only
                        STATUS current
                        DESCRIPTION
                                "The primary server name."
                        ::= { fkGponProfileVoIPDetailEntry 35 }

                
                -- 1.3.6.1.4.1.10428 9 1.101.23.5.5.5.1.1.36
                fkGponProfileVoIPDetailMgcSecServer OBJECT-TYPE
                        SYNTAX OCTET STRING
                        MAX-ACCESS read-only
                        STATUS current
                        DESCRIPTION
                                "The secondary server name."
                        ::= { fkGponProfileVoIPDetailEntry 36 }

                
                -- 1.3.6.1.4.1.10428 9 1.101.23.5.5.5.1.1.37
                fkGponProfileVoIPDetailMgcMsgVersion OBJECT-TYPE
                        SYNTAX INTEGER (1..255)
                        MAX-ACCESS read-only
                        STATUS current
                        DESCRIPTION
                                "The message version."
                        ::= { fkGponProfileVoIPDetailEntry 37 }

                
                -- 1.3.6.1.4.1.10428 9 1.101.23.5.5.5.1.1.38
                fkGponProfileVoIPDetailMgcMsgFormat OBJECT-TYPE
                        SYNTAX INTEGER
                                {
                                textLong(0),
                                textShort(1),
                                binary(2)
                                }
                        MAX-ACCESS read-only
                        STATUS current
                        DESCRIPTION
                                "The message format.
                                0:textLong
                                1:textShort
                                2:binary"
                        ::= { fkGponProfileVoIPDetailEntry 38 }

                
                -- 1.3.6.1.4.1.10428 9 1.101.23.5.5.5.1.1.39
                fkGponProfileVoIPDetailMgcMaxRetryTime OBJECT-TYPE
                        SYNTAX INTEGER (0..65535)
                        MAX-ACCESS read-only
                        STATUS current
                        DESCRIPTION
                                "The max retry time.
                                65535: unused"
                        ::= { fkGponProfileVoIPDetailEntry 39 }

                
                -- 1.3.6.1.4.1.10428 9 1.101.23.5.5.5.1.1.40
                fkGponProfileVoIPDetailMgcMaxRetryAttempts OBJECT-TYPE
                        SYNTAX INTEGER (0..65535)
                        MAX-ACCESS read-only
                        STATUS current
                        DESCRIPTION
                                "The max retry attemption
                                65535: unused"
                        ::= { fkGponProfileVoIPDetailEntry 40 }

                
                -- 1.3.6.1.4.1.10428 9 1.101.23.5.5.5.1.1.41
                fkGponProfileVoIPDetailMgcSvcChangeDelay OBJECT-TYPE
                        SYNTAX INTEGER (0..65535)
                        MAX-ACCESS read-only
                        STATUS current
                        DESCRIPTION
                                "The service change delay
                                65535: unused"
                        ::= { fkGponProfileVoIPDetailEntry 41 }

                
                -- 1.3.6.1.4.1.10428 9 1.101.23.5.5.5.1.1.42
                fkGponProfileVoIPDetailMgcTerminationId OBJECT-TYPE
                        SYNTAX OCTET STRING
                        MAX-ACCESS read-only
                        STATUS current
                        DESCRIPTION
                                "The termination id."
                        ::= { fkGponProfileVoIPDetailEntry 42 }

                
                -- 1.3.6.1.4.1.10428 9 1.101.23.5.5.5.1.1.43
                fkGponProfileVoIPDetailMgcSoftswitch OBJECT-TYPE
                        SYNTAX OCTET STRING
                        MAX-ACCESS read-only
                        STATUS current
                        DESCRIPTION
                                "The soft switch"
                        ::= { fkGponProfileVoIPDetailEntry 43 }

                
                -- 1.3.6.1.4.1.10428 9 1.101.23.5.5.5.1.1.44
                fkGponProfileVoIPDetailVoicemailServer OBJECT-TYPE
                        SYNTAX OCTET STRING
                        MAX-ACCESS read-only
                        STATUS current
                        DESCRIPTION
                                "VoIP voice mail server."
                        ::= { fkGponProfileVoIPDetailEntry 44 }

                
                -- 1.3.6.1.4.1.10428 9 1.101.23.5.5.5.1.1.45
                fkGponProfileVoIPDetailVoicemmailExpireTime OBJECT-TYPE
                        SYNTAX INTEGER (1..65535)
                        MAX-ACCESS read-only
                        STATUS current
                        DESCRIPTION
                                "VoIP voice mail Expire time"
                        ::= { fkGponProfileVoIPDetailEntry 45 }

                
                -- 1.3.6.1.4.1.10428 9 1.101.23.5.5.5.1.1.46
                fkGponProfileVoIPDetailReleaseTime OBJECT-TYPE
                        SYNTAX INTEGER (1..65535)
                        MAX-ACCESS read-only
                        STATUS current
                        DESCRIPTION
                                "VoIp release time"
                        ::= { fkGponProfileVoIPDetailEntry 46 }

                
                -- 1.3.6.1.4.1.10428 9 1.101.23.5.5.5.1.1.47
                fkGponProfileVoIPDetailRohTimer OBJECT-TYPE
                        SYNTAX INTEGER (1..65535)
                        MAX-ACCESS read-only
                        STATUS current
                        DESCRIPTION
                                "ROH timer"
                        ::= { fkGponProfileVoIPDetailEntry 47 }

                
                -- 1.3.6.1.4.1.10428 9 1.101.23.5.5.5.1.1.48
                fkGponProfileVoIPDetailProxyServer OBJECT-TYPE
                        SYNTAX OCTET STRING
                        MAX-ACCESS read-only
                        STATUS current
                        DESCRIPTION
                                "Proxy server address"
                        ::= { fkGponProfileVoIPDetailEntry 48 }

                
                -- 1.3.6.1.4.1.10428 9 1.101.23.5.5.5.1.1.49
                fkGponProfileVoIPDetailOutboundProxyServer OBJECT-TYPE
                        SYNTAX OCTET STRING
                        MAX-ACCESS read-only
                        STATUS current
                        DESCRIPTION
                                "Outbound proxy address"
                        ::= { fkGponProfileVoIPDetailEntry 49 }

                
                -- 1.3.6.1.4.1.10428 9 1.101.23.5.5.5.1.1.50
                fkGponProfileVoIPDetailRegisterServer OBJECT-TYPE
                        SYNTAX OCTET STRING
                        MAX-ACCESS read-only
                        STATUS current
                        DESCRIPTION
                                "VoIP register server"
                        ::= { fkGponProfileVoIPDetailEntry 50 }

                
                -- 1.3.6.1.4.1.10428 9 1.101.23.5.5.5.1.1.51
                fkGponProfileVoIPDetailHostPartServer OBJECT-TYPE
                        SYNTAX OCTET STRING
                        MAX-ACCESS read-only
                        STATUS current
                        DESCRIPTION
                                "VoIp host part server."
                        ::= { fkGponProfileVoIPDetailEntry 51 }

                
                -- 1.3.6.1.4.1.10428 9 1.101.23.5.5.5.1.1.52
                fkGponProfileVoIPDetailPriDns OBJECT-TYPE
                        SYNTAX IpAddress
                        MAX-ACCESS read-only
                        STATUS current
                        DESCRIPTION
                                "VoIP primary dns"
                        ::= { fkGponProfileVoIPDetailEntry 52 }

                
                -- 1.3.6.1.4.1.10428 9 1.101.23.5.5.5.1.1.53
                fkGponProfileVoIPDetailSecDns OBJECT-TYPE
                        SYNTAX IpAddress
                        MAX-ACCESS read-only
                        STATUS current
                        DESCRIPTION
                                "VoIP secondary dns"
                        ::= { fkGponProfileVoIPDetailEntry 53 }

                
                -- 1.3.6.1.4.1.10428 9 1.101.23.5.5.5.1.1.54
                fkGponProfileVoIPDetailRegExpTime OBJECT-TYPE
                        SYNTAX INTEGER (1..65535)
                        MAX-ACCESS read-only
                        STATUS current
                        DESCRIPTION
                                "Registration expiration time"
                        ::= { fkGponProfileVoIPDetailEntry 54 }

                
                -- 1.3.6.1.4.1.10428 9 1.101.23.5.5.5.1.1.55
                fkGponProfileVoIPDetailReregHeadStartTime OBJECT-TYPE
                        SYNTAX INTEGER (1..65535)
                        MAX-ACCESS read-only
                        STATUS current
                        DESCRIPTION
                                "Registration head start time"
                        ::= { fkGponProfileVoIPDetailEntry 55 }

                
                -- 1.3.6.1.4.1.10428 9 1.101.23.5.5.5.1.1.56
                fkGponProfileVoIPDetailSoftSwitchVendor OBJECT-TYPE
                        SYNTAX OCTET STRING
                        MAX-ACCESS read-only
                        STATUS current
                        DESCRIPTION
                                "Softswitch Vendor name"
                        ::= { fkGponProfileVoIPDetailEntry 56 }

                
                -- 1.3.6.1.4.1.10428 9 1.101.23.5.5.5.1.1.57
                fkGponProfileVoIPDetailSipOptionTransmitCtl OBJECT-TYPE
                        SYNTAX INTEGER
                                {
                                disable(0),
                                enable(1)
                                }
                        MAX-ACCESS read-only
                        STATUS current
                        DESCRIPTION
                                "Transmit control"
                        ::= { fkGponProfileVoIPDetailEntry 57 }

                
                -- 1.3.6.1.4.1.10428 9 1.101.23.5.5.5.1.1.58
                fkGponProfileVoIPDetailSipUriFormat OBJECT-TYPE
                        SYNTAX INTEGER
                                {
                                telUri(0),
                                sipUri(1)
                                }
                        MAX-ACCESS read-only
                        STATUS current
                        DESCRIPTION
                                "URI format"
                        ::= { fkGponProfileVoIPDetailEntry 58 }

                
                -- 1.3.6.1.4.1.10428 9 1.101.23.5.5.5.1.1.59
                fkGponProfileVoIPDetailCallerId OBJECT-TYPE
                        SYNTAX BITS
                                {
                                callNumber(0),
                                callName(1),
                                cidBlocking(2),
                                cidNumber(3),
                                cidName(4),
                                acr(5)
                                }
                        MAX-ACCESS read-only
                        STATUS current
                        DESCRIPTION
                                "Caller ID feature"
                        ::= { fkGponProfileVoIPDetailEntry 59 }

                
                -- 1.3.6.1.4.1.10428 9 1.101.23.5.5.5.1.1.60
                fkGponProfileVoIPDetailCallWaiting OBJECT-TYPE
                        SYNTAX BITS
                                {
                                callFeature(0),
                                cidAnnounce(1)
                                }
                        MAX-ACCESS read-only
                        STATUS current
                        DESCRIPTION
                                "Call waiting features"
                        ::= { fkGponProfileVoIPDetailEntry 60 }

                
                -- 1.3.6.1.4.1.10428 9 1.101.23.5.5.5.1.1.61
                fkGponProfileVoIPDetailCallProgressTransfer OBJECT-TYPE
                        SYNTAX BITS
                                {
                                threeWay(0),
                                callTransfer(1),
                                callHold(2),
                                callPark(3),
                                notDisturb(4),
                                flashEmergCall(5),
                                emergOriginatingHold(6)
                                }
                        MAX-ACCESS read-only
                        STATUS current
                        DESCRIPTION
                                "Call progress or transfer features"
                        ::= { fkGponProfileVoIPDetailEntry 61 }

                
                -- 1.3.6.1.4.1.10428 9 1.101.23.5.5.5.1.1.62
                fkGponProfileVoIPDetailCallPresent OBJECT-TYPE
                        SYNTAX BITS
                                {
                                splashRing(0),
                                dialTone(1),
                                visualIndicate(2),
                                callForward(3)
                                }
                        MAX-ACCESS read-only
                        STATUS current
                        DESCRIPTION
                                "Call presentation features"
                        ::= { fkGponProfileVoIPDetailEntry 62 }

                
                -- 1.3.6.1.4.1.10428 9 1.101.23.5.5.5.1.1.63
                fkGponProfileVoIPDetailDirectConnect OBJECT-TYPE
                        SYNTAX INTEGER
                                {
                                disable(0),
                                enable(1),
                                delayOption(2)
                                }
                        MAX-ACCESS read-only
                        STATUS current
                        DESCRIPTION
                                "Direct connect feature"
                        ::= { fkGponProfileVoIPDetailEntry 63 }

                
                -- 1.3.6.1.4.1.10428 9 1.101.23.5.5.5.1.1.64
                fkGponProfileVoIPDetailDirectConnectUri OBJECT-TYPE
                        SYNTAX OCTET STRING
                        MAX-ACCESS read-only
                        STATUS current
                        DESCRIPTION
                                "Direct connect URI"
                        ::= { fkGponProfileVoIPDetailEntry 64 }

                
                -- 1.3.6.1.4.1.10428 9 1.101.23.5.5.5.1.1.65
                fkGponProfileVoIPDetailBridgedLineAgentUri OBJECT-TYPE
                        SYNTAX OCTET STRING
                        MAX-ACCESS read-only
                        STATUS current
                        DESCRIPTION
                                "Bridged line agent URI"
                        ::= { fkGponProfileVoIPDetailEntry 65 }

                
                -- 1.3.6.1.4.1.10428 9 1.101.23.5.5.5.1.1.66
                fkGponProfileVoIPDetailConferenceFactoryUri OBJECT-TYPE
                        SYNTAX OCTET STRING
                        MAX-ACCESS read-only
                        STATUS current
                        DESCRIPTION
                                "Conference factory URI"
                        ::= { fkGponProfileVoIPDetailEntry 66 }

                
                -- 1.3.6.1.4.1.10428 9 1.101.23.5.5.5.1.1.67
                fkGponProfileVoIPDetailCancelCallWait OBJECT-TYPE
                        SYNTAX OCTET STRING
                        MAX-ACCESS read-only
                        STATUS current
                        DESCRIPTION
                                "Cancel call waiting"
                        ::= { fkGponProfileVoIPDetailEntry 67 }

                
                -- 1.3.6.1.4.1.10428 9 1.101.23.5.5.5.1.1.68
                fkGponProfileVoIPDetailCallHold OBJECT-TYPE
                        SYNTAX OCTET STRING
                        MAX-ACCESS read-only
                        STATUS current
                        DESCRIPTION
                                "Call hold"
                        ::= { fkGponProfileVoIPDetailEntry 68 }

                
                -- 1.3.6.1.4.1.10428 9 1.101.23.5.5.5.1.1.69
                fkGponProfileVoIPDetailCallPark OBJECT-TYPE
                        SYNTAX OCTET STRING
                        MAX-ACCESS read-only
                        STATUS current
                        DESCRIPTION
                                "Call park"
                        ::= { fkGponProfileVoIPDetailEntry 69 }

                
                -- 1.3.6.1.4.1.10428 9 1.101.23.5.5.5.1.1.70
                fkGponProfileVoIPDetailCallerIdAct OBJECT-TYPE
                        SYNTAX OCTET STRING
                        MAX-ACCESS read-only
                        STATUS current
                        DESCRIPTION
                                "Caller ID activate"
                        ::= { fkGponProfileVoIPDetailEntry 70 }

                
                -- 1.3.6.1.4.1.10428 9 1.101.23.5.5.5.1.1.71
                fkGponProfileVoIPDetailCallerIdDeact OBJECT-TYPE
                        SYNTAX OCTET STRING
                        MAX-ACCESS read-only
                        STATUS current
                        DESCRIPTION
                                "Caller ID deactivate"
                        ::= { fkGponProfileVoIPDetailEntry 71 }

                
                -- 1.3.6.1.4.1.10428 9 1.101.23.5.5.5.1.1.72
                fkGponProfileVoIPDetailDoNotDisturbAct OBJECT-TYPE
                        SYNTAX OCTET STRING
                        MAX-ACCESS read-only
                        STATUS current
                        DESCRIPTION
                                "Do not disturb activation"
                        ::= { fkGponProfileVoIPDetailEntry 72 }

                
                -- 1.3.6.1.4.1.10428 9 1.101.23.5.5.5.1.1.73
                fkGponProfileVoIPDetailDoNotDisturbDeact OBJECT-TYPE
                        SYNTAX OCTET STRING
                        MAX-ACCESS read-only
                        STATUS current
                        DESCRIPTION
                                "Do not disturb deactivation"
                        ::= { fkGponProfileVoIPDetailEntry 73 }

                
                -- 1.3.6.1.4.1.10428 9 1.101.23.5.5.5.1.1.74
                fkGponProfileVoIPDetailDoNotDisturbPinChange OBJECT-TYPE
                        SYNTAX OCTET STRING
                        MAX-ACCESS read-only
                        STATUS current
                        DESCRIPTION
                                "Do not disturb PIN change"
                        ::= { fkGponProfileVoIPDetailEntry 74 }

                
                -- 1.3.6.1.4.1.10428 9 1.101.23.5.5.5.1.1.75
                fkGponProfileVoIPDetailEmergServiceNumber OBJECT-TYPE
                        SYNTAX OCTET STRING
                        MAX-ACCESS read-only
                        STATUS current
                        DESCRIPTION
                                "Emergency service number"
                        ::= { fkGponProfileVoIPDetailEntry 75 }

                
                -- 1.3.6.1.4.1.10428 9 1.101.23.5.5.5.1.1.76
                fkGponProfileVoIPDetailIntercomService OBJECT-TYPE
                        SYNTAX OCTET STRING
                        MAX-ACCESS read-only
                        STATUS current
                        DESCRIPTION
                                "Intercom service"
                        ::= { fkGponProfileVoIPDetailEntry 76 }

                
                -- 1.3.6.1.4.1.10428 9 1.101.23.5.5.5.1.1.77
                fkGponProfileVoIPDetailDialplanCritTimeout OBJECT-TYPE
                        SYNTAX INTEGER (0..65535)
                        MAX-ACCESS read-only
                        STATUS current
                        DESCRIPTION
                                "dial-plan crit-timeout TIMEOUT (ms)"
                        ::= { fkGponProfileVoIPDetailEntry 77 }

                
                -- 1.3.6.1.4.1.10428 9 1.101.23.5.5.5.1.1.78
                fkGponProfileVoIPDetailDialplanPartTimeout OBJECT-TYPE
                        SYNTAX INTEGER (0..65535)
                        MAX-ACCESS read-only
                        STATUS current
                        DESCRIPTION
                                "dial-plan part-timeout TIMEOUT (ms)"
                        ::= { fkGponProfileVoIPDetailEntry 78 }

                
                -- 1.3.6.1.4.1.10428 9 1.101.23.5.5.5.1.1.79
                fkGponProfileVoIPDetailDialplanFormat OBJECT-TYPE
                        SYNTAX INTEGER
                                {
                                h248(1),
                                nsc(2),
                                vendor(3)
                                }
                        MAX-ACCESS read-only
                        STATUS current
                        DESCRIPTION
                                "dial-plan format (h248|nsc|vendor)"
                        ::= { fkGponProfileVoIPDetailEntry 79 }

                
                -- 1.3.6.1.4.1.10428 9 1.101.23.5.5.5.1.1.80
                fkGponProfileVoIPDetailSpecialLineService OBJECT-TYPE
                        SYNTAX INTEGER
                                {
                                disable(0),
                                enableHotLine(1),
                                enableWarmLine(2)
                                }
                        MAX-ACCESS read-only
                        STATUS current
                        DESCRIPTION
                                "Special Line Service"
                        ::= { fkGponProfileVoIPDetailEntry 80 }

                
                -- 1.3.6.1.4.1.10428 9 1.101.23.5.5.5.1.1.81
                fkGponProfileVoIPDetailWarmLineTimeout OBJECT-TYPE
                        SYNTAX Integer32 (0..30)
                        MAX-ACCESS read-only
                        STATUS current
                        DESCRIPTION
                                "Warm Line Waiting Time"
                        ::= { fkGponProfileVoIPDetailEntry 81 }

                
                -- 1.3.6.1.4.1.10428 9 1.101.23.5.5.5.1.1.82
                fkGponProfileVoIPDetailLineNumber OBJECT-TYPE
                        SYNTAX OCTET STRING
                        MAX-ACCESS read-only
                        STATUS current
                        DESCRIPTION
                                "Special Line Number"
                        ::= { fkGponProfileVoIPDetailEntry 82 }

                
                -- 1.3.6.1.4.1.10428 9 1.101.23.5.5.5.1.1.83
                fkGponProfileVoIPDetailThreeWaySSWMixing OBJECT-TYPE
                        SYNTAX INTEGER
                                {
                                server(0),
                                client(1)
                                }
                        MAX-ACCESS read-only
                        STATUS current
                        DESCRIPTION
                                "3Way Call Voice Mixing"
                        ::= { fkGponProfileVoIPDetailEntry 83 }

                
                -- 1.3.6.1.4.1.10428 9 1.101.23.5.5.5.1.1.84
                fkGponProfileVoIPDetailSIPDNSCache OBJECT-TYPE
                        SYNTAX INTEGER
                                {
                                ttl(0),
                                permanent(1)
                                }
                        MAX-ACCESS read-only
                        STATUS current
                        DESCRIPTION
                                "SIP Stack DNS Cache update policy"
                        ::= { fkGponProfileVoIPDetailEntry 84 }

                
                -- 1.3.6.1.4.1.10428 9 1.101.23.5.5.5.1.1.85
                fkGponProfileVoIPDetailSIPTimerT1 OBJECT-TYPE
                        SYNTAX Integer32 (0..2500)
                        MAX-ACCESS read-only
                        STATUS current
                        DESCRIPTION
                                "First Response Wait Time"
                        ::= { fkGponProfileVoIPDetailEntry 85 }

                
                -- 1.3.6.1.4.1.10428 9 1.101.23.5.5.5.1.1.86
                fkGponProfileVoIPDetailSIPTimerT2 OBJECT-TYPE
                        SYNTAX Integer32 (0..5000)
                        MAX-ACCESS read-only
                        STATUS current
                        DESCRIPTION
                                "Next Increase Waiting Time"
                        ::= { fkGponProfileVoIPDetailEntry 86 }

                
                -- 1.3.6.1.4.1.10428 9 1.101.23.5.5.5.1.1.87
                fkGponProfileVoIPDetailSIPTimerTd OBJECT-TYPE
                        SYNTAX Integer32 (5000..65535)
                        MAX-ACCESS read-only
                        STATUS current
                        DESCRIPTION
                                "Max Transaction Time"
                        ::= { fkGponProfileVoIPDetailEntry 87 }

                
                -- 1.3.6.1.4.1.10428 9 1.101.23.5.5.5.1.1.88
                fkGponProfileVoIPDetailSIPSessionTimer OBJECT-TYPE
                        SYNTAX INTEGER
                                {
                                disable(0),
                                enable(1)
                                }
                        MAX-ACCESS read-only
                        STATUS current
                        DESCRIPTION
                                "SIP Session Timer"
                        ::= { fkGponProfileVoIPDetailEntry 88 }

                
                -- 1.3.6.1.4.1.10428 9 1.101.23.5.5.5.1.1.89
                fkGponProfileVoIPDetailSIPSessionTimeout OBJECT-TYPE
                        SYNTAX Integer32 (0..65535)
                        MAX-ACCESS read-only
                        STATUS current
                        DESCRIPTION
                                "SIP Session Timer Timeout"
                        ::= { fkGponProfileVoIPDetailEntry 89 }

                
                -- 1.3.6.1.4.1.10428 9 1.101.23.5.5.5.1.1.90
                fkGponProfileVoIPDetailSIPEndOfDigit OBJECT-TYPE
                        SYNTAX INTEGER
                                {
                                disable(0),
                                enable(1)
                                }
                        MAX-ACCESS read-only
                        STATUS current
                        DESCRIPTION
                                "SIP End of Digit"
                        ::= { fkGponProfileVoIPDetailEntry 90 }

                
                -- 1.3.6.1.4.1.10428 9 1.101.23.5.5.5.1.1.91
                fkGponProfileVoIPDetailSIPEndSharpToken OBJECT-TYPE
                        SYNTAX INTEGER
                                {
                                hex(0),
                                ascii(1)
                                }
                        MAX-ACCESS read-only
                        STATUS current
                        DESCRIPTION
                                "SIP End # Token"
                        ::= { fkGponProfileVoIPDetailEntry 91 }

                
--  1.3.6.1.4.1.10428 9 1.101.23.5.5.1.2
                -- 1.3.6.1.4.1.10428 9 1.101.23.5.5.5.2
                fkGponProfileVoIPDetailControl OBJECT IDENTIFIER ::= { fkGponProfileVoIPDetail 2 }

                
--  1.3.6.1.4.1.10428 9 1.101.23.5.5.5.2.1
                -- 1.3.6.1.4.1.10428 9 1.101.23.5.5.5.2.1
                fkGponProfileVoIPDetailControlRequest OBJECT-TYPE
                        SYNTAX INTEGER
                                {
                                createProfile(1),
                                destroylProfile(2),
                                setFaxMode(3),
                                setCodec1st(4),
                                setCodec2nd(5),
                                setCodec3rd(6),
                                setCodec4th(7),
                                setOobDtmf(8),
                                setAnnouncementType(9),
                                setJitterTarget(10),
                                setJitterBuffMax(11),
                                setEchoCancel(12),
                                setPstnProto(13),
                                setDtmfDigit(14),
                                setHookFlashTimeMin(15),
                                setHookFlashTimeMax(16),
                                setSignalingCode(17),
                                setRtpLocalPort(18),
                                setRtpDscpMark(19),
                                setRtpPiggybackEvent(20),
                                setRtpToneEvent(21),
                                setRtpDtmfEvent(22),
                                setRtpCasEvent(23),
                                setProtocol(24),
                                setMgcPriServer(25),
                                setMgcSecServer(26),
                                setMgcVersion(27),
                                setMgcFormat(28),
                                setMgcMaxRetryTime(29),
                                setMgcRetryAttempts(30),
                                setMgcServiceChangeDelay(31),
                                setMgcTerminationId(32),
                                setMgcSoftswitch(33),
                                setVoicemailServer(34),
                                setVoicemailExpireTime(35),
                                setReleaseTime(36),
                                setRohTimer(37),
                                setProxyServer(38),
                                setOutboundProxyServer(39),
                                setRegisterServer(40),
                                setHostpartServer(41),
                                setDns(42),
                                setRegExpTime(43),
                                setReregHeadStartTime(44),
                                setSoftSwitch(45),
                                setSipOptionTransmitCtl(46),
                                setSipUriFormat(47),
                                setCallerId(48),
                                setCallWaiting(49),
                                setCallProgressTransfer(50),
                                setCallPresent(51),
                                setDirectConnect(52),
                                setDirectConnectUri(53),
                                setBridgedLineAgentUri(54),
                                setConferenceFactoryUri(55),
                                setCancelCallWait(56),
                                setCallHost(57),
                                setCallPark(58),
                                setCallerIdAct(59),
                                setCallerIdDeact(60),
                                setDoNotDisturbAct(61),
                                setDoNotDisturbDeact(62),
                                setDoNotDisturbPinChange(63),
                                setEmergServiceNumber(64),
                                setIntercomService(65),
                                setDialPlanCritTimeOut(66),
                                setDialPlanPartTimeOut(67),
                                setDialPlanFormat(68),
                                setSpecialLineService(69),
                                setThreeWaySSWMixing(70),
                                setDNSCachePolicy(71),
                                setSIPTimer(72),
                                setSessionTimer(73),
                                setEndOfDigit(74),
                                setEndSharpToken(75)
                                }
                        MAX-ACCESS read-write
                        STATUS current
                        DESCRIPTION
                                "The request of a user command"
                        ::= { fkGponProfileVoIPDetailControl 1 }

                
--  1.3.6.1.4.1.10428 9 1.101.23.5.5.1.2.2
                -- 1.3.6.1.4.1.10428 9 1.101.23.5.5.5.2.2
                fkGponProfileVoIPDetailControlStatus OBJECT-TYPE
                        SYNTAX FkControlStatusType
                        MAX-ACCESS read-only
                        STATUS current
                        DESCRIPTION
                                "The status of user command"
                        ::= { fkGponProfileVoIPDetailControl 2 }

                
--  1.3.6.1.4.1.10428 9 1.101.23.5.5.1.2.3
                -- 1.3.6.1.4.1.10428 9 1.101.23.5.5.5.2.3
                fkGponProfileVoIPDetailControlTimer OBJECT-TYPE
                        SYNTAX Gauge32
                        MAX-ACCESS read-write
                        STATUS current
                        DESCRIPTION
                                "The maximum time for the manager for a long running user command"
                        ::= { fkGponProfileVoIPDetailControl 3 }

                
--  1.3.6.1.4.1.10428 9 1.101.23.5.5.1.2.4
                -- 1.3.6.1.4.1.10428 9 1.101.23.5.5.5.2.4
                fkGponProfileVoIPDetailControlTimeStamp OBJECT-TYPE
                        SYNTAX TimeTicks
                        MAX-ACCESS read-only
                        STATUS current
                        DESCRIPTION
                                "The time stamp of the last command(end of command)"
                        ::= { fkGponProfileVoIPDetailControl 4 }

                
--  1.3.6.1.4.1.10428 9 1.101.23.5.5.1.2.5
                -- 1.3.6.1.4.1.10428 9 1.101.23.5.5.5.2.5
                fkGponProfileVoIPDetailControlReqResult OBJECT-TYPE
                        SYNTAX FkControlRequestResultType
                        MAX-ACCESS read-only
                        STATUS current
                        DESCRIPTION
                                "The result of the last user command"
                        ::= { fkGponProfileVoIPDetailControl 5 }

                
--  1.3.6.1.4.1.10428 9 1.101.23.5.5.1.2.6
                -- 1.3.6.1.4.1.10428 9 1.101.23.5.5.5.2.6
                fkGponProfileVoIPDetailControlIndex OBJECT-TYPE
                        SYNTAX INTEGER (1..65535)
                        MAX-ACCESS read-write
                        STATUS current
                        DESCRIPTION
                                "VoIP Profile Index"
                        ::= { fkGponProfileVoIPDetailControl 6 }

                
--  1.3.6.1.4.1.10428 9 1.101.23.5.5.1.2.7
                -- 1.3.6.1.4.1.10428 9 1.101.23.5.5.5.2.7
                fkGponProfileVoIPDetailControlName OBJECT-TYPE
                        SYNTAX OCTET STRING
                        MAX-ACCESS read-write
                        STATUS current
                        DESCRIPTION
                                "The VoIp profile name."
                        ::= { fkGponProfileVoIPDetailControl 7 }

                
--  1.3.6.1.4.1.10428 9 1.101.23.5.5.1.2.8
                -- 1.3.6.1.4.1.10428 9 1.101.23.5.5.5.2.8
                fkGponProfileVoIPDetailControlFaxMode OBJECT-TYPE
                        SYNTAX INTEGER
                                {
                                passthru(0),
                                t38(1)
                                }
                        MAX-ACCESS read-write
                        STATUS current
                        DESCRIPTION
                                "VoIP fax mode."
                        ::= { fkGponProfileVoIPDetailControl 8 }

                
                -- 1.3.6.1.4.1.10428 9 1.101.23.5.5.5.2.9
                fkGponProfileVoIPDetailControlCodecType1st OBJECT-TYPE
                        SYNTAX INTEGER
                                {
                                pcmu(0),
                                gsm(3),
                                g723(4),
                                dvi4and8k(5),
                                dvi4and16k(6),
                                lpc(7),
                                pcma(8),
                                g722(9),
                                l16and2ch(10),
                                l16and1h(11),
                                qcelp(12),
                                cn(13),
                                mpa(14),
                                g728(15),
                                dvi4and11k(16),
                                dvi4and22k(17),
                                g729(18)
                                }
                        MAX-ACCESS read-write
                        STATUS current
                        DESCRIPTION
                                "Codec type 1st"
                        ::= { fkGponProfileVoIPDetailControl 9 }

                
                -- 1.3.6.1.4.1.10428 9 1.101.23.5.5.5.2.10
                fkGponProfileVoIPDetailControlCodecPeriod1st OBJECT-TYPE
                        SYNTAX INTEGER (1..65535)
                        MAX-ACCESS read-write
                        STATUS current
                        DESCRIPTION
                                "Packet Period Selection
                                <10-30> ms (default 10ms)"
                        ::= { fkGponProfileVoIPDetailControl 10 }

                
                -- 1.3.6.1.4.1.10428 9 1.101.23.5.5.5.2.11
                fkGponProfileVoIPDetailControlCodecSilenceSuppression1st OBJECT-TYPE
                        SYNTAX INTEGER (1..65535)
                        MAX-ACCESS read-write
                        STATUS current
                        DESCRIPTION
                                "Silence Suppression 
                                (0:off 1:on)"
                        ::= { fkGponProfileVoIPDetailControl 11 }

                
                -- 1.3.6.1.4.1.10428 9 1.101.23.5.5.5.2.12
                fkGponProfileVoIPDetailControlCodecType2nd OBJECT-TYPE
                        SYNTAX INTEGER
                                {
                                pcmu(0),
                                gsm(3),
                                g723(4),
                                dvi4and8k(5),
                                dvi4and16k(6),
                                lpc(7),
                                pcma(8),
                                g722(9),
                                l16and2ch(10),
                                l16and1h(11),
                                qcelp(12),
                                cn(13),
                                mpa(14),
                                g728(15),
                                dvi4and11k(16),
                                dvi4and22k(17),
                                g729(18)
                                }
                        MAX-ACCESS read-write
                        STATUS current
                        DESCRIPTION
                                "Codec type 2nd "
                        ::= { fkGponProfileVoIPDetailControl 12 }

                
                -- 1.3.6.1.4.1.10428 9 1.101.23.5.5.5.2.13
                fkGponProfileVoIPDetailControlCodecPeriod2nd OBJECT-TYPE
                        SYNTAX INTEGER (1..65535)
                        MAX-ACCESS read-write
                        STATUS current
                        DESCRIPTION
                                "Packet Period Selection
                                <10-30> ms (default 10ms)
                                "
                        ::= { fkGponProfileVoIPDetailControl 13 }

                
                -- 1.3.6.1.4.1.10428 9 1.101.23.5.5.5.2.14
                fkGponProfileVoIPDetailControlCodecSilenceSuppression2nd OBJECT-TYPE
                        SYNTAX INTEGER (1..65535)
                        MAX-ACCESS read-write
                        STATUS current
                        DESCRIPTION
                                "Silence Suppression 
                                (0:off 1:on)"
                        ::= { fkGponProfileVoIPDetailControl 14 }

                
                -- 1.3.6.1.4.1.10428 9 1.101.23.5.5.5.2.15
                fkGponProfileVoIPDetailControlCodecType3rd OBJECT-TYPE
                        SYNTAX INTEGER
                                {
                                pcmu(0),
                                gsm(3),
                                g723(4),
                                dvi4and8k(5),
                                dvi4and16k(6),
                                lpc(7),
                                pcma(8),
                                g722(9),
                                l16and2ch(10),
                                l16and1h(11),
                                qcelp(12),
                                cn(13),
                                mpa(14),
                                g728(15),
                                dvi4and11k(16),
                                dvi4and22k(17),
                                g729(18)
                                }
                        MAX-ACCESS read-write
                        STATUS current
                        DESCRIPTION
                                "Codec type 3rd"
                        ::= { fkGponProfileVoIPDetailControl 15 }

                
                -- 1.3.6.1.4.1.10428 9 1.101.23.5.5.5.2.16
                fkGponProfileVoIPDetailControlCodecPeriod3rd OBJECT-TYPE
                        SYNTAX INTEGER (1..65535)
                        MAX-ACCESS read-write
                        STATUS current
                        DESCRIPTION
                                "Packet Period Selection
                                <10-30> ms (default 10ms)"
                        ::= { fkGponProfileVoIPDetailControl 16 }

                
                -- 1.3.6.1.4.1.10428 9 1.101.23.5.5.5.2.17
                fkGponProfileVoIPDetailControlCodecSilenceSuppression3rd OBJECT-TYPE
                        SYNTAX INTEGER (1..65535)
                        MAX-ACCESS read-write
                        STATUS current
                        DESCRIPTION
                                "Silence Suppression 
                                (0:off 1:on)"
                        ::= { fkGponProfileVoIPDetailControl 17 }

                
                -- 1.3.6.1.4.1.10428 9 1.101.23.5.5.5.2.18
                fkGponProfileVoIPDetailControlCodecType4th OBJECT-TYPE
                        SYNTAX INTEGER
                                {
                                pcmu(0),
                                gsm(3),
                                g723(4),
                                dvi4and8k(5),
                                dvi4and16k(6),
                                lpc(7),
                                pcma(8),
                                g722(9),
                                l16and2ch(10),
                                l16and1h(11),
                                qcelp(12),
                                cn(13),
                                mpa(14),
                                g728(15),
                                dvi4and11k(16),
                                dvi4and22k(17),
                                g729(18)
                                }
                        MAX-ACCESS read-write
                        STATUS current
                        DESCRIPTION
                                "Codec type 4th"
                        ::= { fkGponProfileVoIPDetailControl 18 }

                
                -- 1.3.6.1.4.1.10428 9 1.101.23.5.5.5.2.19
                fkGponProfileVoIPDetailCodecControlPeriod4th OBJECT-TYPE
                        SYNTAX INTEGER (1..65535)
                        MAX-ACCESS read-write
                        STATUS current
                        DESCRIPTION
                                "Packet Period Selection
                                <10-30> ms (default 10ms)"
                        ::= { fkGponProfileVoIPDetailControl 19 }

                
                -- 1.3.6.1.4.1.10428 9 1.101.23.5.5.5.2.20
                fkGponProfileVoIPDetailControlCodecSilenceSuppression4th OBJECT-TYPE
                        SYNTAX INTEGER (1..65535)
                        MAX-ACCESS read-write
                        STATUS current
                        DESCRIPTION
                                "Silence Suppression 
                                (0:off 1:on)"
                        ::= { fkGponProfileVoIPDetailControl 20 }

                
--  1.3.6.1.4.1.10428 9 1.101.23.5.5.1.2.13
                -- 1.3.6.1.4.1.10428 9 1.101.23.5.5.5.2.21
                fkGponProfileVoIPDetailControlOobdtmf OBJECT-TYPE
                        SYNTAX INTEGER
                                {
                                disable(0),
                                enable(1)
                                }
                        MAX-ACCESS read-write
                        STATUS current
                        DESCRIPTION
                                "Out-of-band DMTF"
                        ::= { fkGponProfileVoIPDetailControl 21 }

                
--  1.3.6.1.4.1.10428 9 1.101.23.5.5.1.2.14
                -- 1.3.6.1.4.1.10428 9 1.101.23.5.5.5.2.22
                fkGponProfileVoIPDetailControlAnnouncementType OBJECT-TYPE
                        SYNTAX INTEGER
                                {
                                silence(1),
                                reorderTone(2),
                                fastBusy(3),
                                voiceAnnouncement(4)
                                }
                        MAX-ACCESS read-write
                        STATUS current
                        DESCRIPTION
                                "Announcement Type"
                        ::= { fkGponProfileVoIPDetailControl 22 }

                
--  1.3.6.1.4.1.10428 9 1.101.23.5.5.1.2.15
                -- 1.3.6.1.4.1.10428 9 1.101.23.5.5.5.2.23
                fkGponProfileVoIPDetailControlJitterTarget OBJECT-TYPE
                        SYNTAX INTEGER (1..65535)
                        MAX-ACCESS read-write
                        STATUS current
                        DESCRIPTION
                                "Jitter target (milliseconds)"
                        ::= { fkGponProfileVoIPDetailControl 23 }

                
--  1.3.6.1.4.1.10428 9 1.101.23.5.5.1.2.16
                -- 1.3.6.1.4.1.10428 9 1.101.23.5.5.5.2.24
                fkGponProfileVoIPDetailControlJitterBuffMax OBJECT-TYPE
                        SYNTAX INTEGER (0..65535)
                        MAX-ACCESS read-write
                        STATUS current
                        DESCRIPTION
                                "Jitter Buffer Max"
                        ::= { fkGponProfileVoIPDetailControl 24 }

                
--  1.3.6.1.4.1.10428 9 1.101.23.5.5.1.2.16
                -- 1.3.6.1.4.1.10428 9 1.101.23.5.5.5.2.25
                fkGponProfileVoIPDetailControlEchoCancel OBJECT-TYPE
                        SYNTAX INTEGER
                                {
                                false(0),
                                true(1)
                                }
                        MAX-ACCESS read-write
                        STATUS current
                        DESCRIPTION
                                "Echo cancellation"
                        ::= { fkGponProfileVoIPDetailControl 25 }

                
--  1.3.6.1.4.1.10428 9 1.101.23.5.5.1.2.16
                -- 1.3.6.1.4.1.10428 9 1.101.23.5.5.5.2.26
                fkGponProfileVoIPDetailControlPstnProtoVariant OBJECT-TYPE
                        SYNTAX INTEGER (1..65535)
                        MAX-ACCESS read-write
                        STATUS current
                        DESCRIPTION
                                "PSTN Protocol Variant"
                        ::= { fkGponProfileVoIPDetailControl 26 }

                
--  1.3.6.1.4.1.10428 9 1.101.23.5.5.1.2.16
                -- 1.3.6.1.4.1.10428 9 1.101.23.5.5.5.2.27
                fkGponProfileVoIPDetailControlDtmfDigitLevels OBJECT-TYPE
                        SYNTAX INTEGER (0..65535)
                        MAX-ACCESS read-write
                        STATUS current
                        DESCRIPTION
                                "DTMF digit Power Level configuration "
                        ::= { fkGponProfileVoIPDetailControl 27 }

                
--  1.3.6.1.4.1.10428 9 1.101.23.5.5.1.2.16
                -- 1.3.6.1.4.1.10428 9 1.101.23.5.5.5.2.28
                fkGponProfileVoIPDetailControlDtmfDigitDuration OBJECT-TYPE
                        SYNTAX INTEGER (0..65535)
                        MAX-ACCESS read-write
                        STATUS current
                        DESCRIPTION
                                "DTMF digit Power Duration configuration"
                        ::= { fkGponProfileVoIPDetailControl 28 }

                
--  1.3.6.1.4.1.10428 9 1.101.23.5.5.1.2.16
                -- 1.3.6.1.4.1.10428 9 1.101.23.5.5.5.2.29
                fkGponProfileVoIPDetailControlHookFlashTimeMin OBJECT-TYPE
                        SYNTAX INTEGER (0..65535)
                        MAX-ACCESS read-write
                        STATUS current
                        DESCRIPTION
                                "Hook Flash Duration Min"
                        ::= { fkGponProfileVoIPDetailControl 29 }

                
--  1.3.6.1.4.1.10428 9 1.101.23.5.5.1.2.16
                -- 1.3.6.1.4.1.10428 9 1.101.23.5.5.5.2.30
                fkGponProfileVoIPDetailControlHookFlashTimeMax OBJECT-TYPE
                        SYNTAX INTEGER (0..65535)
                        MAX-ACCESS read-write
                        STATUS current
                        DESCRIPTION
                                "Hook Flash Duration Max"
                        ::= { fkGponProfileVoIPDetailControl 30 }

                
--  1.3.6.1.4.1.10428 9 1.101.23.5.5.1.2.16
                -- 1.3.6.1.4.1.10428 9 1.101.23.5.5.5.2.31
                fkGponProfileVoIPDetailControlSignalingCode OBJECT-TYPE
                        SYNTAX INTEGER
                                {
                                loopStart(1),
                                groundStart(2),
                                loopReverseBattery(3),
                                coinFirst(4),
                                dialToneFirst(5),
                                multiParty(6)
                                }
                        MAX-ACCESS read-write
                        STATUS current
                        DESCRIPTION
                                "POTS-side Signalling"
                        ::= { fkGponProfileVoIPDetailControl 31 }

                
--  1.3.6.1.4.1.10428 9 1.101.23.5.5.1.2.16
                -- 1.3.6.1.4.1.10428 9 1.101.23.5.5.5.2.32
                fkGponProfileVoIPDetailControlRtpLocalPortMin OBJECT-TYPE
                        SYNTAX INTEGER (1..65535)
                        MAX-ACCESS read-write
                        STATUS current
                        DESCRIPTION
                                "RTP Local Port Min"
                        ::= { fkGponProfileVoIPDetailControl 32 }

                
--  1.3.6.1.4.1.10428 9 1.101.23.5.5.1.2.16
                -- 1.3.6.1.4.1.10428 9 1.101.23.5.5.5.2.33
                fkGponProfileVoIPDetailControlRtpLocalPortMax OBJECT-TYPE
                        SYNTAX INTEGER (1..65535)
                        MAX-ACCESS read-write
                        STATUS current
                        DESCRIPTION
                                "RTP Local Port Max"
                        ::= { fkGponProfileVoIPDetailControl 33 }

                
--  1.3.6.1.4.1.10428 9 1.101.23.5.5.1.2.16
                -- 1.3.6.1.4.1.10428 9 1.101.23.5.5.5.2.34
                fkGponProfileVoIPDetailControlRtpDscpMark OBJECT-TYPE
                        SYNTAX INTEGER (1..65535)
                        MAX-ACCESS read-write
                        STATUS current
                        DESCRIPTION
                                "RTP DSCP Mark"
                        ::= { fkGponProfileVoIPDetailControl 34 }

                
--  1.3.6.1.4.1.10428 9 1.101.23.5.5.1.2.16
                -- 1.3.6.1.4.1.10428 9 1.101.23.5.5.5.2.35
                fkGponProfileVoIPDetailControlRtpPiggybackEvent OBJECT-TYPE
                        SYNTAX INTEGER
                                {
                                disable(0),
                                enable(1)
                                }
                        MAX-ACCESS read-write
                        STATUS current
                        DESCRIPTION
                                "RTP Piggyback event"
                        ::= { fkGponProfileVoIPDetailControl 35 }

                
--  1.3.6.1.4.1.10428 9 1.101.23.5.5.1.2.16
                -- 1.3.6.1.4.1.10428 9 1.101.23.5.5.5.2.36
                fkGponProfileVoIPDetailControlRtpToneEvent OBJECT-TYPE
                        SYNTAX INTEGER
                                {
                                disable(0),
                                enable(1)
                                }
                        MAX-ACCESS read-write
                        STATUS current
                        DESCRIPTION
                                "RTP Tone event"
                        ::= { fkGponProfileVoIPDetailControl 36 }

                
--  1.3.6.1.4.1.10428 9 1.101.23.5.5.1.2.16
                -- 1.3.6.1.4.1.10428 9 1.101.23.5.5.5.2.37
                fkGponProfileVoIPDetailControlRtpDtmfEvent OBJECT-TYPE
                        SYNTAX INTEGER
                                {
                                disable(0),
                                enable(1)
                                }
                        MAX-ACCESS read-write
                        STATUS current
                        DESCRIPTION
                                "RTP DTMF event"
                        ::= { fkGponProfileVoIPDetailControl 37 }

                
--  1.3.6.1.4.1.10428 9 1.101.23.5.5.1.2.16
                -- 1.3.6.1.4.1.10428 9 1.101.23.5.5.5.2.38
                fkGponProfileVoIPDetailControlRtpCasEvent OBJECT-TYPE
                        SYNTAX INTEGER
                                {
                                disable(0),
                                enable(1)
                                }
                        MAX-ACCESS read-write
                        STATUS current
                        DESCRIPTION
                                "The status of RTP CAS event"
                        ::= { fkGponProfileVoIPDetailControl 38 }

                
--  1.3.6.1.4.1.10428 9 1.101.23.5.5.1.2.16
                -- 1.3.6.1.4.1.10428 9 1.101.23.5.5.5.2.39
                fkGponProfileVoIPDetailControlProtocol OBJECT-TYPE
                        SYNTAX INTEGER
                                {
                                none(0),
                                sip(1),
                                h248(2),
                                mgcp(3)
                                }
                        MAX-ACCESS read-write
                        STATUS current
                        DESCRIPTION
                                "VoIP Protocol configuration"
                        ::= { fkGponProfileVoIPDetailControl 39 }

                
--  1.3.6.1.4.1.10428 9 1.101.23.5.5.1.2.16
                -- 1.3.6.1.4.1.10428 9 1.101.23.5.5.5.2.40
                fkGponProfileVoIPDetailControlMgcPriServer OBJECT-TYPE
                        SYNTAX OCTET STRING
                        MAX-ACCESS read-write
                        STATUS current
                        DESCRIPTION
                                "The primary server name."
                        ::= { fkGponProfileVoIPDetailControl 40 }

                
--  1.3.6.1.4.1.10428 9 1.101.23.5.5.1.2.16
                -- 1.3.6.1.4.1.10428 9 1.101.23.5.5.5.2.41
                fkGponProfileVoIPDetailControlMgcSecServer OBJECT-TYPE
                        SYNTAX OCTET STRING
                        MAX-ACCESS read-write
                        STATUS current
                        DESCRIPTION
                                "The secondary server name."
                        ::= { fkGponProfileVoIPDetailControl 41 }

                
--  1.3.6.1.4.1.10428 9 1.101.23.5.5.1.2.16
                -- 1.3.6.1.4.1.10428 9 1.101.23.5.5.5.2.42
                fkGponProfileVoIPDetailControlMgcMsgVersion OBJECT-TYPE
                        SYNTAX INTEGER (1..255)
                        MAX-ACCESS read-write
                        STATUS current
                        DESCRIPTION
                                "The message version."
                        ::= { fkGponProfileVoIPDetailControl 42 }

                
--  1.3.6.1.4.1.10428 9 1.101.23.5.5.1.2.16
                -- 1.3.6.1.4.1.10428 9 1.101.23.5.5.5.2.43
                fkGponProfileVoIPDetailControlMgcMsgFormat OBJECT-TYPE
                        SYNTAX INTEGER
                                {
                                textLong(0),
                                textShort(1),
                                binary(2)
                                }
                        MAX-ACCESS read-write
                        STATUS current
                        DESCRIPTION
                                "The message format."
                        ::= { fkGponProfileVoIPDetailControl 43 }

                
--  1.3.6.1.4.1.10428 9 1.101.23.5.5.1.2.16
                -- 1.3.6.1.4.1.10428 9 1.101.23.5.5.5.2.44
                fkGponProfileVoIPDetailControlMgcMaxRetryTime OBJECT-TYPE
                        SYNTAX INTEGER (0..65535)
                        MAX-ACCESS read-write
                        STATUS current
                        DESCRIPTION
                                "The max retry time.
                                65535: unused"
                        ::= { fkGponProfileVoIPDetailControl 44 }

                
--  1.3.6.1.4.1.10428 9 1.101.23.5.5.1.2.16
                -- 1.3.6.1.4.1.10428 9 1.101.23.5.5.5.2.45
                fkGponProfileVoIPDetailControlMgcMaxRetryAttempts OBJECT-TYPE
                        SYNTAX INTEGER (0..65535)
                        MAX-ACCESS read-write
                        STATUS current
                        DESCRIPTION
                                "The max retry attemption
                                65535: unused"
                        ::= { fkGponProfileVoIPDetailControl 45 }

                
--  1.3.6.1.4.1.10428 9 1.101.23.5.5.1.2.16
                -- 1.3.6.1.4.1.10428 9 1.101.23.5.5.5.2.46
                fkGponProfileVoIPDetailControlMgcSvcChangeDelay OBJECT-TYPE
                        SYNTAX INTEGER (0..65535)
                        MAX-ACCESS read-write
                        STATUS current
                        DESCRIPTION
                                "The service change delay
                                65535: unused"
                        ::= { fkGponProfileVoIPDetailControl 46 }

                
--  1.3.6.1.4.1.10428 9 1.101.23.5.5.1.2.16
                -- 1.3.6.1.4.1.10428 9 1.101.23.5.5.5.2.47
                fkGponProfileVoIPDetailControlMgcTerminationId OBJECT-TYPE
                        SYNTAX OCTET STRING
                        MAX-ACCESS read-write
                        STATUS current
                        DESCRIPTION
                                "The termination id."
                        ::= { fkGponProfileVoIPDetailControl 47 }

                
--  1.3.6.1.4.1.10428 9 1.101.23.5.5.1.2.16
                -- 1.3.6.1.4.1.10428 9 1.101.23.5.5.5.2.48
                fkGponProfileVoIPDetailControlMgcSoftswitch OBJECT-TYPE
                        SYNTAX OCTET STRING
                        MAX-ACCESS read-write
                        STATUS current
                        DESCRIPTION
                                "The soft switch"
                        ::= { fkGponProfileVoIPDetailControl 48 }

                
--  1.3.6.1.4.1.10428 9 1.101.23.5.5.1.2.16
                -- 1.3.6.1.4.1.10428 9 1.101.23.5.5.5.2.49
                fkGponProfileVoIPDetailControlVoicemailServer OBJECT-TYPE
                        SYNTAX OCTET STRING
                        MAX-ACCESS read-write
                        STATUS current
                        DESCRIPTION
                                "Voicemail server SIP URI"
                        ::= { fkGponProfileVoIPDetailControl 49 }

                
--  1.3.6.1.4.1.10428 9 1.101.23.5.5.1.2.16
                -- 1.3.6.1.4.1.10428 9 1.101.23.5.5.5.2.50
                fkGponProfileVoIPDetailControlVoicemmailExpireTime OBJECT-TYPE
                        SYNTAX INTEGER (1..65535)
                        MAX-ACCESS read-write
                        STATUS current
                        DESCRIPTION
                                "Voicemail Subscription Expiration Time"
                        ::= { fkGponProfileVoIPDetailControl 50 }

                
--  1.3.6.1.4.1.10428 9 1.101.23.5.5.1.2.16
                -- 1.3.6.1.4.1.10428 9 1.101.23.5.5.5.2.51
                fkGponProfileVoIPDetailControlReleaseTime OBJECT-TYPE
                        SYNTAX INTEGER (1..65535)
                        MAX-ACCESS read-write
                        STATUS current
                        DESCRIPTION
                                "Release timer"
                        ::= { fkGponProfileVoIPDetailControl 51 }

                
--  1.3.6.1.4.1.10428 9 1.101.23.5.5.1.2.16
                -- 1.3.6.1.4.1.10428 9 1.101.23.5.5.5.2.52
                fkGponProfileVoIPDetailControlRohTimer OBJECT-TYPE
                        SYNTAX INTEGER (1..65535)
                        MAX-ACCESS read-write
                        STATUS current
                        DESCRIPTION
                                "ROH timer"
                        ::= { fkGponProfileVoIPDetailControl 52 }

                
--  1.3.6.1.4.1.10428 9 1.101.23.5.5.1.2.16
                -- 1.3.6.1.4.1.10428 9 1.101.23.5.5.5.2.53
                fkGponProfileVoIPDetailControlProxyServer OBJECT-TYPE
                        SYNTAX OCTET STRING
                        MAX-ACCESS read-write
                        STATUS current
                        DESCRIPTION
                                "Proxy server address"
                        ::= { fkGponProfileVoIPDetailControl 53 }

                
--  1.3.6.1.4.1.10428 9 1.101.23.5.5.1.2.16
                -- 1.3.6.1.4.1.10428 9 1.101.23.5.5.5.2.54
                fkGponProfileVoIPDetailControlOutboundProxyServer OBJECT-TYPE
                        SYNTAX OCTET STRING
                        MAX-ACCESS read-write
                        STATUS current
                        DESCRIPTION
                                "Outbound proxy address"
                        ::= { fkGponProfileVoIPDetailControl 54 }

                
--  1.3.6.1.4.1.10428 9 1.101.23.5.5.1.2.16
                -- 1.3.6.1.4.1.10428 9 1.101.23.5.5.5.2.55
                fkGponProfileVoIPDetailControlRegisterServer OBJECT-TYPE
                        SYNTAX OCTET STRING
                        MAX-ACCESS read-write
                        STATUS current
                        DESCRIPTION
                                "Registrar server address"
                        ::= { fkGponProfileVoIPDetailControl 55 }

                
--  1.3.6.1.4.1.10428 9 1.101.23.5.5.1.2.16
                -- 1.3.6.1.4.1.10428 9 1.101.23.5.5.5.2.56
                fkGponProfileVoIPDetailControlHostPartServer OBJECT-TYPE
                        SYNTAX OCTET STRING
                        MAX-ACCESS read-write
                        STATUS current
                        DESCRIPTION
                                "Host part server address"
                        ::= { fkGponProfileVoIPDetailControl 56 }

                
--  1.3.6.1.4.1.10428 9 1.101.23.5.5.1.2.16
                -- 1.3.6.1.4.1.10428 9 1.101.23.5.5.5.2.57
                fkGponProfileVoIPDetailControlPriDns OBJECT-TYPE
                        SYNTAX IpAddress
                        MAX-ACCESS read-write
                        STATUS current
                        DESCRIPTION
                                "Primary DNS Server"
                        ::= { fkGponProfileVoIPDetailControl 57 }

                
--  1.3.6.1.4.1.10428 9 1.101.23.5.5.1.2.16
                -- 1.3.6.1.4.1.10428 9 1.101.23.5.5.5.2.58
                fkGponProfileVoIPDetailControlSecDns OBJECT-TYPE
                        SYNTAX IpAddress
                        MAX-ACCESS read-write
                        STATUS current
                        DESCRIPTION
                                "Secondary DNS Server"
                        ::= { fkGponProfileVoIPDetailControl 58 }

                
--  1.3.6.1.4.1.10428 9 1.101.23.5.5.1.2.16
                -- 1.3.6.1.4.1.10428 9 1.101.23.5.5.5.2.59
                fkGponProfileVoIPDetailControlRegExpTime OBJECT-TYPE
                        SYNTAX INTEGER (1..65535)
                        MAX-ACCESS read-write
                        STATUS current
                        DESCRIPTION
                                "Registration expiration time"
                        ::= { fkGponProfileVoIPDetailControl 59 }

                
--  1.3.6.1.4.1.10428 9 1.101.23.5.5.1.2.16
                -- 1.3.6.1.4.1.10428 9 1.101.23.5.5.5.2.60
                fkGponProfileVoIPDetailControlReregHeadStartTime OBJECT-TYPE
                        SYNTAX INTEGER (1..65535)
                        MAX-ACCESS read-write
                        STATUS current
                        DESCRIPTION
                                "Registration head start time"
                        ::= { fkGponProfileVoIPDetailControl 60 }

                
--  1.3.6.1.4.1.10428 9 1.101.23.5.5.1.2.16
                -- 1.3.6.1.4.1.10428 9 1.101.23.5.5.5.2.61
                fkGponProfileVoIPDetailControlSoftSwitchVendor OBJECT-TYPE
                        SYNTAX OCTET STRING
                        MAX-ACCESS read-write
                        STATUS current
                        DESCRIPTION
                                "Softswitch Vendor name"
                        ::= { fkGponProfileVoIPDetailControl 61 }

                
--  1.3.6.1.4.1.10428 9 1.101.23.5.5.1.2.16
                -- 1.3.6.1.4.1.10428 9 1.101.23.5.5.5.2.62
                fkGponProfileVoIPDetailControlSipOptionTransmitCtl OBJECT-TYPE
                        SYNTAX INTEGER
                                {
                                disable(0),
                                enable(1)
                                }
                        MAX-ACCESS read-write
                        STATUS current
                        DESCRIPTION
                                "Transmit control"
                        ::= { fkGponProfileVoIPDetailControl 62 }

                
--  1.3.6.1.4.1.10428 9 1.101.23.5.5.1.2.16
                -- 1.3.6.1.4.1.10428 9 1.101.23.5.5.5.2.63
                fkGponProfileVoIPDetailControlSipUriFormat OBJECT-TYPE
                        SYNTAX INTEGER
                                {
                                telUri(0),
                                sipUri(1)
                                }
                        MAX-ACCESS read-write
                        STATUS current
                        DESCRIPTION
                                "URI format"
                        ::= { fkGponProfileVoIPDetailControl 63 }

                
--  1.3.6.1.4.1.10428 9 1.101.23.5.5.1.2.16
                -- 1.3.6.1.4.1.10428 9 1.101.23.5.5.5.2.64
                fkGponProfileVoIPDetailControlCallerId OBJECT-TYPE
                        SYNTAX BITS
                                {
                                callNumber(0),
                                callName(1),
                                cidBlocking(2),
                                cidNumber(3),
                                cidName(4),
                                acr(5)
                                }
                        MAX-ACCESS read-write
                        STATUS current
                        DESCRIPTION
                                "Caller ID feature"
                        ::= { fkGponProfileVoIPDetailControl 64 }

                
--  1.3.6.1.4.1.10428 9 1.101.23.5.5.1.2.16
                -- 1.3.6.1.4.1.10428 9 1.101.23.5.5.5.2.65
                fkGponProfileVoIPDetailControlCallWaiting OBJECT-TYPE
                        SYNTAX BITS
                                {
                                callFeature(0),
                                cidAnnounce(1)
                                }
                        MAX-ACCESS read-write
                        STATUS current
                        DESCRIPTION
                                "Call waiting features"
                        ::= { fkGponProfileVoIPDetailControl 65 }

                
--  1.3.6.1.4.1.10428 9 1.101.23.5.5.1.2.16
                -- 1.3.6.1.4.1.10428 9 1.101.23.5.5.5.2.66
                fkGponProfileVoIPDetailControlCallProgressTransfer OBJECT-TYPE
                        SYNTAX BITS
                                {
                                threeWay(0),
                                callTransfer(1),
                                callHold(2),
                                callPark(3),
                                notDisturb(4),
                                flashEmergCall(5),
                                emergOriginatingHold(6)
                                }
                        MAX-ACCESS read-write
                        STATUS current
                        DESCRIPTION
                                "Call progress or transfer features"
                        ::= { fkGponProfileVoIPDetailControl 66 }

                
--  1.3.6.1.4.1.10428 9 1.101.23.5.5.1.2.16
                -- 1.3.6.1.4.1.10428 9 1.101.23.5.5.5.2.67
                fkGponProfileVoIPDetailControlCallPresent OBJECT-TYPE
                        SYNTAX BITS
                                {
                                splashRing(0),
                                dialTone(1),
                                visualIndicate(2),
                                callForward(3)
                                }
                        MAX-ACCESS read-write
                        STATUS current
                        DESCRIPTION
                                "Call presentation features"
                        ::= { fkGponProfileVoIPDetailControl 67 }

                
--  1.3.6.1.4.1.10428 9 1.101.23.5.5.1.2.16
                -- 1.3.6.1.4.1.10428 9 1.101.23.5.5.5.2.68
                fkGponProfileVoIPDetailControlDirectConnect OBJECT-TYPE
                        SYNTAX INTEGER
                                {
                                disable(0),
                                enable(1),
                                delayOption(2)
                                }
                        MAX-ACCESS read-write
                        STATUS current
                        DESCRIPTION
                                "Direct connect feature"
                        ::= { fkGponProfileVoIPDetailControl 68 }

                
--  1.3.6.1.4.1.10428 9 1.101.23.5.5.1.2.16
                -- 1.3.6.1.4.1.10428 9 1.101.23.5.5.5.2.69
                fkGponProfileVoIPDetailControlDirectConnectUri OBJECT-TYPE
                        SYNTAX OCTET STRING
                        MAX-ACCESS read-write
                        STATUS current
                        DESCRIPTION
                                "Direct connect URI"
                        ::= { fkGponProfileVoIPDetailControl 69 }

                
--  1.3.6.1.4.1.10428 9 1.101.23.5.5.1.2.16
                -- 1.3.6.1.4.1.10428 9 1.101.23.5.5.5.2.70
                fkGponProfileVoIPDetailControlBridgedLineAgentUri OBJECT-TYPE
                        SYNTAX OCTET STRING
                        MAX-ACCESS read-write
                        STATUS current
                        DESCRIPTION
                                "Bridged line agent URI"
                        ::= { fkGponProfileVoIPDetailControl 70 }

                
--  1.3.6.1.4.1.10428 9 1.101.23.5.5.1.2.16
                -- 1.3.6.1.4.1.10428 9 1.101.23.5.5.5.2.71
                fkGponProfileVoIPDetailControlConferenceFactoryUri OBJECT-TYPE
                        SYNTAX OCTET STRING
                        MAX-ACCESS read-write
                        STATUS current
                        DESCRIPTION
                                "Conference factory URI"
                        ::= { fkGponProfileVoIPDetailControl 71 }

                
--  1.3.6.1.4.1.10428 9 1.101.23.5.5.1.2.16
                -- 1.3.6.1.4.1.10428 9 1.101.23.5.5.5.2.72
                fkGponProfileVoIPDetailControlCancelCallWait OBJECT-TYPE
                        SYNTAX OCTET STRING
                        MAX-ACCESS read-write
                        STATUS current
                        DESCRIPTION
                                "Cancel call waiting"
                        ::= { fkGponProfileVoIPDetailControl 72 }

                
--  1.3.6.1.4.1.10428 9 1.101.23.5.5.1.2.16
                -- 1.3.6.1.4.1.10428 9 1.101.23.5.5.5.2.73
                fkGponProfileVoIPDetailControlCallHold OBJECT-TYPE
                        SYNTAX OCTET STRING
                        MAX-ACCESS read-write
                        STATUS current
                        DESCRIPTION
                                "Call hold"
                        ::= { fkGponProfileVoIPDetailControl 73 }

                
--  1.3.6.1.4.1.10428 9 1.101.23.5.5.1.2.16
                -- 1.3.6.1.4.1.10428 9 1.101.23.5.5.5.2.74
                fkGponProfileVoIPDetailControlCallPark OBJECT-TYPE
                        SYNTAX OCTET STRING
                        MAX-ACCESS read-write
                        STATUS current
                        DESCRIPTION
                                "Call park"
                        ::= { fkGponProfileVoIPDetailControl 74 }

                
--  1.3.6.1.4.1.10428 9 1.101.23.5.5.1.2.16
                -- 1.3.6.1.4.1.10428 9 1.101.23.5.5.5.2.75
                fkGponProfileVoIPDetailControlCallerIdAct OBJECT-TYPE
                        SYNTAX OCTET STRING
                        MAX-ACCESS read-write
                        STATUS current
                        DESCRIPTION
                                "Caller ID activate"
                        ::= { fkGponProfileVoIPDetailControl 75 }

                
--  1.3.6.1.4.1.10428 9 1.101.23.5.5.1.2.16
                -- 1.3.6.1.4.1.10428 9 1.101.23.5.5.5.2.76
                fkGponProfileVoIPDetailControlCallerIdDeact OBJECT-TYPE
                        SYNTAX OCTET STRING
                        MAX-ACCESS read-write
                        STATUS current
                        DESCRIPTION
                                "Caller ID deactivate"
                        ::= { fkGponProfileVoIPDetailControl 76 }

                
--  1.3.6.1.4.1.10428 9 1.101.23.5.5.1.2.16
                -- 1.3.6.1.4.1.10428 9 1.101.23.5.5.5.2.77
                fkGponProfileVoIPDetailControlDoNotDisturbAct OBJECT-TYPE
                        SYNTAX OCTET STRING
                        MAX-ACCESS read-write
                        STATUS current
                        DESCRIPTION
                                "Do not disturb activation"
                        ::= { fkGponProfileVoIPDetailControl 77 }

                
--  1.3.6.1.4.1.10428 9 1.101.23.5.5.1.2.16
                -- 1.3.6.1.4.1.10428 9 1.101.23.5.5.5.2.78
                fkGponProfileVoIPDetailControlDoNotDisturbDeact OBJECT-TYPE
                        SYNTAX OCTET STRING
                        MAX-ACCESS read-write
                        STATUS current
                        DESCRIPTION
                                "Do not disturb deactivation"
                        ::= { fkGponProfileVoIPDetailControl 78 }

                
--  1.3.6.1.4.1.10428 9 1.101.23.5.5.1.2.16
                -- 1.3.6.1.4.1.10428 9 1.101.23.5.5.5.2.79
                fkGponProfileVoIPDetailControlDoNotDisturbPinChange OBJECT-TYPE
                        SYNTAX OCTET STRING
                        MAX-ACCESS read-write
                        STATUS current
                        DESCRIPTION
                                "Do not disturb PIN change"
                        ::= { fkGponProfileVoIPDetailControl 79 }

                
--  1.3.6.1.4.1.10428 9 1.101.23.5.5.1.2.16
                -- 1.3.6.1.4.1.10428 9 1.101.23.5.5.5.2.80
                fkGponProfileVoIPDetailControlEmergServiceNumber OBJECT-TYPE
                        SYNTAX OCTET STRING
                        MAX-ACCESS read-write
                        STATUS current
                        DESCRIPTION
                                "Emergency service number"
                        ::= { fkGponProfileVoIPDetailControl 80 }

                
--  1.3.6.1.4.1.10428 9 1.101.23.5.5.1.2.16
                -- 1.3.6.1.4.1.10428 9 1.101.23.5.5.5.2.81
                fkGponProfileVoIPDetailControlIntercomService OBJECT-TYPE
                        SYNTAX OCTET STRING
                        MAX-ACCESS read-write
                        STATUS current
                        DESCRIPTION
                                "Intercom service"
                        ::= { fkGponProfileVoIPDetailControl 81 }

                
                -- 1.3.6.1.4.1.10428 9 1.101.23.5.5.5.2.82
                fkGponProfileVoIPDetailControlDialplanCritTimeout OBJECT-TYPE
                        SYNTAX INTEGER (0..65535)
                        MAX-ACCESS read-write
                        STATUS current
                        DESCRIPTION
                                "dial-plan crit-timeout TIMEOUT (ms)"
                        ::= { fkGponProfileVoIPDetailControl 82 }

                
                -- 1.3.6.1.4.1.10428 9 1.101.23.5.5.5.2.83
                fkGponProfileVoIPDetailControlDialplanPartTimeout OBJECT-TYPE
                        SYNTAX INTEGER (0..65535)
                        MAX-ACCESS read-write
                        STATUS current
                        DESCRIPTION
                                "dial-plan part-timeout TIMEOUT (ms)"
                        ::= { fkGponProfileVoIPDetailControl 83 }

                
                -- 1.3.6.1.4.1.10428 9 1.101.23.5.5.5.2.84
                fkGponProfileVoIPDetailControlDialplanFormat OBJECT-TYPE
                        SYNTAX INTEGER
                                {
                                h248(1),
                                nsc(2),
                                vendor(3)
                                }
                        MAX-ACCESS read-write
                        STATUS current
                        DESCRIPTION
                                "dial-plan format (h248|nsc|vendor)"
                        ::= { fkGponProfileVoIPDetailControl 84 }

                
                -- 1.3.6.1.4.1.10428 9 1.101.23.5.5.5.2.85
                fkGponProfileVoIPDetailControlSpecialLineService OBJECT-TYPE
                        SYNTAX INTEGER
                                {
                                disable(0),
                                enableHotLine(1),
                                enableWarmLine(2)
                                }
                        MAX-ACCESS read-write
                        STATUS current
                        DESCRIPTION
                                "Special Line Service"
                        ::= { fkGponProfileVoIPDetailControl 85 }

                
                -- 1.3.6.1.4.1.10428 9 1.101.23.5.5.5.2.86
                fkGponProfileVoIPDetailControlWarmLineTimeout OBJECT-TYPE
                        SYNTAX Integer32 (0..30)
                        MAX-ACCESS read-write
                        STATUS current
                        DESCRIPTION
                                "Warm Line Waiting Time"
                        ::= { fkGponProfileVoIPDetailControl 86 }

                
                -- 1.3.6.1.4.1.10428 9 1.101.23.5.5.5.2.87
                fkGponProfileVoIPDetailControlLineNumber OBJECT-TYPE
                        SYNTAX OCTET STRING
                        MAX-ACCESS read-write
                        STATUS current
                        DESCRIPTION
                                "Special Line Number"
                        ::= { fkGponProfileVoIPDetailControl 87 }

                
                -- 1.3.6.1.4.1.10428 9 1.101.23.5.5.5.2.88
                fkGponProfileVoIPDetailControlThreeWaySSWMixing OBJECT-TYPE
                        SYNTAX INTEGER
                                {
                                server(0),
                                client(1)
                                }
                        MAX-ACCESS read-write
                        STATUS current
                        DESCRIPTION
                                "3Way Call Voice Mixing"
                        ::= { fkGponProfileVoIPDetailControl 88 }

                
                -- 1.3.6.1.4.1.10428 9 1.101.23.5.5.5.2.89
                fkGponProfileVoIPDetailControlSIPDNSCache OBJECT-TYPE
                        SYNTAX INTEGER
                                {
                                ttl(0),
                                permanent(1)
                                }
                        MAX-ACCESS read-write
                        STATUS current
                        DESCRIPTION
                                "SIP Stack DNS Cache update policy"
                        ::= { fkGponProfileVoIPDetailControl 89 }

                
                -- 1.3.6.1.4.1.10428 9 1.101.23.5.5.5.2.90
                fkGponProfileVoIPDetailControlSIPTimerT1 OBJECT-TYPE
                        SYNTAX Integer32 (0..2500)
                        MAX-ACCESS read-write
                        STATUS current
                        DESCRIPTION
                                "First Response Wait Time"
                        ::= { fkGponProfileVoIPDetailControl 90 }

                
                -- 1.3.6.1.4.1.10428 9 1.101.23.5.5.5.2.91
                fkGponProfileVoIPDetailControlSIPTimerT2 OBJECT-TYPE
                        SYNTAX Integer32 (0..5000)
                        MAX-ACCESS read-write
                        STATUS current
                        DESCRIPTION
                                "Next Increase Waiting Time"
                        ::= { fkGponProfileVoIPDetailControl 91 }

                
                -- 1.3.6.1.4.1.10428 9 1.101.23.5.5.5.2.92
                fkGponProfileVoIPDetailControlSIPTimerTd OBJECT-TYPE
                        SYNTAX Integer32 (5000..65535)
                        MAX-ACCESS read-write
                        STATUS current
                        DESCRIPTION
                                "Max Transaction Time"
                        ::= { fkGponProfileVoIPDetailControl 92 }

                
                -- 1.3.6.1.4.1.10428 9 1.101.23.5.5.5.2.93
                fkGponProfileVoIPDetailControlSIPSessionTimer OBJECT-TYPE
                        SYNTAX INTEGER
                                {
                                disable(0),
                                enable(1)
                                }
                        MAX-ACCESS read-write
                        STATUS current
                        DESCRIPTION
                                "SIP Session Timer"
                        ::= { fkGponProfileVoIPDetailControl 93 }

                
                -- 1.3.6.1.4.1.10428 9 1.101.23.5.5.5.2.94
                fkGponProfileVoIPDetailControlSIPSessionTimeout OBJECT-TYPE
                        SYNTAX Integer32 (0..65535)
                        MAX-ACCESS read-write
                        STATUS current
                        DESCRIPTION
                                "SIP Session Timer Timeout"
                        ::= { fkGponProfileVoIPDetailControl 94 }

                
                -- 1.3.6.1.4.1.10428 9 1.101.23.5.5.5.2.95
                fkGponProfileVoIPDetailControlSIPEndOfDigit OBJECT-TYPE
                        SYNTAX INTEGER
                                {
                                disable(0),
                                enable(1)
                                }
                        MAX-ACCESS read-write
                        STATUS current
                        DESCRIPTION
                                "SIP End of Digit"
                        ::= { fkGponProfileVoIPDetailControl 95 }

                
                -- 1.3.6.1.4.1.10428 9 1.101.23.5.5.5.2.96
                fkGponProfileVoIPDetailControlSIPEndSharpToken OBJECT-TYPE
                        SYNTAX INTEGER
                                {
                                hex(0),
                                ascii(1)
                                }
                        MAX-ACCESS read-write
                        STATUS current
                        DESCRIPTION
                                "SIP End # Token."
                        ::= { fkGponProfileVoIPDetailControl 96 }

                
--  1.3.6.1.4.1.10428 9 1.101.23.5.5.1.3
                -- 1.3.6.1.4.1.10428 9 1.101.23.5.5.5.3
                fkGponProfileVoIPDetailNotification OBJECT IDENTIFIER ::= { fkGponProfileVoIPDetail 3 }

                
--  1.3.6.1.4.1.10428 9 1.101.23.5.5.1.3.1
                -- 1.3.6.1.4.1.10428 9 1.101.23.5.5.5.3.1
                fkGponProfileVoIPDetailProfileCreated NOTIFICATION-TYPE
                        OBJECTS { fkGponProfileVoIPDetailControlRequest, fkGponProfileVoIPDetailControlTimeStamp, fkGponProfileVoIPDetailControlReqResult, fkGponProfileVoIPDetailControlName, fkGponProfileVoIPDetailControlProtocol
                                 }
                        STATUS current
                        DESCRIPTION 
                                "Description."
                        ::= { fkGponProfileVoIPDetailNotification 1 }

                
--  1.3.6.1.4.1.10428 9 1.101.23.5.5.1.3.1
                -- 1.3.6.1.4.1.10428 9 1.101.23.5.5.5.3.2
                fkGponProfileVoIPDetailProfileDeleted NOTIFICATION-TYPE
                        OBJECTS { fkGponProfileVoIPDetailControlRequest, fkGponProfileVoIPDetailControlTimeStamp, fkGponProfileVoIPDetailControlReqResult, fkGponProfileVoIPDetailControlIndex }
                        STATUS current
                        DESCRIPTION 
                                "Description."
                        ::= { fkGponProfileVoIPDetailNotification 2 }

                
--  1.3.6.1.4.1.10428 9 1.101.23.5.5.1.3.1
                -- 1.3.6.1.4.1.10428 9 1.101.23.5.5.5.3.3
                fkGponProfileVoIPDetailFaxModeChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlFaxMode
                                 }
                        STATUS current
                        DESCRIPTION 
                                "Description."
                        ::= { fkGponProfileVoIPDetailNotification 3 }

                
--  1.3.6.1.4.1.10428 9 1.101.23.5.5.1.3.1
                -- 1.3.6.1.4.1.10428 9 1.101.23.5.5.5.3.4
                fkGponProfileVoIPDetailCodec1stChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCodecType1st, 
                                fkGponProfileVoIPDetailControlCodecPeriod1st, fkGponProfileVoIPDetailControlCodecSilenceSuppression1st }
                        STATUS current
                        DESCRIPTION 
                                "Description."
                        ::= { fkGponProfileVoIPDetailNotification 4 }

                
--  1.3.6.1.4.1.10428 9 1.101.23.5.5.1.3.1
                -- 1.3.6.1.4.1.10428 9 1.101.23.5.5.5.3.5
                fkGponProfileVoIPDetailCodec2ndChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCodecType2nd, 
                                fkGponProfileVoIPDetailControlCodecPeriod2nd, fkGponProfileVoIPDetailControlCodecSilenceSuppression2nd }
                        STATUS current
                        DESCRIPTION 
                                "Description."
                        ::= { fkGponProfileVoIPDetailNotification 5 }

                
--  1.3.6.1.4.1.10428 9 1.101.23.5.5.1.3.1
                -- 1.3.6.1.4.1.10428 9 1.101.23.5.5.5.3.6
                fkGponProfileVoIPDetailCodec3rdChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCodecType3rd, 
                                fkGponProfileVoIPDetailControlCodecPeriod3rd, fkGponProfileVoIPDetailControlCodecSilenceSuppression3rd }
                        STATUS current
                        DESCRIPTION 
                                "Description."
                        ::= { fkGponProfileVoIPDetailNotification 6 }

                
--  1.3.6.1.4.1.10428 9 1.101.23.5.5.1.3.1
                -- 1.3.6.1.4.1.10428 9 1.101.23.5.5.5.3.7
                fkGponProfileVoIPDetailCodec4thChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCodecType4th, 
                                fkGponProfileVoIPDetailCodecControlPeriod4th, fkGponProfileVoIPDetailControlCodecSilenceSuppression4th }
                        STATUS current
                        DESCRIPTION 
                                "Description."
                        ::= { fkGponProfileVoIPDetailNotification 7 }

                
--  1.3.6.1.4.1.10428 9 1.101.23.5.5.1.3.1
                -- 1.3.6.1.4.1.10428 9 1.101.23.5.5.5.3.8
                fkGponProfileVoIPDetailOobDtmfChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlOobdtmf
                                 }
                        STATUS current
                        DESCRIPTION 
                                "Description."
                        ::= { fkGponProfileVoIPDetailNotification 8 }

                
--  1.3.6.1.4.1.10428 9 1.101.23.5.5.1.3.1
                -- 1.3.6.1.4.1.10428 9 1.101.23.5.5.5.3.9
                fkGponProfileVoIPDetailAnnouncementTypeChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlAnnouncementType
                                 }
                        STATUS current
                        DESCRIPTION 
                                "Description."
                        ::= { fkGponProfileVoIPDetailNotification 9 }

                
--  1.3.6.1.4.1.10428 9 1.101.23.5.5.1.3.1
                -- 1.3.6.1.4.1.10428 9 1.101.23.5.5.5.3.10
                fkGponProfileVoIPDetailJitterTargetChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlJitterTarget
                                 }
                        STATUS current
                        DESCRIPTION 
                                "Description."
                        ::= { fkGponProfileVoIPDetailNotification 10 }

                
--  1.3.6.1.4.1.10428 9 1.101.23.5.5.1.3.1
                -- 1.3.6.1.4.1.10428 9 1.101.23.5.5.5.3.11
                fkGponProfileVoIPDetailJitterBuffMaxChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlJitterBuffMax
                                 }
                        STATUS current
                        DESCRIPTION 
                                "Description."
                        ::= { fkGponProfileVoIPDetailNotification 11 }

                
--  1.3.6.1.4.1.10428 9 1.101.23.5.5.1.3.1
                -- 1.3.6.1.4.1.10428 9 1.101.23.5.5.5.3.12
                fkGponProfileVoIPDetailEchoCancelChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlEchoCancel
                                 }
                        STATUS current
                        DESCRIPTION 
                                "Description."
                        ::= { fkGponProfileVoIPDetailNotification 12 }

                
--  1.3.6.1.4.1.10428 9 1.101.23.5.5.1.3.1
                -- 1.3.6.1.4.1.10428 9 1.101.23.5.5.5.3.13
                fkGponProfileVoIPDetailPstnProtoChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlPstnProtoVariant
                                 }
                        STATUS current
                        DESCRIPTION 
                                "Description."
                        ::= { fkGponProfileVoIPDetailNotification 13 }

                
--  1.3.6.1.4.1.10428 9 1.101.23.5.5.1.3.1
                -- 1.3.6.1.4.1.10428 9 1.101.23.5.5.5.3.14
                fkGponProfileVoIPDetailDtmfDigitChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlDtmfDigitLevels, 
                                fkGponProfileVoIPDetailControlDtmfDigitDuration }
                        STATUS current
                        DESCRIPTION 
                                "Description."
                        ::= { fkGponProfileVoIPDetailNotification 14 }

                
--  1.3.6.1.4.1.10428 9 1.101.23.5.5.1.3.1
                -- 1.3.6.1.4.1.10428 9 1.101.23.5.5.5.3.15
                fkGponProfileVoIPDetailHookFlashTimeMinChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlHookFlashTimeMin
                                 }
                        STATUS current
                        DESCRIPTION 
                                "Description."
                        ::= { fkGponProfileVoIPDetailNotification 15 }

                
--  1.3.6.1.4.1.10428 9 1.101.23.5.5.1.3.1
                -- 1.3.6.1.4.1.10428 9 1.101.23.5.5.5.3.16
                fkGponProfileVoIPDetailHookFlashTimeMaxChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlHookFlashTimeMax
                                 }
                        STATUS current
                        DESCRIPTION 
                                "Description."
                        ::= { fkGponProfileVoIPDetailNotification 16 }

                
--  1.3.6.1.4.1.10428 9 1.101.23.5.5.1.3.1
                -- 1.3.6.1.4.1.10428 9 1.101.23.5.5.5.3.17
                fkGponProfileVoIPDetailSignalingCodeChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlSignalingCode
                                 }
                        STATUS current
                        DESCRIPTION 
                                "Description."
                        ::= { fkGponProfileVoIPDetailNotification 17 }

                
--  1.3.6.1.4.1.10428 9 1.101.23.5.5.1.3.1
                -- 1.3.6.1.4.1.10428 9 1.101.23.5.5.5.3.18
                fkGponProfileVoIPDetailRtpLocalPortChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlRtpLocalPortMin, 
                                fkGponProfileVoIPDetailControlRtpLocalPortMax }
                        STATUS current
                        DESCRIPTION 
                                "Description."
                        ::= { fkGponProfileVoIPDetailNotification 18 }

                
--  1.3.6.1.4.1.10428 9 1.101.23.5.5.1.3.1
                -- 1.3.6.1.4.1.10428 9 1.101.23.5.5.5.3.19
                fkGponProfileVoIPDetailRtpDscpMarkChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlRtpDscpMark
                                 }
                        STATUS current
                        DESCRIPTION 
                                "Description."
                        ::= { fkGponProfileVoIPDetailNotification 19 }

                
--  1.3.6.1.4.1.10428 9 1.101.23.5.5.1.3.1
                -- 1.3.6.1.4.1.10428 9 1.101.23.5.5.5.3.20
                fkGponProfileVoIPDetailRtpPiggybackEventChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlRtpPiggybackEvent
                                 }
                        STATUS current
                        DESCRIPTION 
                                "Description."
                        ::= { fkGponProfileVoIPDetailNotification 20 }

                
--  1.3.6.1.4.1.10428 9 1.101.23.5.5.1.3.1
                -- 1.3.6.1.4.1.10428 9 1.101.23.5.5.5.3.21
                fkGponProfileVoIPDetailRtpToneEventChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlRtpToneEvent
                                 }
                        STATUS current
                        DESCRIPTION 
                                "Description."
                        ::= { fkGponProfileVoIPDetailNotification 21 }

                
--  1.3.6.1.4.1.10428 9 1.101.23.5.5.1.3.1
                -- 1.3.6.1.4.1.10428 9 1.101.23.5.5.5.3.22
                fkGponProfileVoIPDetailRtpDtmfEventChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlRtpDtmfEvent
                                 }
                        STATUS current
                        DESCRIPTION 
                                "Description."
                        ::= { fkGponProfileVoIPDetailNotification 22 }

                
--  1.3.6.1.4.1.10428 9 1.101.23.5.5.1.3.1
                -- 1.3.6.1.4.1.10428 9 1.101.23.5.5.5.3.23
                fkGponProfileVoIPDetailRtpCasEventChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlRtpCasEvent
                                 }
                        STATUS current
                        DESCRIPTION 
                                "Description."
                        ::= { fkGponProfileVoIPDetailNotification 23 }

                
--  1.3.6.1.4.1.10428 9 1.101.23.5.5.1.3.1
                -- 1.3.6.1.4.1.10428 9 1.101.23.5.5.5.3.24
                fkGponProfileVoIPDetailProtocolChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlProtocol
                                 }
                        STATUS current
                        DESCRIPTION 
                                "Description."
                        ::= { fkGponProfileVoIPDetailNotification 24 }

                
--  1.3.6.1.4.1.10428 9 1.101.23.5.5.1.3.1
                -- 1.3.6.1.4.1.10428 9 1.101.23.5.5.5.3.25
                fkGponProfileVoIPDetailMgcPriServerChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlMgcPriServer
                                 }
                        STATUS current
                        DESCRIPTION 
                                "Description."
                        ::= { fkGponProfileVoIPDetailNotification 25 }

                
--  1.3.6.1.4.1.10428 9 1.101.23.5.5.1.3.1
                -- 1.3.6.1.4.1.10428 9 1.101.23.5.5.5.3.26
                fkGponProfileVoIPDetailMgcSecServerChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlMgcSecServer
                                 }
                        STATUS current
                        DESCRIPTION 
                                "Description."
                        ::= { fkGponProfileVoIPDetailNotification 26 }

                
--  1.3.6.1.4.1.10428 9 1.101.23.5.5.1.3.1
                -- 1.3.6.1.4.1.10428 9 1.101.23.5.5.5.3.27
                fkGponProfileVoIPDetailMgcVersionChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlMgcMsgVersion
                                 }
                        STATUS current
                        DESCRIPTION 
                                "Description."
                        ::= { fkGponProfileVoIPDetailNotification 27 }

                
--  1.3.6.1.4.1.10428 9 1.101.23.5.5.1.3.1
                -- 1.3.6.1.4.1.10428 9 1.101.23.5.5.5.3.28
                fkGponProfileVoIPDetailMgcFormatChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlMgcMsgFormat
                                 }
                        STATUS current
                        DESCRIPTION 
                                "Description."
                        ::= { fkGponProfileVoIPDetailNotification 28 }

                
--  1.3.6.1.4.1.10428 9 1.101.23.5.5.1.3.1
                -- 1.3.6.1.4.1.10428 9 1.101.23.5.5.5.3.29
                fkGponProfileVoIPDetailMgcMaxRetryTimeChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlMgcMaxRetryTime
                                 }
                        STATUS current
                        DESCRIPTION 
                                "Description."
                        ::= { fkGponProfileVoIPDetailNotification 29 }

                
--  1.3.6.1.4.1.10428 9 1.101.23.5.5.1.3.1
                -- 1.3.6.1.4.1.10428 9 1.101.23.5.5.5.3.30
                fkGponProfileVoIPDetailMgcRetryAttemptsChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlMgcMaxRetryAttempts
                                 }
                        STATUS current
                        DESCRIPTION 
                                "Description."
                        ::= { fkGponProfileVoIPDetailNotification 30 }

                
--  1.3.6.1.4.1.10428 9 1.101.23.5.5.1.3.1
                -- 1.3.6.1.4.1.10428 9 1.101.23.5.5.5.3.31
                fkGponProfileVoIPDetailMgcServiceChangeDelayChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlMgcSvcChangeDelay
                                 }
                        STATUS current
                        DESCRIPTION 
                                "Description."
                        ::= { fkGponProfileVoIPDetailNotification 31 }

                
--  1.3.6.1.4.1.10428 9 1.101.23.5.5.1.3.1
                -- 1.3.6.1.4.1.10428 9 1.101.23.5.5.5.3.32
                fkGponProfileVoIPDetailMgcTerminationIdChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlMgcTerminationId
                                 }
                        STATUS current
                        DESCRIPTION 
                                "Description."
                        ::= { fkGponProfileVoIPDetailNotification 32 }

                
--  1.3.6.1.4.1.10428 9 1.101.23.5.5.1.3.1
                -- 1.3.6.1.4.1.10428 9 1.101.23.5.5.5.3.33
                fkGponProfileVoIPDetailMgcSoftswitchChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlMgcSoftswitch
                                 }
                        STATUS current
                        DESCRIPTION 
                                "Description."
                        ::= { fkGponProfileVoIPDetailNotification 33 }

                
--  1.3.6.1.4.1.10428 9 1.101.23.5.5.1.3.1
                -- 1.3.6.1.4.1.10428 9 1.101.23.5.5.5.3.34
                fkGponProfileVoIPDetailVoicemailServerChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlVoicemailServer
                                 }
                        STATUS current
                        DESCRIPTION 
                                "Description."
                        ::= { fkGponProfileVoIPDetailNotification 34 }

                
--  1.3.6.1.4.1.10428 9 1.101.23.5.5.1.3.1
                -- 1.3.6.1.4.1.10428 9 1.101.23.5.5.5.3.35
                fkGponProfileVoIPDetailVoicemailExpireTimeChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlVoicemmailExpireTime
                                 }
                        STATUS current
                        DESCRIPTION 
                                "Description."
                        ::= { fkGponProfileVoIPDetailNotification 35 }

                
--  1.3.6.1.4.1.10428 9 1.101.23.5.5.1.3.1
                -- 1.3.6.1.4.1.10428 9 1.101.23.5.5.5.3.36
                fkGponProfileVoIPDetailReleaseTimeChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlReleaseTime
                                 }
                        STATUS current
                        DESCRIPTION 
                                "Description."
                        ::= { fkGponProfileVoIPDetailNotification 36 }

                
--  1.3.6.1.4.1.10428 9 1.101.23.5.5.1.3.1
                -- 1.3.6.1.4.1.10428 9 1.101.23.5.5.5.3.37
                fkGponProfileVoIPDetailRohTimerChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlRohTimer
                                 }
                        STATUS current
                        DESCRIPTION 
                                "Description."
                        ::= { fkGponProfileVoIPDetailNotification 37 }

                
--  1.3.6.1.4.1.10428 9 1.101.23.5.5.1.3.1
                -- 1.3.6.1.4.1.10428 9 1.101.23.5.5.5.3.38
                fkGponProfileVoIPDetailProxyServerChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlProxyServer
                                 }
                        STATUS current
                        DESCRIPTION 
                                "Description."
                        ::= { fkGponProfileVoIPDetailNotification 38 }

                
--  1.3.6.1.4.1.10428 9 1.101.23.5.5.1.3.1
                -- 1.3.6.1.4.1.10428 9 1.101.23.5.5.5.3.39
                fkGponProfileVoIPDetailOutboundProxyServerChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlOutboundProxyServer
                                 }
                        STATUS current
                        DESCRIPTION 
                                "Description."
                        ::= { fkGponProfileVoIPDetailNotification 39 }

                
--  1.3.6.1.4.1.10428 9 1.101.23.5.5.1.3.1
                -- 1.3.6.1.4.1.10428 9 1.101.23.5.5.5.3.40
                fkGponProfileVoIPDetailRegisterServerChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlRegisterServer
                                 }
                        STATUS current
                        DESCRIPTION 
                                "Description."
                        ::= { fkGponProfileVoIPDetailNotification 40 }

                
--  1.3.6.1.4.1.10428 9 1.101.23.5.5.1.3.1
                -- 1.3.6.1.4.1.10428 9 1.101.23.5.5.5.3.41
                fkGponProfileVoIPDetailHostpartServerChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlHostPartServer
                                 }
                        STATUS current
                        DESCRIPTION 
                                "Description."
                        ::= { fkGponProfileVoIPDetailNotification 41 }

                
--  1.3.6.1.4.1.10428 9 1.101.23.5.5.1.3.1
                -- 1.3.6.1.4.1.10428 9 1.101.23.5.5.5.3.42
                fkGponProfileVoIPDetailDnsChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlPriDns, 
                                fkGponProfileVoIPDetailControlSecDns }
                        STATUS current
                        DESCRIPTION 
                                "Description."
                        ::= { fkGponProfileVoIPDetailNotification 42 }

                
--  1.3.6.1.4.1.10428 9 1.101.23.5.5.1.3.1
                -- 1.3.6.1.4.1.10428 9 1.101.23.5.5.5.3.43
                fkGponProfileVoIPDetailRegExpTimeChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlRegExpTime
                                 }
                        STATUS current
                        DESCRIPTION 
                                "Description."
                        ::= { fkGponProfileVoIPDetailNotification 43 }

                
--  1.3.6.1.4.1.10428 9 1.101.23.5.5.1.3.1
                -- 1.3.6.1.4.1.10428 9 1.101.23.5.5.5.3.44
                fkGponProfileVoIPDetailReregHeadStartTimeChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlReregHeadStartTime
                                 }
                        STATUS current
                        DESCRIPTION 
                                "Description."
                        ::= { fkGponProfileVoIPDetailNotification 44 }

                
--  1.3.6.1.4.1.10428 9 1.101.23.5.5.1.3.1
                -- 1.3.6.1.4.1.10428 9 1.101.23.5.5.5.3.45
                fkGponProfileVoIPDetailSoftSwitchChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlSoftSwitchVendor
                                 }
                        STATUS current
                        DESCRIPTION 
                                "Description."
                        ::= { fkGponProfileVoIPDetailNotification 45 }

                
--  1.3.6.1.4.1.10428 9 1.101.23.5.5.1.3.1
                -- 1.3.6.1.4.1.10428 9 1.101.23.5.5.5.3.46
                fkGponProfileVoIPDetailSipOptionTransmitCtlChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlSipOptionTransmitCtl
                                 }
                        STATUS current
                        DESCRIPTION 
                                "Description."
                        ::= { fkGponProfileVoIPDetailNotification 46 }

                
--  1.3.6.1.4.1.10428 9 1.101.23.5.5.1.3.1
                -- 1.3.6.1.4.1.10428 9 1.101.23.5.5.5.3.47
                fkGponProfileVoIPDetailSipUriFormatChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlSipUriFormat
                                 }
                        STATUS current
                        DESCRIPTION 
                                "Description."
                        ::= { fkGponProfileVoIPDetailNotification 47 }

                
--  1.3.6.1.4.1.10428 9 1.101.23.5.5.1.3.1
                -- 1.3.6.1.4.1.10428 9 1.101.23.5.5.5.3.48
                fkGponProfileVoIPDetailCallerIdChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCallerId
                                 }
                        STATUS current
                        DESCRIPTION 
                                "Description."
                        ::= { fkGponProfileVoIPDetailNotification 48 }

                
--  1.3.6.1.4.1.10428 9 1.101.23.5.5.1.3.1
                -- 1.3.6.1.4.1.10428 9 1.101.23.5.5.5.3.49
                fkGponProfileVoIPDetailCallWaitingChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCallWaiting
                                 }
                        STATUS current
                        DESCRIPTION 
                                "Description."
                        ::= { fkGponProfileVoIPDetailNotification 49 }

                
--  1.3.6.1.4.1.10428 9 1.101.23.5.5.1.3.1
                -- 1.3.6.1.4.1.10428 9 1.101.23.5.5.5.3.50
                fkGponProfileVoIPDetailCallProgressTransferChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCallProgressTransfer
                                 }
                        STATUS current
                        DESCRIPTION 
                                "Description."
                        ::= { fkGponProfileVoIPDetailNotification 50 }

                
--  1.3.6.1.4.1.10428 9 1.101.23.5.5.1.3.1
                -- 1.3.6.1.4.1.10428 9 1.101.23.5.5.5.3.51
                fkGponProfileVoIPDetailCallPresentChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCallProgressTransfer
                                 }
                        STATUS current
                        DESCRIPTION 
                                "Description."
                        ::= { fkGponProfileVoIPDetailNotification 51 }

                
--  1.3.6.1.4.1.10428 9 1.101.23.5.5.1.3.1
                -- 1.3.6.1.4.1.10428 9 1.101.23.5.5.5.3.52
                fkGponProfileVoIPDetailDirectConnectChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlDirectConnect
                                 }
                        STATUS current
                        DESCRIPTION 
                                "Description."
                        ::= { fkGponProfileVoIPDetailNotification 52 }

                
--  1.3.6.1.4.1.10428 9 1.101.23.5.5.1.3.1
                -- 1.3.6.1.4.1.10428 9 1.101.23.5.5.5.3.53
                fkGponProfileVoIPDetailDirectConnectUriChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlDirectConnectUri
                                 }
                        STATUS current
                        DESCRIPTION 
                                "Description."
                        ::= { fkGponProfileVoIPDetailNotification 53 }

                
--  1.3.6.1.4.1.10428 9 1.101.23.5.5.1.3.1
                -- 1.3.6.1.4.1.10428 9 1.101.23.5.5.5.3.54
                fkGponProfileVoIPDetailBridgedLineAgentUriChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlBridgedLineAgentUri
                                 }
                        STATUS current
                        DESCRIPTION 
                                "Description."
                        ::= { fkGponProfileVoIPDetailNotification 54 }

                
--  1.3.6.1.4.1.10428 9 1.101.23.5.5.1.3.1
                -- 1.3.6.1.4.1.10428 9 1.101.23.5.5.5.3.55
                fkGponProfileVoIPDetailConferenceFactoryUriChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlConferenceFactoryUri
                                 }
                        STATUS current
                        DESCRIPTION 
                                "Description."
                        ::= { fkGponProfileVoIPDetailNotification 55 }

                
--  1.3.6.1.4.1.10428 9 1.101.23.5.5.1.3.1
                -- 1.3.6.1.4.1.10428 9 1.101.23.5.5.5.3.56
                fkGponProfileVoIPDetailCancelCallWaitChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCancelCallWait
                                 }
                        STATUS current
                        DESCRIPTION 
                                "Description."
                        ::= { fkGponProfileVoIPDetailNotification 56 }

                
--  1.3.6.1.4.1.10428 9 1.101.23.5.5.1.3.1
                -- 1.3.6.1.4.1.10428 9 1.101.23.5.5.5.3.57
                fkGponProfileVoIPDetailCallHoldChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCallHold
                                 }
                        STATUS current
                        DESCRIPTION 
                                "Description."
                        ::= { fkGponProfileVoIPDetailNotification 57 }

                
--  1.3.6.1.4.1.10428 9 1.101.23.5.5.1.3.1
                -- 1.3.6.1.4.1.10428 9 1.101.23.5.5.5.3.58
                fkGponProfileVoIPDetailCallParkChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCallPark
                                 }
                        STATUS current
                        DESCRIPTION 
                                "Description."
                        ::= { fkGponProfileVoIPDetailNotification 58 }

                
--  1.3.6.1.4.1.10428 9 1.101.23.5.5.1.3.1
                -- 1.3.6.1.4.1.10428 9 1.101.23.5.5.5.3.59
                fkGponProfileVoIPDetailCallerIdActChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCallerIdAct
                                 }
                        STATUS current
                        DESCRIPTION 
                                "Description."
                        ::= { fkGponProfileVoIPDetailNotification 59 }

                
--  1.3.6.1.4.1.10428 9 1.101.23.5.5.1.3.1
                -- 1.3.6.1.4.1.10428 9 1.101.23.5.5.5.3.60
                fkGponProfileVoIPDetailCallerIdDeactChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlCallerIdDeact
                                 }
                        STATUS current
                        DESCRIPTION 
                                "Description."
                        ::= { fkGponProfileVoIPDetailNotification 60 }

                
--  1.3.6.1.4.1.10428 9 1.101.23.5.5.1.3.1
                -- 1.3.6.1.4.1.10428 9 1.101.23.5.5.5.3.61
                fkGponProfileVoIPDetailDoNotDisturbActChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlDoNotDisturbAct
                                 }
                        STATUS current
                        DESCRIPTION 
                                "Description."
                        ::= { fkGponProfileVoIPDetailNotification 61 }

                
--  1.3.6.1.4.1.10428 9 1.101.23.5.5.1.3.1
                -- 1.3.6.1.4.1.10428 9 1.101.23.5.5.5.3.62
                fkGponProfileVoIPDetailDoNotDisturbDeactChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlDoNotDisturbDeact
                                 }
                        STATUS current
                        DESCRIPTION 
                                "Description."
                        ::= { fkGponProfileVoIPDetailNotification 62 }

                
--  1.3.6.1.4.1.10428 9 1.101.23.5.5.1.3.1
                -- 1.3.6.1.4.1.10428 9 1.101.23.5.5.5.3.63
                fkGponProfileVoIPDetailDoNotDisturbPinChangeChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlDoNotDisturbPinChange
                                 }
                        STATUS current
                        DESCRIPTION 
                                "Description."
                        ::= { fkGponProfileVoIPDetailNotification 63 }

                
--  1.3.6.1.4.1.10428 9 1.101.23.5.5.1.3.1
                -- 1.3.6.1.4.1.10428 9 1.101.23.5.5.5.3.64
                fkGponProfileVoIPDetailEmergServiceNumberChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlEmergServiceNumber
                                 }
                        STATUS current
                        DESCRIPTION 
                                "Description."
                        ::= { fkGponProfileVoIPDetailNotification 64 }

                
--  1.3.6.1.4.1.10428 9 1.101.23.5.5.1.3.1
                -- 1.3.6.1.4.1.10428 9 1.101.23.5.5.5.3.65
                fkGponProfileVoIPDetailIntercomServiceChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlIntercomService
                                 }
                        STATUS current
                        DESCRIPTION 
                                "Description."
                        ::= { fkGponProfileVoIPDetailNotification 65 }

                
                -- 1.3.6.1.4.1.10428 9 1.101.23.5.5.5.3.66
                fkGponProfileVoIPDetailDialPlanCritTimeOutChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlDialplanCritTimeout
                                 }
                        STATUS current
                        DESCRIPTION 
                                "Description."
                        ::= { fkGponProfileVoIPDetailNotification 66 }

                
                -- 1.3.6.1.4.1.10428 9 1.101.23.5.5.5.3.67
                fkGponProfileVoIPDetailDialPlanPartTimeOutChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlDialplanPartTimeout
                                 }
                        STATUS current
                        DESCRIPTION 
                                "Description."
                        ::= { fkGponProfileVoIPDetailNotification 67 }

                
                -- 1.3.6.1.4.1.10428 9 1.101.23.5.5.5.3.68
                fkGponProfileVoIPDetailDialPlanFormatChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlDialplanFormat
                                 }
                        STATUS current
                        DESCRIPTION 
                                "Description."
                        ::= { fkGponProfileVoIPDetailNotification 68 }

                
                -- 1.3.6.1.4.1.10428 9 1.101.23.5.5.5.3.69
                fkGponProfileVoIPDetailSpecialLineServiceChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlSpecialLineService, 
                                fkGponProfileVoIPDetailControlWarmLineTimeout, fkGponProfileVoIPDetailControlLineNumber }
                        STATUS current
                        DESCRIPTION 
                                "setSpecialLineService"
                        ::= { fkGponProfileVoIPDetailNotification 69 }

                
                -- 1.3.6.1.4.1.10428 9 1.101.23.5.5.5.3.70
                fkGponProfileVoIPDetailThreeWaySSWMixingChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlThreeWaySSWMixing
                                 }
                        STATUS current
                        DESCRIPTION 
                                "setThreeWaySSWMixing"
                        ::= { fkGponProfileVoIPDetailNotification 70 }

                
                -- 1.3.6.1.4.1.10428 9 1.101.23.5.5.5.3.71
                fkGponProfileVoIPDetailSIPDNSCacheChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlSIPDNSCache
                                 }
                        STATUS current
                        DESCRIPTION 
                                "setDNSCachePolicy"
                        ::= { fkGponProfileVoIPDetailNotification 71 }

                
                -- 1.3.6.1.4.1.10428 9 1.101.23.5.5.5.3.72
                fkGponProfileVoIPDetailSIPTimerChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlSIPTimerT1, 
                                fkGponProfileVoIPDetailControlSIPTimerT2, fkGponProfileVoIPDetailControlSIPTimerTd }
                        STATUS current
                        DESCRIPTION 
                                "setSIPTimer"
                        ::= { fkGponProfileVoIPDetailNotification 72 }

                
                -- 1.3.6.1.4.1.10428 9 1.101.23.5.5.5.3.73
                fkGponProfileVoIPDetailSIPSessionTimerChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlSIPSessionTimer, 
                                fkGponProfileVoIPDetailControlSIPSessionTimeout }
                        STATUS current
                        DESCRIPTION 
                                "setSessionTimer"
                        ::= { fkGponProfileVoIPDetailNotification 73 }

                
                -- 1.3.6.1.4.1.10428 9 1.101.23.5.5.5.3.74
                fkGponProfileVoIPDetailSIPEndOfDigitChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlSIPEndOfDigit
                                 }
                        STATUS current
                        DESCRIPTION 
                                "setEndOfDigit"
                        ::= { fkGponProfileVoIPDetailNotification 74 }

                
                -- 1.3.6.1.4.1.10428 9 1.101.23.5.5.5.3.75
                fkGponProfileVoIPDetailSIPEndSharpTokenChanged NOTIFICATION-TYPE
                        OBJECTS { fkGponProfileVoIPDetailControlRequest, fkGponProfileVoIPDetailControlTimeStamp, fkGponProfileVoIPDetailControlReqResult, fkGponProfileVoIPDetailControlIndex, fkGponProfileVoIPDetailControlSIPEndSharpToken
                                 }
                        STATUS current
                        DESCRIPTION 
                                "setEndSharpToken"
                        ::= { fkGponProfileVoIPDetailNotification 75 }

                
                -- 1.3.6.1.4.1.10428 9 1.101.23.5.5.6
                fkGponProfileVoIPDetailDialPlan OBJECT IDENTIFIER ::= { fkGponVoIP 6 }

                
                -- 1.3.6.1.4.1.10428 9 1.101.23.5.5.6.1
                fkGponProfileVoIPDetailDialPlanTable OBJECT-TYPE
                        SYNTAX SEQUENCE OF FkGponProfileVoIPDetailDialPlanEntry
                        MAX-ACCESS not-accessible
                        STATUS current
                        DESCRIPTION
                                "fkGponProfileVoIPDetailDialPlanTable"
                        ::= { fkGponProfileVoIPDetailDialPlan 1 }

                
                -- 1.3.6.1.4.1.10428 9 1.101.23.5.5.6.1.1
                fkGponProfileVoIPDetailDialPlanEntry OBJECT-TYPE
                        SYNTAX FkGponProfileVoIPDetailDialPlanEntry
                        MAX-ACCESS not-accessible
                        STATUS current
                        DESCRIPTION
                                "key: fkGponProfileVoIPDetailIndex, fkGponProfileVoIPDetailDialPlanTableIndex"
                        INDEX { fkGponProfileVoIPDetailIndex, fkGponProfileVoIPDetailDialPlanTableIndex }
                        ::= { fkGponProfileVoIPDetailDialPlanTable 1 }

                
                FkGponProfileVoIPDetailDialPlanEntry ::=
                        SEQUENCE { 
                                fkGponProfileVoIPDetailDialPlanTableIndex
                                        INTEGER,
                                fkGponProfileVoIPDetailDialPlanTableToken
                                        OCTET STRING
                         }

                -- 1.3.6.1.4.1.10428 9 1.101.23.5.5.6.1.1.1
                fkGponProfileVoIPDetailDialPlanTableIndex OBJECT-TYPE
                        SYNTAX INTEGER (1..65535)
                        MAX-ACCESS read-only
                        STATUS current
                        DESCRIPTION
                                "The Dial Plan Table Index."
                        ::= { fkGponProfileVoIPDetailDialPlanEntry 1 }

                
                -- 1.3.6.1.4.1.10428 9 1.101.23.5.5.6.1.1.2
                fkGponProfileVoIPDetailDialPlanTableToken OBJECT-TYPE
                        SYNTAX OCTET STRING
                        MAX-ACCESS read-only
                        STATUS current
                        DESCRIPTION
                                "The Dial Plan Table Name."
                        ::= { fkGponProfileVoIPDetailDialPlanEntry 2 }

                
                -- 1.3.6.1.4.1.10428 9 1.101.23.5.5.6.2
                fkGponProfileVoIPDetailDialPlanControl OBJECT IDENTIFIER ::= { fkGponProfileVoIPDetailDialPlan 2 }

                
                -- 1.3.6.1.4.1.10428 9 1.101.23.5.5.6.2.1
                fkGponProfileVoIPDetailDialPlanControlRequest OBJECT-TYPE
                        SYNTAX INTEGER
                                {
                                addDialPlanTable(1),
                                delDialPlanTable(2)
                                }
                        MAX-ACCESS read-write
                        STATUS current
                        DESCRIPTION
                                "The request of a user command"
                        ::= { fkGponProfileVoIPDetailDialPlanControl 1 }

                
                -- 1.3.6.1.4.1.10428 9 1.101.23.5.5.6.2.2
                fkGponProfileVoIPDetailDialPlanControlStatus OBJECT-TYPE
                        SYNTAX FkControlStatusType
                        MAX-ACCESS read-write
                        STATUS current
                        DESCRIPTION
                                "The status of user command"
                        ::= { fkGponProfileVoIPDetailDialPlanControl 2 }

                
                -- 1.3.6.1.4.1.10428 9 1.101.23.5.5.6.2.3
                fkGponProfileVoIPDetailDialPlanControlTimer OBJECT-TYPE
                        SYNTAX Gauge32
                        MAX-ACCESS read-write
                        STATUS current
                        DESCRIPTION
                                "The maximum time for the manager for a long running user command"
                        ::= { fkGponProfileVoIPDetailDialPlanControl 3 }

                
                -- 1.3.6.1.4.1.10428 9 1.101.23.5.5.6.2.4
                fkGponProfileVoIPDetailDialPlanControlTimeStamp OBJECT-TYPE
                        SYNTAX TimeTicks
                        MAX-ACCESS read-write
                        STATUS current
                        DESCRIPTION
                                "The time stamp of the last command(end of command)"
                        ::= { fkGponProfileVoIPDetailDialPlanControl 4 }

                
                -- 1.3.6.1.4.1.10428 9 1.101.23.5.5.6.2.5
                fkGponProfileVoIPDetailDialPlanControlReqResult OBJECT-TYPE
                        SYNTAX FkControlRequestResultType
                        MAX-ACCESS read-write
                        STATUS current
                        DESCRIPTION
                                "The result of the last user command"
                        ::= { fkGponProfileVoIPDetailDialPlanControl 5 }

                
                -- 1.3.6.1.4.1.10428 9 1.101.23.5.5.6.2.6
                fkGponProfileVoIPDetailDialPlanControlProfileIndex OBJECT-TYPE
                        SYNTAX INTEGER (1..65535)
                        MAX-ACCESS read-write
                        STATUS current
                        DESCRIPTION
                                "fkGponProfileVoIPDetailIndex"
                        ::= { fkGponProfileVoIPDetailDialPlanControl 6 }

                
                -- 1.3.6.1.4.1.10428 9 1.101.23.5.5.6.2.7
                fkGponProfileVoIPDetailDialPlanControlTableIndex OBJECT-TYPE
                        SYNTAX INTEGER (1..65535)
                        MAX-ACCESS read-write
                        STATUS current
                        DESCRIPTION
                                "The Dial Plan Table Index."
                        ::= { fkGponProfileVoIPDetailDialPlanControl 7 }

                
                -- 1.3.6.1.4.1.10428 9 1.101.23.5.5.6.2.8
                fkGponProfileVoIPDetailDialPlanControlTableToken OBJECT-TYPE
                        SYNTAX OCTET STRING
                        MAX-ACCESS read-write
                        STATUS current
                        DESCRIPTION
                                "The Dial Plan Table Name."
                        ::= { fkGponProfileVoIPDetailDialPlanControl 8 }

                
                -- 1.3.6.1.4.1.10428 9 1.101.23.5.5.6.3
                fkGponProfileVoIPDetailDialPlanNotification OBJECT IDENTIFIER ::= { fkGponProfileVoIPDetailDialPlan 3 }

                
                -- 1.3.6.1.4.1.10428 9 1.101.23.5.5.6.3.1
                fkGponProfileVoIPDetailDialPlanTableCreated NOTIFICATION-TYPE
                        OBJECTS { fkGponProfileVoIPDetailDialPlanControlRequest, fkGponProfileVoIPDetailDialPlanControlTimeStamp, fkGponProfileVoIPDetailDialPlanControlReqResult, fkGponProfileVoIPDetailDialPlanControlProfileIndex, fkGponProfileVoIPDetailDialPlanControlTableIndex, 
                                fkGponProfileVoIPDetailDialPlanControlTableToken }
                        STATUS current
                        DESCRIPTION 
                                "Description."
                        ::= { fkGponProfileVoIPDetailDialPlanNotification 1 }

                
                -- 1.3.6.1.4.1.10428 9 1.101.23.5.5.6.3.2
                fkGponProfileVoIPDetailDialPlanTableDeleted NOTIFICATION-TYPE
                        OBJECTS { fkGponProfileVoIPDetailDialPlanControlRequest, fkGponProfileVoIPDetailDialPlanControlTimeStamp, fkGponProfileVoIPDetailDialPlanControlReqResult, fkGponProfileVoIPDetailDialPlanControlProfileIndex, fkGponProfileVoIPDetailDialPlanControlTableIndex
                                 }
                        STATUS current
                        DESCRIPTION 
                                "Description."
                        ::= { fkGponProfileVoIPDetailDialPlanNotification 2 }

                
                -- 1.3.6.1.4.1.10428 9 1.101.23.5.5.7
                fkGponProfileVoIPService OBJECT IDENTIFIER ::= { fkGponVoIP 7 }

                
                -- 1.3.6.1.4.1.10428 9 1.101.23.5.5.7.1
                fkGponProfileVoIPServiceTable OBJECT-TYPE
                        SYNTAX SEQUENCE OF FkGponProfileVoIPServiceEntry
                        MAX-ACCESS not-accessible
                        STATUS current
                        DESCRIPTION
                                "Description."
                        ::= { fkGponProfileVoIPService 1 }

                
                -- 1.3.6.1.4.1.10428 9 1.101.23.5.5.7.1.1
                fkGponProfileVoIPServiceEntry OBJECT-TYPE
                        SYNTAX FkGponProfileVoIPServiceEntry
                        MAX-ACCESS not-accessible
                        STATUS current
                        DESCRIPTION
                                "Description."
                        INDEX { fkGponOltId, fkGponOnuId, fkGponProfileVoIPServiceIndex }
                        ::= { fkGponProfileVoIPServiceTable 1 }

                
                FkGponProfileVoIPServiceEntry ::=
                        SEQUENCE { 
                                fkGponProfileVoIPServiceIndex
                                        Integer32,
                                fkGponProfileVoIPServiceMgcMessageId
                                        OCTET STRING
                         }

                -- 1.3.6.1.4.1.10428 9 1.101.23.5.5.7.1.1.1
                fkGponProfileVoIPServiceIndex OBJECT-TYPE
                        SYNTAX Integer32 (1..65535)
                        MAX-ACCESS read-only
                        STATUS current
                        DESCRIPTION
                                "The VoIP service index"
                        ::= { fkGponProfileVoIPServiceEntry 1 }

                
                -- 1.3.6.1.4.1.10428 9 1.101.23.5.5.7.1.1.2
                fkGponProfileVoIPServiceMgcMessageId OBJECT-TYPE
                        SYNTAX OCTET STRING
                        MAX-ACCESS read-only
                        STATUS current
                        DESCRIPTION
                                "The MGC message index."
                        ::= { fkGponProfileVoIPServiceEntry 2 }

                
                -- 1.3.6.1.4.1.10428 9 1.101.23.5.5.7.2
                fkGponProfileVoIPServiceControl OBJECT IDENTIFIER ::= { fkGponProfileVoIPService 2 }

                
--  1.3.6.1.4.1.10428 9 1.101.23.5.5.1.2.1
                -- 1.3.6.1.4.1.10428 9 1.101.23.5.5.7.2.1
                fkGponProfileVoIPServiceControlRequest OBJECT-TYPE
                        SYNTAX INTEGER { setMgcMessage(1) }
                        MAX-ACCESS read-write
                        STATUS current
                        DESCRIPTION
                                "The request of a user command"
                        ::= { fkGponProfileVoIPServiceControl 1 }

                
--  1.3.6.1.4.1.10428 9 1.101.23.5.5.1.2.2
                -- 1.3.6.1.4.1.10428 9 1.101.23.5.5.7.2.2
                fkGponProfileVoIPServiceControlStatus OBJECT-TYPE
                        SYNTAX FkControlStatusType
                        MAX-ACCESS read-only
                        STATUS current
                        DESCRIPTION
                                "The status of user command"
                        ::= { fkGponProfileVoIPServiceControl 2 }

                
--  1.3.6.1.4.1.10428 9 1.101.23.5.5.1.2.3
                -- 1.3.6.1.4.1.10428 9 1.101.23.5.5.7.2.3
                fkGponProfileVoIPServiceControlTimer OBJECT-TYPE
                        SYNTAX Gauge32
                        MAX-ACCESS read-write
                        STATUS current
                        DESCRIPTION
                                "The maximum time for the manager for a long running user command"
                        ::= { fkGponProfileVoIPServiceControl 3 }

                
--  1.3.6.1.4.1.10428 9 1.101.23.5.5.1.2.4
                -- 1.3.6.1.4.1.10428 9 1.101.23.5.5.7.2.4
                fkGponProfileVoIPServiceControlTimeStamp OBJECT-TYPE
                        SYNTAX TimeTicks
                        MAX-ACCESS read-only
                        STATUS current
                        DESCRIPTION
                                "The time stamp of the last command(end of command)"
                        ::= { fkGponProfileVoIPServiceControl 4 }

                
--  1.3.6.1.4.1.10428 9 1.101.23.5.5.1.2.5
                -- 1.3.6.1.4.1.10428 9 1.101.23.5.5.7.2.5
                fkGponProfileVoIPServiceControlReqResult OBJECT-TYPE
                        SYNTAX FkControlRequestResultType
                        MAX-ACCESS read-only
                        STATUS current
                        DESCRIPTION
                                "The result of the last user command"
                        ::= { fkGponProfileVoIPServiceControl 5 }

                
                -- 1.3.6.1.4.1.10428 9 1.101.23.5.5.7.2.6
                fkGponProfileVoIPServiceControlOltId OBJECT-TYPE
                        SYNTAX INTEGER (1..65535)
                        MAX-ACCESS read-write
                        STATUS current
                        DESCRIPTION
                                "The OLT index."
                        ::= { fkGponProfileVoIPServiceControl 6 }

                
                -- 1.3.6.1.4.1.10428 9 1.101.23.5.5.7.2.7
                fkGponProfileVoIPServiceControlOnuId OBJECT-TYPE
                        SYNTAX INTEGER (1..65535)
                        MAX-ACCESS read-write
                        STATUS current
                        DESCRIPTION
                                "The ONU index."
                        ::= { fkGponProfileVoIPServiceControl 7 }

                
                -- 1.3.6.1.4.1.10428 9 1.101.23.5.5.7.2.8
                fkGponProfileVoIPServiceControlIndex OBJECT-TYPE
                        SYNTAX Integer32 (1..65535)
                        MAX-ACCESS read-write
                        STATUS current
                        DESCRIPTION
                                "The VoIP service index"
                        ::= { fkGponProfileVoIPServiceControl 8 }

                
                -- 1.3.6.1.4.1.10428 9 1.101.23.5.5.7.2.9
                fkGponProfileVoIPServiceControlMgcMessageId OBJECT-TYPE
                        SYNTAX OCTET STRING
                        MAX-ACCESS read-write
                        STATUS current
                        DESCRIPTION
                                "The MGC message index."
                        ::= { fkGponProfileVoIPServiceControl 9 }

                
                -- 1.3.6.1.4.1.10428 9 1.101.23.5.5.7.3
                fkGponProfileVoIPServiceNotification OBJECT IDENTIFIER ::= { fkGponProfileVoIPService 3 }

                
                -- 1.3.6.1.4.1.10428 9 1.101.23.5.5.7.3.1
                fkGponProfileVoIPServiceMgcMessageChanged NOTIFICATION-TYPE
                        OBJECTS { fkGponProfileVoIPServiceControlRequest, fkGponProfileVoIPServiceControlTimeStamp, fkGponProfileVoIPServiceControlReqResult, fkGponProfileVoIPServiceControlOltId, fkGponProfileVoIPServiceControlOnuId, 
                                fkGponProfileVoIPServiceControlIndex, fkGponProfileVoIPServiceControlMgcMessageId }
                        STATUS current
                        DESCRIPTION 
                                "setMgcMessage"
                        ::= { fkGponProfileVoIPServiceNotification 1 }

                
--  1.3.6.1.4.1.10428 9 1.101.23.5.6
                -- 1.3.6.1.4.1.10428 9 1.101.23.5.6
                fkGponServiceProfile OBJECT IDENTIFIER ::= { fkGponProfile 6 }

                
--  1.3.6.1.4.1.10428 9 1.101.23.5.6.1
                -- 1.3.6.1.4.1.10428 9 1.101.23.5.6.1
                fkGponServiceProfileTable OBJECT-TYPE
                        SYNTAX SEQUENCE OF FkGponServiceProfileEntry
                        MAX-ACCESS not-accessible
                        STATUS current
                        DESCRIPTION
                                "fkGponServiceProfileTable"
                        ::= { fkGponServiceProfile 1 }

                
--  1.3.6.1.4.1.10428 9 1.101.23.5.6.1.1
                -- 1.3.6.1.4.1.10428 9 1.101.23.5.6.1.1
                fkGponServiceProfileEntry OBJECT-TYPE
                        SYNTAX FkGponServiceProfileEntry
                        MAX-ACCESS not-accessible
                        STATUS current
                        DESCRIPTION
                                "key: fkGponServiceProfileIndex"
                        INDEX { fkGponServiceProfileIndex }
                        ::= { fkGponServiceProfileTable 1 }

                
                FkGponServiceProfileEntry ::=
                        SEQUENCE { 
                                fkGponServiceProfileIndex
                                        Integer32,
                                fkGponServiceProfileModelName
                                        OCTET STRING,
                                fkGponServiceProfileProfileName
                                        OCTET STRING
                         }

--  1.3.6.1.4.1.10428 9 1.101.23.5.6.1.1.1
                -- 1.3.6.1.4.1.10428 9 1.101.23.5.6.1.1.1
                fkGponServiceProfileIndex OBJECT-TYPE
                        SYNTAX Integer32 (1..65535)
                        MAX-ACCESS read-write
                        STATUS current
                        DESCRIPTION
                                "The profile index."
                        ::= { fkGponServiceProfileEntry 1 }

                
--  1.3.6.1.4.1.10428 9 1.101.23.5.6.1.1.2
                -- 1.3.6.1.4.1.10428 9 1.101.23.5.6.1.1.2
                fkGponServiceProfileModelName OBJECT-TYPE
                        SYNTAX OCTET STRING
                        MAX-ACCESS read-only
                        STATUS current
                        DESCRIPTION
                                "The Service Profile Model name."
                        ::= { fkGponServiceProfileEntry 2 }

                
--  1.3.6.1.4.1.10428 9 1.101.23.5.6.1.1.3
                -- 1.3.6.1.4.1.10428 9 1.101.23.5.6.1.1.3
                fkGponServiceProfileProfileName OBJECT-TYPE
                        SYNTAX OCTET STRING
                        MAX-ACCESS read-only
                        STATUS current
                        DESCRIPTION
                                "The Service Profile Name."
                        ::= { fkGponServiceProfileEntry 3 }

                
--  1.3.6.1.4.1.10428 9 1.101.23.5.6.2
                -- 1.3.6.1.4.1.10428 9 1.101.23.5.6.2
                fkGponServiceProfileControl OBJECT IDENTIFIER ::= { fkGponServiceProfile 2 }

                
--  1.3.6.1.4.1.10428 9 1.101.23.5.6.2.1
                -- 1.3.6.1.4.1.10428 9 1.101.23.5.6.2.1
                fkGponServiceProfileControlRequest OBJECT-TYPE
                        SYNTAX INTEGER { setGponServiceProfileModel(1) }
                        MAX-ACCESS read-write
                        STATUS current
                        DESCRIPTION
                                "The request of a user command"
                        ::= { fkGponServiceProfileControl 1 }

                
--  1.3.6.1.4.1.10428 9 1.101.23.5.6.2.2
                -- 1.3.6.1.4.1.10428 9 1.101.23.5.6.2.2
                fkGponServiceProfileControlStatus OBJECT-TYPE
                        SYNTAX FkControlStatusType
                        MAX-ACCESS read-write
                        STATUS current
                        DESCRIPTION
                                "The status of user command"
                        ::= { fkGponServiceProfileControl 2 }

                
--  1.3.6.1.4.1.10428 9 1.101.23.5.6.2.3
                -- 1.3.6.1.4.1.10428 9 1.101.23.5.6.2.3
                fkGponServiceProfileControlTimer OBJECT-TYPE
                        SYNTAX Gauge32
                        MAX-ACCESS read-write
                        STATUS current
                        DESCRIPTION
                                "The maximum time for the manager for a long running user command"
                        ::= { fkGponServiceProfileControl 3 }

                
--  1.3.6.1.4.1.10428 9 1.101.23.5.6.2.4
                -- 1.3.6.1.4.1.10428 9 1.101.23.5.6.2.4
                fkGponServiceProfileControlTimeStamp OBJECT-TYPE
                        SYNTAX TimeTicks
                        MAX-ACCESS read-write
                        STATUS current
                        DESCRIPTION
                                "The time stamp of the last command(end of command)"
                        ::= { fkGponServiceProfileControl 4 }

                
--  1.3.6.1.4.1.10428 9 1.101.23.5.6.2.5
                -- 1.3.6.1.4.1.10428 9 1.101.23.5.6.2.5
                fkGponServiceProfileControlReqResult OBJECT-TYPE
                        SYNTAX FkControlRequestResultType
                        MAX-ACCESS read-write
                        STATUS current
                        DESCRIPTION
                                "The result of the last user command"
                        ::= { fkGponServiceProfileControl 5 }

                
--  1.3.6.1.4.1.10428 9 1.101.23.5.6.2.6
                -- 1.3.6.1.4.1.10428 9 1.101.23.5.6.2.6
                fkGponServiceProfileControlModelName OBJECT-TYPE
                        SYNTAX OCTET STRING
                        MAX-ACCESS read-write
                        STATUS current
                        DESCRIPTION
                                "The Service Profile Model name."
                        ::= { fkGponServiceProfileControl 6 }

                
--  1.3.6.1.4.1.10428 9 1.101.23.5.6.2.7
                -- 1.3.6.1.4.1.10428 9 1.101.23.5.6.2.7
                fkGponServiceProfileControlProfileName OBJECT-TYPE
                        SYNTAX OCTET STRING
                        MAX-ACCESS read-write
                        STATUS current
                        DESCRIPTION
                                "The Service Profile Name."
                        ::= { fkGponServiceProfileControl 7 }

                
--  1.3.6.1.4.1.10428 9 1.101.23.5.6.3
                -- 1.3.6.1.4.1.10428 9 1.101.23.5.6.3
                fkGponServiceProfileNotification OBJECT IDENTIFIER ::= { fkGponServiceProfile 3 }

                
--  1.3.6.1.4.1.10428 9 1.101.23.5.6.3.1
                -- 1.3.6.1.4.1.10428 9 1.101.23.5.6.3.1
                fkGponServiceProfileModelChanged NOTIFICATION-TYPE
                        OBJECTS { fkGponServiceProfileControlRequest, fkGponServiceProfileControlTimeStamp, fkGponServiceProfileControlReqResult, fkGponServiceProfileControlModelName, fkGponServiceProfileControlProfileName
                                 }
                        STATUS current
                        DESCRIPTION 
                                "Description."
                        ::= { fkGponServiceProfileNotification 1 }

                
                -- 1.3.6.1.4.1.10428 9 1.101.23.5.7
                fkGponProfileTdm OBJECT IDENTIFIER ::= { fkGponProfile 7 }

                
                -- 1.3.6.1.4.1.10428 9 1.101.23.5.7.1
                fkGponProfileTdmPwMt OBJECT IDENTIFIER ::= { fkGponProfileTdm 1 }

                
                -- 1.3.6.1.4.1.10428 9 1.101.23.5.7.1.1
                fkGponProfileTdmPwMtTable OBJECT-TYPE
                        SYNTAX SEQUENCE OF FkGponProfileTdmPwMtEntry
                        MAX-ACCESS not-accessible
                        STATUS current
                        DESCRIPTION
                                "fkGponProfileTdmPwMtTable"
                        ::= { fkGponProfileTdmPwMt 1 }

                
                -- 1.3.6.1.4.1.10428 9 1.101.23.5.7.1.1.1
                fkGponProfileTdmPwMtEntry OBJECT-TYPE
                        SYNTAX FkGponProfileTdmPwMtEntry
                        MAX-ACCESS not-accessible
                        STATUS current
                        DESCRIPTION
                                "key: fkGponProfileTdmPwMtIndex"
                        INDEX { fkGponProfileTdmPwMtIndex }
                        ::= { fkGponProfileTdmPwMtTable 1 }

                
                FkGponProfileTdmPwMtEntry ::=
                        SEQUENCE { 
                                fkGponProfileTdmPwMtIndex
                                        INTEGER,
                                fkGponProfileTdmPwMtName
                                        OCTET STRING,
                                fkGponProfileTdmPwMtMaxDepth
                                        INTEGER,
                                fkGponProfileTdmPwMtDesiredDepth
                                        INTEGER,
                                fkGponProfileTdmPwMtFillPolicy
                                        INTEGER,
                                fkGponProfileTdmPwMtMisconnectDeclarePolicy
                                        INTEGER,
                                fkGponProfileTdmPwMtMisconnectClearPolicy
                                        INTEGER,
                                fkGponProfileTdmPwMtLossDeclarePolicy
                                        INTEGER,
                                fkGponProfileTdmPwMtLossClearPolicy
                                        INTEGER,
                                fkGponProfileTdmPwMtBuffUnderrunDeclarePolicy
                                        INTEGER,
                                fkGponProfileTdmPwMtBuffUnderrunClearPolicy
                                        INTEGER,
                                fkGponProfileTdmPwMtMalformedDeclarePolicy
                                        INTEGER,
                                fkGponProfileTdmPwMtMalformedClearPolicy
                                        INTEGER,
                                fkGponProfileTdmPwMtRBitTransmitPolicy
                                        INTEGER,
                                fkGponProfileTdmPwMtRBitReceivePolicy
                                        INTEGER,
                                fkGponProfileTdmPwMtLBitReceivePolicy
                                        INTEGER,
                                fkGponProfileTdmPwMtSesThreshold
                                        INTEGER
                         }

                -- 1.3.6.1.4.1.10428 9 1.101.23.5.7.1.1.1.1
                fkGponProfileTdmPwMtIndex OBJECT-TYPE
                        SYNTAX INTEGER (1..65535)
                        MAX-ACCESS read-only
                        STATUS current
                        DESCRIPTION
                                "PW Maintenance Profile Index"
                        ::= { fkGponProfileTdmPwMtEntry 1 }

                
                -- 1.3.6.1.4.1.10428 9 1.101.23.5.7.1.1.1.2
                fkGponProfileTdmPwMtName OBJECT-TYPE
                        SYNTAX OCTET STRING
                        MAX-ACCESS read-only
                        STATUS current
                        DESCRIPTION
                                "PW Maintenance Profile Name"
                        ::= { fkGponProfileTdmPwMtEntry 2 }

                
                -- 1.3.6.1.4.1.10428 9 1.101.23.5.7.1.1.1.3
                fkGponProfileTdmPwMtMaxDepth OBJECT-TYPE
                        SYNTAX INTEGER (1..65535)
                        MAX-ACCESS read-only
                        STATUS current
                        DESCRIPTION
                                "Configure Jitter buffer maximum depth"
                        ::= { fkGponProfileTdmPwMtEntry 3 }

                
                -- 1.3.6.1.4.1.10428 9 1.101.23.5.7.1.1.1.4
                fkGponProfileTdmPwMtDesiredDepth OBJECT-TYPE
                        SYNTAX INTEGER (1..65535)
                        MAX-ACCESS read-only
                        STATUS current
                        DESCRIPTION
                                "Configure Jitter buffer desired depth"
                        ::= { fkGponProfileTdmPwMtEntry 4 }

                
                -- 1.3.6.1.4.1.10428 9 1.101.23.5.7.1.1.1.5
                fkGponProfileTdmPwMtFillPolicy OBJECT-TYPE
                        SYNTAX INTEGER
                                {
                                vendorSpecific(0),
                                playOutAis(1),
                                playOutAll1S(2),
                                playOutAll0S(3),
                                repeatPrevData(4),
                                playOutDs1Idle(5)
                                }
                        MAX-ACCESS read-only
                        STATUS current
                        DESCRIPTION
                                "Configure Fill Payload Bit Pattern"
                        ::= { fkGponProfileTdmPwMtEntry 5 }

                
                -- 1.3.6.1.4.1.10428 9 1.101.23.5.7.1.1.1.6
                fkGponProfileTdmPwMtMisconnectDeclarePolicy OBJECT-TYPE
                        SYNTAX INTEGER (0 | 1..100)
                        MAX-ACCESS read-only
                        STATUS current
                        DESCRIPTION
                                "Configure Misconnected packets declaration policy                                      "
                        ::= { fkGponProfileTdmPwMtEntry 6 }

                
                -- 1.3.6.1.4.1.10428 9 1.101.23.5.7.1.1.1.7
                fkGponProfileTdmPwMtMisconnectClearPolicy OBJECT-TYPE
                        SYNTAX INTEGER (0..99 | 255)
                        MAX-ACCESS read-only
                        STATUS current
                        DESCRIPTION
                                "Configure Misconnected packets clear policy"
                        ::= { fkGponProfileTdmPwMtEntry 7 }

                
                -- 1.3.6.1.4.1.10428 9 1.101.23.5.7.1.1.1.8
                fkGponProfileTdmPwMtLossDeclarePolicy OBJECT-TYPE
                        SYNTAX INTEGER (0 | 1..100)
                        MAX-ACCESS read-only
                        STATUS current
                        DESCRIPTION
                                "Configure Loss of packets declaration policy"
                        ::= { fkGponProfileTdmPwMtEntry 8 }

                
                -- 1.3.6.1.4.1.10428 9 1.101.23.5.7.1.1.1.9
                fkGponProfileTdmPwMtLossClearPolicy OBJECT-TYPE
                        SYNTAX INTEGER (0..99 | 255)
                        MAX-ACCESS read-only
                        STATUS current
                        DESCRIPTION
                                "Configure Loss of packets clear policy"
                        ::= { fkGponProfileTdmPwMtEntry 9 }

                
                -- 1.3.6.1.4.1.10428 9 1.101.23.5.7.1.1.1.10
                fkGponProfileTdmPwMtBuffUnderrunDeclarePolicy OBJECT-TYPE
                        SYNTAX INTEGER (0 | 1..100)
                        MAX-ACCESS read-only
                        STATUS current
                        DESCRIPTION
                                "Configure Buffer overrun/underrun declaration policy"
                        ::= { fkGponProfileTdmPwMtEntry 10 }

                
                -- 1.3.6.1.4.1.10428 9 1.101.23.5.7.1.1.1.11
                fkGponProfileTdmPwMtBuffUnderrunClearPolicy OBJECT-TYPE
                        SYNTAX INTEGER (0..99 | 255)
                        MAX-ACCESS read-only
                        STATUS current
                        DESCRIPTION
                                "Configure Buffer overrun/underrun clear policy"
                        ::= { fkGponProfileTdmPwMtEntry 11 }

                
                -- 1.3.6.1.4.1.10428 9 1.101.23.5.7.1.1.1.12
                fkGponProfileTdmPwMtMalformedDeclarePolicy OBJECT-TYPE
                        SYNTAX INTEGER (0 | 1..100)
                        MAX-ACCESS read-only
                        STATUS current
                        DESCRIPTION
                                "Configure Malformed packets declaration policy"
                        ::= { fkGponProfileTdmPwMtEntry 12 }

                
                -- 1.3.6.1.4.1.10428 9 1.101.23.5.7.1.1.1.13
                fkGponProfileTdmPwMtMalformedClearPolicy OBJECT-TYPE
                        SYNTAX INTEGER (0..99 | 255)
                        MAX-ACCESS read-only
                        STATUS current
                        DESCRIPTION
                                "Configure Malformed packets clear policy"
                        ::= { fkGponProfileTdmPwMtEntry 13 }

                
                -- 1.3.6.1.4.1.10428 9 1.101.23.5.7.1.1.1.14
                fkGponProfileTdmPwMtRBitTransmitPolicy OBJECT-TYPE
                        SYNTAX INTEGER (0 | 1..255)
                        MAX-ACCESS read-only
                        STATUS current
                        DESCRIPTION
                                "Configure R-bit transmit set policy"
                        ::= { fkGponProfileTdmPwMtEntry 14 }

                
                -- 1.3.6.1.4.1.10428 9 1.101.23.5.7.1.1.1.15
                fkGponProfileTdmPwMtRBitReceivePolicy OBJECT-TYPE
                        SYNTAX INTEGER
                                {
                                none(0),
                                playOut(1),
                                sendIdle(2)
                                }
                        MAX-ACCESS read-only
                        STATUS current
                        DESCRIPTION
                                "Configure R-bit receive policy"
                        ::= { fkGponProfileTdmPwMtEntry 15 }

                
                -- 1.3.6.1.4.1.10428 9 1.101.23.5.7.1.1.1.16
                fkGponProfileTdmPwMtLBitReceivePolicy OBJECT-TYPE
                        SYNTAX INTEGER
                                {
                                playOut(0),
                                repeatLastPacket(1),
                                sendIdle(2)
                                }
                        MAX-ACCESS read-only
                        STATUS current
                        DESCRIPTION
                                "Configure L-bit receive policy"
                        ::= { fkGponProfileTdmPwMtEntry 16 }

                
                -- 1.3.6.1.4.1.10428 9 1.101.23.5.7.1.1.1.17
                fkGponProfileTdmPwMtSesThreshold OBJECT-TYPE
                        SYNTAX INTEGER (1..65535)
                        MAX-ACCESS read-only
                        STATUS current
                        DESCRIPTION
                                "Configure SES threshold"
                        ::= { fkGponProfileTdmPwMtEntry 17 }

                
                -- 1.3.6.1.4.1.10428 9 1.101.23.5.7.1.2
                fkGponProfileTdmPwMtControl OBJECT IDENTIFIER ::= { fkGponProfileTdmPwMt 2 }

                
                -- 1.3.6.1.4.1.10428 9 1.101.23.5.7.1.2.1
                fkGponProfileTdmPwMtControlRequest OBJECT-TYPE
                        SYNTAX INTEGER
                                {
                                createProfile(1),
                                destroyProfile(2),
                                setMaxDepth(3),
                                setDesiredDepth(4),
                                setFillPolicy(5),
                                setMisconnectDeclarePolicy(6),
                                setMisconnectClearPolicy(7),
                                setLossDeclarePolicy(8),
                                setLossClearPolicy(9),
                                setBuffUnderrunDeclarePolicy(10),
                                setbuffUnderrunClearPolicy(11),
                                setMalformedDeclarePolicy(12),
                                setMalformedClearPolicy(13),
                                setRBitTransmitPolicy(14),
                                setRBitReceivePolicy(15),
                                setLBitReceivePolicy(16),
                                setSesThreshold(17)
                                }
                        MAX-ACCESS read-write
                        STATUS current
                        DESCRIPTION
                                "The request of a user command"
                        ::= { fkGponProfileTdmPwMtControl 1 }

                
                -- 1.3.6.1.4.1.10428 9 1.101.23.5.7.1.2.2
                fkGponProfileTdmPwMtControlStatus OBJECT-TYPE
                        SYNTAX FkControlStatusType
                        MAX-ACCESS read-only
                        STATUS current
                        DESCRIPTION
                                "The status of user command"
                        ::= { fkGponProfileTdmPwMtControl 2 }

                
                -- 1.3.6.1.4.1.10428 9 1.101.23.5.7.1.2.3
                fkGponProfileTdmPwMtControlTimer OBJECT-TYPE
                        SYNTAX Gauge32
                        MAX-ACCESS read-write
                        STATUS current
                        DESCRIPTION
                                "The maximum time for the manager for a long running user command"
                        ::= { fkGponProfileTdmPwMtControl 3 }

                
                -- 1.3.6.1.4.1.10428 9 1.101.23.5.7.1.2.4
                fkGponProfileTdmPwMtControlTimeStamp OBJECT-TYPE
                        SYNTAX TimeTicks
                        MAX-ACCESS read-only
                        STATUS current
                        DESCRIPTION
                                "The time stamp of the last command(end of command)"
                        ::= { fkGponProfileTdmPwMtControl 4 }

                
                -- 1.3.6.1.4.1.10428 9 1.101.23.5.7.1.2.5
                fkGponProfileTdmPwMtControlReqResult OBJECT-TYPE
                        SYNTAX FkControlRequestResultType
                        MAX-ACCESS read-only
                        STATUS current
                        DESCRIPTION
                                "The result of the last user command"
                        ::= { fkGponProfileTdmPwMtControl 5 }

                
                -- 1.3.6.1.4.1.10428 9 1.101.23.5.7.1.2.6
                fkGponProfileTdmPwMtControlIndex OBJECT-TYPE
                        SYNTAX INTEGER (1..65535)
                        MAX-ACCESS read-write
                        STATUS current
                        DESCRIPTION
                                "PW Maintenance Profile Index"
                        ::= { fkGponProfileTdmPwMtControl 6 }

                
                -- 1.3.6.1.4.1.10428 9 1.101.23.5.7.1.2.7
                fkGponProfileTdmPwMtControlName OBJECT-TYPE
                        SYNTAX OCTET STRING
                        MAX-ACCESS read-write
                        STATUS current
                        DESCRIPTION
                                "PW Maintenance Profile Name"
                        ::= { fkGponProfileTdmPwMtControl 7 }

                
                -- 1.3.6.1.4.1.10428 9 1.101.23.5.7.1.2.8
                fkGponProfileTdmPwMtControlMaxDepth OBJECT-TYPE
                        SYNTAX INTEGER (1..65535)
                        MAX-ACCESS read-write
                        STATUS current
                        DESCRIPTION
                                "Configure Jitter buffer maximum depth"
                        ::= { fkGponProfileTdmPwMtControl 8 }

                
                -- 1.3.6.1.4.1.10428 9 1.101.23.5.7.1.2.9
                fkGponProfileTdmPwMtControlDesiredDepth OBJECT-TYPE
                        SYNTAX INTEGER (1..65535)
                        MAX-ACCESS read-write
                        STATUS current
                        DESCRIPTION
                                "Configure Jitter buffer desired depth"
                        ::= { fkGponProfileTdmPwMtControl 9 }

                
                -- 1.3.6.1.4.1.10428 9 1.101.23.5.7.1.2.10
                fkGponProfileTdmPwMtControlFillPolicy OBJECT-TYPE
                        SYNTAX INTEGER
                                {
                                vendorSpecific(0),
                                playOutAis(1),
                                playOutAll1S(2),
                                playOutAll0S(3),
                                repeatPrevData(4),
                                playOutDs1Idle(5)
                                }
                        MAX-ACCESS read-write
                        STATUS current
                        DESCRIPTION
                                "Configure Fill Payload Bit Pattern"
                        ::= { fkGponProfileTdmPwMtControl 10 }

                
                -- 1.3.6.1.4.1.10428 9 1.101.23.5.7.1.2.11
                fkGponProfileTdmPwMtControlMisconnectDeclarePolicy OBJECT-TYPE
                        SYNTAX INTEGER (0 | 1..100)
                        MAX-ACCESS read-write
                        STATUS current
                        DESCRIPTION
                                "Configure Misconnected packets declaration policy"
                        ::= { fkGponProfileTdmPwMtControl 11 }

                
                -- 1.3.6.1.4.1.10428 9 1.101.23.5.7.1.2.12
                fkGponProfileTdmPwMtControlMisconnectClearPolicy OBJECT-TYPE
                        SYNTAX INTEGER (0..99 | 255)
                        MAX-ACCESS read-write
                        STATUS current
                        DESCRIPTION
                                "Configure Misconnected packets clear policy"
                        ::= { fkGponProfileTdmPwMtControl 12 }

                
                -- 1.3.6.1.4.1.10428 9 1.101.23.5.7.1.2.13
                fkGponProfileTdmPwMtControlLossDeclarePolicy OBJECT-TYPE
                        SYNTAX INTEGER (0 | 1..100)
                        MAX-ACCESS read-write
                        STATUS current
                        DESCRIPTION
                                "Configure Loss of packets declaration policy"
                        ::= { fkGponProfileTdmPwMtControl 13 }

                
                -- 1.3.6.1.4.1.10428 9 1.101.23.5.7.1.2.14
                fkGponProfileTdmPwMtControlLossClearPolicy OBJECT-TYPE
                        SYNTAX INTEGER (0..99 | 255)
                        MAX-ACCESS read-write
                        STATUS current
                        DESCRIPTION
                                "Configure Loss of packets clear policy"
                        ::= { fkGponProfileTdmPwMtControl 14 }

                
                -- 1.3.6.1.4.1.10428 9 1.101.23.5.7.1.2.15
                fkGponProfileTdmPwMtControlBuffUnderrunDeclarePolicy OBJECT-TYPE
                        SYNTAX INTEGER (0 | 1..100)
                        MAX-ACCESS read-write
                        STATUS current
                        DESCRIPTION
                                "Configure Buffer overrun/underrun declaration policy"
                        ::= { fkGponProfileTdmPwMtControl 15 }

                
                -- 1.3.6.1.4.1.10428 9 1.101.23.5.7.1.2.16
                fkGponProfileTdmPwMtControlBuffUnderrunClearPolicy OBJECT-TYPE
                        SYNTAX INTEGER (0..99 | 255)
                        MAX-ACCESS read-write
                        STATUS current
                        DESCRIPTION
                                "Configure Buffer overrun/underrun clear policy"
                        ::= { fkGponProfileTdmPwMtControl 16 }

                
                -- 1.3.6.1.4.1.10428 9 1.101.23.5.7.1.2.17
                fkGponProfileTdmPwMtControlMalformedDeclarePolicy OBJECT-TYPE
                        SYNTAX INTEGER (0 | 1..100)
                        MAX-ACCESS read-write
                        STATUS current
                        DESCRIPTION
                                "Configure Malformed packets declaration policy"
                        ::= { fkGponProfileTdmPwMtControl 17 }

                
                -- 1.3.6.1.4.1.10428 9 1.101.23.5.7.1.2.18
                fkGponProfileTdmPwMtControlMalformedClearPolicy OBJECT-TYPE
                        SYNTAX INTEGER (0..99 | 255)
                        MAX-ACCESS read-write
                        STATUS current
                        DESCRIPTION
                                "Configure Malformed packets clear policy"
                        ::= { fkGponProfileTdmPwMtControl 18 }

                
                -- 1.3.6.1.4.1.10428 9 1.101.23.5.7.1.2.19
                fkGponProfileTdmPwMtControlRBitTransmitPolicy OBJECT-TYPE
                        SYNTAX INTEGER (0 | 1..255)
                        MAX-ACCESS read-write
                        STATUS current
                        DESCRIPTION
                                "Configure R-bit transmit set policy"
                        ::= { fkGponProfileTdmPwMtControl 19 }

                
                -- 1.3.6.1.4.1.10428 9 1.101.23.5.7.1.2.20
                fkGponProfileTdmPwMtControlRBitReceivePolicy OBJECT-TYPE
                        SYNTAX INTEGER
                                {
                                none(0),
                                playOut(1),
                                sendIdle(2)
                                }
                        MAX-ACCESS read-write
                        STATUS current
                        DESCRIPTION
                                "Configure R-bit receive policy"
                        ::= { fkGponProfileTdmPwMtControl 20 }

                
                -- 1.3.6.1.4.1.10428 9 1.101.23.5.7.1.2.21
                fkGponProfileTdmPwMtControlLBitReceivePolicy OBJECT-TYPE
                        SYNTAX INTEGER
                                {
                                playOut(0),
                                repeatLastPacket(1),
                                sendIdle(2)
                                }
                        MAX-ACCESS read-write
                        STATUS current
                        DESCRIPTION
                                "Configure L-bit receive policy"
                        ::= { fkGponProfileTdmPwMtControl 21 }

                
                -- 1.3.6.1.4.1.10428 9 1.101.23.5.7.1.2.22
                fkGponProfileTdmPwMtControlSesThreshold OBJECT-TYPE
                        SYNTAX INTEGER (1..65535)
                        MAX-ACCESS read-write
                        STATUS current
                        DESCRIPTION
                                "Configure SES threshold"
                        ::= { fkGponProfileTdmPwMtControl 22 }

                
                -- 1.3.6.1.4.1.10428 9 1.101.23.5.7.1.3
                fkGponProfileTdmPwMtNotification OBJECT IDENTIFIER ::= { fkGponProfileTdmPwMt 3 }

                
                -- 1.3.6.1.4.1.10428 9 1.101.23.5.7.1.3.1
                fkGponProfileTdmPwMtProfileCreated NOTIFICATION-TYPE
                        OBJECTS { fkGponProfileTdmPwMtControlName, fkGponProfileTdmPwMtControlRequest, fkGponProfileTdmPwMtControlTimeStamp, fkGponProfileTdmPwMtControlReqResult }
                        STATUS current
                        DESCRIPTION 
                                "Description."
                        ::= { fkGponProfileTdmPwMtNotification 1 }

                
                -- 1.3.6.1.4.1.10428 9 1.101.23.5.7.1.3.2
                fkGponProfileTdmPwMtProfileDeleted NOTIFICATION-TYPE
                        OBJECTS { fkGponProfileTdmPwMtControlRequest, fkGponProfileTdmPwMtControlTimeStamp, fkGponProfileTdmPwMtControlReqResult, fkGponProfileTdmPwMtControlIndex }
                        STATUS current
                        DESCRIPTION 
                                "Description."
                        ::= { fkGponProfileTdmPwMtNotification 2 }

                
                -- 1.3.6.1.4.1.10428 9 1.101.23.5.7.1.3.3
                fkGponProfileTdmPwMtMaxDepthChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlMaxDepth
                                 }
                        STATUS current
                        DESCRIPTION 
                                "Description."
                        ::= { fkGponProfileTdmPwMtNotification 3 }

                
                -- 1.3.6.1.4.1.10428 9 1.101.23.5.7.1.3.4
                fkGponProfileTdmDesiredDepthChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlDesiredDepth
                                 }
                        STATUS current
                        DESCRIPTION 
                                "Description."
                        ::= { fkGponProfileTdmPwMtNotification 4 }

                
                -- 1.3.6.1.4.1.10428 9 1.101.23.5.7.1.3.5
                fkGponProfileTdmFillPolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlFillPolicy
                                 }
                        STATUS current
                        DESCRIPTION 
                                "Description."
                        ::= { fkGponProfileTdmPwMtNotification 5 }

                
                -- 1.3.6.1.4.1.10428 9 1.101.23.5.7.1.3.6
                fkGponProfileTdmMisconnectDeclarePolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlMisconnectDeclarePolicy
                                 }
                        STATUS current
                        DESCRIPTION 
                                "Description."
                        ::= { fkGponProfileTdmPwMtNotification 6 }

                
                -- 1.3.6.1.4.1.10428 9 1.101.23.5.7.1.3.7
                fkGponProfileTdmMisconnectClearPolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlMisconnectClearPolicy
                                 }
                        STATUS current
                        DESCRIPTION 
                                "Description."
                        ::= { fkGponProfileTdmPwMtNotification 7 }

                
                -- 1.3.6.1.4.1.10428 9 1.101.23.5.7.1.3.8
                fkGponProfileTdmLossDeclarePolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlLossDeclarePolicy
                                 }
                        STATUS current
                        DESCRIPTION 
                                "Description."
                        ::= { fkGponProfileTdmPwMtNotification 8 }

                
                -- 1.3.6.1.4.1.10428 9 1.101.23.5.7.1.3.9
                fkGponProfileTdmLossClearPolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlLossClearPolicy
                                 }
                        STATUS current
                        DESCRIPTION 
                                "Description."
                        ::= { fkGponProfileTdmPwMtNotification 9 }

                
                -- 1.3.6.1.4.1.10428 9 1.101.23.5.7.1.3.10
                fkGponProfileTdmBuffUnderrunDeclarePolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlBuffUnderrunDeclarePolicy
                                 }
                        STATUS current
                        DESCRIPTION 
                                "Description."
                        ::= { fkGponProfileTdmPwMtNotification 10 }

                
                -- 1.3.6.1.4.1.10428 9 1.101.23.5.7.1.3.11
                fkGponProfileTdmbuffUnderrunClearPolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlBuffUnderrunClearPolicy
                                 }
                        STATUS current
                        DESCRIPTION 
                                "Description."
                        ::= { fkGponProfileTdmPwMtNotification 11 }

                
                -- 1.3.6.1.4.1.10428 9 1.101.23.5.7.1.3.12
                fkGponProfileTdmMalformedDeclarePolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlMalformedDeclarePolicy
                                 }
                        STATUS current
                        DESCRIPTION 
                                "Description."
                        ::= { fkGponProfileTdmPwMtNotification 12 }

                
                -- 1.3.6.1.4.1.10428 9 1.101.23.5.7.1.3.13
                fkGponProfileTdmMalformedClearPolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlMalformedClearPolicy
                                 }
                        STATUS current
                        DESCRIPTION 
                                "Description."
                        ::= { fkGponProfileTdmPwMtNotification 13 }

                
                -- 1.3.6.1.4.1.10428 9 1.101.23.5.7.1.3.14
                fkGponProfileTdmRBitTransmitPolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlRBitTransmitPolicy
                                 }
                        STATUS current
                        DESCRIPTION 
                                "Description."
                        ::= { fkGponProfileTdmPwMtNotification 14 }

                
                -- 1.3.6.1.4.1.10428 9 1.101.23.5.7.1.3.15
                fkGponProfileTdmRBitReceivePolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlRBitReceivePolicy
                                 }
                        STATUS current
                        DESCRIPTION 
                                "Description."
                        ::= { fkGponProfileTdmPwMtNotification 15 }

                
                -- 1.3.6.1.4.1.10428 9 1.101.23.5.7.1.3.16
                fkGponProfileTdmLBitReceivePolicyChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlLBitReceivePolicy
                                 }
                        STATUS current
                        DESCRIPTION 
                                "Description."
                        ::= { fkGponProfileTdmPwMtNotification 16 }

                
                -- 1.3.6.1.4.1.10428 9 1.101.23.5.7.1.3.17
                fkGponProfileTdmSesThresholdChanged NOTIFICATION-TYPE
                        OBJECTS { fkGponProfileTdmPwMtControlRequest, fkGponProfileTdmPwMtControlTimeStamp, fkGponProfileTdmPwMtControlReqResult, fkGponProfileTdmPwMtControlIndex, fkGponProfileTdmPwMtControlSesThreshold
                                 }
                        STATUS current
                        DESCRIPTION 
                                "Description."
                        ::= { fkGponProfileTdmPwMtNotification 17 }

                
                -- 1.3.6.1.4.1.10428 9 1.101.23.5.7.2
                fkGponProfileTdmPw OBJECT IDENTIFIER ::= { fkGponProfileTdm 2 }

                
                -- 1.3.6.1.4.1.10428 9 1.101.23.5.7.2.1
                fkGponProfileTdmPwTable OBJECT-TYPE
                        SYNTAX SEQUENCE OF FkGponProfileTdmPwEntry
                        MAX-ACCESS not-accessible
                        STATUS current
                        DESCRIPTION
                                "fkGponProfileTdmPwTable"
                        ::= { fkGponProfileTdmPw 1 }

                
                -- 1.3.6.1.4.1.10428 9 1.101.23.5.7.2.1.1
                fkGponProfileTdmPwEntry OBJECT-TYPE
                        SYNTAX FkGponProfileTdmPwEntry
                        MAX-ACCESS not-accessible
                        STATUS current
                        DESCRIPTION
                                "key: fkGponProfileTdmPwIndex"
                        INDEX { fkGponProfileTdmPwIndex }
                        ::= { fkGponProfileTdmPwTable 1 }

                
                FkGponProfileTdmPwEntry ::=
                        SEQUENCE { 
                                fkGponProfileTdmPwIndex
                                        INTEGER,
                                fkGponProfileTdmPwName
                                        OCTET STRING,
                                fkGponProfileTdmPwServiceType
                                        INTEGER,
                                fkGponProfileTdmPwSignalling
                                        INTEGER,
                                fkGponProfileTdmPwPayloadSize
                                        INTEGER,
                                fkGponProfileTdmPwPayloadEncapulationDelay
                                        INTEGER,
                                fkGponProfileTdmPwTimingMode
                                        INTEGER,
                                fkGponProfileTdmPwRtpClockRefernce
                                        INTEGER,
                                fkGponProfileTdmPwRtpTimeStampMode
                                        INTEGER,
                                fkGponProfileTdmPwRtpPayloadChannel
                                        INTEGER,
                                fkGponProfileTdmPwRtpPayloadSignalling
                                        INTEGER,
                                fkGponProfileTdmPwRtpSyncSourceChannel
                                        INTEGER,
                                fkGponProfileTdmPwRtpSyncSourceSignalling
                                        INTEGER,
                                fkGponProfileTdmPwRtpExpectPayloadChannel
                                        INTEGER,
                                fkGponProfileTdmPwRtpExpectPaloadSignalling
                                        INTEGER,
                                fkGponProfileTdmPwRtpExpectSyncSourceChannel
                                        INTEGER,
                                fkGponProfileTdmPwRtpExpectSyncSourceSignalling
                                        INTEGER,
                                fkGponProfileTdmPwMtProfileName
                                        OCTET STRING
                         }

                -- 1.3.6.1.4.1.10428 9 1.101.23.5.7.2.1.1.1
                fkGponProfileTdmPwIndex OBJECT-TYPE
                        SYNTAX INTEGER (1..65535)
                        MAX-ACCESS read-only
                        STATUS current
                        DESCRIPTION
                                "Tdm pw index"
                        ::= { fkGponProfileTdmPwEntry 1 }

                
                -- 1.3.6.1.4.1.10428 9 1.101.23.5.7.2.1.1.2
                fkGponProfileTdmPwName OBJECT-TYPE
                        SYNTAX OCTET STRING
                        MAX-ACCESS read-only
                        STATUS current
                        DESCRIPTION
                                "TDM pw profile name"
                        ::= { fkGponProfileTdmPwEntry 2 }

                
                -- 1.3.6.1.4.1.10428 9 1.101.23.5.7.2.1.1.3
                fkGponProfileTdmPwServiceType OBJECT-TYPE
                        SYNTAX INTEGER
                                {
                                unstructured(0),
                                octetAlignedUnstructured(1),
                                structured(2)
                                }
                        MAX-ACCESS read-only
                        STATUS current
                        DESCRIPTION
                                "Configure Basic Service Type"
                        ::= { fkGponProfileTdmPwEntry 3 }

                
                -- 1.3.6.1.4.1.10428 9 1.101.23.5.7.2.1.1.4
                fkGponProfileTdmPwSignalling OBJECT-TYPE
                        SYNTAX INTEGER
                                {
                                noSignalling(0),
                                casCarryPacket(1),
                                casCarryChannel(2)
                                }
                        MAX-ACCESS read-only
                        STATUS current
                        DESCRIPTION
                                "Configure Signalling"
                        ::= { fkGponProfileTdmPwEntry 4 }

                
                -- 1.3.6.1.4.1.10428 9 1.101.23.5.7.2.1.1.5
                fkGponProfileTdmPwPayloadSize OBJECT-TYPE
                        SYNTAX INTEGER (0..65535)
                        MAX-ACCESS read-only
                        STATUS current
                        DESCRIPTION
                                "Configure Payload bytes per packet"
                        ::= { fkGponProfileTdmPwEntry 5 }

                
                -- 1.3.6.1.4.1.10428 9 1.101.23.5.7.2.1.1.6
                fkGponProfileTdmPwPayloadEncapulationDelay OBJECT-TYPE
                        SYNTAX INTEGER (0..65535)
                        MAX-ACCESS read-only
                        STATUS current
                        DESCRIPTION
                                "Configure Payload Encapsulation Delay (unit :ms)"
                        ::= { fkGponProfileTdmPwEntry 6 }

                
                -- 1.3.6.1.4.1.10428 9 1.101.23.5.7.2.1.1.7
                fkGponProfileTdmPwTimingMode OBJECT-TYPE
                        SYNTAX INTEGER
                                {
                                network(0),
                                differential(1),
                                adaptive(2),
                                loop(3)
                                }
                        MAX-ACCESS read-only
                        STATUS current
                        DESCRIPTION
                                "Configure Timing Mode of the TDM service"
                        ::= { fkGponProfileTdmPwEntry 7 }

                
                -- 1.3.6.1.4.1.10428 9 1.101.23.5.7.2.1.1.8
                fkGponProfileTdmPwRtpClockRefernce OBJECT-TYPE
                        SYNTAX INTEGER (0..65535)
                        MAX-ACCESS read-only
                        STATUS current
                        DESCRIPTION
                                "Configure RTP Clock Reference"
                        ::= { fkGponProfileTdmPwEntry 8 }

                
                -- 1.3.6.1.4.1.10428 9 1.101.23.5.7.2.1.1.9
                fkGponProfileTdmPwRtpTimeStampMode OBJECT-TYPE
                        SYNTAX INTEGER
                                {
                                unknown(0),
                                absolute(1),
                                differential(2)
                                }
                        MAX-ACCESS read-only
                        STATUS current
                        DESCRIPTION
                                "Configure RTP Time Stamp Mode"
                        ::= { fkGponProfileTdmPwEntry 9 }

                
                -- 1.3.6.1.4.1.10428 9 1.101.23.5.7.2.1.1.10
                fkGponProfileTdmPwRtpPayloadChannel OBJECT-TYPE
                        SYNTAX INTEGER (0..65535)
                        MAX-ACCESS read-only
                        STATUS current
                        DESCRIPTION
                                "Configure RTP Payload Type"
                        ::= { fkGponProfileTdmPwEntry 10 }

                
                -- 1.3.6.1.4.1.10428 9 1.101.23.5.7.2.1.1.11
                fkGponProfileTdmPwRtpPayloadSignalling OBJECT-TYPE
                        SYNTAX INTEGER (0..65535)
                        MAX-ACCESS read-only
                        STATUS current
                        DESCRIPTION
                                "Configure RTP Payload Signalling"
                        ::= { fkGponProfileTdmPwEntry 11 }

                
                -- 1.3.6.1.4.1.10428 9 1.101.23.5.7.2.1.1.12
                fkGponProfileTdmPwRtpSyncSourceChannel OBJECT-TYPE
                        SYNTAX INTEGER (0..65535)
                        MAX-ACCESS read-only
                        STATUS current
                        DESCRIPTION
                                "Configure RTP Synchronization Source"
                        ::= { fkGponProfileTdmPwEntry 12 }

                
                -- 1.3.6.1.4.1.10428 9 1.101.23.5.7.2.1.1.13
                fkGponProfileTdmPwRtpSyncSourceSignalling OBJECT-TYPE
                        SYNTAX INTEGER (0..65535)
                        MAX-ACCESS read-only
                        STATUS current
                        DESCRIPTION
                                "Configure RTP Synchronization Source Signalling"
                        ::= { fkGponProfileTdmPwEntry 13 }

                
                -- 1.3.6.1.4.1.10428 9 1.101.23.5.7.2.1.1.14
                fkGponProfileTdmPwRtpExpectPayloadChannel OBJECT-TYPE
                        SYNTAX INTEGER (0..65535)
                        MAX-ACCESS read-only
                        STATUS current
                        DESCRIPTION
                                "Configure Expected RTP Payload Type"
                        ::= { fkGponProfileTdmPwEntry 14 }

                
                -- 1.3.6.1.4.1.10428 9 1.101.23.5.7.2.1.1.15
                fkGponProfileTdmPwRtpExpectPaloadSignalling OBJECT-TYPE
                        SYNTAX INTEGER (0..65535)
                        MAX-ACCESS read-only
                        STATUS current
                        DESCRIPTION
                                "Configure Expected RTP Payload Signalling"
                        ::= { fkGponProfileTdmPwEntry 15 }

                
                -- 1.3.6.1.4.1.10428 9 1.101.23.5.7.2.1.1.16
                fkGponProfileTdmPwRtpExpectSyncSourceChannel OBJECT-TYPE
                        SYNTAX INTEGER (0..65535)
                        MAX-ACCESS read-only
                        STATUS current
                        DESCRIPTION
                                "Configure Expected RTP Synchronization Source"
                        ::= { fkGponProfileTdmPwEntry 16 }

                
                -- 1.3.6.1.4.1.10428 9 1.101.23.5.7.2.1.1.17
                fkGponProfileTdmPwRtpExpectSyncSourceSignalling OBJECT-TYPE
                        SYNTAX INTEGER (0..65535)
                        MAX-ACCESS read-only
                        STATUS current
                        DESCRIPTION
                                "Configure Expected RTP Synchronization Source Signalling"
                        ::= { fkGponProfileTdmPwEntry 17 }

                
                -- 1.3.6.1.4.1.10428 9 1.101.23.5.7.2.1.1.18
                fkGponProfileTdmPwMtProfileName OBJECT-TYPE
                        SYNTAX OCTET STRING
                        MAX-ACCESS read-only
                        STATUS current
                        DESCRIPTION
                                "Configure PW Maintenance Profile"
                        ::= { fkGponProfileTdmPwEntry 18 }

                
                -- 1.3.6.1.4.1.10428 9 1.101.23.5.7.2.2
                fkGponProfileTdmPwControl OBJECT IDENTIFIER ::= { fkGponProfileTdmPw 2 }

                
                -- 1.3.6.1.4.1.10428 9 1.101.23.5.7.2.2.1
                fkGponProfileTdmPwControlRequest OBJECT-TYPE
                        SYNTAX INTEGER
                                {
                                createProfile(1),
                                destroyProfile(2),
                                setServiceType(3),
                                setSignalling(4),
                                setPayloadSize(5),
                                setPayloadEncapsulationDelay(6),
                                setTimingMode(7),
                                setRtpClockReference(8),
                                setRtpTimeStampmode(9),
                                setRtpPayloadType(10),
                                setRtpSyncSource(11),
                                setRtpExpectPayloadType(12),
                                setRtpExpectSyncSource(13),
                                setMtProfile(14)
                                }
                        MAX-ACCESS read-write
                        STATUS current
                        DESCRIPTION
                                "The request of a user command"
                        ::= { fkGponProfileTdmPwControl 1 }

                
                -- 1.3.6.1.4.1.10428 9 1.101.23.5.7.2.2.2
                fkGponProfileTdmPwControlStatus OBJECT-TYPE
                        SYNTAX FkControlStatusType
                        MAX-ACCESS read-only
                        STATUS current
                        DESCRIPTION
                                "The status of user command"
                        ::= { fkGponProfileTdmPwControl 2 }

                
                -- 1.3.6.1.4.1.10428 9 1.101.23.5.7.2.2.3
                fkGponProfileTdmPwControlTimer OBJECT-TYPE
                        SYNTAX Gauge32
                        MAX-ACCESS read-write
                        STATUS current
                        DESCRIPTION
                                "The maximum time for the manager for a long running user command"
                        ::= { fkGponProfileTdmPwControl 3 }

                
                -- 1.3.6.1.4.1.10428 9 1.101.23.5.7.2.2.4
                fkGponProfileTdmPwControlTimeStamp OBJECT-TYPE
                        SYNTAX TimeTicks
                        MAX-ACCESS read-only
                        STATUS current
                        DESCRIPTION
                                "The time stamp of the last command(end of command)"
                        ::= { fkGponProfileTdmPwControl 4 }

                
                -- 1.3.6.1.4.1.10428 9 1.101.23.5.7.2.2.5
                fkGponProfileTdmPwControlReqResult OBJECT-TYPE
                        SYNTAX FkControlRequestResultType
                        MAX-ACCESS read-only
                        STATUS current
                        DESCRIPTION
                                "The result of the last user command"
                        ::= { fkGponProfileTdmPwControl 5 }

                
                -- 1.3.6.1.4.1.10428 9 1.101.23.5.7.2.2.6
                fkGponProfileTdmPwControlIndex OBJECT-TYPE
                        SYNTAX INTEGER (0..65535)
                        MAX-ACCESS read-write
                        STATUS current
                        DESCRIPTION
                                "Tdm pw index"
                        ::= { fkGponProfileTdmPwControl 6 }

                
                -- 1.3.6.1.4.1.10428 9 1.101.23.5.7.2.2.7
                fkGponProfileTdmPwControlName OBJECT-TYPE
                        SYNTAX OCTET STRING
                        MAX-ACCESS read-write
                        STATUS current
                        DESCRIPTION
                                "TDM pw profile name"
                        ::= { fkGponProfileTdmPwControl 7 }

                
                -- 1.3.6.1.4.1.10428 9 1.101.23.5.7.2.2.8
                fkGponProfileTdmPwControlServiceType OBJECT-TYPE
                        SYNTAX INTEGER
                                {
                                unstructured(0),
                                octetAlignedUnstructured(1),
                                structured(2)
                                }
                        MAX-ACCESS read-write
                        STATUS current
                        DESCRIPTION
                                "Configure Basic Service Type"
                        ::= { fkGponProfileTdmPwControl 8 }

                
                -- 1.3.6.1.4.1.10428 9 1.101.23.5.7.2.2.9
                fkGponProfileTdmPwControlSignalling OBJECT-TYPE
                        SYNTAX INTEGER
                                {
                                noSignalling(0),
                                casCarryPacket(1),
                                casCarryChannel(2)
                                }
                        MAX-ACCESS read-write
                        STATUS current
                        DESCRIPTION
                                "Configure Signalling"
                        ::= { fkGponProfileTdmPwControl 9 }

                
                -- 1.3.6.1.4.1.10428 9 1.101.23.5.7.2.2.10
                fkGponProfileTdmPwControlPayloadSize OBJECT-TYPE
                        SYNTAX INTEGER (0..65535)
                        MAX-ACCESS read-write
                        STATUS current
                        DESCRIPTION
                                "Configure Payload bytes per packet"
                        ::= { fkGponProfileTdmPwControl 10 }

                
                -- 1.3.6.1.4.1.10428 9 1.101.23.5.7.2.2.11
                fkGponProfileTdmPwControlPayloadEncapulationDelay OBJECT-TYPE
                        SYNTAX INTEGER (0..65535)
                        MAX-ACCESS read-write
                        STATUS current
                        DESCRIPTION
                                "Configure Payload Encapsulation Delay (unit :ms)"
                        ::= { fkGponProfileTdmPwControl 11 }

                
                -- 1.3.6.1.4.1.10428 9 1.101.23.5.7.2.2.12
                fkGponProfileTdmPwControlTimingMode OBJECT-TYPE
                        SYNTAX INTEGER
                                {
                                network(0),
                                absolute(1),
                                differential(2)
                                }
                        MAX-ACCESS read-write
                        STATUS current
                        DESCRIPTION
                                "Configure Timing Mode of the TDM service"
                        ::= { fkGponProfileTdmPwControl 12 }

                
                -- 1.3.6.1.4.1.10428 9 1.101.23.5.7.2.2.13
                fkGponProfileTdmPwControlRtpClockRefernce OBJECT-TYPE
                        SYNTAX INTEGER (0..65535)
                        MAX-ACCESS read-write
                        STATUS current
                        DESCRIPTION
                                "Configure RTP Clock Reference"
                        ::= { fkGponProfileTdmPwControl 13 }

                
                -- 1.3.6.1.4.1.10428 9 1.101.23.5.7.2.2.14
                fkGponProfileTdmPwControlRtpTimeStampMode OBJECT-TYPE
                        SYNTAX INTEGER
                                {
                                unknown(0),
                                absolute(1),
                                differential(2)
                                }
                        MAX-ACCESS read-write
                        STATUS current
                        DESCRIPTION
                                "Configure RTP Time Stamp Mode"
                        ::= { fkGponProfileTdmPwControl 14 }

                
                -- 1.3.6.1.4.1.10428 9 1.101.23.5.7.2.2.15
                fkGponProfileTdmPwControlRtpPayloadChannel OBJECT-TYPE
                        SYNTAX INTEGER (0..65535)
                        MAX-ACCESS read-write
                        STATUS current
                        DESCRIPTION
                                "Configure RTP Payload Type"
                        ::= { fkGponProfileTdmPwControl 15 }

                
                -- 1.3.6.1.4.1.10428 9 1.101.23.5.7.2.2.16
                fkGponProfileTdmPwControlRtpPayloadSignalling OBJECT-TYPE
                        SYNTAX INTEGER (0..65535)
                        MAX-ACCESS read-write
                        STATUS current
                        DESCRIPTION
                                "Configure RTP Payload Signalling"
                        ::= { fkGponProfileTdmPwControl 16 }

                
                -- 1.3.6.1.4.1.10428 9 1.101.23.5.7.2.2.17
                fkGponProfileTdmPwControlRtpSyncSourceChannel OBJECT-TYPE
                        SYNTAX INTEGER (0..65535)
                        MAX-ACCESS read-write
                        STATUS current
                        DESCRIPTION
                                "Configure RTP Synchronization Source"
                        ::= { fkGponProfileTdmPwControl 17 }

                
                -- 1.3.6.1.4.1.10428 9 1.101.23.5.7.2.2.18
                fkGponProfileTdmPwControlRtpSyncSourceSignalling OBJECT-TYPE
                        SYNTAX INTEGER (0..65535)
                        MAX-ACCESS read-write
                        STATUS current
                        DESCRIPTION
                                "Configure RTP Synchronization Source Signalling"
                        ::= { fkGponProfileTdmPwControl 18 }

                
                -- 1.3.6.1.4.1.10428 9 1.101.23.5.7.2.2.19
                fkGponProfileTdmPwControlRtpExpectPayloadChannel OBJECT-TYPE
                        SYNTAX INTEGER (0..65535)
                        MAX-ACCESS read-write
                        STATUS current
                        DESCRIPTION
                                "Configure Expected RTP Payload Type"
                        ::= { fkGponProfileTdmPwControl 19 }

                
                -- 1.3.6.1.4.1.10428 9 1.101.23.5.7.2.2.20
                fkGponProfileTdmPwControlRtpExpectPaloadSignalling OBJECT-TYPE
                        SYNTAX INTEGER (0..65535)
                        MAX-ACCESS read-write
                        STATUS current
                        DESCRIPTION
                                "Configure Expected RTP Payload Signalling"
                        ::= { fkGponProfileTdmPwControl 20 }

                
                -- 1.3.6.1.4.1.10428 9 1.101.23.5.7.2.2.21
                fkGponProfileTdmPwControlRtpExpectSyncSourceChannel OBJECT-TYPE
                        SYNTAX INTEGER (0..65535)
                        MAX-ACCESS read-write
                        STATUS current
                        DESCRIPTION
                                "Configure Expected RTP Synchronization Source"
                        ::= { fkGponProfileTdmPwControl 21 }

                
                -- 1.3.6.1.4.1.10428 9 1.101.23.5.7.2.2.22
                fkGponProfileTdmPwControlRtpExpectSyncSourceSignalling OBJECT-TYPE
                        SYNTAX INTEGER (0..65535)
                        MAX-ACCESS read-write
                        STATUS current
                        DESCRIPTION
                                "Configure Expected RTP Synchronization Source Signalling"
                        ::= { fkGponProfileTdmPwControl 22 }

                
                -- 1.3.6.1.4.1.10428 9 1.101.23.5.7.2.2.23
                fkGponProfileTdmPwControlMtProfileName OBJECT-TYPE
                        SYNTAX OCTET STRING
                        MAX-ACCESS read-write
                        STATUS current
                        DESCRIPTION
                                "Configure PW Maintenance Profile"
                        ::= { fkGponProfileTdmPwControl 23 }

                
                -- 1.3.6.1.4.1.10428 9 1.101.23.5.7.2.3
                fkGponProfileTdmPwNotification OBJECT IDENTIFIER ::= { fkGponProfileTdmPw 3 }

                
                -- 1.3.6.1.4.1.10428 9 1.101.23.5.7.2.3.1
                fkGponProfileTdmPwProfileCreated NOTIFICATION-TYPE
                        OBJECTS { fkGponProfileTdmPwControlRequest, fkGponProfileTdmPwControlTimeStamp, fkGponProfileTdmPwControlReqResult, fkGponProfileTdmPwControlName }
                        STATUS current
                        DESCRIPTION 
                                "Description."
                        ::= { fkGponProfileTdmPwNotification 1 }

                
                -- 1.3.6.1.4.1.10428 9 1.101.23.5.7.2.3.2
                fkGponProfileTdmPwProfileDeleted NOTIFICATION-TYPE
                        OBJECTS { fkGponProfileTdmPwControlRequest, fkGponProfileTdmPwControlTimeStamp, fkGponProfileTdmPwControlReqResult, fkGponProfileTdmPwControlIndex }
                        STATUS current
                        DESCRIPTION 
                                "Description."
                        ::= { fkGponProfileTdmPwNotification 2 }

                
                -- 1.3.6.1.4.1.10428 9 1.101.23.5.7.2.3.3
                fkGponProfileTdmPwServiceTypeChanged NOTIFICATION-TYPE
                        OBJECTS { fkGponProfileTdmPwControlRequest, fkGponProfileTdmPwControlTimeStamp, fkGponProfileTdmPwControlReqResult, fkGponProfileTdmPwControlIndex, fkGponProfileTdmPwControlServiceType
                                 }
                        STATUS current
                        DESCRIPTION 
                                "Description."
                        ::= { fkGponProfileTdmPwNotification 3 }

                
                -- 1.3.6.1.4.1.10428 9 1.101.23.5.7.2.3.4
                fkGponProfileTdmPwSignallingChanged NOTIFICATION-TYPE
                        OBJECTS { fkGponProfileTdmPwControlRequest, fkGponProfileTdmPwControlTimeStamp, fkGponProfileTdmPwControlReqResult, fkGponProfileTdmPwControlIndex, fkGponProfileTdmPwControlSignalling
                                 }
                        STATUS current
                        DESCRIPTION 
                                "Description."
                        ::= { fkGponProfileTdmPwNotification 4 }

                
                -- 1.3.6.1.4.1.10428 9 1.101.23.5.7.2.3.5
                fkGponProfileTdmPwPayloadSizeChanged NOTIFICATION-TYPE
                        OBJECTS { fkGponProfileTdmPwControlRequest, fkGponProfileTdmPwControlTimeStamp, fkGponProfileTdmPwControlReqResult, fkGponProfileTdmPwControlIndex, fkGponProfileTdmPwControlPayloadSize
                                 }
                        STATUS current
                        DESCRIPTION 
                                "Description."
                        ::= { fkGponProfileTdmPwNotification 5 }

                
                -- 1.3.6.1.4.1.10428 9 1.101.23.5.7.2.3.6
                fkGponProfileTdmPwPayloadEncapsulationDelayChanged NOTIFICATION-TYPE
                        OBJECTS { fkGponProfileTdmPwControlRequest, fkGponProfileTdmPwControlTimeStamp, fkGponProfileTdmPwControlReqResult, fkGponProfileTdmPwControlIndex, fkGponProfileTdmPwControlPayloadEncapulationDelay
                                 }
                        STATUS current
                        DESCRIPTION 
                                "Description."
                        ::= { fkGponProfileTdmPwNotification 6 }

                
                -- 1.3.6.1.4.1.10428 9 1.101.23.5.7.2.3.7
                fkGponProfileTdmPwTimingModeChanged NOTIFICATION-TYPE
                        OBJECTS { fkGponProfileTdmPwControlRequest, fkGponProfileTdmPwControlTimeStamp, fkGponProfileTdmPwControlReqResult, fkGponProfileTdmPwControlIndex, fkGponProfileTdmPwControlTimingMode
                                 }
                        STATUS current
                        DESCRIPTION 
                                "Description."
                        ::= { fkGponProfileTdmPwNotification 7 }

                
                -- 1.3.6.1.4.1.10428 9 1.101.23.5.7.2.3.8
                fkGponProfileTdmPwRtpClockReferenceChanged NOTIFICATION-TYPE
                        OBJECTS { fkGponProfileTdmPwControlRequest, fkGponProfileTdmPwControlTimeStamp, fkGponProfileTdmPwControlReqResult, fkGponProfileTdmPwControlIndex, fkGponProfileTdmPwControlRtpClockRefernce
                                 }
                        STATUS current
                        DESCRIPTION 
                                "Description."
                        ::= { fkGponProfileTdmPwNotification 8 }

                
                -- 1.3.6.1.4.1.10428 9 1.101.23.5.7.2.3.9
                fkGponProfileTdmPwRtpTimeStampmodeChanged NOTIFICATION-TYPE
                        OBJECTS { fkGponProfileTdmPwControlRequest, fkGponProfileTdmPwControlTimeStamp, fkGponProfileTdmPwControlReqResult, fkGponProfileTdmPwControlIndex, fkGponProfileTdmPwControlRtpTimeStampMode
                                 }
                        STATUS current
                        DESCRIPTION 
                                "Description."
                        ::= { fkGponProfileTdmPwNotification 9 }

                
                -- 1.3.6.1.4.1.10428 9 1.101.23.5.7.2.3.10
                fkGponProfileTdmPwRtpPayloadTypeChanged NOTIFICATION-TYPE
                        OBJECTS { fkGponProfileTdmPwControlRequest, fkGponProfileTdmPwControlTimeStamp, fkGponProfileTdmPwControlReqResult, fkGponProfileTdmPwControlIndex, fkGponProfileTdmPwControlRtpPayloadChannel, 
                                fkGponProfileTdmPwControlRtpPayloadSignalling }
                        STATUS current
                        DESCRIPTION 
                                "Description."
                        ::= { fkGponProfileTdmPwNotification 10 }

                
                -- 1.3.6.1.4.1.10428 9 1.101.23.5.7.2.3.11
                fkGponProfileTdmPwRtpSyncSourceChanged NOTIFICATION-TYPE
                        OBJECTS { fkGponProfileTdmPwControlRequest, fkGponProfileTdmPwControlTimeStamp, fkGponProfileTdmPwControlReqResult, fkGponProfileTdmPwControlIndex, fkGponProfileTdmPwControlRtpSyncSourceChannel, 
                                fkGponProfileTdmPwControlRtpSyncSourceSignalling }
                        STATUS current
                        DESCRIPTION 
                                "Description."
                        ::= { fkGponProfileTdmPwNotification 11 }

                
                -- 1.3.6.1.4.1.10428 9 1.101.23.5.7.2.3.12
                fkGponProfileTdmPwRtpExpectPayloadTypeChanged NOTIFICATION-TYPE
                        OBJECTS { fkGponProfileTdmPwControlRequest, fkGponProfileTdmPwControlTimeStamp, fkGponProfileTdmPwControlReqResult, fkGponProfileTdmPwControlIndex, fkGponProfileTdmPwControlRtpExpectPayloadChannel, 
                                fkGponProfileTdmPwControlRtpExpectPaloadSignalling }
                        STATUS current
                        DESCRIPTION 
                                "Description."
                        ::= { fkGponProfileTdmPwNotification 12 }

                
                -- 1.3.6.1.4.1.10428 9 1.101.23.5.7.2.3.13
                fkGponProfileTdmPwRtpExpectSyncSourceChanged NOTIFICATION-TYPE
                        OBJECTS { fkGponProfileTdmPwControlRequest, fkGponProfileTdmPwControlTimeStamp, fkGponProfileTdmPwControlReqResult, fkGponProfileTdmPwControlIndex, fkGponProfileTdmPwControlRtpExpectSyncSourceChannel, 
                                fkGponProfileTdmPwControlRtpExpectSyncSourceSignalling }
                        STATUS current
                        DESCRIPTION 
                                "Description."
                        ::= { fkGponProfileTdmPwNotification 13 }

                
                -- 1.3.6.1.4.1.10428 9 1.101.23.5.7.2.3.14
                fkGponProfileTdmPwMtProfileChanged NOTIFICATION-TYPE
                        OBJECTS { fkGponProfileTdmPwControlRequest, fkGponProfileTdmPwControlTimeStamp, fkGponProfileTdmPwControlReqResult, fkGponProfileTdmPwControlIndex, fkGponProfileTdmPwControlMtProfileName
                                 }
                        STATUS current
                        DESCRIPTION 
                                "Description."
                        ::= { fkGponProfileTdmPwNotification 14 }

                
--  1.3.6.1.4.1.10428 9 1.101.23.5.7.3
                -- 1.3.6.1.4.1.10428 9 1.101.23.5.7.3
                fkGponProfileTdmSdh OBJECT IDENTIFIER ::= { fkGponProfileTdm 3 }

                
--  1.3.6.1.4.1.10428 9 1.101.23.5.7.3.1
                -- 1.3.6.1.4.1.10428 9 1.101.23.5.7.3.1
                fkGponProfileTdmSdhTable OBJECT-TYPE
                        SYNTAX SEQUENCE OF FkGponProfileTdmSdhEntry
                        MAX-ACCESS not-accessible
                        STATUS current
                        DESCRIPTION
                                "fkGponProfileTdmSdhTable"
                        ::= { fkGponProfileTdmSdh 1 }

                
--  1.3.6.1.4.1.10428 9 1.101.23.5.7.3.1.1
                -- 1.3.6.1.4.1.10428 9 1.101.23.5.7.3.1.1
                fkGponProfileTdmSdhEntry OBJECT-TYPE
                        SYNTAX FkGponProfileTdmSdhEntry
                        MAX-ACCESS not-accessible
                        STATUS current
                        DESCRIPTION
                                "key: fkGponProfileTdmSdhIndex"
                        INDEX { fkGponProfileTdmSdhIndex }
                        ::= { fkGponProfileTdmSdhTable 1 }

                
                FkGponProfileTdmSdhEntry ::=
                        SEQUENCE { 
                                fkGponProfileTdmSdhIndex
                                        INTEGER,
                                fkGponProfileTdmSdhName
                                        OCTET STRING,
                                fkGponProfileTdmSdhTuType
                                        INTEGER,
                                fkGponProfileTdmSdhGemLossIntergrationPeriod
                                        INTEGER,
                                fkGponProfileTdmSdhTransmitJ1J2
                                        INTEGER,
                                fkGponProfileTdmSdhExpectJ1J2
                                        INTEGER,
                                fkGponProfileTdmSdhReceiveJ1J2
                                        INTEGER,
                                fkGponProfileTdmSdhTimMonitor
                                        INTEGER,
                                fkGponProfileTdmSdhTimAis
                                        INTEGER
                         }

--  1.3.6.1.4.1.10428 9 1.101.23.5.7.3.1.1.1
                -- 1.3.6.1.4.1.10428 9 1.101.23.5.7.3.1.1.1
                fkGponProfileTdmSdhIndex OBJECT-TYPE
                        SYNTAX INTEGER (1..65535)
                        MAX-ACCESS read-only
                        STATUS current
                        DESCRIPTION
                                "fkGponProfileTdmSdhIndex (unused)"
                        ::= { fkGponProfileTdmSdhEntry 1 }

                
--  1.3.6.1.4.1.10428 9 1.101.23.5.7.3.1.1.2
                -- 1.3.6.1.4.1.10428 9 1.101.23.5.7.3.1.1.2
                fkGponProfileTdmSdhName OBJECT-TYPE
                        SYNTAX OCTET STRING
                        MAX-ACCESS read-only
                        STATUS current
                        DESCRIPTION
                                "fkGponProfileTdmSdhName (unused)"
                        ::= { fkGponProfileTdmSdhEntry 2 }

                
--  1.3.6.1.4.1.10428 9 1.101.23.5.7.3.1.1.3
                -- 1.3.6.1.4.1.10428 9 1.101.23.5.7.3.1.1.3
                fkGponProfileTdmSdhTuType OBJECT-TYPE
                        SYNTAX INTEGER
                                {
                                tu11(0),
                                tu12(1),
                                tu2(2),
                                tu3(3)
                                }
                        MAX-ACCESS read-only
                        STATUS current
                        DESCRIPTION
                                "fkGponProfileTdmSdhTuType (unused)"
                        ::= { fkGponProfileTdmSdhEntry 3 }

                
--  1.3.6.1.4.1.10428 9 1.101.23.5.7.3.1.1.4
                -- 1.3.6.1.4.1.10428 9 1.101.23.5.7.3.1.1.4
                fkGponProfileTdmSdhGemLossIntergrationPeriod OBJECT-TYPE
                        SYNTAX INTEGER (1..65535)
                        MAX-ACCESS read-only
                        STATUS current
                        DESCRIPTION
                                "fkGponProfileTdmSdhGemLossIntergrationPeriod (unused)"
                        ::= { fkGponProfileTdmSdhEntry 4 }

                
--  1.3.6.1.4.1.10428 9 1.101.23.5.7.3.1.1.5
                -- 1.3.6.1.4.1.10428 9 1.101.23.5.7.3.1.1.5
                fkGponProfileTdmSdhTransmitJ1J2 OBJECT-TYPE
                        SYNTAX INTEGER (1..65535)
                        MAX-ACCESS read-only
                        STATUS current
                        DESCRIPTION
                                "fkGponProfileTdmSdhTransmitJ1J2 (unused)"
                        ::= { fkGponProfileTdmSdhEntry 5 }

                
--  1.3.6.1.4.1.10428 9 1.101.23.5.7.3.1.1.6
                -- 1.3.6.1.4.1.10428 9 1.101.23.5.7.3.1.1.6
                fkGponProfileTdmSdhExpectJ1J2 OBJECT-TYPE
                        SYNTAX INTEGER (1..65535)
                        MAX-ACCESS read-only
                        STATUS current
                        DESCRIPTION
                                "fkGponProfileTdmSdhExpectJ1J2 (unused)"
                        ::= { fkGponProfileTdmSdhEntry 6 }

                
--  1.3.6.1.4.1.10428 9 1.101.23.5.7.3.1.1.7
                -- 1.3.6.1.4.1.10428 9 1.101.23.5.7.3.1.1.7
                fkGponProfileTdmSdhReceiveJ1J2 OBJECT-TYPE
                        SYNTAX INTEGER (1..65535)
                        MAX-ACCESS read-only
                        STATUS current
                        DESCRIPTION
                                "fkGponProfileTdmSdhReceiveJ1J2 (unused)"
                        ::= { fkGponProfileTdmSdhEntry 7 }

                
--  1.3.6.1.4.1.10428 9 1.101.23.5.7.3.1.1.8
                -- 1.3.6.1.4.1.10428 9 1.101.23.5.7.3.1.1.8
                fkGponProfileTdmSdhTimMonitor OBJECT-TYPE
                        SYNTAX INTEGER
                                {
                                disable(0),
                                enable(1)
                                }
                        MAX-ACCESS read-only
                        STATUS current
                        DESCRIPTION
                                "fkGponProfileTdmSdhTimMonitor (unused)"
                        ::= { fkGponProfileTdmSdhEntry 8 }

                
--  1.3.6.1.4.1.10428 9 1.101.23.5.7.3.1.1.9
                -- 1.3.6.1.4.1.10428 9 1.101.23.5.7.3.1.1.9
                fkGponProfileTdmSdhTimAis OBJECT-TYPE
                        SYNTAX INTEGER
                                {
                                disable(0),
                                enable(1)
                                }
                        MAX-ACCESS read-only
                        STATUS current
                        DESCRIPTION
                                "fkGponProfileTdmSdhTimAis (unused)"
                        ::= { fkGponProfileTdmSdhEntry 9 }

                
--  1.3.6.1.4.1.10428 9 1.101.23.5.7.3.2
                -- 1.3.6.1.4.1.10428 9 1.101.23.5.7.3.2
                fkGponProfileTdmSdhControl OBJECT IDENTIFIER ::= { fkGponProfileTdmSdh 2 }

                
--  1.3.6.1.4.1.10428 9 1.101.23.5.7.3.2.1
                -- 1.3.6.1.4.1.10428 9 1.101.23.5.7.3.2.1
                fkGponProfileTdmSdhControlRequest OBJECT-TYPE
                        SYNTAX INTEGER
                                {
                                createProfile(1),
                                destroyProfile(2),
                                setTuType(3),
                                setGemLossIntergrationPeriod(4),
                                setTransmitJ1J2(5),
                                setExpectJ1J2(6),
                                setreceiveJ1J2(7),
                                setTimMonitor(8),
                                setTimAis(9)
                                }
                        MAX-ACCESS read-write
                        STATUS current
                        DESCRIPTION
                                "The request of a user command"
                        ::= { fkGponProfileTdmSdhControl 1 }

                
--  1.3.6.1.4.1.10428 9 1.101.23.5.7.3.2.2
                -- 1.3.6.1.4.1.10428 9 1.101.23.5.7.3.2.2
                fkGponProfileTdmSdhControlStatus OBJECT-TYPE
                        SYNTAX FkControlStatusType
                        MAX-ACCESS read-only
                        STATUS current
                        DESCRIPTION
                                "The status of user command"
                        ::= { fkGponProfileTdmSdhControl 2 }

                
--  1.3.6.1.4.1.10428 9 1.101.23.5.7.3.2.3
                -- 1.3.6.1.4.1.10428 9 1.101.23.5.7.3.2.3
                fkGponProfileTdmSdhControlTimer OBJECT-TYPE
                        SYNTAX Gauge32
                        MAX-ACCESS read-write
                        STATUS current
                        DESCRIPTION
                                "The maximum time for the manager for a long running user command"
                        ::= { fkGponProfileTdmSdhControl 3 }

                
--  1.3.6.1.4.1.10428 9 1.101.23.5.7.3.2.4
                -- 1.3.6.1.4.1.10428 9 1.101.23.5.7.3.2.4
                fkGponProfileTdmSdhControlTimeStamp OBJECT-TYPE
                        SYNTAX TimeTicks
                        MAX-ACCESS read-only
                        STATUS current
                        DESCRIPTION
                                "The time stamp of the last command(end of command)"
                        ::= { fkGponProfileTdmSdhControl 4 }

                
--  1.3.6.1.4.1.10428 9 1.101.23.5.7.3.2.5
                -- 1.3.6.1.4.1.10428 9 1.101.23.5.7.3.2.5
                fkGponProfileTdmSdhControlReqResult OBJECT-TYPE
                        SYNTAX FkControlRequestResultType
                        MAX-ACCESS read-only
                        STATUS current
                        DESCRIPTION
                                "The result of the last user command"
                        ::= { fkGponProfileTdmSdhControl 5 }

                
--  1.3.6.1.4.1.10428 9 1.101.23.5.7.3.2.6
                -- 1.3.6.1.4.1.10428 9 1.101.23.5.7.3.2.6
                fkGponProfileTdmSdhControlIndex OBJECT-TYPE
                        SYNTAX INTEGER (1..65535)
                        MAX-ACCESS read-write
                        STATUS current
                        DESCRIPTION
                                "fkGponProfileTdmSdhControlIndex (unused)"
                        ::= { fkGponProfileTdmSdhControl 6 }

                
--  1.3.6.1.4.1.10428 9 1.101.23.5.7.3.2.7
                -- 1.3.6.1.4.1.10428 9 1.101.23.5.7.3.2.7
                fkGponProfileTdmSdhControlName OBJECT-TYPE
                        SYNTAX OCTET STRING
                        MAX-ACCESS read-write
                        STATUS current
                        DESCRIPTION
                                "fkGponProfileTdmSdhControlName (unused)"
                        ::= { fkGponProfileTdmSdhControl 7 }

                
--  1.3.6.1.4.1.10428 9 1.101.23.5.7.3.2.8
                -- 1.3.6.1.4.1.10428 9 1.101.23.5.7.3.2.8
                fkGponProfileTdmSdhControlTuType OBJECT-TYPE
                        SYNTAX INTEGER
                                {
                                tu11(0),
                                tu12(1),
                                tu2(2),
                                tu3(3)
                                }
                        MAX-ACCESS read-write
                        STATUS current
                        DESCRIPTION
                                "fkGponProfileTdmSdhControlTuType (unused)"
                        ::= { fkGponProfileTdmSdhControl 8 }

                
--  1.3.6.1.4.1.10428 9 1.101.23.5.7.3.2.9
                -- 1.3.6.1.4.1.10428 9 1.101.23.5.7.3.2.9
                fkGponProfileTdmSdhControlGemLossIntergrationPeriod OBJECT-TYPE
                        SYNTAX INTEGER (1..65535)
                        MAX-ACCESS read-write
                        STATUS current
                        DESCRIPTION
                                "fkGponProfileTdmSdhControlGemLossIntergrationPeriod (unused)"
                        ::= { fkGponProfileTdmSdhControl 9 }

                
--  1.3.6.1.4.1.10428 9 1.101.23.5.7.3.2.10
                -- 1.3.6.1.4.1.10428 9 1.101.23.5.7.3.2.10
                fkGponProfileTdmSdhControlTransmitJ1J2 OBJECT-TYPE
                        SYNTAX INTEGER (1..65535)
                        MAX-ACCESS read-write
                        STATUS current
                        DESCRIPTION
                                "fkGponProfileTdmSdhControlTransmitJ1J2 (unused)"
                        ::= { fkGponProfileTdmSdhControl 10 }

                
--  1.3.6.1.4.1.10428 9 1.101.23.5.7.3.2.11
                -- 1.3.6.1.4.1.10428 9 1.101.23.5.7.3.2.11
                fkGponProfileTdmSdhControlExpectJ1J2 OBJECT-TYPE
                        SYNTAX INTEGER (1..65535)
                        MAX-ACCESS read-write
                        STATUS current
                        DESCRIPTION
                                "fkGponProfileTdmSdhControlExpectJ1J2 (unused)"
                        ::= { fkGponProfileTdmSdhControl 11 }

                
--  1.3.6.1.4.1.10428 9 1.101.23.5.7.3.2.12
                -- 1.3.6.1.4.1.10428 9 1.101.23.5.7.3.2.12
                fkGponProfileTdmSdhControlReceiveJ1J2 OBJECT-TYPE
                        SYNTAX INTEGER (1..65535)
                        MAX-ACCESS read-write
                        STATUS current
                        DESCRIPTION
                                "fkGponProfileTdmSdhControlReceiveJ1J2 (unused)"
                        ::= { fkGponProfileTdmSdhControl 12 }

                
--  1.3.6.1.4.1.10428 9 1.101.23.5.7.3.2.13
                -- 1.3.6.1.4.1.10428 9 1.101.23.5.7.3.2.13
                fkGponProfileTdmSdhControlTimMonitor OBJECT-TYPE
                        SYNTAX INTEGER
                                {
                                disable(0),
                                enable(1)
                                }
                        MAX-ACCESS read-write
                        STATUS current
                        DESCRIPTION
                                "fkGponProfileTdmSdhControlTimMonitor (unused)"
                        ::= { fkGponProfileTdmSdhControl 13 }

                
--  1.3.6.1.4.1.10428 9 1.101.23.5.7.3.2.14
                -- 1.3.6.1.4.1.10428 9 1.101.23.5.7.3.2.14
                fkGponProfileTdmSdhControlTimAis OBJECT-TYPE
                        SYNTAX INTEGER
                                {
                                disable(0),
                                enable(1)
                                }
                        MAX-ACCESS read-write
                        STATUS current
                        DESCRIPTION
                                "fkGponProfileTdmSdhControlTimAis (unused)"
                        ::= { fkGponProfileTdmSdhControl 14 }

                
--  1.3.6.1.4.1.10428 9 1.101.23.5.7.3.3
                -- 1.3.6.1.4.1.10428 9 1.101.23.5.7.3.3
                fkGponProfileTdmSdhNotification OBJECT IDENTIFIER ::= { fkGponProfileTdmSdh 3 }

                
--  1.3.6.1.4.1.10428 9 1.101.23.5.7.3.3.1
                -- 1.3.6.1.4.1.10428 9 1.101.23.5.7.3.3.1
                fkGponProfileTdmSdhProfileCreated NOTIFICATION-TYPE
                        OBJECTS { fkGponProfileTdmSdhControlRequest, fkGponProfileTdmSdhControlTimeStamp, fkGponProfileTdmSdhControlReqResult, fkGponProfileTdmSdhControlName }
                        STATUS current
                        DESCRIPTION 
                                "Description."
                        ::= { fkGponProfileTdmSdhNotification 1 }

                
--  1.3.6.1.4.1.10428 9 1.101.23.5.7.3.3.2
                -- 1.3.6.1.4.1.10428 9 1.101.23.5.7.3.3.2
                fkGponProfileTdmSdhProfileDeleted NOTIFICATION-TYPE
                        OBJECTS { fkGponProfileTdmSdhControlRequest, fkGponProfileTdmSdhControlTimeStamp, fkGponProfileTdmSdhControlReqResult, fkGponProfileTdmSdhControlIndex }
                        STATUS current
                        DESCRIPTION 
                                "Description."
                        ::= { fkGponProfileTdmSdhNotification 2 }

                
--  1.3.6.1.4.1.10428 9 1.101.23.5.7.3.3.3
                -- 1.3.6.1.4.1.10428 9 1.101.23.5.7.3.3.3
                fkGponProfileTdmSdhTuTypeChanged NOTIFICATION-TYPE
                        OBJECTS { fkGponProfileTdmSdhControlRequest, fkGponProfileTdmSdhControlTimeStamp, fkGponProfileTdmSdhControlReqResult, fkGponProfileTdmSdhControlIndex, fkGponProfileTdmSdhControlTuType
                                 }
                        STATUS current
                        DESCRIPTION 
                                "Description."
                        ::= { fkGponProfileTdmSdhNotification 3 }

                
--  1.3.6.1.4.1.10428 9 1.101.23.5.7.3.3.4
                -- 1.3.6.1.4.1.10428 9 1.101.23.5.7.3.3.4
                fkGponProfileTdmSdhGemLossIntergrationPeriodChanged NOTIFICATION-TYPE
                        OBJECTS { fkGponProfileTdmSdhControlRequest, fkGponProfileTdmSdhControlTimeStamp, fkGponProfileTdmSdhControlReqResult, fkGponProfileTdmSdhControlIndex, fkGponProfileTdmSdhControlGemLossIntergrationPeriod
                                 }
                        STATUS current
                        DESCRIPTION 
                                "Description."
                        ::= { fkGponProfileTdmSdhNotification 4 }

                
--  1.3.6.1.4.1.10428 9 1.101.23.5.7.3.3.5
                -- 1.3.6.1.4.1.10428 9 1.101.23.5.7.3.3.5
                fkGponProfileTdmSdhTransmitJ1J2Changed NOTIFICATION-TYPE
                        OBJECTS { fkGponProfileTdmSdhControlRequest, fkGponProfileTdmSdhControlTimeStamp, fkGponProfileTdmSdhControlReqResult, fkGponProfileTdmSdhControlIndex, fkGponProfileTdmSdhControlTransmitJ1J2
                                 }
                        STATUS current
                        DESCRIPTION 
                                "Description."
                        ::= { fkGponProfileTdmSdhNotification 5 }

                
--  1.3.6.1.4.1.10428 9 1.101.23.5.7.3.3.6
                -- 1.3.6.1.4.1.10428 9 1.101.23.5.7.3.3.6
                fkGponProfileTdmSdhExpectJ1J2Changed NOTIFICATION-TYPE
                        OBJECTS { fkGponProfileTdmSdhControlRequest, fkGponProfileTdmSdhControlTimeStamp, fkGponProfileTdmSdhControlReqResult, fkGponProfileTdmSdhControlIndex, fkGponProfileTdmSdhControlExpectJ1J2
                                 }
                        STATUS current
                        DESCRIPTION 
                                "Description."
                        ::= { fkGponProfileTdmSdhNotification 6 }

                
--  1.3.6.1.4.1.10428 9 1.101.23.5.7.3.3.7
                -- 1.3.6.1.4.1.10428 9 1.101.23.5.7.3.3.7
                fkGponProfileTdmSdhreceiveJ1J2Changed NOTIFICATION-TYPE
                        OBJECTS { fkGponProfileTdmSdhControlRequest, fkGponProfileTdmSdhControlTimeStamp, fkGponProfileTdmSdhControlReqResult, fkGponProfileTdmSdhControlIndex, fkGponProfileTdmSdhControlReceiveJ1J2
                                 }
                        STATUS current
                        DESCRIPTION 
                                "Description."
                        ::= { fkGponProfileTdmSdhNotification 7 }

                
--  1.3.6.1.4.1.10428 9 1.101.23.5.7.3.3.8
                -- 1.3.6.1.4.1.10428 9 1.101.23.5.7.3.3.8
                fkGponProfileTdmSdhTimMonitorChanged NOTIFICATION-TYPE
                        OBJECTS { fkGponProfileTdmSdhControlRequest, fkGponProfileTdmSdhControlTimeStamp, fkGponProfileTdmSdhControlReqResult, fkGponProfileTdmSdhControlIndex, fkGponProfileTdmSdhControlTimMonitor
                                 }
                        STATUS current
                        DESCRIPTION 
                                "Description."
                        ::= { fkGponProfileTdmSdhNotification 8 }

                
--  1.3.6.1.4.1.10428 9 1.101.23.5.7.3.3.9
                -- 1.3.6.1.4.1.10428 9 1.101.23.5.7.3.3.9
                fkGponProfileTdmSdhTimAisChanged NOTIFICATION-TYPE
                        OBJECTS { fkGponProfileTdmSdhControlRequest, fkGponProfileTdmSdhControlTimeStamp, fkGponProfileTdmSdhControlReqResult, fkGponProfileTdmSdhControlIndex, fkGponProfileTdmSdhControlTimAis
                                 }
                        STATUS current
                        DESCRIPTION 
                                "Description."
                        ::= { fkGponProfileTdmSdhNotification 9 }

                
--  1.3.6.1.4.1.10428 9 1.101.23.6
                -- 1.3.6.1.4.1.10428 9 1.101.23.6
                fkGponBridge OBJECT IDENTIFIER ::= { fkGpon 6 }

                
--  1.3.6.1.4.1.10428 9 1.101.23.6.1
                -- 1.3.6.1.4.1.10428 9 1.101.23.6.1
                fkGponOnuPort OBJECT IDENTIFIER ::= { fkGponBridge 1 }

                
--  1.3.6.1.4.1.10428 9 1.101.23.6.1.1
                -- 1.3.6.1.4.1.10428 9 1.101.23.6.1.1
                fkGponOnuPortTable OBJECT-TYPE
                        SYNTAX SEQUENCE OF FkGponOnuPortEntry
                        MAX-ACCESS not-accessible
                        STATUS current
                        DESCRIPTION
                                "fkGponOnuPortTable"
                        ::= { fkGponOnuPort 1 }

                
--  1.3.6.1.4.1.10428 9 1.101.23.6.1.1.1
                -- 1.3.6.1.4.1.10428 9 1.101.23.6.1.1.1
                fkGponOnuPortEntry OBJECT-TYPE
                        SYNTAX FkGponOnuPortEntry
                        MAX-ACCESS not-accessible
                        STATUS current
                        DESCRIPTION
                                "key: fkGponOltId, fkGponOnuId, fkGponOnuPortSlotId, fkGponOnuPortId"
                        INDEX { fkGponOltId, fkGponOnuId, fkGponOnuPortSlotId, fkGponOnuPortId }
                        ::= { fkGponOnuPortTable 1 }

                
                FkGponOnuPortEntry ::=
                        SEQUENCE { 
                                fkGponOnuPortSlotId
                                        INTEGER,
                                fkGponOnuPortId
                                        Integer32,
                                fkGponOnuPortSlotType
                                        INTEGER,
                                fkGponOnuPortAdminStatus
                                        INTEGER,
                                fkGponOnuPortOperStatus
                                        INTEGER,
                                fkGponOnuPortLinkUptime
                                        Counter64,
                                fkGponOnuPortAutoNego
                                        INTEGER,
                                fkGponOnuPortSpeed
                                        INTEGER,
                                fkGponOnuPortDuplex
                                        INTEGER,
                                fkGponOnuPortGemblockRx
                                        Counter64,
                                fkGponOnuPortGemblockTx
                                        Counter64,
                                fkGponOnuPortDiscardFrames
                                        Counter64,
                                fkGponOnuPortElapsedTimeAfterClearStats
                                        Counter64,
                                fkGponOnuPortHookState
                                        INTEGER,
                                fkGponOnuPortSensedType
                                        INTEGER,
                                fkGponOnuPortUniDescription
                                        OCTET STRING,
                                fkGponOnuPortConfSpeed
                                        INTEGER,
                                fkGponOnuPortConfDuplex
                                        INTEGER,
                                fkGponOnuPortMediumMode
                                        INTEGER,
                                fkGponOnuPortLoopbackStatus
                                        INTEGER,
                                fkGponOnuPortOpticModuleInstall
                                        INTEGER,
                                fkGponOnuPortOpticModuleTransceiverType
                                        INTEGER,
                                fkGponOnuPortOpticModuleTransceiverDetailType
                                        INTEGER,
                                fkGponOnuPortOpticModuleLengthMode
                                        INTEGER,
                                fkGponOnuPortOpticModuleLength
                                        INTEGER,
                                fkGponOnuPortOpticModuleSpeed
                                        INTEGER,
                                fkGponOnuPortOpticModuleWavelength
                                        INTEGER,
                                fkGponOnuPortOpticModuleConnecterType
                                        INTEGER,
                                fkGponOnuPortOpticModuleVendorName
                                        OCTET STRING,
                                fkGponOnuPortOpticModuleVendorPartName
                                        OCTET STRING,
                                fkGponOnuPortOpticModuleVendorRevision
                                        OCTET STRING,
                                fkGponOnuPortOpticModuleVendorSerialNumber
                                        OCTET STRING,
                                fkGponOnuPortOpticModuleProductDate
                                        OCTET STRING,
                                fkGponOnuPortLinkUpCount
                                        Integer32,
                                fkGponOnuPortLinkDownCount
                                        Integer32,
                                fkGponOnuPortOpticModuleTemper
                                        OCTET STRING,
                                fkGponOnuPortOpticModuleVoltage
                                        OCTET STRING,
                                fkGponOnuPortOpticModuleTxbias
                                        OCTET STRING,
                                fkGponOnuPortOpticModuleTxPower
                                        OCTET STRING,
                                fkGponOnuPortOpticModuleRxPower
                                        OCTET STRING,
                                fkGponOnuPortMgmtAdminStatus
                                        INTEGER,
                                fkGponOnuPortMgmtCapability
                                        INTEGER,
                                fkGponOnuPortMgmtMethod
                                        INTEGER
                         }

--  1.3.6.1.4.1.10428 9 1.101.23.6.1.1.1.1
                -- 1.3.6.1.4.1.10428 9 1.101.23.6.1.1.1.1
                fkGponOnuPortSlotId OBJECT-TYPE
                        SYNTAX INTEGER
                                {
                                ethernet(1),
                                pots(2),
                                ces(3),
                                video(4),
                                virtualEthernet(5),
                                wifi(6)
                                }
                        MAX-ACCESS read-only
                        STATUS current
                        DESCRIPTION
                                "Slot Number of ONU Port"
                        ::= { fkGponOnuPortEntry 1 }

                
--  1.3.6.1.4.1.10428 9 1.101.23.6.1.1.1.2
                -- 1.3.6.1.4.1.10428 9 1.101.23.6.1.1.1.2
                fkGponOnuPortId OBJECT-TYPE
                        SYNTAX Integer32 (1..65535)
                        MAX-ACCESS read-only
                        STATUS current
                        DESCRIPTION
                                "ONU Port Number"
                        ::= { fkGponOnuPortEntry 2 }

                
--  1.3.6.1.4.1.10428 9 1.101.23.6.1.1.1.3
                -- 1.3.6.1.4.1.10428 9 1.101.23.6.1.1.1.3
                fkGponOnuPortSlotType OBJECT-TYPE
                        SYNTAX INTEGER
                                {
                                unknown(0),
                                speed10M(1),
                                speed100M(2),
                                speed10Mspeed100M(3),
                                speed10Mspeed100Mspeed1000M(4),
                                pots(5),
                                virtualEthernet(6),
                                moca(7),
                                video(8),
                                ieee802dot11(9),
                                ds1(10),
                                e1(11),
                                configurableDs1E1(12)
                                }
                        MAX-ACCESS read-only
                        STATUS current
                        DESCRIPTION
                                "Slot type of ONU Port"
                        ::= { fkGponOnuPortEntry 3 }

                
--  1.3.6.1.4.1.10428 9 1.101.23.6.1.1.1.4
                -- 1.3.6.1.4.1.10428 9 1.101.23.6.1.1.1.4
                fkGponOnuPortAdminStatus OBJECT-TYPE
                        SYNTAX INTEGER
                                {
                                up(1),
                                down(2)
                                }
                        MAX-ACCESS read-only
                        STATUS current
                        DESCRIPTION
                                "State of ONU Port Administratoration"
                        ::= { fkGponOnuPortEntry 4 }

                
--  1.3.6.1.4.1.10428 9 1.101.23.6.1.1.1.5
                -- 1.3.6.1.4.1.10428 9 1.101.23.6.1.1.1.5
                fkGponOnuPortOperStatus OBJECT-TYPE
                        SYNTAX INTEGER
                                {
                                up(1),
                                down(2)
                                }
                        MAX-ACCESS read-only
                        STATUS current
                        DESCRIPTION
                                "State of ONU Port Operation"
                        ::= { fkGponOnuPortEntry 5 }

                
--  1.3.6.1.4.1.10428 9 1.101.23.6.1.1.1.6
                -- 1.3.6.1.4.1.10428 9 1.101.23.6.1.1.1.6
                fkGponOnuPortLinkUptime OBJECT-TYPE
                        SYNTAX Counter64
                        UNITS "1 sec"
                        MAX-ACCESS read-only
                        STATUS current
                        DESCRIPTION
                                "The elapsed time after link-up event"
                        ::= { fkGponOnuPortEntry 6 }

                
--  1.3.6.1.4.1.10428 9 1.101.23.6.1.1.1.7
                -- 1.3.6.1.4.1.10428 9 1.101.23.6.1.1.1.7
                fkGponOnuPortAutoNego OBJECT-TYPE
                        SYNTAX INTEGER
                                {
                                on(1),
                                off(2)
                                }
                        MAX-ACCESS read-only
                        STATUS current
                        DESCRIPTION
                                "The port auto negotiation.
                                (This OID is not available)"
                        ::= { fkGponOnuPortEntry 7 }

                
--  1.3.6.1.4.1.10428 9 1.101.23.6.1.1.1.8
                -- 1.3.6.1.4.1.10428 9 1.101.23.6.1.1.1.8
                fkGponOnuPortSpeed OBJECT-TYPE
                        SYNTAX INTEGER
                                {
                                speed10(1),
                                speed100(2),
                                speed1000(3),
                                unknown(255)
                                }
                        MAX-ACCESS read-only
                        STATUS current
                        DESCRIPTION
                                "The port speed.
                                (This OID is not available)"
                        ::= { fkGponOnuPortEntry 8 }

                
--  1.3.6.1.4.1.10428 9 1.101.23.6.1.1.1.9
                -- 1.3.6.1.4.1.10428 9 1.101.23.6.1.1.1.9
                fkGponOnuPortDuplex OBJECT-TYPE
                        SYNTAX INTEGER
                                {
                                full(1),
                                half(2),
                                unknown(255)
                                }
                        MAX-ACCESS read-only
                        STATUS current
                        DESCRIPTION
                                "The port duplex."
                        ::= { fkGponOnuPortEntry 9 }

                
--  1.3.6.1.4.1.10428 9 1.101.23.6.1.1.1.10
                -- 1.3.6.1.4.1.10428 9 1.101.23.6.1.1.1.10
                fkGponOnuPortGemblockRx OBJECT-TYPE
                        SYNTAX Counter64
                        MAX-ACCESS read-only
                        STATUS current
                        DESCRIPTION
                                "The gemblock port Rx count"
                        ::= { fkGponOnuPortEntry 10 }

                
--  1.3.6.1.4.1.10428 9 1.101.23.6.1.1.1.11
                -- 1.3.6.1.4.1.10428 9 1.101.23.6.1.1.1.11
                fkGponOnuPortGemblockTx OBJECT-TYPE
                        SYNTAX Counter64
                        MAX-ACCESS read-only
                        STATUS current
                        DESCRIPTION
                                "The gemblock port Tx count
                                "
                        ::= { fkGponOnuPortEntry 11 }

                
--  1.3.6.1.4.1.10428 9 1.101.23.6.1.1.1.12
                -- 1.3.6.1.4.1.10428 9 1.101.23.6.1.1.1.12
                fkGponOnuPortDiscardFrames OBJECT-TYPE
                        SYNTAX Counter64
                        MAX-ACCESS read-only
                        STATUS current
                        DESCRIPTION
                                "The discard frames."
                        ::= { fkGponOnuPortEntry 12 }

                
--  1.3.6.1.4.1.10428 9 1.101.23.6.1.1.1.13
                -- 1.3.6.1.4.1.10428 9 1.101.23.6.1.1.1.13
                fkGponOnuPortElapsedTimeAfterClearStats OBJECT-TYPE
                        SYNTAX Counter64
                        UNITS "1 sec"
                        MAX-ACCESS read-only
                        STATUS current
                        DESCRIPTION
                                "The elapsed time after clearing statistics."
                        ::= { fkGponOnuPortEntry 13 }

                
                -- 1.3.6.1.4.1.10428 9 1.101.23.6.1.1.1.14
                fkGponOnuPortHookState OBJECT-TYPE
                        SYNTAX INTEGER
                                {
                                on(1),
                                off(2),
                                unused(255)
                                }
                        MAX-ACCESS read-only
                        STATUS current
                        DESCRIPTION
                                "The port hook state"
                        ::= { fkGponOnuPortEntry 14 }

                
                -- 1.3.6.1.4.1.10428 9 1.101.23.6.1.1.1.15
                fkGponOnuPortSensedType OBJECT-TYPE
                        SYNTAX INTEGER
                                {
                                ds1(10),
                                e1(11),
                                unknown(255)
                                }
                        MAX-ACCESS read-only
                        STATUS current
                        DESCRIPTION
                                "The port sensed type"
                        ::= { fkGponOnuPortEntry 15 }

                
                -- 1.3.6.1.4.1.10428 9 1.101.23.6.1.1.1.16
                fkGponOnuPortUniDescription OBJECT-TYPE
                        SYNTAX OCTET STRING
                        MAX-ACCESS read-only
                        STATUS current
                        DESCRIPTION
                                "The port description for UNI of ONT."
                        ::= { fkGponOnuPortEntry 16 }

                
                -- 1.3.6.1.4.1.10428 9 1.101.23.6.1.1.1.17
                fkGponOnuPortConfSpeed OBJECT-TYPE
                        SYNTAX INTEGER
                                {
                                auto(0),
                                speed10(1),
                                speed100(2),
                                speed1000(3)
                                }
                        MAX-ACCESS read-only
                        STATUS current
                        DESCRIPTION
                                "The port speed configuration."
                        ::= { fkGponOnuPortEntry 17 }

                
                -- 1.3.6.1.4.1.10428 9 1.101.23.6.1.1.1.18
                fkGponOnuPortConfDuplex OBJECT-TYPE
                        SYNTAX INTEGER
                                {
                                auto(0),
                                full(1),
                                half(2)
                                }
                        MAX-ACCESS read-only
                        STATUS current
                        DESCRIPTION
                                "The port duplex configuration"
                        ::= { fkGponOnuPortEntry 18 }

                
                -- 1.3.6.1.4.1.10428 9 1.101.23.6.1.1.1.19
                fkGponOnuPortMediumMode OBJECT-TYPE
                        SYNTAX INTEGER
                                {
                                mdiX(0),
                                mdi(1),
                                auto(2),
                                unknown(255)
                                }
                        MAX-ACCESS read-only
                        STATUS current
                        DESCRIPTION
                                "The port medium mode."
                        ::= { fkGponOnuPortEntry 19 }

                
                -- 1.3.6.1.4.1.10428 9 1.101.23.6.1.1.1.20
                fkGponOnuPortLoopbackStatus OBJECT-TYPE
                        SYNTAX INTEGER
                                {
                                disable(0),
                                enableType1(1),
                                enableType2(2),
                                enableType3(3),
                                enableType4(4),
                                enableType5(5),
                                unknown(255)
                                }
                        MAX-ACCESS read-only
                        STATUS current
                        DESCRIPTION
                                "The port loopback Status configuration."
                        ::= { fkGponOnuPortEntry 20 }

                
                -- 1.3.6.1.4.1.10428 9 1.101.23.6.1.1.1.21
                fkGponOnuPortOpticModuleInstall OBJECT-TYPE
                        SYNTAX INTEGER
                                {
                                uninstall(0),
                                install(1)
                                }
                        MAX-ACCESS read-only
                        STATUS current
                        DESCRIPTION
                                "The module instatll status."
                        ::= { fkGponOnuPortEntry 21 }

                
                -- 1.3.6.1.4.1.10428 9 1.101.23.6.1.1.1.22
                fkGponOnuPortOpticModuleTransceiverType OBJECT-TYPE
                        SYNTAX INTEGER
                                {
                                gbic(1),
                                solderedToMotherboard(2),
                                sfp(3),
                                xbi300Pin(4),
                                xenpak(5),
                                xfp(6),
                                xff(7),
                                xfpE(8),
                                spak(9),
                                x2(10),
                                unknown(255)
                                }
                        MAX-ACCESS read-only
                        STATUS current
                        DESCRIPTION
                                "The module transceiver type.
                                1: GBIC
                                2 :Soldered to motherboard
                                3: SFP
                                4 :300 pin XBI
                                5: XENPAK
                                6: XFP
                                7: XFF
                                8: XFP-E
                                9 :XPAK
                                10: X2
                                255:Unknown"
                        ::= { fkGponOnuPortEntry 22 }

                
                -- 1.3.6.1.4.1.10428 9 1.101.23.6.1.1.1.23
                fkGponOnuPortOpticModuleTransceiverDetailType OBJECT-TYPE
                        SYNTAX INTEGER
                                {
                                base1000SX(1),
                                base1000LX(2),
                                base1000CX(3),
                                base1000T(4),
                                base1000LXorLX10(5),
                                base1000FX(6),
                                base1000BX10(7),
                                base1000PX(8),
                                oc3MultiShortReach(9),
                                oc3SingleIntermediateReach(10),
                                oc3SingleLongReach(11),
                                unknown(255)
                                }
                        MAX-ACCESS read-only
                        STATUS current
                        DESCRIPTION
                                "The module tranceiver detail type.
                                1: 1000Base-SX
                                2: 1000Base-LX
                                3: 1000Base-CX
                                4: 1000Base-T
                                5: 1000Base-LX/LX10
                                6: 100Base-FX
                                7: 1000Base-BX10
                                8: 1000Base-PX
                                9: OC-3(155M) Multi Mode Short Reach
                                10: OC-3(155M) Single Mode Intermediate Reach
                                11: OC-3(155M) Single Mode Long Reach
                                255: Unknown"
                        ::= { fkGponOnuPortEntry 23 }

                
                -- 1.3.6.1.4.1.10428 9 1.101.23.6.1.1.1.24
                fkGponOnuPortOpticModuleLengthMode OBJECT-TYPE
                        SYNTAX INTEGER
                                {
                                singleMode(1),
                                multiMode(2),
                                unknown(255)
                                }
                        MAX-ACCESS read-only
                        STATUS current
                        DESCRIPTION
                                "The module length mode.
                                1: singleMode
                                2: multiMode
                                255 : unknown"
                        ::= { fkGponOnuPortEntry 24 }

                
                -- 1.3.6.1.4.1.10428 9 1.101.23.6.1.1.1.25
                fkGponOnuPortOpticModuleLength OBJECT-TYPE
                        SYNTAX INTEGER (1..65535)
                        MAX-ACCESS read-only
                        STATUS current
                        DESCRIPTION
                                "the module length(m)."
                        ::= { fkGponOnuPortEntry 25 }

                
                -- 1.3.6.1.4.1.10428 9 1.101.23.6.1.1.1.26
                fkGponOnuPortOpticModuleSpeed OBJECT-TYPE
                        SYNTAX INTEGER
                                {
                                speed155(1),
                                speed200(2),
                                speed622(3),
                                speed1062dot5(4),
                                speed1250(5),
                                speed2125(6),
                                speed4250(7),
                                speed2488(8),
                                unknown(255)
                                }
                        MAX-ACCESS read-only
                        STATUS current
                        DESCRIPTION
                                "The module speed.
                                1: 155 Mb/s
                                2: 200 Mb/s
                                3: 622 Mb/s
                                4: 1062.5 Mb/s
                                5: 1250 Mb/s
                                6: 2125 Mb/s
                                7: 4250 Mb/s
                                8: 2488 Mb/s
                                255: unknown"
                        ::= { fkGponOnuPortEntry 26 }

                
                -- 1.3.6.1.4.1.10428 9 1.101.23.6.1.1.1.27
                fkGponOnuPortOpticModuleWavelength OBJECT-TYPE
                        SYNTAX INTEGER
                                {
                                length850(1),
                                length1310(2),
                                length1490(3),
                                length1550(4),
                                unknown(255)
                                }
                        MAX-ACCESS read-only
                        STATUS current
                        DESCRIPTION
                                "The module wavelength
                                1: 850 nm
                                2: 1310 nm
                                3: 1490 nm
                                4: 1550 nm
                                255: unknown"
                        ::= { fkGponOnuPortEntry 27 }

                
                -- 1.3.6.1.4.1.10428 9 1.101.23.6.1.1.1.28
                fkGponOnuPortOpticModuleConnecterType OBJECT-TYPE
                        SYNTAX INTEGER
                                {
                                sc(1),
                                fiberChannelStyle1(2),
                                fiberChannelStyle2(3),
                                bncTnc(4),
                                fiberChannelCoaxialHeaders(5),
                                fiberJack(6),
                                lc(7),
                                mtRj(8),
                                mu(9),
                                sg(10),
                                opticalPigtail(11),
                                hssdc2(12),
                                copperPigtail(13),
                                unknown(255)
                                }
                        MAX-ACCESS read-only
                        STATUS current
                        DESCRIPTION
                                "The module connecter type.
                                1: SC
                                2: Fiber Channel Style 1 copper connector
                                3: Fiber Channel Style 2 copper connector
                                4: BNC/TNC
                                5: Fiber Channel coaxial headers
                                6: Fiber Jack
                                7: LC
                                8: MT-RJ
                                9: MU
                                10: SG
                                11: Optical Pigtail
                                12: HSSDC II
                                13: Copper Pigtail
                                255: unknown"
                        ::= { fkGponOnuPortEntry 28 }

                
                -- 1.3.6.1.4.1.10428 9 1.101.23.6.1.1.1.29
                fkGponOnuPortOpticModuleVendorName OBJECT-TYPE
                        SYNTAX OCTET STRING
                        MAX-ACCESS read-only
                        STATUS current
                        DESCRIPTION
                                "The module vendor name."
                        ::= { fkGponOnuPortEntry 29 }

                
                -- 1.3.6.1.4.1.10428 9 1.101.23.6.1.1.1.30
                fkGponOnuPortOpticModuleVendorPartName OBJECT-TYPE
                        SYNTAX OCTET STRING
                        MAX-ACCESS read-only
                        STATUS current
                        DESCRIPTION
                                "The module vendor part name."
                        ::= { fkGponOnuPortEntry 30 }

                
                -- 1.3.6.1.4.1.10428 9 1.101.23.6.1.1.1.31
                fkGponOnuPortOpticModuleVendorRevision OBJECT-TYPE
                        SYNTAX OCTET STRING
                        MAX-ACCESS read-only
                        STATUS current
                        DESCRIPTION
                                "The module vendor revision."
                        ::= { fkGponOnuPortEntry 31 }

                
                -- 1.3.6.1.4.1.10428 9 1.101.23.6.1.1.1.32
                fkGponOnuPortOpticModuleVendorSerialNumber OBJECT-TYPE
                        SYNTAX OCTET STRING
                        MAX-ACCESS read-only
                        STATUS current
                        DESCRIPTION
                                "the moduel vendor serial number."
                        ::= { fkGponOnuPortEntry 32 }

                
                -- 1.3.6.1.4.1.10428 9 1.101.23.6.1.1.1.33
                fkGponOnuPortOpticModuleProductDate OBJECT-TYPE
                        SYNTAX OCTET STRING
                        MAX-ACCESS read-only
                        STATUS current
                        DESCRIPTION
                                "The module vendor product date."
                        ::= { fkGponOnuPortEntry 33 }

                
                -- 1.3.6.1.4.1.10428 9 1.101.23.6.1.1.1.34
                fkGponOnuPortLinkUpCount OBJECT-TYPE
                        SYNTAX Integer32 (0..65535)
                        MAX-ACCESS read-only
                        STATUS current
                        DESCRIPTION
                                "The Link Up Count of ONU Port"
                        ::= { fkGponOnuPortEntry 34 }

                
                -- 1.3.6.1.4.1.10428 9 1.101.23.6.1.1.1.35
                fkGponOnuPortLinkDownCount OBJECT-TYPE
                        SYNTAX Integer32 (0..65535)
                        MAX-ACCESS read-only
                        STATUS current
                        DESCRIPTION
                                "The Link Down Count of ONU Port"
                        ::= { fkGponOnuPortEntry 35 }

                
                -- 1.3.6.1.4.1.10428 9 1.101.23.6.1.1.1.36
                fkGponOnuPortOpticModuleTemper OBJECT-TYPE
                        SYNTAX OCTET STRING
                        MAX-ACCESS read-only
                        STATUS current
                        DESCRIPTION
                                "Internally measured module temperature.(C)"
                        ::= { fkGponOnuPortEntry 36 }

                
                -- 1.3.6.1.4.1.10428 9 1.101.23.6.1.1.1.37
                fkGponOnuPortOpticModuleVoltage OBJECT-TYPE
                        SYNTAX OCTET STRING
                        MAX-ACCESS read-only
                        STATUS current
                        DESCRIPTION
                                "Internally measured supply voltage in transceiver.(V)
                                "
                        ::= { fkGponOnuPortEntry 37 }

                
                -- 1.3.6.1.4.1.10428 9 1.101.23.6.1.1.1.38
                fkGponOnuPortOpticModuleTxbias OBJECT-TYPE
                        SYNTAX OCTET STRING
                        MAX-ACCESS read-only
                        STATUS current
                        DESCRIPTION
                                "Internally measured TX Bias Current.(mA)"
                        ::= { fkGponOnuPortEntry 38 }

                
                -- 1.3.6.1.4.1.10428 9 1.101.23.6.1.1.1.39
                fkGponOnuPortOpticModuleTxPower OBJECT-TYPE
                        SYNTAX OCTET STRING
                        MAX-ACCESS read-only
                        STATUS current
                        DESCRIPTION
                                "Measured TX output power.(dBm)"
                        ::= { fkGponOnuPortEntry 39 }

                
                -- 1.3.6.1.4.1.10428 9 1.101.23.6.1.1.1.40
                fkGponOnuPortOpticModuleRxPower OBJECT-TYPE
                        SYNTAX OCTET STRING
                        MAX-ACCESS read-only
                        STATUS current
                        DESCRIPTION
                                "Measured RX input power.(dBm)"
                        ::= { fkGponOnuPortEntry 40 }

                
                -- 1.3.6.1.4.1.10428 9 1.101.23.6.1.1.1.41
                fkGponOnuPortMgmtAdminStatus OBJECT-TYPE
                        SYNTAX INTEGER
                                {
                                up(0),
                                down(1),
                                unknown(255)
                                }
                        MAX-ACCESS read-only
                        STATUS current
                        DESCRIPTION
                                "State of ONU Port Administratoration"
                        ::= { fkGponOnuPortEntry 41 }

                
                -- 1.3.6.1.4.1.10428 9 1.101.23.6.1.1.1.42
                fkGponOnuPortMgmtCapability OBJECT-TYPE
                        SYNTAX INTEGER
                                {
                                omci(0),
                                nonOmci(1),
                                both(2),
                                unknown(255)
                                }
                        MAX-ACCESS read-only
                        STATUS current
                        DESCRIPTION
                                "The port management capability"
                        ::= { fkGponOnuPortEntry 42 }

                
                -- 1.3.6.1.4.1.10428 9 1.101.23.6.1.1.1.43
                fkGponOnuPortMgmtMethod OBJECT-TYPE
                        SYNTAX INTEGER
                                {
                                omci(0),
                                nonOmci(1),
                                unknown(255)
                                }
                        MAX-ACCESS read-only
                        STATUS current
                        DESCRIPTION
                                "The port management method"
                        ::= { fkGponOnuPortEntry 43 }

                
--  1.3.6.1.4.1.10428 9 1.101.23.6.1.2
                -- 1.3.6.1.4.1.10428 9 1.101.23.6.1.2
                fkGponOnuPortControl OBJECT IDENTIFIER ::= { fkGponOnuPort 2 }

                
--  1.3.6.1.4.1.10428 9 1.101.23.6.1.2.1
                -- 1.3.6.1.4.1.10428 9 1.101.23.6.1.2.1
                fkGponOnuPortControlRequest OBJECT-TYPE
                        SYNTAX INTEGER
                                {
                                setOnuPortAdmin(1),
                                setOnuPortAutoNego(2),
                                setOnuPortSpeed(3),
                                clearOnuPortStats(4),
                                setUniDescription(5),
                                setAutoDetection(6),
                                setOnuPortMediumMode(7),
                                setOnuPortLoopbackStatus(8),
                                updateOnuPortOpticModuleInfo(9),
                                updateOnuPortLinkStatisticsInfo(10),
                                updateOnuPortMgmtData(11)
                                }
                        MAX-ACCESS read-write
                        STATUS current
                        DESCRIPTION
                                "The request of a user command"
                        ::= { fkGponOnuPortControl 1 }

                
--  1.3.6.1.4.1.10428 9 1.101.23.6.1.2.2
                -- 1.3.6.1.4.1.10428 9 1.101.23.6.1.2.2
                fkGponOnuPortControlStatus OBJECT-TYPE
                        SYNTAX FkControlStatusType
                        MAX-ACCESS read-only
                        STATUS current
                        DESCRIPTION
                                "The status of user command"
                        ::= { fkGponOnuPortControl 2 }

                
--  1.3.6.1.4.1.10428 9 1.101.23.6.1.2.3
                -- 1.3.6.1.4.1.10428 9 1.101.23.6.1.2.3
                fkGponOnuPortControlTimer OBJECT-TYPE
                        SYNTAX Gauge32
                        MAX-ACCESS read-write
                        STATUS current
                        DESCRIPTION
                                "The maximum time for the manager for a long running user command"
                        ::= { fkGponOnuPortControl 3 }

                
--  1.3.6.1.4.1.10428 9 1.101.23.6.1.2.4
                -- 1.3.6.1.4.1.10428 9 1.101.23.6.1.2.4
                fkGponOnuPortControlTimeStamp OBJECT-TYPE
                        SYNTAX TimeTicks
                        MAX-ACCESS read-only
                        STATUS current
                        DESCRIPTION
                                "The time stamp of the last command(end of command)"
                        ::= { fkGponOnuPortControl 4 }

                
--  1.3.6.1.4.1.10428 9 1.101.23.6.1.2.5
                -- 1.3.6.1.4.1.10428 9 1.101.23.6.1.2.5
                fkGponOnuPortControlReqResult OBJECT-TYPE
                        SYNTAX FkControlRequestResultType
                        MAX-ACCESS read-only
                        STATUS current
                        DESCRIPTION
                                "The result of the last user command"
                        ::= { fkGponOnuPortControl 5 }

                
--  1.3.6.1.4.1.10428 9 1.101.23.6.1.2.6
                -- 1.3.6.1.4.1.10428 9 1.101.23.6.1.2.6
                fkGponOnuPortControlOltId OBJECT-TYPE
                        SYNTAX INTEGER (1..65535)
                        MAX-ACCESS read-write
                        STATUS current
                        DESCRIPTION
                                "Gpon Olt Index"
                        ::= { fkGponOnuPortControl 6 }

                
--  1.3.6.1.4.1.10428 9 1.101.23.6.1.2.7
                -- 1.3.6.1.4.1.10428 9 1.101.23.6.1.2.7
                fkGponOnuPortControlOnuId OBJECT-TYPE
                        SYNTAX INTEGER (1..65535)
                        MAX-ACCESS read-write
                        STATUS current
                        DESCRIPTION
                                "Gpon Onu Index"
                        ::= { fkGponOnuPortControl 7 }

                
--  1.3.6.1.4.1.10428 9 1.101.23.6.1.2.8
                -- 1.3.6.1.4.1.10428 9 1.101.23.6.1.2.8
                fkGponOnuPortControlSlotId OBJECT-TYPE
                        SYNTAX INTEGER
                                {
                                ethernet(1),
                                pots(2),
                                ces(3),
                                video(4),
                                virtualEthernet(5),
                                wifi(6)
                                }
                        MAX-ACCESS read-write
                        STATUS current
                        DESCRIPTION
                                "OSlot Number of ONU Port"
                        ::= { fkGponOnuPortControl 8 }

                
--  1.3.6.1.4.1.10428 9 1.101.23.6.1.2.9
                -- 1.3.6.1.4.1.10428 9 1.101.23.6.1.2.9
                fkGponOnuPortControlPortId OBJECT-TYPE
                        SYNTAX INTEGER (1..65535)
                        MAX-ACCESS read-write
                        STATUS current
                        DESCRIPTION
                                "ONU Port Number"
                        ::= { fkGponOnuPortControl 9 }

                
--  1.3.6.1.4.1.10428 9 1.101.23.6.1.2.10
                -- 1.3.6.1.4.1.10428 9 1.101.23.6.1.2.10
                fkGponOnuPortControlAdminStatus OBJECT-TYPE
                        SYNTAX INTEGER
                                {
                                up(1),
                                down(2)
                                }
                        MAX-ACCESS read-write
                        STATUS current
                        DESCRIPTION
                                "State of ONU Port Administratoration"
                        ::= { fkGponOnuPortControl 10 }

                
--  1.3.6.1.4.1.10428 9 1.101.23.6.1.2.11
                -- 1.3.6.1.4.1.10428 9 1.101.23.6.1.2.11
                fkGponOnuPortControlOnuSerial OBJECT-TYPE
                        SYNTAX OCTET STRING
                        MAX-ACCESS read-write
                        STATUS current
                        DESCRIPTION
                                "ONU Serial Number 
                                (This OID is not available.)"
                        ::= { fkGponOnuPortControl 11 }

                
--  1.3.6.1.4.1.10428 9 1.101.23.6.1.2.12
                -- 1.3.6.1.4.1.10428 9 1.101.23.6.1.2.12
                fkGponOnuPortControlAutoNego OBJECT-TYPE
                        SYNTAX INTEGER
                                {
                                on(1),
                                off(2)
                                }
                        MAX-ACCESS read-write
                        STATUS current
                        DESCRIPTION
                                "The port auto negotiation.
                                (This OID is not available.)"
                        ::= { fkGponOnuPortControl 12 }

                
--  1.3.6.1.4.1.10428 9 1.101.23.6.1.2.13
                -- 1.3.6.1.4.1.10428 9 1.101.23.6.1.2.13
                fkGponOnuPortControlSpeed OBJECT-TYPE
                        SYNTAX INTEGER
                                {
                                auto(0),
                                speed10(1),
                                speed100(2),
                                speed1000(3)
                                }
                        MAX-ACCESS read-write
                        STATUS current
                        DESCRIPTION
                                "The port speed configuration.
                                (This OID is not available.)"
                        ::= { fkGponOnuPortControl 13 }

                
                -- 1.3.6.1.4.1.10428 9 1.101.23.6.1.2.14
                fkGponOnuPortControlUniDescription OBJECT-TYPE
                        SYNTAX OCTET STRING
                        MAX-ACCESS read-write
                        STATUS current
                        DESCRIPTION
                                "The port description for UNI of ONT."
                        ::= { fkGponOnuPortControl 14 }

                
                -- 1.3.6.1.4.1.10428 9 1.101.23.6.1.2.15
                fkGponOnuPortControlDuplex OBJECT-TYPE
                        SYNTAX INTEGER
                                {
                                auto(0),
                                full(1),
                                half(2)
                                }
                        MAX-ACCESS read-write
                        STATUS current
                        DESCRIPTION
                                "The port duplex configuration"
                        ::= { fkGponOnuPortControl 15 }

                
                -- 1.3.6.1.4.1.10428 9 1.101.23.6.1.2.16
                fkGponOnuPortControlMediumMode OBJECT-TYPE
                        SYNTAX INTEGER
                                {
                                mdiX(0),
                                mdi(1),
                                auto(2),
                                unknown(255)
                                }
                        MAX-ACCESS read-write
                        STATUS current
                        DESCRIPTION
                                "The port medium mode."
                        ::= { fkGponOnuPortControl 16 }

                
                -- 1.3.6.1.4.1.10428 9 1.101.23.6.1.2.17
                fkGponOnuPortControlLoopbackStatus OBJECT-TYPE
                        SYNTAX INTEGER
                                {
                                disable(0),
                                enableType1(1),
                                enableType2(2),
                                enableType3(3),
                                enableType4(4),
                                enableType5(5),
                                unknown(255)
                                }
                        MAX-ACCESS read-write
                        STATUS current
                        DESCRIPTION
                                "The port loopback Status configuration."
                        ::= { fkGponOnuPortControl 17 }

                
--  1.3.6.1.4.1.10428 9 1.101.23.6.1.3
                -- 1.3.6.1.4.1.10428 9 1.101.23.6.1.3
                fkGponOnuPortNotification OBJECT IDENTIFIER ::= { fkGponOnuPort 3 }

                
--  1.3.6.1.4.1.10428 9 1.101.23.6.1.3.1
                -- 1.3.6.1.4.1.10428 9 1.101.23.6.1.3.1
                fkGponOnuPortAdminChanged NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId, fkGponOnuPortControlAdminStatus, fkGponOnuPortControlOnuSerial }
                        STATUS current
                        DESCRIPTION 
                                "Description."
                        ::= { fkGponOnuPortNotification 1 }

                
--  1.3.6.1.4.1.10428 9 1.101.23.6.1.3.2
                -- 1.3.6.1.4.1.10428 9 1.101.23.6.1.3.2
                fkGponOnuPortAutoNegoChanged NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId, fkGponOnuPortControlOnuSerial, fkGponOnuPortControlAutoNego }
                        STATUS current
                        DESCRIPTION 
                                "setOnuPortAutoNego
                                (This OID is not available)
                                "
                        ::= { fkGponOnuPortNotification 2 }

                
--  1.3.6.1.4.1.10428 9 1.101.23.6.1.3.3
                -- 1.3.6.1.4.1.10428 9 1.101.23.6.1.3.3
                fkGponOnuPortSpeedChanged NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId, fkGponOnuPortControlOnuSerial, fkGponOnuPortControlSpeed }
                        STATUS current
                        DESCRIPTION 
                                "setOnuPortSpeed
                                (This OID is not available)
                                "
                        ::= { fkGponOnuPortNotification 3 }

                
--  1.3.6.1.4.1.10428 9 1.101.23.6.1.3.4
                -- 1.3.6.1.4.1.10428 9 1.101.23.6.1.3.4
                fkGponOnuPortStatisticsCleared NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId }
                        STATUS current
                        DESCRIPTION 
                                "clearOnuPortStats
                                (This OID is not available)"
                        ::= { fkGponOnuPortNotification 4 }

                
                -- 1.3.6.1.4.1.10428 9 1.101.23.6.1.3.5
                fkGponOnuPortUniDescriptionChanged NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId, fkGponOnuPortControlUniDescription }
                        STATUS current
                        DESCRIPTION 
                                "setUniDescription"
                        ::= { fkGponOnuPortNotification 5 }

                
                -- 1.3.6.1.4.1.10428 9 1.101.23.6.1.3.6
                fkGponOnuPortAutoDetectionChanged NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId, fkGponOnuPortControlSpeed, fkGponOnuPortControlDuplex }
                        STATUS current
                        DESCRIPTION 
                                "setAutoDetection."
                        ::= { fkGponOnuPortNotification 6 }

                
                -- 1.3.6.1.4.1.10428 9 1.101.23.6.1.3.7
                fkGponOnuPortMediumModeChanged NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId, fkGponOnuPortControlMediumMode }
                        STATUS current
                        DESCRIPTION 
                                "setOnuPortMediumMode"
                        ::= { fkGponOnuPortNotification 7 }

                
                -- 1.3.6.1.4.1.10428 9 1.101.23.6.1.3.8
                fkGponOnuPortLoopbackStatusChanged NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId, fkGponOnuPortControlLoopbackStatus }
                        STATUS current
                        DESCRIPTION 
                                "setOnuPortLoopbackStatus"
                        ::= { fkGponOnuPortNotification 8 }

                
                -- 1.3.6.1.4.1.10428 9 1.101.23.6.1.3.9
                fkGponOnuPortOpticModuleInfoUpdated NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId }
                        STATUS current
                        DESCRIPTION 
                                "updateOnuPortOpticModuleInfo."
                        ::= { fkGponOnuPortNotification 9 }

                
                -- 1.3.6.1.4.1.10428 9 1.101.23.6.1.3.10
                fkGponOnuPortLinkStatisticsUpdated NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId }
                        STATUS current
                        DESCRIPTION 
                                "updateOnuPortLinkStatisticsInfo"
                        ::= { fkGponOnuPortNotification 10 }

                
--  1.3.6.1.4.1.10428 9 1.101.23.6.1.3.1
                -- 1.3.6.1.4.1.10428 9 1.101.23.6.1.3.11
                fkGponOnuPortMgmtChanged NOTIFICATION-TYPE
                        OBJECTS { fkGponOnuPortControlRequest, fkGponOnuPortControlTimeStamp, fkGponOnuPortControlReqResult, fkGponOnuPortControlOltId, fkGponOnuPortControlOnuId, 
                                fkGponOnuPortControlSlotId, fkGponOnuPortControlPortId }
                        STATUS current
                        DESCRIPTION 
                                "updateOnuPortMgmtData "
                        ::= { fkGponOnuPortNotification 11 }

                
--  1.3.6.1.4.1.10428 9 1.101.23.6.2
                -- 1.3.6.1.4.1.10428 9 1.101.23.6.2
                fkGponOnuUserMac OBJECT IDENTIFIER ::= { fkGponBridge 2 }

                
--  1.3.6.1.4.1.10428 9 1.101.23.6.2.1
                -- 1.3.6.1.4.1.10428 9 1.101.23.6.2.1
                fkGponOnuUserMacTable OBJECT-TYPE
                        SYNTAX SEQUENCE OF FkGponOnuUserMacEntry
                        MAX-ACCESS not-accessible
                        STATUS current
                        DESCRIPTION
                                "fkGponOnuUserMacTable"
                        ::= { fkGponOnuUserMac 1 }

                
--  1.3.6.1.4.1.10428 9 1.101.23.6.2.1.1
                -- 1.3.6.1.4.1.10428 9 1.101.23.6.2.1.1
                fkGponOnuUserMacEntry OBJECT-TYPE
                        SYNTAX FkGponOnuUserMacEntry
                        MAX-ACCESS not-accessible
                        STATUS current
                        DESCRIPTION
                                "key: fkGponOltId, fkGponOnuId, fkGponOnuUserMacVlanId, fkGponOnuUserMacAddress"
                        INDEX { fkGponOltId, fkGponOnuId, fkGponOnuUserMacVlanId, fkGponOnuUserMacAddress }
                        ::= { fkGponOnuUserMacTable 1 }

                
                FkGponOnuUserMacEntry ::=
                        SEQUENCE { 
                                fkGponOnuUserMacAddress
                                        OCTET STRING,
                                fkGponOnuUserMacVlanId
                                        INTEGER,
                                fkGponOnuUserMacPortId
                                        INTEGER,
                                fkGponOnuUserMacOltId
                                        INTEGER,
                                fkGponOnuUserMacOnuId
                                        INTEGER,
                                fkGponOnuUserMacStatus
                                        INTEGER
                         }

--  1.3.6.1.4.1.10428 9 1.101.23.6.2.1.1.1
                -- 1.3.6.1.4.1.10428 9 1.101.23.6.2.1.1.1
                fkGponOnuUserMacAddress OBJECT-TYPE
                        SYNTAX OCTET STRING (SIZE (0..6))
                        MAX-ACCESS read-only
                        STATUS current
                        DESCRIPTION
                                "The user MAC addresses that are leant at the running ONU."
                        ::= { fkGponOnuUserMacEntry 1 }

                
--  1.3.6.1.4.1.10428 9 1.101.23.6.2.1.1.2
                -- 1.3.6.1.4.1.10428 9 1.101.23.6.2.1.1.2
                fkGponOnuUserMacVlanId OBJECT-TYPE
                        SYNTAX INTEGER (1..4094)
                        MAX-ACCESS read-only
                        STATUS current
                        DESCRIPTION
                                "The user VLAN-ID that are leant at the running ONU."
                        ::= { fkGponOnuUserMacEntry 2 }

                
--  1.3.6.1.4.1.10428 9 1.101.23.6.2.1.1.3
                -- 1.3.6.1.4.1.10428 9 1.101.23.6.2.1.1.3
                fkGponOnuUserMacPortId OBJECT-TYPE
                        SYNTAX INTEGER (0..4096)
                        MAX-ACCESS read-only
                        STATUS current
                        DESCRIPTION
                                "The user GEM PORT-ID that are leant at the running ONU."
                        ::= { fkGponOnuUserMacEntry 3 }

                
--    1.3.6.1.4.1.10428 9 1.101.23.6.2.1.1.4
-- 1.3.6.1.4.1.10428 9 1.101.23.6.2.1.1.4
-- 1.3.6.1.4.1.10428 9 1.101.23.6.2.1.1.4
                -- 1.3.6.1.4.1.10428 9 1.101.23.6.2.1.1.4
                fkGponOnuUserMacOltId OBJECT-TYPE
                        SYNTAX INTEGER (1..65535)
                        MAX-ACCESS read-only
                        STATUS current
                        DESCRIPTION
                                "Gpon Olt Index."
                        ::= { fkGponOnuUserMacEntry 4 }

                
--    1.3.6.1.4.1.10428 9 1.101.23.6.2.1.1.5
-- 1.3.6.1.4.1.10428 9 1.101.23.6.2.1.1.5
-- 1.3.6.1.4.1.10428 9 1.101.23.6.2.1.1.5
                -- 1.3.6.1.4.1.10428 9 1.101.23.6.2.1.1.5
                fkGponOnuUserMacOnuId OBJECT-TYPE
                        SYNTAX INTEGER (1..65535)
                        MAX-ACCESS read-only
                        STATUS current
                        DESCRIPTION
                                "Gpon Onu Index."
                        ::= { fkGponOnuUserMacEntry 5 }

                
                -- 1.3.6.1.4.1.10428 9 1.101.23.6.2.1.1.6
                fkGponOnuUserMacStatus OBJECT-TYPE
                        SYNTAX INTEGER
                                {
                                dynamic(0),
                                snoop(1),
                                static(2),
                                unknown(3)
                                }
                        MAX-ACCESS read-only
                        STATUS current
                        DESCRIPTION
                                "The mac learning status."
                        ::= { fkGponOnuUserMacEntry 6 }

                
--  1.3.6.1.4.1.10428 9 1.101.23.6.2.2
                -- 1.3.6.1.4.1.10428 9 1.101.23.6.2.2
                fkGponOnuUserMacControl OBJECT IDENTIFIER ::= { fkGponOnuUserMac 2 }

                
--  1.3.6.1.4.1.10428 9 1.101.23.6.2.2.1
                -- 1.3.6.1.4.1.10428 9 1.101.23.6.2.2.1
                fkGponOnuUserMacControlRequest OBJECT-TYPE
                        SYNTAX INTEGER
                                {
                                clearOltMacOne(1),
                                clearOltMacOnu(2),
                                clearOltMacAll(3),
                                updateOltMac(4)
                                }
                        MAX-ACCESS read-write
                        STATUS current
                        DESCRIPTION
                                "The request of a user command"
                        ::= { fkGponOnuUserMacControl 1 }

                
--  1.3.6.1.4.1.10428 9 1.101.23.6.2.2.2
                -- 1.3.6.1.4.1.10428 9 1.101.23.6.2.2.2
                fkGponOnuUserMacControlStatus OBJECT-TYPE
                        SYNTAX FkControlStatusType
                        MAX-ACCESS read-write
                        STATUS current
                        DESCRIPTION
                                "The status of user command"
                        ::= { fkGponOnuUserMacControl 2 }

                
--  1.3.6.1.4.1.10428 9 1.101.23.6.2.2.3
                -- 1.3.6.1.4.1.10428 9 1.101.23.6.2.2.3
                fkGponOnuUserMacControlTimer OBJECT-TYPE
                        SYNTAX Gauge32
                        MAX-ACCESS read-write
                        STATUS current
                        DESCRIPTION
                                "The maximum time for the manager for a long running user command"
                        ::= { fkGponOnuUserMacControl 3 }

                
--  1.3.6.1.4.1.10428 9 1.101.23.6.2.2.4
                -- 1.3.6.1.4.1.10428 9 1.101.23.6.2.2.4
                fkGponOnuUserMacControlTimeStamp OBJECT-TYPE
                        SYNTAX Integer32
                        MAX-ACCESS read-write
                        STATUS current
                        DESCRIPTION
                                "The time stamp of the last command(end of command)"
                        ::= { fkGponOnuUserMacControl 4 }

                
--  1.3.6.1.4.1.10428 9 1.101.23.6.2.2.5
                -- 1.3.6.1.4.1.10428 9 1.101.23.6.2.2.5
                fkGponOnuUserMacControlReqResult OBJECT-TYPE
                        SYNTAX FkControlRequestResultType
                        MAX-ACCESS read-write
                        STATUS current
                        DESCRIPTION
                                "The result of the last user command"
                        ::= { fkGponOnuUserMacControl 5 }

                
--  1.3.6.1.4.1.10428 9 1.101.23.6.2.2.6
                -- 1.3.6.1.4.1.10428 9 1.101.23.6.2.2.6
                fkGponOnuUserMacControlOltId OBJECT-TYPE
                        SYNTAX INTEGER (1..65535)
                        MAX-ACCESS read-write
                        STATUS current
                        DESCRIPTION
                                "Gpon Olt Index"
                        ::= { fkGponOnuUserMacControl 6 }

                
--  1.3.6.1.4.1.10428 9 1.101.23.6.2.2.7
                -- 1.3.6.1.4.1.10428 9 1.101.23.6.2.2.7
                fkGponOnuUserMacControlOnuId OBJECT-TYPE
                        SYNTAX INTEGER (1..65535)
                        MAX-ACCESS read-write
                        STATUS current
                        DESCRIPTION
                                "Gpon Onu Index"
                        ::= { fkGponOnuUserMacControl 7 }

                
--  1.3.6.1.4.1.10428 9 1.101.23.6.2.2.8
                -- 1.3.6.1.4.1.10428 9 1.101.23.6.2.2.8
                fkGponOnuUserMacControlAddress OBJECT-TYPE
                        SYNTAX OCTET STRING
                        MAX-ACCESS read-write
                        STATUS current
                        DESCRIPTION
                                "The user MAC addresses that are leant at the running ONU."
                        ::= { fkGponOnuUserMacControl 8 }

                
--  1.3.6.1.4.1.10428 9 1.101.23.6.2.2.9
                -- 1.3.6.1.4.1.10428 9 1.101.23.6.2.2.9
                fkGponOnuUserMacControlVlanId OBJECT-TYPE
                        SYNTAX INTEGER (1..65535)
                        MAX-ACCESS read-write
                        STATUS current
                        DESCRIPTION
                                "GPON ONU Vlan Index"
                        ::= { fkGponOnuUserMacControl 9 }

                
--  1.3.6.1.4.1.10428 9 1.101.23.6.2.3
                -- 1.3.6.1.4.1.10428 9 1.101.23.6.2.3
                fkGponOnuUserMacNotification OBJECT IDENTIFIER ::= { fkGponOnuUserMac 3 }

                
--  1.3.6.1.4.1.10428 9 1.101.23.6.2.3.1
                -- 1.3.6.1.4.1.10428 9 1.101.23.6.2.3.1
                fkGponOnuUserMacOltMacChanged NOTIFICATION-TYPE
                        OBJECTS { fkGponOnuUserMacControlRequest, fkGponOnuUserMacControlTimeStamp, fkGponOnuUserMacControlReqResult, fkGponOnuUserMacControlOltId, fkGponOnuUserMacControlOnuId, 
                                fkGponOnuUserMacControlAddress, fkGponOnuUserMacControlVlanId }
                        STATUS current
                        DESCRIPTION 
                                "clearOltMacOne"
                        ::= { fkGponOnuUserMacNotification 1 }

                
--  1.3.6.1.4.1.10428 9 1.101.23.6.2.3.2
                -- 1.3.6.1.4.1.10428 9 1.101.23.6.2.3.2
                fkGponOnuUserMacOltMacOnuChanged NOTIFICATION-TYPE
                        OBJECTS { fkGponOnuUserMacControlRequest, fkGponOnuUserMacControlTimeStamp, fkGponOnuUserMacControlReqResult, fkGponOnuUserMacControlOltId, fkGponOnuUserMacControlOnuId
                                 }
                        STATUS current
                        DESCRIPTION 
                                "clearOltMacOnu"
                        ::= { fkGponOnuUserMacNotification 2 }

                
--  1.3.6.1.4.1.10428 9 1.101.23.6.2.3.3
                -- 1.3.6.1.4.1.10428 9 1.101.23.6.2.3.3
                fkGponOnuUserMacOltMacAllChanged NOTIFICATION-TYPE
                        OBJECTS { fkGponOnuUserMacControlRequest, fkGponOnuUserMacControlTimeStamp, fkGponOnuUserMacControlReqResult, fkGponOnuUserMacControlOltId }
                        STATUS current
                        DESCRIPTION 
                                "clearOltMacAll"
                        ::= { fkGponOnuUserMacNotification 3 }

                
--  1.3.6.1.4.1.10428 9 1.101.23.6.2.3.4
                -- 1.3.6.1.4.1.10428 9 1.101.23.6.2.3.4
                fkGponOnuUserMacOltMacUpdated NOTIFICATION-TYPE
                        OBJECTS { fkGponOnuUserMacControlRequest, fkGponOnuUserMacControlTimeStamp, fkGponOnuUserMacControlReqResult, fkGponOnuUserMacControlOltId, fkGponOnuUserMacControlOnuId
                                 }
                        STATUS current
                        DESCRIPTION 
                                "updateOltMac"
                        ::= { fkGponOnuUserMacNotification 4 }

                
--  1.3.6.1.4.1.10428 9 1.101.23.6.3
                -- 1.3.6.1.4.1.10428 9 1.101.23.6.3
                fkGponBridgeVoIP OBJECT IDENTIFIER ::= { fkGponBridge 3 }

                
--  1.3.6.1.4.1.10428 9 1.101.23.6.3.1
                -- 1.3.6.1.4.1.10428 9 1.101.23.6.3.1
                fkGponBridgeVoIPInfoTable OBJECT-TYPE
                        SYNTAX SEQUENCE OF FkGponBridgeVoIPInfoEntry
                        MAX-ACCESS not-accessible
                        STATUS current
                        DESCRIPTION
                                "fkGponBridgeVoIPInfoTable"
                        ::= { fkGponBridgeVoIP 1 }

                
--  1.3.6.1.4.1.10428 9 1.101.23.6.3.1.1
                -- 1.3.6.1.4.1.10428 9 1.101.23.6.3.1.1
                fkGponBridgeVoIPInfoEntry OBJECT-TYPE
                        SYNTAX FkGponBridgeVoIPInfoEntry
                        MAX-ACCESS not-accessible
                        STATUS current
                        DESCRIPTION
                                "key: fkGponBridgeVoIPInfoOltId, fkGponBridgeVoIPInfoOnuId"
                        INDEX { fkGponBridgeVoIPInfoOltId, fkGponBridgeVoIPInfoOnuId }
                        ::= { fkGponBridgeVoIPInfoTable 1 }

                
                FkGponBridgeVoIPInfoEntry ::=
                        SEQUENCE { 
                                fkGponBridgeVoIPInfoOltId
                                        Integer32,
                                fkGponBridgeVoIPInfoOnuId
                                        Integer32,
                                fkGponBridgeVoIPInfoDHCP
                                        INTEGER,
                                fkGponBridgeVoIPInfoIpAddress
                                        IpAddress,
                                fkGponBridgeVoIPInfoMethods
                                        BITS,
                                fkGponBridgeVoIPInfoCurrMethods
                                        INTEGER,
                                fkGponBridgeVoIPInfoProtocols
                                        BITS,
                                fkGponBridgeVoIPInfoCurrProtocols
                                        INTEGER
                         }

--  1.3.6.1.4.1.10428 9 1.101.23.6.3.1.1.1
                -- 1.3.6.1.4.1.10428 9 1.101.23.6.3.1.1.1
                fkGponBridgeVoIPInfoOltId OBJECT-TYPE
                        SYNTAX Integer32 (1..65535)
                        MAX-ACCESS read-only
                        STATUS current
                        DESCRIPTION
                                "Olt Index."
                        ::= { fkGponBridgeVoIPInfoEntry 1 }

                
--  1.3.6.1.4.1.10428 9 1.101.23.6.3.1.1.2
                -- 1.3.6.1.4.1.10428 9 1.101.23.6.3.1.1.2
                fkGponBridgeVoIPInfoOnuId OBJECT-TYPE
                        SYNTAX Integer32 (1..65535)
                        MAX-ACCESS read-only
                        STATUS current
                        DESCRIPTION
                                "Onu Index."
                        ::= { fkGponBridgeVoIPInfoEntry 2 }

                
--  1.3.6.1.4.1.10428 9 1.101.23.6.3.1.1.3
                -- 1.3.6.1.4.1.10428 9 1.101.23.6.3.1.1.3
                fkGponBridgeVoIPInfoDHCP OBJECT-TYPE
                        SYNTAX INTEGER
                                {
                                auto(1),
                                manual(2)
                                }
                        MAX-ACCESS read-only
                        STATUS current
                        DESCRIPTION
                                "Indicate whether using DHCP or not."
                        ::= { fkGponBridgeVoIPInfoEntry 3 }

                
--  1.3.6.1.4.1.10428 9 1.101.23.6.3.1.1.4
                -- 1.3.6.1.4.1.10428 9 1.101.23.6.3.1.1.4
                fkGponBridgeVoIPInfoIpAddress OBJECT-TYPE
                        SYNTAX IpAddress
                        MAX-ACCESS read-only
                        STATUS current
                        DESCRIPTION
                                "IP Address."
                        ::= { fkGponBridgeVoIPInfoEntry 4 }

                
--  1.3.6.1.4.1.10428 9 1.101.23.6.3.1.1.5
                -- 1.3.6.1.4.1.10428 9 1.101.23.6.3.1.1.5
                fkGponBridgeVoIPInfoMethods OBJECT-TYPE
                        SYNTAX BITS
                                {
                                omci(0),
                                file(1),
                                tr69(2),
                                ietf(3)
                                }
                        MAX-ACCESS read-only
                        STATUS current
                        DESCRIPTION
                                "Supporting Methods."
                        ::= { fkGponBridgeVoIPInfoEntry 5 }

                
--   
-- 1.3.6.1.4.1.10428 9 1.101.23.6.3.1.1.6
                -- 1.3.6.1.4.1.10428 9 1.101.23.6.3.1.1.6
                fkGponBridgeVoIPInfoCurrMethods OBJECT-TYPE
                        SYNTAX INTEGER
                                {
                                omci(1),
                                file(2),
                                tr69(3),
                                ietf(4),
                                unknown(255)
                                }
                        MAX-ACCESS read-only
                        STATUS current
                        DESCRIPTION
                                "Current using method."
                        ::= { fkGponBridgeVoIPInfoEntry 6 }

                
--  1.3.6.1.4.1.10428 9 1.101.23.6.3.1.1.7
                -- 1.3.6.1.4.1.10428 9 1.101.23.6.3.1.1.7
                fkGponBridgeVoIPInfoProtocols OBJECT-TYPE
                        SYNTAX BITS
                                {
                                sip(0),
                                h248(1),
                                mgcp(2)
                                }
                        MAX-ACCESS read-only
                        STATUS current
                        DESCRIPTION
                                "Supporting Protocols."
                        ::= { fkGponBridgeVoIPInfoEntry 7 }

                
--  1.3.6.1.4.1.10428 9 1.101.23.6.3.1.1.8
                -- 1.3.6.1.4.1.10428 9 1.101.23.6.3.1.1.8
                fkGponBridgeVoIPInfoCurrProtocols OBJECT-TYPE
                        SYNTAX INTEGER
                                {
                                sip(1),
                                h248(2),
                                mgcp(3),
                                unknown(255)
                                }
                        MAX-ACCESS read-only
                        STATUS current
                        DESCRIPTION
                                "Current using protocol."
                        ::= { fkGponBridgeVoIPInfoEntry 8 }

                
--  1.3.6.1.4.1.10428 9 1.101.23.6.3.2
                -- 1.3.6.1.4.1.10428 9 1.101.23.6.3.2
                fkGponBridgeVoIPLineTable OBJECT-TYPE
                        SYNTAX SEQUENCE OF FkGponBridgeVoIPLineEntry
                        MAX-ACCESS not-accessible
                        STATUS current
                        DESCRIPTION
                                "fkGponBridgeVoIPLineTable"
                        ::= { fkGponBridgeVoIP 2 }

                
--  1.3.6.1.4.1.10428 9 1.101.23.6.3.2.1
                -- 1.3.6.1.4.1.10428 9 1.101.23.6.3.2.1
                fkGponBridgeVoIPLineEntry OBJECT-TYPE
                        SYNTAX FkGponBridgeVoIPLineEntry
                        MAX-ACCESS not-accessible
                        STATUS current
                        DESCRIPTION
                                "fkGponBridgeVoIPLineOltId, fkGponBridgeVoIPLineOnuId, fkGponBridgeVoIPLinePots"
                        INDEX { fkGponBridgeVoIPLineOltId, fkGponBridgeVoIPLineOnuId, fkGponBridgeVoIPLinePots }
                        ::= { fkGponBridgeVoIPLineTable 1 }

                
                FkGponBridgeVoIPLineEntry ::=
                        SEQUENCE { 
                                fkGponBridgeVoIPLineOltId
                                        Integer32,
                                fkGponBridgeVoIPLineOnuId
                                        Integer32,
                                fkGponBridgeVoIPLinePots
                                        Integer32,
                                fkGponBridgeVoIPLineAdminStatus
                                        INTEGER,
                                fkGponBridgeVoIPLineOperStatus
                                        INTEGER,
                                fkGponBridgeVoIPLineStatus
                                        INTEGER
                         }

--  1.3.6.1.4.1.10428 9 1.101.23.6.3.2.1.1
                -- 1.3.6.1.4.1.10428 9 1.101.23.6.3.2.1.1
                fkGponBridgeVoIPLineOltId OBJECT-TYPE
                        SYNTAX Integer32 (1..65535)
                        MAX-ACCESS read-only
                        STATUS current
                        DESCRIPTION
                                "Olt Index."
                        ::= { fkGponBridgeVoIPLineEntry 1 }

                
--  1.3.6.1.4.1.10428 9 1.101.23.6.3.2.1.2
                -- 1.3.6.1.4.1.10428 9 1.101.23.6.3.2.1.2
                fkGponBridgeVoIPLineOnuId OBJECT-TYPE
                        SYNTAX Integer32 (1..65535)
                        MAX-ACCESS read-only
                        STATUS current
                        DESCRIPTION
                                "Onu Index."
                        ::= { fkGponBridgeVoIPLineEntry 2 }

                
--  1.3.6.1.4.1.10428 9 1.101.23.6.3.2.1.3
                -- 1.3.6.1.4.1.10428 9 1.101.23.6.3.2.1.3
                fkGponBridgeVoIPLinePots OBJECT-TYPE
                        SYNTAX Integer32 (1..65535)
                        MAX-ACCESS read-only
                        STATUS current
                        DESCRIPTION
                                "The Outer Vlan-ID to tag for incoming packet with vlan index."
                        ::= { fkGponBridgeVoIPLineEntry 3 }

                
--  1.3.6.1.4.1.10428 9 1.101.23.6.3.2.1.4
                -- 1.3.6.1.4.1.10428 9 1.101.23.6.3.2.1.4
                fkGponBridgeVoIPLineAdminStatus OBJECT-TYPE
                        SYNTAX INTEGER
                                {
                                up(1),
                                down(2)
                                }
                        MAX-ACCESS read-only
                        STATUS current
                        DESCRIPTION
                                "Admin status."
                        ::= { fkGponBridgeVoIPLineEntry 4 }

                
--  1.3.6.1.4.1.10428 9 1.101.23.6.3.2.1.5
                -- 1.3.6.1.4.1.10428 9 1.101.23.6.3.2.1.5
                fkGponBridgeVoIPLineOperStatus OBJECT-TYPE
                        SYNTAX INTEGER
                                {
                                up(1),
                                down(2)
                                }
                        MAX-ACCESS read-only
                        STATUS current
                        DESCRIPTION
                                "Oper status."
                        ::= { fkGponBridgeVoIPLineEntry 5 }

                
--  1.3.6.1.4.1.10428 9 1.101.23.6.3.2.1.6
                -- 1.3.6.1.4.1.10428 9 1.101.23.6.3.2.1.6
                fkGponBridgeVoIPLineStatus OBJECT-TYPE
                        SYNTAX INTEGER
                                {
                                noneInitial(1),
                                registered(2),
                                inSession(3),
                                failedRegistrationIcmpError(4),
                                failedRegistrationFailedTcp(5),
                                failedRegistrationFailedAuthentication(6),
                                failedRegistrationTimeout(7),
                                failedRegistrationServerFailCode(8),
                                failedInviteIcmpError(9),
                                failedInviteFailedTcp(10),
                                failedInviteFailedAuthentication(11),
                                failedInviteTimeout(12),
                                failedInviteServerFailCode(13),
                                portNotConfigured(14),
                                configDone(15)
                                }
                        MAX-ACCESS read-only
                        STATUS current
                        DESCRIPTION
                                "Line Status"
                        ::= { fkGponBridgeVoIPLineEntry 6 }

                
--  1.3.6.1.4.1.10428 9 1.101.23.6.4
                -- 1.3.6.1.4.1.10428 9 1.101.23.6.4
                fkGponBridgeSlot OBJECT IDENTIFIER ::= { fkGponBridge 4 }

                
--  1.3.6.1.4.1.10428 9 1.101.23.6.4.1
                -- 1.3.6.1.4.1.10428 9 1.101.23.6.4.1
                fkGponBridgeSlotStatusTable OBJECT-TYPE
                        SYNTAX SEQUENCE OF FkGponBridgeSlotStatusEntry
                        MAX-ACCESS not-accessible
                        STATUS current
                        DESCRIPTION
                                "fkGponBridgeSlotStatusTable"
                        ::= { fkGponBridgeSlot 1 }

                
--  1.3.6.1.4.1.10428 9 1.101.23.6.4.1.1
                -- 1.3.6.1.4.1.10428 9 1.101.23.6.4.1.1
                fkGponBridgeSlotStatusEntry OBJECT-TYPE
                        SYNTAX FkGponBridgeSlotStatusEntry
                        MAX-ACCESS not-accessible
                        STATUS current
                        DESCRIPTION
                                "key: fkGponBridgeSlotIndex"
                        INDEX { fkGponBridgeSlotIndex }
                        ::= { fkGponBridgeSlotStatusTable 1 }

                
                FkGponBridgeSlotStatusEntry ::=
                        SEQUENCE { 
                                fkGponBridgeSlotIndex
                                        Integer32,
                                fkGponBridgeSlotConnectionStatus
                                        INTEGER,
                                fkGponBridgeSlotFlags
                                        INTEGER
                         }

--  1.3.6.1.4.1.10428 9 1.101.23.6.4.1.1.1
                -- 1.3.6.1.4.1.10428 9 1.101.23.6.4.1.1.1
                fkGponBridgeSlotIndex OBJECT-TYPE
                        SYNTAX Integer32 (1..65535)
                        MAX-ACCESS read-only
                        STATUS current
                        DESCRIPTION
                                "Gpon slot index."
                        ::= { fkGponBridgeSlotStatusEntry 1 }

                
--  1.3.6.1.4.1.10428 9 1.101.23.6.4.1.1.2
                -- 1.3.6.1.4.1.10428 9 1.101.23.6.4.1.1.2
                fkGponBridgeSlotConnectionStatus OBJECT-TYPE
                        SYNTAX INTEGER
                                {
                                nonCreate(1),
                                disconnect(2),
                                waiting(3),
                                connect(4),
                                monitoring(5),
                                unknown(255)
                                }
                        MAX-ACCESS read-only
                        STATUS current
                        DESCRIPTION
                                "Gpon slot connection status."
                        ::= { fkGponBridgeSlotStatusEntry 2 }

                
--  1.3.6.1.4.1.10428 9 1.101.23.6.4.1.1.3
                -- 1.3.6.1.4.1.10428 9 1.101.23.6.4.1.1.3
                fkGponBridgeSlotFlags OBJECT-TYPE
                        SYNTAX INTEGER
                                {
                                true(1),
                                false(2)
                                }
                        MAX-ACCESS read-only
                        STATUS current
                        DESCRIPTION
                                "Flags."
                        ::= { fkGponBridgeSlotStatusEntry 3 }

                
                -- 1.3.6.1.4.1.10428 9 1.101.23.6.5
                fkGponOnuVoipLine OBJECT IDENTIFIER ::= { fkGponBridge 5 }

                
                -- 1.3.6.1.4.1.10428 9 1.101.23.6.5.1
                fkGponOnuVoipLineTable OBJECT-TYPE
                        SYNTAX SEQUENCE OF FkGponOnuVoipLineEntry
                        MAX-ACCESS not-accessible
                        STATUS current
                        DESCRIPTION
                                "fkGponOnuVoipLineTable"
                        ::= { fkGponOnuVoipLine 1 }

                
                -- 1.3.6.1.4.1.10428 9 1.101.23.6.5.1.1
                fkGponOnuVoipLineEntry OBJECT-TYPE
                        SYNTAX FkGponOnuVoipLineEntry
                        MAX-ACCESS not-accessible
                        STATUS current
                        DESCRIPTION
                                "key: fkGponOnuVoipLineOltId, fkGponOnuVoipLineOnuId, fkGponOnuVoipLineId"
                        INDEX { fkGponOnuVoipLineOltId, fkGponOnuVoipLineOnuId, fkGponOnuVoipLineId }
                        ::= { fkGponOnuVoipLineTable 1 }

                
                FkGponOnuVoipLineEntry ::=
                        SEQUENCE { 
                                fkGponOnuVoipLineOltId
                                        Integer32,
                                fkGponOnuVoipLineOnuId
                                        Integer32,
                                fkGponOnuVoipLineId
                                        Integer32,
                                fkGponOnuVoipLineStatus
                                        INTEGER,
                                fkGponOnuVoipLineUsedCodec
                                        INTEGER,
                                fkGponOnuVoipLineSessionType
                                        INTEGER,
                                fkGponOnuVoipLine1stProtocolPeriod
                                        INTEGER,
                                fkGponOnuVoipLine1stDestAddr
                                        OCTET STRING,
                                fkGponOnuVoipLine2ndProtocolPeriod
                                        INTEGER,
                                fkGponOnuVoipLine2ndDestAddr
                                        OCTET STRING
                         }

                -- 1.3.6.1.4.1.10428 9 1.101.23.6.5.1.1.1
                fkGponOnuVoipLineOltId OBJECT-TYPE
                        SYNTAX Integer32 (1..65535)
                        MAX-ACCESS read-only
                        STATUS current
                        DESCRIPTION
                                "Olt Index."
                        ::= { fkGponOnuVoipLineEntry 1 }

                
                -- 1.3.6.1.4.1.10428 9 1.101.23.6.5.1.1.2
                fkGponOnuVoipLineOnuId OBJECT-TYPE
                        SYNTAX Integer32 (1..65535)
                        MAX-ACCESS read-only
                        STATUS current
                        DESCRIPTION
                                "Onu Index."
                        ::= { fkGponOnuVoipLineEntry 2 }

                
                -- 1.3.6.1.4.1.10428 9 1.101.23.6.5.1.1.3
                fkGponOnuVoipLineId OBJECT-TYPE
                        SYNTAX Integer32 (1..65535)
                        MAX-ACCESS read-only
                        STATUS current
                        DESCRIPTION
                                "The Outer Vlan-ID to tag for incoming packet with vlan index."
                        ::= { fkGponOnuVoipLineEntry 3 }

                
                -- 1.3.6.1.4.1.10428 9 1.101.23.6.5.1.1.4
                fkGponOnuVoipLineStatus OBJECT-TYPE
                        SYNTAX INTEGER
                                {
                                noneInitial(1),
                                registered(2),
                                inSession(3),
                                failedRegistrationIcmpError(4),
                                failedRegistrationFailedTcp(5),
                                failedRegistrationFailedAuthentication(6),
                                failedRegistrationTimeout(7),
                                failedRegistrationServerFailCode(8),
                                failedInviteIcmpError(9),
                                failedInviteFailedTcp(10),
                                failedInviteFailedAuthentication(11),
                                failedInviteTimeout(12),
                                failedInviteServerFailCode(13),
                                portNotConfigured(14),
                                configDone(15)
                                }
                        MAX-ACCESS read-only
                        STATUS current
                        DESCRIPTION
                                "The line status"
                        ::= { fkGponOnuVoipLineEntry 4 }

                
                -- 1.3.6.1.4.1.10428 9 1.101.23.6.5.1.1.5
                fkGponOnuVoipLineUsedCodec OBJECT-TYPE
                        SYNTAX INTEGER
                                {
                                autoSelect(0),
                                gDot711ALaw(1),
                                gDot711MuLaw(2),
                                gDot723(3),
                                gDot722Dot1(4),
                                gDot722Dot2(5),
                                gDot723Dot1(6),
                                gDot726(7),
                                gDot728(8),
                                gDot729A(9),
                                gDot729B(10),
                                gDot729D(11),
                                gDot729E(12),
                                melp(13),
                                unknown(255)
                                }
                        MAX-ACCESS read-only
                        STATUS current
                        DESCRIPTION
                                "The used codec configuration"
                        ::= { fkGponOnuVoipLineEntry 5 }

                
                -- 1.3.6.1.4.1.10428 9 1.101.23.6.5.1.1.6
                fkGponOnuVoipLineSessionType OBJECT-TYPE
                        SYNTAX INTEGER
                                {
                                idle(0),
                                twoWay(1),
                                threeWay(2),
                                fax(3),
                                telem(4),
                                conference(5),
                                unknown(255)
                                }
                        MAX-ACCESS read-only
                        STATUS current
                        DESCRIPTION
                                "The session type"
                        ::= { fkGponOnuVoipLineEntry 6 }

                
                -- 1.3.6.1.4.1.10428 9 1.101.23.6.5.1.1.7
                fkGponOnuVoipLine1stProtocolPeriod OBJECT-TYPE
                        SYNTAX INTEGER (1..65535)
                        MAX-ACCESS read-only
                        STATUS current
                        DESCRIPTION
                                "1st protocol period"
                        ::= { fkGponOnuVoipLineEntry 7 }

                
                -- 1.3.6.1.4.1.10428 9 1.101.23.6.5.1.1.8
                fkGponOnuVoipLine1stDestAddr OBJECT-TYPE
                        SYNTAX OCTET STRING
                        MAX-ACCESS read-only
                        STATUS current
                        DESCRIPTION
                                "1st destination address"
                        ::= { fkGponOnuVoipLineEntry 8 }

                
                -- 1.3.6.1.4.1.10428 9 1.101.23.6.5.1.1.9
                fkGponOnuVoipLine2ndProtocolPeriod OBJECT-TYPE
                        SYNTAX INTEGER (1..65535)
                        MAX-ACCESS read-only
                        STATUS current
                        DESCRIPTION
                                "2nd protocol period"
                        ::= { fkGponOnuVoipLineEntry 9 }

                
                -- 1.3.6.1.4.1.10428 9 1.101.23.6.5.1.1.10
                fkGponOnuVoipLine2ndDestAddr OBJECT-TYPE
                        SYNTAX OCTET STRING
                        MAX-ACCESS read-only
                        STATUS current
                        DESCRIPTION
                                "2nd destination address"
                        ::= { fkGponOnuVoipLineEntry 10 }

                
                -- 1.3.6.1.4.1.10428 9 1.101.23.6.5.2
                fkGponOnuVoipLineControl OBJECT IDENTIFIER ::= { fkGponOnuVoipLine 2 }

                
                -- 1.3.6.1.4.1.10428 9 1.101.23.6.5.2.1
                fkGponOnuVoipLineControlRequest OBJECT-TYPE
                        SYNTAX INTEGER { updateVoipInfo(1) }
                        MAX-ACCESS read-write
                        STATUS current
                        DESCRIPTION
                                "The request of a user command"
                        ::= { fkGponOnuVoipLineControl 1 }

                
                -- 1.3.6.1.4.1.10428 9 1.101.23.6.5.2.2
                fkGponOnuVoipLineControlStatus OBJECT-TYPE
                        SYNTAX FkControlStatusType
                        MAX-ACCESS read-write
                        STATUS current
                        DESCRIPTION
                                "The status of user command"
                        ::= { fkGponOnuVoipLineControl 2 }

                
                -- 1.3.6.1.4.1.10428 9 1.101.23.6.5.2.3
                fkGponOnuVoipLineControlTimer OBJECT-TYPE
                        SYNTAX Gauge32
                        MAX-ACCESS read-write
                        STATUS current
                        DESCRIPTION
                                "The maximum time for the manager for a long running user command"
                        ::= { fkGponOnuVoipLineControl 3 }

                
                -- 1.3.6.1.4.1.10428 9 1.101.23.6.5.2.4
                fkGponOnuVoipLineControlTimeStamp OBJECT-TYPE
                        SYNTAX TimeTicks
                        MAX-ACCESS read-write
                        STATUS current
                        DESCRIPTION
                                "The time stamp of the last command(end of command)"
                        ::= { fkGponOnuVoipLineControl 4 }

                
                -- 1.3.6.1.4.1.10428 9 1.101.23.6.5.2.5
                fkGponOnuVoipLineControlReqResult OBJECT-TYPE
                        SYNTAX FkControlRequestResultType
                        MAX-ACCESS read-write
                        STATUS current
                        DESCRIPTION
                                "The result of the last user command"
                        ::= { fkGponOnuVoipLineControl 5 }

                
                -- 1.3.6.1.4.1.10428 9 1.101.23.6.5.2.6
                fkGponOnuVoipLineControlOltId OBJECT-TYPE
                        SYNTAX Integer32 (1..65535)
                        MAX-ACCESS read-write
                        STATUS current
                        DESCRIPTION
                                "Olt Index."
                        ::= { fkGponOnuVoipLineControl 6 }

                
                -- 1.3.6.1.4.1.10428 9 1.101.23.6.5.2.7
                fkGponOnuVoipLineControlOnuId OBJECT-TYPE
                        SYNTAX Integer32 (1..65535)
                        MAX-ACCESS read-write
                        STATUS current
                        DESCRIPTION
                                "Onu Index."
                        ::= { fkGponOnuVoipLineControl 7 }

                
                -- 1.3.6.1.4.1.10428 9 1.101.23.6.5.3
                fkGponOnuVoipLineNotification OBJECT IDENTIFIER ::= { fkGponOnuVoipLine 3 }

                
                -- 1.3.6.1.4.1.10428 9 1.101.23.6.5.3.1
                fkGponOnuVoipLineVoipInfoChanged NOTIFICATION-TYPE
                        OBJECTS { fkGponOnuVoipLineControlRequest, fkGponOnuVoipLineControlTimeStamp, fkGponOnuVoipLineControlReqResult, fkGponOnuVoipLineControlOltId, fkGponOnuVoipLineControlOnuId
                                 }
                        STATUS current
                        DESCRIPTION 
                                "Description."
                        ::= { fkGponOnuVoipLineNotification 1 }

                
                -- 1.3.6.1.4.1.10428 9 1.101.23.6.6
                fkGponOnuAni OBJECT IDENTIFIER ::= { fkGponBridge 6 }

                
--  1.3.6.1.4.1.10428 9 1.101.23.6.1.1
                -- 1.3.6.1.4.1.10428 9 1.101.23.6.6.1
                fkGponOnuAniTable OBJECT-TYPE
                        SYNTAX SEQUENCE OF FkGponOnuAniEntry
                        MAX-ACCESS not-accessible
                        STATUS current
                        DESCRIPTION
                                "fkGponOnuPortTable"
                        ::= { fkGponOnuAni 1 }

                
--  1.3.6.1.4.1.10428 9 1.101.23.6.1.1.1
                -- 1.3.6.1.4.1.10428 9 1.101.23.6.6.1.1
                fkGponOnuAniEntry OBJECT-TYPE
                        SYNTAX FkGponOnuAniEntry
                        MAX-ACCESS not-accessible
                        STATUS current
                        DESCRIPTION
                                "key: fkGponOltId, fkGponOnuId, fkGponOnuPortSlotId, fkGponOnuPortId"
                        INDEX { fkGponOltId, fkGponOnuId, fkGponOnuAniId }
                        ::= { fkGponOnuAniTable 1 }

                
                FkGponOnuAniEntry ::=
                        SEQUENCE { 
                                fkGponOnuAniId
                                        Integer32,
                                fkGponOnuAniType
                                        INTEGER,
                                fkGponOnuAniOpticModuleInstall
                                        INTEGER,
                                fkGponOnuAniOpticModuleTransceiverType
                                        INTEGER,
                                fkGponOnuAniOpticModuleTransceiverDetailType
                                        INTEGER,
                                fkGponOnuAniOpticModuleLengthMode
                                        INTEGER,
                                fkGponOnuAniOpticModuleLength
                                        INTEGER,
                                fkGponOnuAniOpticModuleSpeed
                                        INTEGER,
                                fkGponOnuAniOpticModuleWavelength
                                        INTEGER,
                                fkGponOnuAniOpticModuleConnecterType
                                        INTEGER,
                                fkGponOnuAniOpticModuleVendorName
                                        OCTET STRING,
                                fkGponOnuAniOpticModuleVendorPartName
                                        OCTET STRING,
                                fkGponOnuAniOpticModuleVendorRevision
                                        OCTET STRING,
                                fkGponOnuAniOpticModuleVendorSerialNumber
                                        OCTET STRING,
                                fkGponOnuAniOpticModuleProductDate
                                        OCTET STRING,
                                fkGponOnuAniOpticModuleTemper
                                        OCTET STRING,
                                fkGponOnuAniOpticModuleVoltage
                                        OCTET STRING,
                                fkGponOnuAniOpticModuleTxbias
                                        OCTET STRING,
                                fkGponOnuAniOpticModuleTxPower
                                        OCTET STRING,
                                fkGponOnuAniOpticModuleRxPower
                                        OCTET STRING,
                                fkGponOnuAniOpticModuleTemperHighThr
                                        Integer32,
                                fkGponOnuAniOpticModuleTemperLowThr
                                        Integer32,
                                fkGponOnuAniOpticModuleVoltageHighThr
                                        Integer32,
                                fkGponOnuAniOpticModuleVoltageLowThr
                                        Integer32,
                                fkGponOnuAniOpticModuleTxbiasHighThr
                                        Integer32,
                                fkGponOnuAniOpticModuleTxbiasLowThr
                                        Integer32,
                                fkGponOnuAniOpticModuleTxPowerHighThr
                                        Integer32,
                                fkGponOnuAniOpticModuleTxPowerLowThr
                                        Integer32,
                                fkGponOnuAniOpticModuleRxPowerHighThr
                                        Integer32,
                                fkGponOnuAniOpticModuleRxPowerLowThr
                                        Integer32
                         }

                -- 1.3.6.1.4.1.10428 9 1.101.23.6.6.1.1.1
                fkGponOnuAniId OBJECT-TYPE
                        SYNTAX Integer32 (1..65535)
                        MAX-ACCESS read-only
                        STATUS current
                        DESCRIPTION
                                "The ani index."
                        ::= { fkGponOnuAniEntry 1 }

                
                -- 1.3.6.1.4.1.10428 9 1.101.23.6.6.1.1.2
                fkGponOnuAniType OBJECT-TYPE
                        SYNTAX INTEGER
                                {
                                gpon(1),
                                video(2)
                                }
                        MAX-ACCESS read-only
                        STATUS current
                        DESCRIPTION
                                "The ONU ANI type."
                        ::= { fkGponOnuAniEntry 2 }

                
                -- 1.3.6.1.4.1.10428 9 1.101.23.6.6.1.1.3
                fkGponOnuAniOpticModuleInstall OBJECT-TYPE
                        SYNTAX INTEGER
                                {
                                uninstall(0),
                                install(1)
                                }
                        MAX-ACCESS read-only
                        STATUS current
                        DESCRIPTION
                                "The module instatll status."
                        ::= { fkGponOnuAniEntry 3 }

                
                -- 1.3.6.1.4.1.10428 9 1.101.23.6.6.1.1.4
                fkGponOnuAniOpticModuleTransceiverType OBJECT-TYPE
                        SYNTAX INTEGER
                                {
                                gbic(1),
                                solderedToMotherboard(2),
                                sfp(3),
                                xbi300Pin(4),
                                xenpak(5),
                                xfp(6),
                                xff(7),
                                xfpE(8),
                                spak(9),
                                x2(10),
                                unknown(255)
                                }
                        MAX-ACCESS read-only
                        STATUS current
                        DESCRIPTION
                                "The module transceiver type.
                                1: GBIC
                                2 :Soldered to motherboard
                                3: SFP
                                4 :300 pin XBI
                                5: XENPAK
                                6: XFP
                                7: XFF
                                8: XFP-E
                                9 :XPAK
                                10: X2
                                255:Unknown"
                        ::= { fkGponOnuAniEntry 4 }

                
                -- 1.3.6.1.4.1.10428 9 1.101.23.6.6.1.1.5
                fkGponOnuAniOpticModuleTransceiverDetailType OBJECT-TYPE
                        SYNTAX INTEGER
                                {
                                base1000SX(1),
                                base1000LX(2),
                                base1000CX(3),
                                base1000T(4),
                                base1000LXorLX10(5),
                                base1000FX(6),
                                base1000BX10(7),
                                base1000PX(8),
                                oc3MultiShortReach(9),
                                oc3SingleIntermediateReach(10),
                                oc3SingleLongReach(11),
                                unknown(255)
                                }
                        MAX-ACCESS read-only
                        STATUS current
                        DESCRIPTION
                                "The module tranceiver detail type.
                                1: 1000Base-SX
                                2: 1000Base-LX
                                3: 1000Base-CX
                                4: 1000Base-T
                                5: 1000Base-LX/LX10
                                6: 100Base-FX
                                7: 1000Base-BX10
                                8: 1000Base-PX
                                9: OC-3(155M) Multi Mode Short Reach
                                10: OC-3(155M) Single Mode Intermediate Reach
                                11: OC-3(155M) Single Mode Long Reach
                                255: Unknown"
                        ::= { fkGponOnuAniEntry 5 }

                
                -- 1.3.6.1.4.1.10428 9 1.101.23.6.6.1.1.6
                fkGponOnuAniOpticModuleLengthMode OBJECT-TYPE
                        SYNTAX INTEGER
                                {
                                singleMode(1),
                                multiMode(2),
                                unknown(255)
                                }
                        MAX-ACCESS read-only
                        STATUS current
                        DESCRIPTION
                                "The module length mode.
                                1: singleMode
                                2: multiMode
                                255 : unknown"
                        ::= { fkGponOnuAniEntry 6 }

                
                -- 1.3.6.1.4.1.10428 9 1.101.23.6.6.1.1.7
                fkGponOnuAniOpticModuleLength OBJECT-TYPE
                        SYNTAX INTEGER (1..65535)
                        MAX-ACCESS read-only
                        STATUS current
                        DESCRIPTION
                                "the module length(m)."
                        ::= { fkGponOnuAniEntry 7 }

                
                -- 1.3.6.1.4.1.10428 9 1.101.23.6.6.1.1.8
                fkGponOnuAniOpticModuleSpeed OBJECT-TYPE
                        SYNTAX INTEGER
                                {
                                speed155(1),
                                speed200(2),
                                speed622(3),
                                speed1062dot5(4),
                                speed1250(5),
                                speed2125(6),
                                speed4250(7),
                                speed2488(8),
                                unknown(255)
                                }
                        MAX-ACCESS read-only
                        STATUS current
                        DESCRIPTION
                                "The module speed.
                                1: 155 Mb/s
                                2: 200 Mb/s
                                3: 622 Mb/s
                                4: 1062.5 Mb/s
                                5: 1250 Mb/s
                                6: 2125 Mb/s
                                7: 4250 Mb/s
                                8: 2488 Mb/s
                                255: unknown"
                        ::= { fkGponOnuAniEntry 8 }

                
                -- 1.3.6.1.4.1.10428 9 1.101.23.6.6.1.1.9
                fkGponOnuAniOpticModuleWavelength OBJECT-TYPE
                        SYNTAX INTEGER
                                {
                                length850(1),
                                length1310(2),
                                length1490(3),
                                length1550(4),
                                unknown(255)
                                }
                        MAX-ACCESS read-only
                        STATUS current
                        DESCRIPTION
                                "The module wavelength
                                1: 850 nm
                                2: 1310 nm
                                3: 1490 nm
                                4: 1550 nm
                                255: unknown"
                        ::= { fkGponOnuAniEntry 9 }

                
                -- 1.3.6.1.4.1.10428 9 1.101.23.6.6.1.1.10
                fkGponOnuAniOpticModuleConnecterType OBJECT-TYPE
                        SYNTAX INTEGER
                                {
                                sc(1),
                                fiberChannelStyle1(2),
                                fiberChannelStyle2(3),
                                bncTnc(4),
                                fiberChannelCoaxialHeaders(5),
                                fiberJack(6),
                                lc(7),
                                mtRj(8),
                                mu(9),
                                sg(10),
                                opticalPigtail(11),
                                hssdc2(12),
                                copperPigtail(13),
                                unknown(255)
                                }
                        MAX-ACCESS read-only
                        STATUS current
                        DESCRIPTION
                                "The module connecter type.
                                1: SC
                                2: Fiber Channel Style 1 copper connector
                                3: Fiber Channel Style 2 copper connector
                                4: BNC/TNC
                                5: Fiber Channel coaxial headers
                                6: Fiber Jack
                                7: LC
                                8: MT-RJ
                                9: MU
                                10: SG
                                11: Optical Pigtail
                                12: HSSDC II
                                13: Copper Pigtail
                                255: unknown"
                        ::= { fkGponOnuAniEntry 10 }

                
                -- 1.3.6.1.4.1.10428 9 1.101.23.6.6.1.1.11
                fkGponOnuAniOpticModuleVendorName OBJECT-TYPE
                        SYNTAX OCTET STRING
                        MAX-ACCESS read-only
                        STATUS current
                        DESCRIPTION
                                "The module vendor name."
                        ::= { fkGponOnuAniEntry 11 }

                
                -- 1.3.6.1.4.1.10428 9 1.101.23.6.6.1.1.12
                fkGponOnuAniOpticModuleVendorPartName OBJECT-TYPE
                        SYNTAX OCTET STRING
                        MAX-ACCESS read-only
                        STATUS current
                        DESCRIPTION
                                "The module vendor part name."
                        ::= { fkGponOnuAniEntry 12 }

                
                -- 1.3.6.1.4.1.10428 9 1.101.23.6.6.1.1.13
                fkGponOnuAniOpticModuleVendorRevision OBJECT-TYPE
                        SYNTAX OCTET STRING
                        MAX-ACCESS read-only
                        STATUS current
                        DESCRIPTION
                                "The module vendor revision."
                        ::= { fkGponOnuAniEntry 13 }

                
                -- 1.3.6.1.4.1.10428 9 1.101.23.6.6.1.1.14
                fkGponOnuAniOpticModuleVendorSerialNumber OBJECT-TYPE
                        SYNTAX OCTET STRING
                        MAX-ACCESS read-only
                        STATUS current
                        DESCRIPTION
                                "the moduel vendor serial number."
                        ::= { fkGponOnuAniEntry 14 }

                
                -- 1.3.6.1.4.1.10428 9 1.101.23.6.6.1.1.15
                fkGponOnuAniOpticModuleProductDate OBJECT-TYPE
                        SYNTAX OCTET STRING
                        MAX-ACCESS read-only
                        STATUS current
                        DESCRIPTION
                                "The module vendor product date."
                        ::= { fkGponOnuAniEntry 15 }

                
                -- 1.3.6.1.4.1.10428 9 1.101.23.6.6.1.1.16
                fkGponOnuAniOpticModuleTemper OBJECT-TYPE
                        SYNTAX OCTET STRING
                        MAX-ACCESS read-only
                        STATUS current
                        DESCRIPTION
                                "Internally measured module temperature.(C)"
                        ::= { fkGponOnuAniEntry 16 }

                
                -- 1.3.6.1.4.1.10428 9 1.101.23.6.6.1.1.17
                fkGponOnuAniOpticModuleVoltage OBJECT-TYPE
                        SYNTAX OCTET STRING
                        MAX-ACCESS read-only
                        STATUS current
                        DESCRIPTION
                                "Internally measured supply voltage in transceiver.(V)
                                "
                        ::= { fkGponOnuAniEntry 17 }

                
                -- 1.3.6.1.4.1.10428 9 1.101.23.6.6.1.1.18
                fkGponOnuAniOpticModuleTxbias OBJECT-TYPE
                        SYNTAX OCTET STRING
                        MAX-ACCESS read-only
                        STATUS current
                        DESCRIPTION
                                "Internally measured TX Bias Current.(mA)"
                        ::= { fkGponOnuAniEntry 18 }

                
                -- 1.3.6.1.4.1.10428 9 1.101.23.6.6.1.1.19
                fkGponOnuAniOpticModuleTxPower OBJECT-TYPE
                        SYNTAX OCTET STRING
                        MAX-ACCESS read-only
                        STATUS current
                        DESCRIPTION
                                "Measured TX output power.(dBm)"
                        ::= { fkGponOnuAniEntry 19 }

                
                -- 1.3.6.1.4.1.10428 9 1.101.23.6.6.1.1.20
                fkGponOnuAniOpticModuleRxPower OBJECT-TYPE
                        SYNTAX OCTET STRING
                        MAX-ACCESS read-only
                        STATUS current
                        DESCRIPTION
                                "Measured RX input power.(dBm)"
                        ::= { fkGponOnuAniEntry 20 }

                
                -- 1.3.6.1.4.1.10428 9 1.101.23.6.6.1.1.21
                fkGponOnuAniOpticModuleTemperHighThr OBJECT-TYPE
                        SYNTAX Integer32
                        MAX-ACCESS read-only
                        STATUS current
                        DESCRIPTION
                                "The temperature high threshold"
                        ::= { fkGponOnuAniEntry 21 }

                
                -- 1.3.6.1.4.1.10428 9 1.101.23.6.6.1.1.22
                fkGponOnuAniOpticModuleTemperLowThr OBJECT-TYPE
                        SYNTAX Integer32
                        MAX-ACCESS read-only
                        STATUS current
                        DESCRIPTION
                                "The temperature low threshold"
                        ::= { fkGponOnuAniEntry 22 }

                
                -- 1.3.6.1.4.1.10428 9 1.101.23.6.6.1.1.23
                fkGponOnuAniOpticModuleVoltageHighThr OBJECT-TYPE
                        SYNTAX Integer32
                        MAX-ACCESS read-only
                        STATUS current
                        DESCRIPTION
                                "The voltage high threshold (0.1 V)"
                        ::= { fkGponOnuAniEntry 23 }

                
                -- 1.3.6.1.4.1.10428 9 1.101.23.6.6.1.1.24
                fkGponOnuAniOpticModuleVoltageLowThr OBJECT-TYPE
                        SYNTAX Integer32
                        MAX-ACCESS read-only
                        STATUS current
                        DESCRIPTION
                                "The voltage low threshold (0.1 V)"
                        ::= { fkGponOnuAniEntry 24 }

                
                -- 1.3.6.1.4.1.10428 9 1.101.23.6.6.1.1.25
                fkGponOnuAniOpticModuleTxbiasHighThr OBJECT-TYPE
                        SYNTAX Integer32
                        MAX-ACCESS read-only
                        STATUS current
                        DESCRIPTION
                                "The TX bias high threshold"
                        ::= { fkGponOnuAniEntry 25 }

                
                -- 1.3.6.1.4.1.10428 9 1.101.23.6.6.1.1.26
                fkGponOnuAniOpticModuleTxbiasLowThr OBJECT-TYPE
                        SYNTAX Integer32
                        MAX-ACCESS read-only
                        STATUS current
                        DESCRIPTION
                                "The TX bias low threshold"
                        ::= { fkGponOnuAniEntry 26 }

                
                -- 1.3.6.1.4.1.10428 9 1.101.23.6.6.1.1.27
                fkGponOnuAniOpticModuleTxPowerHighThr OBJECT-TYPE
                        SYNTAX Integer32
                        MAX-ACCESS read-only
                        STATUS current
                        DESCRIPTION
                                "The TX power high threshold (0.1 dBm)"
                        ::= { fkGponOnuAniEntry 27 }

                
                -- 1.3.6.1.4.1.10428 9 1.101.23.6.6.1.1.28
                fkGponOnuAniOpticModuleTxPowerLowThr OBJECT-TYPE
                        SYNTAX Integer32
                        MAX-ACCESS read-only
                        STATUS current
                        DESCRIPTION
                                "The TX power low threshold (0.1 dBm)"
                        ::= { fkGponOnuAniEntry 28 }

                
                -- 1.3.6.1.4.1.10428 9 1.101.23.6.6.1.1.29
                fkGponOnuAniOpticModuleRxPowerHighThr OBJECT-TYPE
                        SYNTAX Integer32
                        MAX-ACCESS read-only
                        STATUS current
                        DESCRIPTION
                                "The RX power high threshold"
                        ::= { fkGponOnuAniEntry 29 }

                
                -- 1.3.6.1.4.1.10428 9 1.101.23.6.6.1.1.30
                fkGponOnuAniOpticModuleRxPowerLowThr OBJECT-TYPE
                        SYNTAX Integer32
                        MAX-ACCESS read-only
                        STATUS current
                        DESCRIPTION
                                "The RX power low threshold"
                        ::= { fkGponOnuAniEntry 30 }

                
--  1.3.6.1.4.1.10428 9 1.101.23.6.1.2
                -- 1.3.6.1.4.1.10428 9 1.101.23.6.6.2
                fkGponOnuAniControl OBJECT IDENTIFIER ::= { fkGponOnuAni 2 }

                
--  1.3.6.1.4.1.10428 9 1.101.23.6.1.2.1
                -- 1.3.6.1.4.1.10428 9 1.101.23.6.6.2.1
                fkGponOnuAniControlRequest OBJECT-TYPE
                        SYNTAX INTEGER { updateOnuAniOpticModuleInfo(1) }
                        MAX-ACCESS read-write
                        STATUS current
                        DESCRIPTION
                                "The request of a user command"
                        ::= { fkGponOnuAniControl 1 }

                
--  1.3.6.1.4.1.10428 9 1.101.23.6.1.2.2
                -- 1.3.6.1.4.1.10428 9 1.101.23.6.6.2.2
                fkGponOnuAniControlStatus OBJECT-TYPE
                        SYNTAX FkControlStatusType
                        MAX-ACCESS read-only
                        STATUS current
                        DESCRIPTION
                                "The status of user command"
                        ::= { fkGponOnuAniControl 2 }

                
--  1.3.6.1.4.1.10428 9 1.101.23.6.1.2.3
                -- 1.3.6.1.4.1.10428 9 1.101.23.6.6.2.3
                fkGponOnuAniControlTimer OBJECT-TYPE
                        SYNTAX Gauge32
                        MAX-ACCESS read-write
                        STATUS current
                        DESCRIPTION
                                "The maximum time for the manager for a long running user command"
                        ::= { fkGponOnuAniControl 3 }

                
--  1.3.6.1.4.1.10428 9 1.101.23.6.1.2.4
                -- 1.3.6.1.4.1.10428 9 1.101.23.6.6.2.4
                fkGponOnuAniControlTimeStamp OBJECT-TYPE
                        SYNTAX TimeTicks
                        MAX-ACCESS read-only
                        STATUS current
                        DESCRIPTION
                                "The time stamp of the last command(end of command)"
                        ::= { fkGponOnuAniControl 4 }

                
--  1.3.6.1.4.1.10428 9 1.101.23.6.1.2.5
                -- 1.3.6.1.4.1.10428 9 1.101.23.6.6.2.5
                fkGponOnuAniControlReqResult OBJECT-TYPE
                        SYNTAX FkControlRequestResultType
                        MAX-ACCESS read-only
                        STATUS current
                        DESCRIPTION
                                "The result of the last user command"
                        ::= { fkGponOnuAniControl 5 }

                
--  1.3.6.1.4.1.10428 9 1.101.23.6.1.2.6
                -- 1.3.6.1.4.1.10428 9 1.101.23.6.6.2.6
                fkGponOnuAniControlOltId OBJECT-TYPE
                        SYNTAX INTEGER (1..65535)
                        MAX-ACCESS read-write
                        STATUS current
                        DESCRIPTION
                                "Gpon Olt Index"
                        ::= { fkGponOnuAniControl 6 }

                
--  1.3.6.1.4.1.10428 9 1.101.23.6.1.2.7
                -- 1.3.6.1.4.1.10428 9 1.101.23.6.6.2.7
                fkGponOnuAniControlOnuId OBJECT-TYPE
                        SYNTAX INTEGER (1..65535)
                        MAX-ACCESS read-write
                        STATUS current
                        DESCRIPTION
                                "Gpon Onu Index"
                        ::= { fkGponOnuAniControl 7 }

                
                -- 1.3.6.1.4.1.10428 9 1.101.23.6.6.2.8
                fkGponOnuAniControlAniId OBJECT-TYPE
                        SYNTAX Integer32
                        MAX-ACCESS read-write
                        STATUS current
                        DESCRIPTION
                                "The ANI index."
                        ::= { fkGponOnuAniControl 8 }

                
                -- 1.3.6.1.4.1.10428 9 1.101.23.6.6.3
                fkGponOnuAniNotification OBJECT IDENTIFIER ::= { fkGponOnuAni 3 }

                
                -- 1.3.6.1.4.1.10428 9 1.101.23.6.6.3.1
                fkGponOnuAniOpticModuleInfoUpdated NOTIFICATION-TYPE
                        OBJECTS { fkGponOnuAniControlRequest, fkGponOnuAniControlTimeStamp, fkGponOnuAniControlReqResult, fkGponOltId, fkGponOnuId, 
                                fkGponOnuAniId }
                        STATUS current
                        DESCRIPTION 
                                "updateOnuAniOpticModuleInfo"
                        ::= { fkGponOnuAniNotification 1 }

                
                -- 1.3.6.1.4.1.10428 9 1.101.23.6.7
                fkGponStaticMac OBJECT IDENTIFIER ::= { fkGponBridge 7 }

                
                -- 1.3.6.1.4.1.10428 9 1.101.23.6.7.1
                fkGponStaticMacTable OBJECT-TYPE
                        SYNTAX SEQUENCE OF FkGponStaticMacEntry
                        MAX-ACCESS not-accessible
                        STATUS current
                        DESCRIPTION
                                "Description."
                        ::= { fkGponStaticMac 1 }

                
                -- 1.3.6.1.4.1.10428 9 1.101.23.6.7.1.1
                fkGponStaticMacEntry OBJECT-TYPE
                        SYNTAX FkGponStaticMacEntry
                        MAX-ACCESS not-accessible
                        STATUS current
                        DESCRIPTION
                                "Description."
                        INDEX { fkGponOltId, fkGponStaticMacListId }
                        ::= { fkGponStaticMacTable 1 }

                
                FkGponStaticMacEntry ::=
                        SEQUENCE { 
                                fkGponStaticMacListId
                                        Integer32,
                                fkGponStaticMacStartAddr
                                        OCTET STRING,
                                fkGponStaticMacEndAddr
                                        Integer32,
                                fkGponStaticMacTrafficId
                                        INTEGER,
                                fkGponStaticMacVlanId
                                        Integer32,
                                fkGponStaticMacPortId
                                        Integer32,
                                fkGponStaticMacCount
                                        Integer32
                         }

                -- 1.3.6.1.4.1.10428 9 1.101.23.6.7.1.1.1
                fkGponStaticMacListId OBJECT-TYPE
                        SYNTAX Integer32 (1..65535)
                        MAX-ACCESS read-only
                        STATUS current
                        DESCRIPTION
                                "Gpon List Index. (only use for showing GET)"
                        ::= { fkGponStaticMacEntry 1 }

                
                -- 1.3.6.1.4.1.10428 9 1.101.23.6.7.1.1.2
                fkGponStaticMacStartAddr OBJECT-TYPE
                        SYNTAX OCTET STRING
                        MAX-ACCESS read-only
                        STATUS current
                        DESCRIPTION
                                "The start static MAC address used by range of a multicast or broadcast stream."
                        ::= { fkGponStaticMacEntry 2 }

                
                -- 1.3.6.1.4.1.10428 9 1.101.23.6.7.1.1.3
                fkGponStaticMacEndAddr OBJECT-TYPE
                        SYNTAX Integer32
                        MAX-ACCESS read-only
                        STATUS current
                        DESCRIPTION
                                "The end static MAC address used by range of multicast or broadcast stream"
                        ::= { fkGponStaticMacEntry 3 }

                
                -- 1.3.6.1.4.1.10428 9 1.101.23.6.7.1.1.4
                fkGponStaticMacTrafficId OBJECT-TYPE
                        SYNTAX INTEGER
                                {
                                multicast(1),
                                broadcast(2)
                                }
                        MAX-ACCESS read-only
                        STATUS current
                        DESCRIPTION
                                "Traffic ID information
                                  1       Multicast
                                  2       Broadcast
                                "
                        ::= { fkGponStaticMacEntry 4 }

                
                -- 1.3.6.1.4.1.10428 9 1.101.23.6.7.1.1.5
                fkGponStaticMacVlanId OBJECT-TYPE
                        SYNTAX Integer32 (1..4094)
                        MAX-ACCESS read-only
                        STATUS current
                        DESCRIPTION
                                "VLAN ID information"
                        ::= { fkGponStaticMacEntry 5 }

                
                -- 1.3.6.1.4.1.10428 9 1.101.23.6.7.1.1.6
                fkGponStaticMacPortId OBJECT-TYPE
                        SYNTAX Integer32 (1..4095)
                        MAX-ACCESS read-only
                        STATUS current
                        DESCRIPTION
                                "GEM Port ID information"
                        ::= { fkGponStaticMacEntry 6 }

                
                -- 1.3.6.1.4.1.10428 9 1.101.23.6.7.1.1.7
                fkGponStaticMacCount OBJECT-TYPE
                        SYNTAX Integer32 (0..4096)
                        MAX-ACCESS read-only
                        STATUS current
                        DESCRIPTION
                                "The total range of static MAC address "
                        ::= { fkGponStaticMacEntry 7 }

                
                -- 1.3.6.1.4.1.10428 9 1.101.23.6.7.2
                fkGponStaticMacControl OBJECT IDENTIFIER ::= { fkGponStaticMac 2 }

                
--  1.3.6.1.4.1.10428 9 1.101.23.6.1.2.1
                -- 1.3.6.1.4.1.10428 9 1.101.23.6.7.2.1
                fkGponStaticMacControlRequest OBJECT-TYPE
                        SYNTAX INTEGER
                                {
                                setGponStaticMac(1),
                                deleteGponStaticMac(2)
                                }
                        MAX-ACCESS read-write
                        STATUS current
                        DESCRIPTION
                                "The request of a user command"
                        ::= { fkGponStaticMacControl 1 }

                
--  1.3.6.1.4.1.10428 9 1.101.23.6.1.2.2
                -- 1.3.6.1.4.1.10428 9 1.101.23.6.7.2.2
                fkGponStaticMacControlStatus OBJECT-TYPE
                        SYNTAX FkControlStatusType
                        MAX-ACCESS read-only
                        STATUS current
                        DESCRIPTION
                                "The status of user command"
                        ::= { fkGponStaticMacControl 2 }

                
--  1.3.6.1.4.1.10428 9 1.101.23.6.1.2.3
                -- 1.3.6.1.4.1.10428 9 1.101.23.6.7.2.3
                fkGponStaticMacControlTimer OBJECT-TYPE
                        SYNTAX Gauge32
                        MAX-ACCESS read-write
                        STATUS current
                        DESCRIPTION
                                "The maximum time for the manager for a long running user command"
                        ::= { fkGponStaticMacControl 3 }

                
--  1.3.6.1.4.1.10428 9 1.101.23.6.1.2.4
                -- 1.3.6.1.4.1.10428 9 1.101.23.6.7.2.4
                fkGponStaticMacControlTimeStamp OBJECT-TYPE
                        SYNTAX TimeTicks
                        MAX-ACCESS read-only
                        STATUS current
                        DESCRIPTION
                                "The time stamp of the last command(end of command)"
                        ::= { fkGponStaticMacControl 4 }

                
--  1.3.6.1.4.1.10428 9 1.101.23.6.1.2.5
                -- 1.3.6.1.4.1.10428 9 1.101.23.6.7.2.5
                fkGponStaticMacControlReqResult OBJECT-TYPE
                        SYNTAX FkControlRequestResultType
                        MAX-ACCESS read-only
                        STATUS current
                        DESCRIPTION
                                "The result of the last user command"
                        ::= { fkGponStaticMacControl 5 }

                
                -- 1.3.6.1.4.1.10428 9 1.101.23.6.7.2.6
                fkGponStaticMacControlOltId OBJECT-TYPE
                        SYNTAX Integer32 (1..512)
                        MAX-ACCESS read-write
                        STATUS current
                        DESCRIPTION
                                "OLT index."
                        ::= { fkGponStaticMacControl 6 }

                
                -- 1.3.6.1.4.1.10428 9 1.101.23.6.7.2.7
                fkGponStaticMacControlStartAddr OBJECT-TYPE
                        SYNTAX OCTET STRING
                        MAX-ACCESS read-write
                        STATUS current
                        DESCRIPTION
                                "The start static MAC address used by range of a multicast or broadcast stream."
                        ::= { fkGponStaticMacControl 7 }

                
                -- 1.3.6.1.4.1.10428 9 1.101.23.6.7.2.8
                fkGponStaticMacControlEndAddr OBJECT-TYPE
                        SYNTAX OCTET STRING
                        MAX-ACCESS read-write
                        STATUS current
                        DESCRIPTION
                                "The end static MAC address used by range of multicast or broadcast stream"
                        ::= { fkGponStaticMacControl 8 }

                
                -- 1.3.6.1.4.1.10428 9 1.101.23.6.7.2.9
                fkGponStaticMacControlTrafficId OBJECT-TYPE
                        SYNTAX INTEGER
                                {
                                multicast(1),
                                broadcast(2)
                                }
                        MAX-ACCESS read-write
                        STATUS current
                        DESCRIPTION
                                "The traffic type method about the Static MAC address"
                        ::= { fkGponStaticMacControl 9 }

                
                -- 1.3.6.1.4.1.10428 9 1.101.23.6.7.2.10
                fkGponStaticMacControlVlanId OBJECT-TYPE
                        SYNTAX Integer32 (0..4094)
                        MAX-ACCESS read-write
                        STATUS current
                        DESCRIPTION
                                "VLAN ID method"
                        ::= { fkGponStaticMacControl 10 }

                
                -- 1.3.6.1.4.1.10428 9 1.101.23.6.7.3
                fkGponStaticMacNotification OBJECT IDENTIFIER ::= { fkGponStaticMac 3 }

                
                -- 1.3.6.1.4.1.10428 9 1.101.23.6.7.3.1
                fkGponStaticMacCreated NOTIFICATION-TYPE
                        OBJECTS { fkGponStaticMacControlRequest, fkGponStaticMacControlTimeStamp, fkGponStaticMacControlReqResult, fkGponStaticMacControlOltId, fkGponStaticMacControlStartAddr, 
                                fkGponStaticMacControlEndAddr, fkGponStaticMacControlTrafficId, fkGponStaticMacControlVlanId }
                        STATUS current
                        DESCRIPTION 
                                "setGponStaticMac"
                        ::= { fkGponStaticMacNotification 1 }

                
                -- 1.3.6.1.4.1.10428 9 1.101.23.6.7.3.2
                fkGponStaticMacDeleted NOTIFICATION-TYPE
                        OBJECTS { fkGponStaticMacControlRequest, fkGponStaticMacControlTimeStamp, fkGponStaticMacControlReqResult, fkGponStaticMacControlOltId, fkGponStaticMacControlStartAddr, 
                                fkGponStaticMacControlEndAddr, fkGponStaticMacControlTrafficId, fkGponStaticMacControlVlanId }
                        STATUS current
                        DESCRIPTION 
                                "deleteGponStaticMac"
                        ::= { fkGponStaticMacNotification 2 }

                
                -- 1.3.6.1.4.1.10428 9 1.101.23.6.8
                fkGponOnuVideoAni OBJECT IDENTIFIER ::= { fkGponBridge 8 }

                
                -- 1.3.6.1.4.1.10428 9 1.101.23.6.8.1
                fkGponOnuVideoAniTable OBJECT-TYPE
                        SYNTAX SEQUENCE OF FkGponOnuVideoAniEntry
                        MAX-ACCESS not-accessible
                        STATUS current
                        DESCRIPTION
                                "Description."
                        ::= { fkGponOnuVideoAni 1 }

                
                -- 1.3.6.1.4.1.10428 9 1.101.23.6.8.1.1
                fkGponOnuVideoAniEntry OBJECT-TYPE
                        SYNTAX FkGponOnuVideoAniEntry
                        MAX-ACCESS not-accessible
                        STATUS current
                        DESCRIPTION
                                "Description."
                        INDEX { fkGponOltId, fkGponOnuId, fkGponOnuVideoAniIndex }
                        ::= { fkGponOnuVideoAniTable 1 }

                
                FkGponOnuVideoAniEntry ::=
                        SEQUENCE { 
                                fkGponOnuVideoAniIndex
                                        Integer32,
                                fkGponOnuVideoAniAdminState
                                        INTEGER,
                                fkGponOnuVideoAniOperState
                                        INTEGER,
                                fkGponOnuVideoAniArc
                                        Integer32,
                                fkGponOnuVideoAniArcInterval
                                        Integer32,
                                fkGponOnuVideoAniFreqRangeLow
                                        INTEGER,
                                fkGponOnuVideoAniFreqRangeHigh
                                        INTEGER,
                                fkGponOnuVideoAniSignalCapability
                                        INTEGER,
                                fkGponOnuVideoAniOpticalSignalLevel
                                        Integer32,
                                fkGponOnuVideoAniPilotSignalLevel
                                        Integer32,
                                fkGponOnuVideoAniSignalLevelMin
                                        Integer32,
                                fkGponOnuVideoAniSignalLevelMax
                                        Integer32,
                                fkGponOnuVideoAniPilotFreq
                                        Integer32,
                                fkGponOnuVideoAniAgcMode
                                        INTEGER,
                                fkGponOnuVideoAniAgcSetting
                                        Integer32,
                                fkGponOnuVideoAniVideoLowerOpticalThr
                                        Integer32,
                                fkGponOnuVideoAniVideoUpperOpticalThr
                                        Integer32,
                                fkGponOnuVideoAniConfAgcSetting
                                        Integer32
                         }

                -- 1.3.6.1.4.1.10428 9 1.101.23.6.8.1.1.1
                fkGponOnuVideoAniIndex OBJECT-TYPE
                        SYNTAX Integer32 (1..65535)
                        MAX-ACCESS read-only
                        STATUS current
                        DESCRIPTION
                                "The ANI index."
                        ::= { fkGponOnuVideoAniEntry 1 }

                
                -- 1.3.6.1.4.1.10428 9 1.101.23.6.8.1.1.2
                fkGponOnuVideoAniAdminState OBJECT-TYPE
                        SYNTAX INTEGER
                                {
                                unlock(0),
                                lock(1)
                                }
                        MAX-ACCESS read-only
                        STATUS current
                        DESCRIPTION
                                "This attribute locks (1) and unlocks (0) the functions performed by this 
                                managed entity. When the administrative state is set to lock, all user 
                                functions of this managed entity are blocked, and alarms, TCAs and AVCs 
                                for this managed entity and all dependent managed entities are no longer 
                                generated. Selection of a default value for this attribute is outside the scope 
                                of this Recommendation.
                                "
                        ::= { fkGponOnuVideoAniEntry 2 }

                
                -- 1.3.6.1.4.1.10428 9 1.101.23.6.8.1.1.3
                fkGponOnuVideoAniOperState OBJECT-TYPE
                        SYNTAX INTEGER
                                {
                                enable(0),
                                disable(1)
                                }
                        MAX-ACCESS read-only
                        STATUS current
                        DESCRIPTION
                                "This attribute indicates whether or not the managed entity is capable of 
                                performing its function. Valid values are enabled (0) and disabled (1). 
                                "
                        ::= { fkGponOnuVideoAniEntry 3 }

                
                -- 1.3.6.1.4.1.10428 9 1.101.23.6.8.1.1.4
                fkGponOnuVideoAniArc OBJECT-TYPE
                        SYNTAX Integer32 (1..255)
                        MAX-ACCESS read-only
                        STATUS current
                        DESCRIPTION
                                "This attribute allows the activation of alarm reporting control (ARC) for this PPTP. The attribute 
                                works in concert with the ARC_interval attribute"
                        ::= { fkGponOnuVideoAniEntry 4 }

                
                -- 1.3.6.1.4.1.10428 9 1.101.23.6.8.1.1.5
                fkGponOnuVideoAniArcInterval OBJECT-TYPE
                        SYNTAX Integer32 (1..255)
                        MAX-ACCESS read-only
                        STATUS current
                        DESCRIPTION
                                "This attribute defines the interval to be used with the ARC function for this PPTP. The values 0 
                                through 254 give the duration in minutes for the NALM-QI timer. The special value 255 means that 
                                the timer never expires. The default value is zero.  
                                Note that ARC suppresses the reporting of the alarms, and not the alarm conditions themselves. 
                                Therefore, if an alarm condition develops during an ARC interval, then the ONT should maintain 
                                the internal indication of the alarm, and if the OLT gets all the alarms, it should be reported. "
                        ::= { fkGponOnuVideoAniEntry 5 }

                
                -- 1.3.6.1.4.1.10428 9 1.101.23.6.8.1.1.6
                fkGponOnuVideoAniFreqRangeLow OBJECT-TYPE
                        SYNTAX INTEGER
                                {
                                noLowBand(0),
                                band50To550Mhz(1),
                                band50To750Mhz(2),
                                band50To870Mhz(3)
                                }
                        MAX-ACCESS read-only
                        STATUS current
                        DESCRIPTION
                                "This attribute indicates the lower of the two possible frequency ranges 
                                supported. Different frequency ranges are indicated by code points: 
                                0 No low band. 
                                1 50..550 MHz. 
                                2 50..750 MHz. 
                                3 50..870 MHz. 
                                
                                "
                        ::= { fkGponOnuVideoAniEntry 6 }

                
                -- 1.3.6.1.4.1.10428 9 1.101.23.6.8.1.1.7
                fkGponOnuVideoAniFreqRangeHigh OBJECT-TYPE
                        SYNTAX INTEGER
                                {
                                noHighBand(0),
                                band550To750(1),
                                band550To870(2),
                                band950To2050(3),
                                band2150To3250(4),
                                band950To3250(5)
                                }
                        MAX-ACCESS read-only
                        STATUS current
                        DESCRIPTION
                                "This attribute indicates the higher of the two frequency ranges supported. 
                                Different frequency ranges are indicated by code points: 
                                0 No high band. 
                                1 550..750 MHz. 
                                2 550..870 MHz. 
                                3 950..2050 MHz. 
                                4 2150..3250 MHz. 
                                5 950..3250 MHz. 
                                "
                        ::= { fkGponOnuVideoAniEntry 7 }

                
                -- 1.3.6.1.4.1.10428 9 1.101.23.6.8.1.1.8
                fkGponOnuVideoAniSignalCapability OBJECT-TYPE
                        SYNTAX INTEGER
                                {
                                noSignal(0),
                                totalOptical(1),
                                fixedFrequencyPilotTone(2),
                                totalOpticalAndFixedFrequencyPilotTone(3),
                                variableFrequencyPilotTone(4),
                                totalOpticalAndVariableFrequencyPilotTone(5),
                                broadbandRF(6),
                                totalOpticalAndBroadbandRF(7)
                                }
                        MAX-ACCESS read-only
                        STATUS current
                        DESCRIPTION
                                "This attribute indicates the capability of the ONT to measure the video 
                                signal level. Capabilities are indicated by code points: 
                                0 No signal level capability. 
                                1 Total optical power level. 
                                2 Fixed frequency pilot tone power level. 
                                3 Total optical power level and fixed frequency pilot tone power level. 
                                4 Variable frequency pilot tone power level. 
                                5 Total optical power level and variable frequency pilot tone power level. 
                                6 Broadband RF power level. 
                                7 Total optical power level and broadband RF power level. 
                                8..255 Reserved. 
                                "
                        ::= { fkGponOnuVideoAniEntry 8 }

                
                -- 1.3.6.1.4.1.10428 9 1.101.23.6.8.1.1.9
                fkGponOnuVideoAniOpticalSignalLevel OBJECT-TYPE
                        SYNTAX Integer32 (1..255)
                        MAX-ACCESS read-only
                        STATUS current
                        DESCRIPTION
                                "This attribute is an unsigned integer that returns the current measurement 
                                of the total optical signal level. The unit of this attribute is dBm optical. 
                                If signal capability = 0, 2, 4 or 6, this attribute is undefined. 
                                If signal capability =1, 3, 5 or 7, this attribute describes the total 
                                optical power that is generating photocurrent on the receiver. 
                                "
                        ::= { fkGponOnuVideoAniEntry 9 }

                
                -- 1.3.6.1.4.1.10428 9 1.101.23.6.8.1.1.10
                fkGponOnuVideoAniPilotSignalLevel OBJECT-TYPE
                        SYNTAX Integer32 (1..255)
                        MAX-ACCESS read-only
                        STATUS current
                        DESCRIPTION
                                "This attribute indicates the current measurement of the pilot signal level or 
                                broadband RF level. The unit of this attribute is dB⊥iV at the RF video 
                                service port. 
                                If signal capability = 0 or 1, then this attribute is undefined. 
                                If signal capability = 2, 3, 4 or 5, this attribute reports the pilot signal level 
                                at the out put of the video UNI. 
                                If signal capability = 6 or 7, this attribute reports the total RF power level at the out
                                put of the video UNI. 
                                "
                        ::= { fkGponOnuVideoAniEntry 10 }

                
                -- 1.3.6.1.4.1.10428 9 1.101.23.6.8.1.1.11
                fkGponOnuVideoAniSignalLevelMin OBJECT-TYPE
                        SYNTAX Integer32 (1..255)
                        MAX-ACCESS read-only
                        STATUS current
                        DESCRIPTION
                                "This attribute indicates the minimum optical RF power per channel that 
                                results in a CNR of 47 dBc for a channel of 4.5 MHz bandwidth at a 
                                receive optical power of -5 dBm. The unit of this attribute is dB⊥iW 
                                optical."
                        ::= { fkGponOnuVideoAniEntry 11 }

                
                -- 1.3.6.1.4.1.10428 9 1.101.23.6.8.1.1.12
                fkGponOnuVideoAniSignalLevelMax OBJECT-TYPE
                        SYNTAX Integer32 (1..255)
                        MAX-ACCESS read-only
                        STATUS current
                        DESCRIPTION
                                "This attribute indicates the maximum optical RF power per channel that 
                                results in a CTB of -57 dBc for an 80-channel ensemble of carriers at a 
                                per-channel optical modulation index of 3.5%. The unit of this attribute is 
                                dB⊥iW optical. "
                        ::= { fkGponOnuVideoAniEntry 12 }

                
                -- 1.3.6.1.4.1.10428 9 1.101.23.6.8.1.1.13
                fkGponOnuVideoAniPilotFreq OBJECT-TYPE
                        SYNTAX Integer32 (1..255)
                        MAX-ACCESS read-only
                        STATUS current
                        DESCRIPTION
                                "This attribute specifies the frequency of the pilot channel receiver. The unit of this attribute is Hz. 
                                If signal capability = 0, 1, 6 or 7, this attribute is undefined. 
                                If signal capability = 2 or 3, this tionally read only.
                                If signal capability = 4 or 5, this attribute is read-write. 
                                "
                        ::= { fkGponOnuVideoAniEntry 13 }

                
                -- 1.3.6.1.4.1.10428 9 1.101.23.6.8.1.1.14
                fkGponOnuVideoAniAgcMode OBJECT-TYPE
                        SYNTAX INTEGER
                                {
                                noAgc(0),
                                broadbandRfAgc(1),
                                opticalAgc(2)
                                }
                        MAX-ACCESS read-only
                        STATUS current
                        DESCRIPTION
                                "This attribute allows the discovery and configuration of the ONT's AGC 
                                capabilities. The attribute contains a codepoint for several AGC types. The 
                                ONT displays the currently used AGC mode. The OLT can discover new 
                                modes via the set command; the ONT denies attempts to set an 
                                unsupported mode. The code points are: 
                                0  No AGC. 
                                1  Broadband RF AGC. 
                                2  Optical AGC. 
                                "
                        ::= { fkGponOnuVideoAniEntry 14 }

                
                -- 1.3.6.1.4.1.10428 9 1.101.23.6.8.1.1.15
                fkGponOnuVideoAniAgcSetting OBJECT-TYPE
                        SYNTAX Integer32 (-128..127)
                        MAX-ACCESS read-only
                        STATUS current
                        DESCRIPTION
                                "This attribute indicates the measurement offset that the ONT should use in 
                                AGC. The attribute has a step size of 0.1 dB, represented as a signed integer. 
                                
                                The theoretical nominal RF signal is 80 channels of NTSC video, each 
                                having a per-channel optical modulation index of 3.5%. An ONT 
                                presented with such a signal should produce its specified ou
                                tput when this attribute is set to zero. 
                                
                                If total optical power is used for AGC, this attribute provides the OMI 
                                offset for any NTSC carriers present from the theoretical 3.5% value. For 
                                example, if the actual signal uses an OMI of 7.0% per channel (3 dB 
                                higher), then the ONT should be given an AGC setting of 30 
                                (coded 0x1E). 
                                
                                If broadband RF power is used for AGC, this attribute provides the total 
                                power offset for any NTSC carriers present from the theoretical 80 channel 
                                value. For example, if an actual signal contains 40 NTSC channels (3 dB 
                                lower), then the ONT should be given an AGC setting of <0096>30 (coded 
                                0xE2). 
                                "
                        ::= { fkGponOnuVideoAniEntry 15 }

                
                -- 1.3.6.1.4.1.10428 9 1.101.23.6.8.1.1.16
                fkGponOnuVideoAniVideoLowerOpticalThr OBJECT-TYPE
                        SYNTAX Integer32 (1..255)
                        MAX-ACCESS read-only
                        STATUS current
                        DESCRIPTION
                                "This attribute specifies the optical level used to declare the video OOR low 
                                alarm. Valid values are <0096>12 to +6 dBm in 0.1 dB increments, represented 
                                as a 2s complement integer (coding -120 to +60, where 0x00 = 0 dBm, 
                                0x88 = -12.0 dBm, etc.). Upon ME instantiation, the ONT sets this 
                                attribute to 0xA1 (-9.5 dBm). (R, W) (optional) (1 byte) 
                                
                                NOTE <0096> Because the power measurement returned in the optical signal level 
                                attribute has a resolution of 1 dB, it is possible that the measured value could 
                                appear to be in-range, even though an out-of-range alarm has been declared 
                                against a threshold with 0.1 dB resolution. 
                                "
                        ::= { fkGponOnuVideoAniEntry 16 }

                
                -- 1.3.6.1.4.1.10428 9 1.101.23.6.8.1.1.17
                fkGponOnuVideoAniVideoUpperOpticalThr OBJECT-TYPE
                        SYNTAX Integer32 (1..255)
                        MAX-ACCESS read-only
                        STATUS current
                        DESCRIPTION
                                "This attribute specifies the optical level used to declare the video OOR 
                                high alarm. Valid values are -12 to +6 dBm in 0.1 dB increments, 
                                represented as a 2s complement integer (coding -120 to +60, 
                                0x00 = 0dBm, 0x88 = -12.0 dBm, etc.). 
                                Upon ME instantiation, the ONT sets this attribute to 0x19 (+2.5 dB
                                m)."
                        ::= { fkGponOnuVideoAniEntry 17 }

                
                -- 1.3.6.1.4.1.10428 9 1.101.23.6.8.1.1.18
                fkGponOnuVideoAniConfAgcSetting OBJECT-TYPE
                        SYNTAX Integer32 (-128..127)
                        MAX-ACCESS read-only
                        STATUS current
                        DESCRIPTION
                                "This attribute indicates the measurement offset that the ONT should use in 
                                AGC. The attribute has a step size of 0.1 dB, represented as a signed integer. 
                                
                                The theoretical nominal RF signal is 80 channels of NTSC video, each 
                                having a per-channel optical modulation index of 3.5%. An ONT 
                                presented with such a signal should produce its specified ou
                                tput when this attribute is set to zero. 
                                
                                If total optical power is used for AGC, this attribute provides the OMI 
                                offset for any NTSC carriers present from the theoretical 3.5% value. For 
                                example, if the actual signal uses an OMI of 7.0% per channel (3 dB 
                                higher), then the ONT should be given an AGC setting of 30 
                                (coded 0x1E). 
                                
                                If broadband RF power is used for AGC, this attribute provides the total 
                                power offset for any NTSC carriers present from the theoretical 80 channel 
                                value. For example, if an actual signal contains 40 NTSC channels (3 dB 
                                lower), then the ONT should be given an AGC setting of <0096>30 (coded 
                                0xE2). 
                                
                                "
                        ::= { fkGponOnuVideoAniEntry 18 }

                
                -- 1.3.6.1.4.1.10428 9 1.101.23.6.8.2
                fkGponOnuVideoAniControl OBJECT IDENTIFIER ::= { fkGponOnuVideoAni 2 }

                
--  1.3.6.1.4.1.10428 9 1.101.23.6.1.2.1
                -- 1.3.6.1.4.1.10428 9 1.101.23.6.8.2.1
                fkGponOnuVideoAniControlRequest OBJECT-TYPE
                        SYNTAX INTEGER
                                {
                                updateVideoAniStatus(1),
                                setVideoAniAgc(2)
                                }
                        MAX-ACCESS read-write
                        STATUS current
                        DESCRIPTION
                                "The request of a user command"
                        ::= { fkGponOnuVideoAniControl 1 }

                
--  1.3.6.1.4.1.10428 9 1.101.23.6.1.2.2
                -- 1.3.6.1.4.1.10428 9 1.101.23.6.8.2.2
                fkGponOnuVideoAniControlStatus OBJECT-TYPE
                        SYNTAX FkControlStatusType
                        MAX-ACCESS read-only
                        STATUS current
                        DESCRIPTION
                                "The status of user command"
                        ::= { fkGponOnuVideoAniControl 2 }

                
--  1.3.6.1.4.1.10428 9 1.101.23.6.1.2.3
                -- 1.3.6.1.4.1.10428 9 1.101.23.6.8.2.3
                fkGponOnuVideoAniControlTimer OBJECT-TYPE
                        SYNTAX Gauge32
                        MAX-ACCESS read-write
                        STATUS current
                        DESCRIPTION
                                "The maximum time for the manager for a long running user command"
                        ::= { fkGponOnuVideoAniControl 3 }

                
--  1.3.6.1.4.1.10428 9 1.101.23.6.1.2.4
                -- 1.3.6.1.4.1.10428 9 1.101.23.6.8.2.4
                fkGponOnuVideoAniControlTimeStamp OBJECT-TYPE
                        SYNTAX TimeTicks
                        MAX-ACCESS read-only
                        STATUS current
                        DESCRIPTION
                                "The time stamp of the last command(end of command)"
                        ::= { fkGponOnuVideoAniControl 4 }

                
--  1.3.6.1.4.1.10428 9 1.101.23.6.1.2.5
                -- 1.3.6.1.4.1.10428 9 1.101.23.6.8.2.5
                fkGponOnuVideoAniControlReqResult OBJECT-TYPE
                        SYNTAX FkControlRequestResultType
                        MAX-ACCESS read-only
                        STATUS current
                        DESCRIPTION
                                "The result of the last user command"
                        ::= { fkGponOnuVideoAniControl 5 }

                
                -- 1.3.6.1.4.1.10428 9 1.101.23.6.8.2.6
                fkGponOnuVideoAniControlOltIndex OBJECT-TYPE
                        SYNTAX Integer32 (1..512)
                        MAX-ACCESS read-write
                        STATUS current
                        DESCRIPTION
                                "The OLT index."
                        ::= { fkGponOnuVideoAniControl 6 }

                
                -- 1.3.6.1.4.1.10428 9 1.101.23.6.8.2.7
                fkGponOnuVideoAniControlOnuIndex OBJECT-TYPE
                        SYNTAX Integer32 (1..256)
                        MAX-ACCESS read-write
                        STATUS current
                        DESCRIPTION
                                "The ONU index."
                        ::= { fkGponOnuVideoAniControl 7 }

                
                -- 1.3.6.1.4.1.10428 9 1.101.23.6.8.2.8
                fkGponOnuVideoAniControlAniIndex OBJECT-TYPE
                        SYNTAX Integer32 (1..65535)
                        MAX-ACCESS read-write
                        STATUS current
                        DESCRIPTION
                                "The ANI index."
                        ::= { fkGponOnuVideoAniControl 8 }

                
                -- 1.3.6.1.4.1.10428 9 1.101.23.6.8.2.9
                fkGponOnuVideoAniControlConfAgcSetting OBJECT-TYPE
                        SYNTAX Integer32 (-128..127)
                        MAX-ACCESS read-write
                        STATUS current
                        DESCRIPTION
                                "This attribute indicates the measurement offset that the ONT should use in 
                                AGC. The attribute has a step size of 0.1 dB, represented as a signed integer. 
                                
                                The theoretical nominal RF signal is 80 channels of NTSC video, each 
                                having a per-channel optical modulation index of 3.5%. An ONT 
                                presented with such a signal should produce its specified ou
                                tput when this attribute is set to zero. 
                                
                                If total optical power is used for AGC, this attribute provides the OMI 
                                offset for any NTSC carriers present from the theoretical 3.5% value. For 
                                example, if the actual signal uses an OMI of 7.0% per channel (3 dB 
                                higher), then the ONT should be given an AGC setting of 30 
                                (coded 0x1E). 
                                
                                If broadband RF power is used for AGC, this attribute provides the total 
                                power offset for any NTSC carriers present from the theoretical 80 channel 
                                value. For example, if an actual signal contains 40 NTSC channels (3 dB 
                                lower), then the ONT should be given an AGC setting of <0096>30 (coded 
                                0xE2). 
                                
                                "
                        ::= { fkGponOnuVideoAniControl 9 }

                
                -- 1.3.6.1.4.1.10428 9 1.101.23.6.8.3
                fkGponOnuVideoAniNotification OBJECT IDENTIFIER ::= { fkGponOnuVideoAni 3 }

                
                -- 1.3.6.1.4.1.10428 9 1.101.23.6.8.3.1
                fkGponOnuVideoAniupdateVideoAniStatusUpdated NOTIFICATION-TYPE
                        OBJECTS { fkGponOnuVideoAniControlRequest, fkGponOnuVideoAniControlTimeStamp, fkGponOnuVideoAniControlReqResult, fkGponOnuVideoAniControlOltIndex, fkGponOnuVideoAniControlOnuIndex
                                 }
                        STATUS current
                        DESCRIPTION 
                                "updateVideoAniStatus"
                        ::= { fkGponOnuVideoAniNotification 1 }

                
                -- 1.3.6.1.4.1.10428 9 1.101.23.6.8.3.2
                fkGponOnuVideoAniControlVideoAniArcChanged NOTIFICATION-TYPE
                        OBJECTS { fkGponOnuVideoAniControlRequest, fkGponOnuVideoAniControlTimeStamp, fkGponOnuVideoAniControlReqResult, fkGponOnuVideoAniControlOltIndex, fkGponOnuVideoAniControlOnuIndex, 
                                fkGponOnuVideoAniControlAniIndex, fkGponOnuVideoAniControlConfAgcSetting }
                        STATUS current
                        DESCRIPTION 
                                "setVideoAniAgc"
                        ::= { fkGponOnuVideoAniNotification 2 }

                
--  1.3.6.1.4.1.10428 9 1.101.23.7
                -- 1.3.6.1.4.1.10428 9 1.101.23.7
                fkGponStatistics OBJECT IDENTIFIER ::= { fkGpon 7 }

                
--  1.3.6.1.4.1.10428 9 1.101.23.7.1
                -- 1.3.6.1.4.1.10428 9 1.101.23.7.1
                fkGponOltStatistics OBJECT IDENTIFIER ::= { fkGponStatistics 1 }

                
--  1.3.6.1.4.1.10428 9 1.101.23.7.1.1
                -- 1.3.6.1.4.1.10428 9 1.101.23.7.1.1
                fkGponOltStatsTable OBJECT-TYPE
                        SYNTAX SEQUENCE OF FkGponOltStatsEntry
                        MAX-ACCESS not-accessible
                        STATUS current
                        DESCRIPTION
                                "fkGponOltStatsTable"
                        ::= { fkGponOltStatistics 1 }

                
--  1.3.6.1.4.1.10428 9 1.101.23.7.1.1.1
                -- 1.3.6.1.4.1.10428 9 1.101.23.7.1.1.1
                fkGponOltStatsEntry OBJECT-TYPE
                        SYNTAX FkGponOltStatsEntry
                        MAX-ACCESS not-accessible
                        STATUS current
                        DESCRIPTION
                                "key: fkGponOltId"
                        INDEX { fkGponOltId }
                        ::= { fkGponOltStatsTable 1 }

                
                FkGponOltStatsEntry ::=
                        SEQUENCE { 
                                fkGponOltStatsPonValidEthPacketsRx
                                        Counter64,
                                fkGponOltStatsPonCpuPacketsRx
                                        Counter64,
                                fkGponOltStatsPonPloamsRx
                                        Counter64,
                                fkGponOltStatsPonInvalidPacketsRx
                                        Counter64,
                                fkGponOltStatsPonValidEthPacketsTx
                                        Counter64,
                                fkGponOltStatsPonCpuPacketsTx
                                        Counter64,
                                fkGponOltStatsPonPloamsTx
                                        Counter64,
                                fkGponOltStatsPonInvalidPacketsTx
                                        Counter64,
                                fkGponOltStatsPerfRxValidPackets
                                        Counter64,
                                fkGponOltStatsPerfRxErroredPackets
                                        Counter64,
                                fkGponOltStatsPerfCRCdroppedPackets
                                        Counter64
                         }

--  1.3.6.1.4.1.10428 9 1.101.23.7.1.1.1.1
                -- 1.3.6.1.4.1.10428 9 1.101.23.7.1.1.1.1
                fkGponOltStatsPonValidEthPacketsRx OBJECT-TYPE
                        SYNTAX Counter64
                        MAX-ACCESS read-only
                        STATUS current
                        DESCRIPTION
                                "UpStream(Rx), N/A"
                        ::= { fkGponOltStatsEntry 1 }

                
--  1.3.6.1.4.1.10428 9 1.101.23.7.1.1.1.2
                -- 1.3.6.1.4.1.10428 9 1.101.23.7.1.1.1.2
                fkGponOltStatsPonCpuPacketsRx OBJECT-TYPE
                        SYNTAX Counter64
                        MAX-ACCESS read-only
                        STATUS current
                        DESCRIPTION
                                "UpStream(Rx), N/A"
                        ::= { fkGponOltStatsEntry 2 }

                
--  1.3.6.1.4.1.10428 9 1.101.23.7.1.1.1.3
                -- 1.3.6.1.4.1.10428 9 1.101.23.7.1.1.1.3
                fkGponOltStatsPonPloamsRx OBJECT-TYPE
                        SYNTAX Counter64
                        MAX-ACCESS read-only
                        STATUS current
                        DESCRIPTION
                                "UpStream(Rx)"
                        ::= { fkGponOltStatsEntry 3 }

                
--  1.3.6.1.4.1.10428 9 1.101.23.7.1.1.1.4
                -- 1.3.6.1.4.1.10428 9 1.101.23.7.1.1.1.4
                fkGponOltStatsPonInvalidPacketsRx OBJECT-TYPE
                        SYNTAX Counter64
                        MAX-ACCESS read-only
                        STATUS current
                        DESCRIPTION
                                "UpStream(Rx)"
                        ::= { fkGponOltStatsEntry 4 }

                
--  1.3.6.1.4.1.10428 9 1.101.23.7.1.1.1.5
                -- 1.3.6.1.4.1.10428 9 1.101.23.7.1.1.1.5
                fkGponOltStatsPonValidEthPacketsTx OBJECT-TYPE
                        SYNTAX Counter64
                        MAX-ACCESS read-only
                        STATUS current
                        DESCRIPTION
                                "DownStream(Tx)"
                        ::= { fkGponOltStatsEntry 5 }

                
--  1.3.6.1.4.1.10428 9 1.101.23.7.1.1.1.6
                -- 1.3.6.1.4.1.10428 9 1.101.23.7.1.1.1.6
                fkGponOltStatsPonCpuPacketsTx OBJECT-TYPE
                        SYNTAX Counter64
                        MAX-ACCESS read-only
                        STATUS current
                        DESCRIPTION
                                "DownStream(Tx)"
                        ::= { fkGponOltStatsEntry 6 }

                
--  1.3.6.1.4.1.10428 9 1.101.23.7.1.1.1.7
                -- 1.3.6.1.4.1.10428 9 1.101.23.7.1.1.1.7
                fkGponOltStatsPonPloamsTx OBJECT-TYPE
                        SYNTAX Counter64
                        MAX-ACCESS read-only
                        STATUS current
                        DESCRIPTION
                                "DownStream(Tx)"
                        ::= { fkGponOltStatsEntry 7 }

                
--  1.3.6.1.4.1.10428 9 1.101.23.7.1.1.1.8
                -- 1.3.6.1.4.1.10428 9 1.101.23.7.1.1.1.8
                fkGponOltStatsPonInvalidPacketsTx OBJECT-TYPE
                        SYNTAX Counter64
                        MAX-ACCESS read-only
                        STATUS current
                        DESCRIPTION
                                "N/A"
                        ::= { fkGponOltStatsEntry 8 }

                
--  1.3.6.1.4.1.10428 9 1.101.23.7.1.1.1.9
                -- 1.3.6.1.4.1.10428 9 1.101.23.7.1.1.1.9
                fkGponOltStatsPerfRxValidPackets OBJECT-TYPE
                        SYNTAX Counter64
                        MAX-ACCESS read-only
                        STATUS current
                        DESCRIPTION
                                "UpStream(Rx)"
                        ::= { fkGponOltStatsEntry 9 }

                
--  1.3.6.1.4.1.10428 9 1.101.23.7.1.1.1.10
                -- 1.3.6.1.4.1.10428 9 1.101.23.7.1.1.1.10
                fkGponOltStatsPerfRxErroredPackets OBJECT-TYPE
                        SYNTAX Counter64
                        MAX-ACCESS read-only
                        STATUS current
                        DESCRIPTION
                                "UpStream(Rx)"
                        ::= { fkGponOltStatsEntry 10 }

                
--  1.3.6.1.4.1.10428 9 1.101.23.7.1.1.1.11
                -- 1.3.6.1.4.1.10428 9 1.101.23.7.1.1.1.11
                fkGponOltStatsPerfCRCdroppedPackets OBJECT-TYPE
                        SYNTAX Counter64
                        MAX-ACCESS read-only
                        STATUS current
                        DESCRIPTION
                                "UpStream(Rx)"
                        ::= { fkGponOltStatsEntry 11 }

                
--  1.3.6.1.4.1.10428 9 1.101.23.7.1.2
                -- 1.3.6.1.4.1.10428 9 1.101.23.7.1.2
                fkGponOltStatsAllocTable OBJECT-TYPE
                        SYNTAX SEQUENCE OF FkGponOltStatsAllocEntry
                        MAX-ACCESS not-accessible
                        STATUS current
                        DESCRIPTION
                                "fkGponOltStatsAllocTable"
                        ::= { fkGponOltStatistics 2 }

                
--  1.3.6.1.4.1.10428 9 1.101.23.7.1.2.1
                -- 1.3.6.1.4.1.10428 9 1.101.23.7.1.2.1
                fkGponOltStatsAllocEntry OBJECT-TYPE
                        SYNTAX FkGponOltStatsAllocEntry
                        MAX-ACCESS not-accessible
                        STATUS current
                        DESCRIPTION
                                "key: fkGponOltId, fkGponOltStatsAllocId"
                        INDEX { fkGponOltId, fkGponOltStatsAllocId }
                        ::= { fkGponOltStatsAllocTable 1 }

                
                FkGponOltStatsAllocEntry ::=
                        SEQUENCE { 
                                fkGponOltStatsAllocId
                                        INTEGER,
                                fkGponOltStatsAllocDataRx
                                        Counter64
                         }

--  1.3.6.1.4.1.10428 9 1.101.23.7.1.2.1.1
                -- 1.3.6.1.4.1.10428 9 1.101.23.7.1.2.1.1
                fkGponOltStatsAllocId OBJECT-TYPE
                        SYNTAX INTEGER (256..1023)
                        MAX-ACCESS read-only
                        STATUS current
                        DESCRIPTION
                                "Alloc-Id"
                        ::= { fkGponOltStatsAllocEntry 1 }

                
--  1.3.6.1.4.1.10428 9 1.101.23.7.1.2.1.2
                -- 1.3.6.1.4.1.10428 9 1.101.23.7.1.2.1.2
                fkGponOltStatsAllocDataRx OBJECT-TYPE
                        SYNTAX Counter64
                        MAX-ACCESS read-only
                        STATUS current
                        DESCRIPTION
                                "The total value of received data in bytes per Alloc-Id."
                        ::= { fkGponOltStatsAllocEntry 2 }

                
--  1.3.6.1.4.1.10428 9 1.101.23.7.1.3
                -- 1.3.6.1.4.1.10428 9 1.101.23.7.1.3
                fkGponOltStatsOnuTable OBJECT-TYPE
                        SYNTAX SEQUENCE OF FkGponOltStatsOnuEntry
                        MAX-ACCESS not-accessible
                        STATUS current
                        DESCRIPTION
                                "fkGponOltStatsOnuTable"
                        ::= { fkGponOltStatistics 3 }

                
--  1.3.6.1.4.1.10428 9 1.101.23.7.1.3.1
                -- 1.3.6.1.4.1.10428 9 1.101.23.7.1.3.1
                fkGponOltStatsOnuEntry OBJECT-TYPE
                        SYNTAX FkGponOltStatsOnuEntry
                        MAX-ACCESS not-accessible
                        STATUS current
                        DESCRIPTION
                                "key: fkGponOltId, fkGponOnuId"
                        INDEX { fkGponOltId, fkGponOnuId }
                        ::= { fkGponOltStatsOnuTable 1 }

                
                FkGponOltStatsOnuEntry ::=
                        SEQUENCE { 
                                fkGponOltStatsOnuPonUnreceivedBursts
                                        Counter64,
                                fkGponOltStatsOnuPonPositiveDrift
                                        Counter64,
                                fkGponOltStatsOnuNegativeDrift
                                        Counter64,
                                fkGponOltStatsOnuPonBip8Errors
                                        Counter64,
                                fkGponOltStatsOnuPonFecCorrectedBytes
                                        Counter64,
                                fkGponOltStatsOnuPonFecUncorrectedCodewords
                                        Counter64,
                                fkGponOltStatsOnuPonFecCorrectedCodewords
                                        Counter64,
                                fkGponOltStatsOnuPonFecReceivedCodewords
                                        Counter64,
                                fkGponOltStatsOnuAlarmSf
                                        Counter32,
                                fkGponOltStatsOnuAlarmSd
                                        Counter32,
                                fkGponOltStatsOnuElapsedTimeAfterClear
                                        TimeTicks
                         }

--  1.3.6.1.4.1.10428 9 1.101.23.7.1.3.1.1
                -- 1.3.6.1.4.1.10428 9 1.101.23.7.1.3.1.1
                fkGponOltStatsOnuPonUnreceivedBursts OBJECT-TYPE
                        SYNTAX Counter64
                        MAX-ACCESS read-only
                        STATUS current
                        DESCRIPTION
                                "Returns the number of unreceived bursts per ONU-Id."
                        ::= { fkGponOltStatsOnuEntry 1 }

                
--  1.3.6.1.4.1.10428 9 1.101.23.7.1.3.1.2
                -- 1.3.6.1.4.1.10428 9 1.101.23.7.1.3.1.2
                fkGponOltStatsOnuPonPositiveDrift OBJECT-TYPE
                        SYNTAX Counter64
                        MAX-ACCESS read-only
                        STATUS current
                        DESCRIPTION
                                "Returns accumulated positive drifts value in bits."
                        ::= { fkGponOltStatsOnuEntry 2 }

                
--  1.3.6.1.4.1.10428 9 1.101.23.7.1.3.1.3
                -- 1.3.6.1.4.1.10428 9 1.101.23.7.1.3.1.3
                fkGponOltStatsOnuNegativeDrift OBJECT-TYPE
                        SYNTAX Counter64
                        MAX-ACCESS read-only
                        STATUS current
                        DESCRIPTION
                                "Returns accumulated negative drifts value in bits."
                        ::= { fkGponOltStatsOnuEntry 3 }

                
--  1.3.6.1.4.1.10428 9 1.101.23.7.1.3.1.4
                -- 1.3.6.1.4.1.10428 9 1.101.23.7.1.3.1.4
                fkGponOltStatsOnuPonBip8Errors OBJECT-TYPE
                        SYNTAX Counter64
                        MAX-ACCESS read-only
                        STATUS current
                        DESCRIPTION
                                "Returns the number of BIP8 errors."
                        ::= { fkGponOltStatsOnuEntry 4 }

                
--  1.3.6.1.4.1.10428 9 1.101.23.7.1.3.1.5
                -- 1.3.6.1.4.1.10428 9 1.101.23.7.1.3.1.5
                fkGponOltStatsOnuPonFecCorrectedBytes OBJECT-TYPE
                        SYNTAX Counter64
                        MAX-ACCESS read-only
                        STATUS current
                        DESCRIPTION
                                "Returns FEC Corrected Bytes statistics."
                        ::= { fkGponOltStatsOnuEntry 5 }

                
--  1.3.6.1.4.1.10428 9 1.101.23.7.1.3.1.6
                -- 1.3.6.1.4.1.10428 9 1.101.23.7.1.3.1.6
                fkGponOltStatsOnuPonFecUncorrectedCodewords OBJECT-TYPE
                        SYNTAX Counter64
                        MAX-ACCESS read-only
                        STATUS current
                        DESCRIPTION
                                "Returns FEC Corrected Codewords statistics."
                        ::= { fkGponOltStatsOnuEntry 6 }

                
--  1.3.6.1.4.1.10428 9 1.101.23.7.1.3.1.7
                -- 1.3.6.1.4.1.10428 9 1.101.23.7.1.3.1.7
                fkGponOltStatsOnuPonFecCorrectedCodewords OBJECT-TYPE
                        SYNTAX Counter64
                        MAX-ACCESS read-only
                        STATUS current
                        DESCRIPTION
                                "Returns FEC Uncorrectable Codewords statistics."
                        ::= { fkGponOltStatsOnuEntry 7 }

                
--  1.3.6.1.4.1.10428 9 1.101.23.7.1.3.1.8
                -- 1.3.6.1.4.1.10428 9 1.101.23.7.1.3.1.8
                fkGponOltStatsOnuPonFecReceivedCodewords OBJECT-TYPE
                        SYNTAX Counter64
                        MAX-ACCESS read-only
                        STATUS current
                        DESCRIPTION
                                "Returns FEC Total number of received Codewords statistics."
                        ::= { fkGponOltStatsOnuEntry 8 }

                
                -- 1.3.6.1.4.1.10428 9 1.101.23.7.1.3.1.9
                fkGponOltStatsOnuAlarmSf OBJECT-TYPE
                        SYNTAX Counter32
                        MAX-ACCESS read-only
                        STATUS current
                        DESCRIPTION
                                "The OLT statistics alarm SF counter"
                        ::= { fkGponOltStatsOnuEntry 9 }

                
                -- 1.3.6.1.4.1.10428 9 1.101.23.7.1.3.1.10
                fkGponOltStatsOnuAlarmSd OBJECT-TYPE
                        SYNTAX Counter32
                        MAX-ACCESS read-only
                        STATUS current
                        DESCRIPTION
                                "The OLT statistics alarm SD counter"
                        ::= { fkGponOltStatsOnuEntry 10 }

                
                -- 1.3.6.1.4.1.10428 9 1.101.23.7.1.3.1.11
                fkGponOltStatsOnuElapsedTimeAfterClear OBJECT-TYPE
                        SYNTAX TimeTicks
                        MAX-ACCESS read-only
                        STATUS current
                        DESCRIPTION
                                "The OLT statistics alarm elapsed time"
                        ::= { fkGponOltStatsOnuEntry 11 }

                
--  1.3.6.1.4.1.10428 9 1.101.23.7.1.4
                -- 1.3.6.1.4.1.10428 9 1.101.23.7.1.4
                fkGponOltStatsControl OBJECT IDENTIFIER ::= { fkGponOltStatistics 4 }

                
--  1.3.6.1.4.1.10428 9 1.101.23.7.1.4.1
                -- 1.3.6.1.4.1.10428 9 1.101.23.7.1.4.1
                fkGponOltStatsControlRequest OBJECT-TYPE
                        SYNTAX INTEGER { clearGponOltStatistics(1) }
                        MAX-ACCESS read-write
                        STATUS current
                        DESCRIPTION
                                "The request of a user command"
                        ::= { fkGponOltStatsControl 1 }

                
--  1.3.6.1.4.1.10428 9 1.101.23.7.1.4.2
                -- 1.3.6.1.4.1.10428 9 1.101.23.7.1.4.2
                fkGponOltStatsControlStatus OBJECT-TYPE
                        SYNTAX FkControlStatusType
                        MAX-ACCESS read-only
                        STATUS current
                        DESCRIPTION
                                "The status of user command"
                        ::= { fkGponOltStatsControl 2 }

                
--  1.3.6.1.4.1.10428 9 1.101.23.7.1.4.3
                -- 1.3.6.1.4.1.10428 9 1.101.23.7.1.4.3
                fkGponOltStatsControlTimer OBJECT-TYPE
                        SYNTAX Gauge32
                        MAX-ACCESS read-write
                        STATUS current
                        DESCRIPTION
                                "The maximum time for the manager for a long running user command"
                        ::= { fkGponOltStatsControl 3 }

                
--  1.3.6.1.4.1.10428 9 1.101.23.7.1.4.4
                -- 1.3.6.1.4.1.10428 9 1.101.23.7.1.4.4
                fkGponOltStatsControlTimeStamp OBJECT-TYPE
                        SYNTAX TimeTicks
                        MAX-ACCESS read-only
                        STATUS current
                        DESCRIPTION
                                "The time stamp of the last command(end of command)"
                        ::= { fkGponOltStatsControl 4 }

                
--  1.3.6.1.4.1.10428 9 1.101.23.7.1.4.5
                -- 1.3.6.1.4.1.10428 9 1.101.23.7.1.4.5
                fkGponOltStatsControlReqResult OBJECT-TYPE
                        SYNTAX FkControlRequestResultType
                        MAX-ACCESS read-only
                        STATUS current
                        DESCRIPTION
                                "The result of the last user command"
                        ::= { fkGponOltStatsControl 5 }

                
--  1.3.6.1.4.1.10428 9 1.101.23.7.1.4.6
                -- 1.3.6.1.4.1.10428 9 1.101.23.7.1.4.6
                fkGponOltStatsControlOltIndex OBJECT-TYPE
                        SYNTAX INTEGER (1..65535)
                        MAX-ACCESS read-write
                        STATUS current
                        DESCRIPTION
                                "Profile Id"
                        ::= { fkGponOltStatsControl 6 }

                
--  1.3.6.1.4.1.10428 9 1.101.23.7.1.4.7
                -- 1.3.6.1.4.1.10428 9 1.101.23.7.1.4.7
                fkGponOltStatsControlOnuIndex OBJECT-TYPE
                        SYNTAX INTEGER (1..65535)
                        MAX-ACCESS read-write
                        STATUS current
                        DESCRIPTION
                                "Profile Name"
                        ::= { fkGponOltStatsControl 7 }

                
--  1.3.6.1.4.1.10428 9 1.101.23.7.1.5
                -- 1.3.6.1.4.1.10428 9 1.101.23.7.1.5
                fkGponOltStatsNotification OBJECT IDENTIFIER ::= { fkGponOltStatistics 5 }

                
--  1.3.6.1.4.1.10428 9 1.101.23.7.1.5.1
                -- 1.3.6.1.4.1.10428 9 1.101.23.7.1.5.1
                fkGponOltStatsCleared NOTIFICATION-TYPE
                        OBJECTS { fkGponOltStatsControlRequest, fkGponOltStatsControlTimeStamp, fkGponOltStatsControlReqResult, fkGponOltStatsControlOltIndex }
                        STATUS current
                        DESCRIPTION 
                                "Description."
                        ::= { fkGponOltStatsNotification 1 }

                
--  1.3.6.1.4.1.10428 9 1.101.23.7.2
                -- 1.3.6.1.4.1.10428 9 1.101.23.7.2
                fkGponOnuPMStatistics OBJECT IDENTIFIER ::= { fkGponStatistics 2 }

                
--  1.3.6.1.4.1.10428 9 1.101.23.7.2.1
                -- 1.3.6.1.4.1.10428 9 1.101.23.7.2.1
                fkGponOnuPMStatsTable OBJECT-TYPE
                        SYNTAX SEQUENCE OF FkGponOnuPMStatsEntry
                        MAX-ACCESS not-accessible
                        STATUS current
                        DESCRIPTION
                                "fkGponOnuPMStatsTable"
                        ::= { fkGponOnuPMStatistics 1 }

                
--  1.3.6.1.4.1.10428 9 1.101.23.7.2.1.1
                -- 1.3.6.1.4.1.10428 9 1.101.23.7.2.1.1
                fkGponOnuPMStatsEntry OBJECT-TYPE
                        SYNTAX FkGponOnuPMStatsEntry
                        MAX-ACCESS not-accessible
                        STATUS current
                        DESCRIPTION
                                "key: fkGponOltId, fkGponOnuId"
                        INDEX { fkGponOltId, fkGponOnuId }
                        ::= { fkGponOnuPMStatsTable 1 }

                
                FkGponOnuPMStatsEntry ::=
                        SEQUENCE { 
                                fkGponOnuPMStatsPrev15mLostPackets
                                        Counter64,
                                fkGponOnuPMStatsPrev15mMisInsertedPackets
                                        Counter64,
                                fkGponOnuPMStatsPrev15mReceivedPackets
                                        Counter64,
                                fkGponOnuPMStatsPrev15mReceivedBlocks
                                        Counter64,
                                fkGponOnuPMStatsPrev15mTransmittedBlocks
                                        Counter64,
                                fkGponOnuPMStatsPrev15mImpairedBlocks
                                        Counter64,
                                fkGponOnuPMStatsPrev15mDiscardedFrames
                                        Counter64,
                                fkGponOnuPMStatsPrev30mLostPackets
                                        Counter64,
                                fkGponOnuPMStatsPrev30mMisInsertedPackets
                                        Counter64,
                                fkGponOnuPMStatsPrev30mReceivedPackets
                                        Counter64,
                                fkGponOnuPMStatsPrev30mReceivedBlocks
                                        Counter64,
                                fkGponOnuPMStatsPrev30mTransmittedBlocks
                                        Counter64,
                                fkGponOnuPMStatsPrev30mImpairedBlocks
                                        Counter64,
                                fkGponOnuPMStatsPrev30mDiscardedFrames
                                        Counter64,
                                fkGponOnuPMStatsTotalLostPackets
                                        Counter64,
                                fkGponOnuPMStatsTotalMisInsertedPackets
                                        Counter64,
                                fkGponOnuPMStatsTotalReceivedPackets
                                        Counter64,
                                fkGponOnuPMStatsTotalReceivedBlocks
                                        Counter64,
                                fkGponOnuPMStatsTotalTransmittedBlocks
                                        Counter64,
                                fkGponOnuPMStatsTotalImpairedBlocks
                                        Counter64,
                                fkGponOnuPMStatsTotalDiscardedFrames
                                        Counter64,
                                fkGponOnuPMStatsElapsedTimeAfterClear
                                        TimeTicks,
                                fkGponOnuPMStatsElapsedTimeAfterUpdate
                                        Counter64
                         }

--  1.3.6.1.4.1.10428 9 1.101.23.7.2.1.1.1
                -- 1.3.6.1.4.1.10428 9 1.101.23.7.2.1.1.1
                fkGponOnuPMStatsPrev15mLostPackets OBJECT-TYPE
                        SYNTAX Counter64
                        MAX-ACCESS read-only
                        STATUS current
                        DESCRIPTION
                                "This attribute counts background GEM frame loss."
                        ::= { fkGponOnuPMStatsEntry 1 }

                
--  1.3.6.1.4.1.10428 9 1.101.23.7.2.1.1.2
                -- 1.3.6.1.4.1.10428 9 1.101.23.7.2.1.1.2
                fkGponOnuPMStatsPrev15mMisInsertedPackets OBJECT-TYPE
                        SYNTAX Counter64
                        MAX-ACCESS read-only
                        STATUS current
                        DESCRIPTION
                                "This attribute counts GEM frames misrouted to this GEM port."
                        ::= { fkGponOnuPMStatsEntry 2 }

                
--  1.3.6.1.4.1.10428 9 1.101.23.7.2.1.1.3
                -- 1.3.6.1.4.1.10428 9 1.101.23.7.2.1.1.3
                fkGponOnuPMStatsPrev15mReceivedPackets OBJECT-TYPE
                        SYNTAX Counter64
                        MAX-ACCESS read-only
                        STATUS current
                        DESCRIPTION
                                "This attribute counts GEM frames that were received correctly at the monitored GEM port."
                        ::= { fkGponOnuPMStatsEntry 3 }

                
--  1.3.6.1.4.1.10428 9 1.101.23.7.2.1.1.4
                -- 1.3.6.1.4.1.10428 9 1.101.23.7.2.1.1.4
                fkGponOnuPMStatsPrev15mReceivedBlocks OBJECT-TYPE
                        SYNTAX Counter64
                        MAX-ACCESS read-only
                        STATUS current
                        DESCRIPTION
                                "This attribute counts GEM blocks that were received correctly at the monitored GEM port."
                        ::= { fkGponOnuPMStatsEntry 4 }

                
--  1.3.6.1.4.1.10428 9 1.101.23.7.2.1.1.5
                -- 1.3.6.1.4.1.10428 9 1.101.23.7.2.1.1.5
                fkGponOnuPMStatsPrev15mTransmittedBlocks OBJECT-TYPE
                        SYNTAX Counter64
                        MAX-ACCESS read-only
                        STATUS current
                        DESCRIPTION
                                "This attribute counts GEM blocks originated by the transmitting end point"
                        ::= { fkGponOnuPMStatsEntry 5 }

                
--  1.3.6.1.4.1.10428 9 1.101.23.7.2.1.1.6
                -- 1.3.6.1.4.1.10428 9 1.101.23.7.2.1.1.6
                fkGponOnuPMStatsPrev15mImpairedBlocks OBJECT-TYPE
                        SYNTAX Counter64
                        MAX-ACCESS read-only
                        STATUS current
                        DESCRIPTION
                                "This attribute counts GEM blocks originated by the number of misinserted packets reaches its threshold."
                        ::= { fkGponOnuPMStatsEntry 6 }

                
--  1.3.6.1.4.1.10428 9 1.101.23.7.2.1.1.7
                -- 1.3.6.1.4.1.10428 9 1.101.23.7.2.1.1.7
                fkGponOnuPMStatsPrev15mDiscardedFrames OBJECT-TYPE
                        SYNTAX Counter64
                        MAX-ACCESS read-only
                        STATUS current
                        DESCRIPTION
                                "This attribute counts the number of downstream GEM frames discarded for any reason (erroneous FCS, too long length, buffer overflow, etc)"
                        ::= { fkGponOnuPMStatsEntry 7 }

                
--  1.3.6.1.4.1.10428 9 1.101.23.7.2.1.1.8
                -- 1.3.6.1.4.1.10428 9 1.101.23.7.2.1.1.8
                fkGponOnuPMStatsPrev30mLostPackets OBJECT-TYPE
                        SYNTAX Counter64
                        MAX-ACCESS read-only
                        STATUS current
                        DESCRIPTION
                                "This attribute counts background GEM frame loss."
                        ::= { fkGponOnuPMStatsEntry 8 }

                
--  1.3.6.1.4.1.10428 9 1.101.23.7.2.1.1.9
                -- 1.3.6.1.4.1.10428 9 1.101.23.7.2.1.1.9
                fkGponOnuPMStatsPrev30mMisInsertedPackets OBJECT-TYPE
                        SYNTAX Counter64
                        MAX-ACCESS read-only
                        STATUS current
                        DESCRIPTION
                                "This attribute counts GEM frames misrouted to this GEM port."
                        ::= { fkGponOnuPMStatsEntry 9 }

                
--  1.3.6.1.4.1.10428 9 1.101.23.7.2.1.1.10
                -- 1.3.6.1.4.1.10428 9 1.101.23.7.2.1.1.10
                fkGponOnuPMStatsPrev30mReceivedPackets OBJECT-TYPE
                        SYNTAX Counter64
                        MAX-ACCESS read-only
                        STATUS current
                        DESCRIPTION
                                "This attribute counts GEM frames that were received correctly at the monitored GEM port."
                        ::= { fkGponOnuPMStatsEntry 10 }

                
--  1.3.6.1.4.1.10428 9 1.101.23.7.2.1.1.11
                -- 1.3.6.1.4.1.10428 9 1.101.23.7.2.1.1.11
                fkGponOnuPMStatsPrev30mReceivedBlocks OBJECT-TYPE
                        SYNTAX Counter64
                        MAX-ACCESS read-only
                        STATUS current
                        DESCRIPTION
                                "This attribute counts GEM blocks that were received correctly at the monitored GEM port."
                        ::= { fkGponOnuPMStatsEntry 11 }

                
--  1.3.6.1.4.1.10428 9 1.101.23.7.2.1.1.12
                -- 1.3.6.1.4.1.10428 9 1.101.23.7.2.1.1.12
                fkGponOnuPMStatsPrev30mTransmittedBlocks OBJECT-TYPE
                        SYNTAX Counter64
                        MAX-ACCESS read-only
                        STATUS current
                        DESCRIPTION
                                "This attribute counts GEM blocks originated by the transmitting end point"
                        ::= { fkGponOnuPMStatsEntry 12 }

                
--  1.3.6.1.4.1.10428 9 1.101.23.7.2.1.1.13
                -- 1.3.6.1.4.1.10428 9 1.101.23.7.2.1.1.13
                fkGponOnuPMStatsPrev30mImpairedBlocks OBJECT-TYPE
                        SYNTAX Counter64
                        MAX-ACCESS read-only
                        STATUS current
                        DESCRIPTION
                                "This attribute counts GEM blocks originated by the number of misinserted packets reaches its threshold."
                        ::= { fkGponOnuPMStatsEntry 13 }

                
--  1.3.6.1.4.1.10428 9 1.101.23.7.2.1.1.14
                -- 1.3.6.1.4.1.10428 9 1.101.23.7.2.1.1.14
                fkGponOnuPMStatsPrev30mDiscardedFrames OBJECT-TYPE
                        SYNTAX Counter64
                        MAX-ACCESS read-only
                        STATUS current
                        DESCRIPTION
                                "This attribute counts the number of downstream GEM frames discarded for any reason (erroneous FCS, too long length, buffer overflow, etc)"
                        ::= { fkGponOnuPMStatsEntry 14 }

                
--  1.3.6.1.4.1.10428 9 1.101.23.7.2.1.1.15
                -- 1.3.6.1.4.1.10428 9 1.101.23.7.2.1.1.15
                fkGponOnuPMStatsTotalLostPackets OBJECT-TYPE
                        SYNTAX Counter64
                        MAX-ACCESS read-only
                        STATUS current
                        DESCRIPTION
                                "This attribute counts background GEM frame loss."
                        ::= { fkGponOnuPMStatsEntry 15 }

                
--  1.3.6.1.4.1.10428 9 1.101.23.7.2.1.1.16
                -- 1.3.6.1.4.1.10428 9 1.101.23.7.2.1.1.16
                fkGponOnuPMStatsTotalMisInsertedPackets OBJECT-TYPE
                        SYNTAX Counter64
                        MAX-ACCESS read-only
                        STATUS current
                        DESCRIPTION
                                "This attribute counts GEM frames misrouted to this GEM port."
                        ::= { fkGponOnuPMStatsEntry 16 }

                
--  1.3.6.1.4.1.10428 9 1.101.23.7.2.1.1.17
                -- 1.3.6.1.4.1.10428 9 1.101.23.7.2.1.1.17
                fkGponOnuPMStatsTotalReceivedPackets OBJECT-TYPE
                        SYNTAX Counter64
                        MAX-ACCESS read-only
                        STATUS current
                        DESCRIPTION
                                "This attribute counts GEM frames that were received correctly at the monitored GEM port."
                        ::= { fkGponOnuPMStatsEntry 17 }

                
--  1.3.6.1.4.1.10428 9 1.101.23.7.2.1.1.18
                -- 1.3.6.1.4.1.10428 9 1.101.23.7.2.1.1.18
                fkGponOnuPMStatsTotalReceivedBlocks OBJECT-TYPE
                        SYNTAX Counter64
                        MAX-ACCESS read-only
                        STATUS current
                        DESCRIPTION
                                "This attribute counts GEM blocks that were received correctly at the monitored GEM port."
                        ::= { fkGponOnuPMStatsEntry 18 }

                
--  1.3.6.1.4.1.10428 9 1.101.23.7.2.1.1.19
                -- 1.3.6.1.4.1.10428 9 1.101.23.7.2.1.1.19
                fkGponOnuPMStatsTotalTransmittedBlocks OBJECT-TYPE
                        SYNTAX Counter64
                        MAX-ACCESS read-only
                        STATUS current
                        DESCRIPTION
                                "This attribute counts GEM blocks originated by the transmitting end point"
                        ::= { fkGponOnuPMStatsEntry 19 }

                
--  1.3.6.1.4.1.10428 9 1.101.23.7.2.1.1.20
                -- 1.3.6.1.4.1.10428 9 1.101.23.7.2.1.1.20
                fkGponOnuPMStatsTotalImpairedBlocks OBJECT-TYPE
                        SYNTAX Counter64
                        MAX-ACCESS read-only
                        STATUS current
                        DESCRIPTION
                                "This attribute counts GEM blocks originated by the number of misinserted packets reaches its threshold."
                        ::= { fkGponOnuPMStatsEntry 20 }

                
--  1.3.6.1.4.1.10428 9 1.101.23.7.2.1.1.21
                -- 1.3.6.1.4.1.10428 9 1.101.23.7.2.1.1.21
                fkGponOnuPMStatsTotalDiscardedFrames OBJECT-TYPE
                        SYNTAX Counter64
                        MAX-ACCESS read-only
                        STATUS current
                        DESCRIPTION
                                "This attribute counts the number of downstream GEM frames discarded for any reason (erroneous FCS, too long length, buffer overflow, etc)"
                        ::= { fkGponOnuPMStatsEntry 21 }

                
--  1.3.6.1.4.1.10428 9 1.101.23.7.2.1.1.22
                -- 1.3.6.1.4.1.10428 9 1.101.23.7.2.1.1.22
                fkGponOnuPMStatsElapsedTimeAfterClear OBJECT-TYPE
                        SYNTAX TimeTicks
                        MAX-ACCESS read-only
                        STATUS current
                        DESCRIPTION
                                "ONU PM counter  time after Clear "
                        ::= { fkGponOnuPMStatsEntry 22 }

                
--  1.3.6.1.4.1.10428 9 1.101.23.7.2.1.1.23
                -- 1.3.6.1.4.1.10428 9 1.101.23.7.2.1.1.23
                fkGponOnuPMStatsElapsedTimeAfterUpdate OBJECT-TYPE
                        SYNTAX Counter64
                        MAX-ACCESS read-only
                        STATUS current
                        DESCRIPTION
                                "ONU PM counter  time after update"
                        ::= { fkGponOnuPMStatsEntry 23 }

                
--  1.3.6.1.4.1.10428 9 1.101.23.7.2.2
                -- 1.3.6.1.4.1.10428 9 1.101.23.7.2.2
                fkGponOnuPMStatsControl OBJECT IDENTIFIER ::= { fkGponOnuPMStatistics 2 }

                
--  1.3.6.1.4.1.10428 9 1.101.23.7.2.2.1
                -- 1.3.6.1.4.1.10428 9 1.101.23.7.2.2.1
                fkGponOnuPMStatsControlRequest OBJECT-TYPE
                        SYNTAX INTEGER
                                {
                                clearPmStats(1),
                                setCurrentDetailStats(2)
                                }
                        MAX-ACCESS read-write
                        STATUS current
                        DESCRIPTION
                                "The request of a user command"
                        ::= { fkGponOnuPMStatsControl 1 }

                
--  1.3.6.1.4.1.10428 9 1.101.23.7.2.2.2
                -- 1.3.6.1.4.1.10428 9 1.101.23.7.2.2.2
                fkGponOnuPMStatsControlStatus OBJECT-TYPE
                        SYNTAX FkControlStatusType
                        MAX-ACCESS read-only
                        STATUS current
                        DESCRIPTION
                                "The status of user command"
                        ::= { fkGponOnuPMStatsControl 2 }

                
--  1.3.6.1.4.1.10428 9 1.101.23.7.2.2.3
                -- 1.3.6.1.4.1.10428 9 1.101.23.7.2.2.3
                fkGponOnuPMStatsControlTimer OBJECT-TYPE
                        SYNTAX Gauge32
                        MAX-ACCESS read-write
                        STATUS current
                        DESCRIPTION
                                "The maximum time for the manager for a long running user command"
                        ::= { fkGponOnuPMStatsControl 3 }

                
--  1.3.6.1.4.1.10428 9 1.101.23.7.2.2.4
                -- 1.3.6.1.4.1.10428 9 1.101.23.7.2.2.4
                fkGponOnuPMStatsControlTimeStamp OBJECT-TYPE
                        SYNTAX TimeTicks
                        MAX-ACCESS read-only
                        STATUS current
                        DESCRIPTION
                                "The time stamp of the last command(end of command)"
                        ::= { fkGponOnuPMStatsControl 4 }

                
--  1.3.6.1.4.1.10428 9 1.101.23.7.2.2.5
                -- 1.3.6.1.4.1.10428 9 1.101.23.7.2.2.5
                fkGponOnuPMStatsControlReqResult OBJECT-TYPE
                        SYNTAX FkControlRequestResultType
                        MAX-ACCESS read-only
                        STATUS current
                        DESCRIPTION
                                "The result of the last user command"
                        ::= { fkGponOnuPMStatsControl 5 }

                
--  1.3.6.1.4.1.10428 9 1.101.23.7.2.2.6
                -- 1.3.6.1.4.1.10428 9 1.101.23.7.2.2.6
                fkGponOnuPMStatsControlOltIndex OBJECT-TYPE
                        SYNTAX Integer32
                        MAX-ACCESS read-write
                        STATUS current
                        DESCRIPTION
                                "The OLT index."
                        ::= { fkGponOnuPMStatsControl 6 }

                
--  1.3.6.1.4.1.10428 9 1.101.23.7.2.2.7
                -- 1.3.6.1.4.1.10428 9 1.101.23.7.2.2.7
                fkGponOnuPMStatsControlOnuIndex OBJECT-TYPE
                        SYNTAX Integer32
                        MAX-ACCESS read-write
                        STATUS current
                        DESCRIPTION
                                "The result of the last user command"
                        ::= { fkGponOnuPMStatsControl 7 }

                
--  1.3.6.1.4.1.10428 9 1.101.23.7.2.3
                -- 1.3.6.1.4.1.10428 9 1.101.23.7.2.3
                fkGponOnuPMStatsNotification OBJECT IDENTIFIER ::= { fkGponOnuPMStatistics 3 }

                
--  1.3.6.1.4.1.10428 9 1.101.23.7.2.3.1
                -- 1.3.6.1.4.1.10428 9 1.101.23.7.2.3.1
                fkGponOnuPMStatsCleared NOTIFICATION-TYPE
                        OBJECTS { fkGponOnuPMStatsControlRequest, fkGponOnuPMStatsControlTimeStamp, fkGponOnuPMStatsControlReqResult, fkGponOnuPMStatsControlOltIndex, fkGponOnuPMStatsControlOnuIndex
                                 }
                        STATUS current
                        DESCRIPTION 
                                "Description."
                        ::= { fkGponOnuPMStatsNotification 1 }

                
--  1.3.6.1.4.1.10428 9 1.101.23.7.2.3.1
                -- 1.3.6.1.4.1.10428 9 1.101.23.7.2.3.2
                fkGponOnuPMStatsCurrentDetailChanged NOTIFICATION-TYPE
                        OBJECTS { fkGponOnuPMStatsControlRequest, fkGponOnuPMStatsControlTimeStamp, fkGponOnuPMStatsControlReqResult, fkGponOnuPMStatsControlOltIndex, fkGponOnuPMStatsControlOnuIndex
                                 }
                        STATUS current
                        DESCRIPTION 
                                "Description."
                        ::= { fkGponOnuPMStatsNotification 2 }

                
--  1.3.6.1.4.1.10428 9 1.101.23.7.3
                -- 1.3.6.1.4.1.10428 9 1.101.23.7.3
                fkGponOnuPMStatisticsDetail OBJECT IDENTIFIER ::= { fkGponStatistics 3 }

                
--  1.3.6.1.4.1.10428 9 1.101.23.7.3.1
                -- 1.3.6.1.4.1.10428 9 1.101.23.7.3.1
                fkGponOnuPMStatsDetailGEMTable OBJECT-TYPE
                        SYNTAX SEQUENCE OF FkGponOnuPMStatsDetailGEMEntry
                        MAX-ACCESS not-accessible
                        STATUS current
                        DESCRIPTION
                                "fkGponOnuPMStatsDetailGEMTable"
                        ::= { fkGponOnuPMStatisticsDetail 1 }

                
--  1.3.6.1.4.1.10428 9 1.101.23.7.3.1.1
                -- 1.3.6.1.4.1.10428 9 1.101.23.7.3.1.1
                fkGponOnuPMStatsDetailGEMEntry OBJECT-TYPE
                        SYNTAX FkGponOnuPMStatsDetailGEMEntry
                        MAX-ACCESS not-accessible
                        STATUS current
                        DESCRIPTION
                                "key: fkGponOnuPMStatsDetailGEMPort, fkGponOltId, fkGponOnuId"
                        INDEX { fkGponOltId, fkGponOnuId, fkGponOnuPMStatsDetailGEMPortIndex }
                        ::= { fkGponOnuPMStatsDetailGEMTable 1 }

                
                FkGponOnuPMStatsDetailGEMEntry ::=
                        SEQUENCE { 
                                fkGponOnuPMStatsDetailGEMPortIndex
                                        INTEGER,
                                fkGponOnuPMStatsDetailGEMPort
                                        INTEGER,
                                fkGponOnuPMStatsDetailGEMPre15mLostPackets
                                        Counter64,
                                fkGponOnuPMStatsDetailGEMPre15mMisInsertedPackets
                                        Counter64,
                                fkGponOnuPMStatsDetailGEMPre15mReceivedPackets
                                        Counter64,
                                fkGponOnuPMStatsDetailGEMPre15mReceivedBlocks
                                        Counter64,
                                fkGponOnuPMStatsDetailGEMPre15mTransmittedBlocks
                                        Counter64,
                                fkGponOnuPMStatsDetailGEMPre15mImpairedBlocks
                                        Counter64,
                                fkGponOnuPMStatsDetailGEMHourLostPackets
                                        Counter64,
                                fkGponOnuPMStatsDetailGEMHourMisInsertedPackets
                                        Counter64,
                                fkGponOnuPMStatsDetailGEMHourReceivedPackets
                                        Counter64,
                                fkGponOnuPMStatsDetailGEMHourReceivedBlocks
                                        Counter64,
                                fkGponOnuPMStatsDetailGEMHourTransmittedBlocks
                                        Counter64,
                                fkGponOnuPMStatsDetailGEMHourImpairedBlocks
                                        Counter64,
                                fkGponOnuPMStatsDetailGEMDayLostPackets
                                        Counter64,
                                fkGponOnuPMStatsDetailGEMDayMisInsertedPackets
                                        Counter64,
                                fkGponOnuPMStatsDetailGEMDayReceivedPackets
                                        Counter64,
                                fkGponOnuPMStatsDetailGEMDayReceivedBlocks
                                        Counter64,
                                fkGponOnuPMStatsDetailGEMDayTransmittedBlocks
                                        Counter64,
                                fkGponOnuPMStatsDetailGEMDayImpairedBlocks
                                        Counter64,
                                fkGponOnuPMStatsDetailGEMTotalLostPackets
                                        Counter64,
                                fkGponOnuPMStatsDetailGEMTotalMisInsertedPackets
                                        Counter64,
                                fkGponOnuPMStatsDetailGEMTotalReceivedPackets
                                        Counter64,
                                fkGponOnuPMStatsDetailGEMTotalReceivedBlocks
                                        Counter64,
                                fkGponOnuPMStatsDetailGEMTotalTransmittedBlocks
                                        Counter64,
                                fkGponOnuPMStatsDetailGEMTotalImpairedBlocks
                                        Counter64,
                                fkGponOnuPMStatsDetailGEMElapsedTimeAfterClear
                                        TimeTicks,
                                fkGponOnuPMStatsDetailGEMElapsedTimeAfterUpdate
                                        Counter64
                         }

                -- 1.3.6.1.4.1.10428 9 1.101.23.7.3.1.1.1
                fkGponOnuPMStatsDetailGEMPortIndex OBJECT-TYPE
                        SYNTAX INTEGER (1..65535)
                        MAX-ACCESS read-only
                        STATUS current
                        DESCRIPTION
                                "The GEM port index."
                        ::= { fkGponOnuPMStatsDetailGEMEntry 1 }

                
--  1.3.6.1.4.1.10428 9 1.101.23.7.3.1.1.1
                -- 1.3.6.1.4.1.10428 9 1.101.23.7.3.1.1.2
                fkGponOnuPMStatsDetailGEMPort OBJECT-TYPE
                        SYNTAX INTEGER (1..65535)
                        MAX-ACCESS read-only
                        STATUS current
                        DESCRIPTION
                                "The GEM port information"
                        ::= { fkGponOnuPMStatsDetailGEMEntry 2 }

                
--  1.3.6.1.4.1.10428 9 1.101.23.7.3.1.1.2
                -- 1.3.6.1.4.1.10428 9 1.101.23.7.3.1.1.3
                fkGponOnuPMStatsDetailGEMPre15mLostPackets OBJECT-TYPE
                        SYNTAX Counter64
                        MAX-ACCESS read-only
                        STATUS current
                        DESCRIPTION
                                "The pre 15 minute number of lost packet "
                        ::= { fkGponOnuPMStatsDetailGEMEntry 3 }

                
--  1.3.6.1.4.1.10428 9 1.101.23.7.3.1.1.3
                -- 1.3.6.1.4.1.10428 9 1.101.23.7.3.1.1.4
                fkGponOnuPMStatsDetailGEMPre15mMisInsertedPackets OBJECT-TYPE
                        SYNTAX Counter64
                        MAX-ACCESS read-only
                        STATUS current
                        DESCRIPTION
                                "The pre 15 minute number of mis inserted packet "
                        ::= { fkGponOnuPMStatsDetailGEMEntry 4 }

                
--  1.3.6.1.4.1.10428 9 1.101.23.7.3.1.1.4
                -- 1.3.6.1.4.1.10428 9 1.101.23.7.3.1.1.5
                fkGponOnuPMStatsDetailGEMPre15mReceivedPackets OBJECT-TYPE
                        SYNTAX Counter64
                        MAX-ACCESS read-only
                        STATUS current
                        DESCRIPTION
                                "The pre 15 minute number of received packet"
                        ::= { fkGponOnuPMStatsDetailGEMEntry 5 }

                
--  1.3.6.1.4.1.10428 9 1.101.23.7.3.1.1.5
                -- 1.3.6.1.4.1.10428 9 1.101.23.7.3.1.1.6
                fkGponOnuPMStatsDetailGEMPre15mReceivedBlocks OBJECT-TYPE
                        SYNTAX Counter64
                        MAX-ACCESS read-only
                        STATUS current
                        DESCRIPTION
                                "The pre 15 minute number of received blocks"
                        ::= { fkGponOnuPMStatsDetailGEMEntry 6 }

                
--  1.3.6.1.4.1.10428 9 1.101.23.7.3.1.1.6
                -- 1.3.6.1.4.1.10428 9 1.101.23.7.3.1.1.7
                fkGponOnuPMStatsDetailGEMPre15mTransmittedBlocks OBJECT-TYPE
                        SYNTAX Counter64
                        MAX-ACCESS read-only
                        STATUS current
                        DESCRIPTION
                                "The pre 15 minute number of transmitted blocks"
                        ::= { fkGponOnuPMStatsDetailGEMEntry 7 }

                
--  1.3.6.1.4.1.10428 9 1.101.23.7.3.1.1.7
                -- 1.3.6.1.4.1.10428 9 1.101.23.7.3.1.1.8
                fkGponOnuPMStatsDetailGEMPre15mImpairedBlocks OBJECT-TYPE
                        SYNTAX Counter64
                        MAX-ACCESS read-only
                        STATUS current
                        DESCRIPTION
                                "The pre 15 minute number of impaired blocks"
                        ::= { fkGponOnuPMStatsDetailGEMEntry 8 }

                
--  1.3.6.1.4.1.10428 9 1.101.23.7.3.1.1.8
                -- 1.3.6.1.4.1.10428 9 1.101.23.7.3.1.1.9
                fkGponOnuPMStatsDetailGEMHourLostPackets OBJECT-TYPE
                        SYNTAX Counter64
                        MAX-ACCESS read-only
                        STATUS current
                        DESCRIPTION
                                "The hour number of lost packet "
                        ::= { fkGponOnuPMStatsDetailGEMEntry 9 }

                
--  1.3.6.1.4.1.10428 9 1.101.23.7.3.1.1.9
                -- 1.3.6.1.4.1.10428 9 1.101.23.7.3.1.1.10
                fkGponOnuPMStatsDetailGEMHourMisInsertedPackets OBJECT-TYPE
                        SYNTAX Counter64
                        MAX-ACCESS read-only
                        STATUS current
                        DESCRIPTION
                                "The hour number of mis inserted packet "
                        ::= { fkGponOnuPMStatsDetailGEMEntry 10 }

                
--  1.3.6.1.4.1.10428 9 1.101.23.7.3.1.1.10
                -- 1.3.6.1.4.1.10428 9 1.101.23.7.3.1.1.11
                fkGponOnuPMStatsDetailGEMHourReceivedPackets OBJECT-TYPE
                        SYNTAX Counter64
                        MAX-ACCESS read-only
                        STATUS current
                        DESCRIPTION
                                "The hour number of received packet"
                        ::= { fkGponOnuPMStatsDetailGEMEntry 11 }

                
--  1.3.6.1.4.1.10428 9 1.101.23.7.3.1.1.11
                -- 1.3.6.1.4.1.10428 9 1.101.23.7.3.1.1.12
                fkGponOnuPMStatsDetailGEMHourReceivedBlocks OBJECT-TYPE
                        SYNTAX Counter64
                        MAX-ACCESS read-only
                        STATUS current
                        DESCRIPTION
                                "The hour number of received blocks"
                        ::= { fkGponOnuPMStatsDetailGEMEntry 12 }

                
--  1.3.6.1.4.1.10428 9 1.101.23.7.3.1.1.12
                -- 1.3.6.1.4.1.10428 9 1.101.23.7.3.1.1.13
                fkGponOnuPMStatsDetailGEMHourTransmittedBlocks OBJECT-TYPE
                        SYNTAX Counter64
                        MAX-ACCESS read-only
                        STATUS current
                        DESCRIPTION
                                "The hour number of transmitted blocks"
                        ::= { fkGponOnuPMStatsDetailGEMEntry 13 }

                
--  1.3.6.1.4.1.10428 9 1.101.23.7.3.1.1.13
                -- 1.3.6.1.4.1.10428 9 1.101.23.7.3.1.1.14
                fkGponOnuPMStatsDetailGEMHourImpairedBlocks OBJECT-TYPE
                        SYNTAX Counter64
                        MAX-ACCESS read-only
                        STATUS current
                        DESCRIPTION
                                "The hour number of impaired blocks"
                        ::= { fkGponOnuPMStatsDetailGEMEntry 14 }

                
--  1.3.6.1.4.1.10428 9 1.101.23.7.3.1.1.14
                -- 1.3.6.1.4.1.10428 9 1.101.23.7.3.1.1.15
                fkGponOnuPMStatsDetailGEMDayLostPackets OBJECT-TYPE
                        SYNTAX Counter64
                        MAX-ACCESS read-only
                        STATUS current
                        DESCRIPTION
                                "The day number of lost packet "
                        ::= { fkGponOnuPMStatsDetailGEMEntry 15 }

                
--  1.3.6.1.4.1.10428 9 1.101.23.7.3.1.1.15
                -- 1.3.6.1.4.1.10428 9 1.101.23.7.3.1.1.16
                fkGponOnuPMStatsDetailGEMDayMisInsertedPackets OBJECT-TYPE
                        SYNTAX Counter64
                        MAX-ACCESS read-only
                        STATUS current
                        DESCRIPTION
                                "The day number of mis inserted packet "
                        ::= { fkGponOnuPMStatsDetailGEMEntry 16 }

                
--  1.3.6.1.4.1.10428 9 1.101.23.7.3.1.1.16
                -- 1.3.6.1.4.1.10428 9 1.101.23.7.3.1.1.17
                fkGponOnuPMStatsDetailGEMDayReceivedPackets OBJECT-TYPE
                        SYNTAX Counter64
                        MAX-ACCESS read-only
                        STATUS current
                        DESCRIPTION
                                "The day number of received packet"
                        ::= { fkGponOnuPMStatsDetailGEMEntry 17 }

                
--  1.3.6.1.4.1.10428 9 1.101.23.7.3.1.1.17
                -- 1.3.6.1.4.1.10428 9 1.101.23.7.3.1.1.18
                fkGponOnuPMStatsDetailGEMDayReceivedBlocks OBJECT-TYPE
                        SYNTAX Counter64
                        MAX-ACCESS read-only
                        STATUS current
                        DESCRIPTION
                                "The day number of received blocks"
                        ::= { fkGponOnuPMStatsDetailGEMEntry 18 }

                
--  1.3.6.1.4.1.10428 9 1.101.23.7.3.1.1.18
                -- 1.3.6.1.4.1.10428 9 1.101.23.7.3.1.1.19
                fkGponOnuPMStatsDetailGEMDayTransmittedBlocks OBJECT-TYPE
                        SYNTAX Counter64
                        MAX-ACCESS read-only
                        STATUS current
                        DESCRIPTION
                                "The day number of transmitted blocks"
                        ::= { fkGponOnuPMStatsDetailGEMEntry 19 }

                
--  1.3.6.1.4.1.10428 9 1.101.23.7.3.1.1.19
                -- 1.3.6.1.4.1.10428 9 1.101.23.7.3.1.1.20
                fkGponOnuPMStatsDetailGEMDayImpairedBlocks OBJECT-TYPE
                        SYNTAX Counter64
                        MAX-ACCESS read-only
                        STATUS current
                        DESCRIPTION
                                "The day number of impaired blocks"
                        ::= { fkGponOnuPMStatsDetailGEMEntry 20 }

                
--  1.3.6.1.4.1.10428 9 1.101.23.7.3.1.1.20
                -- 1.3.6.1.4.1.10428 9 1.101.23.7.3.1.1.21
                fkGponOnuPMStatsDetailGEMTotalLostPackets OBJECT-TYPE
                        SYNTAX Counter64
                        MAX-ACCESS read-only
                        STATUS current
                        DESCRIPTION
                                "The total number of lost packet "
                        ::= { fkGponOnuPMStatsDetailGEMEntry 21 }

                
--  1.3.6.1.4.1.10428 9 1.101.23.7.3.1.1.21
                -- 1.3.6.1.4.1.10428 9 1.101.23.7.3.1.1.22
                fkGponOnuPMStatsDetailGEMTotalMisInsertedPackets OBJECT-TYPE
                        SYNTAX Counter64
                        MAX-ACCESS read-only
                        STATUS current
                        DESCRIPTION
                                "The total number of mis inserted packet "
                        ::= { fkGponOnuPMStatsDetailGEMEntry 22 }

                
--  1.3.6.1.4.1.10428 9 1.101.23.7.3.1.1.22
                -- 1.3.6.1.4.1.10428 9 1.101.23.7.3.1.1.23
                fkGponOnuPMStatsDetailGEMTotalReceivedPackets OBJECT-TYPE
                        SYNTAX Counter64
                        MAX-ACCESS read-only
                        STATUS current
                        DESCRIPTION
                                "The total number of received packet"
                        ::= { fkGponOnuPMStatsDetailGEMEntry 23 }

                
--  1.3.6.1.4.1.10428 9 1.101.23.7.3.1.1.23
                -- 1.3.6.1.4.1.10428 9 1.101.23.7.3.1.1.24
                fkGponOnuPMStatsDetailGEMTotalReceivedBlocks OBJECT-TYPE
                        SYNTAX Counter64
                        MAX-ACCESS read-only
                        STATUS current
                        DESCRIPTION
                                "The total number of received blocks"
                        ::= { fkGponOnuPMStatsDetailGEMEntry 24 }

                
--  1.3.6.1.4.1.10428 9 1.101.23.7.3.1.1.24
                -- 1.3.6.1.4.1.10428 9 1.101.23.7.3.1.1.25
                fkGponOnuPMStatsDetailGEMTotalTransmittedBlocks OBJECT-TYPE
                        SYNTAX Counter64
                        MAX-ACCESS read-only
                        STATUS current
                        DESCRIPTION
                                "The total number of transmitted blocks"
                        ::= { fkGponOnuPMStatsDetailGEMEntry 25 }

                
--  1.3.6.1.4.1.10428 9 1.101.23.7.3.1.1.25
                -- 1.3.6.1.4.1.10428 9 1.101.23.7.3.1.1.26
                fkGponOnuPMStatsDetailGEMTotalImpairedBlocks OBJECT-TYPE
                        SYNTAX Counter64
                        MAX-ACCESS read-only
                        STATUS current
                        DESCRIPTION
                                "The total number of impaired blocks"
                        ::= { fkGponOnuPMStatsDetailGEMEntry 26 }

                
--  1.3.6.1.4.1.10428 9 1.101.23.7.3.1.1.26
                -- 1.3.6.1.4.1.10428 9 1.101.23.7.3.1.1.27
                fkGponOnuPMStatsDetailGEMElapsedTimeAfterClear OBJECT-TYPE
                        SYNTAX TimeTicks
                        MAX-ACCESS read-only
                        STATUS current
                        DESCRIPTION
                                "The number of packets for elapsed time after clear"
                        ::= { fkGponOnuPMStatsDetailGEMEntry 27 }

                
--  1.3.6.1.4.1.10428 9 1.101.23.7.3.1.1.27
                -- 1.3.6.1.4.1.10428 9 1.101.23.7.3.1.1.28
                fkGponOnuPMStatsDetailGEMElapsedTimeAfterUpdate OBJECT-TYPE
                        SYNTAX Counter64
                        MAX-ACCESS read-only
                        STATUS current
                        DESCRIPTION
                                "The number of packets for elapsed time after update"
                        ::= { fkGponOnuPMStatsDetailGEMEntry 28 }

                
--  1.3.6.1.4.1.10428 9 1.101.23.7.3.2
                -- 1.3.6.1.4.1.10428 9 1.101.23.7.3.2
                fkGponOnuPMStatsDetailAniTable OBJECT-TYPE
                        SYNTAX SEQUENCE OF FkGponOnuPMStatsDetailAniEntry
                        MAX-ACCESS not-accessible
                        STATUS current
                        DESCRIPTION
                                "fkGponOnuPMStatsDetailAniTable"
                        ::= { fkGponOnuPMStatisticsDetail 2 }

                
--  1.3.6.1.4.1.10428 9 1.101.23.7.3.2.1
                -- 1.3.6.1.4.1.10428 9 1.101.23.7.3.2.1
                fkGponOnuPMStatsDetailAniEntry OBJECT-TYPE
                        SYNTAX FkGponOnuPMStatsDetailAniEntry
                        MAX-ACCESS not-accessible
                        STATUS current
                        DESCRIPTION
                                "key: fkGponOnuPMStatsDetailAniPort, fkGponOltId, fkGponOnuId"
                        INDEX { fkGponOltId, fkGponOnuId, fkGponOnuPMStatsDetailAniPortIndex }
                        ::= { fkGponOnuPMStatsDetailAniTable 1 }

                
                FkGponOnuPMStatsDetailAniEntry ::=
                        SEQUENCE { 
                                fkGponOnuPMStatsDetailAniPortIndex
                                        INTEGER,
                                fkGponOnuPMStatsDetailAniPort
                                        INTEGER,
                                fkGponOnuPMStatsDetailAniPre15mDiscardedFrames
                                        Counter64,
                                fkGponOnuPMStatsDetailAniHourDiscardedFrames
                                        Counter64,
                                fkGponOnuPMStatsDetailAniDayDiscardedFrames
                                        Counter64,
                                fkGponOnuPMStatsDetailAniTotalDiscardedFrames
                                        Counter64,
                                fkGponOnuPMStatsDetailAniElapsedTimeAfterClear
                                        TimeTicks,
                                fkGponOnuPMStatsDetailAniElapsedTimeAfterUpdate
                                        Counter64
                         }

                -- 1.3.6.1.4.1.10428 9 1.101.23.7.3.2.1.1
                fkGponOnuPMStatsDetailAniPortIndex OBJECT-TYPE
                        SYNTAX INTEGER (1..65535)
                        MAX-ACCESS read-only
                        STATUS current
                        DESCRIPTION
                                "The ANI port index."
                        ::= { fkGponOnuPMStatsDetailAniEntry 1 }

                
--  1.3.6.1.4.1.10428 9 1.101.23.7.3.2.1.1
                -- 1.3.6.1.4.1.10428 9 1.101.23.7.3.2.1.2
                fkGponOnuPMStatsDetailAniPort OBJECT-TYPE
                        SYNTAX INTEGER (1..65535)
                        MAX-ACCESS read-only
                        STATUS current
                        DESCRIPTION
                                "The Ani port information"
                        ::= { fkGponOnuPMStatsDetailAniEntry 2 }

                
--  1.3.6.1.4.1.10428 9 1.101.23.7.3.2.1.2
                -- 1.3.6.1.4.1.10428 9 1.101.23.7.3.2.1.3
                fkGponOnuPMStatsDetailAniPre15mDiscardedFrames OBJECT-TYPE
                        SYNTAX Counter64
                        MAX-ACCESS read-only
                        STATUS current
                        DESCRIPTION
                                "The pre 15 minute number of lost discarded frames"
                        ::= { fkGponOnuPMStatsDetailAniEntry 3 }

                
--  1.3.6.1.4.1.10428 9 1.101.23.7.3.2.1.3
                -- 1.3.6.1.4.1.10428 9 1.101.23.7.3.2.1.4
                fkGponOnuPMStatsDetailAniHourDiscardedFrames OBJECT-TYPE
                        SYNTAX Counter64
                        MAX-ACCESS read-only
                        STATUS current
                        DESCRIPTION
                                "The hour number of lost discarded frames"
                        ::= { fkGponOnuPMStatsDetailAniEntry 4 }

                
--  1.3.6.1.4.1.10428 9 1.101.23.7.3.2.1.4
                -- 1.3.6.1.4.1.10428 9 1.101.23.7.3.2.1.5
                fkGponOnuPMStatsDetailAniDayDiscardedFrames OBJECT-TYPE
                        SYNTAX Counter64
                        MAX-ACCESS read-only
                        STATUS current
                        DESCRIPTION
                                "The day number of lost discarded frames"
                        ::= { fkGponOnuPMStatsDetailAniEntry 5 }

                
--  1.3.6.1.4.1.10428 9 1.101.23.7.3.2.1.5
                -- 1.3.6.1.4.1.10428 9 1.101.23.7.3.2.1.6
                fkGponOnuPMStatsDetailAniTotalDiscardedFrames OBJECT-TYPE
                        SYNTAX Counter64
                        MAX-ACCESS read-only
                        STATUS current
                        DESCRIPTION
                                "The total number of lost discarded frames"
                        ::= { fkGponOnuPMStatsDetailAniEntry 6 }

                
--  1.3.6.1.4.1.10428 9 1.101.23.7.3.2.1.6
                -- 1.3.6.1.4.1.10428 9 1.101.23.7.3.2.1.7
                fkGponOnuPMStatsDetailAniElapsedTimeAfterClear OBJECT-TYPE
                        SYNTAX TimeTicks
                        MAX-ACCESS read-only
                        STATUS current
                        DESCRIPTION
                                "The number of packets for elapsed time after clear"
                        ::= { fkGponOnuPMStatsDetailAniEntry 7 }

                
--  1.3.6.1.4.1.10428 9 1.101.23.7.3.2.1.7
                -- 1.3.6.1.4.1.10428 9 1.101.23.7.3.2.1.8
                fkGponOnuPMStatsDetailAniElapsedTimeAfterUpdate OBJECT-TYPE
                        SYNTAX Counter64
                        MAX-ACCESS read-only
                        STATUS current
                        DESCRIPTION
                                "The number of packets for elapsed time after update"
                        ::= { fkGponOnuPMStatsDetailAniEntry 8 }

                
--  1.3.6.1.4.1.10428 9 1.101.23.7.3.3
                -- 1.3.6.1.4.1.10428 9 1.101.23.7.3.3
                fkGponOnuPMStatsDetailUniEthFrameUpTable OBJECT-TYPE
                        SYNTAX SEQUENCE OF FkGponOnuPMStatsDetailUniEthFrameUpEntry
                        MAX-ACCESS not-accessible
                        STATUS current
                        DESCRIPTION
                                "fkGponOnuPMStatsDetailUniEthFrameUpTable"
                        ::= { fkGponOnuPMStatisticsDetail 3 }

                
--  1.3.6.1.4.1.10428 9 1.101.23.7.3.3.1
                -- 1.3.6.1.4.1.10428 9 1.101.23.7.3.3.1
                fkGponOnuPMStatsDetailUniEthFrameUpEntry OBJECT-TYPE
                        SYNTAX FkGponOnuPMStatsDetailUniEthFrameUpEntry
                        MAX-ACCESS not-accessible
                        STATUS current
                        DESCRIPTION
                                "key: fkGponOltId, fkGponOnuId, fkGponOnuPMStatsDetailUniEthFrameUpUniPort"
                        INDEX { fkGponOltId, fkGponOnuId, fkGponOnuPMStatsDetailUniEthFrameUpUniPort }
                        ::= { fkGponOnuPMStatsDetailUniEthFrameUpTable 1 }

                
                FkGponOnuPMStatsDetailUniEthFrameUpEntry ::=
                        SEQUENCE { 
                                fkGponOnuPMStatsDetailUniEthFrameUpUniPort
                                        INTEGER,
                                fkGponOnuPMStatsDetailUniEthFrameUpPre15mDropEvents
                                        Counter64,
                                fkGponOnuPMStatsDetailUniEthFrameUpPre15mOctets
                                        Counter64,
                                fkGponOnuPMStatsDetailUniEthFrameUpPre15mPackets
                                        Counter64,
                                fkGponOnuPMStatsDetailUniEthFrameUpPre15mBcastPackets
                                        Counter64,
                                fkGponOnuPMStatsDetailUniEthFrameUpPre15mMcastPackets
                                        Counter64,
                                fkGponOnuPMStatsDetailUniEthFrameUpPre15mUcastPackets
                                        Counter64,
                                fkGponOnuPMStatsDetailUniEthFrameUpPre15mCRCErroredPackets
                                        Counter64,
                                fkGponOnuPMStatsDetailUniEthFrameUpPre15mUndersizePackets
                                        Counter64,
                                fkGponOnuPMStatsDetailUniEthFrameUpPre15mOversizePackets
                                        Counter64,
                                fkGponOnuPMStatsDetailUniEthFrameUpPre15mPkt64Octets
                                        Counter64,
                                fkGponOnuPMStatsDetailUniEthFrameUpPre15mPkt65To127Octets
                                        Counter64,
                                fkGponOnuPMStatsDetailUniEthFrameUpPre15mPkt128To255Octets
                                        Counter64,
                                fkGponOnuPMStatsDetailUniEthFrameUpPre15mPkt256To511Octets
                                        Counter64,
                                fkGponOnuPMStatsDetailUniEthFrameUpPre15mPkt512To1023Octets
                                        Counter64,
                                fkGponOnuPMStatsDetailUniEthFrameUpPre15mPkt1024To1518Octets
                                        Counter64,
                                fkGponOnuPMStatsDetailUniEthFrameUpHourDropEvents
                                        Counter64,
                                fkGponOnuPMStatsDetailUniEthFrameUpHourOctets
                                        Counter64,
                                fkGponOnuPMStatsDetailUniEthFrameUpHourPackets
                                        Counter64,
                                fkGponOnuPMStatsDetailUniEthFrameUpHourBcastPackets
                                        Counter64,
                                fkGponOnuPMStatsDetailUniEthFrameUpHourMcastPackets
                                        Counter64,
                                fkGponOnuPMStatsDetailUniEthFrameUpHourUcastPackets
                                        Counter64,
                                fkGponOnuPMStatsDetailUniEthFrameUpHourCRCErroredPackets
                                        Counter64,
                                fkGponOnuPMStatsDetailUniEthFrameUpHourUndersizePackets
                                        Counter64,
                                fkGponOnuPMStatsDetailUniEthFrameUpHourOversizePackets
                                        Counter64,
                                fkGponOnuPMStatsDetailUniEthFrameUpHourPkt64Octets
                                        Counter64,
                                fkGponOnuPMStatsDetailUniEthFrameUpHourPkt65To127Octets
                                        Counter64,
                                fkGponOnuPMStatsDetailUniEthFrameUpHourPkt128To255Octets
                                        Counter64,
                                fkGponOnuPMStatsDetailUniEthFrameUpHourPkt256To511Octets
                                        Counter64,
                                fkGponOnuPMStatsDetailUniEthFrameUpHourPkt512To1023Octets
                                        Counter64,
                                fkGponOnuPMStatsDetailUniEthFrameUpHourPkt1024To1518Octets
                                        Counter64,
                                fkGponOnuPMStatsDetailUniEthFrameUpDayDropEvents
                                        Counter64,
                                fkGponOnuPMStatsDetailUniEthFrameUpDayOctets
                                        Counter64,
                                fkGponOnuPMStatsDetailUniEthFrameUpDayPackets
                                        Counter64,
                                fkGponOnuPMStatsDetailUniEthFrameUpDayBcastPackets
                                        Counter64,
                                fkGponOnuPMStatsDetailUniEthFrameUpDayMcastPackets
                                        Counter64,
                                fkGponOnuPMStatsDetailUniEthFrameUpDayUcastPackets
                                        Counter64,
                                fkGponOnuPMStatsDetailUniEthFrameUpDayCRCErroredPackets
                                        Counter64,
                                fkGponOnuPMStatsDetailUniEthFrameUpDayUndersizePackets
                                        Counter64,
                                fkGponOnuPMStatsDetailUniEthFrameUpDayOversizePackets
                                        Counter64,
                                fkGponOnuPMStatsDetailUniEthFrameUpDayPkt64Octets
                                        Counter64,
                                fkGponOnuPMStatsDetailUniEthFrameUpDayPkt65To127Octets
                                        Counter64,
                                fkGponOnuPMStatsDetailUniEthFrameUpDayPkt128To255Octets
                                        Counter64,
                                fkGponOnuPMStatsDetailUniEthFrameUpDayPkt256To511Octets
                                        Counter64,
                                fkGponOnuPMStatsDetailUniEthFrameUpDayPkt512To1023Octets
                                        Counter64,
                                fkGponOnuPMStatsDetailUniEthFrameUpDayPkt1024To1518Octets
                                        Counter64,
                                fkGponOnuPMStatsDetailUniEthFrameUpTotalDropEvents
                                        Counter64,
                                fkGponOnuPMStatsDetailUniEthFrameUpTotalOctets
                                        Counter64,
                                fkGponOnuPMStatsDetailUniEthFrameUpTotalPackets
                                        Counter64,
                                fkGponOnuPMStatsDetailUniEthFrameUpTotalBcastPackets
                                        Counter64,
                                fkGponOnuPMStatsDetailUniEthFrameUpTotalMcastPackets
                                        Counter64,
                                fkGponOnuPMStatsDetailUniEthFrameUpTotalUcastPackets
                                        Counter64,
                                fkGponOnuPMStatsDetailUniEthFrameUpTotalCRCErroredPackets
                                        Counter64,
                                fkGponOnuPMStatsDetailUniEthFrameUpTotalUndersizePackets
                                        Counter64,
                                fkGponOnuPMStatsDetailUniEthFrameUpTotalOversizePackets
                                        Counter64,
                                fkGponOnuPMStatsDetailUniEthFrameUpTotalPkt64Octets
                                        Counter64,
                                fkGponOnuPMStatsDetailUniEthFrameUpTotalPkt65To127Octets
                                        Counter64,
                                fkGponOnuPMStatsDetailUniEthFrameUpTotalPkt128To255Octets
                                        Counter64,
                                fkGponOnuPMStatsDetailUniEthFrameUpTotalPkt256To511Octets
                                        Counter64,
                                fkGponOnuPMStatsDetailUniEthFrameUpTotalPkt512To1023Octets
                                        Counter64,
                                fkGponOnuPMStatsDetailUniEthFrameUpTotalPkt1024To1518Octets
                                        Counter64,
                                fkGponOnuPMStatsDetailUniEthFrameUpElapsedTimeAfterClear
                                        TimeTicks,
                                fkGponOnuPMStatsDetailUniEthFrameUpElapsedTimeAfterUpdate
                                        Counter64
                         }

--  1.3.6.1.4.1.10428 9 1.101.23.7.3.3.1.1
                -- 1.3.6.1.4.1.10428 9 1.101.23.7.3.3.1.1
                fkGponOnuPMStatsDetailUniEthFrameUpUniPort OBJECT-TYPE
                        SYNTAX INTEGER (1..65535)
                        MAX-ACCESS read-only
                        STATUS current
                        DESCRIPTION
                                "The Uni port information"
                        ::= { fkGponOnuPMStatsDetailUniEthFrameUpEntry 1 }

                
--  1.3.6.1.4.1.10428 9 1.101.23.7.3.3.1.2
                -- 1.3.6.1.4.1.10428 9 1.101.23.7.3.3.1.2
                fkGponOnuPMStatsDetailUniEthFrameUpPre15mDropEvents OBJECT-TYPE
                        SYNTAX Counter64
                        MAX-ACCESS read-only
                        STATUS current
                        DESCRIPTION
                                "The pre 15 minute number of events in which packets were dropped due to lack
                                of resources."
                        ::= { fkGponOnuPMStatsDetailUniEthFrameUpEntry 2 }

                
--  1.3.6.1.4.1.10428 9 1.101.23.7.3.3.1.3
                -- 1.3.6.1.4.1.10428 9 1.101.23.7.3.3.1.3
                fkGponOnuPMStatsDetailUniEthFrameUpPre15mOctets OBJECT-TYPE
                        SYNTAX Counter64
                        MAX-ACCESS read-only
                        STATUS current
                        DESCRIPTION
                                "The pre 15 minute number of octets received"
                        ::= { fkGponOnuPMStatsDetailUniEthFrameUpEntry 3 }

                
--  1.3.6.1.4.1.10428 9 1.101.23.7.3.3.1.4
                -- 1.3.6.1.4.1.10428 9 1.101.23.7.3.3.1.4
                fkGponOnuPMStatsDetailUniEthFrameUpPre15mPackets OBJECT-TYPE
                        SYNTAX Counter64
                        MAX-ACCESS read-only
                        STATUS current
                        DESCRIPTION
                                "The pre 15 minute number of packets received,"
                        ::= { fkGponOnuPMStatsDetailUniEthFrameUpEntry 4 }

                
--  1.3.6.1.4.1.10428 9 1.101.23.7.3.3.1.5
                -- 1.3.6.1.4.1.10428 9 1.101.23.7.3.3.1.5
                fkGponOnuPMStatsDetailUniEthFrameUpPre15mBcastPackets OBJECT-TYPE
                        SYNTAX Counter64
                        MAX-ACCESS read-only
                        STATUS current
                        DESCRIPTION
                                "The pre 15 minute number of received good packets directed to the broadcast address"
                        ::= { fkGponOnuPMStatsDetailUniEthFrameUpEntry 5 }

                
--  1.3.6.1.4.1.10428 9 1.101.23.7.3.3.1.6
                -- 1.3.6.1.4.1.10428 9 1.101.23.7.3.3.1.6
                fkGponOnuPMStatsDetailUniEthFrameUpPre15mMcastPackets OBJECT-TYPE
                        SYNTAX Counter64
                        MAX-ACCESS read-only
                        STATUS current
                        DESCRIPTION
                                "The pre 15 minute number of received good packets directed to a multicast address."
                        ::= { fkGponOnuPMStatsDetailUniEthFrameUpEntry 6 }

                
--  1.3.6.1.4.1.10428 9 1.101.23.7.3.3.1.7
                -- 1.3.6.1.4.1.10428 9 1.101.23.7.3.3.1.7
                fkGponOnuPMStatsDetailUniEthFrameUpPre15mUcastPackets OBJECT-TYPE
                        SYNTAX Counter64
                        MAX-ACCESS read-only
                        STATUS current
                        DESCRIPTION
                                "The pre 15 minute number of received good packets directed to the unicast address"
                        ::= { fkGponOnuPMStatsDetailUniEthFrameUpEntry 7 }

                
--  1.3.6.1.4.1.10428 9 1.101.23.7.3.3.1.8
                -- 1.3.6.1.4.1.10428 9 1.101.23.7.3.3.1.8
                fkGponOnuPMStatsDetailUniEthFrameUpPre15mCRCErroredPackets OBJECT-TYPE
                        SYNTAX Counter64
                        MAX-ACCESS read-only
                        STATUS current
                        DESCRIPTION
                                "The pre 15 minute number of packets received that had a length"
                        ::= { fkGponOnuPMStatsDetailUniEthFrameUpEntry 8 }

                
--  1.3.6.1.4.1.10428 9 1.101.23.7.3.3.1.9
                -- 1.3.6.1.4.1.10428 9 1.101.23.7.3.3.1.9
                fkGponOnuPMStatsDetailUniEthFrameUpPre15mUndersizePackets OBJECT-TYPE
                        SYNTAX Counter64
                        MAX-ACCESS read-only
                        STATUS current
                        DESCRIPTION
                                "The pre 15 minute number of packets received that were less than 64 octets long"
                        ::= { fkGponOnuPMStatsDetailUniEthFrameUpEntry 9 }

                
--  1.3.6.1.4.1.10428 9 1.101.23.7.3.3.1.10
                -- 1.3.6.1.4.1.10428 9 1.101.23.7.3.3.1.10
                fkGponOnuPMStatsDetailUniEthFrameUpPre15mOversizePackets OBJECT-TYPE
                        SYNTAX Counter64
                        MAX-ACCESS read-only
                        STATUS current
                        DESCRIPTION
                                "The pre 15 minute number of packets received that were longer than 1518 octets"
                        ::= { fkGponOnuPMStatsDetailUniEthFrameUpEntry 10 }

                
--  1.3.6.1.4.1.10428 9 1.101.23.7.3.3.1.11
                -- 1.3.6.1.4.1.10428 9 1.101.23.7.3.3.1.11
                fkGponOnuPMStatsDetailUniEthFrameUpPre15mPkt64Octets OBJECT-TYPE
                        SYNTAX Counter64
                        MAX-ACCESS read-only
                        STATUS current
                        DESCRIPTION
                                "The pre 15 minute number of received packets (including bad packets) that were
                                64 octets long,
                                "
                        ::= { fkGponOnuPMStatsDetailUniEthFrameUpEntry 11 }

                
--  1.3.6.1.4.1.10428 9 1.101.23.7.3.3.1.12
                -- 1.3.6.1.4.1.10428 9 1.101.23.7.3.3.1.12
                fkGponOnuPMStatsDetailUniEthFrameUpPre15mPkt65To127Octets OBJECT-TYPE
                        SYNTAX Counter64
                        MAX-ACCESS read-only
                        STATUS current
                        DESCRIPTION
                                "The pre 15 minute number of received packets (including bad packets) that were
                                65..127 octets long,
                                "
                        ::= { fkGponOnuPMStatsDetailUniEthFrameUpEntry 12 }

                
--  1.3.6.1.4.1.10428 9 1.101.23.7.3.3.1.13
                -- 1.3.6.1.4.1.10428 9 1.101.23.7.3.3.1.13
                fkGponOnuPMStatsDetailUniEthFrameUpPre15mPkt128To255Octets OBJECT-TYPE
                        SYNTAX Counter64
                        MAX-ACCESS read-only
                        STATUS current
                        DESCRIPTION
                                "The pre 15 minute number of packets (including bad packets) received that were
                                128..255 octets long,
                                "
                        ::= { fkGponOnuPMStatsDetailUniEthFrameUpEntry 13 }

                
--  1.3.6.1.4.1.10428 9 1.101.23.7.3.3.1.14
                -- 1.3.6.1.4.1.10428 9 1.101.23.7.3.3.1.14
                fkGponOnuPMStatsDetailUniEthFrameUpPre15mPkt256To511Octets OBJECT-TYPE
                        SYNTAX Counter64
                        MAX-ACCESS read-only
                        STATUS current
                        DESCRIPTION
                                "The pre 15 minute number of packets (including bad packets) received that were
                                256..511 octets long,
                                "
                        ::= { fkGponOnuPMStatsDetailUniEthFrameUpEntry 14 }

                
--  1.3.6.1.4.1.10428 9 1.101.23.7.3.3.1.15
                -- 1.3.6.1.4.1.10428 9 1.101.23.7.3.3.1.15
                fkGponOnuPMStatsDetailUniEthFrameUpPre15mPkt512To1023Octets OBJECT-TYPE
                        SYNTAX Counter64
                        MAX-ACCESS read-only
                        STATUS current
                        DESCRIPTION
                                "The pre 15 minute number of packets (including bad packets) received that were
                                512..1023 octets long,
                                "
                        ::= { fkGponOnuPMStatsDetailUniEthFrameUpEntry 15 }

                
--  1.3.6.1.4.1.10428 9 1.101.23.7.3.3.1.16
                -- 1.3.6.1.4.1.10428 9 1.101.23.7.3.3.1.16
                fkGponOnuPMStatsDetailUniEthFrameUpPre15mPkt1024To1518Octets OBJECT-TYPE
                        SYNTAX Counter64
                        MAX-ACCESS read-only
                        STATUS current
                        DESCRIPTION
                                "The pre 15 minute number of packets (including bad packets) received that were
                                1024..1518 octets long,
                                "
                        ::= { fkGponOnuPMStatsDetailUniEthFrameUpEntry 16 }

                
--  1.3.6.1.4.1.10428 9 1.101.23.7.3.3.1.17
                -- 1.3.6.1.4.1.10428 9 1.101.23.7.3.3.1.17
                fkGponOnuPMStatsDetailUniEthFrameUpHourDropEvents OBJECT-TYPE
                        SYNTAX Counter64
                        MAX-ACCESS read-only
                        STATUS current
                        DESCRIPTION
                                "The hour number of events in which packets were dropped due to lack
                                of resources.
                                "
                        ::= { fkGponOnuPMStatsDetailUniEthFrameUpEntry 17 }

                
--  1.3.6.1.4.1.10428 9 1.101.23.7.3.3.1.18
                -- 1.3.6.1.4.1.10428 9 1.101.23.7.3.3.1.18
                fkGponOnuPMStatsDetailUniEthFrameUpHourOctets OBJECT-TYPE
                        SYNTAX Counter64
                        MAX-ACCESS read-only
                        STATUS current
                        DESCRIPTION
                                "The hour number of octets received"
                        ::= { fkGponOnuPMStatsDetailUniEthFrameUpEntry 18 }

                
--  1.3.6.1.4.1.10428 9 1.101.23.7.3.3.1.19
                -- 1.3.6.1.4.1.10428 9 1.101.23.7.3.3.1.19
                fkGponOnuPMStatsDetailUniEthFrameUpHourPackets OBJECT-TYPE
                        SYNTAX Counter64
                        MAX-ACCESS read-only
                        STATUS current
                        DESCRIPTION
                                "The hour number of packets received,"
                        ::= { fkGponOnuPMStatsDetailUniEthFrameUpEntry 19 }

                
--  1.3.6.1.4.1.10428 9 1.101.23.7.3.3.1.20
                -- 1.3.6.1.4.1.10428 9 1.101.23.7.3.3.1.20
                fkGponOnuPMStatsDetailUniEthFrameUpHourBcastPackets OBJECT-TYPE
                        SYNTAX Counter64
                        MAX-ACCESS read-only
                        STATUS current
                        DESCRIPTION
                                "The hour number of received good packets directed to the broadcast address"
                        ::= { fkGponOnuPMStatsDetailUniEthFrameUpEntry 20 }

                
--  1.3.6.1.4.1.10428 9 1.101.23.7.3.3.1.21
                -- 1.3.6.1.4.1.10428 9 1.101.23.7.3.3.1.21
                fkGponOnuPMStatsDetailUniEthFrameUpHourMcastPackets OBJECT-TYPE
                        SYNTAX Counter64
                        MAX-ACCESS read-only
                        STATUS current
                        DESCRIPTION
                                "The hour number of received good packets directed to a multicast address."
                        ::= { fkGponOnuPMStatsDetailUniEthFrameUpEntry 21 }

                
--  1.3.6.1.4.1.10428 9 1.101.23.7.3.3.1.22
                -- 1.3.6.1.4.1.10428 9 1.101.23.7.3.3.1.22
                fkGponOnuPMStatsDetailUniEthFrameUpHourUcastPackets OBJECT-TYPE
                        SYNTAX Counter64
                        MAX-ACCESS read-only
                        STATUS current
                        DESCRIPTION
                                "The hour number of received good packets directed to the unicast address"
                        ::= { fkGponOnuPMStatsDetailUniEthFrameUpEntry 22 }

                
--  1.3.6.1.4.1.10428 9 1.101.23.7.3.3.1.23
                -- 1.3.6.1.4.1.10428 9 1.101.23.7.3.3.1.23
                fkGponOnuPMStatsDetailUniEthFrameUpHourCRCErroredPackets OBJECT-TYPE
                        SYNTAX Counter64
                        MAX-ACCESS read-only
                        STATUS current
                        DESCRIPTION
                                "The hour number of packets received that had a length"
                        ::= { fkGponOnuPMStatsDetailUniEthFrameUpEntry 23 }

                
--  1.3.6.1.4.1.10428 9 1.101.23.7.3.3.1.24
                -- 1.3.6.1.4.1.10428 9 1.101.23.7.3.3.1.24
                fkGponOnuPMStatsDetailUniEthFrameUpHourUndersizePackets OBJECT-TYPE
                        SYNTAX Counter64
                        MAX-ACCESS read-only
                        STATUS current
                        DESCRIPTION
                                "The hour number of packets received that were less than 64 octets long"
                        ::= { fkGponOnuPMStatsDetailUniEthFrameUpEntry 24 }

                
--  1.3.6.1.4.1.10428 9 1.101.23.7.3.3.1.25
                -- 1.3.6.1.4.1.10428 9 1.101.23.7.3.3.1.25
                fkGponOnuPMStatsDetailUniEthFrameUpHourOversizePackets OBJECT-TYPE
                        SYNTAX Counter64
                        MAX-ACCESS read-only
                        STATUS current
                        DESCRIPTION
                                "The hour number of packets received that were longer than 1518 octets"
                        ::= { fkGponOnuPMStatsDetailUniEthFrameUpEntry 25 }

                
--  1.3.6.1.4.1.10428 9 1.101.23.7.3.3.1.26
                -- 1.3.6.1.4.1.10428 9 1.101.23.7.3.3.1.26
                fkGponOnuPMStatsDetailUniEthFrameUpHourPkt64Octets OBJECT-TYPE
                        SYNTAX Counter64
                        MAX-ACCESS read-only
                        STATUS current
                        DESCRIPTION
                                "The hour number of received packets (including bad packets) that were
                                64 octets long,
                                "
                        ::= { fkGponOnuPMStatsDetailUniEthFrameUpEntry 26 }

                
--  1.3.6.1.4.1.10428 9 1.101.23.7.3.3.1.27
                -- 1.3.6.1.4.1.10428 9 1.101.23.7.3.3.1.27
                fkGponOnuPMStatsDetailUniEthFrameUpHourPkt65To127Octets OBJECT-TYPE
                        SYNTAX Counter64
                        MAX-ACCESS read-only
                        STATUS current
                        DESCRIPTION
                                "The hour number of received packets (including bad packets) that were
                                65..127 octets long,
                                "
                        ::= { fkGponOnuPMStatsDetailUniEthFrameUpEntry 27 }

                
--  1.3.6.1.4.1.10428 9 1.101.23.7.3.3.1.28
                -- 1.3.6.1.4.1.10428 9 1.101.23.7.3.3.1.28
                fkGponOnuPMStatsDetailUniEthFrameUpHourPkt128To255Octets OBJECT-TYPE
                        SYNTAX Counter64
                        MAX-ACCESS read-only
                        STATUS current
                        DESCRIPTION
                                "The hour number of packets (including bad packets) received that were
                                128..255 octets long,
                                "
                        ::= { fkGponOnuPMStatsDetailUniEthFrameUpEntry 28 }

                
--  1.3.6.1.4.1.10428 9 1.101.23.7.3.3.1.29
                -- 1.3.6.1.4.1.10428 9 1.101.23.7.3.3.1.29
                fkGponOnuPMStatsDetailUniEthFrameUpHourPkt256To511Octets OBJECT-TYPE
                        SYNTAX Counter64
                        MAX-ACCESS read-only
                        STATUS current
                        DESCRIPTION
                                "The hour number of packets (including bad packets) received that were
                                256..511 octets long,
                                "
                        ::= { fkGponOnuPMStatsDetailUniEthFrameUpEntry 29 }

                
--  1.3.6.1.4.1.10428 9 1.101.23.7.3.3.1.30
                -- 1.3.6.1.4.1.10428 9 1.101.23.7.3.3.1.30
                fkGponOnuPMStatsDetailUniEthFrameUpHourPkt512To1023Octets OBJECT-TYPE
                        SYNTAX Counter64
                        MAX-ACCESS read-only
                        STATUS current
                        DESCRIPTION
                                "The hour number of packets (including bad packets) received that were
                                512..1023 octets long,
                                "
                        ::= { fkGponOnuPMStatsDetailUniEthFrameUpEntry 30 }

                
--  1.3.6.1.4.1.10428 9 1.101.23.7.3.3.1.31
                -- 1.3.6.1.4.1.10428 9 1.101.23.7.3.3.1.31
                fkGponOnuPMStatsDetailUniEthFrameUpHourPkt1024To1518Octets OBJECT-TYPE
                        SYNTAX Counter64
                        MAX-ACCESS read-only
                        STATUS current
                        DESCRIPTION
                                "The hour number of packets (including bad packets) received that were
                                1024..1518 octets long,
                                
                                "
                        ::= { fkGponOnuPMStatsDetailUniEthFrameUpEntry 31 }

                
--  1.3.6.1.4.1.10428 9 1.101.23.7.3.3.1.32
                -- 1.3.6.1.4.1.10428 9 1.101.23.7.3.3.1.32
                fkGponOnuPMStatsDetailUniEthFrameUpDayDropEvents OBJECT-TYPE
                        SYNTAX Counter64
                        MAX-ACCESS read-only
                        STATUS current
                        DESCRIPTION
                                "The day number of events in which packets were dropped due to lack of resources."
                        ::= { fkGponOnuPMStatsDetailUniEthFrameUpEntry 32 }

                
--  1.3.6.1.4.1.10428 9 1.101.23.7.3.3.1.33
                -- 1.3.6.1.4.1.10428 9 1.101.23.7.3.3.1.33
                fkGponOnuPMStatsDetailUniEthFrameUpDayOctets OBJECT-TYPE
                        SYNTAX Counter64
                        MAX-ACCESS read-only
                        STATUS current
                        DESCRIPTION
                                "The day number of octets received"
                        ::= { fkGponOnuPMStatsDetailUniEthFrameUpEntry 33 }

                
--  1.3.6.1.4.1.10428 9 1.101.23.7.3.3.1.34
                -- 1.3.6.1.4.1.10428 9 1.101.23.7.3.3.1.34
                fkGponOnuPMStatsDetailUniEthFrameUpDayPackets OBJECT-TYPE
                        SYNTAX Counter64
                        MAX-ACCESS read-only
                        STATUS current
                        DESCRIPTION
                                "The day number of packets received,"
                        ::= { fkGponOnuPMStatsDetailUniEthFrameUpEntry 34 }

                
--  1.3.6.1.4.1.10428 9 1.101.23.7.3.3.1.35
                -- 1.3.6.1.4.1.10428 9 1.101.23.7.3.3.1.35
                fkGponOnuPMStatsDetailUniEthFrameUpDayBcastPackets OBJECT-TYPE
                        SYNTAX Counter64
                        MAX-ACCESS read-only
                        STATUS current
                        DESCRIPTION
                                "The day number of received good packets directed to the broadcast address"
                        ::= { fkGponOnuPMStatsDetailUniEthFrameUpEntry 35 }

                
--  1.3.6.1.4.1.10428 9 1.101.23.7.3.3.1.36
                -- 1.3.6.1.4.1.10428 9 1.101.23.7.3.3.1.36
                fkGponOnuPMStatsDetailUniEthFrameUpDayMcastPackets OBJECT-TYPE
                        SYNTAX Counter64
                        MAX-ACCESS read-only
                        STATUS current
                        DESCRIPTION
                                "The day number of received good packets directed to a multicast address."
                        ::= { fkGponOnuPMStatsDetailUniEthFrameUpEntry 36 }

                
--  1.3.6.1.4.1.10428 9 1.101.23.7.3.3.1.37
                -- 1.3.6.1.4.1.10428 9 1.101.23.7.3.3.1.37
                fkGponOnuPMStatsDetailUniEthFrameUpDayUcastPackets OBJECT-TYPE
                        SYNTAX Counter64
                        MAX-ACCESS read-only
                        STATUS current
                        DESCRIPTION
                                "The day number of received good packets directed to the unicast address"
                        ::= { fkGponOnuPMStatsDetailUniEthFrameUpEntry 37 }

                
--  1.3.6.1.4.1.10428 9 1.101.23.7.3.3.1.38
                -- 1.3.6.1.4.1.10428 9 1.101.23.7.3.3.1.38
                fkGponOnuPMStatsDetailUniEthFrameUpDayCRCErroredPackets OBJECT-TYPE
                        SYNTAX Counter64
                        MAX-ACCESS read-only
                        STATUS current
                        DESCRIPTION
                                "The day number of packets received that had a length"
                        ::= { fkGponOnuPMStatsDetailUniEthFrameUpEntry 38 }

                
--  1.3.6.1.4.1.10428 9 1.101.23.7.3.3.1.39
                -- 1.3.6.1.4.1.10428 9 1.101.23.7.3.3.1.39
                fkGponOnuPMStatsDetailUniEthFrameUpDayUndersizePackets OBJECT-TYPE
                        SYNTAX Counter64
                        MAX-ACCESS read-only
                        STATUS current
                        DESCRIPTION
                                "The day number of packets received that were less than 64 octets long"
                        ::= { fkGponOnuPMStatsDetailUniEthFrameUpEntry 39 }

                
--  1.3.6.1.4.1.10428 9 1.101.23.7.3.3.1.40
                -- 1.3.6.1.4.1.10428 9 1.101.23.7.3.3.1.40
                fkGponOnuPMStatsDetailUniEthFrameUpDayOversizePackets OBJECT-TYPE
                        SYNTAX Counter64
                        MAX-ACCESS read-only
                        STATUS current
                        DESCRIPTION
                                "The day number of packets received that were longer than 1518 octets"
                        ::= { fkGponOnuPMStatsDetailUniEthFrameUpEntry 40 }

                
--  1.3.6.1.4.1.10428 9 1.101.23.7.3.3.1.41
                -- 1.3.6.1.4.1.10428 9 1.101.23.7.3.3.1.41
                fkGponOnuPMStatsDetailUniEthFrameUpDayPkt64Octets OBJECT-TYPE
                        SYNTAX Counter64
                        MAX-ACCESS read-only
                        STATUS current
                        DESCRIPTION
                                "The day number of received packets (including bad packets) that were
                                64 octets long,
                                "
                        ::= { fkGponOnuPMStatsDetailUniEthFrameUpEntry 41 }

                
--  1.3.6.1.4.1.10428 9 1.101.23.7.3.3.1.42
                -- 1.3.6.1.4.1.10428 9 1.101.23.7.3.3.1.42
                fkGponOnuPMStatsDetailUniEthFrameUpDayPkt65To127Octets OBJECT-TYPE
                        SYNTAX Counter64
                        MAX-ACCESS read-only
                        STATUS current
                        DESCRIPTION
                                "The day number of received packets (including bad packets) that were
                                65..127 octets long,
                                "
                        ::= { fkGponOnuPMStatsDetailUniEthFrameUpEntry 42 }

                
--  1.3.6.1.4.1.10428 9 1.101.23.7.3.3.1.43
                -- 1.3.6.1.4.1.10428 9 1.101.23.7.3.3.1.43
                fkGponOnuPMStatsDetailUniEthFrameUpDayPkt128To255Octets OBJECT-TYPE
                        SYNTAX Counter64
                        MAX-ACCESS read-only
                        STATUS current
                        DESCRIPTION
                                "The day number of received packets (including bad packets) that were
                                128..255 octets long,
                                "
                        ::= { fkGponOnuPMStatsDetailUniEthFrameUpEntry 43 }

                
--  1.3.6.1.4.1.10428 9 1.101.23.7.3.3.1.44
                -- 1.3.6.1.4.1.10428 9 1.101.23.7.3.3.1.44
                fkGponOnuPMStatsDetailUniEthFrameUpDayPkt256To511Octets OBJECT-TYPE
                        SYNTAX Counter64
                        MAX-ACCESS read-only
                        STATUS current
                        DESCRIPTION
                                "The day number of received packets (including bad packets) that were
                                256..511 octets long,
                                "
                        ::= { fkGponOnuPMStatsDetailUniEthFrameUpEntry 44 }

                
--  1.3.6.1.4.1.10428 9 1.101.23.7.3.3.1.45
                -- 1.3.6.1.4.1.10428 9 1.101.23.7.3.3.1.45
                fkGponOnuPMStatsDetailUniEthFrameUpDayPkt512To1023Octets OBJECT-TYPE
                        SYNTAX Counter64
                        MAX-ACCESS read-only
                        STATUS current
                        DESCRIPTION
                                "The day number of packets (including bad packets) received that were
                                512..1023 octets long,
                                "
                        ::= { fkGponOnuPMStatsDetailUniEthFrameUpEntry 45 }

                
--  1.3.6.1.4.1.10428 9 1.101.23.7.3.3.1.46
                -- 1.3.6.1.4.1.10428 9 1.101.23.7.3.3.1.46
                fkGponOnuPMStatsDetailUniEthFrameUpDayPkt1024To1518Octets OBJECT-TYPE
                        SYNTAX Counter64
                        MAX-ACCESS read-only
                        STATUS current
                        DESCRIPTION
                                "The day number of packets (including bad packets) received that were
                                1024..1518 octets long,
                                "
                        ::= { fkGponOnuPMStatsDetailUniEthFrameUpEntry 46 }

                
--  1.3.6.1.4.1.10428 9 1.101.23.7.3.3.1.47
                -- 1.3.6.1.4.1.10428 9 1.101.23.7.3.3.1.47
                fkGponOnuPMStatsDetailUniEthFrameUpTotalDropEvents OBJECT-TYPE
                        SYNTAX Counter64
                        MAX-ACCESS read-only
                        STATUS current
                        DESCRIPTION
                                "The total number of events in which packets were dropped due to lack
                                of resources."
                        ::= { fkGponOnuPMStatsDetailUniEthFrameUpEntry 47 }

                
--  1.3.6.1.4.1.10428 9 1.101.23.7.3.3.1.48
                -- 1.3.6.1.4.1.10428 9 1.101.23.7.3.3.1.48
                fkGponOnuPMStatsDetailUniEthFrameUpTotalOctets OBJECT-TYPE
                        SYNTAX Counter64
                        MAX-ACCESS read-only
                        STATUS current
                        DESCRIPTION
                                "The total number of octets received"
                        ::= { fkGponOnuPMStatsDetailUniEthFrameUpEntry 48 }

                
--  1.3.6.1.4.1.10428 9 1.101.23.7.3.3.1.49
                -- 1.3.6.1.4.1.10428 9 1.101.23.7.3.3.1.49
                fkGponOnuPMStatsDetailUniEthFrameUpTotalPackets OBJECT-TYPE
                        SYNTAX Counter64
                        MAX-ACCESS read-only
                        STATUS current
                        DESCRIPTION
                                "The total number of packets received,"
                        ::= { fkGponOnuPMStatsDetailUniEthFrameUpEntry 49 }

                
--  1.3.6.1.4.1.10428 9 1.101.23.7.3.3.1.50
                -- 1.3.6.1.4.1.10428 9 1.101.23.7.3.3.1.50
                fkGponOnuPMStatsDetailUniEthFrameUpTotalBcastPackets OBJECT-TYPE
                        SYNTAX Counter64
                        MAX-ACCESS read-only
                        STATUS current
                        DESCRIPTION
                                "The total number of received good packets directed to a broadcast  address."
                        ::= { fkGponOnuPMStatsDetailUniEthFrameUpEntry 50 }

                
--  1.3.6.1.4.1.10428 9 1.101.23.7.3.3.1.51
                -- 1.3.6.1.4.1.10428 9 1.101.23.7.3.3.1.51
                fkGponOnuPMStatsDetailUniEthFrameUpTotalMcastPackets OBJECT-TYPE
                        SYNTAX Counter64
                        MAX-ACCESS read-only
                        STATUS current
                        DESCRIPTION
                                "The total number of received good packets directed to a multicast address."
                        ::= { fkGponOnuPMStatsDetailUniEthFrameUpEntry 51 }

                
--  1.3.6.1.4.1.10428 9 1.101.23.7.3.3.1.52
                -- 1.3.6.1.4.1.10428 9 1.101.23.7.3.3.1.52
                fkGponOnuPMStatsDetailUniEthFrameUpTotalUcastPackets OBJECT-TYPE
                        SYNTAX Counter64
                        MAX-ACCESS read-only
                        STATUS current
                        DESCRIPTION
                                "The total number of received good packets directed to a multicast address."
                        ::= { fkGponOnuPMStatsDetailUniEthFrameUpEntry 52 }

                
--  1.3.6.1.4.1.10428 9 1.101.23.7.3.3.1.53
                -- 1.3.6.1.4.1.10428 9 1.101.23.7.3.3.1.53
                fkGponOnuPMStatsDetailUniEthFrameUpTotalCRCErroredPackets OBJECT-TYPE
                        SYNTAX Counter64
                        MAX-ACCESS read-only
                        STATUS current
                        DESCRIPTION
                                "The total number of packets received that had a length"
                        ::= { fkGponOnuPMStatsDetailUniEthFrameUpEntry 53 }

                
--  1.3.6.1.4.1.10428 9 1.101.23.7.3.3.1.54
                -- 1.3.6.1.4.1.10428 9 1.101.23.7.3.3.1.54
                fkGponOnuPMStatsDetailUniEthFrameUpTotalUndersizePackets OBJECT-TYPE
                        SYNTAX Counter64
                        MAX-ACCESS read-only
                        STATUS current
                        DESCRIPTION
                                "The total number of packets received that were less than 64 octets long"
                        ::= { fkGponOnuPMStatsDetailUniEthFrameUpEntry 54 }

                
--  1.3.6.1.4.1.10428 9 1.101.23.7.3.3.1.55
                -- 1.3.6.1.4.1.10428 9 1.101.23.7.3.3.1.55
                fkGponOnuPMStatsDetailUniEthFrameUpTotalOversizePackets OBJECT-TYPE
                        SYNTAX Counter64
                        MAX-ACCESS read-only
                        STATUS current
                        DESCRIPTION
                                "The total number of packets received that were longer than 1518 octets"
                        ::= { fkGponOnuPMStatsDetailUniEthFrameUpEntry 55 }

                
--  1.3.6.1.4.1.10428 9 1.101.23.7.3.3.1.56
                -- 1.3.6.1.4.1.10428 9 1.101.23.7.3.3.1.56
                fkGponOnuPMStatsDetailUniEthFrameUpTotalPkt64Octets OBJECT-TYPE
                        SYNTAX Counter64
                        MAX-ACCESS read-only
                        STATUS current
                        DESCRIPTION
                                "The total number of received packets (including bad packets) that were
                                64 octets long,"
                        ::= { fkGponOnuPMStatsDetailUniEthFrameUpEntry 56 }

                
--  1.3.6.1.4.1.10428 9 1.101.23.7.3.3.1.57
                -- 1.3.6.1.4.1.10428 9 1.101.23.7.3.3.1.57
                fkGponOnuPMStatsDetailUniEthFrameUpTotalPkt65To127Octets OBJECT-TYPE
                        SYNTAX Counter64
                        MAX-ACCESS read-only
                        STATUS current
                        DESCRIPTION
                                "The total number of received packets (including bad packets) that were
                                65..127 octets long,"
                        ::= { fkGponOnuPMStatsDetailUniEthFrameUpEntry 57 }

                
--  1.3.6.1.4.1.10428 9 1.101.23.7.3.3.1.58
                -- 1.3.6.1.4.1.10428 9 1.101.23.7.3.3.1.58
                fkGponOnuPMStatsDetailUniEthFrameUpTotalPkt128To255Octets OBJECT-TYPE
                        SYNTAX Counter64
                        MAX-ACCESS read-only
                        STATUS current
                        DESCRIPTION
                                "The total number of packets (including bad packets) received that were
                                128..255 octets long,"
                        ::= { fkGponOnuPMStatsDetailUniEthFrameUpEntry 58 }

                
--  1.3.6.1.4.1.10428 9 1.101.23.7.3.3.1.59
                -- 1.3.6.1.4.1.10428 9 1.101.23.7.3.3.1.59
                fkGponOnuPMStatsDetailUniEthFrameUpTotalPkt256To511Octets OBJECT-TYPE
                        SYNTAX Counter64
                        MAX-ACCESS read-only
                        STATUS current
                        DESCRIPTION
                                "The total number of packets (including bad packets) received that were
                                256..511 octets long,"
                        ::= { fkGponOnuPMStatsDetailUniEthFrameUpEntry 59 }

                
--  1.3.6.1.4.1.10428 9 1.101.23.7.3.3.1.60
                -- 1.3.6.1.4.1.10428 9 1.101.23.7.3.3.1.60
                fkGponOnuPMStatsDetailUniEthFrameUpTotalPkt512To1023Octets OBJECT-TYPE
                        SYNTAX Counter64
                        MAX-ACCESS read-only
                        STATUS current
                        DESCRIPTION
                                "The total number of packets (including bad packets) received that were
                                512..1023 octets long,"
                        ::= { fkGponOnuPMStatsDetailUniEthFrameUpEntry 60 }

                
--  1.3.6.1.4.1.10428 9 1.101.23.7.3.3.1.61
                -- 1.3.6.1.4.1.10428 9 1.101.23.7.3.3.1.61
                fkGponOnuPMStatsDetailUniEthFrameUpTotalPkt1024To1518Octets OBJECT-TYPE
                        SYNTAX Counter64
                        MAX-ACCESS read-only
                        STATUS current
                        DESCRIPTION
                                "The total number of packets (including bad packets) received that were
                                1024..1518 octets long,"
                        ::= { fkGponOnuPMStatsDetailUniEthFrameUpEntry 61 }

                
--  1.3.6.1.4.1.10428 9 1.101.23.7.3.3.1.62
                -- 1.3.6.1.4.1.10428 9 1.101.23.7.3.3.1.62
                fkGponOnuPMStatsDetailUniEthFrameUpElapsedTimeAfterClear OBJECT-TYPE
                        SYNTAX TimeTicks
                        MAX-ACCESS read-only
                        STATUS current
                        DESCRIPTION
                                "The total number of packets for elapsed time after clear"
                        ::= { fkGponOnuPMStatsDetailUniEthFrameUpEntry 62 }

                
--  1.3.6.1.4.1.10428 9 1.101.23.7.3.3.1.63
                -- 1.3.6.1.4.1.10428 9 1.101.23.7.3.3.1.63
                fkGponOnuPMStatsDetailUniEthFrameUpElapsedTimeAfterUpdate OBJECT-TYPE
                        SYNTAX Counter64
                        MAX-ACCESS read-only
                        STATUS current
                        DESCRIPTION
                                "The total number of packets for elapsed time after update"
                        ::= { fkGponOnuPMStatsDetailUniEthFrameUpEntry 63 }

                
--  1.3.6.1.4.1.10428 9 1.101.23.7.3.4
                -- 1.3.6.1.4.1.10428 9 1.101.23.7.3.4
                fkGponOnuPMStatsDetailUniEthFrameDownTable OBJECT-TYPE
                        SYNTAX SEQUENCE OF FkGponOnuPMStatsDetailUniEthFrameDownEntry
                        MAX-ACCESS not-accessible
                        STATUS current
                        DESCRIPTION
                                "fkGponOnuPMStatsDetailUniEthFrameDownTable"
                        ::= { fkGponOnuPMStatisticsDetail 4 }

                
--  1.3.6.1.4.1.10428 9 1.101.23.7.3.4.1
                -- 1.3.6.1.4.1.10428 9 1.101.23.7.3.4.1
                fkGponOnuPMStatsDetailUniEthFrameDownEntry OBJECT-TYPE
                        SYNTAX FkGponOnuPMStatsDetailUniEthFrameDownEntry
                        MAX-ACCESS not-accessible
                        STATUS current
                        DESCRIPTION
                                "key: fkGponOltId, fkGponOnuId, fkGponOnuPMStatsDetailUniEthFrameUpUniPort"
                        INDEX { fkGponOltId, fkGponOnuId, fkGponOnuPMStatsDetailUniEthFrameUpUniPort }
                        ::= { fkGponOnuPMStatsDetailUniEthFrameDownTable 1 }

                
                FkGponOnuPMStatsDetailUniEthFrameDownEntry ::=
                        SEQUENCE { 
                                fkGponOnuPMStatsDetailUniEthFrameDownUniPort
                                        Integer32,
                                fkGponOnuPMStatsDetailUniEthFrameDownPre15mDropEvents
                                        Counter64,
                                fkGponOnuPMStatsDetailUniEthFrameDownPre15mOctets
                                        Counter64,
                                fkGponOnuPMStatsDetailUniEthFrameDownPre15mPackets
                                        Counter64,
                                fkGponOnuPMStatsDetailUniEthFrameDownPre15mBcastPackets
                                        Counter64,
                                fkGponOnuPMStatsDetailUniEthFrameDownPre15mMcastPackets
                                        Counter64,
                                fkGponOnuPMStatsDetailUniEthFrameDownPre15mUcastPackets
                                        Counter64,
                                fkGponOnuPMStatsDetailUniEthFrameDownPre15mCRCErroredPackets
                                        Counter64,
                                fkGponOnuPMStatsDetailUniEthFrameDownPre15mUndersizePackets
                                        Counter64,
                                fkGponOnuPMStatsDetailUniEthFrameDownPre15mOversizePackets
                                        Counter64,
                                fkGponOnuPMStatsDetailUniEthFrameDownPre15mPkt64Octets
                                        Counter64,
                                fkGponOnuPMStatsDetailUniEthFrameDownPre15mPkt65To127Octets
                                        Counter64,
                                fkGponOnuPMStatsDetailUniEthFrameDownPre15mPkt128To255Octets
                                        Counter64,
                                fkGponOnuPMStatsDetailUniEthFrameDownPre15mPkt256To511Octets
                                        Counter64,
                                fkGponOnuPMStatsDetailUniEthFrameDownPre15mPkt512To1023Octets
                                        Counter64,
                                fkGponOnuPMStatsDetailUniEthFrameDownPre15mPkt1024To1518Octets
                                        Counter64,
                                fkGponOnuPMStatsDetailUniEthFrameDownHourDropEvents
                                        Counter64,
                                fkGponOnuPMStatsDetailUniEthFrameDownHourOctets
                                        Counter64,
                                fkGponOnuPMStatsDetailUniEthFrameDownHourPackets
                                        Counter64,
                                fkGponOnuPMStatsDetailUniEthFrameDownHourBcastPackets
                                        Counter64,
                                fkGponOnuPMStatsDetailUniEthFrameDownHourMcastPackets
                                        Counter64,
                                fkGponOnuPMStatsDetailUniEthFrameDownHourUcastPackets
                                        Counter64,
                                fkGponOnuPMStatsDetailUniEthFrameDownHourCRCErroredPackets
                                        Counter64,
                                fkGponOnuPMStatsDetailUniEthFrameDownHourUndersizePackets
                                        Counter64,
                                fkGponOnuPMStatsDetailUniEthFrameDownHourOversizePackets
                                        Counter64,
                                fkGponOnuPMStatsDetailUniEthFrameDownHourPkt64Octets
                                        Counter64,
                                fkGponOnuPMStatsDetailUniEthFrameDownHourPkt65To127Octets
                                        Counter64,
                                fkGponOnuPMStatsDetailUniEthFrameDownHourPkt128To255Octets
                                        Counter64,
                                fkGponOnuPMStatsDetailUniEthFrameDownHourPkt256To511Octets
                                        Counter64,
                                fkGponOnuPMStatsDetailUniEthFrameDownHourPkt512To1023Octets
                                        Counter64,
                                fkGponOnuPMStatsDetailUniEthFrameDownHourPkt1024To1518Octets
                                        Counter64,
                                fkGponOnuPMStatsDetailUniEthFrameDownDayDropEvents
                                        Counter64,
                                fkGponOnuPMStatsDetailUniEthFrameDownDayOctets
                                        Counter64,
                                fkGponOnuPMStatsDetailUniEthFrameDownDayPackets
                                        Counter64,
                                fkGponOnuPMStatsDetailUniEthFrameDownDayBcastPackets
                                        Counter64,
                                fkGponOnuPMStatsDetailUniEthFrameDownDayMcastPackets
                                        Counter64,
                                fkGponOnuPMStatsDetailUniEthFrameDownDayUcastPackets
                                        Counter64,
                                fkGponOnuPMStatsDetailUniEthFrameDownDayCRCErroredPackets
                                        Counter64,
                                fkGponOnuPMStatsDetailUniEthFrameDownDayUndersizePackets
                                        Counter64,
                                fkGponOnuPMStatsDetailUniEthFrameDownDayOversizePackets
                                        Counter64,
                                fkGponOnuPMStatsDetailUniEthFrameDownDayPkt64Octets
                                        Counter64,
                                fkGponOnuPMStatsDetailUniEthFrameDownDayPkt65To127Octets
                                        Counter64,
                                fkGponOnuPMStatsDetailUniEthFrameDownDayPkt128To255Octets
                                        Counter64,
                                fkGponOnuPMStatsDetailUniEthFrameDownDayPkt256To511Octets
                                        Counter64,
                                fkGponOnuPMStatsDetailUniEthFrameDownDayPkt512To1023Octets
                                        Counter64,
                                fkGponOnuPMStatsDetailUniEthFrameDownDayPkt1024To1518Octets
                                        Counter64,
                                fkGponOnuPMStatsDetailUniEthFrameDownTotalDropEvents
                                        Counter64,
                                fkGponOnuPMStatsDetailUniEthFrameDownTotalOctets
                                        Counter64,
                                fkGponOnuPMStatsDetailUniEthFrameDownTotalPackets
                                        Counter64,
                                fkGponOnuPMStatsDetailUniEthFrameDownTotalBcastPackets
                                        Counter64,
                                fkGponOnuPMStatsDetailUniEthFrameDownTotalMcastPackets
                                        Counter64,
                                fkGponOnuPMStatsDetailUniEthFrameDownTotalUcastPackets
                                        Counter64,
                                fkGponOnuPMStatsDetailUniEthFrameDownTotalCRCErroredPackets
                                        Counter64,
                                fkGponOnuPMStatsDetailUniEthFrameDownTotalUndersizePackets
                                        Counter64,
                                fkGponOnuPMStatsDetailUniEthFrameDownTotalOversizePackets
                                        Counter64,
                                fkGponOnuPMStatsDetailUniEthFrameDownTotalPkt64Octets
                                        Counter64,
                                fkGponOnuPMStatsDetailUniEthFrameDownTotalPkt65To127Octets
                                        Counter64,
                                fkGponOnuPMStatsDetailUniEthFrameDownTotalPkt128To255Octets
                                        Counter64,
                                fkGponOnuPMStatsDetailUniEthFrameDownTotalPkt256To511Octets
                                        Counter64,
                                fkGponOnuPMStatsDetailUniEthFrameDownTotalPkt512To1023Octets
                                        Counter64,
                                fkGponOnuPMStatsDetailUniEthFrameDownTotalPkt1024To1518Octets
                                        Counter64,
                                fkGponOnuPMStatsDetailUniEthFrameDownElapsedTimeAfterClear
                                        TimeTicks,
                                fkGponOnuPMStatsDetailUniEthFrameDownElapsedTimeAfterUpdate
                                        Counter64
                         }

--  1.3.6.1.4.1.10428 9 1.101.23.7.3.4.1.1
                -- 1.3.6.1.4.1.10428 9 1.101.23.7.3.4.1.1
                fkGponOnuPMStatsDetailUniEthFrameDownUniPort OBJECT-TYPE
                        SYNTAX Integer32
                        MAX-ACCESS read-only
                        STATUS current
                        DESCRIPTION
                                "fkGponOltId, fkGponOnuId, fkGponOnuPMStatsDetailUniEthFrameUpUniPort"
                        ::= { fkGponOnuPMStatsDetailUniEthFrameDownEntry 1 }

                
--  1.3.6.1.4.1.10428 9 1.101.23.7.3.4.1.2
                -- 1.3.6.1.4.1.10428 9 1.101.23.7.3.4.1.2
                fkGponOnuPMStatsDetailUniEthFrameDownPre15mDropEvents OBJECT-TYPE
                        SYNTAX Counter64
                        MAX-ACCESS read-only
                        STATUS current
                        DESCRIPTION
                                "The pre 15 minute number of events in which packets were dropped due to lack of resources.
                                "
                        ::= { fkGponOnuPMStatsDetailUniEthFrameDownEntry 2 }

                
--  1.3.6.1.4.1.10428 9 1.101.23.7.3.4.1.3
                -- 1.3.6.1.4.1.10428 9 1.101.23.7.3.4.1.3
                fkGponOnuPMStatsDetailUniEthFrameDownPre15mOctets OBJECT-TYPE
                        SYNTAX Counter64
                        MAX-ACCESS read-only
                        STATUS current
                        DESCRIPTION
                                "The pre 15 minute number of octets received"
                        ::= { fkGponOnuPMStatsDetailUniEthFrameDownEntry 3 }

                
--  1.3.6.1.4.1.10428 9 1.101.23.7.3.4.1.4
                -- 1.3.6.1.4.1.10428 9 1.101.23.7.3.4.1.4
                fkGponOnuPMStatsDetailUniEthFrameDownPre15mPackets OBJECT-TYPE
                        SYNTAX Counter64
                        MAX-ACCESS read-only
                        STATUS current
                        DESCRIPTION
                                "The pre 15 minute number of packets received,"
                        ::= { fkGponOnuPMStatsDetailUniEthFrameDownEntry 4 }

                
--  1.3.6.1.4.1.10428 9 1.101.23.7.3.4.1.5
                -- 1.3.6.1.4.1.10428 9 1.101.23.7.3.4.1.5
                fkGponOnuPMStatsDetailUniEthFrameDownPre15mBcastPackets OBJECT-TYPE
                        SYNTAX Counter64
                        MAX-ACCESS read-only
                        STATUS current
                        DESCRIPTION
                                "The pre 15 minute number of received good packets directed to the broadcast address"
                        ::= { fkGponOnuPMStatsDetailUniEthFrameDownEntry 5 }

                
--  1.3.6.1.4.1.10428 9 1.101.23.7.3.4.1.6
                -- 1.3.6.1.4.1.10428 9 1.101.23.7.3.4.1.6
                fkGponOnuPMStatsDetailUniEthFrameDownPre15mMcastPackets OBJECT-TYPE
                        SYNTAX Counter64
                        MAX-ACCESS read-only
                        STATUS current
                        DESCRIPTION
                                "The pre 15 minute number of received good packets directed to a multicast address."
                        ::= { fkGponOnuPMStatsDetailUniEthFrameDownEntry 6 }

                
--  1.3.6.1.4.1.10428 9 1.101.23.7.3.4.1.7
                -- 1.3.6.1.4.1.10428 9 1.101.23.7.3.4.1.7
                fkGponOnuPMStatsDetailUniEthFrameDownPre15mUcastPackets OBJECT-TYPE
                        SYNTAX Counter64
                        MAX-ACCESS read-only
                        STATUS current
                        DESCRIPTION
                                "The pre 15 minute number of received good packets directed to the unicast address"
                        ::= { fkGponOnuPMStatsDetailUniEthFrameDownEntry 7 }

                
--  1.3.6.1.4.1.10428 9 1.101.23.7.3.4.1.8
                -- 1.3.6.1.4.1.10428 9 1.101.23.7.3.4.1.8
                fkGponOnuPMStatsDetailUniEthFrameDownPre15mCRCErroredPackets OBJECT-TYPE
                        SYNTAX Counter64
                        MAX-ACCESS read-only
                        STATUS current
                        DESCRIPTION
                                "The pre 15 minute number of packets received that had a length"
                        ::= { fkGponOnuPMStatsDetailUniEthFrameDownEntry 8 }

                
--  1.3.6.1.4.1.10428 9 1.101.23.7.3.4.1.9
                -- 1.3.6.1.4.1.10428 9 1.101.23.7.3.4.1.9
                fkGponOnuPMStatsDetailUniEthFrameDownPre15mUndersizePackets OBJECT-TYPE
                        SYNTAX Counter64
                        MAX-ACCESS read-only
                        STATUS current
                        DESCRIPTION
                                "The pre 15 minute number of packets received that were less than 64 octets long"
                        ::= { fkGponOnuPMStatsDetailUniEthFrameDownEntry 9 }

                
--  1.3.6.1.4.1.10428 9 1.101.23.7.3.4.1.10
                -- 1.3.6.1.4.1.10428 9 1.101.23.7.3.4.1.10
                fkGponOnuPMStatsDetailUniEthFrameDownPre15mOversizePackets OBJECT-TYPE
                        SYNTAX Counter64
                        MAX-ACCESS read-only
                        STATUS current
                        DESCRIPTION
                                "The pre 15 minute number of packets received that were longer than 1518 octets"
                        ::= { fkGponOnuPMStatsDetailUniEthFrameDownEntry 10 }

                
--  1.3.6.1.4.1.10428 9 1.101.23.7.3.4.1.11
                -- 1.3.6.1.4.1.10428 9 1.101.23.7.3.4.1.11
                fkGponOnuPMStatsDetailUniEthFrameDownPre15mPkt64Octets OBJECT-TYPE
                        SYNTAX Counter64
                        MAX-ACCESS read-only
                        STATUS current
                        DESCRIPTION
                                "The pre 15 minute number of received packets (including bad packets) that were
                                64 octets long,"
                        ::= { fkGponOnuPMStatsDetailUniEthFrameDownEntry 11 }

                
--  1.3.6.1.4.1.10428 9 1.101.23.7.3.4.1.12
                -- 1.3.6.1.4.1.10428 9 1.101.23.7.3.4.1.12
                fkGponOnuPMStatsDetailUniEthFrameDownPre15mPkt65To127Octets OBJECT-TYPE
                        SYNTAX Counter64
                        MAX-ACCESS read-only
                        STATUS current
                        DESCRIPTION
                                "The pre 15 minute number of received packets (including bad packets) that were
                                65..127 octets long,"
                        ::= { fkGponOnuPMStatsDetailUniEthFrameDownEntry 12 }

                
--  1.3.6.1.4.1.10428 9 1.101.23.7.3.4.1.13
                -- 1.3.6.1.4.1.10428 9 1.101.23.7.3.4.1.13
                fkGponOnuPMStatsDetailUniEthFrameDownPre15mPkt128To255Octets OBJECT-TYPE
                        SYNTAX Counter64
                        MAX-ACCESS read-only
                        STATUS current
                        DESCRIPTION
                                "The pre 15 minute number of packets (including bad packets) received that were
                                128..255 octets long,"
                        ::= { fkGponOnuPMStatsDetailUniEthFrameDownEntry 13 }

                
--  1.3.6.1.4.1.10428 9 1.101.23.7.3.4.1.14
                -- 1.3.6.1.4.1.10428 9 1.101.23.7.3.4.1.14
                fkGponOnuPMStatsDetailUniEthFrameDownPre15mPkt256To511Octets OBJECT-TYPE
                        SYNTAX Counter64
                        MAX-ACCESS read-only
                        STATUS current
                        DESCRIPTION
                                "The pre 15 minute number of packets (including bad packets) received that were
                                256..511 octets long,"
                        ::= { fkGponOnuPMStatsDetailUniEthFrameDownEntry 14 }

                
--  1.3.6.1.4.1.10428 9 1.101.23.7.3.4.1.15
                -- 1.3.6.1.4.1.10428 9 1.101.23.7.3.4.1.15
                fkGponOnuPMStatsDetailUniEthFrameDownPre15mPkt512To1023Octets OBJECT-TYPE
                        SYNTAX Counter64
                        MAX-ACCESS read-only
                        STATUS current
                        DESCRIPTION
                                "The pre 15 minute number of packets (including bad packets) received that were
                                512..1023 octets long,"
                        ::= { fkGponOnuPMStatsDetailUniEthFrameDownEntry 15 }

                
--  1.3.6.1.4.1.10428 9 1.101.23.7.3.4.1.16
                -- 1.3.6.1.4.1.10428 9 1.101.23.7.3.4.1.16
                fkGponOnuPMStatsDetailUniEthFrameDownPre15mPkt1024To1518Octets OBJECT-TYPE
                        SYNTAX Counter64
                        MAX-ACCESS read-only
                        STATUS current
                        DESCRIPTION
                                "The pre 15 minute number of packets (including bad packets) received that were
                                1024..1518 octets long,"
                        ::= { fkGponOnuPMStatsDetailUniEthFrameDownEntry 16 }

                
--  1.3.6.1.4.1.10428 9 1.101.23.7.3.4.1.17
                -- 1.3.6.1.4.1.10428 9 1.101.23.7.3.4.1.17
                fkGponOnuPMStatsDetailUniEthFrameDownHourDropEvents OBJECT-TYPE
                        SYNTAX Counter64
                        MAX-ACCESS read-only
                        STATUS current
                        DESCRIPTION
                                "The hour number of events in which packets were dropped due to lack
                                of resources."
                        ::= { fkGponOnuPMStatsDetailUniEthFrameDownEntry 17 }

                
--  1.3.6.1.4.1.10428 9 1.101.23.7.3.4.1.18
                -- 1.3.6.1.4.1.10428 9 1.101.23.7.3.4.1.18
                fkGponOnuPMStatsDetailUniEthFrameDownHourOctets OBJECT-TYPE
                        SYNTAX Counter64
                        MAX-ACCESS read-only
                        STATUS current
                        DESCRIPTION
                                "The hour number of octets received"
                        ::= { fkGponOnuPMStatsDetailUniEthFrameDownEntry 18 }

                
--  1.3.6.1.4.1.10428 9 1.101.23.7.3.4.1.19
                -- 1.3.6.1.4.1.10428 9 1.101.23.7.3.4.1.19
                fkGponOnuPMStatsDetailUniEthFrameDownHourPackets OBJECT-TYPE
                        SYNTAX Counter64
                        MAX-ACCESS read-only
                        STATUS current
                        DESCRIPTION
                                "The hour number of packets received,"
                        ::= { fkGponOnuPMStatsDetailUniEthFrameDownEntry 19 }

                
--  1.3.6.1.4.1.10428 9 1.101.23.7.3.4.1.20
                -- 1.3.6.1.4.1.10428 9 1.101.23.7.3.4.1.20
                fkGponOnuPMStatsDetailUniEthFrameDownHourBcastPackets OBJECT-TYPE
                        SYNTAX Counter64
                        MAX-ACCESS read-only
                        STATUS current
                        DESCRIPTION
                                "The hour number of received good packets directed to the broadcast address"
                        ::= { fkGponOnuPMStatsDetailUniEthFrameDownEntry 20 }

                
--  1.3.6.1.4.1.10428 9 1.101.23.7.3.4.1.21
                -- 1.3.6.1.4.1.10428 9 1.101.23.7.3.4.1.21
                fkGponOnuPMStatsDetailUniEthFrameDownHourMcastPackets OBJECT-TYPE
                        SYNTAX Counter64
                        MAX-ACCESS read-only
                        STATUS current
                        DESCRIPTION
                                "The hour number of received good packets directed to a multicast address."
                        ::= { fkGponOnuPMStatsDetailUniEthFrameDownEntry 21 }

                
--  1.3.6.1.4.1.10428 9 1.101.23.7.3.4.1.22
                -- 1.3.6.1.4.1.10428 9 1.101.23.7.3.4.1.22
                fkGponOnuPMStatsDetailUniEthFrameDownHourUcastPackets OBJECT-TYPE
                        SYNTAX Counter64
                        MAX-ACCESS read-only
                        STATUS current
                        DESCRIPTION
                                "The hour number of received good packets directed to the unicast address"
                        ::= { fkGponOnuPMStatsDetailUniEthFrameDownEntry 22 }

                
--  1.3.6.1.4.1.10428 9 1.101.23.7.3.4.1.23
                -- 1.3.6.1.4.1.10428 9 1.101.23.7.3.4.1.23
                fkGponOnuPMStatsDetailUniEthFrameDownHourCRCErroredPackets OBJECT-TYPE
                        SYNTAX Counter64
                        MAX-ACCESS read-only
                        STATUS current
                        DESCRIPTION
                                "The hour number of packets received that had a length"
                        ::= { fkGponOnuPMStatsDetailUniEthFrameDownEntry 23 }

                
--  1.3.6.1.4.1.10428 9 1.101.23.7.3.4.1.24
                -- 1.3.6.1.4.1.10428 9 1.101.23.7.3.4.1.24
                fkGponOnuPMStatsDetailUniEthFrameDownHourUndersizePackets OBJECT-TYPE
                        SYNTAX Counter64
                        MAX-ACCESS read-only
                        STATUS current
                        DESCRIPTION
                                "The hour number of packets received that were less than 64 octets long"
                        ::= { fkGponOnuPMStatsDetailUniEthFrameDownEntry 24 }

                
--  1.3.6.1.4.1.10428 9 1.101.23.7.3.4.1.25
                -- 1.3.6.1.4.1.10428 9 1.101.23.7.3.4.1.25
                fkGponOnuPMStatsDetailUniEthFrameDownHourOversizePackets OBJECT-TYPE
                        SYNTAX Counter64
                        MAX-ACCESS read-only
                        STATUS current
                        DESCRIPTION
                                "The hour number of received packets (including bad packets) that were
                                64 octets long,
                                "
                        ::= { fkGponOnuPMStatsDetailUniEthFrameDownEntry 25 }

                
--  1.3.6.1.4.1.10428 9 1.101.23.7.3.4.1.26
                -- 1.3.6.1.4.1.10428 9 1.101.23.7.3.4.1.26
                fkGponOnuPMStatsDetailUniEthFrameDownHourPkt64Octets OBJECT-TYPE
                        SYNTAX Counter64
                        MAX-ACCESS read-only
                        STATUS current
                        DESCRIPTION
                                "The hour number of received packets (including bad packets) that were
                                64 octets long,
                                "
                        ::= { fkGponOnuPMStatsDetailUniEthFrameDownEntry 26 }

                
--  1.3.6.1.4.1.10428 9 1.101.23.7.3.4.1.27
                -- 1.3.6.1.4.1.10428 9 1.101.23.7.3.4.1.27
                fkGponOnuPMStatsDetailUniEthFrameDownHourPkt65To127Octets OBJECT-TYPE
                        SYNTAX Counter64
                        MAX-ACCESS read-only
                        STATUS current
                        DESCRIPTION
                                "The hour number of received packets (including bad packets) that were
                                65..127 octets long,"
                        ::= { fkGponOnuPMStatsDetailUniEthFrameDownEntry 27 }

                
--  1.3.6.1.4.1.10428 9 1.101.23.7.3.4.1.28
                -- 1.3.6.1.4.1.10428 9 1.101.23.7.3.4.1.28
                fkGponOnuPMStatsDetailUniEthFrameDownHourPkt128To255Octets OBJECT-TYPE
                        SYNTAX Counter64
                        MAX-ACCESS read-only
                        STATUS current
                        DESCRIPTION
                                "The hour number of packets (including bad packets) received that were
                                128..255 octets long,"
                        ::= { fkGponOnuPMStatsDetailUniEthFrameDownEntry 28 }

                
--  1.3.6.1.4.1.10428 9 1.101.23.7.3.4.1.29
                -- 1.3.6.1.4.1.10428 9 1.101.23.7.3.4.1.29
                fkGponOnuPMStatsDetailUniEthFrameDownHourPkt256To511Octets OBJECT-TYPE
                        SYNTAX Counter64
                        MAX-ACCESS read-only
                        STATUS current
                        DESCRIPTION
                                "The hour number of packets (including bad packets) received that were
                                256..511 octets long,"
                        ::= { fkGponOnuPMStatsDetailUniEthFrameDownEntry 29 }

                
--  1.3.6.1.4.1.10428 9 1.101.23.7.3.4.1.30
                -- 1.3.6.1.4.1.10428 9 1.101.23.7.3.4.1.30
                fkGponOnuPMStatsDetailUniEthFrameDownHourPkt512To1023Octets OBJECT-TYPE
                        SYNTAX Counter64
                        MAX-ACCESS read-only
                        STATUS current
                        DESCRIPTION
                                "The hour number of packets (including bad packets) received that were
                                512..1023 octets long,
                                "
                        ::= { fkGponOnuPMStatsDetailUniEthFrameDownEntry 30 }

                
--  1.3.6.1.4.1.10428 9 1.101.23.7.3.4.1.31
                -- 1.3.6.1.4.1.10428 9 1.101.23.7.3.4.1.31
                fkGponOnuPMStatsDetailUniEthFrameDownHourPkt1024To1518Octets OBJECT-TYPE
                        SYNTAX Counter64
                        MAX-ACCESS read-only
                        STATUS current
                        DESCRIPTION
                                "The hour number of packets (including bad packets) received that were
                                1024..1518 octets long,
                                "
                        ::= { fkGponOnuPMStatsDetailUniEthFrameDownEntry 31 }

                
--  1.3.6.1.4.1.10428 9 1.101.23.7.3.4.1.32
                -- 1.3.6.1.4.1.10428 9 1.101.23.7.3.4.1.32
                fkGponOnuPMStatsDetailUniEthFrameDownDayDropEvents OBJECT-TYPE
                        SYNTAX Counter64
                        MAX-ACCESS read-only
                        STATUS current
                        DESCRIPTION
                                "The day number of events in which packets were dropped due to lack of resources.
                                "
                        ::= { fkGponOnuPMStatsDetailUniEthFrameDownEntry 32 }

                
--  1.3.6.1.4.1.10428 9 1.101.23.7.3.4.1.33
                -- 1.3.6.1.4.1.10428 9 1.101.23.7.3.4.1.33
                fkGponOnuPMStatsDetailUniEthFrameDownDayOctets OBJECT-TYPE
                        SYNTAX Counter64
                        MAX-ACCESS read-only
                        STATUS current
                        DESCRIPTION
                                "The day number of octets received"
                        ::= { fkGponOnuPMStatsDetailUniEthFrameDownEntry 33 }

                
--  1.3.6.1.4.1.10428 9 1.101.23.7.3.4.1.34
                -- 1.3.6.1.4.1.10428 9 1.101.23.7.3.4.1.34
                fkGponOnuPMStatsDetailUniEthFrameDownDayPackets OBJECT-TYPE
                        SYNTAX Counter64
                        MAX-ACCESS read-only
                        STATUS current
                        DESCRIPTION
                                "The day number of packets received,"
                        ::= { fkGponOnuPMStatsDetailUniEthFrameDownEntry 34 }

                
--  1.3.6.1.4.1.10428 9 1.101.23.7.3.4.1.35
                -- 1.3.6.1.4.1.10428 9 1.101.23.7.3.4.1.35
                fkGponOnuPMStatsDetailUniEthFrameDownDayBcastPackets OBJECT-TYPE
                        SYNTAX Counter64
                        MAX-ACCESS read-only
                        STATUS current
                        DESCRIPTION
                                "The day number of received good packets directed to a broadcast address."
                        ::= { fkGponOnuPMStatsDetailUniEthFrameDownEntry 35 }

                
--  1.3.6.1.4.1.10428 9 1.101.23.7.3.4.1.36
                -- 1.3.6.1.4.1.10428 9 1.101.23.7.3.4.1.36
                fkGponOnuPMStatsDetailUniEthFrameDownDayMcastPackets OBJECT-TYPE
                        SYNTAX Counter64
                        MAX-ACCESS read-only
                        STATUS current
                        DESCRIPTION
                                "The day number of received good packets directed to a multicast address."
                        ::= { fkGponOnuPMStatsDetailUniEthFrameDownEntry 36 }

                
--  1.3.6.1.4.1.10428 9 1.101.23.7.3.4.1.37
                -- 1.3.6.1.4.1.10428 9 1.101.23.7.3.4.1.37
                fkGponOnuPMStatsDetailUniEthFrameDownDayUcastPackets OBJECT-TYPE
                        SYNTAX Counter64
                        MAX-ACCESS read-only
                        STATUS current
                        DESCRIPTION
                                "The day number of received good packets directed to the unicast address"
                        ::= { fkGponOnuPMStatsDetailUniEthFrameDownEntry 37 }

                
--  1.3.6.1.4.1.10428 9 1.101.23.7.3.4.1.38
                -- 1.3.6.1.4.1.10428 9 1.101.23.7.3.4.1.38
                fkGponOnuPMStatsDetailUniEthFrameDownDayCRCErroredPackets OBJECT-TYPE
                        SYNTAX Counter64
                        MAX-ACCESS read-only
                        STATUS current
                        DESCRIPTION
                                "The day number of packets received that had a length"
                        ::= { fkGponOnuPMStatsDetailUniEthFrameDownEntry 38 }

                
--  1.3.6.1.4.1.10428 9 1.101.23.7.3.4.1.39
                -- 1.3.6.1.4.1.10428 9 1.101.23.7.3.4.1.39
                fkGponOnuPMStatsDetailUniEthFrameDownDayUndersizePackets OBJECT-TYPE
                        SYNTAX Counter64
                        MAX-ACCESS read-only
                        STATUS current
                        DESCRIPTION
                                "The day number of packets received that were less than 64 octets long"
                        ::= { fkGponOnuPMStatsDetailUniEthFrameDownEntry 39 }

                
--  1.3.6.1.4.1.10428 9 1.101.23.7.3.4.1.40
                -- 1.3.6.1.4.1.10428 9 1.101.23.7.3.4.1.40
                fkGponOnuPMStatsDetailUniEthFrameDownDayOversizePackets OBJECT-TYPE
                        SYNTAX Counter64
                        MAX-ACCESS read-only
                        STATUS current
                        DESCRIPTION
                                "The day number of packets received that were longer than 1518 octets"
                        ::= { fkGponOnuPMStatsDetailUniEthFrameDownEntry 40 }

                
--  1.3.6.1.4.1.10428 9 1.101.23.7.3.4.1.41
                -- 1.3.6.1.4.1.10428 9 1.101.23.7.3.4.1.41
                fkGponOnuPMStatsDetailUniEthFrameDownDayPkt64Octets OBJECT-TYPE
                        SYNTAX Counter64
                        MAX-ACCESS read-only
                        STATUS current
                        DESCRIPTION
                                "The day number of received packets (including bad packets) that were
                                64 octets long,"
                        ::= { fkGponOnuPMStatsDetailUniEthFrameDownEntry 41 }

                
--  1.3.6.1.4.1.10428 9 1.101.23.7.3.4.1.42
                -- 1.3.6.1.4.1.10428 9 1.101.23.7.3.4.1.42
                fkGponOnuPMStatsDetailUniEthFrameDownDayPkt65To127Octets OBJECT-TYPE
                        SYNTAX Counter64
                        MAX-ACCESS read-only
                        STATUS current
                        DESCRIPTION
                                "The day number of received packets (including bad packets) that were
                                65..127 octets long,"
                        ::= { fkGponOnuPMStatsDetailUniEthFrameDownEntry 42 }

                
--  1.3.6.1.4.1.10428 9 1.101.23.7.3.4.1.43
                -- 1.3.6.1.4.1.10428 9 1.101.23.7.3.4.1.43
                fkGponOnuPMStatsDetailUniEthFrameDownDayPkt128To255Octets OBJECT-TYPE
                        SYNTAX Counter64
                        MAX-ACCESS read-only
                        STATUS current
                        DESCRIPTION
                                "The day number of received packets (including bad packets) that were
                                128..255 octets long,
                                "
                        ::= { fkGponOnuPMStatsDetailUniEthFrameDownEntry 43 }

                
--  1.3.6.1.4.1.10428 9 1.101.23.7.3.4.1.44
                -- 1.3.6.1.4.1.10428 9 1.101.23.7.3.4.1.44
                fkGponOnuPMStatsDetailUniEthFrameDownDayPkt256To511Octets OBJECT-TYPE
                        SYNTAX Counter64
                        MAX-ACCESS read-only
                        STATUS current
                        DESCRIPTION
                                "The day number of packets (including bad packets) received that were
                                256..511 octets long,"
                        ::= { fkGponOnuPMStatsDetailUniEthFrameDownEntry 44 }

                
--  1.3.6.1.4.1.10428 9 1.101.23.7.3.4.1.45
                -- 1.3.6.1.4.1.10428 9 1.101.23.7.3.4.1.45
                fkGponOnuPMStatsDetailUniEthFrameDownDayPkt512To1023Octets OBJECT-TYPE
                        SYNTAX Counter64
                        MAX-ACCESS read-only
                        STATUS current
                        DESCRIPTION
                                "The day number of packets (including bad packets) received that were
                                512..1023 octets long,"
                        ::= { fkGponOnuPMStatsDetailUniEthFrameDownEntry 45 }

                
--  1.3.6.1.4.1.10428 9 1.101.23.7.3.4.1.46
                -- 1.3.6.1.4.1.10428 9 1.101.23.7.3.4.1.46
                fkGponOnuPMStatsDetailUniEthFrameDownDayPkt1024To1518Octets OBJECT-TYPE
                        SYNTAX Counter64
                        MAX-ACCESS read-only
                        STATUS current
                        DESCRIPTION
                                "The day number of packets (including bad packets) received that were
                                1024..1518 octets long,"
                        ::= { fkGponOnuPMStatsDetailUniEthFrameDownEntry 46 }

                
--  1.3.6.1.4.1.10428 9 1.101.23.7.3.4.1.47
                -- 1.3.6.1.4.1.10428 9 1.101.23.7.3.4.1.47
                fkGponOnuPMStatsDetailUniEthFrameDownTotalDropEvents OBJECT-TYPE
                        SYNTAX Counter64
                        MAX-ACCESS read-only
                        STATUS current
                        DESCRIPTION
                                "The total number of events in which packets were dropped due to lack of resources."
                        ::= { fkGponOnuPMStatsDetailUniEthFrameDownEntry 47 }

                
--  1.3.6.1.4.1.10428 9 1.101.23.7.3.4.1.48
                -- 1.3.6.1.4.1.10428 9 1.101.23.7.3.4.1.48
                fkGponOnuPMStatsDetailUniEthFrameDownTotalOctets OBJECT-TYPE
                        SYNTAX Counter64
                        MAX-ACCESS read-only
                        STATUS current
                        DESCRIPTION
                                "The total number of octets received"
                        ::= { fkGponOnuPMStatsDetailUniEthFrameDownEntry 48 }

                
--  1.3.6.1.4.1.10428 9 1.101.23.7.3.4.1.49
                -- 1.3.6.1.4.1.10428 9 1.101.23.7.3.4.1.49
                fkGponOnuPMStatsDetailUniEthFrameDownTotalPackets OBJECT-TYPE
                        SYNTAX Counter64
                        MAX-ACCESS read-only
                        STATUS current
                        DESCRIPTION
                                "The total number of packets received,"
                        ::= { fkGponOnuPMStatsDetailUniEthFrameDownEntry 49 }

                
--  1.3.6.1.4.1.10428 9 1.101.23.7.3.4.1.50
                -- 1.3.6.1.4.1.10428 9 1.101.23.7.3.4.1.50
                fkGponOnuPMStatsDetailUniEthFrameDownTotalBcastPackets OBJECT-TYPE
                        SYNTAX Counter64
                        MAX-ACCESS read-only
                        STATUS current
                        DESCRIPTION
                                "The total number of received good packets directed to a broadcast address."
                        ::= { fkGponOnuPMStatsDetailUniEthFrameDownEntry 50 }

                
--  1.3.6.1.4.1.10428 9 1.101.23.7.3.4.1.51
                -- 1.3.6.1.4.1.10428 9 1.101.23.7.3.4.1.51
                fkGponOnuPMStatsDetailUniEthFrameDownTotalMcastPackets OBJECT-TYPE
                        SYNTAX Counter64
                        MAX-ACCESS read-only
                        STATUS current
                        DESCRIPTION
                                "The total number of received good packets directed to a multicast address."
                        ::= { fkGponOnuPMStatsDetailUniEthFrameDownEntry 51 }

                
--  1.3.6.1.4.1.10428 9 1.101.23.7.3.4.1.52
                -- 1.3.6.1.4.1.10428 9 1.101.23.7.3.4.1.52
                fkGponOnuPMStatsDetailUniEthFrameDownTotalUcastPackets OBJECT-TYPE
                        SYNTAX Counter64
                        MAX-ACCESS read-only
                        STATUS current
                        DESCRIPTION
                                "The total number of received good packets directed to the unicast address"
                        ::= { fkGponOnuPMStatsDetailUniEthFrameDownEntry 52 }

                
--  1.3.6.1.4.1.10428 9 1.101.23.7.3.4.1.53
                -- 1.3.6.1.4.1.10428 9 1.101.23.7.3.4.1.53
                fkGponOnuPMStatsDetailUniEthFrameDownTotalCRCErroredPackets OBJECT-TYPE
                        SYNTAX Counter64
                        MAX-ACCESS read-only
                        STATUS current
                        DESCRIPTION
                                "Description."
                        ::= { fkGponOnuPMStatsDetailUniEthFrameDownEntry 53 }

                
--  1.3.6.1.4.1.10428 9 1.101.23.7.3.4.1.54
                -- 1.3.6.1.4.1.10428 9 1.101.23.7.3.4.1.54
                fkGponOnuPMStatsDetailUniEthFrameDownTotalUndersizePackets OBJECT-TYPE
                        SYNTAX Counter64
                        MAX-ACCESS read-only
                        STATUS current
                        DESCRIPTION
                                "The total number of packets received that were less than 64 octets long"
                        ::= { fkGponOnuPMStatsDetailUniEthFrameDownEntry 54 }

                
--  1.3.6.1.4.1.10428 9 1.101.23.7.3.4.1.55
                -- 1.3.6.1.4.1.10428 9 1.101.23.7.3.4.1.55
                fkGponOnuPMStatsDetailUniEthFrameDownTotalOversizePackets OBJECT-TYPE
                        SYNTAX Counter64
                        MAX-ACCESS read-only
                        STATUS current
                        DESCRIPTION
                                "The total number of packets received that were longer than 1518 octets"
                        ::= { fkGponOnuPMStatsDetailUniEthFrameDownEntry 55 }

                
--  1.3.6.1.4.1.10428 9 1.101.23.7.3.4.1.56
                -- 1.3.6.1.4.1.10428 9 1.101.23.7.3.4.1.56
                fkGponOnuPMStatsDetailUniEthFrameDownTotalPkt64Octets OBJECT-TYPE
                        SYNTAX Counter64
                        MAX-ACCESS read-only
                        STATUS current
                        DESCRIPTION
                                "The total number of received packets (including bad packets) that were
                                64 octets long,"
                        ::= { fkGponOnuPMStatsDetailUniEthFrameDownEntry 56 }

                
--  1.3.6.1.4.1.10428 9 1.101.23.7.3.4.1.57
                -- 1.3.6.1.4.1.10428 9 1.101.23.7.3.4.1.57
                fkGponOnuPMStatsDetailUniEthFrameDownTotalPkt65To127Octets OBJECT-TYPE
                        SYNTAX Counter64
                        MAX-ACCESS read-only
                        STATUS current
                        DESCRIPTION
                                "The total number of received packets (including bad packets) that were
                                65..127 octets long,"
                        ::= { fkGponOnuPMStatsDetailUniEthFrameDownEntry 57 }

                
--  1.3.6.1.4.1.10428 9 1.101.23.7.3.4.1.58
                -- 1.3.6.1.4.1.10428 9 1.101.23.7.3.4.1.58
                fkGponOnuPMStatsDetailUniEthFrameDownTotalPkt128To255Octets OBJECT-TYPE
                        SYNTAX Counter64
                        MAX-ACCESS read-only
                        STATUS current
                        DESCRIPTION
                                "The total number of packets (including bad packets) received that were
                                128..255 octets long,"
                        ::= { fkGponOnuPMStatsDetailUniEthFrameDownEntry 58 }

                
--  1.3.6.1.4.1.10428 9 1.101.23.7.3.4.1.59
                -- 1.3.6.1.4.1.10428 9 1.101.23.7.3.4.1.59
                fkGponOnuPMStatsDetailUniEthFrameDownTotalPkt256To511Octets OBJECT-TYPE
                        SYNTAX Counter64
                        MAX-ACCESS read-only
                        STATUS current
                        DESCRIPTION
                                "The total number of packets (including bad packets) received that were
                                256..511 octets long,"
                        ::= { fkGponOnuPMStatsDetailUniEthFrameDownEntry 59 }

                
--  1.3.6.1.4.1.10428 9 1.101.23.7.3.4.1.60
                -- 1.3.6.1.4.1.10428 9 1.101.23.7.3.4.1.60
                fkGponOnuPMStatsDetailUniEthFrameDownTotalPkt512To1023Octets OBJECT-TYPE
                        SYNTAX Counter64
                        MAX-ACCESS read-only
                        STATUS current
                        DESCRIPTION
                                "The total number of packets (including bad packets) received that were
                                512..1023 octets long,"
                        ::= { fkGponOnuPMStatsDetailUniEthFrameDownEntry 60 }

                
--  1.3.6.1.4.1.10428 9 1.101.23.7.3.4.1.61
                -- 1.3.6.1.4.1.10428 9 1.101.23.7.3.4.1.61
                fkGponOnuPMStatsDetailUniEthFrameDownTotalPkt1024To1518Octets OBJECT-TYPE
                        SYNTAX Counter64
                        MAX-ACCESS read-only
                        STATUS current
                        DESCRIPTION
                                "The total number of packets (including bad packets) received that were
                                1024..1518 octets long,"
                        ::= { fkGponOnuPMStatsDetailUniEthFrameDownEntry 61 }

                
--  1.3.6.1.4.1.10428 9 1.101.23.7.3.4.1.62
                -- 1.3.6.1.4.1.10428 9 1.101.23.7.3.4.1.62
                fkGponOnuPMStatsDetailUniEthFrameDownElapsedTimeAfterClear OBJECT-TYPE
                        SYNTAX TimeTicks
                        MAX-ACCESS read-only
                        STATUS current
                        DESCRIPTION
                                "The total number of packets for elapsed time after clear"
                        ::= { fkGponOnuPMStatsDetailUniEthFrameDownEntry 62 }

                
--  1.3.6.1.4.1.10428 9 1.101.23.7.3.4.1.63
                -- 1.3.6.1.4.1.10428 9 1.101.23.7.3.4.1.63
                fkGponOnuPMStatsDetailUniEthFrameDownElapsedTimeAfterUpdate OBJECT-TYPE
                        SYNTAX Counter64
                        MAX-ACCESS read-only
                        STATUS current
                        DESCRIPTION
                                "The total number of packets for elapsed time after update"
                        ::= { fkGponOnuPMStatsDetailUniEthFrameDownEntry 63 }

                
--  1.3.6.1.4.1.10428 9 1.101.23.7.3.5
                -- 1.3.6.1.4.1.10428 9 1.101.23.7.3.5
                fkGponOnuPMStatsDetailUniEth3Table OBJECT-TYPE
                        SYNTAX SEQUENCE OF FkGponOnuPMStatsDetailUniEth3Entry
                        MAX-ACCESS not-accessible
                        STATUS current
                        DESCRIPTION
                                "fkGponOnuPMStatsDetailUniEth3Table"
                        ::= { fkGponOnuPMStatisticsDetail 5 }

                
--  1.3.6.1.4.1.10428 9 1.101.23.7.3.5.1
                -- 1.3.6.1.4.1.10428 9 1.101.23.7.3.5.1
                fkGponOnuPMStatsDetailUniEth3Entry OBJECT-TYPE
                        SYNTAX FkGponOnuPMStatsDetailUniEth3Entry
                        MAX-ACCESS not-accessible
                        STATUS current
                        DESCRIPTION
                                "key: fkGponOltId, fkGponOnuId, fkGponOnuPMStatsDetailUniEthFrameUpUniPort"
                        INDEX { fkGponOltId, fkGponOnuId, fkGponOnuPMStatsDetailUniEthFrameUpUniPort }
                        ::= { fkGponOnuPMStatsDetailUniEth3Table 1 }

                
                FkGponOnuPMStatsDetailUniEth3Entry ::=
                        SEQUENCE { 
                                fkGponOnuPMStatsDetailUniEth3UniPort
                                        Integer32,
                                fkGponOnuPMStatsDetailUniEth3Pre15mDropEvents
                                        Counter64,
                                fkGponOnuPMStatsDetailUniEth3Pre15mOctets
                                        Counter64,
                                fkGponOnuPMStatsDetailUniEth3Pre15mPackets
                                        Counter64,
                                fkGponOnuPMStatsDetailUniEth3Pre15mBcastPackets
                                        Counter64,
                                fkGponOnuPMStatsDetailUniEth3Pre15mMcastPackets
                                        Counter64,
                                fkGponOnuPMStatsDetailUniEth3Pre15mUcastPackets
                                        Counter64,
                                fkGponOnuPMStatsDetailUniEth3Pre15mUndersizePackets
                                        Counter64,
                                fkGponOnuPMStatsDetailUniEth3Pre15mFragments
                                        Counter64,
                                fkGponOnuPMStatsDetailUniEth3Pre15mJabbers
                                        Counter64,
                                fkGponOnuPMStatsDetailUniEth3Pre15mPkt64Octets
                                        Counter64,
                                fkGponOnuPMStatsDetailUniEth3Pre15mPkt65To127Octets
                                        Counter64,
                                fkGponOnuPMStatsDetailUniEth3Pre15mPkt128To255Octets
                                        Counter64,
                                fkGponOnuPMStatsDetailUniEth3Pre15mPkt256To511Octets
                                        Counter64,
                                fkGponOnuPMStatsDetailUniEth3Pre15mPkt512To1023Octets
                                        Counter64,
                                fkGponOnuPMStatsDetailUniEth3Pre15mPkt1024To1518Octets
                                        Counter64,
                                fkGponOnuPMStatsDetailUniEth3HourDropEvents
                                        Counter64,
                                fkGponOnuPMStatsDetailUniEth3HourOctets
                                        Counter64,
                                fkGponOnuPMStatsDetailUniEth3HourPackets
                                        Counter64,
                                fkGponOnuPMStatsDetailUniEth3HourBcastPackets
                                        Counter64,
                                fkGponOnuPMStatsDetailUniEth3HourMcastPackets
                                        Counter64,
                                fkGponOnuPMStatsDetailUniEth3HourUcastPackets
                                        Counter64,
                                fkGponOnuPMStatsDetailUniEth3HourUndersizePackets
                                        Counter64,
                                fkGponOnuPMStatsDetailUniEth3HourFragments
                                        Counter64,
                                fkGponOnuPMStatsDetailUniEth3HourJabbers
                                        Counter64,
                                fkGponOnuPMStatsDetailUniEth3HourPkt64Octets
                                        Counter64,
                                fkGponOnuPMStatsDetailUniEth3HourPkt65To127Octets
                                        Counter64,
                                fkGponOnuPMStatsDetailUniEth3HourPkt128To255Octets
                                        Counter64,
                                fkGponOnuPMStatsDetailUniEth3HourPkt256To511Octets
                                        Counter64,
                                fkGponOnuPMStatsDetailUniEth3HourPkt512To1023Octets
                                        Counter64,
                                fkGponOnuPMStatsDetailUniEth3HourPkt1024To1518Octets
                                        Counter64,
                                fkGponOnuPMStatsDetailUniEth3DayDropEvents
                                        Counter64,
                                fkGponOnuPMStatsDetailUniEth3DayOctets
                                        Counter64,
                                fkGponOnuPMStatsDetailUniEth3DayPackets
                                        Counter64,
                                fkGponOnuPMStatsDetailUniEth3DayBcastPackets
                                        Counter64,
                                fkGponOnuPMStatsDetailUniEth3DayMcastPackets
                                        Counter64,
                                fkGponOnuPMStatsDetailUniEth3DayUcastPackets
                                        Counter64,
                                fkGponOnuPMStatsDetailUniEth3DayUndersizePackets
                                        Counter64,
                                fkGponOnuPMStatsDetailUniEth3DayFragments
                                        Counter64,
                                fkGponOnuPMStatsDetailUniEth3DayJabbers
                                        Counter64,
                                fkGponOnuPMStatsDetailUniEth3DayPkt64Octets
                                        Counter64,
                                fkGponOnuPMStatsDetailUniEth3DayPkt65To127Octets
                                        Counter64,
                                fkGponOnuPMStatsDetailUniEth3DayPkt128To255Octets
                                        Counter64,
                                fkGponOnuPMStatsDetailUniEth3DayPkt256To511Octets
                                        Counter64,
                                fkGponOnuPMStatsDetailUniEth3DayPkt512To1023Octets
                                        Counter64,
                                fkGponOnuPMStatsDetailUniEth3DayPkt1024To1518Octets
                                        Counter64,
                                fkGponOnuPMStatsDetailUniEth3TotalDropEvents
                                        Counter64,
                                fkGponOnuPMStatsDetailUniEth3TotalOctets
                                        Counter64,
                                fkGponOnuPMStatsDetailUniEth3TotalPackets
                                        Counter64,
                                fkGponOnuPMStatsDetailUniEth3TotalBcastPackets
                                        Counter64,
                                fkGponOnuPMStatsDetailUniEth3TotalMcastPackets
                                        Counter64,
                                fkGponOnuPMStatsDetailUniEth3TotalUcastPackets
                                        Counter64,
                                fkGponOnuPMStatsDetailUniEth3TotalUndersizePackets
                                        Counter64,
                                fkGponOnuPMStatsDetailUniEth3TotalFragments
                                        Counter64,
                                fkGponOnuPMStatsDetailUniEth3TotalJabbers
                                        Counter64,
                                fkGponOnuPMStatsDetailUniEth3TotalPkt64Octets
                                        Counter64,
                                fkGponOnuPMStatsDetailUniEth3TotalPkt65To127Octets
                                        Counter64,
                                fkGponOnuPMStatsDetailUniEth3TotalPkt128To255Octets
                                        Counter64,
                                fkGponOnuPMStatsDetailUniEth3TotalPkt256To511Octets
                                        Counter64,
                                fkGponOnuPMStatsDetailUniEth3TotalPkt512To1023Octets
                                        Counter64,
                                fkGponOnuPMStatsDetailUniEth3TotalPkt1024To1518Octets
                                        Counter64,
                                fkGponOnuPMStatsDetailUniEth3ElapsedTimeAfterClear
                                        TimeTicks,
                                fkGponOnuPMStatsDetailUniEth3ElapsedTimeAfterUpdate
                                        Counter64
                         }

--  1.3.6.1.4.1.10428 9 1.101.23.7.3.5.1.1
                -- 1.3.6.1.4.1.10428 9 1.101.23.7.3.5.1.1
                fkGponOnuPMStatsDetailUniEth3UniPort OBJECT-TYPE
                        SYNTAX Integer32
                        MAX-ACCESS read-only
                        STATUS current
                        DESCRIPTION
                                "The Uni port information"
                        ::= { fkGponOnuPMStatsDetailUniEth3Entry 1 }

                
--  1.3.6.1.4.1.10428 9 1.101.23.7.3.5.1.2
                -- 1.3.6.1.4.1.10428 9 1.101.23.7.3.5.1.2
                fkGponOnuPMStatsDetailUniEth3Pre15mDropEvents OBJECT-TYPE
                        SYNTAX Counter64
                        MAX-ACCESS read-only
                        STATUS current
                        DESCRIPTION
                                "The pre 15 minute number of events in which packets were dropped due to lack of resources."
                        ::= { fkGponOnuPMStatsDetailUniEth3Entry 2 }

                
--  1.3.6.1.4.1.10428 9 1.101.23.7.3.5.1.3
                -- 1.3.6.1.4.1.10428 9 1.101.23.7.3.5.1.3
                fkGponOnuPMStatsDetailUniEth3Pre15mOctets OBJECT-TYPE
                        SYNTAX Counter64
                        MAX-ACCESS read-only
                        STATUS current
                        DESCRIPTION
                                "The pre 15 minute number of octets received"
                        ::= { fkGponOnuPMStatsDetailUniEth3Entry 3 }

                
--  1.3.6.1.4.1.10428 9 1.101.23.7.3.5.1.4
                -- 1.3.6.1.4.1.10428 9 1.101.23.7.3.5.1.4
                fkGponOnuPMStatsDetailUniEth3Pre15mPackets OBJECT-TYPE
                        SYNTAX Counter64
                        MAX-ACCESS read-only
                        STATUS current
                        DESCRIPTION
                                "The pre 15 minute number of packets received, including bad packets"
                        ::= { fkGponOnuPMStatsDetailUniEth3Entry 4 }

                
--  1.3.6.1.4.1.10428 9 1.101.23.7.3.5.1.5
                -- 1.3.6.1.4.1.10428 9 1.101.23.7.3.5.1.5
                fkGponOnuPMStatsDetailUniEth3Pre15mBcastPackets OBJECT-TYPE
                        SYNTAX Counter64
                        MAX-ACCESS read-only
                        STATUS current
                        DESCRIPTION
                                "The pre 15 minute number of received good packets directed to the broadcast address."
                        ::= { fkGponOnuPMStatsDetailUniEth3Entry 5 }

                
--  1.3.6.1.4.1.10428 9 1.101.23.7.3.5.1.6
                -- 1.3.6.1.4.1.10428 9 1.101.23.7.3.5.1.6
                fkGponOnuPMStatsDetailUniEth3Pre15mMcastPackets OBJECT-TYPE
                        SYNTAX Counter64
                        MAX-ACCESS read-only
                        STATUS current
                        DESCRIPTION
                                "The pre 15 minute number of received good packets directed to a multicast address."
                        ::= { fkGponOnuPMStatsDetailUniEth3Entry 6 }

                
--  1.3.6.1.4.1.10428 9 1.101.23.7.3.5.1.7
                -- 1.3.6.1.4.1.10428 9 1.101.23.7.3.5.1.7
                fkGponOnuPMStatsDetailUniEth3Pre15mUcastPackets OBJECT-TYPE
                        SYNTAX Counter64
                        MAX-ACCESS read-only
                        STATUS current
                        DESCRIPTION
                                "The pre 15 minute number of received good packets directed to a unicast address."
                        ::= { fkGponOnuPMStatsDetailUniEth3Entry 7 }

                
--  1.3.6.1.4.1.10428 9 1.101.23.7.3.5.1.8
                -- 1.3.6.1.4.1.10428 9 1.101.23.7.3.5.1.8
                fkGponOnuPMStatsDetailUniEth3Pre15mUndersizePackets OBJECT-TYPE
                        SYNTAX Counter64
                        MAX-ACCESS read-only
                        STATUS current
                        DESCRIPTION
                                "The pre 15 minute number of packets received that were less than 64 octets long"
                        ::= { fkGponOnuPMStatsDetailUniEth3Entry 8 }

                
--  1.3.6.1.4.1.10428 9 1.101.23.7.3.5.1.9
                -- 1.3.6.1.4.1.10428 9 1.101.23.7.3.5.1.9
                fkGponOnuPMStatsDetailUniEth3Pre15mFragments OBJECT-TYPE
                        SYNTAX Counter64
                        MAX-ACCESS read-only
                        STATUS current
                        DESCRIPTION
                                "The pre 15 minute number of packets received that were fragments"
                        ::= { fkGponOnuPMStatsDetailUniEth3Entry 9 }

                
--  1.3.6.1.4.1.10428 9 1.101.23.7.3.5.1.10
                -- 1.3.6.1.4.1.10428 9 1.101.23.7.3.5.1.10
                fkGponOnuPMStatsDetailUniEth3Pre15mJabbers OBJECT-TYPE
                        SYNTAX Counter64
                        MAX-ACCESS read-only
                        STATUS current
                        DESCRIPTION
                                "The pre 15 minute number of packets received that were jabbers"
                        ::= { fkGponOnuPMStatsDetailUniEth3Entry 10 }

                
--  1.3.6.1.4.1.10428 9 1.101.23.7.3.5.1.11
                -- 1.3.6.1.4.1.10428 9 1.101.23.7.3.5.1.11
                fkGponOnuPMStatsDetailUniEth3Pre15mPkt64Octets OBJECT-TYPE
                        SYNTAX Counter64
                        MAX-ACCESS read-only
                        STATUS current
                        DESCRIPTION
                                "The pre 15 minute number of received packets (including bad packets) that were 64 octets long"
                        ::= { fkGponOnuPMStatsDetailUniEth3Entry 11 }

                
--  1.3.6.1.4.1.10428 9 1.101.23.7.3.5.1.12
                -- 1.3.6.1.4.1.10428 9 1.101.23.7.3.5.1.12
                fkGponOnuPMStatsDetailUniEth3Pre15mPkt65To127Octets OBJECT-TYPE
                        SYNTAX Counter64
                        MAX-ACCESS read-only
                        STATUS current
                        DESCRIPTION
                                "The pre 15 minute number of received packets (including bad packets) that were 65..127 octets long"
                        ::= { fkGponOnuPMStatsDetailUniEth3Entry 12 }

                
--  1.3.6.1.4.1.10428 9 1.101.23.7.3.5.1.13
                -- 1.3.6.1.4.1.10428 9 1.101.23.7.3.5.1.13
                fkGponOnuPMStatsDetailUniEth3Pre15mPkt128To255Octets OBJECT-TYPE
                        SYNTAX Counter64
                        MAX-ACCESS read-only
                        STATUS current
                        DESCRIPTION
                                "The pre 15 minute number of packets (including bad packets) received that were 128..255 octets long"
                        ::= { fkGponOnuPMStatsDetailUniEth3Entry 13 }

                
--  1.3.6.1.4.1.10428 9 1.101.23.7.3.5.1.14
                -- 1.3.6.1.4.1.10428 9 1.101.23.7.3.5.1.14
                fkGponOnuPMStatsDetailUniEth3Pre15mPkt256To511Octets OBJECT-TYPE
                        SYNTAX Counter64
                        MAX-ACCESS read-only
                        STATUS current
                        DESCRIPTION
                                "The pre 15 minute number of packets (including bad packets) received that were 256..511 octets long"
                        ::= { fkGponOnuPMStatsDetailUniEth3Entry 14 }

                
--  1.3.6.1.4.1.10428 9 1.101.23.7.3.5.1.15
                -- 1.3.6.1.4.1.10428 9 1.101.23.7.3.5.1.15
                fkGponOnuPMStatsDetailUniEth3Pre15mPkt512To1023Octets OBJECT-TYPE
                        SYNTAX Counter64
                        MAX-ACCESS read-only
                        STATUS current
                        DESCRIPTION
                                "The pre 15 minute number of packets (including bad packets) received that were 512..1023 octets long"
                        ::= { fkGponOnuPMStatsDetailUniEth3Entry 15 }

                
--  1.3.6.1.4.1.10428 9 1.101.23.7.3.5.1.16
                -- 1.3.6.1.4.1.10428 9 1.101.23.7.3.5.1.16
                fkGponOnuPMStatsDetailUniEth3Pre15mPkt1024To1518Octets OBJECT-TYPE
                        SYNTAX Counter64
                        MAX-ACCESS read-only
                        STATUS current
                        DESCRIPTION
                                "The pre 15 minute number of packets (including bad packets) received that were 1024..1518 octets long"
                        ::= { fkGponOnuPMStatsDetailUniEth3Entry 16 }

                
--  1.3.6.1.4.1.10428 9 1.101.23.7.3.5.1.17
                -- 1.3.6.1.4.1.10428 9 1.101.23.7.3.5.1.17
                fkGponOnuPMStatsDetailUniEth3HourDropEvents OBJECT-TYPE
                        SYNTAX Counter64
                        MAX-ACCESS read-only
                        STATUS current
                        DESCRIPTION
                                "The hour number of events in which packets were dropped due to lack of resources."
                        ::= { fkGponOnuPMStatsDetailUniEth3Entry 17 }

                
--  1.3.6.1.4.1.10428 9 1.101.23.7.3.5.1.18
                -- 1.3.6.1.4.1.10428 9 1.101.23.7.3.5.1.18
                fkGponOnuPMStatsDetailUniEth3HourOctets OBJECT-TYPE
                        SYNTAX Counter64
                        MAX-ACCESS read-only
                        STATUS current
                        DESCRIPTION
                                "The hour number of octets received"
                        ::= { fkGponOnuPMStatsDetailUniEth3Entry 18 }

                
--  1.3.6.1.4.1.10428 9 1.101.23.7.3.5.1.19
                -- 1.3.6.1.4.1.10428 9 1.101.23.7.3.5.1.19
                fkGponOnuPMStatsDetailUniEth3HourPackets OBJECT-TYPE
                        SYNTAX Counter64
                        MAX-ACCESS read-only
                        STATUS current
                        DESCRIPTION
                                "The hour number of packets received,"
                        ::= { fkGponOnuPMStatsDetailUniEth3Entry 19 }

                
--  1.3.6.1.4.1.10428 9 1.101.23.7.3.5.1.20
                -- 1.3.6.1.4.1.10428 9 1.101.23.7.3.5.1.20
                fkGponOnuPMStatsDetailUniEth3HourBcastPackets OBJECT-TYPE
                        SYNTAX Counter64
                        MAX-ACCESS read-only
                        STATUS current
                        DESCRIPTION
                                "The hour number of received good packets directed to the broadcast address"
                        ::= { fkGponOnuPMStatsDetailUniEth3Entry 20 }

                
--  1.3.6.1.4.1.10428 9 1.101.23.7.3.5.1.21
                -- 1.3.6.1.4.1.10428 9 1.101.23.7.3.5.1.21
                fkGponOnuPMStatsDetailUniEth3HourMcastPackets OBJECT-TYPE
                        SYNTAX Counter64
                        MAX-ACCESS read-only
                        STATUS current
                        DESCRIPTION
                                "The hour number of received good packets directed to a multicast address."
                        ::= { fkGponOnuPMStatsDetailUniEth3Entry 21 }

                
--  1.3.6.1.4.1.10428 9 1.101.23.7.3.5.1.22
                -- 1.3.6.1.4.1.10428 9 1.101.23.7.3.5.1.22
                fkGponOnuPMStatsDetailUniEth3HourUcastPackets OBJECT-TYPE
                        SYNTAX Counter64
                        MAX-ACCESS read-only
                        STATUS current
                        DESCRIPTION
                                "The hour number of received good packets directed to the unicast address"
                        ::= { fkGponOnuPMStatsDetailUniEth3Entry 22 }

                
--  1.3.6.1.4.1.10428 9 1.101.23.7.3.5.1.23
                -- 1.3.6.1.4.1.10428 9 1.101.23.7.3.5.1.23
                fkGponOnuPMStatsDetailUniEth3HourUndersizePackets OBJECT-TYPE
                        SYNTAX Counter64
                        MAX-ACCESS read-only
                        STATUS current
                        DESCRIPTION
                                "The hour number of packets received that were less than 64 octets long"
                        ::= { fkGponOnuPMStatsDetailUniEth3Entry 23 }

                
--  1.3.6.1.4.1.10428 9 1.101.23.7.3.5.1.24
                -- 1.3.6.1.4.1.10428 9 1.101.23.7.3.5.1.24
                fkGponOnuPMStatsDetailUniEth3HourFragments OBJECT-TYPE
                        SYNTAX Counter64
                        MAX-ACCESS read-only
                        STATUS current
                        DESCRIPTION
                                "The hour number of packets received that were fragments"
                        ::= { fkGponOnuPMStatsDetailUniEth3Entry 24 }

                
--  1.3.6.1.4.1.10428 9 1.101.23.7.3.5.1.25
                -- 1.3.6.1.4.1.10428 9 1.101.23.7.3.5.1.25
                fkGponOnuPMStatsDetailUniEth3HourJabbers OBJECT-TYPE
                        SYNTAX Counter64
                        MAX-ACCESS read-only
                        STATUS current
                        DESCRIPTION
                                "The hour number of packets received that were jabbers"
                        ::= { fkGponOnuPMStatsDetailUniEth3Entry 25 }

                
--  1.3.6.1.4.1.10428 9 1.101.23.7.3.5.1.26
                -- 1.3.6.1.4.1.10428 9 1.101.23.7.3.5.1.26
                fkGponOnuPMStatsDetailUniEth3HourPkt64Octets OBJECT-TYPE
                        SYNTAX Counter64
                        MAX-ACCESS read-only
                        STATUS current
                        DESCRIPTION
                                "The hour number of received packets (including bad packets) that were
                                64 octets long,"
                        ::= { fkGponOnuPMStatsDetailUniEth3Entry 26 }

                
--  1.3.6.1.4.1.10428 9 1.101.23.7.3.5.1.27
                -- 1.3.6.1.4.1.10428 9 1.101.23.7.3.5.1.27
                fkGponOnuPMStatsDetailUniEth3HourPkt65To127Octets OBJECT-TYPE
                        SYNTAX Counter64
                        MAX-ACCESS read-only
                        STATUS current
                        DESCRIPTION
                                "The hour number of received packets (including bad packets) that were
                                65..127 octets long,"
                        ::= { fkGponOnuPMStatsDetailUniEth3Entry 27 }

                
--  1.3.6.1.4.1.10428 9 1.101.23.7.3.5.1.28
                -- 1.3.6.1.4.1.10428 9 1.101.23.7.3.5.1.28
                fkGponOnuPMStatsDetailUniEth3HourPkt128To255Octets OBJECT-TYPE
                        SYNTAX Counter64
                        MAX-ACCESS read-only
                        STATUS current
                        DESCRIPTION
                                "The hour number of packets (including bad packets) received that were
                                128..255 octets long,"
                        ::= { fkGponOnuPMStatsDetailUniEth3Entry 28 }

                
--  1.3.6.1.4.1.10428 9 1.101.23.7.3.5.1.29
                -- 1.3.6.1.4.1.10428 9 1.101.23.7.3.5.1.29
                fkGponOnuPMStatsDetailUniEth3HourPkt256To511Octets OBJECT-TYPE
                        SYNTAX Counter64
                        MAX-ACCESS read-only
                        STATUS current
                        DESCRIPTION
                                "The hour number of packets (including bad packets) received that were
                                256..511 octets long,"
                        ::= { fkGponOnuPMStatsDetailUniEth3Entry 29 }

                
--  1.3.6.1.4.1.10428 9 1.101.23.7.3.5.1.30
                -- 1.3.6.1.4.1.10428 9 1.101.23.7.3.5.1.30
                fkGponOnuPMStatsDetailUniEth3HourPkt512To1023Octets OBJECT-TYPE
                        SYNTAX Counter64
                        MAX-ACCESS read-only
                        STATUS current
                        DESCRIPTION
                                "The hour number of packets (including bad packets) received that were
                                512..1023 octets long,"
                        ::= { fkGponOnuPMStatsDetailUniEth3Entry 30 }

                
--  1.3.6.1.4.1.10428 9 1.101.23.7.3.5.1.31
                -- 1.3.6.1.4.1.10428 9 1.101.23.7.3.5.1.31
                fkGponOnuPMStatsDetailUniEth3HourPkt1024To1518Octets OBJECT-TYPE
                        SYNTAX Counter64
                        MAX-ACCESS read-only
                        STATUS current
                        DESCRIPTION
                                "The hour number of packets (including bad packets) received that were
                                1024..1518 octets long,"
                        ::= { fkGponOnuPMStatsDetailUniEth3Entry 31 }

                
--  1.3.6.1.4.1.10428 9 1.101.23.7.3.5.1.32
                -- 1.3.6.1.4.1.10428 9 1.101.23.7.3.5.1.32
                fkGponOnuPMStatsDetailUniEth3DayDropEvents OBJECT-TYPE
                        SYNTAX Counter64
                        MAX-ACCESS read-only
                        STATUS current
                        DESCRIPTION
                                "The day number of events in which packets were dropped due to lack of resources."
                        ::= { fkGponOnuPMStatsDetailUniEth3Entry 32 }

                
--  1.3.6.1.4.1.10428 9 1.101.23.7.3.5.1.33
                -- 1.3.6.1.4.1.10428 9 1.101.23.7.3.5.1.33
                fkGponOnuPMStatsDetailUniEth3DayOctets OBJECT-TYPE
                        SYNTAX Counter64
                        MAX-ACCESS read-only
                        STATUS current
                        DESCRIPTION
                                "The day number of events in which packets were dropped due to lack of resources.
                                "
                        ::= { fkGponOnuPMStatsDetailUniEth3Entry 33 }

                
--  1.3.6.1.4.1.10428 9 1.101.23.7.3.5.1.34
                -- 1.3.6.1.4.1.10428 9 1.101.23.7.3.5.1.34
                fkGponOnuPMStatsDetailUniEth3DayPackets OBJECT-TYPE
                        SYNTAX Counter64
                        MAX-ACCESS read-only
                        STATUS current
                        DESCRIPTION
                                "The day number of octets received"
                        ::= { fkGponOnuPMStatsDetailUniEth3Entry 34 }

                
--  1.3.6.1.4.1.10428 9 1.101.23.7.3.5.1.35
                -- 1.3.6.1.4.1.10428 9 1.101.23.7.3.5.1.35
                fkGponOnuPMStatsDetailUniEth3DayBcastPackets OBJECT-TYPE
                        SYNTAX Counter64
                        MAX-ACCESS read-only
                        STATUS current
                        DESCRIPTION
                                "The day number of received good packets directed to the broadcast address"
                        ::= { fkGponOnuPMStatsDetailUniEth3Entry 35 }

                
--  1.3.6.1.4.1.10428 9 1.101.23.7.3.5.1.36
                -- 1.3.6.1.4.1.10428 9 1.101.23.7.3.5.1.36
                fkGponOnuPMStatsDetailUniEth3DayMcastPackets OBJECT-TYPE
                        SYNTAX Counter64
                        MAX-ACCESS read-only
                        STATUS current
                        DESCRIPTION
                                "The day number of received good packets directed to a multicast address."
                        ::= { fkGponOnuPMStatsDetailUniEth3Entry 36 }

                
--  1.3.6.1.4.1.10428 9 1.101.23.7.3.5.1.37
                -- 1.3.6.1.4.1.10428 9 1.101.23.7.3.5.1.37
                fkGponOnuPMStatsDetailUniEth3DayUcastPackets OBJECT-TYPE
                        SYNTAX Counter64
                        MAX-ACCESS read-only
                        STATUS current
                        DESCRIPTION
                                "The day number of received good packets directed to the unicast address"
                        ::= { fkGponOnuPMStatsDetailUniEth3Entry 37 }

                
--  1.3.6.1.4.1.10428 9 1.101.23.7.3.5.1.38
                -- 1.3.6.1.4.1.10428 9 1.101.23.7.3.5.1.38
                fkGponOnuPMStatsDetailUniEth3DayUndersizePackets OBJECT-TYPE
                        SYNTAX Counter64
                        MAX-ACCESS read-only
                        STATUS current
                        DESCRIPTION
                                "The day number of packets received that were less than 64 octets long"
                        ::= { fkGponOnuPMStatsDetailUniEth3Entry 38 }

                
--  1.3.6.1.4.1.10428 9 1.101.23.7.3.5.1.39
                -- 1.3.6.1.4.1.10428 9 1.101.23.7.3.5.1.39
                fkGponOnuPMStatsDetailUniEth3DayFragments OBJECT-TYPE
                        SYNTAX Counter64
                        MAX-ACCESS read-only
                        STATUS current
                        DESCRIPTION
                                "The day number of packets received that were fragments"
                        ::= { fkGponOnuPMStatsDetailUniEth3Entry 39 }

                
--  1.3.6.1.4.1.10428 9 1.101.23.7.3.5.1.40
                -- 1.3.6.1.4.1.10428 9 1.101.23.7.3.5.1.40
                fkGponOnuPMStatsDetailUniEth3DayJabbers OBJECT-TYPE
                        SYNTAX Counter64
                        MAX-ACCESS read-only
                        STATUS current
                        DESCRIPTION
                                "The day number of packets received that were jabbers"
                        ::= { fkGponOnuPMStatsDetailUniEth3Entry 40 }

                
--  1.3.6.1.4.1.10428 9 1.101.23.7.3.5.1.41
                -- 1.3.6.1.4.1.10428 9 1.101.23.7.3.5.1.41
                fkGponOnuPMStatsDetailUniEth3DayPkt64Octets OBJECT-TYPE
                        SYNTAX Counter64
                        MAX-ACCESS read-only
                        STATUS current
                        DESCRIPTION
                                "The day number of received packets (including bad packets) that were
                                64 octets long,"
                        ::= { fkGponOnuPMStatsDetailUniEth3Entry 41 }

                
--  1.3.6.1.4.1.10428 9 1.101.23.7.3.5.1.42
                -- 1.3.6.1.4.1.10428 9 1.101.23.7.3.5.1.42
                fkGponOnuPMStatsDetailUniEth3DayPkt65To127Octets OBJECT-TYPE
                        SYNTAX Counter64
                        MAX-ACCESS read-only
                        STATUS current
                        DESCRIPTION
                                "The day number of received packets (including bad packets) that were
                                65..127 octets long,"
                        ::= { fkGponOnuPMStatsDetailUniEth3Entry 42 }

                
--  1.3.6.1.4.1.10428 9 1.101.23.7.3.5.1.43
                -- 1.3.6.1.4.1.10428 9 1.101.23.7.3.5.1.43
                fkGponOnuPMStatsDetailUniEth3DayPkt128To255Octets OBJECT-TYPE
                        SYNTAX Counter64
                        MAX-ACCESS read-only
                        STATUS current
                        DESCRIPTION
                                "The day number of received packets (including bad packets) that were
                                128..255 octets long,"
                        ::= { fkGponOnuPMStatsDetailUniEth3Entry 43 }

                
--  1.3.6.1.4.1.10428 9 1.101.23.7.3.5.1.44
                -- 1.3.6.1.4.1.10428 9 1.101.23.7.3.5.1.44
                fkGponOnuPMStatsDetailUniEth3DayPkt256To511Octets OBJECT-TYPE
                        SYNTAX Counter64
                        MAX-ACCESS read-only
                        STATUS current
                        DESCRIPTION
                                "The day number of received packets (including bad packets) that were
                                256..511 octets long,"
                        ::= { fkGponOnuPMStatsDetailUniEth3Entry 44 }

                
--  1.3.6.1.4.1.10428 9 1.101.23.7.3.5.1.45
                -- 1.3.6.1.4.1.10428 9 1.101.23.7.3.5.1.45
                fkGponOnuPMStatsDetailUniEth3DayPkt512To1023Octets OBJECT-TYPE
                        SYNTAX Counter64
                        MAX-ACCESS read-only
                        STATUS current
                        DESCRIPTION
                                "The day number of packets (including bad packets) received that were
                                512..1023 octets long,"
                        ::= { fkGponOnuPMStatsDetailUniEth3Entry 45 }

                
--  1.3.6.1.4.1.10428 9 1.101.23.7.3.5.1.46
                -- 1.3.6.1.4.1.10428 9 1.101.23.7.3.5.1.46
                fkGponOnuPMStatsDetailUniEth3DayPkt1024To1518Octets OBJECT-TYPE
                        SYNTAX Counter64
                        MAX-ACCESS read-only
                        STATUS current
                        DESCRIPTION
                                "The day number of packets (including bad packets) received that were
                                1024..1518 octets long,"
                        ::= { fkGponOnuPMStatsDetailUniEth3Entry 46 }

                
--  1.3.6.1.4.1.10428 9 1.101.23.7.3.5.1.47
                -- 1.3.6.1.4.1.10428 9 1.101.23.7.3.5.1.47
                fkGponOnuPMStatsDetailUniEth3TotalDropEvents OBJECT-TYPE
                        SYNTAX Counter64
                        MAX-ACCESS read-only
                        STATUS current
                        DESCRIPTION
                                "The total number of events in which packets were dropped due to lack
                                of resources."
                        ::= { fkGponOnuPMStatsDetailUniEth3Entry 47 }

                
--  1.3.6.1.4.1.10428 9 1.101.23.7.3.5.1.48
                -- 1.3.6.1.4.1.10428 9 1.101.23.7.3.5.1.48
                fkGponOnuPMStatsDetailUniEth3TotalOctets OBJECT-TYPE
                        SYNTAX Counter64
                        MAX-ACCESS read-only
                        STATUS current
                        DESCRIPTION
                                "The total number of octets received"
                        ::= { fkGponOnuPMStatsDetailUniEth3Entry 48 }

                
--  1.3.6.1.4.1.10428 9 1.101.23.7.3.5.1.49
                -- 1.3.6.1.4.1.10428 9 1.101.23.7.3.5.1.49
                fkGponOnuPMStatsDetailUniEth3TotalPackets OBJECT-TYPE
                        SYNTAX Counter64
                        MAX-ACCESS read-only
                        STATUS current
                        DESCRIPTION
                                "The total number of packets received,"
                        ::= { fkGponOnuPMStatsDetailUniEth3Entry 49 }

                
--  1.3.6.1.4.1.10428 9 1.101.23.7.3.5.1.50
                -- 1.3.6.1.4.1.10428 9 1.101.23.7.3.5.1.50
                fkGponOnuPMStatsDetailUniEth3TotalBcastPackets OBJECT-TYPE
                        SYNTAX Counter64
                        MAX-ACCESS read-only
                        STATUS current
                        DESCRIPTION
                                "The total number of received good packets directed to the broadcast address"
                        ::= { fkGponOnuPMStatsDetailUniEth3Entry 50 }

                
--  1.3.6.1.4.1.10428 9 1.101.23.7.3.5.1.51
                -- 1.3.6.1.4.1.10428 9 1.101.23.7.3.5.1.51
                fkGponOnuPMStatsDetailUniEth3TotalMcastPackets OBJECT-TYPE
                        SYNTAX Counter64
                        MAX-ACCESS read-only
                        STATUS current
                        DESCRIPTION
                                "The total number of received good packets directed to a multicast address."
                        ::= { fkGponOnuPMStatsDetailUniEth3Entry 51 }

                
--  1.3.6.1.4.1.10428 9 1.101.23.7.3.5.1.52
                -- 1.3.6.1.4.1.10428 9 1.101.23.7.3.5.1.52
                fkGponOnuPMStatsDetailUniEth3TotalUcastPackets OBJECT-TYPE
                        SYNTAX Counter64
                        MAX-ACCESS read-only
                        STATUS current
                        DESCRIPTION
                                "The total number of received good packets directed to the unicast address"
                        ::= { fkGponOnuPMStatsDetailUniEth3Entry 52 }

                
--  1.3.6.1.4.1.10428 9 1.101.23.7.3.5.1.53
                -- 1.3.6.1.4.1.10428 9 1.101.23.7.3.5.1.53
                fkGponOnuPMStatsDetailUniEth3TotalUndersizePackets OBJECT-TYPE
                        SYNTAX Counter64
                        MAX-ACCESS read-only
                        STATUS current
                        DESCRIPTION
                                "The total number of packets received that were less than 64 octets long"
                        ::= { fkGponOnuPMStatsDetailUniEth3Entry 53 }

                
--  1.3.6.1.4.1.10428 9 1.101.23.7.3.5.1.54
                -- 1.3.6.1.4.1.10428 9 1.101.23.7.3.5.1.54
                fkGponOnuPMStatsDetailUniEth3TotalFragments OBJECT-TYPE
                        SYNTAX Counter64
                        MAX-ACCESS read-only
                        STATUS current
                        DESCRIPTION
                                "The total number of packets received 
                                (fragments)"
                        ::= { fkGponOnuPMStatsDetailUniEth3Entry 54 }

                
--  1.3.6.1.4.1.10428 9 1.101.23.7.3.5.1.55
                -- 1.3.6.1.4.1.10428 9 1.101.23.7.3.5.1.55
                fkGponOnuPMStatsDetailUniEth3TotalJabbers OBJECT-TYPE
                        SYNTAX Counter64
                        MAX-ACCESS read-only
                        STATUS current
                        DESCRIPTION
                                "The total number of packets received 
                                (jabbers)"
                        ::= { fkGponOnuPMStatsDetailUniEth3Entry 55 }

                
--  1.3.6.1.4.1.10428 9 1.101.23.7.3.5.1.56
                -- 1.3.6.1.4.1.10428 9 1.101.23.7.3.5.1.56
                fkGponOnuPMStatsDetailUniEth3TotalPkt64Octets OBJECT-TYPE
                        SYNTAX Counter64
                        MAX-ACCESS read-only
                        STATUS current
                        DESCRIPTION
                                "The total number of received packets (including bad packets) that were
                                64 octets long,"
                        ::= { fkGponOnuPMStatsDetailUniEth3Entry 56 }

                
--  1.3.6.1.4.1.10428 9 1.101.23.7.3.5.1.57
                -- 1.3.6.1.4.1.10428 9 1.101.23.7.3.5.1.57
                fkGponOnuPMStatsDetailUniEth3TotalPkt65To127Octets OBJECT-TYPE
                        SYNTAX Counter64
                        MAX-ACCESS read-only
                        STATUS current
                        DESCRIPTION
                                "The total number of received packets (including bad packets) that were
                                65..127 octets long,"
                        ::= { fkGponOnuPMStatsDetailUniEth3Entry 57 }

                
--  1.3.6.1.4.1.10428 9 1.101.23.7.3.5.1.58
                -- 1.3.6.1.4.1.10428 9 1.101.23.7.3.5.1.58
                fkGponOnuPMStatsDetailUniEth3TotalPkt128To255Octets OBJECT-TYPE
                        SYNTAX Counter64
                        MAX-ACCESS read-only
                        STATUS current
                        DESCRIPTION
                                "The total number of packets (including bad packets) received that were
                                128..255 octets long,"
                        ::= { fkGponOnuPMStatsDetailUniEth3Entry 58 }

                
--  1.3.6.1.4.1.10428 9 1.101.23.7.3.5.1.59
                -- 1.3.6.1.4.1.10428 9 1.101.23.7.3.5.1.59
                fkGponOnuPMStatsDetailUniEth3TotalPkt256To511Octets OBJECT-TYPE
                        SYNTAX Counter64
                        MAX-ACCESS read-only
                        STATUS current
                        DESCRIPTION
                                "The total number of packets (including bad packets) received that were
                                256..511 octets long,"
                        ::= { fkGponOnuPMStatsDetailUniEth3Entry 59 }

                
--  1.3.6.1.4.1.10428 9 1.101.23.7.3.5.1.60
                -- 1.3.6.1.4.1.10428 9 1.101.23.7.3.5.1.60
                fkGponOnuPMStatsDetailUniEth3TotalPkt512To1023Octets OBJECT-TYPE
                        SYNTAX Counter64
                        MAX-ACCESS read-only
                        STATUS current
                        DESCRIPTION
                                "The total number of packets (including bad packets) received that were
                                512..1023 octets long,"
                        ::= { fkGponOnuPMStatsDetailUniEth3Entry 60 }

                
--  1.3.6.1.4.1.10428 9 1.101.23.7.3.5.1.61
                -- 1.3.6.1.4.1.10428 9 1.101.23.7.3.5.1.61
                fkGponOnuPMStatsDetailUniEth3TotalPkt1024To1518Octets OBJECT-TYPE
                        SYNTAX Counter64
                        MAX-ACCESS read-only
                        STATUS current
                        DESCRIPTION
                                "The total number of packets (including bad packets) received that were
                                1024..1518 octets long,"
                        ::= { fkGponOnuPMStatsDetailUniEth3Entry 61 }

                
--  1.3.6.1.4.1.10428 9 1.101.23.7.3.5.1.62
                -- 1.3.6.1.4.1.10428 9 1.101.23.7.3.5.1.62
                fkGponOnuPMStatsDetailUniEth3ElapsedTimeAfterClear OBJECT-TYPE
                        SYNTAX TimeTicks
                        MAX-ACCESS read-only
                        STATUS current
                        DESCRIPTION
                                "The number of packets for elapsed time after clear"
                        ::= { fkGponOnuPMStatsDetailUniEth3Entry 62 }

                
--  1.3.6.1.4.1.10428 9 1.101.23.7.3.5.1.63
                -- 1.3.6.1.4.1.10428 9 1.101.23.7.3.5.1.63
                fkGponOnuPMStatsDetailUniEth3ElapsedTimeAfterUpdate OBJECT-TYPE
                        SYNTAX Counter64
                        MAX-ACCESS read-only
                        STATUS current
                        DESCRIPTION
                                "The number of packets for elapsed time after update"
                        ::= { fkGponOnuPMStatsDetailUniEth3Entry 63 }

                
                -- 1.3.6.1.4.1.10428 9 1.101.23.7.4
                fkGponOnuPMStatsCurrentDetail OBJECT IDENTIFIER ::= { fkGponStatistics 4 }

                
--  1.3.6.1.4.1.10428 9 1.101.23.7.3.1
                -- 1.3.6.1.4.1.10428 9 1.101.23.7.4.1
                fkGponOnuPMStatsCurrentDetailGEMTable OBJECT-TYPE
                        SYNTAX SEQUENCE OF FkGponOnuPMStatsCurrentDetailGEMEntry
                        MAX-ACCESS not-accessible
                        STATUS current
                        DESCRIPTION
                                "fkGponOnuPMStatsCurrentDetailGEMTable"
                        ::= { fkGponOnuPMStatsCurrentDetail 1 }

                
--  1.3.6.1.4.1.10428 9 1.101.23.7.3.1.1
                -- 1.3.6.1.4.1.10428 9 1.101.23.7.4.1.1
                fkGponOnuPMStatsCurrentDetailGEMEntry OBJECT-TYPE
                        SYNTAX FkGponOnuPMStatsCurrentDetailGEMEntry
                        MAX-ACCESS not-accessible
                        STATUS current
                        DESCRIPTION
                                "key: fkGponOltId, fkGponOnuId, fkGponOnuPMStatsCurrentDetailGEMPortIndex"
                        INDEX { fkGponOltId, fkGponOnuId, fkGponOnuPMStatsCurrentDetailGEMPortIndex }
                        ::= { fkGponOnuPMStatsCurrentDetailGEMTable 1 }

                
                FkGponOnuPMStatsCurrentDetailGEMEntry ::=
                        SEQUENCE { 
                                fkGponOnuPMStatsCurrentDetailGEMPortIndex
                                        INTEGER,
                                fkGponOnuPMStatsCurrentDetailGEMPort
                                        INTEGER,
                                fkGponOnuPMStatsCurrentDetailGEMLostPackets
                                        Counter64,
                                fkGponOnuPMStatsCurrentDetailGEMMisInsertedPackets
                                        Counter64,
                                fkGponOnuPMStatsCurrentDetailGEMReceivedPackets
                                        Counter64,
                                fkGponOnuPMStatsCurrentDetailGEMReceivedBlocks
                                        Counter64,
                                fkGponOnuPMStatsCurrentDetailGEMTransmittedBlocks
                                        Counter64,
                                fkGponOnuPMStatsCurrentDetailGEMImpairedBlocks
                                        Counter64
                         }

                -- 1.3.6.1.4.1.10428 9 1.101.23.7.4.1.1.1
                fkGponOnuPMStatsCurrentDetailGEMPortIndex OBJECT-TYPE
                        SYNTAX INTEGER (1..65535)
                        MAX-ACCESS read-only
                        STATUS current
                        DESCRIPTION
                                "The GEM port index."
                        ::= { fkGponOnuPMStatsCurrentDetailGEMEntry 1 }

                
--  1.3.6.1.4.1.10428 9 1.101.23.7.3.1.1.1
                -- 1.3.6.1.4.1.10428 9 1.101.23.7.4.1.1.2
                fkGponOnuPMStatsCurrentDetailGEMPort OBJECT-TYPE
                        SYNTAX INTEGER (1..65535)
                        MAX-ACCESS read-only
                        STATUS current
                        DESCRIPTION
                                "The GEM port information"
                        ::= { fkGponOnuPMStatsCurrentDetailGEMEntry 2 }

                
--  1.3.6.1.4.1.10428 9 1.101.23.7.3.1.1.2
                -- 1.3.6.1.4.1.10428 9 1.101.23.7.4.1.1.3
                fkGponOnuPMStatsCurrentDetailGEMLostPackets OBJECT-TYPE
                        SYNTAX Counter64
                        MAX-ACCESS read-only
                        STATUS current
                        DESCRIPTION
                                "The number of lost packet "
                        ::= { fkGponOnuPMStatsCurrentDetailGEMEntry 3 }

                
--  1.3.6.1.4.1.10428 9 1.101.23.7.3.1.1.3
                -- 1.3.6.1.4.1.10428 9 1.101.23.7.4.1.1.4
                fkGponOnuPMStatsCurrentDetailGEMMisInsertedPackets OBJECT-TYPE
                        SYNTAX Counter64
                        MAX-ACCESS read-only
                        STATUS current
                        DESCRIPTION
                                "The number of mis inserted packet "
                        ::= { fkGponOnuPMStatsCurrentDetailGEMEntry 4 }

                
--  1.3.6.1.4.1.10428 9 1.101.23.7.3.1.1.4
                -- 1.3.6.1.4.1.10428 9 1.101.23.7.4.1.1.5
                fkGponOnuPMStatsCurrentDetailGEMReceivedPackets OBJECT-TYPE
                        SYNTAX Counter64
                        MAX-ACCESS read-only
                        STATUS current
                        DESCRIPTION
                                "The number of received packet"
                        ::= { fkGponOnuPMStatsCurrentDetailGEMEntry 5 }

                
--  1.3.6.1.4.1.10428 9 1.101.23.7.3.1.1.5
                -- 1.3.6.1.4.1.10428 9 1.101.23.7.4.1.1.6
                fkGponOnuPMStatsCurrentDetailGEMReceivedBlocks OBJECT-TYPE
                        SYNTAX Counter64
                        MAX-ACCESS read-only
                        STATUS current
                        DESCRIPTION
                                "The number of received blocks"
                        ::= { fkGponOnuPMStatsCurrentDetailGEMEntry 6 }

                
--  1.3.6.1.4.1.10428 9 1.101.23.7.3.1.1.6
                -- 1.3.6.1.4.1.10428 9 1.101.23.7.4.1.1.7
                fkGponOnuPMStatsCurrentDetailGEMTransmittedBlocks OBJECT-TYPE
                        SYNTAX Counter64
                        MAX-ACCESS read-only
                        STATUS current
                        DESCRIPTION
                                "The number of transmitted blocks"
                        ::= { fkGponOnuPMStatsCurrentDetailGEMEntry 7 }

                
--  1.3.6.1.4.1.10428 9 1.101.23.7.3.1.1.7
                -- 1.3.6.1.4.1.10428 9 1.101.23.7.4.1.1.8
                fkGponOnuPMStatsCurrentDetailGEMImpairedBlocks OBJECT-TYPE
                        SYNTAX Counter64
                        MAX-ACCESS read-only
                        STATUS current
                        DESCRIPTION
                                "The number of impaired blocks"
                        ::= { fkGponOnuPMStatsCurrentDetailGEMEntry 8 }

                
--  1.3.6.1.4.1.10428 9 1.101.23.7.3.2
                -- 1.3.6.1.4.1.10428 9 1.101.23.7.4.2
                fkGponOnuPMStatsCurrentDetailAniTable OBJECT-TYPE
                        SYNTAX SEQUENCE OF FkGponOnuPMStatsCurrentDetailAniEntry
                        MAX-ACCESS not-accessible
                        STATUS current
                        DESCRIPTION
                                "fkGponOnuPMStatsCurrentDetailAniTable"
                        ::= { fkGponOnuPMStatsCurrentDetail 2 }

                
--  1.3.6.1.4.1.10428 9 1.101.23.7.3.2.1
                -- 1.3.6.1.4.1.10428 9 1.101.23.7.4.2.1
                fkGponOnuPMStatsCurrentDetailAniEntry OBJECT-TYPE
                        SYNTAX FkGponOnuPMStatsCurrentDetailAniEntry
                        MAX-ACCESS not-accessible
                        STATUS current
                        DESCRIPTION
                                "key: fkGponOltId, fkGponOnuId, fkGponOnuPMStatsCurrentDetailAniPortIndex"
                        INDEX { fkGponOltId, fkGponOnuId, fkGponOnuPMStatsCurrentDetailAniPortIndex }
                        ::= { fkGponOnuPMStatsCurrentDetailAniTable 1 }

                
                FkGponOnuPMStatsCurrentDetailAniEntry ::=
                        SEQUENCE { 
                                fkGponOnuPMStatsCurrentDetailAniPortIndex
                                        INTEGER,
                                fkGponOnuPMStatsCurrentDetailAniPort
                                        INTEGER,
                                fkGponOnuPMStatsCurrentDetailAniDiscardedFrames
                                        Counter64
                         }

                -- 1.3.6.1.4.1.10428 9 1.101.23.7.4.2.1.1
                fkGponOnuPMStatsCurrentDetailAniPortIndex OBJECT-TYPE
                        SYNTAX INTEGER (1..65535)
                        MAX-ACCESS read-only
                        STATUS current
                        DESCRIPTION
                                "The ANI port index."
                        ::= { fkGponOnuPMStatsCurrentDetailAniEntry 1 }

                
--  1.3.6.1.4.1.10428 9 1.101.23.7.3.2.1.1
                -- 1.3.6.1.4.1.10428 9 1.101.23.7.4.2.1.2
                fkGponOnuPMStatsCurrentDetailAniPort OBJECT-TYPE
                        SYNTAX INTEGER (1..65535)
                        MAX-ACCESS read-only
                        STATUS current
                        DESCRIPTION
                                "The Ani port information"
                        ::= { fkGponOnuPMStatsCurrentDetailAniEntry 2 }

                
--  1.3.6.1.4.1.10428 9 1.101.23.7.3.2.1.2
                -- 1.3.6.1.4.1.10428 9 1.101.23.7.4.2.1.3
                fkGponOnuPMStatsCurrentDetailAniDiscardedFrames OBJECT-TYPE
                        SYNTAX Counter64
                        MAX-ACCESS read-only
                        STATUS current
                        DESCRIPTION
                                "The number of lost discarded frames"
                        ::= { fkGponOnuPMStatsCurrentDetailAniEntry 3 }

                
--  1.3.6.1.4.1.10428 9 1.101.23.7.3.3
                -- 1.3.6.1.4.1.10428 9 1.101.23.7.4.3
                fkGponOnuPMStatsCurrentDetailUniEthFrameUpTable OBJECT-TYPE
                        SYNTAX SEQUENCE OF FkGponOnuPMStatsCurrentDetailUniEthFrameUpEntry
                        MAX-ACCESS not-accessible
                        STATUS current
                        DESCRIPTION
                                "fkGponOnuPMStatsCurrentDetailUniEthFrameUpTable"
                        ::= { fkGponOnuPMStatsCurrentDetail 3 }

                
--  1.3.6.1.4.1.10428 9 1.101.23.7.3.3.1
                -- 1.3.6.1.4.1.10428 9 1.101.23.7.4.3.1
                fkGponOnuPMStatsCurrentDetailUniEthFrameUpEntry OBJECT-TYPE
                        SYNTAX FkGponOnuPMStatsCurrentDetailUniEthFrameUpEntry
                        MAX-ACCESS not-accessible
                        STATUS current
                        DESCRIPTION
                                "key: fkGponOltId, fkGponOnuId, fkGponOnuPMStatsCurrentDetailUniEthFrameUpUniPort"
                        INDEX { fkGponOltId, fkGponOnuId, fkGponOnuPMStatsCurrentDetailUniEthFrameUpUniPort }
                        ::= { fkGponOnuPMStatsCurrentDetailUniEthFrameUpTable 1 }

                
                FkGponOnuPMStatsCurrentDetailUniEthFrameUpEntry ::=
                        SEQUENCE { 
                                fkGponOnuPMStatsCurrentDetailUniEthFrameUpUniPort
                                        INTEGER,
                                fkGponOnuPMStatsCurrentDetailUniEthFrameUpDropEvents
                                        Counter64,
                                fkGponOnuPMStatsCurrentDetailUniEthFrameUpOctets
                                        Counter64,
                                fkGponOnuPMStatsCurrentDetailUniEthFrameUpPackets
                                        Counter64,
                                fkGponOnuPMStatsCurrentDetailUniEthFrameUpBcastPackets
                                        Counter64,
                                fkGponOnuPMStatsCurrentDetailUniEthFrameUpMcastPackets
                                        Counter64,
                                fkGponOnuPMStatsCurrentDetailUniEthFrameUpUcastPackets
                                        Counter64,
                                fkGponOnuPMStatsCurrentDetailUniEthFrameUpCRCErroredPackets
                                        Counter64,
                                fkGponOnuPMStatsCurrentDetailUniEthFrameUpUndersizePackets
                                        Counter64,
                                fkGponOnuPMStatsCurrentDetailUniEthFrameUpOversizePackets
                                        Counter64,
                                fkGponOnuPMStatsCurrentDetailUniEthFrameUpPkt64Octets
                                        Counter64,
                                fkGponOnuPMStatsCurrentDetailUniEthFrameUpPkt65To127Octets
                                        Counter64,
                                fkGponOnuPMStatsCurrentDetailUniEthFrameUpPkt128To255
                                        Counter64,
                                fkGponOnuPMStatsCurrentDetailUniEthFrameUpPkt256To511
                                        Counter64,
                                fkGponOnuPMStatsCurrentDetailUniEthFrameUpPkt512To1023
                                        Counter64,
                                fkGponOnuPMStatsCurrentDetailUniEthFrameUpPkt1024To1518
                                        Counter64,
                                fkGponOnuPMStatsCurrentDetailUniEthFrameUpAvgPackets
                                        Counter64,
                                fkGponOnuPMStatsCurrentDetailUniEthFrameUpAvgBits
                                        Counter64,
                                fkGponOnuPMStatsCurrentDetailUniEthFrameTotalUpAvgPackets
                                        Counter64,
                                fkGponOnuPMStatsCurrentDetailUniEthFrameTotalUpAvgBits
                                        Counter64
                         }

--  1.3.6.1.4.1.10428 9 1.101.23.7.3.3.1.1
                -- 1.3.6.1.4.1.10428 9 1.101.23.7.4.3.1.1
                fkGponOnuPMStatsCurrentDetailUniEthFrameUpUniPort OBJECT-TYPE
                        SYNTAX INTEGER (1..65535)
                        MAX-ACCESS read-only
                        STATUS current
                        DESCRIPTION
                                "The Uni port information"
                        ::= { fkGponOnuPMStatsCurrentDetailUniEthFrameUpEntry 1 }

                
--  1.3.6.1.4.1.10428 9 1.101.23.7.3.3.1.2
                -- 1.3.6.1.4.1.10428 9 1.101.23.7.4.3.1.2
                fkGponOnuPMStatsCurrentDetailUniEthFrameUpDropEvents OBJECT-TYPE
                        SYNTAX Counter64
                        MAX-ACCESS read-only
                        STATUS current
                        DESCRIPTION
                                "The number of events in which packets were dropped due to lack
                                of resources."
                        ::= { fkGponOnuPMStatsCurrentDetailUniEthFrameUpEntry 2 }

                
--  1.3.6.1.4.1.10428 9 1.101.23.7.3.3.1.3
                -- 1.3.6.1.4.1.10428 9 1.101.23.7.4.3.1.3
                fkGponOnuPMStatsCurrentDetailUniEthFrameUpOctets OBJECT-TYPE
                        SYNTAX Counter64
                        MAX-ACCESS read-only
                        STATUS current
                        DESCRIPTION
                                "The number of octets received"
                        ::= { fkGponOnuPMStatsCurrentDetailUniEthFrameUpEntry 3 }

                
--  1.3.6.1.4.1.10428 9 1.101.23.7.3.3.1.4
                -- 1.3.6.1.4.1.10428 9 1.101.23.7.4.3.1.4
                fkGponOnuPMStatsCurrentDetailUniEthFrameUpPackets OBJECT-TYPE
                        SYNTAX Counter64
                        MAX-ACCESS read-only
                        STATUS current
                        DESCRIPTION
                                "The number of packets received,"
                        ::= { fkGponOnuPMStatsCurrentDetailUniEthFrameUpEntry 4 }

                
--  1.3.6.1.4.1.10428 9 1.101.23.7.3.3.1.5
                -- 1.3.6.1.4.1.10428 9 1.101.23.7.4.3.1.5
                fkGponOnuPMStatsCurrentDetailUniEthFrameUpBcastPackets OBJECT-TYPE
                        SYNTAX Counter64
                        MAX-ACCESS read-only
                        STATUS current
                        DESCRIPTION
                                "The number of received good packets directed to the broadcast address"
                        ::= { fkGponOnuPMStatsCurrentDetailUniEthFrameUpEntry 5 }

                
--  1.3.6.1.4.1.10428 9 1.101.23.7.3.3.1.6
                -- 1.3.6.1.4.1.10428 9 1.101.23.7.4.3.1.6
                fkGponOnuPMStatsCurrentDetailUniEthFrameUpMcastPackets OBJECT-TYPE
                        SYNTAX Counter64
                        MAX-ACCESS read-only
                        STATUS current
                        DESCRIPTION
                                "The number of received good packets directed to a multicast address."
                        ::= { fkGponOnuPMStatsCurrentDetailUniEthFrameUpEntry 6 }

                
--  1.3.6.1.4.1.10428 9 1.101.23.7.3.3.1.7
                -- 1.3.6.1.4.1.10428 9 1.101.23.7.4.3.1.7
                fkGponOnuPMStatsCurrentDetailUniEthFrameUpUcastPackets OBJECT-TYPE
                        SYNTAX Counter64
                        MAX-ACCESS read-only
                        STATUS current
                        DESCRIPTION
                                "The number of received good packets directed to the unicast address"
                        ::= { fkGponOnuPMStatsCurrentDetailUniEthFrameUpEntry 7 }

                
--  1.3.6.1.4.1.10428 9 1.101.23.7.3.3.1.8
                -- 1.3.6.1.4.1.10428 9 1.101.23.7.4.3.1.8
                fkGponOnuPMStatsCurrentDetailUniEthFrameUpCRCErroredPackets OBJECT-TYPE
                        SYNTAX Counter64
                        MAX-ACCESS read-only
                        STATUS current
                        DESCRIPTION
                                "The number of packets received that had a length"
                        ::= { fkGponOnuPMStatsCurrentDetailUniEthFrameUpEntry 8 }

                
--  1.3.6.1.4.1.10428 9 1.101.23.7.3.3.1.9
                -- 1.3.6.1.4.1.10428 9 1.101.23.7.4.3.1.9
                fkGponOnuPMStatsCurrentDetailUniEthFrameUpUndersizePackets OBJECT-TYPE
                        SYNTAX Counter64
                        MAX-ACCESS read-only
                        STATUS current
                        DESCRIPTION
                                "The number of packets received that were less than 64 octets long"
                        ::= { fkGponOnuPMStatsCurrentDetailUniEthFrameUpEntry 9 }

                
--  1.3.6.1.4.1.10428 9 1.101.23.7.3.3.1.10
                -- 1.3.6.1.4.1.10428 9 1.101.23.7.4.3.1.10
                fkGponOnuPMStatsCurrentDetailUniEthFrameUpOversizePackets OBJECT-TYPE
                        SYNTAX Counter64
                        MAX-ACCESS read-only
                        STATUS current
                        DESCRIPTION
                                "The number of packets received that were longer than 1518 octets"
                        ::= { fkGponOnuPMStatsCurrentDetailUniEthFrameUpEntry 10 }

                
--  1.3.6.1.4.1.10428 9 1.101.23.7.3.3.1.11
                -- 1.3.6.1.4.1.10428 9 1.101.23.7.4.3.1.11
                fkGponOnuPMStatsCurrentDetailUniEthFrameUpPkt64Octets OBJECT-TYPE
                        SYNTAX Counter64
                        MAX-ACCESS read-only
                        STATUS current
                        DESCRIPTION
                                "The number of received packets (including bad packets) that were
                                64 octets long,
                                "
                        ::= { fkGponOnuPMStatsCurrentDetailUniEthFrameUpEntry 11 }

                
--  1.3.6.1.4.1.10428 9 1.101.23.7.3.3.1.12
                -- 1.3.6.1.4.1.10428 9 1.101.23.7.4.3.1.12
                fkGponOnuPMStatsCurrentDetailUniEthFrameUpPkt65To127Octets OBJECT-TYPE
                        SYNTAX Counter64
                        MAX-ACCESS read-only
                        STATUS current
                        DESCRIPTION
                                "The number of received packets (including bad packets) that were
                                65..127 octets long,
                                "
                        ::= { fkGponOnuPMStatsCurrentDetailUniEthFrameUpEntry 12 }

                
--  1.3.6.1.4.1.10428 9 1.101.23.7.3.3.1.13
                -- 1.3.6.1.4.1.10428 9 1.101.23.7.4.3.1.13
                fkGponOnuPMStatsCurrentDetailUniEthFrameUpPkt128To255 OBJECT-TYPE
                        SYNTAX Counter64
                        MAX-ACCESS read-only
                        STATUS current
                        DESCRIPTION
                                "The number of packets (including bad packets) received that were
                                128..255 octets long,
                                "
                        ::= { fkGponOnuPMStatsCurrentDetailUniEthFrameUpEntry 13 }

                
--  1.3.6.1.4.1.10428 9 1.101.23.7.3.3.1.14
                -- 1.3.6.1.4.1.10428 9 1.101.23.7.4.3.1.14
                fkGponOnuPMStatsCurrentDetailUniEthFrameUpPkt256To511 OBJECT-TYPE
                        SYNTAX Counter64
                        MAX-ACCESS read-only
                        STATUS current
                        DESCRIPTION
                                "The number of packets (including bad packets) received that were
                                256..511 octets long,
                                "
                        ::= { fkGponOnuPMStatsCurrentDetailUniEthFrameUpEntry 14 }

                
--  1.3.6.1.4.1.10428 9 1.101.23.7.3.3.1.15
                -- 1.3.6.1.4.1.10428 9 1.101.23.7.4.3.1.15
                fkGponOnuPMStatsCurrentDetailUniEthFrameUpPkt512To1023 OBJECT-TYPE
                        SYNTAX Counter64
                        MAX-ACCESS read-only
                        STATUS current
                        DESCRIPTION
                                "The number of packets (including bad packets) received that were
                                512..1023 octets long,
                                "
                        ::= { fkGponOnuPMStatsCurrentDetailUniEthFrameUpEntry 15 }

                
--  1.3.6.1.4.1.10428 9 1.101.23.7.3.3.1.16
                -- 1.3.6.1.4.1.10428 9 1.101.23.7.4.3.1.16
                fkGponOnuPMStatsCurrentDetailUniEthFrameUpPkt1024To1518 OBJECT-TYPE
                        SYNTAX Counter64
                        MAX-ACCESS read-only
                        STATUS current
                        DESCRIPTION
                                "The number of packets (including bad packets) received that were
                                1024..1518 octets long,
                                "
                        ::= { fkGponOnuPMStatsCurrentDetailUniEthFrameUpEntry 16 }

                
                -- 1.3.6.1.4.1.10428 9 1.101.23.7.4.3.1.17
                fkGponOnuPMStatsCurrentDetailUniEthFrameUpAvgPackets OBJECT-TYPE
                        SYNTAX Counter64
                        MAX-ACCESS read-only
                        STATUS current
                        DESCRIPTION
                                "1.3.6.1.4.1.10428 9 1.101.23.7.4.3.1.17"
                        ::= { fkGponOnuPMStatsCurrentDetailUniEthFrameUpEntry 17 }

                
                -- 1.3.6.1.4.1.10428 9 1.101.23.7.4.3.1.18
                fkGponOnuPMStatsCurrentDetailUniEthFrameUpAvgBits OBJECT-TYPE
                        SYNTAX Counter64
                        MAX-ACCESS read-only
                        STATUS current
                        DESCRIPTION
                                "1.3.6.1.4.1.10428 9 1.101.23.7.4.3.1.18"
                        ::= { fkGponOnuPMStatsCurrentDetailUniEthFrameUpEntry 18 }

                
                -- 1.3.6.1.4.1.10428 9 1.101.23.7.4.3.1.19
                fkGponOnuPMStatsCurrentDetailUniEthFrameTotalUpAvgPackets OBJECT-TYPE
                        SYNTAX Counter64
                        MAX-ACCESS read-only
                        STATUS current
                        DESCRIPTION
                                "1.3.6.1.4.1.10428 9 1.101.23.7.4.3.1.19"
                        ::= { fkGponOnuPMStatsCurrentDetailUniEthFrameUpEntry 19 }

                
                -- 1.3.6.1.4.1.10428 9 1.101.23.7.4.3.1.20
                fkGponOnuPMStatsCurrentDetailUniEthFrameTotalUpAvgBits OBJECT-TYPE
                        SYNTAX Counter64
                        MAX-ACCESS read-only
                        STATUS current
                        DESCRIPTION
                                "1.3.6.1.4.1.10428 9 1.101.23.7.4.3.1.20"
                        ::= { fkGponOnuPMStatsCurrentDetailUniEthFrameUpEntry 20 }

                
--  1.3.6.1.4.1.10428 9 1.101.23.7.3.4
                -- 1.3.6.1.4.1.10428 9 1.101.23.7.4.4
                fkGponOnuPMStatsCurrentDetailUniEthFrameDownTable OBJECT-TYPE
                        SYNTAX SEQUENCE OF FkGponOnuPMStatsCurrentDetailUniEthFrameDownEntry
                        MAX-ACCESS not-accessible
                        STATUS current
                        DESCRIPTION
                                "fkGponOnuPMStatsCurrentDetailUniEthFrameDownTable"
                        ::= { fkGponOnuPMStatsCurrentDetail 4 }

                
--  1.3.6.1.4.1.10428 9 1.101.23.7.3.4.1
                -- 1.3.6.1.4.1.10428 9 1.101.23.7.4.4.1
                fkGponOnuPMStatsCurrentDetailUniEthFrameDownEntry OBJECT-TYPE
                        SYNTAX FkGponOnuPMStatsCurrentDetailUniEthFrameDownEntry
                        MAX-ACCESS not-accessible
                        STATUS current
                        DESCRIPTION
                                "key: fkGponOltId, fkGponOnuId, fkGponOnuPMStatsCurrentDetailUniEthFrameDownUniPort"
                        INDEX { fkGponOltId, fkGponOnuId, fkGponOnuPMStatsCurrentDetailUniEthFrameDownUniPort }
                        ::= { fkGponOnuPMStatsCurrentDetailUniEthFrameDownTable 1 }

                
                FkGponOnuPMStatsCurrentDetailUniEthFrameDownEntry ::=
                        SEQUENCE { 
                                fkGponOnuPMStatsCurrentDetailUniEthFrameDownUniPort
                                        Integer32,
                                fkGponOnuPMStatsCurrentDetailUniEthFrameDownDropEvents
                                        Counter64,
                                fkGponOnuPMStatsCurrentDetailUniEthFrameDownOctets
                                        Counter64,
                                fkGponOnuPMStatsCurrentDetailUniEthFrameDownPackets
                                        Counter64,
                                fkGponOnuPMStatsCurrentDetailUniEthFrameDownBcastPackets
                                        Counter64,
                                fkGponOnuPMStatsCurrentDetailUniEthFrameDownMcastPackets
                                        Counter64,
                                fkGponOnuPMStatsCurrentDetailUniEthFrameDownUcastPackets
                                        Counter64,
                                fkGponOnuPMStatsCurrentDetailUniEthFrameDownCRCErroredPackets
                                        Counter64,
                                fkGponOnuPMStatsCurrentDetailUniEthFrameDownUndersizePackets
                                        Counter64,
                                fkGponOnuPMStatsCurrentDetailUniEthFrameDownOversizePackets
                                        Counter64,
                                fkGponOnuPMStatsCurrentDetailUniEthFrameDownPkt64Octets
                                        Counter64,
                                fkGponOnuPMStatsCurrentDetailUniEthFrameDownPkt65To127Octets
                                        Counter64,
                                fkGponOnuPMStatsCurrentDetailUniEthFrameDownPkt128To255Octets
                                        Counter64,
                                fkGponOnuPMStatsCurrentDetailUniEthFrameDownmPkt256To511Octets
                                        Counter64,
                                fkGponOnuPMStatsCurrentDetailUniEthFrameDownmPkt512To1023Octets
                                        Counter64,
                                fkGponOnuPMStatsCurrentDetailUniEthFrameDownPkt1024To1518Octets
                                        Counter64,
                                fkGponOnuPMStatsCurrentDetailUniEthFrameDownAvgPackets
                                        Counter64,
                                fkGponOnuPMStatsCurrentDetailUniEthFrameDownAvgBits
                                        Counter64,
                                fkGponOnuPMStatsCurrentDetailUniEthFrameTotalDownAvgPackets
                                        Counter64,
                                fkGponOnuPMStatsCurrentDetailUniEthFrameTotalDownAvgBits
                                        Counter64
                         }

--  1.3.6.1.4.1.10428 9 1.101.23.7.3.4.1.1
                -- 1.3.6.1.4.1.10428 9 1.101.23.7.4.4.1.1
                fkGponOnuPMStatsCurrentDetailUniEthFrameDownUniPort OBJECT-TYPE
                        SYNTAX Integer32 (1..65535)
                        MAX-ACCESS read-only
                        STATUS current
                        DESCRIPTION
                                "fkGponOltId, fkGponOnuId, fkGponOnuPMStatsDetailUniEthFrameUpUniPort"
                        ::= { fkGponOnuPMStatsCurrentDetailUniEthFrameDownEntry 1 }

                
--  1.3.6.1.4.1.10428 9 1.101.23.7.3.4.1.2
                -- 1.3.6.1.4.1.10428 9 1.101.23.7.4.4.1.2
                fkGponOnuPMStatsCurrentDetailUniEthFrameDownDropEvents OBJECT-TYPE
                        SYNTAX Counter64
                        MAX-ACCESS read-only
                        STATUS current
                        DESCRIPTION
                                "The pre 15 minute number of events in which packets were dropped due to lack of resources.
                                "
                        ::= { fkGponOnuPMStatsCurrentDetailUniEthFrameDownEntry 2 }

                
--  1.3.6.1.4.1.10428 9 1.101.23.7.3.4.1.3
                -- 1.3.6.1.4.1.10428 9 1.101.23.7.4.4.1.3
                fkGponOnuPMStatsCurrentDetailUniEthFrameDownOctets OBJECT-TYPE
                        SYNTAX Counter64
                        MAX-ACCESS read-only
                        STATUS current
                        DESCRIPTION
                                "The pre 15 minute number of octets received"
                        ::= { fkGponOnuPMStatsCurrentDetailUniEthFrameDownEntry 3 }

                
--  1.3.6.1.4.1.10428 9 1.101.23.7.3.4.1.4
                -- 1.3.6.1.4.1.10428 9 1.101.23.7.4.4.1.4
                fkGponOnuPMStatsCurrentDetailUniEthFrameDownPackets OBJECT-TYPE
                        SYNTAX Counter64
                        MAX-ACCESS read-only
                        STATUS current
                        DESCRIPTION
                                "The pre 15 minute number of packets received,"
                        ::= { fkGponOnuPMStatsCurrentDetailUniEthFrameDownEntry 4 }

                
--  1.3.6.1.4.1.10428 9 1.101.23.7.3.4.1.5
                -- 1.3.6.1.4.1.10428 9 1.101.23.7.4.4.1.5
                fkGponOnuPMStatsCurrentDetailUniEthFrameDownBcastPackets OBJECT-TYPE
                        SYNTAX Counter64
                        MAX-ACCESS read-only
                        STATUS current
                        DESCRIPTION
                                "The pre 15 minute number of received good packets directed to the broadcast address"
                        ::= { fkGponOnuPMStatsCurrentDetailUniEthFrameDownEntry 5 }

                
--  1.3.6.1.4.1.10428 9 1.101.23.7.3.4.1.6
                -- 1.3.6.1.4.1.10428 9 1.101.23.7.4.4.1.6
                fkGponOnuPMStatsCurrentDetailUniEthFrameDownMcastPackets OBJECT-TYPE
                        SYNTAX Counter64
                        MAX-ACCESS read-only
                        STATUS current
                        DESCRIPTION
                                "The pre 15 minute number of received good packets directed to a multicast address."
                        ::= { fkGponOnuPMStatsCurrentDetailUniEthFrameDownEntry 6 }

                
--  1.3.6.1.4.1.10428 9 1.101.23.7.3.4.1.7
                -- 1.3.6.1.4.1.10428 9 1.101.23.7.4.4.1.7
                fkGponOnuPMStatsCurrentDetailUniEthFrameDownUcastPackets OBJECT-TYPE
                        SYNTAX Counter64
                        MAX-ACCESS read-only
                        STATUS current
                        DESCRIPTION
                                "The pre 15 minute number of received good packets directed to the unicast address"
                        ::= { fkGponOnuPMStatsCurrentDetailUniEthFrameDownEntry 7 }

                
--  1.3.6.1.4.1.10428 9 1.101.23.7.3.4.1.8
                -- 1.3.6.1.4.1.10428 9 1.101.23.7.4.4.1.8
                fkGponOnuPMStatsCurrentDetailUniEthFrameDownCRCErroredPackets OBJECT-TYPE
                        SYNTAX Counter64
                        MAX-ACCESS read-only
                        STATUS current
                        DESCRIPTION
                                "The pre 15 minute number of packets received that had a length"
                        ::= { fkGponOnuPMStatsCurrentDetailUniEthFrameDownEntry 8 }

                
--  1.3.6.1.4.1.10428 9 1.101.23.7.3.4.1.9
                -- 1.3.6.1.4.1.10428 9 1.101.23.7.4.4.1.9
                fkGponOnuPMStatsCurrentDetailUniEthFrameDownUndersizePackets OBJECT-TYPE
                        SYNTAX Counter64
                        MAX-ACCESS read-only
                        STATUS current
                        DESCRIPTION
                                "The pre 15 minute number of packets received that were less than 64 octets long"
                        ::= { fkGponOnuPMStatsCurrentDetailUniEthFrameDownEntry 9 }

                
--  1.3.6.1.4.1.10428 9 1.101.23.7.3.4.1.10
                -- 1.3.6.1.4.1.10428 9 1.101.23.7.4.4.1.10
                fkGponOnuPMStatsCurrentDetailUniEthFrameDownOversizePackets OBJECT-TYPE
                        SYNTAX Counter64
                        MAX-ACCESS read-only
                        STATUS current
                        DESCRIPTION
                                "The pre 15 minute number of packets received that were longer than 1518 octets"
                        ::= { fkGponOnuPMStatsCurrentDetailUniEthFrameDownEntry 10 }

                
--  1.3.6.1.4.1.10428 9 1.101.23.7.3.4.1.11
                -- 1.3.6.1.4.1.10428 9 1.101.23.7.4.4.1.11
                fkGponOnuPMStatsCurrentDetailUniEthFrameDownPkt64Octets OBJECT-TYPE
                        SYNTAX Counter64
                        MAX-ACCESS read-only
                        STATUS current
                        DESCRIPTION
                                "The pre 15 minute number of received packets (including bad packets) that were
                                64 octets long,"
                        ::= { fkGponOnuPMStatsCurrentDetailUniEthFrameDownEntry 11 }

                
--  1.3.6.1.4.1.10428 9 1.101.23.7.3.4.1.12
                -- 1.3.6.1.4.1.10428 9 1.101.23.7.4.4.1.12
                fkGponOnuPMStatsCurrentDetailUniEthFrameDownPkt65To127Octets OBJECT-TYPE
                        SYNTAX Counter64
                        MAX-ACCESS read-only
                        STATUS current
                        DESCRIPTION
                                "The pre 15 minute number of received packets (including bad packets) that were
                                65..127 octets long,"
                        ::= { fkGponOnuPMStatsCurrentDetailUniEthFrameDownEntry 12 }

                
--  1.3.6.1.4.1.10428 9 1.101.23.7.3.4.1.13
                -- 1.3.6.1.4.1.10428 9 1.101.23.7.4.4.1.13
                fkGponOnuPMStatsCurrentDetailUniEthFrameDownPkt128To255Octets OBJECT-TYPE
                        SYNTAX Counter64
                        MAX-ACCESS read-only
                        STATUS current
                        DESCRIPTION
                                "The pre 15 minute number of packets (including bad packets) received that were
                                128..255 octets long,"
                        ::= { fkGponOnuPMStatsCurrentDetailUniEthFrameDownEntry 13 }

                
--  1.3.6.1.4.1.10428 9 1.101.23.7.3.4.1.14
                -- 1.3.6.1.4.1.10428 9 1.101.23.7.4.4.1.14
                fkGponOnuPMStatsCurrentDetailUniEthFrameDownmPkt256To511Octets OBJECT-TYPE
                        SYNTAX Counter64
                        MAX-ACCESS read-only
                        STATUS current
                        DESCRIPTION
                                "The pre 15 minute number of packets (including bad packets) received that were
                                256..511 octets long,"
                        ::= { fkGponOnuPMStatsCurrentDetailUniEthFrameDownEntry 14 }

                
--  1.3.6.1.4.1.10428 9 1.101.23.7.3.4.1.15
                -- 1.3.6.1.4.1.10428 9 1.101.23.7.4.4.1.15
                fkGponOnuPMStatsCurrentDetailUniEthFrameDownmPkt512To1023Octets OBJECT-TYPE
                        SYNTAX Counter64
                        MAX-ACCESS read-only
                        STATUS current
                        DESCRIPTION
                                "The pre 15 minute number of packets (including bad packets) received that were
                                512..1023 octets long,"
                        ::= { fkGponOnuPMStatsCurrentDetailUniEthFrameDownEntry 15 }

                
--  1.3.6.1.4.1.10428 9 1.101.23.7.3.4.1.16
                -- 1.3.6.1.4.1.10428 9 1.101.23.7.4.4.1.16
                fkGponOnuPMStatsCurrentDetailUniEthFrameDownPkt1024To1518Octets OBJECT-TYPE
                        SYNTAX Counter64
                        MAX-ACCESS read-only
                        STATUS current
                        DESCRIPTION
                                "The pre 15 minute number of packets (including bad packets) received that were
                                1024..1518 octets long,"
                        ::= { fkGponOnuPMStatsCurrentDetailUniEthFrameDownEntry 16 }

                
                -- 1.3.6.1.4.1.10428 9 1.101.23.7.4.4.1.17
                fkGponOnuPMStatsCurrentDetailUniEthFrameDownAvgPackets OBJECT-TYPE
                        SYNTAX Counter64
                        MAX-ACCESS read-only
                        STATUS current
                        DESCRIPTION
                                "1.3.6.1.4.1.10428 9 1.101.23.7.4.4.1.17"
                        ::= { fkGponOnuPMStatsCurrentDetailUniEthFrameDownEntry 17 }

                
                -- 1.3.6.1.4.1.10428 9 1.101.23.7.4.4.1.18
                fkGponOnuPMStatsCurrentDetailUniEthFrameDownAvgBits OBJECT-TYPE
                        SYNTAX Counter64
                        MAX-ACCESS read-only
                        STATUS current
                        DESCRIPTION
                                "1.3.6.1.4.1.10428 9 1.101.23.7.4.4.1.18"
                        ::= { fkGponOnuPMStatsCurrentDetailUniEthFrameDownEntry 18 }

                
                -- 1.3.6.1.4.1.10428 9 1.101.23.7.4.4.1.19
                fkGponOnuPMStatsCurrentDetailUniEthFrameTotalDownAvgPackets OBJECT-TYPE
                        SYNTAX Counter64
                        MAX-ACCESS read-only
                        STATUS current
                        DESCRIPTION
                                "1.3.6.1.4.1.10428 9 1.101.23.7.4.4.1.19"
                        ::= { fkGponOnuPMStatsCurrentDetailUniEthFrameDownEntry 19 }

                
                -- 1.3.6.1.4.1.10428 9 1.101.23.7.4.4.1.20
                fkGponOnuPMStatsCurrentDetailUniEthFrameTotalDownAvgBits OBJECT-TYPE
                        SYNTAX Counter64
                        MAX-ACCESS read-only
                        STATUS current
                        DESCRIPTION
                                "1.3.6.1.4.1.10428 9 1.101.23.7.4.4.1.20"
                        ::= { fkGponOnuPMStatsCurrentDetailUniEthFrameDownEntry 20 }

                
--  1.3.6.1.4.1.10428 9 1.101.23.7.3.5
                -- 1.3.6.1.4.1.10428 9 1.101.23.7.4.5
                fkGponOnuPMStatsCurrentDetailUniEth3Table OBJECT-TYPE
                        SYNTAX SEQUENCE OF FkGponOnuPMStatsCurrentDetailUniEth3Entry
                        MAX-ACCESS not-accessible
                        STATUS current
                        DESCRIPTION
                                "fkGponOnuPMStatsCurrentDetailUniEth3Table"
                        ::= { fkGponOnuPMStatsCurrentDetail 5 }

                
--  1.3.6.1.4.1.10428 9 1.101.23.7.3.5.1
                -- 1.3.6.1.4.1.10428 9 1.101.23.7.4.5.1
                fkGponOnuPMStatsCurrentDetailUniEth3Entry OBJECT-TYPE
                        SYNTAX FkGponOnuPMStatsCurrentDetailUniEth3Entry
                        MAX-ACCESS not-accessible
                        STATUS current
                        DESCRIPTION
                                "key: fkGponOltId, fkGponOnuId, fkGponOnuPMStatsCurrentDetailUniEth3UniPort"
                        INDEX { fkGponOltId, fkGponOnuId, fkGponOnuPMStatsCurrentDetailUniEth3UniPort }
                        ::= { fkGponOnuPMStatsCurrentDetailUniEth3Table 1 }

                
                FkGponOnuPMStatsCurrentDetailUniEth3Entry ::=
                        SEQUENCE { 
                                fkGponOnuPMStatsCurrentDetailUniEth3UniPort
                                        Integer32,
                                fkGponOnuPMStatsCurrentDetailUniEth3DropEvents
                                        Counter64,
                                fkGponOnuPMStatsCurrentDetailUniEth3Octets
                                        Counter64,
                                fkGponOnuPMStatsCurrentDetailUniEth3Packets
                                        Counter64,
                                fkGponOnuPMStatsCurrentDetailUniEth3BcastPackets
                                        Counter64,
                                fkGponOnuPMStatsCurrentDetailUniEth3McastPackets
                                        Counter64,
                                fkGponOnuPMStatsCurrentDetailUniEth3UcastPackets
                                        Counter64,
                                fkGponOnuPMStatsCurrentDetailUniEth3UndersizePackets
                                        Counter64,
                                fkGponOnuPMStatsCurrentDetailUniEth3Fragments
                                        Counter64,
                                fkGponOnuPMStatsCurrentDetailUniEth3Jabbers
                                        Counter64,
                                fkGponOnuPMStatsCurrentDetailUniEth3Pkt64Octets
                                        Counter64,
                                fkGponOnuPMStatsCurrentDetailUniEth3Pkt65To127Octets
                                        Counter64,
                                fkGponOnuPMStatsCurrentDetailUniEth3Pkt128To255Octets
                                        Counter64,
                                fkGponOnuPMStatsCurrentDetailUniEth3Pkt256To511Octets
                                        Counter64,
                                fkGponOnuPMStatsCurrentDetailUniEth3Pkt512To1023Octets
                                        Counter64,
                                fkGponOnuPMStatsCurrentDetailUniEth3Pkt1024To1518Octets
                                        Counter64
                         }

--  1.3.6.1.4.1.10428 9 1.101.23.7.3.5.1.1
                -- 1.3.6.1.4.1.10428 9 1.101.23.7.4.5.1.1
                fkGponOnuPMStatsCurrentDetailUniEth3UniPort OBJECT-TYPE
                        SYNTAX Integer32 (1..65535)
                        MAX-ACCESS read-only
                        STATUS current
                        DESCRIPTION
                                "The Uni port information"
                        ::= { fkGponOnuPMStatsCurrentDetailUniEth3Entry 1 }

                
--  1.3.6.1.4.1.10428 9 1.101.23.7.3.5.1.2
                -- 1.3.6.1.4.1.10428 9 1.101.23.7.4.5.1.2
                fkGponOnuPMStatsCurrentDetailUniEth3DropEvents OBJECT-TYPE
                        SYNTAX Counter64
                        MAX-ACCESS read-only
                        STATUS current
                        DESCRIPTION
                                "The number of events in which packets were dropped due to lack of resources."
                        ::= { fkGponOnuPMStatsCurrentDetailUniEth3Entry 2 }

                
--  1.3.6.1.4.1.10428 9 1.101.23.7.3.5.1.3
                -- 1.3.6.1.4.1.10428 9 1.101.23.7.4.5.1.3
                fkGponOnuPMStatsCurrentDetailUniEth3Octets OBJECT-TYPE
                        SYNTAX Counter64
                        MAX-ACCESS read-only
                        STATUS current
                        DESCRIPTION
                                "The number of octets received"
                        ::= { fkGponOnuPMStatsCurrentDetailUniEth3Entry 3 }

                
--  1.3.6.1.4.1.10428 9 1.101.23.7.3.5.1.4
                -- 1.3.6.1.4.1.10428 9 1.101.23.7.4.5.1.4
                fkGponOnuPMStatsCurrentDetailUniEth3Packets OBJECT-TYPE
                        SYNTAX Counter64
                        MAX-ACCESS read-only
                        STATUS current
                        DESCRIPTION
                                "The number of packets received, including bad packets"
                        ::= { fkGponOnuPMStatsCurrentDetailUniEth3Entry 4 }

                
--  1.3.6.1.4.1.10428 9 1.101.23.7.3.5.1.5
                -- 1.3.6.1.4.1.10428 9 1.101.23.7.4.5.1.5
                fkGponOnuPMStatsCurrentDetailUniEth3BcastPackets OBJECT-TYPE
                        SYNTAX Counter64
                        MAX-ACCESS read-only
                        STATUS current
                        DESCRIPTION
                                "The number of received good packets directed to the broadcast address."
                        ::= { fkGponOnuPMStatsCurrentDetailUniEth3Entry 5 }

                
--  1.3.6.1.4.1.10428 9 1.101.23.7.3.5.1.6
                -- 1.3.6.1.4.1.10428 9 1.101.23.7.4.5.1.6
                fkGponOnuPMStatsCurrentDetailUniEth3McastPackets OBJECT-TYPE
                        SYNTAX Counter64
                        MAX-ACCESS read-only
                        STATUS current
                        DESCRIPTION
                                "The number of received good packets directed to a multicast address."
                        ::= { fkGponOnuPMStatsCurrentDetailUniEth3Entry 6 }

                
--  1.3.6.1.4.1.10428 9 1.101.23.7.3.5.1.7
                -- 1.3.6.1.4.1.10428 9 1.101.23.7.4.5.1.7
                fkGponOnuPMStatsCurrentDetailUniEth3UcastPackets OBJECT-TYPE
                        SYNTAX Counter64
                        MAX-ACCESS read-only
                        STATUS current
                        DESCRIPTION
                                "The number of received good packets directed to a unicast address."
                        ::= { fkGponOnuPMStatsCurrentDetailUniEth3Entry 7 }

                
--  1.3.6.1.4.1.10428 9 1.101.23.7.3.5.1.8
                -- 1.3.6.1.4.1.10428 9 1.101.23.7.4.5.1.8
                fkGponOnuPMStatsCurrentDetailUniEth3UndersizePackets OBJECT-TYPE
                        SYNTAX Counter64
                        MAX-ACCESS read-only
                        STATUS current
                        DESCRIPTION
                                "The number of packets received that were less than 64 octets long"
                        ::= { fkGponOnuPMStatsCurrentDetailUniEth3Entry 8 }

                
--  1.3.6.1.4.1.10428 9 1.101.23.7.3.5.1.9
                -- 1.3.6.1.4.1.10428 9 1.101.23.7.4.5.1.9
                fkGponOnuPMStatsCurrentDetailUniEth3Fragments OBJECT-TYPE
                        SYNTAX Counter64
                        MAX-ACCESS read-only
                        STATUS current
                        DESCRIPTION
                                "The number of packets received that were fragments"
                        ::= { fkGponOnuPMStatsCurrentDetailUniEth3Entry 9 }

                
--  1.3.6.1.4.1.10428 9 1.101.23.7.3.5.1.10
                -- 1.3.6.1.4.1.10428 9 1.101.23.7.4.5.1.10
                fkGponOnuPMStatsCurrentDetailUniEth3Jabbers OBJECT-TYPE
                        SYNTAX Counter64
                        MAX-ACCESS read-only
                        STATUS current
                        DESCRIPTION
                                "The number of packets received that were jabbers"
                        ::= { fkGponOnuPMStatsCurrentDetailUniEth3Entry 10 }

                
--  1.3.6.1.4.1.10428 9 1.101.23.7.3.5.1.11
                -- 1.3.6.1.4.1.10428 9 1.101.23.7.4.5.1.11
                fkGponOnuPMStatsCurrentDetailUniEth3Pkt64Octets OBJECT-TYPE
                        SYNTAX Counter64
                        MAX-ACCESS read-only
                        STATUS current
                        DESCRIPTION
                                "The number of received packets (including bad packets) that were 64 octets long"
                        ::= { fkGponOnuPMStatsCurrentDetailUniEth3Entry 11 }

                
--  1.3.6.1.4.1.10428 9 1.101.23.7.3.5.1.12
                -- 1.3.6.1.4.1.10428 9 1.101.23.7.4.5.1.12
                fkGponOnuPMStatsCurrentDetailUniEth3Pkt65To127Octets OBJECT-TYPE
                        SYNTAX Counter64
                        MAX-ACCESS read-only
                        STATUS current
                        DESCRIPTION
                                "The number of received packets (including bad packets) that were 65..127 octets long"
                        ::= { fkGponOnuPMStatsCurrentDetailUniEth3Entry 12 }

                
--  1.3.6.1.4.1.10428 9 1.101.23.7.3.5.1.13
                -- 1.3.6.1.4.1.10428 9 1.101.23.7.4.5.1.13
                fkGponOnuPMStatsCurrentDetailUniEth3Pkt128To255Octets OBJECT-TYPE
                        SYNTAX Counter64
                        MAX-ACCESS read-only
                        STATUS current
                        DESCRIPTION
                                "The number of packets (including bad packets) received that were 128..255 octets long"
                        ::= { fkGponOnuPMStatsCurrentDetailUniEth3Entry 13 }

                
--  1.3.6.1.4.1.10428 9 1.101.23.7.3.5.1.14
                -- 1.3.6.1.4.1.10428 9 1.101.23.7.4.5.1.14
                fkGponOnuPMStatsCurrentDetailUniEth3Pkt256To511Octets OBJECT-TYPE
                        SYNTAX Counter64
                        MAX-ACCESS read-only
                        STATUS current
                        DESCRIPTION
                                "The number of packets (including bad packets) received that were 256..511 octets long"
                        ::= { fkGponOnuPMStatsCurrentDetailUniEth3Entry 14 }

                
--  1.3.6.1.4.1.10428 9 1.101.23.7.3.5.1.15
                -- 1.3.6.1.4.1.10428 9 1.101.23.7.4.5.1.15
                fkGponOnuPMStatsCurrentDetailUniEth3Pkt512To1023Octets OBJECT-TYPE
                        SYNTAX Counter64
                        MAX-ACCESS read-only
                        STATUS current
                        DESCRIPTION
                                "The number of packets (including bad packets) received that were 512..1023 octets long"
                        ::= { fkGponOnuPMStatsCurrentDetailUniEth3Entry 15 }

                
--  1.3.6.1.4.1.10428 9 1.101.23.7.3.5.1.16
                -- 1.3.6.1.4.1.10428 9 1.101.23.7.4.5.1.16
                fkGponOnuPMStatsCurrentDetailUniEth3Pkt1024To1518Octets OBJECT-TYPE
                        SYNTAX Counter64
                        MAX-ACCESS read-only
                        STATUS current
                        DESCRIPTION
                                "The number of packets (including bad packets) received that were 1024..1518 octets long"
                        ::= { fkGponOnuPMStatsCurrentDetailUniEth3Entry 16 }

                
                -- 1.3.6.1.4.1.10428 9 1.101.23.7.5
                fkGponOnuIgmpPmStatistics OBJECT IDENTIFIER ::= { fkGponStatistics 5 }

                
                -- 1.3.6.1.4.1.10428 9 1.101.23.7.5.1
                fkGponOnuIgmpPmStatisticsTable OBJECT-TYPE
                        SYNTAX SEQUENCE OF FkGponOnuIgmpPmStatisticsEntry
                        MAX-ACCESS not-accessible
                        STATUS current
                        DESCRIPTION
                                "Description."
                        ::= { fkGponOnuIgmpPmStatistics 1 }

                
                -- 1.3.6.1.4.1.10428 9 1.101.23.7.5.1.1
                fkGponOnuIgmpPmStatisticsEntry OBJECT-TYPE
                        SYNTAX FkGponOnuIgmpPmStatisticsEntry
                        MAX-ACCESS not-accessible
                        STATUS current
                        DESCRIPTION
                                "Description."
                        INDEX { fkGponOltId, fkGponOnuId, fkGponOnuIgmpPmStatisticsSlotType, fkGponOnuIgmpPmStatisticsPortIndex }
                        ::= { fkGponOnuIgmpPmStatisticsTable 1 }

                
                FkGponOnuIgmpPmStatisticsEntry ::=
                        SEQUENCE { 
                                fkGponOnuIgmpPmStatisticsSlotType
                                        INTEGER,
                                fkGponOnuIgmpPmStatisticsPortIndex
                                        Integer32,
                                fkGponOnuIgmpPmStatisticsSuccessfulJoins
                                        Integer32,
                                fkGponOnuIgmpPmStatisticsUnsuccessfulJoins
                                        Integer32,
                                fkGponOnuIgmpPmStatisticsLeaveMessages
                                        Integer32,
                                fkGponOnuIgmpPmStatisticsGeneralQueries
                                        Integer32,
                                fkGponOnuIgmpPmStatisticsSpecificQueries
                                        Integer32,
                                fkGponOnuIgmpPmStatisticsInvalidIGMPMessages
                                        Integer32
                         }

                -- 1.3.6.1.4.1.10428 9 1.101.23.7.5.1.1.1
                fkGponOnuIgmpPmStatisticsSlotType OBJECT-TYPE
                        SYNTAX INTEGER
                                {
                                ethernet(1),
                                pots(2),
                                ces(3),
                                video(4),
                                virtualEthernet(5)
                                }
                        MAX-ACCESS read-only
                        STATUS current
                        DESCRIPTION
                                "The slot type"
                        ::= { fkGponOnuIgmpPmStatisticsEntry 1 }

                
                -- 1.3.6.1.4.1.10428 9 1.101.23.7.5.1.1.2
                fkGponOnuIgmpPmStatisticsPortIndex OBJECT-TYPE
                        SYNTAX Integer32 (1..65535)
                        MAX-ACCESS read-only
                        STATUS current
                        DESCRIPTION
                                "The port index."
                        ::= { fkGponOnuIgmpPmStatisticsEntry 2 }

                
                -- 1.3.6.1.4.1.10428 9 1.101.23.7.5.1.1.3
                fkGponOnuIgmpPmStatisticsSuccessfulJoins OBJECT-TYPE
                        SYNTAX Integer32
                        MAX-ACCESS read-only
                        STATUS current
                        DESCRIPTION
                                "The successful Joins."
                        ::= { fkGponOnuIgmpPmStatisticsEntry 3 }

                
                -- 1.3.6.1.4.1.10428 9 1.101.23.7.5.1.1.4
                fkGponOnuIgmpPmStatisticsUnsuccessfulJoins OBJECT-TYPE
                        SYNTAX Integer32
                        MAX-ACCESS read-only
                        STATUS current
                        DESCRIPTION
                                "The unsuccessful Joins."
                        ::= { fkGponOnuIgmpPmStatisticsEntry 4 }

                
                -- 1.3.6.1.4.1.10428 9 1.101.23.7.5.1.1.5
                fkGponOnuIgmpPmStatisticsLeaveMessages OBJECT-TYPE
                        SYNTAX Integer32
                        MAX-ACCESS read-only
                        STATUS current
                        DESCRIPTION
                                "The leave messages."
                        ::= { fkGponOnuIgmpPmStatisticsEntry 5 }

                
                -- 1.3.6.1.4.1.10428 9 1.101.23.7.5.1.1.6
                fkGponOnuIgmpPmStatisticsGeneralQueries OBJECT-TYPE
                        SYNTAX Integer32
                        MAX-ACCESS read-only
                        STATUS current
                        DESCRIPTION
                                "The General Queries "
                        ::= { fkGponOnuIgmpPmStatisticsEntry 6 }

                
                -- 1.3.6.1.4.1.10428 9 1.101.23.7.5.1.1.7
                fkGponOnuIgmpPmStatisticsSpecificQueries OBJECT-TYPE
                        SYNTAX Integer32
                        MAX-ACCESS read-only
                        STATUS current
                        DESCRIPTION
                                "The Specific Queries"
                        ::= { fkGponOnuIgmpPmStatisticsEntry 7 }

                
                -- 1.3.6.1.4.1.10428 9 1.101.23.7.5.1.1.8
                fkGponOnuIgmpPmStatisticsInvalidIGMPMessages OBJECT-TYPE
                        SYNTAX Integer32
                        MAX-ACCESS read-only
                        STATUS current
                        DESCRIPTION
                                "The Invalid IGMP Messages"
                        ::= { fkGponOnuIgmpPmStatisticsEntry 8 }

                
                -- 1.3.6.1.4.1.10428 9 1.101.23.7.5.2
                fkGponOnuIgmpPmStatisticsControl OBJECT IDENTIFIER ::= { fkGponOnuIgmpPmStatistics 2 }

                
                -- 1.3.6.1.4.1.10428 9 1.101.23.7.5.2.1
                fkGponOnuIgmpPmStatisticsControlRequest OBJECT-TYPE
                        SYNTAX INTEGER
                                {
                                updateOnuIgmpPmData(1),
                                clearOnuIgmpPmData(2)
                                }
                        MAX-ACCESS read-write
                        STATUS current
                        DESCRIPTION
                                "The request of a user command"
                        ::= { fkGponOnuIgmpPmStatisticsControl 1 }

                
                -- 1.3.6.1.4.1.10428 9 1.101.23.7.5.2.2
                fkGponOnuIgmpPmStatisticsControlStatus OBJECT-TYPE
                        SYNTAX FkControlStatusType
                        MAX-ACCESS read-only
                        STATUS current
                        DESCRIPTION
                                "The status of user command"
                        ::= { fkGponOnuIgmpPmStatisticsControl 2 }

                
                -- 1.3.6.1.4.1.10428 9 1.101.23.7.5.2.3
                fkGponOnuIgmpPmStatisticsControlTimer OBJECT-TYPE
                        SYNTAX Gauge32
                        MAX-ACCESS read-write
                        STATUS current
                        DESCRIPTION
                                "The maximum time for the manager for a long running user command"
                        ::= { fkGponOnuIgmpPmStatisticsControl 3 }

                
                -- 1.3.6.1.4.1.10428 9 1.101.23.7.5.2.4
                fkGponOnuIgmpPmStatisticsControlTimeStamp OBJECT-TYPE
                        SYNTAX TimeTicks
                        MAX-ACCESS read-only
                        STATUS current
                        DESCRIPTION
                                "The time stamp of the last command(end of command)"
                        ::= { fkGponOnuIgmpPmStatisticsControl 4 }

                
                -- 1.3.6.1.4.1.10428 9 1.101.23.7.5.2.5
                fkGponOnuIgmpPmStatisticsControlReqResult OBJECT-TYPE
                        SYNTAX FkControlRequestResultType
                        MAX-ACCESS read-only
                        STATUS current
                        DESCRIPTION
                                "The result of the last user command"
                        ::= { fkGponOnuIgmpPmStatisticsControl 5 }

                
                -- 1.3.6.1.4.1.10428 9 1.101.23.7.5.2.6
                fkGponOnuIgmpPmStatisticsControlOltIndex OBJECT-TYPE
                        SYNTAX Integer32
                        MAX-ACCESS read-write
                        STATUS current
                        DESCRIPTION
                                "The OLT index."
                        ::= { fkGponOnuIgmpPmStatisticsControl 6 }

                
                -- 1.3.6.1.4.1.10428 9 1.101.23.7.5.2.7
                fkGponOnuIgmpPmStatisticsControlOnuIndex OBJECT-TYPE
                        SYNTAX Integer32
                        MAX-ACCESS read-write
                        STATUS current
                        DESCRIPTION
                                "The ONU index."
                        ::= { fkGponOnuIgmpPmStatisticsControl 7 }

                
                -- 1.3.6.1.4.1.10428 9 1.101.23.7.5.2.8
                fkGponOnuIgmpPmStatisticsControlSlotType OBJECT-TYPE
                        SYNTAX INTEGER
                                {
                                ethernet(1),
                                pots(2),
                                ces(3),
                                video(4),
                                virtualEthernet(5)
                                }
                        MAX-ACCESS read-write
                        STATUS current
                        DESCRIPTION
                                "The slot type."
                        ::= { fkGponOnuIgmpPmStatisticsControl 8 }

                
                -- 1.3.6.1.4.1.10428 9 1.101.23.7.5.2.9
                fkGponOnuIgmpPmStatisticsControlPortIndex OBJECT-TYPE
                        SYNTAX Integer32
                        MAX-ACCESS read-write
                        STATUS current
                        DESCRIPTION
                                "The port index."
                        ::= { fkGponOnuIgmpPmStatisticsControl 9 }

                
                -- 1.3.6.1.4.1.10428 9 1.101.23.7.5.3
                fkGponOnuIgmpPmStatisticsNotification OBJECT IDENTIFIER ::= { fkGponOnuIgmpPmStatistics 3 }

                
                -- 1.3.6.1.4.1.10428 9 1.101.23.7.5.3.1
                fkGponOnuIgmpPmStatisticsPmDataChanged NOTIFICATION-TYPE
                        OBJECTS { fkGponOnuIgmpPmStatisticsControlRequest, fkGponOnuIgmpPmStatisticsControlTimeStamp, fkGponOnuIgmpPmStatisticsControlReqResult, fkGponOnuIgmpPmStatisticsControlOltIndex, fkGponOnuIgmpPmStatisticsControlOnuIndex, 
                                fkGponOnuIgmpPmStatisticsControlSlotType, fkGponOnuIgmpPmStatisticsControlPortIndex }
                        STATUS current
                        DESCRIPTION 
                                "updateOnuIgmpPmData"
                        ::= { fkGponOnuIgmpPmStatisticsNotification 1 }

                
                -- 1.3.6.1.4.1.10428 9 1.101.23.7.5.3.2
                fkGponOnuIgmpPmStatisticsPmDataCleared NOTIFICATION-TYPE
                        OBJECTS { fkGponOnuIgmpPmStatisticsControlRequest, fkGponOnuIgmpPmStatisticsControlTimeStamp, fkGponOnuIgmpPmStatisticsControlReqResult, fkGponOnuIgmpPmStatisticsControlOltIndex, fkGponOnuIgmpPmStatisticsControlOnuIndex, 
                                fkGponOnuIgmpPmStatisticsControlSlotType, fkGponOnuIgmpPmStatisticsControlPortIndex }
                        STATUS current
                        DESCRIPTION 
                                "clearOnuIgmpPmData"
                        ::= { fkGponOnuIgmpPmStatisticsNotification 2 }

                
                -- 1.3.6.1.4.1.10428 9 1.101.23.7.6
                fkGponOnuPmStatsUniAvg OBJECT IDENTIFIER ::= { fkGponStatistics 6 }

                
                -- 1.3.6.1.4.1.10428 9 1.101.23.7.6.1
                fkGponOnuPmStatsUniAvgTable OBJECT-TYPE
                        SYNTAX SEQUENCE OF FkGponOnuPmStatsUniAvgEntry
                        MAX-ACCESS not-accessible
                        STATUS current
                        DESCRIPTION
                                "Description."
                        ::= { fkGponOnuPmStatsUniAvg 1 }

                
                -- 1.3.6.1.4.1.10428 9 1.101.23.7.6.1.1
                fkGponOnuPmStatsUniAvgEntry OBJECT-TYPE
                        SYNTAX FkGponOnuPmStatsUniAvgEntry
                        MAX-ACCESS not-accessible
                        STATUS current
                        DESCRIPTION
                                "Description."
                        INDEX { fkGponOltId, fkGponOnuId, fkGponOnuPmStatsUniAvgPort }
                        ::= { fkGponOnuPmStatsUniAvgTable 1 }

                
                FkGponOnuPmStatsUniAvgEntry ::=
                        SEQUENCE { 
                                fkGponOnuPmStatsUniAvgPort
                                        Integer32,
                                fkGponOnuPmStatsUniAvgEthFrameUpPackets
                                        Counter64,
                                fkGponOnuPmStatsUniAvgEthFrameUpBits
                                        Counter64,
                                fkGponOnuPmStatsUniAvgEthFrameDownPackets
                                        Counter64,
                                fkGponOnuPmStatsUniAvgEthFrameDownBits
                                        Counter64
                         }

                -- 1.3.6.1.4.1.10428 9 1.101.23.7.6.1.1.1
                fkGponOnuPmStatsUniAvgPort OBJECT-TYPE
                        SYNTAX Integer32 (1..65535)
                        MAX-ACCESS read-only
                        STATUS current
                        DESCRIPTION
                                "The port index."
                        ::= { fkGponOnuPmStatsUniAvgEntry 1 }

                
                -- 1.3.6.1.4.1.10428 9 1.101.23.7.6.1.1.2
                fkGponOnuPmStatsUniAvgEthFrameUpPackets OBJECT-TYPE
                        SYNTAX Counter64
                        MAX-ACCESS read-only
                        STATUS current
                        DESCRIPTION
                                "The average frame up packets."
                        ::= { fkGponOnuPmStatsUniAvgEntry 2 }

                
                -- 1.3.6.1.4.1.10428 9 1.101.23.7.6.1.1.3
                fkGponOnuPmStatsUniAvgEthFrameUpBits OBJECT-TYPE
                        SYNTAX Counter64
                        MAX-ACCESS read-only
                        STATUS current
                        DESCRIPTION
                                "The average frame up bits."
                        ::= { fkGponOnuPmStatsUniAvgEntry 3 }

                
                -- 1.3.6.1.4.1.10428 9 1.101.23.7.6.1.1.4
                fkGponOnuPmStatsUniAvgEthFrameDownPackets OBJECT-TYPE
                        SYNTAX Counter64
                        MAX-ACCESS read-only
                        STATUS current
                        DESCRIPTION
                                "The average frame down packets."
                        ::= { fkGponOnuPmStatsUniAvgEntry 4 }

                
                -- 1.3.6.1.4.1.10428 9 1.101.23.7.6.1.1.5
                fkGponOnuPmStatsUniAvgEthFrameDownBits OBJECT-TYPE
                        SYNTAX Counter64
                        MAX-ACCESS read-only
                        STATUS current
                        DESCRIPTION
                                "The average frame down bits."
                        ::= { fkGponOnuPmStatsUniAvgEntry 5 }

                
                -- 1.3.6.1.4.1.10428 9 1.101.23.7.6.2
                fkGponOnuPmStatsUniAvgControl OBJECT IDENTIFIER ::= { fkGponOnuPmStatsUniAvg 2 }

                
                -- 1.3.6.1.4.1.10428 9 1.101.23.7.6.2.1
                fkGponOnuPmStatsUniAvgControlRequest OBJECT-TYPE
                        SYNTAX INTEGER { updateAvgStats(1) }
                        MAX-ACCESS read-write
                        STATUS current
                        DESCRIPTION
                                "The request of a user command"
                        ::= { fkGponOnuPmStatsUniAvgControl 1 }

                
                -- 1.3.6.1.4.1.10428 9 1.101.23.7.6.2.2
                fkGponOnuPmStatsUniAvgControlStatus OBJECT-TYPE
                        SYNTAX FkControlStatusType
                        MAX-ACCESS read-only
                        STATUS current
                        DESCRIPTION
                                "The status of user command"
                        ::= { fkGponOnuPmStatsUniAvgControl 2 }

                
                -- 1.3.6.1.4.1.10428 9 1.101.23.7.6.2.3
                fkGponOnuPmStatsUniAvgControlTimer OBJECT-TYPE
                        SYNTAX Gauge32
                        MAX-ACCESS read-write
                        STATUS current
                        DESCRIPTION
                                "The maximum time for the manager for a long running user command"
                        ::= { fkGponOnuPmStatsUniAvgControl 3 }

                
                -- 1.3.6.1.4.1.10428 9 1.101.23.7.6.2.4
                fkGponOnuPmStatsUniAvgControlTimeStamp OBJECT-TYPE
                        SYNTAX TimeTicks
                        MAX-ACCESS read-only
                        STATUS current
                        DESCRIPTION
                                "The time stamp of the last command(end of command)"
                        ::= { fkGponOnuPmStatsUniAvgControl 4 }

                
                -- 1.3.6.1.4.1.10428 9 1.101.23.7.6.2.5
                fkGponOnuPmStatsUniAvgControlReqResult OBJECT-TYPE
                        SYNTAX FkControlRequestResultType
                        MAX-ACCESS read-only
                        STATUS current
                        DESCRIPTION
                                "The result of the last user command"
                        ::= { fkGponOnuPmStatsUniAvgControl 5 }

                
                -- 1.3.6.1.4.1.10428 9 1.101.23.7.6.2.6
                fkGponOnuPmStatsUniAvgControlOltindex OBJECT-TYPE
                        SYNTAX Integer32
                        MAX-ACCESS read-write
                        STATUS current
                        DESCRIPTION
                                "The OLT index."
                        ::= { fkGponOnuPmStatsUniAvgControl 6 }

                
                -- 1.3.6.1.4.1.10428 9 1.101.23.7.6.2.7
                fkGponOnuPmStatsUniAvgControlOnuIndex OBJECT-TYPE
                        SYNTAX Integer32
                        MAX-ACCESS read-write
                        STATUS current
                        DESCRIPTION
                                "The ONU index."
                        ::= { fkGponOnuPmStatsUniAvgControl 7 }

                
                -- 1.3.6.1.4.1.10428 9 1.101.23.7.6.2.8
                fkGponOnuPmStatsUniAvgControlPort OBJECT-TYPE
                        SYNTAX Integer32
                        MAX-ACCESS read-write
                        STATUS current
                        DESCRIPTION
                                "The port index."
                        ::= { fkGponOnuPmStatsUniAvgControl 8 }

                
                -- 1.3.6.1.4.1.10428 9 1.101.23.7.6.3
                fkGponOnuPmStatsUniAvgNotification OBJECT IDENTIFIER ::= { fkGponOnuPmStatsUniAvg 3 }

                
                -- 1.3.6.1.4.1.10428 9 1.101.23.7.6.3.1
                fkGponOnuPmStatsUniAvgUpdated NOTIFICATION-TYPE
                        OBJECTS { fkGponOnuPmStatsUniAvgControlRequest, fkGponOnuPmStatsUniAvgControlTimeStamp, fkGponOnuPmStatsUniAvgControlReqResult, fkGponOnuPmStatsUniAvgControlOltindex, fkGponOnuPmStatsUniAvgControlOnuIndex, 
                                fkGponOnuPmStatsUniAvgControlPort }
                        STATUS current
                        DESCRIPTION 
                                "updateAvgStats"
                        ::= { fkGponOnuPmStatsUniAvgNotification 1 }

                
--  1.3.6.1.4.1.10428 9 1.101.23.8
                -- 1.3.6.1.4.1.10428 9 1.101.23.8
                fkGponFirmwareMgmt OBJECT IDENTIFIER ::= { fkGpon 8 }

                
--  1.3.6.1.4.1.10428 9 1.101.23.8.1
                -- 1.3.6.1.4.1.10428 9 1.101.23.8.1
                fkGponFirmwareTable OBJECT-TYPE
                        SYNTAX SEQUENCE OF FkGponFirmwareEntry
                        MAX-ACCESS not-accessible
                        STATUS current
                        DESCRIPTION
                                "fkGponFirmwareTable"
                        ::= { fkGponFirmwareMgmt 1 }

                
--  1.3.6.1.4.1.10428 9 1.101.23.8.1.1
                -- 1.3.6.1.4.1.10428 9 1.101.23.8.1.1
                fkGponFirmwareEntry OBJECT-TYPE
                        SYNTAX FkGponFirmwareEntry
                        MAX-ACCESS not-accessible
                        STATUS current
                        DESCRIPTION
                                "key: fkGponFirmwareType, fkGponFirmwareName"
                        INDEX { fkGponFirmwareType, fkGponFirmwareName }
                        ::= { fkGponFirmwareTable 1 }

                
                FkGponFirmwareEntry ::=
                        SEQUENCE { 
                                fkGponFirmwareType
                                        INTEGER,
                                fkGponFirmwareName
                                        OCTET STRING
                         }

--  1.3.6.1.4.1.10428 9 1.101.23.8.1.1.1
                -- 1.3.6.1.4.1.10428 9 1.101.23.8.1.1.1
                fkGponFirmwareType OBJECT-TYPE
                        SYNTAX INTEGER
                                {
                                olt(1),
                                onu(2)
                                }
                        MAX-ACCESS read-only
                        STATUS current
                        DESCRIPTION
                                "Firmware type."
                        ::= { fkGponFirmwareEntry 1 }

                
--  1.3.6.1.4.1.10428 9 1.101.23.8.1.1.2
                -- 1.3.6.1.4.1.10428 9 1.101.23.8.1.1.2
                fkGponFirmwareName OBJECT-TYPE
                        SYNTAX OCTET STRING (SIZE (1..64))
                        MAX-ACCESS read-only
                        STATUS current
                        DESCRIPTION
                                "Firmware name."
                        ::= { fkGponFirmwareEntry 2 }

                
--  1.3.6.1.4.1.10428 9 1.101.23.8.2
                -- 1.3.6.1.4.1.10428 9 1.101.23.8.2
                fkGponFirmwareControl OBJECT IDENTIFIER ::= { fkGponFirmwareMgmt 2 }

                
--  1.3.6.1.4.1.10428 9 1.101.23.8.2.1
                -- 1.3.6.1.4.1.10428 9 1.101.23.8.2.1
                fkGponFirmwareControlRequest OBJECT-TYPE
                        SYNTAX INTEGER
                                {
                                setGponFirmwareUpgradeProfile(1),
                                deleteGponFirmware(2),
                                setGponFirmwareDownload(3)
                                }
                        MAX-ACCESS read-write
                        STATUS current
                        DESCRIPTION
                                "The request of a user command"
                        ::= { fkGponFirmwareControl 1 }

                
--  1.3.6.1.4.1.10428 9 1.101.23.8.2.2
                -- 1.3.6.1.4.1.10428 9 1.101.23.8.2.2
                fkGponFirmwareControlStatus OBJECT-TYPE
                        SYNTAX FkControlStatusType
                        MAX-ACCESS read-only
                        STATUS current
                        DESCRIPTION
                                "The status of user command"
                        ::= { fkGponFirmwareControl 2 }

                
--  1.3.6.1.4.1.10428 9 1.101.23.8.2.3
                -- 1.3.6.1.4.1.10428 9 1.101.23.8.2.3
                fkGponFirmwareControlTimer OBJECT-TYPE
                        SYNTAX Gauge32
                        MAX-ACCESS read-write
                        STATUS current
                        DESCRIPTION
                                "The maximum time for the manager for a long running user command"
                        ::= { fkGponFirmwareControl 3 }

                
--  1.3.6.1.4.1.10428 9 1.101.23.8.2.4
                -- 1.3.6.1.4.1.10428 9 1.101.23.8.2.4
                fkGponFirmwareControlTimeStamp OBJECT-TYPE
                        SYNTAX TimeTicks
                        MAX-ACCESS read-only
                        STATUS current
                        DESCRIPTION
                                "The time stamp of the last command(end of command)"
                        ::= { fkGponFirmwareControl 4 }

                
--  1.3.6.1.4.1.10428 9 1.101.23.8.2.5
                -- 1.3.6.1.4.1.10428 9 1.101.23.8.2.5
                fkGponFirmwareControlReqResult OBJECT-TYPE
                        SYNTAX FkControlRequestResultType
                        MAX-ACCESS read-only
                        STATUS current
                        DESCRIPTION
                                "The result of the last user command"
                        ::= { fkGponFirmwareControl 5 }

                
--  1.3.6.1.4.1.10428 9 1.101.23.8.2.6
                -- 1.3.6.1.4.1.10428 9 1.101.23.8.2.6
                fkGponFirmwareControlName OBJECT-TYPE
                        SYNTAX OCTET STRING (SIZE (1..128))
                        MAX-ACCESS read-write
                        STATUS current
                        DESCRIPTION
                                "Firmware filename."
                        ::= { fkGponFirmwareControl 6 }

                
--  1.3.6.1.4.1.10428 9 1.101.23.8.2.7
                -- 1.3.6.1.4.1.10428 9 1.101.23.8.2.7
                fkGponFirmwareControlUpgradeMethod OBJECT-TYPE
                        SYNTAX INTEGER
                                {
                                ftp(1),
                                tftp(2)
                                }
                        MAX-ACCESS read-write
                        STATUS current
                        DESCRIPTION
                                "1: using FTP
                                2: using TFTP"
                        ::= { fkGponFirmwareControl 7 }

                
--  1.3.6.1.4.1.10428 9 1.101.23.8.2.8
                -- 1.3.6.1.4.1.10428 9 1.101.23.8.2.8
                fkGponFirmwareControlUpgradeMode OBJECT-TYPE
                        SYNTAX INTEGER
                                {
                                upload(1),
                                download(2)
                                }
                        MAX-ACCESS read-write
                        STATUS current
                        DESCRIPTION
                                "1. Uploading firmware to the remote-host
                                2. Downloading firmware from the remote-host."
                        ::= { fkGponFirmwareControl 8 }

                
--  1.3.6.1.4.1.10428 9 1.101.23.8.2.9
                -- 1.3.6.1.4.1.10428 9 1.101.23.8.2.9
                fkGponFirmwareControlServerAddress OBJECT-TYPE
                        SYNTAX IpAddress
                        MAX-ACCESS read-write
                        STATUS current
                        DESCRIPTION
                                "The remote-host's IP address"
                        ::= { fkGponFirmwareControl 9 }

                
--  1.3.6.1.4.1.10428 9 1.101.23.8.2.10
                -- 1.3.6.1.4.1.10428 9 1.101.23.8.2.10
                fkGponFirmwareControlUser OBJECT-TYPE
                        SYNTAX OCTET STRING
                        MAX-ACCESS read-write
                        STATUS current
                        DESCRIPTION
                                "Account-name"
                        ::= { fkGponFirmwareControl 10 }

                
--  1.3.6.1.4.1.10428 9 1.101.23.8.2.11
                -- 1.3.6.1.4.1.10428 9 1.101.23.8.2.11
                fkGponFirmwareControlPasswd OBJECT-TYPE
                        SYNTAX OCTET STRING
                        MAX-ACCESS read-write
                        STATUS current
                        DESCRIPTION
                                "Account-password"
                        ::= { fkGponFirmwareControl 11 }

                
--  1.3.6.1.4.1.10428 9 1.101.23.8.3
                -- 1.3.6.1.4.1.10428 9 1.101.23.8.3
                fkGponFirmwareNotification OBJECT IDENTIFIER ::= { fkGponFirmwareMgmt 3 }

                
--  1.3.6.1.4.1.10428 9 1.101.23.8.3.1
                -- 1.3.6.1.4.1.10428 9 1.101.23.8.3.1
                fkGponFirmwareUpgradeProfileChanged NOTIFICATION-TYPE
                        OBJECTS { fkGponFirmwareControlRequest, fkGponFirmwareControlTimeStamp, fkGponFirmwareControlReqResult, fkGponFirmwareControlName, fkGponFirmwareControlUpgradeMethod, 
                                fkGponFirmwareControlUpgradeMode, fkGponFirmwareControlServerAddress, fkGponFirmwareControlUser, fkGponFirmwareControlPasswd }
                        STATUS current
                        DESCRIPTION 
                                "Description."
                        ::= { fkGponFirmwareNotification 1 }

                
--  1.3.6.1.4.1.10428 9 1.101.23.8.3.2
                -- 1.3.6.1.4.1.10428 9 1.101.23.8.3.2
                fkGponFirmwareDeleted NOTIFICATION-TYPE
                        OBJECTS { fkGponFirmwareControlRequest, fkGponFirmwareControlTimeStamp, fkGponFirmwareControlReqResult, fkGponFirmwareControlName }
                        STATUS current
                        DESCRIPTION 
                                "Description."
                        ::= { fkGponFirmwareNotification 2 }

                
--  1.3.6.1.4.1.10428 9 1.101.23.8.3.3
                -- 1.3.6.1.4.1.10428 9 1.101.23.8.3.3
                fkGponFirmwareDownloadChanged NOTIFICATION-TYPE
                        OBJECTS { fkGponFirmwareControlRequest, fkGponFirmwareControlTimeStamp, fkGponFirmwareControlReqResult, fkGponFirmwareControlName, fkGponFirmwareControlServerAddress, 
                                fkGponFirmwareControlUser, fkGponFirmwareControlPasswd }
                        STATUS current
                        DESCRIPTION 
                                "Description."
                        ::= { fkGponFirmwareNotification 3 }

                
--  1.3.6.1.4.1.10428 9 1.101.23.9
                -- 1.3.6.1.4.1.10428 9 1.101.23.9
                fkGponOnuFirmwareAutoUpgradeMgmt OBJECT IDENTIFIER ::= { fkGpon 9 }

                
--  1.3.6.1.4.1.10428 9 1.101.23.9.1
                -- 1.3.6.1.4.1.10428 9 1.101.23.9.1
                fkGponOnuFWAutoUpgrade OBJECT IDENTIFIER ::= { fkGponOnuFirmwareAutoUpgradeMgmt 1 }

                
--  1.3.6.1.4.1.10428 9 1.101.23.9.1.1
                -- 1.3.6.1.4.1.10428 9 1.101.23.9.1.1
                fkGponOnuFWAutoUpgradeTable OBJECT-TYPE
                        SYNTAX SEQUENCE OF FkGponOnuFWAutoUpgradeEntry
                        MAX-ACCESS not-accessible
                        STATUS current
                        DESCRIPTION
                                "fkGponOnuFWAutoUpgradeTable"
                        ::= { fkGponOnuFWAutoUpgrade 1 }

                
--  1.3.6.1.4.1.10428 9 1.101.23.9.1.1.1
                -- 1.3.6.1.4.1.10428 9 1.101.23.9.1.1.1
                fkGponOnuFWAutoUpgradeEntry OBJECT-TYPE
                        SYNTAX FkGponOnuFWAutoUpgradeEntry
                        MAX-ACCESS not-accessible
                        STATUS current
                        DESCRIPTION
                                "key: fkGponOltId"
                        INDEX { fkGponOltId }
                        ::= { fkGponOnuFWAutoUpgradeTable 1 }

                
                FkGponOnuFWAutoUpgradeEntry ::=
                        SEQUENCE { 
                                fkGponOnuFWAutoUpgradeMode
                                        INTEGER,
                                fkGponOnuFWAutoUpgradeVersionMatch
                                        INTEGER,
                                fkGponOnuFWAutoUpgradeInvalidVersionMatch
                                        INTEGER,
                                fkGponOnuFWAutoUpgradeStatus
                                        INTEGER,
                                fkGponOnuFWAutoUpgradeCurrentUgradingFWName
                                        OCTET STRING
                         }

--  1.3.6.1.4.1.10428 9 1.101.23.9.1.1.1.1
                -- 1.3.6.1.4.1.10428 9 1.101.23.9.1.1.1.1
                fkGponOnuFWAutoUpgradeMode OBJECT-TYPE
                        SYNTAX INTEGER
                                {
                                enable(1),
                                disable(2)
                                }
                        MAX-ACCESS read-only
                        STATUS current
                        DESCRIPTION
                                "Auto upgrade configuration."
                        ::= { fkGponOnuFWAutoUpgradeEntry 1 }

                
--  1.3.6.1.4.1.10428 9 1.101.23.9.1.1.1.2
                -- 1.3.6.1.4.1.10428 9 1.101.23.9.1.1.1.2
                fkGponOnuFWAutoUpgradeVersionMatch OBJECT-TYPE
                        SYNTAX INTEGER
                                {
                                enable(1),
                                disable(2)
                                }
                        MAX-ACCESS read-only
                        STATUS current
                        DESCRIPTION
                                "Upgrade if ONU's version is upper than auto-upgrade-fw."
                        ::= { fkGponOnuFWAutoUpgradeEntry 2 }

                
--  1.3.6.1.4.1.10428 9 1.101.23.9.1.1.1.3
                -- 1.3.6.1.4.1.10428 9 1.101.23.9.1.1.1.3
                fkGponOnuFWAutoUpgradeInvalidVersionMatch OBJECT-TYPE
                        SYNTAX INTEGER
                                {
                                enable(1),
                                disable(2)
                                }
                        MAX-ACCESS read-only
                        STATUS current
                        DESCRIPTION
                                "Upgrade if ONU's version is invalid."
                        ::= { fkGponOnuFWAutoUpgradeEntry 3 }

                
--  1.3.6.1.4.1.10428 9 1.101.23.9.1.1.1.4
                -- 1.3.6.1.4.1.10428 9 1.101.23.9.1.1.1.4
                fkGponOnuFWAutoUpgradeStatus OBJECT-TYPE
                        SYNTAX INTEGER
                                {
                                none(0),
                                downloadFirmware(1),
                                uploadFirmwareToGPIU(2),
                                upgradeOnuProgress(3),
                                upgradeOnuWating(4),
                                unknown(5)
                                }
                        MAX-ACCESS read-only
                        STATUS current
                        DESCRIPTION
                                "Auto upgrade status."
                        ::= { fkGponOnuFWAutoUpgradeEntry 4 }

                
--  1.3.6.1.4.1.10428 9 1.101.23.9.1.1.1.5
                -- 1.3.6.1.4.1.10428 9 1.101.23.9.1.1.1.5
                fkGponOnuFWAutoUpgradeCurrentUgradingFWName OBJECT-TYPE
                        SYNTAX OCTET STRING (SIZE (1..128))
                        MAX-ACCESS read-only
                        STATUS current
                        DESCRIPTION
                                "Firmware of current upgrading."
                        ::= { fkGponOnuFWAutoUpgradeEntry 5 }

                
--  1.3.6.1.4.1.10428 9 1.101.23.9.1.2
                -- 1.3.6.1.4.1.10428 9 1.101.23.9.1.2
                fkGponOnuFWAutoUpgradeControl OBJECT IDENTIFIER ::= { fkGponOnuFWAutoUpgrade 2 }

                
--  1.3.6.1.4.1.10428 9 1.101.23.9.1.2.1
                -- 1.3.6.1.4.1.10428 9 1.101.23.9.1.2.1
                fkGponOnuFWAutoUpgradeControlRequest OBJECT-TYPE
                        SYNTAX INTEGER
                                {
                                setAutoUpgradeMode(1),
                                setVersionMatch(2),
                                setInvalidVersionMatch(3)
                                }
                        MAX-ACCESS read-write
                        STATUS current
                        DESCRIPTION
                                "The request of a user command"
                        ::= { fkGponOnuFWAutoUpgradeControl 1 }

                
--  1.3.6.1.4.1.10428 9 1.101.23.9.1.2.2
                -- 1.3.6.1.4.1.10428 9 1.101.23.9.1.2.2
                fkGponOnuFWAutoUpgradeControlStatus OBJECT-TYPE
                        SYNTAX FkControlStatusType
                        MAX-ACCESS read-only
                        STATUS current
                        DESCRIPTION
                                "The status of user command"
                        ::= { fkGponOnuFWAutoUpgradeControl 2 }

                
--  1.3.6.1.4.1.10428 9 1.101.23.9.1.2.3
                -- 1.3.6.1.4.1.10428 9 1.101.23.9.1.2.3
                fkGponOnuFWAutoUpgradeControlTimer OBJECT-TYPE
                        SYNTAX Gauge32
                        MAX-ACCESS read-write
                        STATUS current
                        DESCRIPTION
                                "The maximum time for the manager for a long running user command"
                        ::= { fkGponOnuFWAutoUpgradeControl 3 }

                
--  1.3.6.1.4.1.10428 9 1.101.23.9.1.2.4
                -- 1.3.6.1.4.1.10428 9 1.101.23.9.1.2.4
                fkGponOnuFWAutoUpgradeControlTimeStamp OBJECT-TYPE
                        SYNTAX TimeTicks
                        MAX-ACCESS read-only
                        STATUS current
                        DESCRIPTION
                                "The time stamp of the last command(end of command)"
                        ::= { fkGponOnuFWAutoUpgradeControl 4 }

                
--  1.3.6.1.4.1.10428 9 1.101.23.9.1.2.5
                -- 1.3.6.1.4.1.10428 9 1.101.23.9.1.2.5
                fkGponOnuFWAutoUpgradeControlReqResult OBJECT-TYPE
                        SYNTAX FkControlRequestResultType
                        MAX-ACCESS read-only
                        STATUS current
                        DESCRIPTION
                                "The result of the last user command"
                        ::= { fkGponOnuFWAutoUpgradeControl 5 }

                
--  1.3.6.1.4.1.10428 9 1.101.23.9.1.2.6
                -- 1.3.6.1.4.1.10428 9 1.101.23.9.1.2.6
                fkGponOnuFWAutoUpgradeControlOltId OBJECT-TYPE
                        SYNTAX INTEGER (1..65535)
                        MAX-ACCESS read-write
                        STATUS current
                        DESCRIPTION
                                "Gpon Olt Index."
                        ::= { fkGponOnuFWAutoUpgradeControl 6 }

                
--  1.3.6.1.4.1.10428 9 1.101.23.9.1.2.7
                -- 1.3.6.1.4.1.10428 9 1.101.23.9.1.2.7
                fkGponOnuFWAutoUpgradeControlMode OBJECT-TYPE
                        SYNTAX INTEGER
                                {
                                enable(1),
                                disable(2)
                                }
                        MAX-ACCESS read-write
                        STATUS current
                        DESCRIPTION
                                "Auto upgrade configuration."
                        ::= { fkGponOnuFWAutoUpgradeControl 7 }

                
--  1.3.6.1.4.1.10428 9 1.101.23.9.1.2.8
                -- 1.3.6.1.4.1.10428 9 1.101.23.9.1.2.8
                fkGponOnuFWAutoUpgradeControlVersionMatch OBJECT-TYPE
                        SYNTAX INTEGER
                                {
                                enable(1),
                                disable(2)
                                }
                        MAX-ACCESS read-write
                        STATUS current
                        DESCRIPTION
                                "Upgrade if ONU's version is upper than auto-upgrade-fw."
                        ::= { fkGponOnuFWAutoUpgradeControl 8 }

                
--  1.3.6.1.4.1.10428 9 1.101.23.9.1.2.9
                -- 1.3.6.1.4.1.10428 9 1.101.23.9.1.2.9
                fkGponOnuFWAutoUpgradeControlInvalidVersionMatch OBJECT-TYPE
                        SYNTAX INTEGER
                                {
                                enable(1),
                                disable(2)
                                }
                        MAX-ACCESS read-write
                        STATUS current
                        DESCRIPTION
                                "Upgrade if ONU's version is invalid."
                        ::= { fkGponOnuFWAutoUpgradeControl 9 }

                
--  1.3.6.1.4.1.10428 9 1.101.23.9.1.3
                -- 1.3.6.1.4.1.10428 9 1.101.23.9.1.3
                fkGponOnuFWAutoUpgradeNotification OBJECT IDENTIFIER ::= { fkGponOnuFWAutoUpgrade 3 }

                
--  1.3.6.1.4.1.10428 9 1.101.23.9.1.3.1
                -- 1.3.6.1.4.1.10428 9 1.101.23.9.1.3.1
                fkGponOnuFWAutoUpgradeModeChanged NOTIFICATION-TYPE
                        OBJECTS { fkGponOnuFWAutoUpgradeControlRequest, fkGponOnuFWAutoUpgradeControlTimeStamp, fkGponOnuFWAutoUpgradeControlReqResult, fkGponOnuFWAutoUpgradeControlOltId, fkGponOnuFWAutoUpgradeControlMode
                                 }
                        STATUS current
                        DESCRIPTION 
                                "Description."
                        ::= { fkGponOnuFWAutoUpgradeNotification 1 }

                
--  1.3.6.1.4.1.10428 9 1.101.23.9.1.3.2
                -- 1.3.6.1.4.1.10428 9 1.101.23.9.1.3.2
                fkGponOnuFWAutoUpgradeVersionMatchChanged NOTIFICATION-TYPE
                        OBJECTS { fkGponOnuFWAutoUpgradeControlRequest, fkGponOnuFWAutoUpgradeControlTimeStamp, fkGponOnuFWAutoUpgradeControlReqResult, fkGponOnuFWAutoUpgradeControlOltId, fkGponOnuFWAutoUpgradeControlVersionMatch
                                 }
                        STATUS current
                        DESCRIPTION 
                                "Description."
                        ::= { fkGponOnuFWAutoUpgradeNotification 2 }

                
--  1.3.6.1.4.1.10428 9 1.101.23.9.1.3.3
                -- 1.3.6.1.4.1.10428 9 1.101.23.9.1.3.3
                fkGponOnuFWAutoUpgradeInvalidVersionMatchChanged NOTIFICATION-TYPE
                        OBJECTS { fkGponOnuFWAutoUpgradeControlRequest, fkGponOnuFWAutoUpgradeControlTimeStamp, fkGponOnuFWAutoUpgradeControlReqResult, fkGponOnuFWAutoUpgradeControlOltId, fkGponOnuFWAutoUpgradeControlInvalidVersionMatch
                                 }
                        STATUS current
                        DESCRIPTION 
                                "Description."
                        ::= { fkGponOnuFWAutoUpgradeNotification 3 }

                
--  1.3.6.1.4.1.10428 9 1.101.23.9.2
                -- 1.3.6.1.4.1.10428 9 1.101.23.9.2
                fkGponOnuFWAutoUpgradeTime OBJECT IDENTIFIER ::= { fkGponOnuFirmwareAutoUpgradeMgmt 2 }

                
--  1.3.6.1.4.1.10428 9 1.101.23.9.2.1
                -- 1.3.6.1.4.1.10428 9 1.101.23.9.2.1
                fkGponOnuFWAutoUpgradeTimeInfo OBJECT IDENTIFIER ::= { fkGponOnuFWAutoUpgradeTime 1 }

                
--  1.3.6.1.4.1.10428 9 1.101.23.9.2.1.1
                -- 1.3.6.1.4.1.10428 9 1.101.23.9.2.1.1
                fkGponOnuFWAutoUpgradeStartTime OBJECT-TYPE
                        SYNTAX INTEGER (-1 | 0..23)
                        UNITS "1 hour"
                        MAX-ACCESS read-only
                        STATUS current
                        DESCRIPTION
                                "ONU upgrade start time. (-1 is none-time : disable)"
                        ::= { fkGponOnuFWAutoUpgradeTimeInfo 1 }

                
--  1.3.6.1.4.1.10428 9 1.101.23.9.2.1.2
                -- 1.3.6.1.4.1.10428 9 1.101.23.9.2.1.2
                fkGponOnuFWAutoUpgradeEndTime OBJECT-TYPE
                        SYNTAX INTEGER (-1 | 0..23)
                        UNITS "1 hour"
                        MAX-ACCESS read-only
                        STATUS current
                        DESCRIPTION
                                "ONU upgrade end time. (-1 is none-time : disable)"
                        ::= { fkGponOnuFWAutoUpgradeTimeInfo 2 }

                
--  1.3.6.1.4.1.10428 9 1.101.23.9.2.1.3
                -- 1.3.6.1.4.1.10428 9 1.101.23.9.2.1.3
                fkGponOnuFWAutoUpgradeRebootTime OBJECT-TYPE
                        SYNTAX INTEGER (-1 | 0..23 | 24)
                        UNITS "1 hour"
                        MAX-ACCESS read-only
                        STATUS current
                        DESCRIPTION
                                "ONU rebooting time. (-1 is none-time : disable / 24 is immediately)"
                        ::= { fkGponOnuFWAutoUpgradeTimeInfo 3 }

                
--  1.3.6.1.4.1.10428 9 1.101.23.9.2.2
                -- 1.3.6.1.4.1.10428 9 1.101.23.9.2.2
                fkGponOnuFWAutoUpgradeTimeControl OBJECT IDENTIFIER ::= { fkGponOnuFWAutoUpgradeTime 2 }

                
--  1.3.6.1.4.1.10428 9 1.101.23.9.2.2.1
                -- 1.3.6.1.4.1.10428 9 1.101.23.9.2.2.1
                fkGponOnuFWAutoUpgradeTimeControlRequest OBJECT-TYPE
                        SYNTAX INTEGER
                                {
                                setOnuFWAutoUpgradeStartEndTime(1),
                                setOnuFWAutoUpgradeRebootTime(2)
                                }
                        MAX-ACCESS read-write
                        STATUS current
                        DESCRIPTION
                                "The request of a user command"
                        ::= { fkGponOnuFWAutoUpgradeTimeControl 1 }

                
--  1.3.6.1.4.1.10428 9 1.101.23.9.2.2.2
                -- 1.3.6.1.4.1.10428 9 1.101.23.9.2.2.2
                fkGponOnuFWAutoUpgradeTimeControlStatus OBJECT-TYPE
                        SYNTAX FkControlStatusType
                        MAX-ACCESS read-only
                        STATUS current
                        DESCRIPTION
                                "The status of user command"
                        ::= { fkGponOnuFWAutoUpgradeTimeControl 2 }

                
--  1.3.6.1.4.1.10428 9 1.101.23.9.2.2.3
                -- 1.3.6.1.4.1.10428 9 1.101.23.9.2.2.3
                fkGponOnuFWAutoUpgradeTimeControlTimer OBJECT-TYPE
                        SYNTAX Gauge32
                        MAX-ACCESS read-write
                        STATUS current
                        DESCRIPTION
                                "The maximum time for the manager for a long running user command"
                        ::= { fkGponOnuFWAutoUpgradeTimeControl 3 }

                
--  1.3.6.1.4.1.10428 9 1.101.23.9.2.2.4
                -- 1.3.6.1.4.1.10428 9 1.101.23.9.2.2.4
                fkGponOnuFWAutoUpgradeTimeControlTimeStamp OBJECT-TYPE
                        SYNTAX TimeTicks
                        MAX-ACCESS read-only
                        STATUS current
                        DESCRIPTION
                                "The time stamp of the last command(end of command)"
                        ::= { fkGponOnuFWAutoUpgradeTimeControl 4 }

                
--  1.3.6.1.4.1.10428 9 1.101.23.9.2.2.5
                -- 1.3.6.1.4.1.10428 9 1.101.23.9.2.2.5
                fkGponOnuFWAutoUpgradeTimeControlReqResult OBJECT-TYPE
                        SYNTAX FkControlRequestResultType
                        MAX-ACCESS read-only
                        STATUS current
                        DESCRIPTION
                                "The result of the last user command"
                        ::= { fkGponOnuFWAutoUpgradeTimeControl 5 }

                
--  1.3.6.1.4.1.10428 9 1.101.23.9.2.2.6
                -- 1.3.6.1.4.1.10428 9 1.101.23.9.2.2.6
                fkGponOnuFWAutoUpgradeTimeControlStartTime OBJECT-TYPE
                        SYNTAX INTEGER (-1 | 0..23)
                        UNITS "1 hour"
                        MAX-ACCESS read-write
                        STATUS current
                        DESCRIPTION
                                "ONU upgrade start time. (-1 is none-time : disable)"
                        ::= { fkGponOnuFWAutoUpgradeTimeControl 6 }

                
--  1.3.6.1.4.1.10428 9 1.101.23.9.2.2.7
                -- 1.3.6.1.4.1.10428 9 1.101.23.9.2.2.7
                fkGponOnuFWAutoUpgradeTimeControlEndTime OBJECT-TYPE
                        SYNTAX INTEGER (-1 | 0..23)
                        UNITS "1 hour"
                        MAX-ACCESS read-write
                        STATUS current
                        DESCRIPTION
                                "ONU upgrade end time. (-1 is none-time : disable)"
                        ::= { fkGponOnuFWAutoUpgradeTimeControl 7 }

                
--  1.3.6.1.4.1.10428 9 1.101.23.9.2.2.8
                -- 1.3.6.1.4.1.10428 9 1.101.23.9.2.2.8
                fkGponOnuFWAutoUpgradeTimeControlRebootTime OBJECT-TYPE
                        SYNTAX INTEGER (-1 | 0..23 | 24)
                        UNITS "1 hour"
                        MAX-ACCESS read-write
                        STATUS current
                        DESCRIPTION
                                "ONU rebooting time. (-1 is none-time : disable / 24 is immediately)"
                        ::= { fkGponOnuFWAutoUpgradeTimeControl 8 }

                
--  1.3.6.1.4.1.10428 9 1.101.23.9.2.3
                -- 1.3.6.1.4.1.10428 9 1.101.23.9.2.3
                fkGponOnuFWAutoUpgradeTimeNotification OBJECT IDENTIFIER ::= { fkGponOnuFWAutoUpgradeTime 3 }

                
--  1.3.6.1.4.1.10428 9 1.101.23.9.2.3.1
                -- 1.3.6.1.4.1.10428 9 1.101.23.9.2.3.1
                fkGponOnuFWAutoUpgradeStartEndTimeChanged NOTIFICATION-TYPE
                        OBJECTS { fkGponOnuFWAutoUpgradeTimeControlRequest, fkGponOnuFWAutoUpgradeTimeControlTimeStamp, fkGponOnuFWAutoUpgradeTimeControlReqResult, fkGponOnuFWAutoUpgradeTimeControlStartTime, fkGponOnuFWAutoUpgradeTimeControlEndTime
                                 }
                        STATUS current
                        DESCRIPTION 
                                "Description."
                        ::= { fkGponOnuFWAutoUpgradeTimeNotification 1 }

                
--  1.3.6.1.4.1.10428 9 1.101.23.9.2.3.2
                -- 1.3.6.1.4.1.10428 9 1.101.23.9.2.3.2
                fkGponOnuFWAutoUpgradeRebootTimeChanged NOTIFICATION-TYPE
                        OBJECTS { fkGponOnuFWAutoUpgradeTimeControlRequest, fkGponOnuFWAutoUpgradeTimeControlTimeStamp, fkGponOnuFWAutoUpgradeTimeControlReqResult, fkGponOnuFWAutoUpgradeTimeControlRebootTime }
                        STATUS current
                        DESCRIPTION 
                                "Description."
                        ::= { fkGponOnuFWAutoUpgradeTimeNotification 2 }

                
--  1.3.6.1.4.1.10428 9 1.101.23.9.3
                -- 1.3.6.1.4.1.10428 9 1.101.23.9.3
                fkGponOnuFWAutoUpgradeModel OBJECT IDENTIFIER ::= { fkGponOnuFirmwareAutoUpgradeMgmt 3 }

                
--  1.3.6.1.4.1.10428 9 1.101.23.9.3.1
                -- 1.3.6.1.4.1.10428 9 1.101.23.9.3.1
                fkGponOnuFWAutoUpgradeModelTable OBJECT-TYPE
                        SYNTAX SEQUENCE OF FkGponOnuFWAutoUpgradeModelEntry
                        MAX-ACCESS not-accessible
                        STATUS current
                        DESCRIPTION
                                "fkGponOnuFWAutoUpgradeModelTable"
                        ::= { fkGponOnuFWAutoUpgradeModel 1 }

                
--  1.3.6.1.4.1.10428 9 1.101.23.9.3.1.1
                -- 1.3.6.1.4.1.10428 9 1.101.23.9.3.1.1
                fkGponOnuFWAutoUpgradeModelEntry OBJECT-TYPE
                        SYNTAX FkGponOnuFWAutoUpgradeModelEntry
                        MAX-ACCESS not-accessible
                        STATUS current
                        DESCRIPTION
                                "key: fkGponOnuFWAutoUpgradeModelId"
                        INDEX { fkGponOnuFWAutoUpgradeModelId }
                        ::= { fkGponOnuFWAutoUpgradeModelTable 1 }

                
                FkGponOnuFWAutoUpgradeModelEntry ::=
                        SEQUENCE { 
                                fkGponOnuFWAutoUpgradeModelId
                                        INTEGER,
                                fkGponOnuFWAutoUpgradeModelName
                                        OCTET STRING,
                                fkGponOnuFWAutoUpgradeModelFWName
                                        OCTET STRING,
                                fkGponOnuFWAutoUpgradeModelFWVersion
                                        OCTET STRING,
                                fkGponOnuFWAutoUpgradeModelStatus
                                        INTEGER,
                                fkGponOnuFWAutoUpgradeModelMethod
                                        INTEGER,
                                fkGponOnuFWAutoUpgradeModelServerAddress
                                        IpAddress,
                                fkGponOnuFWAutoUpgradeModelUser
                                        OCTET STRING,
                                fkGponOnuFWAutoUpgradeModelPasswd
                                        OCTET STRING,
                                fkGponOnuFWAutoUpgradeModelFWTargetVersion
                                        OCTET STRING,
                                fkGponOnuFWAutoUpgradeModelExclude
                                        INTEGER
                         }

--  1.3.6.1.4.1.10428 9 1.101.23.9.3.1.1.1
                -- 1.3.6.1.4.1.10428 9 1.101.23.9.3.1.1.1
                fkGponOnuFWAutoUpgradeModelId OBJECT-TYPE
                        SYNTAX INTEGER (1..65535)
                        MAX-ACCESS read-only
                        STATUS current
                        DESCRIPTION
                                "Onu modle index."
                        ::= { fkGponOnuFWAutoUpgradeModelEntry 1 }

                
--  1.3.6.1.4.1.10428 9 1.101.23.9.3.1.1.2
                -- 1.3.6.1.4.1.10428 9 1.101.23.9.3.1.1.2
                fkGponOnuFWAutoUpgradeModelName OBJECT-TYPE
                        SYNTAX OCTET STRING (SIZE (1..128))
                        MAX-ACCESS read-only
                        STATUS current
                        DESCRIPTION
                                "Onu model name."
                        ::= { fkGponOnuFWAutoUpgradeModelEntry 2 }

                
--  1.3.6.1.4.1.10428 9 1.101.23.9.3.1.1.3
                -- 1.3.6.1.4.1.10428 9 1.101.23.9.3.1.1.3
                fkGponOnuFWAutoUpgradeModelFWName OBJECT-TYPE
                        SYNTAX OCTET STRING (SIZE (1..128))
                        MAX-ACCESS read-only
                        STATUS current
                        DESCRIPTION
                                "Firmware name of onu model."
                        ::= { fkGponOnuFWAutoUpgradeModelEntry 3 }

                
--  1.3.6.1.4.1.10428 9 1.101.23.9.3.1.1.4
                -- 1.3.6.1.4.1.10428 9 1.101.23.9.3.1.1.4
                fkGponOnuFWAutoUpgradeModelFWVersion OBJECT-TYPE
                        SYNTAX OCTET STRING (SIZE (1..20))
                        MAX-ACCESS read-only
                        STATUS current
                        DESCRIPTION
                                "Firmware version of onu model."
                        ::= { fkGponOnuFWAutoUpgradeModelEntry 4 }

                
--  1.3.6.1.4.1.10428 9 1.101.23.9.3.1.1.5
                -- 1.3.6.1.4.1.10428 9 1.101.23.9.3.1.1.5
                fkGponOnuFWAutoUpgradeModelStatus OBJECT-TYPE
                        SYNTAX INTEGER
                                {
                                none(0),
                                downloading(1),
                                uploadingToGPIU(2),
                                noFirmware(3),
                                downloadComplete(4)
                                }
                        MAX-ACCESS read-only
                        STATUS current
                        DESCRIPTION
                                "Firmware status of onu model."
                        ::= { fkGponOnuFWAutoUpgradeModelEntry 5 }

                
--  1.3.6.1.4.1.10428 9 1.101.23.9.3.1.1.6
                -- 1.3.6.1.4.1.10428 9 1.101.23.9.3.1.1.6
                fkGponOnuFWAutoUpgradeModelMethod OBJECT-TYPE
                        SYNTAX INTEGER
                                {
                                local(0),
                                ftp(1),
                                tftp(2)
                                }
                        MAX-ACCESS read-only
                        STATUS current
                        DESCRIPTION
                                "0: using image in local
                                1: using FTP
                                2: using TFTP"
                        ::= { fkGponOnuFWAutoUpgradeModelEntry 6 }

                
--  1.3.6.1.4.1.10428 9 1.101.23.9.3.1.1.7
                -- 1.3.6.1.4.1.10428 9 1.101.23.9.3.1.1.7
                fkGponOnuFWAutoUpgradeModelServerAddress OBJECT-TYPE
                        SYNTAX IpAddress
                        MAX-ACCESS read-only
                        STATUS current
                        DESCRIPTION
                                "FTP/TFTP server IP address."
                        ::= { fkGponOnuFWAutoUpgradeModelEntry 7 }

                
--  1.3.6.1.4.1.10428 9 1.101.23.9.3.1.1.8
                -- 1.3.6.1.4.1.10428 9 1.101.23.9.3.1.1.8
                fkGponOnuFWAutoUpgradeModelUser OBJECT-TYPE
                        SYNTAX OCTET STRING (SIZE (1..20))
                        MAX-ACCESS read-only
                        STATUS current
                        DESCRIPTION
                                "Account-name"
                        ::= { fkGponOnuFWAutoUpgradeModelEntry 8 }

                
--  1.3.6.1.4.1.10428 9 1.101.23.9.3.1.1.9
                -- 1.3.6.1.4.1.10428 9 1.101.23.9.3.1.1.9
                fkGponOnuFWAutoUpgradeModelPasswd OBJECT-TYPE
                        SYNTAX OCTET STRING (SIZE (1..20))
                        MAX-ACCESS read-only
                        STATUS current
                        DESCRIPTION
                                "Account-password"
                        ::= { fkGponOnuFWAutoUpgradeModelEntry 9 }

                
--  1.3.6.1.4.1.10428 9 1.101.23.9.3.1.1.10
                -- 1.3.6.1.4.1.10428 9 1.101.23.9.3.1.1.10
                fkGponOnuFWAutoUpgradeModelFWTargetVersion OBJECT-TYPE
                        SYNTAX OCTET STRING (SIZE (1..20))
                        MAX-ACCESS read-only
                        STATUS current
                        DESCRIPTION
                                "Upgrade target onu's version."
                        ::= { fkGponOnuFWAutoUpgradeModelEntry 10 }

                
                -- 1.3.6.1.4.1.10428 9 1.101.23.9.3.1.1.11
                fkGponOnuFWAutoUpgradeModelExclude OBJECT-TYPE
                        SYNTAX INTEGER
                                {
                                enable(1),
                                disable(2)
                                }
                        MAX-ACCESS read-only
                        STATUS current
                        DESCRIPTION
                                "The upgrade model excluding status"
                        ::= { fkGponOnuFWAutoUpgradeModelEntry 11 }

                
--  1.3.6.1.4.1.10428 9 1.101.23.9.3.2
                -- 1.3.6.1.4.1.10428 9 1.101.23.9.3.2
                fkGponOnuFWAutoUpgradeModelControl OBJECT IDENTIFIER ::= { fkGponOnuFWAutoUpgradeModel 2 }

                
--   
-- 1.3.6.1.4.1.10428 9 1.101.23.9.3.2.1
                -- 1.3.6.1.4.1.10428 9 1.101.23.9.3.2.1
                fkGponOnuFWAutoUpgradeModelControlRequest OBJECT-TYPE
                        SYNTAX INTEGER
                                {
                                setOnuFWAutoUpgradeModelProfile(1),
                                destroyOnuAutoUpgradeFirmware(2),
                                modifyOnuAutoUpgradeTargetVer(3),
                                delGponOnuFWAutoUpgradeModelTargetVer(4)
                                }
                        MAX-ACCESS read-write
                        STATUS current
                        DESCRIPTION
                                "The request of a user command"
                        ::= { fkGponOnuFWAutoUpgradeModelControl 1 }

                
--  1.3.6.1.4.1.10428 9 1.101.23.9.3.2.2
                -- 1.3.6.1.4.1.10428 9 1.101.23.9.3.2.2
                fkGponOnuFWAutoUpgradeModelControlStatus OBJECT-TYPE
                        SYNTAX FkControlStatusType
                        MAX-ACCESS read-only
                        STATUS current
                        DESCRIPTION
                                "The status of user command"
                        ::= { fkGponOnuFWAutoUpgradeModelControl 2 }

                
--  1.3.6.1.4.1.10428 9 1.101.23.9.3.2.3
                -- 1.3.6.1.4.1.10428 9 1.101.23.9.3.2.3
                fkGponOnuFWAutoUpgradeModelControlTimer OBJECT-TYPE
                        SYNTAX Gauge32
                        MAX-ACCESS read-write
                        STATUS current
                        DESCRIPTION
                                "The maximum time for the manager for a long running user command"
                        ::= { fkGponOnuFWAutoUpgradeModelControl 3 }

                
--  1.3.6.1.4.1.10428 9 1.101.23.9.3.2.4
                -- 1.3.6.1.4.1.10428 9 1.101.23.9.3.2.4
                fkGponOnuFWAutoUpgradeModelControlTimeStamp OBJECT-TYPE
                        SYNTAX TimeTicks
                        MAX-ACCESS read-only
                        STATUS current
                        DESCRIPTION
                                "The time stamp of the last command(end of command)"
                        ::= { fkGponOnuFWAutoUpgradeModelControl 4 }

                
--  1.3.6.1.4.1.10428 9 1.101.23.9.3.2.5
                -- 1.3.6.1.4.1.10428 9 1.101.23.9.3.2.5
                fkGponOnuFWAutoUpgradeModelControlReqResult OBJECT-TYPE
                        SYNTAX FkControlRequestResultType
                        MAX-ACCESS read-only
                        STATUS current
                        DESCRIPTION
                                "The result of the last user command"
                        ::= { fkGponOnuFWAutoUpgradeModelControl 5 }

                
--  1.3.6.1.4.1.10428 9 1.101.23.9.3.2.6
                -- 1.3.6.1.4.1.10428 9 1.101.23.9.3.2.6
                fkGponOnuFWAutoUpgradeModelControlName OBJECT-TYPE
                        SYNTAX OCTET STRING (SIZE (1..128))
                        MAX-ACCESS read-write
                        STATUS current
                        DESCRIPTION
                                "Onu model name."
                        ::= { fkGponOnuFWAutoUpgradeModelControl 6 }

                
--  1.3.6.1.4.1.10428 9 1.101.23.9.3.2.7
                -- 1.3.6.1.4.1.10428 9 1.101.23.9.3.2.7
                fkGponOnuFWAutoUpgradeModelControlFWName OBJECT-TYPE
                        SYNTAX OCTET STRING (SIZE (1..128))
                        MAX-ACCESS read-write
                        STATUS current
                        DESCRIPTION
                                "Firmware name of onu model."
                        ::= { fkGponOnuFWAutoUpgradeModelControl 7 }

                
--  1.3.6.1.4.1.10428 9 1.101.23.9.3.2.8
                -- 1.3.6.1.4.1.10428 9 1.101.23.9.3.2.8
                fkGponOnuFWAutoUpgradeModelControlMethod OBJECT-TYPE
                        SYNTAX INTEGER
                                {
                                local(0),
                                ftp(1),
                                tftp(2)
                                }
                        MAX-ACCESS read-write
                        STATUS current
                        DESCRIPTION
                                "0: using image in local
                                1: using FTP
                                2: using TFTP"
                        ::= { fkGponOnuFWAutoUpgradeModelControl 8 }

                
--  1.3.6.1.4.1.10428 9 1.101.23.9.3.2.9
                -- 1.3.6.1.4.1.10428 9 1.101.23.9.3.2.9
                fkGponOnuFWAutoUpgradeModelControlServerAddress OBJECT-TYPE
                        SYNTAX IpAddress
                        MAX-ACCESS read-write
                        STATUS current
                        DESCRIPTION
                                "FTP/TFTP server IP address."
                        ::= { fkGponOnuFWAutoUpgradeModelControl 9 }

                
--  1.3.6.1.4.1.10428 9 1.101.23.9.3.2.10
                -- 1.3.6.1.4.1.10428 9 1.101.23.9.3.2.10
                fkGponOnuFWAutoUpgradeModelControlUser OBJECT-TYPE
                        SYNTAX OCTET STRING (SIZE (1..20))
                        MAX-ACCESS read-write
                        STATUS current
                        DESCRIPTION
                                "Account-name"
                        ::= { fkGponOnuFWAutoUpgradeModelControl 10 }

                
--  1.3.6.1.4.1.10428 9 1.101.23.9.3.2.11
                -- 1.3.6.1.4.1.10428 9 1.101.23.9.3.2.11
                fkGponOnuFWAutoUpgradeModelControlPasswd OBJECT-TYPE
                        SYNTAX OCTET STRING (SIZE (1..20))
                        MAX-ACCESS read-write
                        STATUS current
                        DESCRIPTION
                                "Account-password"
                        ::= { fkGponOnuFWAutoUpgradeModelControl 11 }

                
--  1.3.6.1.4.1.10428 9 1.101.23.9.3.2.12
                -- 1.3.6.1.4.1.10428 9 1.101.23.9.3.2.12
                fkGponOnuFWAutoUpgradeModelControlFWTargetVersion OBJECT-TYPE
                        SYNTAX OCTET STRING (SIZE (1..20))
                        MAX-ACCESS read-write
                        STATUS current
                        DESCRIPTION
                                "Upgrade target onu's version."
                        ::= { fkGponOnuFWAutoUpgradeModelControl 12 }

                
                -- 1.3.6.1.4.1.10428 9 1.101.23.9.3.2.13
                fkGponOnuFWAutoUpgradeModelControlExclude OBJECT-TYPE
                        SYNTAX INTEGER
                                {
                                enable(1),
                                disable(2)
                                }
                        MAX-ACCESS read-write
                        STATUS current
                        DESCRIPTION
                                "The upgrade model excluding status"
                        ::= { fkGponOnuFWAutoUpgradeModelControl 13 }

                
--  1.3.6.1.4.1.10428 9 1.101.23.9.3.3
                -- 1.3.6.1.4.1.10428 9 1.101.23.9.3.3
                fkGponOnuFWAutoUpgradeModelNotification OBJECT IDENTIFIER ::= { fkGponOnuFWAutoUpgradeModel 3 }

                
--  1.3.6.1.4.1.10428 9 1.101.23.9.3.3.1
                -- 1.3.6.1.4.1.10428 9 1.101.23.9.3.3.1
                fkGponOnuFWAutoUpgradeModelProfileChanged NOTIFICATION-TYPE
                        OBJECTS { fkGponOnuFWAutoUpgradeModelControlRequest, fkGponOnuFWAutoUpgradeModelControlTimeStamp, fkGponOnuFWAutoUpgradeModelControlReqResult, fkGponOnuFWAutoUpgradeModelControlName, fkGponOnuFWAutoUpgradeModelControlFWName, 
                                fkGponOnuFWAutoUpgradeModelControlMethod, fkGponOnuFWAutoUpgradeModelControlServerAddress, fkGponOnuFWAutoUpgradeModelControlUser, fkGponOnuFWAutoUpgradeModelControlPasswd, fkGponOnuFWAutoUpgradeModelControlFWTargetVersion
                                 }
                        STATUS current
                        DESCRIPTION 
                                "Description."
                        ::= { fkGponOnuFWAutoUpgradeModelNotification 1 }

                
--  1.3.6.1.4.1.10428 9 1.101.23.9.3.3.2
                -- 1.3.6.1.4.1.10428 9 1.101.23.9.3.3.2
                fkGponOnuFWAutoUpgradeModelDeleted NOTIFICATION-TYPE
                        OBJECTS { fkGponOnuFWAutoUpgradeModelControlRequest, fkGponOnuFWAutoUpgradeModelControlTimeStamp, fkGponOnuFWAutoUpgradeModelControlReqResult, fkGponOnuFWAutoUpgradeModelControlName }
                        STATUS current
                        DESCRIPTION 
                                "Description."
                        ::= { fkGponOnuFWAutoUpgradeModelNotification 2 }

                
--  1.3.6.1.4.1.10428 9 1.101.23.9.3.3.3
                -- 1.3.6.1.4.1.10428 9 1.101.23.9.3.3.3
                fkGponOnuFWAutoUpgradeModelModifyTargetVer NOTIFICATION-TYPE
                        OBJECTS { fkGponOnuFWAutoUpgradeModelControlRequest, fkGponOnuFWAutoUpgradeModelControlTimeStamp, fkGponOnuFWAutoUpgradeModelControlReqResult, fkGponOnuFWAutoUpgradeModelControlName, fkGponOnuFWAutoUpgradeModelControlFWTargetVersion, 
                                fkGponOnuFWAutoUpgradeModelControlExclude }
                        STATUS current
                        DESCRIPTION 
                                "Description."
                        ::= { fkGponOnuFWAutoUpgradeModelNotification 3 }

                
--  1.3.6.1.4.1.10428 9 1.101.23.9.3.3.4
                -- 1.3.6.1.4.1.10428 9 1.101.23.9.3.3.4
                fkGponOnuFWAutoUpgradeModelTargetVerDeleted NOTIFICATION-TYPE
                        OBJECTS { fkGponOnuFWAutoUpgradeModelControlRequest, fkGponOnuFWAutoUpgradeModelControlTimeStamp, fkGponOnuFWAutoUpgradeModelControlReqResult, fkGponOnuFWAutoUpgradeModelControlName, fkGponOnuFWAutoUpgradeModelControlFWTargetVersion
                                 }
                        STATUS current
                        DESCRIPTION 
                                "Description."
                        ::= { fkGponOnuFWAutoUpgradeModelNotification 4 }

                
--  1.3.6.1.4.1.10428 9 1.101.23.9.4
                -- 1.3.6.1.4.1.10428 9 1.101.23.9.4
                fkGponOnuFWAutoUpgradeMTime OBJECT IDENTIFIER ::= { fkGponOnuFirmwareAutoUpgradeMgmt 4 }

                
--  1.3.6.1.4.1.10428 9 1.101.23.9.4.1
                -- 1.3.6.1.4.1.10428 9 1.101.23.9.4.1
                fkGponOnuFWAutoUpgradeMTimeTable OBJECT-TYPE
                        SYNTAX SEQUENCE OF FkGponOnuFWAutoUpgradeMTimeEntry
                        MAX-ACCESS not-accessible
                        STATUS current
                        DESCRIPTION
                                "fkGponOnuFWAutoUpgradeMTimeTable"
                        ::= { fkGponOnuFWAutoUpgradeMTime 1 }

                
--  1.3.6.1.4.1.10428 9 1.101.23.9.4.1.1
                -- 1.3.6.1.4.1.10428 9 1.101.23.9.4.1.1
                fkGponOnuFWAutoUpgradeMTimeEntry OBJECT-TYPE
                        SYNTAX FkGponOnuFWAutoUpgradeMTimeEntry
                        MAX-ACCESS not-accessible
                        STATUS current
                        DESCRIPTION
                                "key: fkGponOnuFWAutoUpgradeMTimeIndex"
                        INDEX { fkGponOnuFWAutoUpgradeMTimeIndex }
                        ::= { fkGponOnuFWAutoUpgradeMTimeTable 1 }

                
                FkGponOnuFWAutoUpgradeMTimeEntry ::=
                        SEQUENCE { 
                                fkGponOnuFWAutoUpgradeMTimeIndex
                                        Integer32,
                                fkGponOnuFWAutoUpgradeMTimeStartTime
                                        INTEGER,
                                fkGponOnuFWAutoUpgradeMTimeEndTime
                                        INTEGER,
                                fkGponOnuFWAutoUpgradeMTimeModelName
                                        OCTET STRING,
                                fkGponOnuFWAutoUpgradeMTimeRebootTime
                                        Integer32
                         }

--  1.3.6.1.4.1.10428 9 1.101.23.9.4.1.1.1
                -- 1.3.6.1.4.1.10428 9 1.101.23.9.4.1.1.1
                fkGponOnuFWAutoUpgradeMTimeIndex OBJECT-TYPE
                        SYNTAX Integer32 (1..65535)
                        MAX-ACCESS read-only
                        STATUS current
                        DESCRIPTION
                                "index"
                        ::= { fkGponOnuFWAutoUpgradeMTimeEntry 1 }

                
--  1.3.6.1.4.1.10428 9 1.101.23.9.4.1.1.2
                -- 1.3.6.1.4.1.10428 9 1.101.23.9.4.1.1.2
                fkGponOnuFWAutoUpgradeMTimeStartTime OBJECT-TYPE
                        SYNTAX INTEGER (-1 | 0..23)
                        UNITS "1 hour"
                        MAX-ACCESS read-only
                        STATUS current
                        DESCRIPTION
                                "upgrade start time for model.
                                (-1 is none-time : disable)"
                        ::= { fkGponOnuFWAutoUpgradeMTimeEntry 2 }

                
--  1.3.6.1.4.1.10428 9 1.101.23.9.4.1.1.3
                -- 1.3.6.1.4.1.10428 9 1.101.23.9.4.1.1.3
                fkGponOnuFWAutoUpgradeMTimeEndTime OBJECT-TYPE
                        SYNTAX INTEGER (-1 | 0..23)
                        UNITS "1 hour"
                        MAX-ACCESS read-only
                        STATUS current
                        DESCRIPTION
                                "upgrade end time for model.
                                (-1 is none-time : disable)"
                        ::= { fkGponOnuFWAutoUpgradeMTimeEntry 3 }

                
--  1.3.6.1.4.1.10428 9 1.101.23.9.4.1.1.4
                -- 1.3.6.1.4.1.10428 9 1.101.23.9.4.1.1.4
                fkGponOnuFWAutoUpgradeMTimeModelName OBJECT-TYPE
                        SYNTAX OCTET STRING (SIZE (1..128))
                        MAX-ACCESS read-only
                        STATUS current
                        DESCRIPTION
                                "Onu model name."
                        ::= { fkGponOnuFWAutoUpgradeMTimeEntry 4 }

                
                -- 1.3.6.1.4.1.10428 9 1.101.23.9.4.1.1.5
                fkGponOnuFWAutoUpgradeMTimeRebootTime OBJECT-TYPE
                        SYNTAX Integer32 (-1 | 0..24)
                        MAX-ACCESS read-only
                        STATUS current
                        DESCRIPTION
                                "The reboot time (hour)
                                -1: unused
                                0~23: available values
                                24: immediately"
                        ::= { fkGponOnuFWAutoUpgradeMTimeEntry 5 }

                
--  1.3.6.1.4.1.10428 9 1.101.23.9.4.2
                -- 1.3.6.1.4.1.10428 9 1.101.23.9.4.2
                fkGponOnuFWAutoUpgradeMTimeControl OBJECT IDENTIFIER ::= { fkGponOnuFWAutoUpgradeMTime 2 }

                
--  1.3.6.1.4.1.10428 9 1.101.23.9.4.2.1
                -- 1.3.6.1.4.1.10428 9 1.101.23.9.4.2.1
                fkGponOnuFWAutoUpgradeMTimeControlRequest OBJECT-TYPE
                        SYNTAX INTEGER
                                {
                                setOnuFWAutoUpgradeMTime(1),
                                destroyOnuAutoUpgradeMTime(2),
                                setRebootTime(3)
                                }
                        MAX-ACCESS read-write
                        STATUS current
                        DESCRIPTION
                                "The request of a user command"
                        ::= { fkGponOnuFWAutoUpgradeMTimeControl 1 }

                
--  1.3.6.1.4.1.10428 9 1.101.23.9.4.2.2
                -- 1.3.6.1.4.1.10428 9 1.101.23.9.4.2.2
                fkGponOnuFWAutoUpgradeMTimeControlStatus OBJECT-TYPE
                        SYNTAX FkControlStatusType
                        MAX-ACCESS read-only
                        STATUS current
                        DESCRIPTION
                                "The status of user command"
                        ::= { fkGponOnuFWAutoUpgradeMTimeControl 2 }

                
--  1.3.6.1.4.1.10428 9 1.101.23.9.4.2.3
                -- 1.3.6.1.4.1.10428 9 1.101.23.9.4.2.3
                fkGponOnuFWAutoUpgradeMTimeControlTimer OBJECT-TYPE
                        SYNTAX Gauge32
                        MAX-ACCESS read-write
                        STATUS current
                        DESCRIPTION
                                "The maximum time for the manager for a long running user command"
                        ::= { fkGponOnuFWAutoUpgradeMTimeControl 3 }

                
--  1.3.6.1.4.1.10428 9 1.101.23.9.4.2.4
                -- 1.3.6.1.4.1.10428 9 1.101.23.9.4.2.4
                fkGponOnuFWAutoUpgradeMTimeControlTimeStamp OBJECT-TYPE
                        SYNTAX TimeTicks
                        MAX-ACCESS read-only
                        STATUS current
                        DESCRIPTION
                                "The time stamp of the last command(end of command)"
                        ::= { fkGponOnuFWAutoUpgradeMTimeControl 4 }

                
--  1.3.6.1.4.1.10428 9 1.101.23.9.4.2.5
                -- 1.3.6.1.4.1.10428 9 1.101.23.9.4.2.5
                fkGponOnuFWAutoUpgradeMTimeControlReqResult OBJECT-TYPE
                        SYNTAX FkControlRequestResultType
                        MAX-ACCESS read-only
                        STATUS current
                        DESCRIPTION
                                "The result of the last user command"
                        ::= { fkGponOnuFWAutoUpgradeMTimeControl 5 }

                
--  1.3.6.1.4.1.10428 9 1.101.23.9.4.2.6
                -- 1.3.6.1.4.1.10428 9 1.101.23.9.4.2.6
                fkGponOnuFWAutoUpgradeMTimeControlStartTime OBJECT-TYPE
                        SYNTAX INTEGER (-1 | 0..23)
                        UNITS "1 hour"
                        MAX-ACCESS read-write
                        STATUS current
                        DESCRIPTION
                                "Upgrade start time for model
                                (-1 is none-time : disable)"
                        ::= { fkGponOnuFWAutoUpgradeMTimeControl 6 }

                
--  1.3.6.1.4.1.10428 9 1.101.23.9.4.2.7
                -- 1.3.6.1.4.1.10428 9 1.101.23.9.4.2.7
                fkGponOnuFWAutoUpgradeMTimeControlEndTime OBJECT-TYPE
                        SYNTAX INTEGER (-1 | 0..23)
                        UNITS "1 hour"
                        MAX-ACCESS read-write
                        STATUS current
                        DESCRIPTION
                                "upgrade end time for model.
                                (-1 is none-time : disable)"
                        ::= { fkGponOnuFWAutoUpgradeMTimeControl 7 }

                
--  1.3.6.1.4.1.10428 9 1.101.23.9.4.2.8
                -- 1.3.6.1.4.1.10428 9 1.101.23.9.4.2.8
                fkGponOnuFWAutoUpgradeMTimeControlModelName OBJECT-TYPE
                        SYNTAX OCTET STRING (SIZE (1..128))
                        MAX-ACCESS read-write
                        STATUS current
                        DESCRIPTION
                                "Onu model name."
                        ::= { fkGponOnuFWAutoUpgradeMTimeControl 8 }

                
                -- 1.3.6.1.4.1.10428 9 1.101.23.9.4.2.9
                fkGponOnuFWAutoUpgradeMTimeControlRebootTime OBJECT-TYPE
                        SYNTAX Integer32 (-1 | 0..24)
                        MAX-ACCESS read-write
                        STATUS current
                        DESCRIPTION
                                "The reboot time (hour)
                                -1: unused
                                0~23: available values
                                24: immediately
                                "
                        ::= { fkGponOnuFWAutoUpgradeMTimeControl 9 }

                
--  1.3.6.1.4.1.10428 9 1.101.23.9.4.3
                -- 1.3.6.1.4.1.10428 9 1.101.23.9.4.3
                fkGponOnuFWAutoUpgradeMTimeNotification OBJECT IDENTIFIER ::= { fkGponOnuFWAutoUpgradeMTime 3 }

                
--  1.3.6.1.4.1.10428 9 1.101.23.9.4.3.1
                -- 1.3.6.1.4.1.10428 9 1.101.23.9.4.3.1
                fkGponOnuFWAutoUpgradeMTimeChanged NOTIFICATION-TYPE
                        OBJECTS { fkGponOnuFWAutoUpgradeMTimeControlRequest, fkGponOnuFWAutoUpgradeMTimeControlTimeStamp, fkGponOnuFWAutoUpgradeMTimeControlReqResult, fkGponOnuFWAutoUpgradeMTimeControlStartTime, fkGponOnuFWAutoUpgradeMTimeControlEndTime, 
                                fkGponOnuFWAutoUpgradeMTimeControlModelName }
                        STATUS current
                        DESCRIPTION 
                                "Description."
                        ::= { fkGponOnuFWAutoUpgradeMTimeNotification 1 }

                
--  1.3.6.1.4.1.10428 9 1.101.23.9.4.3.2
                -- 1.3.6.1.4.1.10428 9 1.101.23.9.4.3.2
                fkGponOnuFWAutoUpgradeMTimeDeleted NOTIFICATION-TYPE
                        OBJECTS { fkGponOnuFWAutoUpgradeMTimeControlRequest, fkGponOnuFWAutoUpgradeMTimeControlTimeStamp, fkGponOnuFWAutoUpgradeMTimeControlReqResult, fkGponOnuFWAutoUpgradeMTimeControlModelName }
                        STATUS current
                        DESCRIPTION 
                                "Description."
                        ::= { fkGponOnuFWAutoUpgradeMTimeNotification 2 }

                
                -- 1.3.6.1.4.1.10428 9 1.101.23.9.4.3.3
                fkGponOnuFWAutoUpgradeMTimeRebootTimeChanged NOTIFICATION-TYPE
                        OBJECTS { fkGponOnuFWAutoUpgradeMTimeControlRequest, fkGponOnuFWAutoUpgradeMTimeControlTimeStamp, fkGponOnuFWAutoUpgradeMTimeControlReqResult, fkGponOnuFWAutoUpgradeMTimeIndex, fkGponOnuFWAutoUpgradeMTimeControlRebootTime
                                 }
                        STATUS current
                        DESCRIPTION 
                                "setRebootTime"
                        ::= { fkGponOnuFWAutoUpgradeMTimeNotification 3 }

                
--  1.3.6.1.4.1.10428 9 1.101.23.9.5
                -- 1.3.6.1.4.1.10428 9 1.101.23.9.5
                fkGponOnuFWAutoUpgradeState OBJECT IDENTIFIER ::= { fkGponOnuFirmwareAutoUpgradeMgmt 5 }

                
--  1.3.6.1.4.1.10428 9 1.101.23.9.5.1
                -- 1.3.6.1.4.1.10428 9 1.101.23.9.5.1
                fkGponOnuFWAutoUpgradeStateTable OBJECT-TYPE
                        SYNTAX SEQUENCE OF FkGponOnuFWAutoUpgradeStateEntry
                        MAX-ACCESS not-accessible
                        STATUS current
                        DESCRIPTION
                                "fkGponOnuFWAutoUpgradeStateTable"
                        ::= { fkGponOnuFWAutoUpgradeState 1 }

                
--  1.3.6.1.4.1.10428 9 1.101.23.9.5.1.1
                -- 1.3.6.1.4.1.10428 9 1.101.23.9.5.1.1
                fkGponOnuFWAutoUpgradeStateEntry OBJECT-TYPE
                        SYNTAX FkGponOnuFWAutoUpgradeStateEntry
                        MAX-ACCESS not-accessible
                        STATUS current
                        DESCRIPTION
                                "key: fkGponOnuFWAutoUpgradeSIndex"
                        INDEX { fkGponOnuFWAutoUpgradeSIndex }
                        ::= { fkGponOnuFWAutoUpgradeStateTable 1 }

                
                FkGponOnuFWAutoUpgradeStateEntry ::=
                        SEQUENCE { 
                                fkGponOnuFWAutoUpgradeSIndex
                                        INTEGER,
                                fkGponOnuFWAutoUpgradeSOltID
                                        INTEGER,
                                fkGponOnuFWAutoUpgradeSOnuID
                                        INTEGER,
                                fkGponOnuFWAutoUpgradeSModelName
                                        OCTET STRING,
                                fkGponOnuFWAutoUpgradeSStatus
                                        INTEGER,
                                fkGponOnuFWAutoUpgradeSFailCnt
                                        INTEGER,
                                fkGponOnuFWAutoUpgradeSActiveVer
                                        OCTET STRING
                         }

--  1.3.6.1.4.1.10428 9 1.101.23.9.5.1.1.1
                -- 1.3.6.1.4.1.10428 9 1.101.23.9.5.1.1.1
                fkGponOnuFWAutoUpgradeSIndex OBJECT-TYPE
                        SYNTAX INTEGER (1..65535)
                        MAX-ACCESS read-only
                        STATUS current
                        DESCRIPTION
                                "Index."
                        ::= { fkGponOnuFWAutoUpgradeStateEntry 1 }

                
--  1.3.6.1.4.1.10428 9 1.101.23.9.5.1.1.2
                -- 1.3.6.1.4.1.10428 9 1.101.23.9.5.1.1.2
                fkGponOnuFWAutoUpgradeSOltID OBJECT-TYPE
                        SYNTAX INTEGER (1..65535)
                        MAX-ACCESS read-only
                        STATUS current
                        DESCRIPTION
                                "OLT ID."
                        ::= { fkGponOnuFWAutoUpgradeStateEntry 2 }

                
--  1.3.6.1.4.1.10428 9 1.101.23.9.5.1.1.3
                -- 1.3.6.1.4.1.10428 9 1.101.23.9.5.1.1.3
                fkGponOnuFWAutoUpgradeSOnuID OBJECT-TYPE
                        SYNTAX INTEGER (1..65535)
                        MAX-ACCESS read-only
                        STATUS current
                        DESCRIPTION
                                "ONU ID."
                        ::= { fkGponOnuFWAutoUpgradeStateEntry 3 }

                
--  1.3.6.1.4.1.10428 9 1.101.23.9.5.1.1.4
                -- 1.3.6.1.4.1.10428 9 1.101.23.9.5.1.1.4
                fkGponOnuFWAutoUpgradeSModelName OBJECT-TYPE
                        SYNTAX OCTET STRING (SIZE (1..128))
                        MAX-ACCESS read-only
                        STATUS current
                        DESCRIPTION
                                "Onu model name."
                        ::= { fkGponOnuFWAutoUpgradeStateEntry 4 }

                
--  1.3.6.1.4.1.10428 9 1.101.23.9.5.1.1.5
                -- 1.3.6.1.4.1.10428 9 1.101.23.9.5.1.1.5
                fkGponOnuFWAutoUpgradeSStatus OBJECT-TYPE
                        SYNTAX INTEGER
                                {
                                none(0),
                                downloadProgress(1),
                                downloadProgressforDevBusy(2),
                                endDownloadForDevBusy(3),
                                downloadComplete(4),
                                downloadFail(5),
                                commitWaitValid(6),
                                commitProgress(7),
                                commitProgressforDevBusy(8),
                                commitFailForDevBusy(9),
                                commitComplete(10),
                                commitFail(11),
                                changeActiveComplete(12),
                                changeActiveFailforDevBusy(13),
                                changeActiveFail(14),
                                autoUpgradeResetWaiting(15),
                                autoUpgradeFail(16),
                                endDownloadSend(17),
                                endDownloadComplete(18),
                                unknown(255)
                                }
                        MAX-ACCESS read-only
                        STATUS current
                        DESCRIPTION
                                "Onu auto upgrade status."
                        ::= { fkGponOnuFWAutoUpgradeStateEntry 5 }

                
--  1.3.6.1.4.1.10428 9 1.101.23.9.5.1.1.6
                -- 1.3.6.1.4.1.10428 9 1.101.23.9.5.1.1.6
                fkGponOnuFWAutoUpgradeSFailCnt OBJECT-TYPE
                        SYNTAX INTEGER (1..65535)
                        MAX-ACCESS read-only
                        STATUS current
                        DESCRIPTION
                                "Auto upgrade fail count"
                        ::= { fkGponOnuFWAutoUpgradeStateEntry 6 }

                
--  1.3.6.1.4.1.10428 9 1.101.23.9.5.1.1.7
                -- 1.3.6.1.4.1.10428 9 1.101.23.9.5.1.1.7
                fkGponOnuFWAutoUpgradeSActiveVer OBJECT-TYPE
                        SYNTAX OCTET STRING (SIZE (1..20))
                        MAX-ACCESS read-only
                        STATUS current
                        DESCRIPTION
                                "Active version of onu."
                        ::= { fkGponOnuFWAutoUpgradeStateEntry 7 }

                
--  1.3.6.1.4.1.10428 9 1.101.23.9.6
                -- 1.3.6.1.4.1.10428 9 1.101.23.9.6
                fkGponOnuFWAutoUpgradeBase OBJECT IDENTIFIER ::= { fkGponOnuFirmwareAutoUpgradeMgmt 6 }

                
--  1.3.6.1.4.1.10428 9 1.101.23.9.6.1
                -- 1.3.6.1.4.1.10428 9 1.101.23.9.6.1
                fkGponOnuFWAutoUpgradeBaseInfo OBJECT IDENTIFIER ::= { fkGponOnuFWAutoUpgradeBase 1 }

                
--  1.3.6.1.4.1.10428 9 1.101.23.9.6.1.1
                -- 1.3.6.1.4.1.10428 9 1.101.23.9.6.1.1
                fkGponOnuFWAutoUpgradeBaseRetryCounts OBJECT-TYPE
                        SYNTAX Integer32
                        MAX-ACCESS read-only
                        STATUS current
                        DESCRIPTION
                                "The retry count."
                        ::= { fkGponOnuFWAutoUpgradeBaseInfo 1 }

                
--  1.3.6.1.4.1.10428 9 1.101.23.9.6.2
                -- 1.3.6.1.4.1.10428 9 1.101.23.9.6.2
                fkGponOnuFWAutoUpgradeBaseControl OBJECT IDENTIFIER ::= { fkGponOnuFWAutoUpgradeBase 2 }

                
--  1.3.6.1.4.1.10428 9 1.101.23.9.6.2.1
                -- 1.3.6.1.4.1.10428 9 1.101.23.9.6.2.1
                fkGponOnuFWAutoUpgradeControlBaseRequest OBJECT-TYPE
                        SYNTAX INTEGER { setRetryCount(1) }
                        MAX-ACCESS read-write
                        STATUS current
                        DESCRIPTION
                                "The request of a user command"
                        ::= { fkGponOnuFWAutoUpgradeBaseControl 1 }

                
--  1.3.6.1.4.1.10428 9 1.101.23.9.6.2.2
                -- 1.3.6.1.4.1.10428 9 1.101.23.9.6.2.2
                fkGponOnuFWAutoUpgradeControlBaseStatus OBJECT-TYPE
                        SYNTAX FkControlStatusType
                        MAX-ACCESS read-write
                        STATUS current
                        DESCRIPTION
                                "The status of user command"
                        ::= { fkGponOnuFWAutoUpgradeBaseControl 2 }

                
--  1.3.6.1.4.1.10428 9 1.101.23.9.6.2.3
                -- 1.3.6.1.4.1.10428 9 1.101.23.9.6.2.3
                fkGponOnuFWAutoUpgradeControlBaseTimer OBJECT-TYPE
                        SYNTAX Gauge32
                        MAX-ACCESS read-only
                        STATUS current
                        DESCRIPTION
                                "The maximum time for the manager for a long running user command"
                        ::= { fkGponOnuFWAutoUpgradeBaseControl 3 }

                
--  1.3.6.1.4.1.10428 9 1.101.23.9.6.2.4
                -- 1.3.6.1.4.1.10428 9 1.101.23.9.6.2.4
                fkGponOnuFWAutoUpgradeControlBaseTimeStamp OBJECT-TYPE
                        SYNTAX TimeTicks
                        MAX-ACCESS read-write
                        STATUS current
                        DESCRIPTION
                                "The time stamp of the last command(end of command)"
                        ::= { fkGponOnuFWAutoUpgradeBaseControl 4 }

                
--  1.3.6.1.4.1.10428 9 1.101.23.9.6.2.5
                -- 1.3.6.1.4.1.10428 9 1.101.23.9.6.2.5
                fkGponOnuFWAutoUpgradeControlBaseReqResult OBJECT-TYPE
                        SYNTAX FkControlRequestResultType
                        MAX-ACCESS read-only
                        STATUS current
                        DESCRIPTION
                                "The result of the last user command"
                        ::= { fkGponOnuFWAutoUpgradeBaseControl 5 }

                
--   
-- 1.3.6.1.4.1.10428 9 1.101.23.9.6.2.6
                -- 1.3.6.1.4.1.10428 9 1.101.23.9.6.2.6
                fkGponOnuFWAutoUpgradeControlBaseCount OBJECT-TYPE
                        SYNTAX INTEGER (3..10)
                        MAX-ACCESS read-write
                        STATUS current
                        DESCRIPTION
                                "The retry count."
                        ::= { fkGponOnuFWAutoUpgradeBaseControl 6 }

                
--  1.3.6.1.4.1.10428 9 1.101.23.9.6.3
                -- 1.3.6.1.4.1.10428 9 1.101.23.9.6.3
                fkGponOnuFWAutoUpgradeBaseNotification OBJECT IDENTIFIER ::= { fkGponOnuFWAutoUpgradeBase 3 }

                
--  1.3.6.1.4.1.10428 9 1.101.23.9.6.3.1
                -- 1.3.6.1.4.1.10428 9 1.101.23.9.6.3.1
                fkGponOnuFWAutoUpgradeBaseRetryCountChanged NOTIFICATION-TYPE
                        OBJECTS { fkGponOnuFWAutoUpgradeControlBaseRequest, fkGponOnuFWAutoUpgradeControlBaseTimeStamp, fkGponOnuFWAutoUpgradeControlBaseReqResult, fkGponOnuFWAutoUpgradeControlBaseCount }
                        STATUS current
                        DESCRIPTION 
                                "Description."
                        ::= { fkGponOnuFWAutoUpgradeBaseNotification 1 }

                
--  1.3.6.1.4.1.10428 9 1.101.23.10
                -- 1.3.6.1.4.1.10428 9 1.101.23.10
                fkGponOntFirmware OBJECT IDENTIFIER ::= { fkGpon 10 }

                
--  1.3.6.1.4.1.10428 9 1.101.23.10.1
                -- 1.3.6.1.4.1.10428 9 1.101.23.10.1
                fkGponOntFirmwareTable OBJECT-TYPE
                        SYNTAX SEQUENCE OF FkGponOntFirmwareEntry
                        MAX-ACCESS not-accessible
                        STATUS current
                        DESCRIPTION
                                "fkGponOntFirmwareTable"
                        ::= { fkGponOntFirmware 1 }

                
--  1.3.6.1.4.1.10428 9 1.101.23.10.1.1
                -- 1.3.6.1.4.1.10428 9 1.101.23.10.1.1
                fkGponOntFirmwareEntry OBJECT-TYPE
                        SYNTAX FkGponOntFirmwareEntry
                        MAX-ACCESS not-accessible
                        STATUS current
                        DESCRIPTION
                                "key: fkGponOntFirmwareIndex"
                        INDEX { fkGponOntFirmwareIndex }
                        ::= { fkGponOntFirmwareTable 1 }

                
                FkGponOntFirmwareEntry ::=
                        SEQUENCE { 
                                fkGponOntFirmwareIndex
                                        Integer32,
                                fkGponOntFirmwareType
                                        INTEGER,
                                fkGponOntFirmwareName
                                        OCTET STRING,
                                fkGponOntiFirmwareSize
                                        Integer32,
                                fkGponOntFirmwareMd5
                                        OCTET STRING
                         }

--  1.3.6.1.4.1.10428 9 1.101.23.10.1.1.1
                -- 1.3.6.1.4.1.10428 9 1.101.23.10.1.1.1
                fkGponOntFirmwareIndex OBJECT-TYPE
                        SYNTAX Integer32 (1..65535)
                        MAX-ACCESS read-only
                        STATUS current
                        DESCRIPTION
                                "Ont Firmware Index."
                        ::= { fkGponOntFirmwareEntry 1 }

                
--  1.3.6.1.4.1.10428 9 1.101.23.10.1.1.2
                -- 1.3.6.1.4.1.10428 9 1.101.23.10.1.1.2
                fkGponOntFirmwareType OBJECT-TYPE
                        SYNTAX INTEGER
                                {
                                os(1),
                                bootloader(2),
                                unknown(255)
                                }
                        MAX-ACCESS read-only
                        STATUS current
                        DESCRIPTION
                                "Ont Firmware type."
                        ::= { fkGponOntFirmwareEntry 2 }

                
--  1.3.6.1.4.1.10428 9 1.101.23.10.1.1.3
                -- 1.3.6.1.4.1.10428 9 1.101.23.10.1.1.3
                fkGponOntFirmwareName OBJECT-TYPE
                        SYNTAX OCTET STRING
                        MAX-ACCESS read-only
                        STATUS current
                        DESCRIPTION
                                "Ont Firmware name."
                        ::= { fkGponOntFirmwareEntry 3 }

                
--  1.3.6.1.4.1.10428 9 1.101.23.10.1.1.4
                -- 1.3.6.1.4.1.10428 9 1.101.23.10.1.1.4
                fkGponOntiFirmwareSize OBJECT-TYPE
                        SYNTAX Integer32
                        MAX-ACCESS read-only
                        STATUS current
                        DESCRIPTION
                                "Ont Firmware size."
                        ::= { fkGponOntFirmwareEntry 4 }

                
--  1.3.6.1.4.1.10428 9 1.101.23.10.1.1.5
                -- 1.3.6.1.4.1.10428 9 1.101.23.10.1.1.5
                fkGponOntFirmwareMd5 OBJECT-TYPE
                        SYNTAX OCTET STRING
                        MAX-ACCESS read-only
                        STATUS current
                        DESCRIPTION
                                "Ont Firmware md5 sum."
                        ::= { fkGponOntFirmwareEntry 5 }

                
--  1.3.6.1.4.1.10428 9 1.101.23.10.2
                -- 1.3.6.1.4.1.10428 9 1.101.23.10.2
                fkGponOntFirmwareOntTable OBJECT-TYPE
                        SYNTAX SEQUENCE OF FkGponOntFirmwareOntEntry
                        MAX-ACCESS not-accessible
                        STATUS current
                        DESCRIPTION
                                "fkGponOntFirmwareOntTable"
                        ::= { fkGponOntFirmware 2 }

                
--  1.3.6.1.4.1.10428 9 1.101.23.10.2.1
                -- 1.3.6.1.4.1.10428 9 1.101.23.10.2.1
                fkGponOntFirmwareOntEntry OBJECT-TYPE
                        SYNTAX FkGponOntFirmwareOntEntry
                        MAX-ACCESS not-accessible
                        STATUS current
                        DESCRIPTION
                                "key: fkGponOntFirmwareOltId, fkGponOntFirmwareOntId"
                        INDEX { fkGponOntFirmwareOltId, fkGponOntFirmwareOntId }
                        ::= { fkGponOntFirmwareOntTable 1 }

                
                FkGponOntFirmwareOntEntry ::=
                        SEQUENCE { 
                                fkGponOntFirmwareOltId
                                        Integer32,
                                fkGponOntFirmwareOntId
                                        Integer32,
                                fkGponOntFirmwareOntOs1Ver
                                        OCTET STRING,
                                fkGponOntFirmwareOntOs2Ver
                                        OCTET STRING,
                                fkGponOntFirmwareOntBLVer
                                        OCTET STRING,
                                fkGponOntFirmeareOntDefaultOS
                                        INTEGER,
                                fkGponOntFirmeareOntRunningOS
                                        INTEGER,
                                fkGponOntFirmwareOntGponOs1Ver
                                        OCTET STRING,
                                fkGponOntFirmwareOntGponOs2Ver
                                        OCTET STRING,
                                fkGponOntFirmwareOntOsStatus
                                        INTEGER,
                                fkGponOntFirmwareOntBLStatus
                                        INTEGER,
                                fkGponOntFirmwareOsUpgrdStatus
                                        INTEGER,
                                fkGponOntFirmwareOsUpgrdResult
                                        INTEGER,
                                fkGponOntFirmwareBLUpgrdStatus
                                        INTEGER,
                                fkGponOntFirmwareBLUpgrdResult
                                        INTEGER
                         }

--  1.3.6.1.4.1.10428 9 1.101.23.10.2.1.1
                -- 1.3.6.1.4.1.10428 9 1.101.23.10.2.1.1
                fkGponOntFirmwareOltId OBJECT-TYPE
                        SYNTAX Integer32 (1..65535)
                        MAX-ACCESS read-only
                        STATUS current
                        DESCRIPTION
                                "Ont-Firmware OLT Index."
                        ::= { fkGponOntFirmwareOntEntry 1 }

                
--  1.3.6.1.4.1.10428 9 1.101.23.10.2.1.2
                -- 1.3.6.1.4.1.10428 9 1.101.23.10.2.1.2
                fkGponOntFirmwareOntId OBJECT-TYPE
                        SYNTAX Integer32 (1..65535)
                        MAX-ACCESS read-only
                        STATUS current
                        DESCRIPTION
                                "Ont-Firmware ONT Index."
                        ::= { fkGponOntFirmwareOntEntry 2 }

                
--  1.3.6.1.4.1.10428 9 1.101.23.10.2.1.3
                -- 1.3.6.1.4.1.10428 9 1.101.23.10.2.1.3
                fkGponOntFirmwareOntOs1Ver OBJECT-TYPE
                        SYNTAX OCTET STRING
                        MAX-ACCESS read-only
                        STATUS current
                        DESCRIPTION
                                "Ont-Firmware OS1 version."
                        ::= { fkGponOntFirmwareOntEntry 3 }

                
--  1.3.6.1.4.1.10428 9 1.101.23.10.2.1.4
                -- 1.3.6.1.4.1.10428 9 1.101.23.10.2.1.4
                fkGponOntFirmwareOntOs2Ver OBJECT-TYPE
                        SYNTAX OCTET STRING
                        MAX-ACCESS read-only
                        STATUS current
                        DESCRIPTION
                                "Ont-Firmware OS2 version."
                        ::= { fkGponOntFirmwareOntEntry 4 }

                
--  1.3.6.1.4.1.10428 9 1.101.23.10.2.1.5
                -- 1.3.6.1.4.1.10428 9 1.101.23.10.2.1.5
                fkGponOntFirmwareOntBLVer OBJECT-TYPE
                        SYNTAX OCTET STRING
                        MAX-ACCESS read-only
                        STATUS current
                        DESCRIPTION
                                "Ont-Firmware ONT bootloader name."
                        ::= { fkGponOntFirmwareOntEntry 5 }

                
--  1.3.6.1.4.1.10428 9 1.101.23.10.2.1.6
                -- 1.3.6.1.4.1.10428 9 1.101.23.10.2.1.6
                fkGponOntFirmeareOntDefaultOS OBJECT-TYPE
                        SYNTAX INTEGER
                                {
                                os1(1),
                                os2(2)
                                }
                        MAX-ACCESS read-only
                        STATUS current
                        DESCRIPTION
                                "Ont-Firmware ONT default-os."
                        ::= { fkGponOntFirmwareOntEntry 6 }

                
--  1.3.6.1.4.1.10428 9 1.101.23.10.2.1.7
                -- 1.3.6.1.4.1.10428 9 1.101.23.10.2.1.7
                fkGponOntFirmeareOntRunningOS OBJECT-TYPE
                        SYNTAX INTEGER
                                {
                                os1(1),
                                os2(2)
                                }
                        MAX-ACCESS read-only
                        STATUS current
                        DESCRIPTION
                                "Ont-Firmware ONT running-os."
                        ::= { fkGponOntFirmwareOntEntry 7 }

                
--  1.3.6.1.4.1.10428 9 1.101.23.10.2.1.8
                -- 1.3.6.1.4.1.10428 9 1.101.23.10.2.1.8
                fkGponOntFirmwareOntGponOs1Ver OBJECT-TYPE
                        SYNTAX OCTET STRING
                        MAX-ACCESS read-only
                        STATUS current
                        DESCRIPTION
                                "Ont-Firmware GPON OS1 version."
                        ::= { fkGponOntFirmwareOntEntry 8 }

                
--  1.3.6.1.4.1.10428 9 1.101.23.10.2.1.9
                -- 1.3.6.1.4.1.10428 9 1.101.23.10.2.1.9
                fkGponOntFirmwareOntGponOs2Ver OBJECT-TYPE
                        SYNTAX OCTET STRING
                        MAX-ACCESS read-only
                        STATUS current
                        DESCRIPTION
                                "Ont-Firmware GPON OS2 version."
                        ::= { fkGponOntFirmwareOntEntry 9 }

                
--  1.3.6.1.4.1.10428 9 1.101.23.10.2.1.10
                -- 1.3.6.1.4.1.10428 9 1.101.23.10.2.1.10
                fkGponOntFirmwareOntOsStatus OBJECT-TYPE
                        SYNTAX INTEGER
                                {
                                notupdatable(1),
                                updatable(2),
                                updating(3),
                                updated(4)
                                }
                        MAX-ACCESS read-only
                        STATUS current
                        DESCRIPTION
                                "Ont-Firmware OS status."
                        ::= { fkGponOntFirmwareOntEntry 10 }

                
--  1.3.6.1.4.1.10428 9 1.101.23.10.2.1.11
                -- 1.3.6.1.4.1.10428 9 1.101.23.10.2.1.11
                fkGponOntFirmwareOntBLStatus OBJECT-TYPE
                        SYNTAX INTEGER
                                {
                                notupdatable(1),
                                updatable(2),
                                updating(3),
                                updated(4)
                                }
                        MAX-ACCESS read-only
                        STATUS current
                        DESCRIPTION
                                "Ont-Firmware BL status."
                        ::= { fkGponOntFirmwareOntEntry 11 }

                
--  1.3.6.1.4.1.10428 9 1.101.23.10.2.1.12
                -- 1.3.6.1.4.1.10428 9 1.101.23.10.2.1.12
                fkGponOntFirmwareOsUpgrdStatus OBJECT-TYPE
                        SYNTAX INTEGER
                                {
                                none(1),
                                idle(2),
                                downloadImage(3),
                                uncompress(4),
                                downloadBL(5),
                                updating(6),
                                abort(7),
                                rollback(8)
                                }
                        MAX-ACCESS read-only
                        STATUS current
                        DESCRIPTION
                                "Ont-Firmware Upgrade status."
                        ::= { fkGponOntFirmwareOntEntry 12 }

                
--  1.3.6.1.4.1.10428 9 1.101.23.10.2.1.13
                -- 1.3.6.1.4.1.10428 9 1.101.23.10.2.1.13
                fkGponOntFirmwareOsUpgrdResult OBJECT-TYPE
                        SYNTAX INTEGER (1..65535)
                        MAX-ACCESS read-only
                        STATUS current
                        DESCRIPTION
                                "Ont-Firmware Upgrade result.
                                Value   Meaning
                                ------------------
                                100     Success
                                101     Upgrade process aborted
                                102     Transfer fail on Bootloader
                                103     Transfer fail on AG
                                104     Transfer fail on BL
                                105     Cannot find a file
                                106     ERROR_ONT_FTP_CON_FAIL_AG
                                107     ERROR_ONT_FTP_CON_FAIL_BL
                                108     ERROR_ONT_CANNOT_OPEN_FILE_AG
                                109     ERROR_ONT_INSUFFICIENT_MEM_AG
                                110     Image checksum error
                                111     ERROR_ONT_INSUFFICIENT_MEM_AG
                                112     ERROR_ONT_INSUFFICIENT_MEM_BL
                                113     Image is corrupted
                                114     Image is corrupted on AG
                                115     Image is corrupted on BL
                                116     ERROR_ONT_TWO_FILES_NO_EXIST
                                117     Write image is fail on Bootloader
                                118     Write image is fail on AG
                                119     Write image is fail on BL
                                120     Rollback image is fail
                                121     ERROR_ONT_ROLLBACK
                                122     ERROR_ONT_TIMEOUT
                                123     Download timeout on Bootloader
                                124     Donwload timeout on AG
                                125     Download timeout on BL
                                126     Uncompress timeout
                                127     Write timeout on Bootloader
                                128     Write timeout on AG
                                129     Write timeout on BL
                                130     Rollback timeout on BL
                                131     Unknown error on Bootloader
                                132     Unknown error on AG
                                133     Unknown error on BL"
                        ::= { fkGponOntFirmwareOntEntry 13 }

                
--  1.3.6.1.4.1.10428 9 1.101.23.10.2.1.14
                -- 1.3.6.1.4.1.10428 9 1.101.23.10.2.1.14
                fkGponOntFirmwareBLUpgrdStatus OBJECT-TYPE
                        SYNTAX INTEGER
                                {
                                none(1),
                                idle(2),
                                downloadImage(3),
                                uncompress(4),
                                downloadBL(5),
                                updating(6),
                                abort(7),
                                rollback(8)
                                }
                        MAX-ACCESS read-only
                        STATUS current
                        DESCRIPTION
                                "Ont-Firmware BL Upgrade status."
                        ::= { fkGponOntFirmwareOntEntry 14 }

                
--  1.3.6.1.4.1.10428 9 1.101.23.10.2.1.15
                -- 1.3.6.1.4.1.10428 9 1.101.23.10.2.1.15
                fkGponOntFirmwareBLUpgrdResult OBJECT-TYPE
                        SYNTAX INTEGER (1..65535)
                        MAX-ACCESS read-only
                        STATUS current
                        DESCRIPTION
                                "Ont-Firmware Upgrade result.
                                Value   Meaning
                                ------------------
                                100     Success
                                101     Upgrade process aborted
                                102     Transfer fail on Bootloader
                                103     Transfer fail on AG
                                104     Transfer fail on BL
                                105     Cannot find a file
                                106     ERROR_ONT_FTP_CON_FAIL_AG
                                107     ERROR_ONT_FTP_CON_FAIL_BL
                                108     ERROR_ONT_CANNOT_OPEN_FILE_AG
                                109     ERROR_ONT_INSUFFICIENT_MEM_AG
                                110     Image checksum error
                                111     ERROR_ONT_INSUFFICIENT_MEM_AG
                                112     ERROR_ONT_INSUFFICIENT_MEM_BL
                                113     Image is corrupted
                                114     Image is corrupted on AG
                                115     Image is corrupted on BL
                                116     ERROR_ONT_TWO_FILES_NO_EXIST
                                117     Write image is fail on Bootloader
                                118     Write image is fail on AG
                                119     Write image is fail on BL
                                120     Rollback image is fail
                                121     ERROR_ONT_ROLLBACK
                                122     ERROR_ONT_TIMEOUT
                                123     Download timeout on Bootloader
                                124     Donwload timeout on AG
                                125     Download timeout on BL
                                126     Uncompress timeout
                                127     Write timeout on Bootloader
                                128     Write timeout on AG
                                129     Write timeout on BL
                                130     Rollback timeout on BL
                                131     Unknown error on Bootloader
                                132     Unknown error on AG
                                133     Unknown error on BL"
                        ::= { fkGponOntFirmwareOntEntry 15 }

                
--  1.3.6.1.4.1.10428 9 1.101.23.10.3
                -- 1.3.6.1.4.1.10428 9 1.101.23.10.3
                fkGponOntFirmwareControl OBJECT IDENTIFIER ::= { fkGponOntFirmware 3 }

                
--  1.3.6.1.4.1.10428 9 1.101.23.10.3.1
                -- 1.3.6.1.4.1.10428 9 1.101.23.10.3.1
                fkGponOntFirmwareControlRequest OBJECT-TYPE
                        SYNTAX INTEGER
                                {
                                setGponOntFwDownload(1),
                                setGponOntFwUpgrade(2),
                                setGponOntReset(3),
                                deleteGponOntFw(4),
                                deleteGponOntFwAll(5)
                                }
                        MAX-ACCESS read-write
                        STATUS current
                        DESCRIPTION
                                "The request of a user command"
                        ::= { fkGponOntFirmwareControl 1 }

                
--  1.3.6.1.4.1.10428 9 1.101.23.10.3.2
                -- 1.3.6.1.4.1.10428 9 1.101.23.10.3.2
                fkGponOntFirmwareControlStatus OBJECT-TYPE
                        SYNTAX FkControlStatusType
                        MAX-ACCESS read-only
                        STATUS current
                        DESCRIPTION
                                "The status of user command"
                        ::= { fkGponOntFirmwareControl 2 }

                
--  1.3.6.1.4.1.10428 9 1.101.23.10.3.3
                -- 1.3.6.1.4.1.10428 9 1.101.23.10.3.3
                fkGponOntFirmwareControlTimer OBJECT-TYPE
                        SYNTAX Gauge32
                        MAX-ACCESS read-write
                        STATUS current
                        DESCRIPTION
                                "The maximum time for the manager for a long running user command"
                        ::= { fkGponOntFirmwareControl 3 }

                
--  1.3.6.1.4.1.10428 9 1.101.23.10.3.4
                -- 1.3.6.1.4.1.10428 9 1.101.23.10.3.4
                fkGponOntFirmwareControlTimeStamp OBJECT-TYPE
                        SYNTAX TimeTicks
                        MAX-ACCESS read-only
                        STATUS current
                        DESCRIPTION
                                "The time stamp of the last command(end of command)"
                        ::= { fkGponOntFirmwareControl 4 }

                
--  1.3.6.1.4.1.10428 9 1.101.23.10.3.5
                -- 1.3.6.1.4.1.10428 9 1.101.23.10.3.5
                fkGponOntFirmwareControlReqResult OBJECT-TYPE
                        SYNTAX FkControlRequestResultType
                        MAX-ACCESS read-only
                        STATUS current
                        DESCRIPTION
                                "The result of the last user command"
                        ::= { fkGponOntFirmwareControl 5 }

                
--  1.3.6.1.4.1.10428 9 1.101.23.10.3.6
                -- 1.3.6.1.4.1.10428 9 1.101.23.10.3.6
                fkGponOntFirmwareControlOltId OBJECT-TYPE
                        SYNTAX INTEGER (1..65535)
                        MAX-ACCESS read-write
                        STATUS current
                        DESCRIPTION
                                "Ont-Firmware OLT index."
                        ::= { fkGponOntFirmwareControl 6 }

                
--  1.3.6.1.4.1.10428 9 1.101.23.10.3.7
                -- 1.3.6.1.4.1.10428 9 1.101.23.10.3.7
                fkGponOntFirmwareControlOntId OBJECT-TYPE
                        SYNTAX INTEGER (1..65535)
                        MAX-ACCESS read-write
                        STATUS current
                        DESCRIPTION
                                "Ont-Firmware ONT index."
                        ::= { fkGponOntFirmwareControl 7 }

                
--  1.3.6.1.4.1.10428 9 1.101.23.10.3.8
                -- 1.3.6.1.4.1.10428 9 1.101.23.10.3.8
                fkGponOntFirmwareControlType OBJECT-TYPE
                        SYNTAX INTEGER
                                {
                                os(1),
                                bootloader(2)
                                }
                        MAX-ACCESS read-write
                        STATUS current
                        DESCRIPTION
                                "Ont Firmware type."
                        ::= { fkGponOntFirmwareControl 8 }

                
--  1.3.6.1.4.1.10428 9 1.101.23.10.3.9
                -- 1.3.6.1.4.1.10428 9 1.101.23.10.3.9
                fkGponOntFirmwareControlFwName OBJECT-TYPE
                        SYNTAX OCTET STRING
                        MAX-ACCESS read-write
                        STATUS current
                        DESCRIPTION
                                "Ont-Firmware Firmware name."
                        ::= { fkGponOntFirmwareControl 9 }

                
--  1.3.6.1.4.1.10428 9 1.101.23.10.3.10
                -- 1.3.6.1.4.1.10428 9 1.101.23.10.3.10
                fkGponOntFirmwareControlMethod OBJECT-TYPE
                        SYNTAX INTEGER
                                {
                                ftp(1),
                                tftp(2)
                                }
                        MAX-ACCESS read-write
                        STATUS current
                        DESCRIPTION
                                "Ont-Firmware transmission method."
                        ::= { fkGponOntFirmwareControl 10 }

                
--  1.3.6.1.4.1.10428 9 1.101.23.10.3.11
                -- 1.3.6.1.4.1.10428 9 1.101.23.10.3.11
                fkGponOntFirmwareControlServer OBJECT-TYPE
                        SYNTAX IpAddress
                        MAX-ACCESS read-write
                        STATUS current
                        DESCRIPTION
                                "Ont-Firmware server address."
                        ::= { fkGponOntFirmwareControl 11 }

                
--  1.3.6.1.4.1.10428 9 1.101.23.10.3.12
                -- 1.3.6.1.4.1.10428 9 1.101.23.10.3.12
                fkGponOntFirmwareControlUser OBJECT-TYPE
                        SYNTAX OCTET STRING
                        MAX-ACCESS read-write
                        STATUS current
                        DESCRIPTION
                                "Ont-Firmware user name."
                        ::= { fkGponOntFirmwareControl 12 }

                
--  1.3.6.1.4.1.10428 9 1.101.23.10.3.13
                -- 1.3.6.1.4.1.10428 9 1.101.23.10.3.13
                fkGponOntFirmwareControlPasswd OBJECT-TYPE
                        SYNTAX OCTET STRING
                        MAX-ACCESS read-write
                        STATUS current
                        DESCRIPTION
                                "Ont-Firmware user password."
                        ::= { fkGponOntFirmwareControl 13 }

                
--  1.3.6.1.4.1.10428 9 1.101.23.10.3.14
                -- 1.3.6.1.4.1.10428 9 1.101.23.10.3.14
                fkGponOntFirmwareControlOnuId OBJECT-TYPE
                        SYNTAX Integer32
                        MAX-ACCESS read-only
                        STATUS current
                        DESCRIPTION
                                "The ONU id"
                        ::= { fkGponOntFirmwareControl 14 }

                
--  1.3.6.1.4.1.10428 9 1.101.23.10.4
                -- 1.3.6.1.4.1.10428 9 1.101.23.10.4
                fkGponOntFirmwareNotification OBJECT IDENTIFIER ::= { fkGponOntFirmware 4 }

                
--  1.3.6.1.4.1.10428 9 1.101.23.10.4.1
                -- 1.3.6.1.4.1.10428 9 1.101.23.10.4.1
                gponOntFwDownloaded NOTIFICATION-TYPE
                        OBJECTS { fkGponOntFirmwareControlRequest, fkGponOntFirmwareControlTimeStamp, fkGponOntFirmwareControlReqResult, fkGponOntFirmwareControlType, fkGponOntFirmwareControlFwName, 
                                fkGponOntFirmwareControlMethod, fkGponOntFirmwareControlServer, fkGponOntFirmwareControlUser, fkGponOntFirmwareControlPasswd }
                        STATUS current
                        DESCRIPTION 
                                "Description."
                        ::= { fkGponOntFirmwareNotification 1 }

                
--   
-- 1.3.6.1.4.1.10428 9 1.101.23.10.4.2
                -- 1.3.6.1.4.1.10428 9 1.101.23.10.4.2
                gponOntFwUpgraded NOTIFICATION-TYPE
                        OBJECTS { fkGponOntFirmwareControlRequest, fkGponOntFirmwareControlTimeStamp, fkGponOntFirmwareControlReqResult, fkGponOntFirmwareControlOltId, fkGponOntFirmwareControlOntId, 
                                fkGponOntFirmwareControlFwName }
                        STATUS current
                        DESCRIPTION 
                                "Description."
                        ::= { fkGponOntFirmwareNotification 2 }

                
--  1.3.6.1.4.1.10428 9 1.101.23.10.4.3
                -- 1.3.6.1.4.1.10428 9 1.101.23.10.4.3
                gponOntFwOntReseted NOTIFICATION-TYPE
                        OBJECTS { fkGponOntFirmwareControlRequest, fkGponOntFirmwareControlTimeStamp, fkGponOntFirmwareControlReqResult, fkGponOntFirmwareControlOltId, fkGponOntFirmwareControlOntId
                                 }
                        STATUS current
                        DESCRIPTION 
                                "Description."
                        ::= { fkGponOntFirmwareNotification 3 }

                
--  1.3.6.1.4.1.10428 9 1.101.23.10.4.4
                -- 1.3.6.1.4.1.10428 9 1.101.23.10.4.4
                gponOntFwDeleted NOTIFICATION-TYPE
                        OBJECTS { fkGponOntFirmwareControlRequest, fkGponOntFirmwareControlTimeStamp, fkGponOntFirmwareControlReqResult, fkGponOntFirmwareControlFwName }
                        STATUS current
                        DESCRIPTION 
                                "Description."
                        ::= { fkGponOntFirmwareNotification 4 }

                
--  1.3.6.1.4.1.10428 9 1.101.23.10.4.5
                -- 1.3.6.1.4.1.10428 9 1.101.23.10.4.5
                gponOntFwDeleteAll NOTIFICATION-TYPE
                        OBJECTS { fkGponOntFirmwareControlRequest, fkGponOntFirmwareControlTimeStamp, fkGponOntFirmwareControlReqResult }
                        STATUS current
                        DESCRIPTION 
                                "Description."
                        ::= { fkGponOntFirmwareNotification 5 }

                
--  1.3.6.1.4.1.10428 9 1.101.23.11
                -- 1.3.6.1.4.1.10428 9 1.101.23.11
                fkGponRedundancy OBJECT IDENTIFIER ::= { fkGpon 11 }

                
--  1.3.6.1.4.1.10428 9 1.101.23.11.1
                -- 1.3.6.1.4.1.10428 9 1.101.23.11.1
                fkGponRedGroupTable OBJECT-TYPE
                        SYNTAX SEQUENCE OF FkGponRedGroupEntry
                        MAX-ACCESS not-accessible
                        STATUS current
                        DESCRIPTION
                                "fkGponRedGroupTable"
                        ::= { fkGponRedundancy 1 }

                
--  1.3.6.1.4.1.10428 9 1.101.23.11.1.1
                -- 1.3.6.1.4.1.10428 9 1.101.23.11.1.1
                fkGponRedGroupEntry OBJECT-TYPE
                        SYNTAX FkGponRedGroupEntry
                        MAX-ACCESS not-accessible
                        STATUS current
                        DESCRIPTION
                                "key: fkGponRedGroupIndex"
                        INDEX { fkGponRedGroupIndex }
                        ::= { fkGponRedGroupTable 1 }

                
                FkGponRedGroupEntry ::=
                        SEQUENCE { 
                                fkGponRedGroupIndex
                                        Integer32,
                                fkGponRedGroupOltAIndex
                                        Integer32,
                                fkGponRedGroupOltAStatus
                                        INTEGER,
                                fkGponRedGroupOltBIndex
                                        Integer32,
                                fkGponRedGroupOltBStatus
                                        INTEGER,
                                fkGponRedLastReason
                                        INTEGER,
                                fkGponRedGroupStandbyLinkStatus
                                        INTEGER,
                                fkGponRedGroupSlaveOltAdminStatus
                                        INTEGER,
                                fkGponRedGroupTrigger
                                        BITS,
                                fkGponRedGroupDbSyncStatus
                                        INTEGER
                         }

--  1.3.6.1.4.1.10428 9 1.101.23.11.1.1.1
                -- 1.3.6.1.4.1.10428 9 1.101.23.11.1.1.1
                fkGponRedGroupIndex OBJECT-TYPE
                        SYNTAX Integer32 (1..65535)
                        MAX-ACCESS read-only
                        STATUS current
                        DESCRIPTION
                                "Gpon redundancy group-id."
                        ::= { fkGponRedGroupEntry 1 }

                
--  1.3.6.1.4.1.10428 9 1.101.23.11.1.1.2
                -- 1.3.6.1.4.1.10428 9 1.101.23.11.1.1.2
                fkGponRedGroupOltAIndex OBJECT-TYPE
                        SYNTAX Integer32
                        MAX-ACCESS read-only
                        STATUS current
                        DESCRIPTION
                                "Gpon redundancy Olt-A index."
                        ::= { fkGponRedGroupEntry 2 }

                
--  1.3.6.1.4.1.10428 9 1.101.23.11.1.1.3
                -- 1.3.6.1.4.1.10428 9 1.101.23.11.1.1.3
                fkGponRedGroupOltAStatus OBJECT-TYPE
                        SYNTAX INTEGER
                                {
                                working(1),
                                standby(2),
                                progress(3),
                                waiting(4),
                                workingPending(5),
                                standbyPending(6),
                                unknown(255)
                                }
                        MAX-ACCESS read-only
                        STATUS current
                        DESCRIPTION
                                "Gpon redundancy Olt-A status."
                        ::= { fkGponRedGroupEntry 3 }

                
--  1.3.6.1.4.1.10428 9 1.101.23.11.1.1.4
                -- 1.3.6.1.4.1.10428 9 1.101.23.11.1.1.4
                fkGponRedGroupOltBIndex OBJECT-TYPE
                        SYNTAX Integer32
                        MAX-ACCESS read-only
                        STATUS current
                        DESCRIPTION
                                "Gpon redundancy Olt-B index."
                        ::= { fkGponRedGroupEntry 4 }

                
--  1.3.6.1.4.1.10428 9 1.101.23.11.1.1.5
                -- 1.3.6.1.4.1.10428 9 1.101.23.11.1.1.5
                fkGponRedGroupOltBStatus OBJECT-TYPE
                        SYNTAX INTEGER
                                {
                                working(1),
                                standby(2),
                                progress(3),
                                waiting(4),
                                workingPending(5),
                                standbyPending(6),
                                unknown(255)
                                }
                        MAX-ACCESS read-only
                        STATUS current
                        DESCRIPTION
                                "Gpon redundancy Olt-B status."
                        ::= { fkGponRedGroupEntry 5 }

                
--  1.3.6.1.4.1.10428 9 1.101.23.11.1.1.6
                -- 1.3.6.1.4.1.10428 9 1.101.23.11.1.1.6
                fkGponRedLastReason OBJECT-TYPE
                        SYNTAX INTEGER
                                {
                                none(0),
                                force(1),
                                los(2),
                                slotRemove(3),
                                slotLock(4),
                                slotRestart(5),
                                slotDisable(6),
                                slotReset(7),
                                slotPowerDown(8),
                                gponMacCrash(9),
                                daemonCrash(10),
                                unknown(255)
                                }
                        MAX-ACCESS read-only
                        STATUS current
                        DESCRIPTION
                                "The Last gpon-redundancy reason."
                        ::= { fkGponRedGroupEntry 6 }

                
                -- 1.3.6.1.4.1.10428 9 1.101.23.11.1.1.7
                fkGponRedGroupStandbyLinkStatus OBJECT-TYPE
                        SYNTAX INTEGER
                                {
                                none(0),
                                rxDetect(1),
                                txEnable(2)
                                }
                        MAX-ACCESS read-only
                        STATUS current
                        DESCRIPTION
                                "The Standby Link Status."
                        ::= { fkGponRedGroupEntry 7 }

                
                -- 1.3.6.1.4.1.10428 9 1.101.23.11.1.1.8
                fkGponRedGroupSlaveOltAdminStatus OBJECT-TYPE
                        SYNTAX INTEGER
                                {
                                activation(1),
                                inActivation(2)
                                }
                        MAX-ACCESS read-only
                        STATUS current
                        DESCRIPTION
                                "The Slave OLT Admin Status."
                        ::= { fkGponRedGroupEntry 8 }

                
                -- 1.3.6.1.4.1.10428 9 1.101.23.11.1.1.9
                fkGponRedGroupTrigger OBJECT-TYPE
                        SYNTAX BITS
                                {
                                los(0),
                                manual(1),
                                slotStatus(2),
                                gponMac(3)
                                }
                        MAX-ACCESS read-only
                        STATUS current
                        DESCRIPTION
                                "olt redundancy trigger (los|manual|slot|gpon-mac) (on|off) group GROUP_ID"
                        ::= { fkGponRedGroupEntry 9 }

                
                -- 1.3.6.1.4.1.10428 9 1.101.23.11.1.1.10
                fkGponRedGroupDbSyncStatus OBJECT-TYPE
                        SYNTAX INTEGER
                                {
                                init(0),
                                same(1),
                                checkDifferent(2),
                                updateSuccess(3),
                                updateFail(4)
                                }
                        MAX-ACCESS read-only
                        STATUS current
                        DESCRIPTION
                                "The DB sync status"
                        ::= { fkGponRedGroupEntry 10 }

                
--  1.3.6.1.4.1.10428 9 1.101.23.11.2
                -- 1.3.6.1.4.1.10428 9 1.101.23.11.2
                fkGponRedGroupControl OBJECT IDENTIFIER ::= { fkGponRedundancy 2 }

                
--  1.3.6.1.4.1.10428 9 1.101.23.11.2.1
                -- 1.3.6.1.4.1.10428 9 1.101.23.11.2.1
                fkGponRedGroupControlRequest OBJECT-TYPE
                        SYNTAX INTEGER
                                {
                                setGponRedGroup(1),
                                clearGponRedGroup(2),
                                setGponRedForceSwitchover(3),
                                setGponRedStandbyOptic(4),
                                setGponRedSlaveAdminStatus(5),
                                setGponRedTrigger(6),
                                setGponRedSafeSwitchover(7),
                                setGponRedDbSyncCheck(8),
                                setGponRedDbResync(9)
                                }
                        MAX-ACCESS read-write
                        STATUS current
                        DESCRIPTION
                                "The request of a user command"
                        ::= { fkGponRedGroupControl 1 }

                
--  1.3.6.1.4.1.10428 9 1.101.23.11.2.2
                -- 1.3.6.1.4.1.10428 9 1.101.23.11.2.2
                fkGponRedGroupControlStatus OBJECT-TYPE
                        SYNTAX FkControlStatusType
                        MAX-ACCESS read-only
                        STATUS current
                        DESCRIPTION
                                "The status of user command"
                        ::= { fkGponRedGroupControl 2 }

                
--  1.3.6.1.4.1.10428 9 1.101.23.11.2.3
                -- 1.3.6.1.4.1.10428 9 1.101.23.11.2.3
                fkGponRedGroupControlTimer OBJECT-TYPE
                        SYNTAX Gauge32
                        MAX-ACCESS read-write
                        STATUS current
                        DESCRIPTION
                                "The maximum time for the manager for a long running user command"
                        ::= { fkGponRedGroupControl 3 }

                
--   
-- 1.3.6.1.4.1.10428 9 1.101.23.11.2.4
                -- 1.3.6.1.4.1.10428 9 1.101.23.11.2.4
                fkGponRedGroupControlTimeStamp OBJECT-TYPE
                        SYNTAX TimeTicks
                        MAX-ACCESS read-only
                        STATUS current
                        DESCRIPTION
                                "The time stamp of the last command(end of command)"
                        ::= { fkGponRedGroupControl 4 }

                
--  1.3.6.1.4.1.10428 9 1.101.23.11.2.5
                -- 1.3.6.1.4.1.10428 9 1.101.23.11.2.5
                fkGponRedGroupControlReqResult OBJECT-TYPE
                        SYNTAX FkControlRequestResultType
                        MAX-ACCESS read-only
                        STATUS current
                        DESCRIPTION
                                "The result of the last user command"
                        ::= { fkGponRedGroupControl 5 }

                
--  1.3.6.1.4.1.10428 9 1.101.23.11.2.6
                -- 1.3.6.1.4.1.10428 9 1.101.23.11.2.6
                fkGponRedGroupControlGroupIndex OBJECT-TYPE
                        SYNTAX Integer32
                        MAX-ACCESS read-write
                        STATUS current
                        DESCRIPTION
                                "Gpon red group Index."
                        ::= { fkGponRedGroupControl 6 }

                
--  1.3.6.1.4.1.10428 9 1.101.23.11.2.7
                -- 1.3.6.1.4.1.10428 9 1.101.23.11.2.7
                fkGponRedGroupControlOltAIndex OBJECT-TYPE
                        SYNTAX Integer32
                        MAX-ACCESS read-write
                        STATUS current
                        DESCRIPTION
                                "Gpon red Olt-A index."
                        ::= { fkGponRedGroupControl 7 }

                
--  1.3.6.1.4.1.10428 9 1.101.23.11.2.8
                -- 1.3.6.1.4.1.10428 9 1.101.23.11.2.8
                fkGponRedGroupControlOltBIndex OBJECT-TYPE
                        SYNTAX Integer32
                        MAX-ACCESS read-write
                        STATUS current
                        DESCRIPTION
                                "Gpon red Olt-B index."
                        ::= { fkGponRedGroupControl 8 }

                
                -- 1.3.6.1.4.1.10428 9 1.101.23.11.2.9
                fkGponRedGroupControlStandbyOptic OBJECT-TYPE
                        SYNTAX INTEGER
                                {
                                enable(1),
                                disable(2)
                                }
                        MAX-ACCESS read-write
                        STATUS current
                        DESCRIPTION
                                "olt redundancy standby-optic (enable|disable) group GROUP_ID"
                        ::= { fkGponRedGroupControl 9 }

                
                -- 1.3.6.1.4.1.10428 9 1.101.23.11.2.10
                fkGponRedGroupControlStandbyOpticEnableTime OBJECT-TYPE
                        SYNTAX INTEGER (0 | 1..600)
                        MAX-ACCESS read-write
                        STATUS current
                        DESCRIPTION
                                "olt redundancy standby-optic (enable|disable) group GROUP_ID (0:permanent|<1-600>)
                                "
                        ::= { fkGponRedGroupControl 10 }

                
                -- 1.3.6.1.4.1.10428 9 1.101.23.11.2.11
                fkGponRedGroupControlSlaveAdminStatus OBJECT-TYPE
                        SYNTAX INTEGER
                                {
                                activation(1),
                                inActivation(2)
                                }
                        MAX-ACCESS read-write
                        STATUS current
                        DESCRIPTION
                                "olt redundancy slave (activate|deactivate) group GROUP_ID"
                        ::= { fkGponRedGroupControl 11 }

                
                -- 1.3.6.1.4.1.10428 9 1.101.23.11.2.12
                fkGponRedGroupControlTrigger OBJECT-TYPE
                        SYNTAX BITS
                                {
                                los(0),
                                manual(1),
                                slotStatus(2),
                                gponMac(3)
                                }
                        MAX-ACCESS read-write
                        STATUS current
                        DESCRIPTION
                                "olt redundancy trigger (los|manual|slot|gpon-mac) (on|off) group GROUP_ID"
                        ::= { fkGponRedGroupControl 12 }

                
--  1.3.6.1.4.1.10428 9 1.101.23.11.3
                -- 1.3.6.1.4.1.10428 9 1.101.23.11.3
                fkGponRedGroupNotification OBJECT IDENTIFIER ::= { fkGponRedundancy 3 }

                
--  1.3.6.1.4.1.10428 9 1.101.23.11.3.1
                -- 1.3.6.1.4.1.10428 9 1.101.23.11.3.1
                fkGponRedGroupChanged NOTIFICATION-TYPE
                        OBJECTS { fkGponRedGroupControlRequest, fkGponRedGroupControlTimeStamp, fkGponRedGroupControlReqResult, fkGponRedGroupControlGroupIndex, fkGponRedGroupControlOltAIndex, 
                                fkGponRedGroupControlOltBIndex }
                        STATUS current
                        DESCRIPTION 
                                "Description."
                        ::= { fkGponRedGroupNotification 1 }

                
--  1.3.6.1.4.1.10428 9 1.101.23.11.3.2
                -- 1.3.6.1.4.1.10428 9 1.101.23.11.3.2
                fkGponRedGroupCleared NOTIFICATION-TYPE
                        OBJECTS { fkGponRedGroupControlRequest, fkGponRedGroupControlTimeStamp, fkGponRedGroupControlReqResult, fkGponRedGroupControlGroupIndex }
                        STATUS current
                        DESCRIPTION 
                                "Description."
                        ::= { fkGponRedGroupNotification 2 }

                
--  1.3.6.1.4.1.10428 9 1.101.23.11.3.3
                -- 1.3.6.1.4.1.10428 9 1.101.23.11.3.3
                fkGponRedGroupForceSwitchovered NOTIFICATION-TYPE
                        OBJECTS { fkGponRedGroupControlRequest, fkGponRedGroupControlTimeStamp, fkGponRedGroupControlReqResult, fkGponRedGroupControlGroupIndex }
                        STATUS current
                        DESCRIPTION 
                                "Description."
                        ::= { fkGponRedGroupNotification 3 }

                
                -- 1.3.6.1.4.1.10428 9 1.101.23.11.3.4
                fkGponRedGroupStandbyOpticChanged NOTIFICATION-TYPE
                        OBJECTS { fkGponRedGroupControlRequest, fkGponRedGroupControlTimeStamp, fkGponRedGroupControlReqResult, fkGponRedGroupControlGroupIndex, fkGponRedGroupControlStandbyOptic, 
                                fkGponRedGroupControlStandbyOpticEnableTime }
                        STATUS current
                        DESCRIPTION 
                                "Description."
                        ::= { fkGponRedGroupNotification 4 }

                
                -- 1.3.6.1.4.1.10428 9 1.101.23.11.3.5
                fkGponRedGroupSlaveAdminStatusChanged NOTIFICATION-TYPE
                        OBJECTS { fkGponRedGroupControlRequest, fkGponRedGroupControlTimeStamp, fkGponRedGroupControlReqResult, fkGponRedGroupControlGroupIndex, fkGponRedGroupControlSlaveAdminStatus
                                 }
                        STATUS current
                        DESCRIPTION 
                                "Description."
                        ::= { fkGponRedGroupNotification 5 }

                
                -- 1.3.6.1.4.1.10428 9 1.101.23.11.3.6
                fkGponRedGroupTriggerChanged NOTIFICATION-TYPE
                        OBJECTS { fkGponRedGroupControlRequest, fkGponRedGroupControlTimeStamp, fkGponRedGroupControlReqResult, fkGponRedGroupControlGroupIndex, fkGponRedGroupControlTrigger
                                 }
                        STATUS current
                        DESCRIPTION 
                                "Description."
                        ::= { fkGponRedGroupNotification 6 }

                
                -- 1.3.6.1.4.1.10428 9 1.101.23.11.3.7
                fkGponRedGroupSafeSwitchOverChanged NOTIFICATION-TYPE
                        OBJECTS { fkGponRedGroupControlRequest, fkGponRedGroupControlTimeStamp, fkGponRedGroupControlReqResult, fkGponRedGroupControlGroupIndex }
                        STATUS current
                        DESCRIPTION 
                                "setGponRedSafeSwitchover"
                        ::= { fkGponRedGroupNotification 7 }

                
                -- 1.3.6.1.4.1.10428 9 1.101.23.11.3.8
                fkGponRedGroupDbSyncCheckChanged NOTIFICATION-TYPE
                        OBJECTS { fkGponRedGroupControlRequest, fkGponRedGroupControlTimeStamp, fkGponRedGroupControlReqResult, fkGponRedGroupControlGroupIndex, fkGponRedGroupDbSyncStatus
                                 }
                        STATUS current
                        DESCRIPTION 
                                "setGponRedDbSyncCheck"
                        ::= { fkGponRedGroupNotification 8 }

                
                -- 1.3.6.1.4.1.10428 9 1.101.23.11.3.9
                fkGponRedGroupDbResyncChanged NOTIFICATION-TYPE
                        OBJECTS { fkGponRedGroupControlRequest, fkGponRedGroupControlTimeStamp, fkGponRedGroupControlReqResult, fkGponRedGroupControlGroupIndex, fkGponRedGroupDbSyncStatus
                                 }
                        STATUS current
                        DESCRIPTION 
                                "setGponRedDbResync"
                        ::= { fkGponRedGroupNotification 9 }

                
--  1.3.6.1.4.1.10428 9 1.101.23.12
                -- 1.3.6.1.4.1.10428 9 1.101.23.12
                fkGponOnuHost OBJECT IDENTIFIER ::= { fkGpon 12 }

                
--  1.3.6.1.4.1.10428 9 1.101.23.12.1
                -- 1.3.6.1.4.1.10428 9 1.101.23.12.1
                fkGponOnuHostTable OBJECT-TYPE
                        SYNTAX SEQUENCE OF FkGponOnuHostEntry
                        MAX-ACCESS not-accessible
                        STATUS current
                        DESCRIPTION
                                "fkGponOnuHostTable"
                        ::= { fkGponOnuHost 1 }

                
--  1.3.6.1.4.1.10428 9 1.101.23.12.1.1
                -- 1.3.6.1.4.1.10428 9 1.101.23.12.1.1
                fkGponOnuHostEntry OBJECT-TYPE
                        SYNTAX FkGponOnuHostEntry
                        MAX-ACCESS not-accessible
                        STATUS current
                        DESCRIPTION
                                "key: fkGponOnuHostOltId, fkGponOnuHostOnuId, fkGponOnuHostId"
                        INDEX { fkGponOnuHostOltId, fkGponOnuHostOnuId, fkGponOnuHostId }
                        ::= { fkGponOnuHostTable 1 }

                
                FkGponOnuHostEntry ::=
                        SEQUENCE { 
                                fkGponOnuHostOltId
                                        INTEGER,
                                fkGponOnuHostOnuId
                                        INTEGER,
                                fkGponOnuHostId
                                        INTEGER,
                                fkGponOnuHostIPAddr
                                        IpAddress,
                                fkGponOnuHostMask
                                        IpAddress,
                                fkGponOnuHostGW
                                        IpAddress,
                                fkGponOnuHostPriDns
                                        IpAddress,
                                fkGponOnuHostSecDns
                                        IpAddress,
                                fkGponOnuHostIpOption
                                        BITS,
                                fkGponOnuHostMacAddress
                                        OCTET STRING,
                                fkGponOnuHostDomainName
                                        OCTET STRING,
                                fkGponOnuHostHostName
                                        OCTET STRING,
                                fkGponOnuHostCurIpAddr
                                        IpAddress,
                                fkGponOnuHostCurMask
                                        IpAddress,
                                fkGponOnuHostCurGW
                                        IpAddress,
                                fkGponOnuHostCurPriDns
                                        IpAddress,
                                fkGponOnuHostCurSecDns
                                        IpAddress
                         }

--  1.3.6.1.4.1.10428 9 1.101.23.12.1.1.1
                -- 1.3.6.1.4.1.10428 9 1.101.23.12.1.1.1
                fkGponOnuHostOltId OBJECT-TYPE
                        SYNTAX INTEGER (1..512)
                        MAX-ACCESS read-only
                        STATUS current
                        DESCRIPTION
                                "Gpon Olt Index"
                        ::= { fkGponOnuHostEntry 1 }

                
--  1.3.6.1.4.1.10428 9 1.101.23.12.1.1.2
                -- 1.3.6.1.4.1.10428 9 1.101.23.12.1.1.2
                fkGponOnuHostOnuId OBJECT-TYPE
                        SYNTAX INTEGER (1..256)
                        MAX-ACCESS read-only
                        STATUS current
                        DESCRIPTION
                                "Gpon Onu Index"
                        ::= { fkGponOnuHostEntry 2 }

                
--  1.3.6.1.4.1.10428 9 1.101.23.12.1.1.3
                -- 1.3.6.1.4.1.10428 9 1.101.23.12.1.1.3
                fkGponOnuHostId OBJECT-TYPE
                        SYNTAX INTEGER (1..8)
                        MAX-ACCESS read-only
                        STATUS current
                        DESCRIPTION
                                "Onu Ip Host Config data Index"
                        ::= { fkGponOnuHostEntry 3 }

                
--  1.3.6.1.4.1.10428 9 1.101.23.12.1.1.4
                -- 1.3.6.1.4.1.10428 9 1.101.23.12.1.1.4
                fkGponOnuHostIPAddr OBJECT-TYPE
                        SYNTAX IpAddress
                        MAX-ACCESS read-only
                        STATUS current
                        DESCRIPTION
                                "Onu IP address"
                        ::= { fkGponOnuHostEntry 4 }

                
--  1.3.6.1.4.1.10428 9 1.101.23.12.1.1.5
                -- 1.3.6.1.4.1.10428 9 1.101.23.12.1.1.5
                fkGponOnuHostMask OBJECT-TYPE
                        SYNTAX IpAddress
                        MAX-ACCESS read-only
                        STATUS current
                        DESCRIPTION
                                "Onu IP Netmask"
                        ::= { fkGponOnuHostEntry 5 }

                
--  1.3.6.1.4.1.10428 9 1.101.23.12.1.1.6
                -- 1.3.6.1.4.1.10428 9 1.101.23.12.1.1.6
                fkGponOnuHostGW OBJECT-TYPE
                        SYNTAX IpAddress
                        MAX-ACCESS read-only
                        STATUS current
                        DESCRIPTION
                                "Onu Gateway"
                        ::= { fkGponOnuHostEntry 6 }

                
                -- 1.3.6.1.4.1.10428 9 1.101.23.12.1.1.7
                fkGponOnuHostPriDns OBJECT-TYPE
                        SYNTAX IpAddress
                        MAX-ACCESS read-only
                        STATUS current
                        DESCRIPTION
                                "The Primary DNS address."
                        ::= { fkGponOnuHostEntry 7 }

                
                -- 1.3.6.1.4.1.10428 9 1.101.23.12.1.1.8
                fkGponOnuHostSecDns OBJECT-TYPE
                        SYNTAX IpAddress
                        MAX-ACCESS read-only
                        STATUS current
                        DESCRIPTION
                                "The secondary DNS address"
                        ::= { fkGponOnuHostEntry 8 }

                
                -- 1.3.6.1.4.1.10428 9 1.101.23.12.1.1.9
                fkGponOnuHostIpOption OBJECT-TYPE
                        SYNTAX BITS
                                {
                                enableDhcp(0),
                                respondPings(1),
                                respondTraceroute(2)
                                }
                        MAX-ACCESS read-only
                        STATUS current
                        DESCRIPTION
                                "The IP option.
                                1:enableDhcp, 2, respondPings 4, respondTraceroute"
                        ::= { fkGponOnuHostEntry 9 }

                
                -- 1.3.6.1.4.1.10428 9 1.101.23.12.1.1.10
                fkGponOnuHostMacAddress OBJECT-TYPE
                        SYNTAX OCTET STRING
                        MAX-ACCESS read-only
                        STATUS current
                        DESCRIPTION
                                "The Mac address."
                        ::= { fkGponOnuHostEntry 10 }

                
                -- 1.3.6.1.4.1.10428 9 1.101.23.12.1.1.11
                fkGponOnuHostDomainName OBJECT-TYPE
                        SYNTAX OCTET STRING
                        MAX-ACCESS read-only
                        STATUS current
                        DESCRIPTION
                                "The Domain name"
                        ::= { fkGponOnuHostEntry 11 }

                
                -- 1.3.6.1.4.1.10428 9 1.101.23.12.1.1.12
                fkGponOnuHostHostName OBJECT-TYPE
                        SYNTAX OCTET STRING
                        MAX-ACCESS read-only
                        STATUS current
                        DESCRIPTION
                                "The host name."
                        ::= { fkGponOnuHostEntry 12 }

                
                -- 1.3.6.1.4.1.10428 9 1.101.23.12.1.1.13
                fkGponOnuHostCurIpAddr OBJECT-TYPE
                        SYNTAX IpAddress
                        MAX-ACCESS read-only
                        STATUS current
                        DESCRIPTION
                                "The Current IP address."
                        ::= { fkGponOnuHostEntry 13 }

                
                -- 1.3.6.1.4.1.10428 9 1.101.23.12.1.1.14
                fkGponOnuHostCurMask OBJECT-TYPE
                        SYNTAX IpAddress
                        MAX-ACCESS read-only
                        STATUS current
                        DESCRIPTION
                                "The Currest Mask."
                        ::= { fkGponOnuHostEntry 14 }

                
                -- 1.3.6.1.4.1.10428 9 1.101.23.12.1.1.15
                fkGponOnuHostCurGW OBJECT-TYPE
                        SYNTAX IpAddress
                        MAX-ACCESS read-only
                        STATUS current
                        DESCRIPTION
                                "The current gate way."
                        ::= { fkGponOnuHostEntry 15 }

                
                -- 1.3.6.1.4.1.10428 9 1.101.23.12.1.1.16
                fkGponOnuHostCurPriDns OBJECT-TYPE
                        SYNTAX IpAddress
                        MAX-ACCESS read-only
                        STATUS current
                        DESCRIPTION
                                "The current primary DNS address."
                        ::= { fkGponOnuHostEntry 16 }

                
                -- 1.3.6.1.4.1.10428 9 1.101.23.12.1.1.17
                fkGponOnuHostCurSecDns OBJECT-TYPE
                        SYNTAX IpAddress
                        MAX-ACCESS read-only
                        STATUS current
                        DESCRIPTION
                                "The current secondary DNS address."
                        ::= { fkGponOnuHostEntry 17 }

                
--  1.3.6.1.4.1.10428 9 1.101.23.12.2
                -- 1.3.6.1.4.1.10428 9 1.101.23.12.2
                fkGponOnuHostControl OBJECT IDENTIFIER ::= { fkGponOnuHost 2 }

                
--  1.3.6.1.4.1.10428 9 1.101.23.12.2.1
                -- 1.3.6.1.4.1.10428 9 1.101.23.12.2.1
                fkGponOnuHostControlRequest OBJECT-TYPE
                        SYNTAX INTEGER
                                {
                                setOnuHostIpInfo(1),
                                updateOnuHostInfo(2)
                                }
                        MAX-ACCESS read-write
                        STATUS current
                        DESCRIPTION
                                "The request of a user command"
                        ::= { fkGponOnuHostControl 1 }

                
--  1.3.6.1.4.1.10428 9 1.101.23.12.2.2
                -- 1.3.6.1.4.1.10428 9 1.101.23.12.2.2
                fkGponOnuHostControlStatus OBJECT-TYPE
                        SYNTAX FkControlStatusType
                        MAX-ACCESS read-only
                        STATUS current
                        DESCRIPTION
                                "The status of user command"
                        ::= { fkGponOnuHostControl 2 }

                
--  1.3.6.1.4.1.10428 9 1.101.23.12.2.3
                -- 1.3.6.1.4.1.10428 9 1.101.23.12.2.3
                fkGponOnuHostControlTimer OBJECT-TYPE
                        SYNTAX Gauge32
                        MAX-ACCESS read-write
                        STATUS current
                        DESCRIPTION
                                "The maximum time for the manager for a long running user command"
                        ::= { fkGponOnuHostControl 3 }

                
--  1.3.6.1.4.1.10428 9 1.101.23.12.2.4
                -- 1.3.6.1.4.1.10428 9 1.101.23.12.2.4
                fkGponOnuHostControlTimeStamp OBJECT-TYPE
                        SYNTAX TimeTicks
                        MAX-ACCESS read-only
                        STATUS current
                        DESCRIPTION
                                "The time stamp of the last command(end of command)"
                        ::= { fkGponOnuHostControl 4 }

                
--  1.3.6.1.4.1.10428 9 1.101.23.12.2.5
                -- 1.3.6.1.4.1.10428 9 1.101.23.12.2.5
                fkGponOnuHostControlReqResult OBJECT-TYPE
                        SYNTAX FkControlRequestResultType
                        MAX-ACCESS read-only
                        STATUS current
                        DESCRIPTION
                                "The result of the last user command"
                        ::= { fkGponOnuHostControl 5 }

                
--  1.3.6.1.4.1.10428 9 1.101.23.12.2.6
                -- 1.3.6.1.4.1.10428 9 1.101.23.12.2.6
                fkGponOnuHostControlOltId OBJECT-TYPE
                        SYNTAX INTEGER (1..512)
                        MAX-ACCESS read-write
                        STATUS current
                        DESCRIPTION
                                "The OLT id."
                        ::= { fkGponOnuHostControl 6 }

                
--  1.3.6.1.4.1.10428 9 1.101.23.12.2.7
                -- 1.3.6.1.4.1.10428 9 1.101.23.12.2.7
                fkGponOnuHostControlOnuId OBJECT-TYPE
                        SYNTAX INTEGER (1..256)
                        MAX-ACCESS read-write
                        STATUS current
                        DESCRIPTION
                                "The ONU id"
                        ::= { fkGponOnuHostControl 7 }

                
--  1.3.6.1.4.1.10428 9 1.101.23.12.2.8
                -- 1.3.6.1.4.1.10428 9 1.101.23.12.2.8
                fkGponOnuHostControlId OBJECT-TYPE
                        SYNTAX INTEGER (1..8)
                        MAX-ACCESS read-write
                        STATUS current
                        DESCRIPTION
                                "Onu Ip Host Config data Index"
                        ::= { fkGponOnuHostControl 8 }

                
--  1.3.6.1.4.1.10428 9 1.101.23.12.2.9
                -- 1.3.6.1.4.1.10428 9 1.101.23.12.2.9
                fkGponOnuHostControlIPAddr OBJECT-TYPE
                        SYNTAX IpAddress
                        MAX-ACCESS read-write
                        STATUS current
                        DESCRIPTION
                                "Onu IP address"
                        ::= { fkGponOnuHostControl 9 }

                
--  1.3.6.1.4.1.10428 9 1.101.23.12.2.10
                -- 1.3.6.1.4.1.10428 9 1.101.23.12.2.10
                fkGponOnuHostControlMask OBJECT-TYPE
                        SYNTAX IpAddress
                        MAX-ACCESS read-write
                        STATUS current
                        DESCRIPTION
                                "Onu IP Netmask"
                        ::= { fkGponOnuHostControl 10 }

                
--  1.3.6.1.4.1.10428 9 1.101.23.12.2.11
                -- 1.3.6.1.4.1.10428 9 1.101.23.12.2.11
                fkGponOnuHostControlGW OBJECT-TYPE
                        SYNTAX IpAddress
                        MAX-ACCESS read-write
                        STATUS current
                        DESCRIPTION
                                "Onu Gateway"
                        ::= { fkGponOnuHostControl 11 }

                
--  1.3.6.1.4.1.10428 9 1.101.23.12.3
                -- 1.3.6.1.4.1.10428 9 1.101.23.12.3
                fkGponOnuHostNotification OBJECT IDENTIFIER ::= { fkGponOnuHost 3 }

                
--  1.3.6.1.4.1.10428 9 1.101.23.12.3.1
                -- 1.3.6.1.4.1.10428 9 1.101.23.12.3.1
                fkGponOnuHostIPInfoChanged NOTIFICATION-TYPE
                        OBJECTS { fkGponOnuHostControlRequest, fkGponOnuHostControlTimeStamp, fkGponOnuHostControlReqResult, fkGponOnuHostControlOltId, fkGponOnuHostControlOnuId, 
                                fkGponOnuHostControlId, fkGponOnuHostControlIPAddr, fkGponOnuHostControlMask, fkGponOnuHostControlGW }
                        STATUS current
                        DESCRIPTION 
                                "Description."
                        ::= { fkGponOnuHostNotification 1 }

                
                -- 1.3.6.1.4.1.10428 9 1.101.23.12.3.2
                fkGponOnuHostInfoChanged NOTIFICATION-TYPE
                        OBJECTS { fkGponOnuHostControlRequest, fkGponOnuHostControlTimeStamp, fkGponOnuHostControlReqResult, fkGponOnuHostControlOltId, fkGponOnuHostControlOnuId
                                 }
                        STATUS current
                        DESCRIPTION 
                                "Description."
                        ::= { fkGponOnuHostNotification 2 }

                
--  1.3.6.1.4.1.10428 9 1.101.23.13
                -- 1.3.6.1.4.1.10428 9 1.101.23.13
                fkGponIgmpGroup OBJECT IDENTIFIER ::= { fkGpon 13 }

                
--   
-- 1.3.6.1.4.1.10428 9 1.101.23.13.1
                -- 1.3.6.1.4.1.10428 9 1.101.23.13.1
                fkGponIgmpGroupTable OBJECT-TYPE
                        SYNTAX SEQUENCE OF FkGponIgmpGroupEntry
                        MAX-ACCESS not-accessible
                        STATUS current
                        DESCRIPTION
                                "fkGponIgmpGroupTable"
                        ::= { fkGponIgmpGroup 1 }

                
--  1.3.6.1.4.1.10428 9 1.101.23.13.1.1
                -- 1.3.6.1.4.1.10428 9 1.101.23.13.1.1
                fkGponIgmpGroupEntry OBJECT-TYPE
                        SYNTAX FkGponIgmpGroupEntry
                        MAX-ACCESS not-accessible
                        STATUS current
                        DESCRIPTION
                                "key: fkGponIgmpGroupOltId, fkGponIgmpGroupOnuId, fkGponIgmpGroupIndex"
                        INDEX { fkGponIgmpGroupOltId, fkGponIgmpGroupOnuId, fkGponIgmpGroupIndex }
                        ::= { fkGponIgmpGroupTable 1 }

                
                FkGponIgmpGroupEntry ::=
                        SEQUENCE { 
                                fkGponIgmpGroupOltId
                                        INTEGER,
                                fkGponIgmpGroupOnuId
                                        INTEGER,
                                fkGponIgmpGroupUniId
                                        INTEGER,
                                fkGponIgmpGroupUniType
                                        INTEGER,
                                fkGponIgmpGroupIndex
                                        INTEGER,
                                fkGponIgmpGroupSrcIPAddr
                                        IpAddress,
                                fkGponIgmpGroupDstIPAddr
                                        IpAddress,
                                fkGponIgmpGroupRptIPAddr
                                        IpAddress,
                                fkGponIgmpGroupJoinTime
                                        INTEGER,
                                fkGponIgmpGroupVlanId
                                        INTEGER
                         }

--  1.3.6.1.4.1.10428 9 1.101.23.13.1.1.1
                -- 1.3.6.1.4.1.10428 9 1.101.23.13.1.1.1
                fkGponIgmpGroupOltId OBJECT-TYPE
                        SYNTAX INTEGER (1..512)
                        MAX-ACCESS read-only
                        STATUS current
                        DESCRIPTION
                                "The OLT id."
                        ::= { fkGponIgmpGroupEntry 1 }

                
--  1.3.6.1.4.1.10428 9 1.101.23.13.1.1.2
                -- 1.3.6.1.4.1.10428 9 1.101.23.13.1.1.2
                fkGponIgmpGroupOnuId OBJECT-TYPE
                        SYNTAX INTEGER (1..256)
                        MAX-ACCESS read-only
                        STATUS current
                        DESCRIPTION
                                "The ONU id."
                        ::= { fkGponIgmpGroupEntry 2 }

                
--  1.3.6.1.4.1.10428 9 1.101.23.13.1.1.3
                -- 1.3.6.1.4.1.10428 9 1.101.23.13.1.1.3
                fkGponIgmpGroupUniId OBJECT-TYPE
                        SYNTAX INTEGER (1..65535)
                        MAX-ACCESS read-only
                        STATUS current
                        DESCRIPTION
                                "The UNI id"
                        ::= { fkGponIgmpGroupEntry 3 }

                
--  1.3.6.1.4.1.10428 9 1.101.23.13.1.1.4
                -- 1.3.6.1.4.1.10428 9 1.101.23.13.1.1.4
                fkGponIgmpGroupUniType OBJECT-TYPE
                        SYNTAX INTEGER { eth(1) }
                        MAX-ACCESS read-only
                        STATUS current
                        DESCRIPTION
                                "The UNI type."
                        ::= { fkGponIgmpGroupEntry 4 }

                
--  1.3.6.1.4.1.10428 9 1.101.23.13.1.1.5
                -- 1.3.6.1.4.1.10428 9 1.101.23.13.1.1.5
                fkGponIgmpGroupIndex OBJECT-TYPE
                        SYNTAX INTEGER (1..65535)
                        MAX-ACCESS read-only
                        STATUS current
                        DESCRIPTION
                                "The IGMP group index."
                        ::= { fkGponIgmpGroupEntry 5 }

                
--  1.3.6.1.4.1.10428 9 1.101.23.13.1.1.6
                -- 1.3.6.1.4.1.10428 9 1.101.23.13.1.1.6
                fkGponIgmpGroupSrcIPAddr OBJECT-TYPE
                        SYNTAX IpAddress
                        MAX-ACCESS read-only
                        STATUS current
                        DESCRIPTION
                                "The source IP address"
                        ::= { fkGponIgmpGroupEntry 6 }

                
--   
-- 1.3.6.1.4.1.10428 9 1.101.23.13.1.1.7
                -- 1.3.6.1.4.1.10428 9 1.101.23.13.1.1.7
                fkGponIgmpGroupDstIPAddr OBJECT-TYPE
                        SYNTAX IpAddress
                        MAX-ACCESS read-only
                        STATUS current
                        DESCRIPTION
                                "The destination IP address"
                        ::= { fkGponIgmpGroupEntry 7 }

                
--  1.3.6.1.4.1.10428 9 1.101.23.13.1.1.8
                -- 1.3.6.1.4.1.10428 9 1.101.23.13.1.1.8
                fkGponIgmpGroupRptIPAddr OBJECT-TYPE
                        SYNTAX IpAddress
                        MAX-ACCESS read-only
                        STATUS current
                        DESCRIPTION
                                "The  IP address"
                        ::= { fkGponIgmpGroupEntry 8 }

                
--   
-- 1.3.6.1.4.1.10428 9 1.101.23.13.1.1.9
                -- 1.3.6.1.4.1.10428 9 1.101.23.13.1.1.9
                fkGponIgmpGroupJoinTime OBJECT-TYPE
                        SYNTAX INTEGER (1..65535)
                        MAX-ACCESS read-only
                        STATUS current
                        DESCRIPTION
                                "The join time."
                        ::= { fkGponIgmpGroupEntry 9 }

                
                -- 1.3.6.1.4.1.10428 9 1.101.23.13.1.1.10
                fkGponIgmpGroupVlanId OBJECT-TYPE
                        SYNTAX INTEGER (1..4094)
                        MAX-ACCESS read-only
                        STATUS current
                        DESCRIPTION
                                "The Vlan Id."
                        ::= { fkGponIgmpGroupEntry 10 }

                
                -- 1.3.6.1.4.1.10428 9 1.101.23.13.2
                fkGponIgmpGroupControl OBJECT IDENTIFIER ::= { fkGponIgmpGroup 2 }

                
                -- 1.3.6.1.4.1.10428 9 1.101.23.13.2.1
                fkGponIgmpGroupControlRequest OBJECT-TYPE
                        SYNTAX INTEGER { setGponIgmpGroup(1) }
                        MAX-ACCESS read-write
                        STATUS current
                        DESCRIPTION
                                "The request of a user command"
                        ::= { fkGponIgmpGroupControl 1 }

                
                -- 1.3.6.1.4.1.10428 9 1.101.23.13.2.2
                fkGponIgmpGroupControlStatus OBJECT-TYPE
                        SYNTAX FkControlStatusType
                        MAX-ACCESS read-write
                        STATUS current
                        DESCRIPTION
                                "The status of user command"
                        ::= { fkGponIgmpGroupControl 2 }

                
                -- 1.3.6.1.4.1.10428 9 1.101.23.13.2.3
                fkGponIgmpGroupControlTimer OBJECT-TYPE
                        SYNTAX Gauge32
                        MAX-ACCESS read-write
                        STATUS current
                        DESCRIPTION
                                "The maximum time for the manager for a long running user command"
                        ::= { fkGponIgmpGroupControl 3 }

                
                -- 1.3.6.1.4.1.10428 9 1.101.23.13.2.4
                fkGponIgmpGroupControlTimeStamp OBJECT-TYPE
                        SYNTAX TimeTicks
                        MAX-ACCESS read-write
                        STATUS current
                        DESCRIPTION
                                "The time stamp of the last command(end of command)"
                        ::= { fkGponIgmpGroupControl 4 }

                
                -- 1.3.6.1.4.1.10428 9 1.101.23.13.2.5
                fkGponIgmpGroupControlReqResult OBJECT-TYPE
                        SYNTAX FkControlRequestResultType
                        MAX-ACCESS read-write
                        STATUS current
                        DESCRIPTION
                                "The result of the last user command"
                        ::= { fkGponIgmpGroupControl 5 }

                
                -- 1.3.6.1.4.1.10428 9 1.101.23.13.2.6
                fkGponIgmpGroupControlOltId OBJECT-TYPE
                        SYNTAX Integer32 (1..65535)
                        MAX-ACCESS read-write
                        STATUS current
                        DESCRIPTION
                                "The OLT id."
                        ::= { fkGponIgmpGroupControl 6 }

                
                -- 1.3.6.1.4.1.10428 9 1.101.23.13.2.7
                fkGponIgmpGroupControlOnuId OBJECT-TYPE
                        SYNTAX Integer32 (1..65535)
                        MAX-ACCESS read-write
                        STATUS current
                        DESCRIPTION
                                "The ONU id."
                        ::= { fkGponIgmpGroupControl 7 }

                
                -- 1.3.6.1.4.1.10428 9 1.101.23.13.3
                fkGponIgmpGroupNotification OBJECT IDENTIFIER ::= { fkGponIgmpGroup 3 }

                
                -- 1.3.6.1.4.1.10428 9 1.101.23.13.3.1
                fkGponIgmpGroupChanged NOTIFICATION-TYPE
                        OBJECTS { fkGponIgmpGroupControlRequest, fkGponIgmpGroupControlTimeStamp, fkGponIgmpGroupControlReqResult, fkGponIgmpGroupControlOltId, fkGponIgmpGroupControlOnuId
                                 }
                        STATUS current
                        DESCRIPTION 
                                "Description."
                        ::= { fkGponIgmpGroupNotification 1 }

                
                -- 1.3.6.1.4.1.10428 9 1.101.23.14
                fkGponAntiSpoofing OBJECT IDENTIFIER ::= { fkGpon 14 }

                
                -- 1.3.6.1.4.1.10428 9 1.101.23.14.1
                fkGponAntiSpoofingTable OBJECT-TYPE
                        SYNTAX SEQUENCE OF FkGponAntiSpoofingEntry
                        MAX-ACCESS not-accessible
                        STATUS current
                        DESCRIPTION
                                "fkGponAntiSpoofingTable"
                        ::= { fkGponAntiSpoofing 1 }

                
                -- 1.3.6.1.4.1.10428 9 1.101.23.14.1.1
                fkGponAntiSpoofingEntry OBJECT-TYPE
                        SYNTAX FkGponAntiSpoofingEntry
                        MAX-ACCESS not-accessible
                        STATUS current
                        DESCRIPTION
                                "key: fkGponAntiSpoofingOltId, fkGponAntiSpoofingOnuId, fkGponAntiSpoofingVlanId, fkGponAntiSpoofingMacIndex"
                        INDEX { fkGponAntiSpoofingOltId, fkGponAntiSpoofingOnuId, fkGponAntiSpoofingVlanId, fkGponAntiSpoofingMacIndex }
                        ::= { fkGponAntiSpoofingTable 1 }

                
                FkGponAntiSpoofingEntry ::=
                        SEQUENCE { 
                                fkGponAntiSpoofingOltId
                                        INTEGER,
                                fkGponAntiSpoofingOnuId
                                        INTEGER,
                                fkGponAntiSpoofingVlanId
                                        Integer32,
                                fkGponAntiSpoofingMacIndex
                                        INTEGER,
                                fkGponAntiSpoofingMac
                                        OCTET STRING,
                                fkGponAntiSpoofingPortId
                                        INTEGER,
                                fkGponAntiSpoofingDupPortId
                                        INTEGER,
                                fkGponAntiSpoofingTimerStatus
                                        INTEGER,
                                fkGponAntiSpoofingFilterStatus
                                        INTEGER
                         }

                -- 1.3.6.1.4.1.10428 9 1.101.23.14.1.1.1
                fkGponAntiSpoofingOltId OBJECT-TYPE
                        SYNTAX INTEGER (1..512)
                        MAX-ACCESS read-only
                        STATUS current
                        DESCRIPTION
                                "The OLT index."
                        ::= { fkGponAntiSpoofingEntry 1 }

                
                -- 1.3.6.1.4.1.10428 9 1.101.23.14.1.1.2
                fkGponAntiSpoofingOnuId OBJECT-TYPE
                        SYNTAX INTEGER (1..256)
                        MAX-ACCESS read-only
                        STATUS current
                        DESCRIPTION
                                "The ONU index."
                        ::= { fkGponAntiSpoofingEntry 2 }

                
                -- 1.3.6.1.4.1.10428 9 1.101.23.14.1.1.3
                fkGponAntiSpoofingVlanId OBJECT-TYPE
                        SYNTAX Integer32 (1..4094)
                        MAX-ACCESS read-only
                        STATUS current
                        DESCRIPTION
                                "The VLAN index."
                        ::= { fkGponAntiSpoofingEntry 3 }

                
                -- 1.3.6.1.4.1.10428 9 1.101.23.14.1.1.4
                fkGponAntiSpoofingMacIndex OBJECT-TYPE
                        SYNTAX INTEGER (1..65535)
                        MAX-ACCESS read-only
                        STATUS current
                        DESCRIPTION
                                "The MAC index is only used at 'Get'. "
                        ::= { fkGponAntiSpoofingEntry 4 }

                
                -- 1.3.6.1.4.1.10428 9 1.101.23.14.1.1.5
                fkGponAntiSpoofingMac OBJECT-TYPE
                        SYNTAX OCTET STRING
                        MAX-ACCESS read-only
                        STATUS current
                        DESCRIPTION
                                "The OLT mac address."
                        ::= { fkGponAntiSpoofingEntry 5 }

                
                -- 1.3.6.1.4.1.10428 9 1.101.23.14.1.1.6
                fkGponAntiSpoofingPortId OBJECT-TYPE
                        SYNTAX INTEGER (1..65535)
                        MAX-ACCESS read-only
                        STATUS current
                        DESCRIPTION
                                "The Port index."
                        ::= { fkGponAntiSpoofingEntry 6 }

                
                -- 1.3.6.1.4.1.10428 9 1.101.23.14.1.1.7
                fkGponAntiSpoofingDupPortId OBJECT-TYPE
                        SYNTAX INTEGER (1..65535)
                        MAX-ACCESS read-only
                        STATUS current
                        DESCRIPTION
                                "The Duplicated Port index."
                        ::= { fkGponAntiSpoofingEntry 7 }

                
                -- 1.3.6.1.4.1.10428 9 1.101.23.14.1.1.8
                fkGponAntiSpoofingTimerStatus OBJECT-TYPE
                        SYNTAX INTEGER (1..65535)
                        MAX-ACCESS read-only
                        STATUS current
                        DESCRIPTION
                                "The Anti-Spoofing Timer."
                        ::= { fkGponAntiSpoofingEntry 8 }

                
                -- 1.3.6.1.4.1.10428 9 1.101.23.14.1.1.9
                fkGponAntiSpoofingFilterStatus OBJECT-TYPE
                        SYNTAX INTEGER
                                {
                                filtering(0),
                                notSupport(1)
                                }
                        MAX-ACCESS read-only
                        STATUS current
                        DESCRIPTION
                                "The filter status."
                        ::= { fkGponAntiSpoofingEntry 9 }

                
                -- 1.3.6.1.4.1.10428 9 1.101.23.14.2
                fkGponAntiSpoofingControl OBJECT IDENTIFIER ::= { fkGponAntiSpoofing 2 }

                
                -- 1.3.6.1.4.1.10428 9 1.101.23.14.2.1
                fkGponAntiSpoofingControlRequest OBJECT-TYPE
                        SYNTAX INTEGER
                                {
                                updateAntiSpoofingStatus(1),
                                clearAntiSpoofingOlt(2),
                                clearAntiSpoofingOnu(3),
                                clearAntiSpoofingOne(4)
                                }
                        MAX-ACCESS read-write
                        STATUS current
                        DESCRIPTION
                                "The request of a user command"
                        ::= { fkGponAntiSpoofingControl 1 }

                
                -- 1.3.6.1.4.1.10428 9 1.101.23.14.2.2
                fkGponAntiSpoofingControlStatus OBJECT-TYPE
                        SYNTAX FkControlStatusType
                        MAX-ACCESS read-write
                        STATUS current
                        DESCRIPTION
                                "The status of user command"
                        ::= { fkGponAntiSpoofingControl 2 }

                
                -- 1.3.6.1.4.1.10428 9 1.101.23.14.2.3
                fkGponAntiSpoofingControlTimer OBJECT-TYPE
                        SYNTAX Gauge32
                        MAX-ACCESS read-write
                        STATUS current
                        DESCRIPTION
                                "The maximum time for the manager for a long running user command"
                        ::= { fkGponAntiSpoofingControl 3 }

                
                -- 1.3.6.1.4.1.10428 9 1.101.23.14.2.4
                fkGponAntiSpoofingControlTimeStamp OBJECT-TYPE
                        SYNTAX TimeTicks
                        MAX-ACCESS read-write
                        STATUS current
                        DESCRIPTION
                                "The time stamp of the last command(end of command)"
                        ::= { fkGponAntiSpoofingControl 4 }

                
                -- 1.3.6.1.4.1.10428 9 1.101.23.14.2.5
                fkGponAntiSpoofingControlReqResult OBJECT-TYPE
                        SYNTAX FkControlRequestResultType
                        MAX-ACCESS read-write
                        STATUS current
                        DESCRIPTION
                                "The result of the last user command"
                        ::= { fkGponAntiSpoofingControl 5 }

                
                -- 1.3.6.1.4.1.10428 9 1.101.23.14.2.6
                fkGponAntiSpoofingControlOltId OBJECT-TYPE
                        SYNTAX INTEGER (1..512)
                        MAX-ACCESS read-write
                        STATUS current
                        DESCRIPTION
                                "The OLT index."
                        ::= { fkGponAntiSpoofingControl 6 }

                
                -- 1.3.6.1.4.1.10428 9 1.101.23.14.2.7
                fkGponAntiSpoofingControlOnuId OBJECT-TYPE
                        SYNTAX INTEGER (1..256)
                        MAX-ACCESS read-write
                        STATUS current
                        DESCRIPTION
                                "The ONU index."
                        ::= { fkGponAntiSpoofingControl 7 }

                
                -- 1.3.6.1.4.1.10428 9 1.101.23.14.2.8
                fkGponAntiSpoofingControlVlanId OBJECT-TYPE
                        SYNTAX Integer32 (1..4094)
                        MAX-ACCESS read-write
                        STATUS current
                        DESCRIPTION
                                "The VLAN index."
                        ::= { fkGponAntiSpoofingControl 8 }

                
                -- 1.3.6.1.4.1.10428 9 1.101.23.14.2.9
                fkGponAntiSpoofingControlMac OBJECT-TYPE
                        SYNTAX OCTET STRING
                        MAX-ACCESS read-write
                        STATUS current
                        DESCRIPTION
                                "The OLT mac address."
                        ::= { fkGponAntiSpoofingControl 9 }

                
                -- 1.3.6.1.4.1.10428 9 1.101.23.14.2.10
                fkGponAntiSpoofingControlPortId OBJECT-TYPE
                        SYNTAX INTEGER (1..65535)
                        MAX-ACCESS read-write
                        STATUS current
                        DESCRIPTION
                                "The Port index."
                        ::= { fkGponAntiSpoofingControl 10 }

                
                -- 1.3.6.1.4.1.10428 9 1.101.23.14.2.11
                fkGponAntiSpoofingControlTimerStatus OBJECT-TYPE
                        SYNTAX INTEGER (1..65535)
                        MAX-ACCESS read-write
                        STATUS current
                        DESCRIPTION
                                "The Anti-Spoofing Timer."
                        ::= { fkGponAntiSpoofingControl 11 }

                
                -- 1.3.6.1.4.1.10428 9 1.101.23.14.3
                fkGponAntiSpoofingNotification OBJECT IDENTIFIER ::= { fkGponAntiSpoofing 3 }

                
                -- 1.3.6.1.4.1.10428 9 1.101.23.14.3.1
                fkGponAntiSpoofingAntiSpoofingStatusChanged NOTIFICATION-TYPE
                        OBJECTS { fkGponAntiSpoofingControlRequest, fkGponAntiSpoofingControlTimeStamp, fkGponAntiSpoofingControlReqResult, fkGponAntiSpoofingControlOltId }
                        STATUS current
                        DESCRIPTION 
                                "Description."
                        ::= { fkGponAntiSpoofingNotification 1 }

                
                -- 1.3.6.1.4.1.10428 9 1.101.23.14.3.2
                fkGponAntiSpoofingAntiSpoofingOltCleared NOTIFICATION-TYPE
                        OBJECTS { fkGponAntiSpoofingControlRequest, fkGponAntiSpoofingControlTimeStamp, fkGponAntiSpoofingControlReqResult, fkGponAntiSpoofingControlOltId }
                        STATUS current
                        DESCRIPTION 
                                "Description."
                        ::= { fkGponAntiSpoofingNotification 2 }

                
                -- 1.3.6.1.4.1.10428 9 1.101.23.14.3.3
                fkGponAntiSpoofingAntiSpoofingOnuCleared NOTIFICATION-TYPE
                        OBJECTS { fkGponAntiSpoofingControlRequest, fkGponAntiSpoofingControlTimeStamp, fkGponAntiSpoofingControlReqResult, fkGponAntiSpoofingControlOltId, fkGponAntiSpoofingControlOnuId
                                 }
                        STATUS current
                        DESCRIPTION 
                                "Description."
                        ::= { fkGponAntiSpoofingNotification 3 }

                
                -- 1.3.6.1.4.1.10428 9 1.101.23.14.3.4
                fkGponAntiSpoofingAntiSpoofingOneCleared NOTIFICATION-TYPE
                        OBJECTS { fkGponAntiSpoofingControlRequest, fkGponAntiSpoofingControlTimeStamp, fkGponAntiSpoofingControlReqResult, fkGponAntiSpoofingControlOltId, fkGponAntiSpoofingControlOnuId, 
                                fkGponAntiSpoofingControlVlanId, fkGponAntiSpoofingControlMac }
                        STATUS current
                        DESCRIPTION 
                                "Description."
                        ::= { fkGponAntiSpoofingNotification 4 }

                
                -- 1.3.6.1.4.1.10428 9 1.101.23.15
                fkGponVlanGemMapping OBJECT IDENTIFIER ::= { fkGpon 15 }

                
                -- 1.3.6.1.4.1.10428 9 1.101.23.15.1
                fkGponVlanGemMappingTable OBJECT-TYPE
                        SYNTAX SEQUENCE OF FkGponVlanGemMappingEntry
                        MAX-ACCESS not-accessible
                        STATUS current
                        DESCRIPTION
                                "fkGpoVlanGemMappingTable"
                        ::= { fkGponVlanGemMapping 1 }

                
                -- 1.3.6.1.4.1.10428 9 1.101.23.15.1.1
                fkGponVlanGemMappingEntry OBJECT-TYPE
                        SYNTAX FkGponVlanGemMappingEntry
                        MAX-ACCESS not-accessible
                        STATUS current
                        DESCRIPTION
                                "key: fkGponOltId, fkGponOnuId, fkGponVlanGemMappingVid"
                        INDEX { fkGponOltId, fkGponVlanGemMappingVid }
                        ::= { fkGponVlanGemMappingTable 1 }

                
                FkGponVlanGemMappingEntry ::=
                        SEQUENCE { 
                                fkGponVlanGemMappingVid
                                        INTEGER,
                                fkGponVlanGemMappingOnuid
                                        INTEGER,
                                fkGponVlanGemMappingMapperId
                                        INTEGER,
                                fkGponVlanGemMappingGemPort
                                        INTEGER
                         }

                -- 1.3.6.1.4.1.10428 9 1.101.23.15.1.1.1
                fkGponVlanGemMappingVid OBJECT-TYPE
                        SYNTAX INTEGER (1..4094)
                        MAX-ACCESS read-only
                        STATUS current
                        DESCRIPTION
                                "The Vlan ID."
                        ::= { fkGponVlanGemMappingEntry 1 }

                
                -- 1.3.6.1.4.1.10428 9 1.101.23.15.1.1.2
                fkGponVlanGemMappingOnuid OBJECT-TYPE
                        SYNTAX INTEGER (1..256)
                        MAX-ACCESS read-only
                        STATUS current
                        DESCRIPTION
                                "The ONU index. (255 is all onu)"
                        ::= { fkGponVlanGemMappingEntry 2 }

                
                -- 1.3.6.1.4.1.10428 9 1.101.23.15.1.1.3
                fkGponVlanGemMappingMapperId OBJECT-TYPE
                        SYNTAX INTEGER (1..65535)
                        MAX-ACCESS read-only
                        STATUS current
                        DESCRIPTION
                                "The mapper ID. (4095 is multicast gem)"
                        ::= { fkGponVlanGemMappingEntry 3 }

                
                -- 1.3.6.1.4.1.10428 9 1.101.23.15.1.1.4
                fkGponVlanGemMappingGemPort OBJECT-TYPE
                        SYNTAX INTEGER (1..65535)
                        MAX-ACCESS read-only
                        STATUS current
                        DESCRIPTION
                                "The GEM port."
                        ::= { fkGponVlanGemMappingEntry 4 }

                
                -- 1.3.6.1.4.1.10428 9 1.101.23.15.2
                fkGponVlanGemMappingControl OBJECT IDENTIFIER ::= { fkGponVlanGemMapping 2 }

                
                -- 1.3.6.1.4.1.10428 9 1.101.23.15.2.1
                fkGponVlanGemMappingControlRequest OBJECT-TYPE
                        SYNTAX INTEGER
                                {
                                setVlanGemMapping(1),
                                clearVlanGemMapping(2),
                                clearOnuVlanGemMapping(3),
                                clearOltVlanGemMapping(4)
                                }
                        MAX-ACCESS read-write
                        STATUS current
                        DESCRIPTION
                                "The request of a user command"
                        ::= { fkGponVlanGemMappingControl 1 }

                
                -- 1.3.6.1.4.1.10428 9 1.101.23.15.2.2
                fkGponVlanGemMappingControlStatus OBJECT-TYPE
                        SYNTAX FkControlStatusType
                        MAX-ACCESS read-only
                        STATUS current
                        DESCRIPTION
                                "The status of user command"
                        ::= { fkGponVlanGemMappingControl 2 }

                
                -- 1.3.6.1.4.1.10428 9 1.101.23.15.2.3
                fkGponVlanGemMappingControlTimer OBJECT-TYPE
                        SYNTAX Gauge32
                        MAX-ACCESS read-write
                        STATUS current
                        DESCRIPTION
                                "The maximum time for the manager for a long running user command"
                        ::= { fkGponVlanGemMappingControl 3 }

                
                -- 1.3.6.1.4.1.10428 9 1.101.23.15.2.4
                fkGponVlanGemMappingControlTimeStamp OBJECT-TYPE
                        SYNTAX TimeTicks
                        MAX-ACCESS read-only
                        STATUS current
                        DESCRIPTION
                                "The time stamp of the last command(end of command)"
                        ::= { fkGponVlanGemMappingControl 4 }

                
                -- 1.3.6.1.4.1.10428 9 1.101.23.15.2.5
                fkGponVlanGemMappingControlReqResult OBJECT-TYPE
                        SYNTAX FkControlRequestResultType
                        MAX-ACCESS read-only
                        STATUS current
                        DESCRIPTION
                                "The result of the last user command"
                        ::= { fkGponVlanGemMappingControl 5 }

                
                -- 1.3.6.1.4.1.10428 9 1.101.23.15.2.6
                fkGponVlanGemMappingControlOltId OBJECT-TYPE
                        SYNTAX INTEGER (1..512)
                        MAX-ACCESS read-write
                        STATUS current
                        DESCRIPTION
                                "The OLT ID."
                        ::= { fkGponVlanGemMappingControl 6 }

                
                -- 1.3.6.1.4.1.10428 9 1.101.23.15.2.7
                fkGponVlanGemMappingControlOnuId OBJECT-TYPE
                        SYNTAX INTEGER (1..256)
                        MAX-ACCESS read-write
                        STATUS current
                        DESCRIPTION
                                "The ONU index. (255 is all onu)"
                        ::= { fkGponVlanGemMappingControl 7 }

                
                -- 1.3.6.1.4.1.10428 9 1.101.23.15.2.8
                fkGponVlanGemMappingControlVid OBJECT-TYPE
                        SYNTAX INTEGER (1..4094)
                        MAX-ACCESS read-write
                        STATUS current
                        DESCRIPTION
                                "The Vlan ID."
                        ::= { fkGponVlanGemMappingControl 8 }

                
                -- 1.3.6.1.4.1.10428 9 1.101.23.15.2.9
                fkGponVlanGemMappingControlMapperId OBJECT-TYPE
                        SYNTAX INTEGER (1..65535)
                        MAX-ACCESS read-write
                        STATUS current
                        DESCRIPTION
                                "The mapper ID. (4095 is multicast gem)"
                        ::= { fkGponVlanGemMappingControl 9 }

                
--  1.3.6.1.4.1.10428 9 1.101.23.15.2.10
                -- 1.3.6.1.4.1.10428 9 1.101.23.15.2.10
                fkGponVlanGemMappingControlVidTo OBJECT-TYPE
                        SYNTAX INTEGER (1..4094)
                        MAX-ACCESS read-write
                        STATUS current
                        DESCRIPTION
                                "The Vlan ID."
                        ::= { fkGponVlanGemMappingControl 10 }

                
--  1.3.6.1.4.1.10428 9 1.101.23.15.3
                -- 1.3.6.1.4.1.10428 9 1.101.23.15.3
                fkGpoVlanGemMappingNotification OBJECT IDENTIFIER ::= { fkGponVlanGemMapping 3 }

                
--  1.3.6.1.4.1.10428 9 1.101.23.15.3.1
                -- 1.3.6.1.4.1.10428 9 1.101.23.15.3.1
                fkGponVlanGemMappingChagned NOTIFICATION-TYPE
                        OBJECTS { fkGponVlanGemMappingControlRequest, fkGponVlanGemMappingControlTimeStamp, fkGponVlanGemMappingControlReqResult, fkGponVlanGemMappingControlOltId, fkGponVlanGemMappingControlOnuId, 
                                fkGponVlanGemMappingControlVid, fkGponVlanGemMappingControlMapperId, fkGponVlanGemMappingControlVidTo }
                        STATUS current
                        DESCRIPTION 
                                "fkGponVlanGemMappingControlRequest, fkGponVlanGemMappingControlTimeStamp, fkGponVlanGemMappingControlReqResult, fkGponVlanGemMappingControlOltId, fkGponVlanGemMappingControlOnuId, fkGponVlanGemMappingControlVid, fkGponVlanGemMappingControlMapperId, fkGponVlanGemMappingControlVidTo"
                        ::= { fkGpoVlanGemMappingNotification 1 }

                
--  1.3.6.1.4.1.10428 9 1.101.23.15.3.2
                -- 1.3.6.1.4.1.10428 9 1.101.23.15.3.2
                fkGponVlanGemMappingCleared NOTIFICATION-TYPE
                        OBJECTS { fkGponVlanGemMappingControlRequest, fkGponVlanGemMappingControlTimeStamp, fkGponVlanGemMappingControlReqResult, fkGponVlanGemMappingControlOltId, fkGponVlanGemMappingControlOnuId, 
                                fkGponVlanGemMappingControlVid, fkGponVlanGemMappingControlVidTo }
                        STATUS current
                        DESCRIPTION 
                                "fkGponVlanGemMappingControlRequest, fkGponVlanGemMappingControlTimeStamp, fkGponVlanGemMappingControlReqResult, fkGponVlanGemMappingControlOltId, fkGponVlanGemMappingControlOnuId, fkGponVlanGemMappingControlVid, fkGponVlanGemMappingControlMapperId, fkGponVlanGemMappingControlVidTo"
                        ::= { fkGpoVlanGemMappingNotification 2 }

                
--  1.3.6.1.4.1.10428 9 1.101.23.15.3.3
                -- 1.3.6.1.4.1.10428 9 1.101.23.15.3.3
                fkGponOnuVlanGemMappingCleared NOTIFICATION-TYPE
                        OBJECTS { fkGponVlanGemMappingControlRequest, fkGponVlanGemMappingControlTimeStamp, fkGponVlanGemMappingControlReqResult, fkGponVlanGemMappingControlOltId, fkGponVlanGemMappingControlOnuId
                                 }
                        STATUS current
                        DESCRIPTION 
                                "clearOnuVlanGemMapping"
                        ::= { fkGpoVlanGemMappingNotification 3 }

                
--  1.3.6.1.4.1.10428 9 1.101.23.15.3.4
                -- 1.3.6.1.4.1.10428 9 1.101.23.15.3.4
                fkGponOltVlanGemMappingCleared NOTIFICATION-TYPE
                        OBJECTS { fkGponVlanGemMappingControlRequest, fkGponVlanGemMappingControlTimeStamp, fkGponVlanGemMappingControlReqResult, fkGponVlanGemMappingControlOltId }
                        STATUS current
                        DESCRIPTION 
                                "clearOltVlanGemMapping"
                        ::= { fkGpoVlanGemMappingNotification 4 }

                
                -- 1.3.6.1.4.1.10428 9 1.101.23.16
                fkGponGemPort OBJECT IDENTIFIER ::= { fkGpon 16 }

                
                -- 1.3.6.1.4.1.10428 9 1.101.23.16.1
                fkGponGemPortTable OBJECT-TYPE
                        SYNTAX SEQUENCE OF FkGponGemPortEntry
                        MAX-ACCESS not-accessible
                        STATUS current
                        DESCRIPTION
                                "fkGponGemPortTable"
                        ::= { fkGponGemPort 1 }

                
                -- 1.3.6.1.4.1.10428 9 1.101.23.16.1.1
                fkGponGemPortEntry OBJECT-TYPE
                        SYNTAX FkGponGemPortEntry
                        MAX-ACCESS not-accessible
                        STATUS current
                        DESCRIPTION
                                "key : fkGponOltId, fkGponOnuId, fkGponGemPortId"
                        INDEX { fkGponOltId, fkGponOnuId, fkGponGemPortId }
                        ::= { fkGponGemPortTable 1 }

                
                FkGponGemPortEntry ::=
                        SEQUENCE { 
                                fkGponGemPortId
                                        INTEGER,
                                fkGponGemPortNum
                                        INTEGER,
                                fkGponGemPortMapperId
                                        INTEGER,
                                fkGponGemPortCos
                                        BITS
                         }

                -- 1.3.6.1.4.1.10428 9 1.101.23.16.1.1.1
                fkGponGemPortId OBJECT-TYPE
                        SYNTAX INTEGER (1..65535)
                        MAX-ACCESS read-only
                        STATUS current
                        DESCRIPTION
                                "the GEM port index."
                        ::= { fkGponGemPortEntry 1 }

                
                -- 1.3.6.1.4.1.10428 9 1.101.23.16.1.1.2
                fkGponGemPortNum OBJECT-TYPE
                        SYNTAX INTEGER (128..4096)
                        MAX-ACCESS read-only
                        STATUS current
                        DESCRIPTION
                                "The GEM Port number."
                        ::= { fkGponGemPortEntry 2 }

                
                -- 1.3.6.1.4.1.10428 9 1.101.23.16.1.1.3
                fkGponGemPortMapperId OBJECT-TYPE
                        SYNTAX INTEGER (1..65535)
                        MAX-ACCESS read-only
                        STATUS current
                        DESCRIPTION
                                "The mapper index."
                        ::= { fkGponGemPortEntry 3 }

                
                -- 1.3.6.1.4.1.10428 9 1.101.23.16.1.1.4
                fkGponGemPortCos OBJECT-TYPE
                        SYNTAX BITS
                                {
                                cos0(0),
                                cos1(1),
                                cos2(2),
                                cos3(3),
                                cos4(4),
                                cos5(5),
                                cos6(6),
                                cos7(7)
                                }
                        MAX-ACCESS read-only
                        STATUS current
                        DESCRIPTION
                                "The CoS value."
                        ::= { fkGponGemPortEntry 4 }

                
                -- 1.3.6.1.4.1.10428 9 1.101.23.17
                fkGponOnuMcast OBJECT IDENTIFIER ::= { fkGpon 17 }

                
                -- 1.3.6.1.4.1.10428 9 1.101.23.17.1
                fkGponOnuMcastAcl OBJECT IDENTIFIER ::= { fkGponOnuMcast 1 }

                
                -- 1.3.6.1.4.1.10428 9 1.101.23.17.1.1
                fkGponOnuMcastAclTable OBJECT-TYPE
                        SYNTAX SEQUENCE OF FkGponOnuMcastAclEntry
                        MAX-ACCESS not-accessible
                        STATUS current
                        DESCRIPTION
                                "Description."
                        ::= { fkGponOnuMcastAcl 1 }

                
                -- 1.3.6.1.4.1.10428 9 1.101.23.17.1.1.1
                fkGponOnuMcastAclEntry OBJECT-TYPE
                        SYNTAX FkGponOnuMcastAclEntry
                        MAX-ACCESS not-accessible
                        STATUS current
                        DESCRIPTION
                                "Description."
                        INDEX { fkGponOltId, fkGponOnuId, fkGponOnuMcastAclMcastIndex, fkGponOnuMcastAclTableIndex }
                        ::= { fkGponOnuMcastAclTable 1 }

                
                FkGponOnuMcastAclEntry ::=
                        SEQUENCE { 
                                fkGponOnuMcastAclOltId
                                        Integer32,
                                fkGponOnuMcastAclOnuId
                                        Integer32,
                                fkGponOnuMcastAclMcastIndex
                                        Integer32,
                                fkGponOnuMcastAclMcastName
                                        OCTET STRING,
                                fkGponOnuMcastAclTableIndex
                                        Integer32,
                                fkGponOnuMcastAclVid
                                        Integer32,
                                fkGponOnuMcastAclDstIpStart
                                        IpAddress,
                                fkGponOnuMcastAclDstIpEnd
                                        IpAddress,
                                fkGponOnuMcastAclSrcIp
                                        IpAddress,
                                fkGponOnuMcastAclBandwidth
                                        Integer32,
                                fkGponOnuMcastAclGem
                                        Integer32
                         }

                -- 1.3.6.1.4.1.10428 9 1.101.23.17.1.1.1.1
                fkGponOnuMcastAclOltId OBJECT-TYPE
                        SYNTAX Integer32 (1..512)
                        MAX-ACCESS read-only
                        STATUS current
                        DESCRIPTION
                                "The OLT index."
                        ::= { fkGponOnuMcastAclEntry 1 }

                
                -- 1.3.6.1.4.1.10428 9 1.101.23.17.1.1.1.2
                fkGponOnuMcastAclOnuId OBJECT-TYPE
                        SYNTAX Integer32 (1..256)
                        MAX-ACCESS read-only
                        STATUS current
                        DESCRIPTION
                                "The ONU index."
                        ::= { fkGponOnuMcastAclEntry 2 }

                
                -- 1.3.6.1.4.1.10428 9 1.101.23.17.1.1.1.3
                fkGponOnuMcastAclMcastIndex OBJECT-TYPE
                        SYNTAX Integer32 (1..65535)
                        MAX-ACCESS read-only
                        STATUS current
                        DESCRIPTION
                                "The Mcast Index."
                        ::= { fkGponOnuMcastAclEntry 3 }

                
                -- 1.3.6.1.4.1.10428 9 1.101.23.17.1.1.1.4
                fkGponOnuMcastAclMcastName OBJECT-TYPE
                        SYNTAX OCTET STRING
                        MAX-ACCESS read-only
                        STATUS current
                        DESCRIPTION
                                "The Mcast name."
                        ::= { fkGponOnuMcastAclEntry 4 }

                
                -- 1.3.6.1.4.1.10428 9 1.101.23.17.1.1.1.5
                fkGponOnuMcastAclTableIndex OBJECT-TYPE
                        SYNTAX Integer32 (1..65535)
                        MAX-ACCESS read-only
                        STATUS current
                        DESCRIPTION
                                "The table index."
                        ::= { fkGponOnuMcastAclEntry 5 }

                
                -- 1.3.6.1.4.1.10428 9 1.101.23.17.1.1.1.6
                fkGponOnuMcastAclVid OBJECT-TYPE
                        SYNTAX Integer32 (1..4094)
                        MAX-ACCESS read-only
                        STATUS current
                        DESCRIPTION
                                "The vlan index."
                        ::= { fkGponOnuMcastAclEntry 6 }

                
                -- 1.3.6.1.4.1.10428 9 1.101.23.17.1.1.1.7
                fkGponOnuMcastAclDstIpStart OBJECT-TYPE
                        SYNTAX IpAddress
                        MAX-ACCESS read-only
                        STATUS current
                        DESCRIPTION
                                "The destination start ip-address."
                        ::= { fkGponOnuMcastAclEntry 7 }

                
                -- 1.3.6.1.4.1.10428 9 1.101.23.17.1.1.1.8
                fkGponOnuMcastAclDstIpEnd OBJECT-TYPE
                        SYNTAX IpAddress
                        MAX-ACCESS read-only
                        STATUS current
                        DESCRIPTION
                                "The destination end ip-address."
                        ::= { fkGponOnuMcastAclEntry 8 }

                
                -- 1.3.6.1.4.1.10428 9 1.101.23.17.1.1.1.9
                fkGponOnuMcastAclSrcIp OBJECT-TYPE
                        SYNTAX IpAddress
                        MAX-ACCESS read-only
                        STATUS current
                        DESCRIPTION
                                "The source ip-address."
                        ::= { fkGponOnuMcastAclEntry 9 }

                
                -- 1.3.6.1.4.1.10428 9 1.101.23.17.1.1.1.10
                fkGponOnuMcastAclBandwidth OBJECT-TYPE
                        SYNTAX Integer32
                        MAX-ACCESS read-only
                        STATUS current
                        DESCRIPTION
                                "The bandwidth"
                        ::= { fkGponOnuMcastAclEntry 10 }

                
                -- 1.3.6.1.4.1.10428 9 1.101.23.17.1.1.1.11
                fkGponOnuMcastAclGem OBJECT-TYPE
                        SYNTAX Integer32 (1..65535)
                        MAX-ACCESS read-only
                        STATUS current
                        DESCRIPTION
                                "The Gem port index."
                        ::= { fkGponOnuMcastAclEntry 11 }

                
                -- 1.3.6.1.4.1.10428 9 1.101.23.17.1.2
                fkGponOnuMcastAclControl OBJECT IDENTIFIER ::= { fkGponOnuMcastAcl 2 }

                
                -- 1.3.6.1.4.1.10428 9 1.101.23.17.1.2.1
                fkGponOnuMcastAclControlRequest OBJECT-TYPE
                        SYNTAX INTEGER
                                {
                                createMcastAcl(1),
                                clearMcastAcl(2),
                                clearMcastAclOnu(3),
                                clearMcastAclOlt(4)
                                }
                        MAX-ACCESS read-write
                        STATUS current
                        DESCRIPTION
                                "The request of a user command"
                        ::= { fkGponOnuMcastAclControl 1 }

                
                -- 1.3.6.1.4.1.10428 9 1.101.23.17.1.2.2
                fkGponOnuMcastAclControlStatus OBJECT-TYPE
                        SYNTAX FkControlStatusType
                        MAX-ACCESS read-only
                        STATUS current
                        DESCRIPTION
                                "The status of user command"
                        ::= { fkGponOnuMcastAclControl 2 }

                
                -- 1.3.6.1.4.1.10428 9 1.101.23.17.1.2.3
                fkGponOnuMcastAclControlTimer OBJECT-TYPE
                        SYNTAX Gauge32
                        MAX-ACCESS read-write
                        STATUS current
                        DESCRIPTION
                                "The maximum time for the manager for a long running user command"
                        ::= { fkGponOnuMcastAclControl 3 }

                
                -- 1.3.6.1.4.1.10428 9 1.101.23.17.1.2.4
                fkGponOnuMcastAclControlTimeStamp OBJECT-TYPE
                        SYNTAX TimeTicks
                        MAX-ACCESS read-only
                        STATUS current
                        DESCRIPTION
                                "The time stamp of the last command(end of command)"
                        ::= { fkGponOnuMcastAclControl 4 }

                
                -- 1.3.6.1.4.1.10428 9 1.101.23.17.1.2.5
                fkGponOnuMcastAclControlReqResult OBJECT-TYPE
                        SYNTAX FkControlRequestResultType
                        MAX-ACCESS read-only
                        STATUS current
                        DESCRIPTION
                                "The result of the last user command"
                        ::= { fkGponOnuMcastAclControl 5 }

                
                -- 1.3.6.1.4.1.10428 9 1.101.23.17.1.2.6
                fkGponOnuMcastAclControlOltId OBJECT-TYPE
                        SYNTAX Integer32 (1..512)
                        MAX-ACCESS read-write
                        STATUS current
                        DESCRIPTION
                                "The OLT index."
                        ::= { fkGponOnuMcastAclControl 6 }

                
                -- 1.3.6.1.4.1.10428 9 1.101.23.17.1.2.7
                fkGponOnuMcastAclControlOnuId OBJECT-TYPE
                        SYNTAX Integer32 (1..256)
                        MAX-ACCESS read-write
                        STATUS current
                        DESCRIPTION
                                "The ONU index."
                        ::= { fkGponOnuMcastAclControl 7 }

                
                -- 1.3.6.1.4.1.10428 9 1.101.23.17.1.2.8
                fkGponOnuMcastAclControlMcastName OBJECT-TYPE
                        SYNTAX OCTET STRING
                        MAX-ACCESS read-write
                        STATUS current
                        DESCRIPTION
                                "The Mcase name."
                        ::= { fkGponOnuMcastAclControl 8 }

                
                -- 1.3.6.1.4.1.10428 9 1.101.23.17.1.2.9
                fkGponOnuMcastAclControlTableIndex OBJECT-TYPE
                        SYNTAX Integer32 (1..65535)
                        MAX-ACCESS read-write
                        STATUS current
                        DESCRIPTION
                                "The table index."
                        ::= { fkGponOnuMcastAclControl 9 }

                
                -- 1.3.6.1.4.1.10428 9 1.101.23.17.1.2.10
                fkGponOnuMcastAclControlVid OBJECT-TYPE
                        SYNTAX Integer32 (1..4094)
                        MAX-ACCESS read-write
                        STATUS current
                        DESCRIPTION
                                "The vlan index."
                        ::= { fkGponOnuMcastAclControl 10 }

                
                -- 1.3.6.1.4.1.10428 9 1.101.23.17.1.2.11
                fkGponOnuMcastAclControlDstIpStart OBJECT-TYPE
                        SYNTAX IpAddress
                        MAX-ACCESS read-write
                        STATUS current
                        DESCRIPTION
                                "The destination start ip-address."
                        ::= { fkGponOnuMcastAclControl 11 }

                
                -- 1.3.6.1.4.1.10428 9 1.101.23.17.1.2.12
                fkGponOnuMcastAclControlDstIpEnd OBJECT-TYPE
                        SYNTAX IpAddress
                        MAX-ACCESS read-write
                        STATUS current
                        DESCRIPTION
                                "The destination end ip-address."
                        ::= { fkGponOnuMcastAclControl 12 }

                
                -- 1.3.6.1.4.1.10428 9 1.101.23.17.1.2.13
                fkGponOnuMcastAclControlSrcIp OBJECT-TYPE
                        SYNTAX IpAddress
                        MAX-ACCESS read-write
                        STATUS current
                        DESCRIPTION
                                "The source ip-address."
                        ::= { fkGponOnuMcastAclControl 13 }

                
                -- 1.3.6.1.4.1.10428 9 1.101.23.17.1.2.14
                fkGponOnuMcastAclControlBandwidth OBJECT-TYPE
                        SYNTAX Integer32
                        MAX-ACCESS read-write
                        STATUS current
                        DESCRIPTION
                                "The bandwidth"
                        ::= { fkGponOnuMcastAclControl 14 }

                
                -- 1.3.6.1.4.1.10428 9 1.101.23.17.1.2.15
                fkGponOnuMcastAclControlGem OBJECT-TYPE
                        SYNTAX Integer32 (1..65535)
                        MAX-ACCESS read-write
                        STATUS current
                        DESCRIPTION
                                "The Gem port index."
                        ::= { fkGponOnuMcastAclControl 15 }

                
                -- 1.3.6.1.4.1.10428 9 1.101.23.17.1.3
                fkGponOnuMcastAclNotification OBJECT IDENTIFIER ::= { fkGponOnuMcastAcl 3 }

                
                -- 1.3.6.1.4.1.10428 9 1.101.23.17.1.3.1
                fkGponOnuMcastAclCreated NOTIFICATION-TYPE
                        OBJECTS { fkGponOnuMcastAclControlRequest, fkGponOnuMcastAclControlTimeStamp, fkGponOnuMcastAclControlReqResult, fkGponOnuMcastAclControlOltId, fkGponOnuMcastAclControlOnuId, 
                                fkGponOnuMcastAclControlMcastName, fkGponOnuMcastAclControlTableIndex, fkGponOnuMcastAclControlVid, fkGponOnuMcastAclControlDstIpStart, fkGponOnuMcastAclControlDstIpEnd, 
                                fkGponOnuMcastAclControlSrcIp, fkGponOnuMcastAclControlBandwidth, fkGponOnuMcastAclControlGem }
                        STATUS current
                        DESCRIPTION 
                                "createMcastAcl"
                        ::= { fkGponOnuMcastAclNotification 1 }

                
                -- 1.3.6.1.4.1.10428 9 1.101.23.17.1.3.2
                fkGponOnuMcastAclCleared NOTIFICATION-TYPE
                        OBJECTS { fkGponOnuMcastAclControlRequest, fkGponOnuMcastAclControlTimeStamp, fkGponOnuMcastAclControlReqResult, fkGponOnuMcastAclControlOltId, fkGponOnuMcastAclControlOnuId, 
                                fkGponOnuMcastAclControlMcastName, fkGponOnuMcastAclControlTableIndex }
                        STATUS current
                        DESCRIPTION 
                                "clearMcastAcl"
                        ::= { fkGponOnuMcastAclNotification 2 }

                
                -- 1.3.6.1.4.1.10428 9 1.101.23.17.1.3.3
                fkGponOnuMcastAclOnuCleared NOTIFICATION-TYPE
                        OBJECTS { fkGponOnuMcastAclControlRequest, fkGponOnuMcastAclControlTimeStamp, fkGponOnuMcastAclControlReqResult, fkGponOnuMcastAclControlOltId, fkGponOnuMcastAclControlOnuId
                                 }
                        STATUS current
                        DESCRIPTION 
                                "clearMcastAclOnu"
                        ::= { fkGponOnuMcastAclNotification 3 }

                
                -- 1.3.6.1.4.1.10428 9 1.101.23.17.1.3.4
                fkGponOnuMcastAclOltCleared NOTIFICATION-TYPE
                        OBJECTS { fkGponOnuMcastAclControlRequest, fkGponOnuMcastAclControlTimeStamp, fkGponOnuMcastAclControlReqResult, fkGponOnuMcastAclControlOltId }
                        STATUS current
                        DESCRIPTION 
                                "Description."
                        ::= { fkGponOnuMcastAclNotification 4 }

                
                -- 1.3.6.1.4.1.10428 9 1.101.23.18
                fkGponFlowMapping OBJECT IDENTIFIER ::= { fkGpon 18 }

                
                -- 1.3.6.1.4.1.10428 9 1.101.23.18.1
                fkGponFlowMappingMethod OBJECT IDENTIFIER ::= { fkGponFlowMapping 1 }

                
                -- 1.3.6.1.4.1.10428 9 1.101.23.18.1.1
                fkGponFlowMappingMethodTable OBJECT-TYPE
                        SYNTAX SEQUENCE OF FkGponFlowMappingMethodEntry
                        MAX-ACCESS not-accessible
                        STATUS current
                        DESCRIPTION
                                "Description."
                        ::= { fkGponFlowMappingMethod 1 }

                
                -- 1.3.6.1.4.1.10428 9 1.101.23.18.1.1.1
                fkGponFlowMappingMethodEntry OBJECT-TYPE
                        SYNTAX FkGponFlowMappingMethodEntry
                        MAX-ACCESS not-accessible
                        STATUS current
                        DESCRIPTION
                                "Description."
                        INDEX { fkGponOltId, fkGponFlowMappingMethodVid }
                        ::= { fkGponFlowMappingMethodTable 1 }

                
                FkGponFlowMappingMethodEntry ::=
                        SEQUENCE { 
                                fkGponFlowMappingMethodVid
                                        Integer32,
                                fkGponFlowMappingMethodType
                                        INTEGER
                         }

                -- 1.3.6.1.4.1.10428 9 1.101.23.18.1.1.1.1
                fkGponFlowMappingMethodVid OBJECT-TYPE
                        SYNTAX Integer32 (1..4094)
                        MAX-ACCESS read-only
                        STATUS current
                        DESCRIPTION
                                "The VLAN index."
                        ::= { fkGponFlowMappingMethodEntry 1 }

                
                -- 1.3.6.1.4.1.10428 9 1.101.23.18.1.1.1.2
                fkGponFlowMappingMethodType OBJECT-TYPE
                        SYNTAX INTEGER
                                {
                                vid(1),
                                mac(2),
                                macVid(3)
                                }
                        MAX-ACCESS read-only
                        STATUS current
                        DESCRIPTION
                                "The method type."
                        ::= { fkGponFlowMappingMethodEntry 2 }

                
                -- 1.3.6.1.4.1.10428 9 1.101.23.18.1.2
                fkGponFlowMappingMethodControl OBJECT IDENTIFIER ::= { fkGponFlowMappingMethod 2 }

                
                -- 1.3.6.1.4.1.10428 9 1.101.23.18.1.2.1
                fkGponFlowMappingMethodControlRequest OBJECT-TYPE
                        SYNTAX INTEGER
                                {
                                setFlowMappingMethod(1),
                                clearFlowMappingMethod(2),
                                clearFlowMappingMethodOlt(3)
                                }
                        MAX-ACCESS read-write
                        STATUS current
                        DESCRIPTION
                                "The request of a user command"
                        ::= { fkGponFlowMappingMethodControl 1 }

                
                -- 1.3.6.1.4.1.10428 9 1.101.23.18.1.2.2
                fkGponFlowMappingMethodControlStatus OBJECT-TYPE
                        SYNTAX FkControlStatusType
                        MAX-ACCESS read-only
                        STATUS current
                        DESCRIPTION
                                "The status of user command"
                        ::= { fkGponFlowMappingMethodControl 2 }

                
                -- 1.3.6.1.4.1.10428 9 1.101.23.18.1.2.3
                fkGponFlowMappingMethodControlTimer OBJECT-TYPE
                        SYNTAX Gauge32
                        MAX-ACCESS read-write
                        STATUS current
                        DESCRIPTION
                                "The maximum time for the manager for a long running user command"
                        ::= { fkGponFlowMappingMethodControl 3 }

                
                -- 1.3.6.1.4.1.10428 9 1.101.23.18.1.2.4
                fkGponFlowMappingMethodControlTimeStamp OBJECT-TYPE
                        SYNTAX TimeTicks
                        MAX-ACCESS read-only
                        STATUS current
                        DESCRIPTION
                                "The time stamp of the last command(end of command)"
                        ::= { fkGponFlowMappingMethodControl 4 }

                
                -- 1.3.6.1.4.1.10428 9 1.101.23.18.1.2.5
                fkGponFlowMappingMethodControlReqResult OBJECT-TYPE
                        SYNTAX FkControlRequestResultType
                        MAX-ACCESS read-only
                        STATUS current
                        DESCRIPTION
                                "The result of the last user command"
                        ::= { fkGponFlowMappingMethodControl 5 }

                
                -- 1.3.6.1.4.1.10428 9 1.101.23.18.1.2.6
                fkGponFlowMappingMethodControlOltId OBJECT-TYPE
                        SYNTAX Integer32 (1..512)
                        MAX-ACCESS read-write
                        STATUS current
                        DESCRIPTION
                                "The OLT ID."
                        ::= { fkGponFlowMappingMethodControl 6 }

                
                -- 1.3.6.1.4.1.10428 9 1.101.23.18.1.2.7
                fkGponFlowMappingMethodControlVid OBJECT-TYPE
                        SYNTAX INTEGER (1..4094)
                        MAX-ACCESS read-write
                        STATUS current
                        DESCRIPTION
                                "The Vlan ID."
                        ::= { fkGponFlowMappingMethodControl 7 }

                
                -- 1.3.6.1.4.1.10428 9 1.101.23.18.1.2.8
                fkGponFlowMappingMethodControlType OBJECT-TYPE
                        SYNTAX INTEGER
                                {
                                vid(1),
                                mac(2),
                                macVid(3)
                                }
                        MAX-ACCESS read-write
                        STATUS current
                        DESCRIPTION
                                "The method type."
                        ::= { fkGponFlowMappingMethodControl 8 }

                
                -- 1.3.6.1.4.1.10428 9 1.101.23.18.1.3
                fkGponFlowMappingMethodNotification OBJECT IDENTIFIER ::= { fkGponFlowMappingMethod 3 }

                
                -- 1.3.6.1.4.1.10428 9 1.101.23.18.1.3.1
                fkGponFlowMappingMethodChanged NOTIFICATION-TYPE
                        OBJECTS { fkGponFlowMappingMethodControlRequest, fkGponFlowMappingMethodControlTimeStamp, fkGponFlowMappingMethodControlReqResult, fkGponFlowMappingMethodControlOltId, fkGponFlowMappingMethodControlVid, 
                                fkGponFlowMappingMethodControlType }
                        STATUS current
                        DESCRIPTION 
                                "setFlowMappingMethod"
                        ::= { fkGponFlowMappingMethodNotification 1 }

                
                -- 1.3.6.1.4.1.10428 9 1.101.23.18.1.3.2
                fkGponFlowMappingMethodCleared NOTIFICATION-TYPE
                        OBJECTS { fkGponFlowMappingMethodControlRequest, fkGponFlowMappingMethodControlTimeStamp, fkGponFlowMappingMethodControlReqResult, fkGponFlowMappingMethodControlOltId, fkGponFlowMappingMethodControlVid
                                 }
                        STATUS current
                        DESCRIPTION 
                                "clearFlowMappingMethod"
                        ::= { fkGponFlowMappingMethodNotification 2 }

                
                -- 1.3.6.1.4.1.10428 9 1.101.23.18.1.3.3
                fkGponFlowMappingMethodOltCleared NOTIFICATION-TYPE
                        OBJECTS { fkGponFlowMappingMethodControlRequest, fkGponFlowMappingMethodControlTimeStamp, fkGponFlowMappingMethodControlReqResult, fkGponFlowMappingMethodControlOltId }
                        STATUS current
                        DESCRIPTION 
                                "clearFlowMappingMethodOlt"
                        ::= { fkGponFlowMappingMethodNotification 3 }

                
                -- 1.3.6.1.4.1.10428 9 1.101.23.19
                fkGponOnuMac OBJECT IDENTIFIER ::= { fkGpon 19 }

                
                -- 1.3.6.1.4.1.10428 9 1.101.23.19.1
                fkGponOnuMacTable OBJECT-TYPE
                        SYNTAX SEQUENCE OF FkGponOnuMacEntry
                        MAX-ACCESS not-accessible
                        STATUS current
                        DESCRIPTION
                                "Description."
                        ::= { fkGponOnuMac 1 }

                
                -- 1.3.6.1.4.1.10428 9 1.101.23.19.1.1
                fkGponOnuMacEntry OBJECT-TYPE
                        SYNTAX FkGponOnuMacEntry
                        MAX-ACCESS not-accessible
                        STATUS current
                        DESCRIPTION
                                "Description."
                        INDEX { fkGponOltId, fkGponOnuId, fkGponOnuMacSlotIndex, fkGponOnuMacPortIndex, fkGponOnuMacIndex
                                 }
                        ::= { fkGponOnuMacTable 1 }

                
                FkGponOnuMacEntry ::=
                        SEQUENCE { 
                                fkGponOnuMacSlotIndex
                                        INTEGER,
                                fkGponOnuMacPortIndex
                                        Integer32,
                                fkGponOnuMacIndex
                                        Integer32,
                                fkGponOnuMacAddress
                                        OCTET STRING,
                                fkGponOnuMacPolicy
                                        INTEGER,
                                fkGponOnuMacStatus
                                        INTEGER,
                                fkGponOnuMacAge
                                        Integer32
                         }

--  1.3.6.1.4.1.10428 9 1.101.23.6.1.1.1.1
                -- 1.3.6.1.4.1.10428 9 1.101.23.19.1.1.1
                fkGponOnuMacSlotIndex OBJECT-TYPE
                        SYNTAX INTEGER
                                {
                                ethernet(1),
                                pots(2),
                                ces(3),
                                video(4),
                                virtualEthernet(5)
                                }
                        MAX-ACCESS read-only
                        STATUS current
                        DESCRIPTION
                                "The slot index."
                        ::= { fkGponOnuMacEntry 1 }

                
                -- 1.3.6.1.4.1.10428 9 1.101.23.19.1.1.2
                fkGponOnuMacPortIndex OBJECT-TYPE
                        SYNTAX Integer32 (1..65523)
                        MAX-ACCESS read-only
                        STATUS current
                        DESCRIPTION
                                "The port index."
                        ::= { fkGponOnuMacEntry 2 }

                
                -- 1.3.6.1.4.1.10428 9 1.101.23.19.1.1.3
                fkGponOnuMacIndex OBJECT-TYPE
                        SYNTAX Integer32 (1..8000)
                        MAX-ACCESS read-only
                        STATUS current
                        DESCRIPTION
                                "The MAC index."
                        ::= { fkGponOnuMacEntry 3 }

                
                -- 1.3.6.1.4.1.10428 9 1.101.23.19.1.1.4
                fkGponOnuMacAddress OBJECT-TYPE
                        SYNTAX OCTET STRING
                        MAX-ACCESS read-only
                        STATUS current
                        DESCRIPTION
                                "The MAC address."
                        ::= { fkGponOnuMacEntry 4 }

                
                -- 1.3.6.1.4.1.10428 9 1.101.23.19.1.1.5
                fkGponOnuMacPolicy OBJECT-TYPE
                        SYNTAX INTEGER
                                {
                                forward(1),
                                filter(2)
                                }
                        MAX-ACCESS read-only
                        STATUS current
                        DESCRIPTION
                                "The MAC policy"
                        ::= { fkGponOnuMacEntry 5 }

                
                -- 1.3.6.1.4.1.10428 9 1.101.23.19.1.1.6
                fkGponOnuMacStatus OBJECT-TYPE
                        SYNTAX INTEGER
                                {
                                static(1),
                                dynamic(2)
                                }
                        MAX-ACCESS read-only
                        STATUS current
                        DESCRIPTION
                                "The MAC status."
                        ::= { fkGponOnuMacEntry 6 }

                
                -- 1.3.6.1.4.1.10428 9 1.101.23.19.1.1.7
                fkGponOnuMacAge OBJECT-TYPE
                        SYNTAX Integer32
                        MAX-ACCESS read-only
                        STATUS current
                        DESCRIPTION
                                "the MAC age"
                        ::= { fkGponOnuMacEntry 7 }

                
                -- 1.3.6.1.4.1.10428 9 1.101.23.19.2
                fkGponOnuMacControl OBJECT IDENTIFIER ::= { fkGponOnuMac 2 }

                
                -- 1.3.6.1.4.1.10428 9 1.101.23.19.2.1
                fkGponOnuMacControlRequest OBJECT-TYPE
                        SYNTAX INTEGER { updateOnuMac(1) }
                        MAX-ACCESS read-write
                        STATUS current
                        DESCRIPTION
                                "The request of a user command"
                        ::= { fkGponOnuMacControl 1 }

                
                -- 1.3.6.1.4.1.10428 9 1.101.23.19.2.2
                fkGponOnuMacControlStatus OBJECT-TYPE
                        SYNTAX FkControlStatusType
                        MAX-ACCESS read-only
                        STATUS current
                        DESCRIPTION
                                "The status of user command"
                        ::= { fkGponOnuMacControl 2 }

                
                -- 1.3.6.1.4.1.10428 9 1.101.23.19.2.3
                fkGponOnuMacControlTimer OBJECT-TYPE
                        SYNTAX Gauge32
                        MAX-ACCESS read-write
                        STATUS current
                        DESCRIPTION
                                "The maximum time for the manager for a long running user command"
                        ::= { fkGponOnuMacControl 3 }

                
                -- 1.3.6.1.4.1.10428 9 1.101.23.19.2.4
                fkGponOnuMacControlTimeStamp OBJECT-TYPE
                        SYNTAX TimeTicks
                        MAX-ACCESS read-only
                        STATUS current
                        DESCRIPTION
                                "The time stamp of the last command(end of command)"
                        ::= { fkGponOnuMacControl 4 }

                
                -- 1.3.6.1.4.1.10428 9 1.101.23.19.2.5
                fkGponOnuMacControlReqResult OBJECT-TYPE
                        SYNTAX FkControlRequestResultType
                        MAX-ACCESS read-only
                        STATUS current
                        DESCRIPTION
                                "The result of the last user command"
                        ::= { fkGponOnuMacControl 5 }

                
                -- 1.3.6.1.4.1.10428 9 1.101.23.19.2.6
                fkGponOnuMacControlOltIndex OBJECT-TYPE
                        SYNTAX Integer32
                        MAX-ACCESS read-write
                        STATUS current
                        DESCRIPTION
                                "The OLT index."
                        ::= { fkGponOnuMacControl 6 }

                
                -- 1.3.6.1.4.1.10428 9 1.101.23.19.2.7
                fkGponOnuMacControlOnuIndex OBJECT-TYPE
                        SYNTAX Integer32
                        MAX-ACCESS read-write
                        STATUS current
                        DESCRIPTION
                                "The ONU index."
                        ::= { fkGponOnuMacControl 7 }

                
                -- 1.3.6.1.4.1.10428 9 1.101.23.19.2.8
                fkGponOnuMacControlSlotIndex OBJECT-TYPE
                        SYNTAX INTEGER
                                {
                                ethernet(1),
                                pots(2),
                                ces(3),
                                video(4),
                                virtualEthernet(5)
                                }
                        MAX-ACCESS read-write
                        STATUS current
                        DESCRIPTION
                                "The slot index."
                        ::= { fkGponOnuMacControl 8 }

                
                -- 1.3.6.1.4.1.10428 9 1.101.23.19.2.9
                fkGponOnuMacControlPortIndex OBJECT-TYPE
                        SYNTAX Integer32
                        MAX-ACCESS read-write
                        STATUS current
                        DESCRIPTION
                                "The port index."
                        ::= { fkGponOnuMacControl 9 }

                
                -- 1.3.6.1.4.1.10428 9 1.101.23.19.3
                fkGponOnuMacNotification OBJECT IDENTIFIER ::= { fkGponOnuMac 3 }

                
                -- 1.3.6.1.4.1.10428 9 1.101.23.19.3.1
                fkGponOnuMacUpdated NOTIFICATION-TYPE
                        OBJECTS { fkGponOnuMacControlRequest, fkGponOnuMacControlTimeStamp, fkGponOnuMacControlReqResult, fkGponOnuMacControlOltIndex, fkGponOnuMacControlOnuIndex, 
                                fkGponOnuMacControlSlotIndex, fkGponOnuMacControlPortIndex }
                        STATUS current
                        DESCRIPTION 
                                "updateOnuMac"
                        ::= { fkGponOnuMacNotification 1 }

                
                -- 1.3.6.1.4.1.10428 9 1.101.23.20
                fkGponOnuMacFilter OBJECT IDENTIFIER ::= { fkGpon 20 }

                
                -- 1.3.6.1.4.1.10428 9 1.101.23.20.1
                fkGponOnuMacFilterTable OBJECT-TYPE
                        SYNTAX SEQUENCE OF FkGponOnuMacFilterEntry
                        MAX-ACCESS not-accessible
                        STATUS current
                        DESCRIPTION
                                "Description."
                        ::= { fkGponOnuMacFilter 1 }

                
                -- 1.3.6.1.4.1.10428 9 1.101.23.20.1.1
                fkGponOnuMacFilterEntry OBJECT-TYPE
                        SYNTAX FkGponOnuMacFilterEntry
                        MAX-ACCESS not-accessible
                        STATUS current
                        DESCRIPTION
                                "Description."
                        INDEX { fkGponOltId, fkGponOnuId, fkGponOnuMacFilterSlotType, fkGponOnuMacFilterPortId, fkGponOnuMacFilterMac
                                 }
                        ::= { fkGponOnuMacFilterTable 1 }

                
                FkGponOnuMacFilterEntry ::=
                        SEQUENCE { 
                                fkGponOnuMacFilterOltId
                                        Integer32,
                                fkGponOnuMacFilterOnuId
                                        Integer32,
                                fkGponOnuMacFilterSlotType
                                        INTEGER,
                                fkGponOnuMacFilterPortId
                                        Integer32,
                                fkGponOnuMacFilterMac
                                        OCTET STRING,
                                fkGponOnuMacFilterType
                                        INTEGER
                         }

                -- 1.3.6.1.4.1.10428 9 1.101.23.20.1.1.1
                fkGponOnuMacFilterOltId OBJECT-TYPE
                        SYNTAX Integer32
                        MAX-ACCESS read-only
                        STATUS current
                        DESCRIPTION
                                "The OLT index."
                        ::= { fkGponOnuMacFilterEntry 1 }

                
                -- 1.3.6.1.4.1.10428 9 1.101.23.20.1.1.2
                fkGponOnuMacFilterOnuId OBJECT-TYPE
                        SYNTAX Integer32
                        MAX-ACCESS read-only
                        STATUS current
                        DESCRIPTION
                                "The ONU index."
                        ::= { fkGponOnuMacFilterEntry 2 }

                
                -- 1.3.6.1.4.1.10428 9 1.101.23.20.1.1.3
                fkGponOnuMacFilterSlotType OBJECT-TYPE
                        SYNTAX INTEGER
                                {
                                ethernet(1),
                                iphost(2),
                                ces(3),
                                virtualEthernet(4),
                                mapper(5),
                                gem(6)
                                }
                        MAX-ACCESS read-only
                        STATUS current
                        DESCRIPTION
                                "The slot type."
                        ::= { fkGponOnuMacFilterEntry 3 }

                
                -- 1.3.6.1.4.1.10428 9 1.101.23.20.1.1.4
                fkGponOnuMacFilterPortId OBJECT-TYPE
                        SYNTAX Integer32 (1..65535)
                        MAX-ACCESS read-only
                        STATUS current
                        DESCRIPTION
                                "The port  index"
                        ::= { fkGponOnuMacFilterEntry 4 }

                
                -- 1.3.6.1.4.1.10428 9 1.101.23.20.1.1.5
                fkGponOnuMacFilterMac OBJECT-TYPE
                        SYNTAX OCTET STRING
                        MAX-ACCESS read-only
                        STATUS current
                        DESCRIPTION
                                "The MAC address."
                        ::= { fkGponOnuMacFilterEntry 5 }

                
                -- 1.3.6.1.4.1.10428 9 1.101.23.20.1.1.6
                fkGponOnuMacFilterType OBJECT-TYPE
                        SYNTAX INTEGER
                                {
                                filter(1),
                                forward(2)
                                }
                        MAX-ACCESS read-only
                        STATUS current
                        DESCRIPTION
                                "The MAC filter type.
                                filter mode       1
                                forward mode    2
                                "
                        ::= { fkGponOnuMacFilterEntry 6 }

                
                -- 1.3.6.1.4.1.10428 9 1.101.23.20.2
                fkGponOnuMacFilterControl OBJECT IDENTIFIER ::= { fkGponOnuMacFilter 2 }

                
                -- 1.3.6.1.4.1.10428 9 1.101.23.20.2.1
                fkGponOnuMacFilterControlRequest OBJECT-TYPE
                        SYNTAX INTEGER
                                {
                                setOnuMacFilter(1),
                                delOnuMacFilter(2)
                                }
                        MAX-ACCESS read-write
                        STATUS current
                        DESCRIPTION
                                "The request of a user command"
                        ::= { fkGponOnuMacFilterControl 1 }

                
                -- 1.3.6.1.4.1.10428 9 1.101.23.20.2.2
                fkGponOnuMacFilterControlStatus OBJECT-TYPE
                        SYNTAX FkControlStatusType
                        MAX-ACCESS read-only
                        STATUS current
                        DESCRIPTION
                                "The status of user command"
                        ::= { fkGponOnuMacFilterControl 2 }

                
                -- 1.3.6.1.4.1.10428 9 1.101.23.20.2.3
                fkGponOnuMacFilterControlTimer OBJECT-TYPE
                        SYNTAX Gauge32
                        MAX-ACCESS read-write
                        STATUS current
                        DESCRIPTION
                                "The maximum time for the manager for a long running user command"
                        ::= { fkGponOnuMacFilterControl 3 }

                
                -- 1.3.6.1.4.1.10428 9 1.101.23.20.2.4
                fkGponOnuMacFilterControlTimeStamp OBJECT-TYPE
                        SYNTAX TimeTicks
                        MAX-ACCESS read-only
                        STATUS current
                        DESCRIPTION
                                "The time stamp of the last command(end of command)"
                        ::= { fkGponOnuMacFilterControl 4 }

                
                -- 1.3.6.1.4.1.10428 9 1.101.23.20.2.5
                fkGponOnuMacFilterControlReqResult OBJECT-TYPE
                        SYNTAX FkControlRequestResultType
                        MAX-ACCESS read-only
                        STATUS current
                        DESCRIPTION
                                "The result of the last user command"
                        ::= { fkGponOnuMacFilterControl 5 }

                
                -- 1.3.6.1.4.1.10428 9 1.101.23.20.2.6
                fkGponOnuMacFilterControlOltIndex OBJECT-TYPE
                        SYNTAX Integer32
                        MAX-ACCESS read-write
                        STATUS current
                        DESCRIPTION
                                "The OLT index."
                        ::= { fkGponOnuMacFilterControl 6 }

                
                -- 1.3.6.1.4.1.10428 9 1.101.23.20.2.7
                fkGponOnuMacFilterControlOnuIndex OBJECT-TYPE
                        SYNTAX Integer32
                        MAX-ACCESS read-write
                        STATUS current
                        DESCRIPTION
                                "The ONU index."
                        ::= { fkGponOnuMacFilterControl 7 }

                
                -- 1.3.6.1.4.1.10428 9 1.101.23.20.2.8
                fkGponOnuMacFilterControlSlotType OBJECT-TYPE
                        SYNTAX INTEGER
                                {
                                ethernet(1),
                                iphost(2),
                                ces(3),
                                virtualEthernet(4),
                                mapper(5),
                                gem(6)
                                }
                        MAX-ACCESS read-write
                        STATUS current
                        DESCRIPTION
                                "The slot index."
                        ::= { fkGponOnuMacFilterControl 8 }

                
                -- 1.3.6.1.4.1.10428 9 1.101.23.20.2.9
                fkGponOnuMacFilterControlPortIndex OBJECT-TYPE
                        SYNTAX Integer32
                        MAX-ACCESS read-write
                        STATUS current
                        DESCRIPTION
                                "The port index."
                        ::= { fkGponOnuMacFilterControl 9 }

                
                -- 1.3.6.1.4.1.10428 9 1.101.23.20.2.10
                fkGponOnuMacFilterControlMac OBJECT-TYPE
                        SYNTAX OCTET STRING
                        MAX-ACCESS read-write
                        STATUS current
                        DESCRIPTION
                                "The mac address"
                        ::= { fkGponOnuMacFilterControl 10 }

                
                -- 1.3.6.1.4.1.10428 9 1.101.23.20.2.11
                fkGponOnuMacFilterControlType OBJECT-TYPE
                        SYNTAX INTEGER
                                {
                                filter(1),
                                forward(2)
                                }
                        MAX-ACCESS read-write
                        STATUS current
                        DESCRIPTION
                                "The MAC filter type.
                                filter mode       1
                                forward mode    2"
                        ::= { fkGponOnuMacFilterControl 11 }

                
                -- 1.3.6.1.4.1.10428 9 1.101.23.20.3
                fkGponOnuMacFilterNotification OBJECT IDENTIFIER ::= { fkGponOnuMacFilter 3 }

                
                -- 1.3.6.1.4.1.10428 9 1.101.23.20.3.1
                fkGponOnuMacFilterChanged NOTIFICATION-TYPE
                        OBJECTS { fkGponOnuMacFilterControlRequest, fkGponOnuMacFilterControlTimeStamp, fkGponOnuMacFilterControlReqResult, fkGponOnuMacFilterControlOltIndex, fkGponOnuMacFilterControlOnuIndex, 
                                fkGponOnuMacFilterControlSlotType, fkGponOnuMacFilterControlPortIndex, fkGponOnuMacFilterControlMac, fkGponOnuMacFilterControlType }
                        STATUS current
                        DESCRIPTION 
                                "setOnuMacFilter"
                        ::= { fkGponOnuMacFilterNotification 1 }

                
                -- 1.3.6.1.4.1.10428 9 1.101.23.20.3.2
                fkGponOnuMacFilterDeleted NOTIFICATION-TYPE
                        OBJECTS { fkGponOnuMacFilterControlRequest, fkGponOnuMacFilterControlTimeStamp, fkGponOnuMacFilterControlReqResult, fkGponOnuMacFilterControlOltIndex, fkGponOnuMacFilterControlOnuIndex, 
                                fkGponOnuMacFilterControlSlotType, fkGponOnuMacFilterControlPortIndex, fkGponOnuMacFilterControlMac, fkGponOnuMacFilterControlType }
                        STATUS current
                        DESCRIPTION 
                                "setOnuMacFilter"
                        ::= { fkGponOnuMacFilterNotification 2 }

                
                -- 1.3.6.1.4.1.10428 9 1.101.23.21
                fkGponOnuMcastAccessList OBJECT IDENTIFIER ::= { fkGpon 21 }

                
                -- 1.3.6.1.4.1.10428 9 1.101.23.21.1
                fkGponOnuMcastAccessListTable OBJECT-TYPE
                        SYNTAX SEQUENCE OF FkGponOnuMcastAccessListEntry
                        MAX-ACCESS not-accessible
                        STATUS current
                        DESCRIPTION
                                "Description."
                        ::= { fkGponOnuMcastAccessList 1 }

                
                -- 1.3.6.1.4.1.10428 9 1.101.23.21.1.1
                fkGponOnuMcastAccessListEntry OBJECT-TYPE
                        SYNTAX FkGponOnuMcastAccessListEntry
                        MAX-ACCESS not-accessible
                        STATUS current
                        DESCRIPTION
                                "Description."
                        INDEX { fkGponOltId, fkGponOnuId, fkGponOnuMcastAccessListIndex, fkGponOnuMcastAccessListProfileIndex }
                        ::= { fkGponOnuMcastAccessListTable 1 }

                
                FkGponOnuMcastAccessListEntry ::=
                        SEQUENCE { 
                                fkGponOnuMcastAccessListOltId
                                        Integer32,
                                fkGponOnuMcastAccessListOnuId
                                        Integer32,
                                fkGponOnuMcastAccessListIndex
                                        Integer32,
                                fkGponOnuMcastAccessListName
                                        OCTET STRING,
                                fkGponOnuMcastAccessListProfileName
                                        OCTET STRING,
                                fkGponOnuMcastAccessListProfileIndex
                                        Integer32
                         }

--  1.3.6.1.4.1.10428 9 1.101.23.6.1.1.1.1
                -- 1.3.6.1.4.1.10428 9 1.101.23.21.1.1.1
                fkGponOnuMcastAccessListOltId OBJECT-TYPE
                        SYNTAX Integer32
                        MAX-ACCESS read-only
                        STATUS current
                        DESCRIPTION
                                "The OLT index."
                        ::= { fkGponOnuMcastAccessListEntry 1 }

                
                -- 1.3.6.1.4.1.10428 9 1.101.23.21.1.1.2
                fkGponOnuMcastAccessListOnuId OBJECT-TYPE
                        SYNTAX Integer32 (1..65523)
                        MAX-ACCESS read-only
                        STATUS current
                        DESCRIPTION
                                "The ONU index."
                        ::= { fkGponOnuMcastAccessListEntry 2 }

                
                -- 1.3.6.1.4.1.10428 9 1.101.23.21.1.1.3
                fkGponOnuMcastAccessListIndex OBJECT-TYPE
                        SYNTAX Integer32 (0..65535)
                        MAX-ACCESS read-write
                        STATUS current
                        DESCRIPTION
                                "The Multicast ACL index."
                        ::= { fkGponOnuMcastAccessListEntry 3 }

                
                -- 1.3.6.1.4.1.10428 9 1.101.23.21.1.1.4
                fkGponOnuMcastAccessListName OBJECT-TYPE
                        SYNTAX OCTET STRING
                        MAX-ACCESS read-only
                        STATUS current
                        DESCRIPTION
                                "The Mcast ACL name."
                        ::= { fkGponOnuMcastAccessListEntry 4 }

                
                -- 1.3.6.1.4.1.10428 9 1.101.23.21.1.1.5
                fkGponOnuMcastAccessListProfileName OBJECT-TYPE
                        SYNTAX OCTET STRING
                        MAX-ACCESS read-only
                        STATUS current
                        DESCRIPTION
                                "The multicast-profile NAME"
                        ::= { fkGponOnuMcastAccessListEntry 5 }

                
                -- 1.3.6.1.4.1.10428 9 1.101.23.21.1.1.6
                fkGponOnuMcastAccessListProfileIndex OBJECT-TYPE
                        SYNTAX Integer32 (0..65535)
                        MAX-ACCESS read-only
                        STATUS current
                        DESCRIPTION
                                "Description."
                        ::= { fkGponOnuMcastAccessListEntry 6 }

                
                -- 1.3.6.1.4.1.10428 9 1.101.23.21.2
                fkGponOnuMcastAccessListControl OBJECT IDENTIFIER ::= { fkGponOnuMcastAccessList 2 }

                
                -- 1.3.6.1.4.1.10428 9 1.101.23.21.2.1
                fkGponOnuMcastAccessListControlRequest OBJECT-TYPE
                        SYNTAX INTEGER
                                {
                                addMcastACL(1),
                                delMcastACL(2),
                                delMcastACLOnu(3),
                                delMcastACLOlt(4)
                                }
                        MAX-ACCESS read-write
                        STATUS current
                        DESCRIPTION
                                "The request of a user command"
                        ::= { fkGponOnuMcastAccessListControl 1 }

                
                -- 1.3.6.1.4.1.10428 9 1.101.23.21.2.2
                fkGponOnuMcastAccessListControlStatus OBJECT-TYPE
                        SYNTAX FkControlStatusType
                        MAX-ACCESS read-only
                        STATUS current
                        DESCRIPTION
                                "The status of user command"
                        ::= { fkGponOnuMcastAccessListControl 2 }

                
                -- 1.3.6.1.4.1.10428 9 1.101.23.21.2.3
                fkGponOnuMcastAccessListControlTimer OBJECT-TYPE
                        SYNTAX Gauge32
                        MAX-ACCESS read-write
                        STATUS current
                        DESCRIPTION
                                "The maximum time for the manager for a long running user command"
                        ::= { fkGponOnuMcastAccessListControl 3 }

                
                -- 1.3.6.1.4.1.10428 9 1.101.23.21.2.4
                fkGponOnuMcastAccessListControlTimeStamp OBJECT-TYPE
                        SYNTAX TimeTicks
                        MAX-ACCESS read-only
                        STATUS current
                        DESCRIPTION
                                "The time stamp of the last command(end of command)"
                        ::= { fkGponOnuMcastAccessListControl 4 }

                
                -- 1.3.6.1.4.1.10428 9 1.101.23.21.2.5
                fkGponOnuMcastAccessListControlReqResult OBJECT-TYPE
                        SYNTAX FkControlRequestResultType
                        MAX-ACCESS read-only
                        STATUS current
                        DESCRIPTION
                                "The result of the last user command"
                        ::= { fkGponOnuMcastAccessListControl 5 }

                
                -- 1.3.6.1.4.1.10428 9 1.101.23.21.2.6
                fkGponOnuMcastAccessListControlOltIndex OBJECT-TYPE
                        SYNTAX Integer32
                        MAX-ACCESS read-write
                        STATUS current
                        DESCRIPTION
                                "The OLT index."
                        ::= { fkGponOnuMcastAccessListControl 6 }

                
                -- 1.3.6.1.4.1.10428 9 1.101.23.21.2.7
                fkGponOnuMcastAccessListControlOnuIndex OBJECT-TYPE
                        SYNTAX Integer32
                        MAX-ACCESS read-write
                        STATUS current
                        DESCRIPTION
                                "The ONU index."
                        ::= { fkGponOnuMcastAccessListControl 7 }

                
                -- 1.3.6.1.4.1.10428 9 1.101.23.21.2.8
                fkGponOnuMcastAccessListControlName OBJECT-TYPE
                        SYNTAX OCTET STRING
                        MAX-ACCESS read-write
                        STATUS current
                        DESCRIPTION
                                "The Mcast ACL name."
                        ::= { fkGponOnuMcastAccessListControl 8 }

                
                -- 1.3.6.1.4.1.10428 9 1.101.23.21.2.9
                fkGponOnuMcastAccessListControlProfileName OBJECT-TYPE
                        SYNTAX OCTET STRING
                        MAX-ACCESS read-write
                        STATUS current
                        DESCRIPTION
                                "The multicast-profile NAME"
                        ::= { fkGponOnuMcastAccessListControl 9 }

                
                -- 1.3.6.1.4.1.10428 9 1.101.23.21.3
                fkGponOnuMcastAccessListNotification OBJECT IDENTIFIER ::= { fkGponOnuMcastAccessList 3 }

                
                -- 1.3.6.1.4.1.10428 9 1.101.23.21.3.1
                fkGponOnuMcastAccessListAdded NOTIFICATION-TYPE
                        OBJECTS { fkGponOnuMcastAccessListControlRequest, fkGponOnuMcastAccessListControlTimeStamp, fkGponOnuMcastAccessListControlReqResult, fkGponOnuMcastAccessListControlOltIndex, fkGponOnuMcastAccessListControlOnuIndex, 
                                fkGponOnuMcastAccessListControlName }
                        STATUS current
                        DESCRIPTION 
                                "addMcastACL"
                        ::= { fkGponOnuMcastAccessListNotification 1 }

                
                -- 1.3.6.1.4.1.10428 9 1.101.23.21.3.2
                fkGponOnuMcastAccessListDeleted NOTIFICATION-TYPE
                        OBJECTS { fkGponOnuMcastAccessListControlRequest, fkGponOnuMcastAccessListControlTimeStamp, fkGponOnuMcastAccessListControlReqResult, fkGponOnuMcastAccessListControlOltIndex, fkGponOnuMcastAccessListControlOnuIndex, 
                                fkGponOnuMcastAccessListControlName }
                        STATUS current
                        DESCRIPTION 
                                "delMcastACL"
                        ::= { fkGponOnuMcastAccessListNotification 2 }

                
                -- 1.3.6.1.4.1.10428 9 1.101.23.21.3.3
                fkGponOnuMcastAccessListOnuDeleted NOTIFICATION-TYPE
                        OBJECTS { fkGponOnuMcastAccessListControlRequest, fkGponOnuMcastAccessListControlTimeStamp, fkGponOnuMcastAccessListControlReqResult, fkGponOnuMcastAccessListControlOltIndex, fkGponOnuMcastAccessListControlOnuIndex
                                 }
                        STATUS current
                        DESCRIPTION 
                                "addMcastACL"
                        ::= { fkGponOnuMcastAccessListNotification 3 }

                
                -- 1.3.6.1.4.1.10428 9 1.101.23.21.3.4
                fkGponOnuMcastAccessListOltDeleted NOTIFICATION-TYPE
                        OBJECTS { fkGponOnuMcastAccessListControlRequest, fkGponOnuMcastAccessListControlTimeStamp, fkGponOnuMcastAccessListControlReqResult, fkGponOnuMcastAccessListControlOltIndex }
                        STATUS current
                        DESCRIPTION 
                                "addMcastACL"
                        ::= { fkGponOnuMcastAccessListNotification 4 }

                
--  1.3.6.1.4.1.10428 9 1.101.23.51
                -- 1.3.6.1.4.1.10428 9 1.101.23.51
                fkGponProfile2 OBJECT IDENTIFIER ::= { fkGpon 51 }

                
--  1.3.6.1.4.1.10428 9 1.101.23.51.1
                -- 1.3.6.1.4.1.10428 9 1.101.23.51.1
                fkGponProfile2Dba OBJECT IDENTIFIER ::= { fkGponProfile2 1 }

                
--  1.3.6.1.4.1.10428 9 1.101.23.51.1.1
                -- 1.3.6.1.4.1.10428 9 1.101.23.51.1.1
                fkGponProfile2DbaTable OBJECT-TYPE
                        SYNTAX SEQUENCE OF FkGponProfile2DbaEntry
                        MAX-ACCESS not-accessible
                        STATUS current
                        DESCRIPTION
                                "fkGponProfile2DbaTable"
                        ::= { fkGponProfile2Dba 1 }

                
--  1.3.6.1.4.1.10428 9 1.101.23.51.1.1.1
                -- 1.3.6.1.4.1.10428 9 1.101.23.51.1.1.1
                fkGponProfile2DbaEntry OBJECT-TYPE
                        SYNTAX FkGponProfile2DbaEntry
                        MAX-ACCESS not-accessible
                        STATUS current
                        DESCRIPTION
                                "key: fkGponProfile2DbaIndex"
                        INDEX { fkGponProfile2DbaIndex }
                        ::= { fkGponProfile2DbaTable 1 }

                
                FkGponProfile2DbaEntry ::=
                        SEQUENCE { 
                                fkGponProfile2DbaIndex
                                        Integer32,
                                fkGponProfile2DbaName
                                        OCTET STRING,
                                fkGponProfile2DbaMode
                                        INTEGER,
                                fkGponProfile2DbaSlaAssured
                                        Integer32,
                                fkGponProfile2DbaSlaFixed
                                        Integer32,
                                fkGponProfile2DbaSlaMax
                                        Integer32,
                                fkGponProfile2DbaSlaMaxFlags
                                        INTEGER
                         }

--  1.3.6.1.4.1.10428 9 1.101.23.51.1.1.1.1
                -- 1.3.6.1.4.1.10428 9 1.101.23.51.1.1.1.1
                fkGponProfile2DbaIndex OBJECT-TYPE
                        SYNTAX Integer32 (1..65535)
                        MAX-ACCESS read-only
                        STATUS current
                        DESCRIPTION
                                "The DBA profile index."
                        ::= { fkGponProfile2DbaEntry 1 }

                
--  1.3.6.1.4.1.10428 9 1.101.23.51.1.1.1.2
                -- 1.3.6.1.4.1.10428 9 1.101.23.51.1.1.1.2
                fkGponProfile2DbaName OBJECT-TYPE
                        SYNTAX OCTET STRING
                        MAX-ACCESS read-only
                        STATUS current
                        DESCRIPTION
                                "The DBA profile name."
                        ::= { fkGponProfile2DbaEntry 2 }

                
--  1.3.6.1.4.1.10428 9 1.101.23.51.1.1.1.3
                -- 1.3.6.1.4.1.10428 9 1.101.23.51.1.1.1.3
                fkGponProfile2DbaMode OBJECT-TYPE
                        SYNTAX INTEGER
                                {
                                sr(1),
                                nsr(2),
                                fixedUbr(3),
                                fixedCbr(4)
                                }
                        MAX-ACCESS read-only
                        STATUS current
                        DESCRIPTION
                                "The SLA mode."
                        ::= { fkGponProfile2DbaEntry 3 }

                
--  1.3.6.1.4.1.10428 9 1.101.23.51.1.1.1.4
                -- 1.3.6.1.4.1.10428 9 1.101.23.51.1.1.1.4
                fkGponProfile2DbaSlaAssured OBJECT-TYPE
                        SYNTAX Integer32
                        MAX-ACCESS read-only
                        STATUS current
                        DESCRIPTION
                                "The SLA Assured bandwidth"
                        ::= { fkGponProfile2DbaEntry 4 }

                
--  1.3.6.1.4.1.10428 9 1.101.23.51.1.1.1.5
                -- 1.3.6.1.4.1.10428 9 1.101.23.51.1.1.1.5
                fkGponProfile2DbaSlaFixed OBJECT-TYPE
                        SYNTAX Integer32
                        MAX-ACCESS read-only
                        STATUS current
                        DESCRIPTION
                                "The SLA fixed bandwidth"
                        ::= { fkGponProfile2DbaEntry 5 }

                
--  1.3.6.1.4.1.10428 9 1.101.23.51.1.1.1.6
                -- 1.3.6.1.4.1.10428 9 1.101.23.51.1.1.1.6
                fkGponProfile2DbaSlaMax OBJECT-TYPE
                        SYNTAX Integer32
                        MAX-ACCESS read-only
                        STATUS current
                        DESCRIPTION
                                "The SLA maximum bandwidth"
                        ::= { fkGponProfile2DbaEntry 6 }

                
--  1.3.6.1.4.1.10428 9 1.101.23.51.1.1.1.7
                -- 1.3.6.1.4.1.10428 9 1.101.23.51.1.1.1.7
                fkGponProfile2DbaSlaMaxFlags OBJECT-TYPE
                        SYNTAX INTEGER
                                {
                                nonAssured(1),
                                bestEffort(2),
                                unknown(255)
                                }
                        MAX-ACCESS read-write
                        STATUS current
                        DESCRIPTION
                                "The SLA maximum Flags"
                        ::= { fkGponProfile2DbaEntry 7 }

                
--  1.3.6.1.4.1.10428 9 1.101.23.51.1.2
                -- 1.3.6.1.4.1.10428 9 1.101.23.51.1.2
                fkGponProfile2DbaControl OBJECT IDENTIFIER ::= { fkGponProfile2Dba 2 }

                
--  1.3.6.1.4.1.10428 9 1.101.23.51.1.2.1
                -- 1.3.6.1.4.1.10428 9 1.101.23.51.1.2.1
                fkGponProfile2DbaControlRequest OBJECT-TYPE
                        SYNTAX INTEGER
                                {
                                addDbaProfile(1),
                                delDbaProfile(2),
                                setDbaSla(3)
                                }
                        MAX-ACCESS read-write
                        STATUS current
                        DESCRIPTION
                                "The request of a user command"
                        ::= { fkGponProfile2DbaControl 1 }

                
--  1.3.6.1.4.1.10428 9 1.101.23.51.1.2.2
                -- 1.3.6.1.4.1.10428 9 1.101.23.51.1.2.2
                fkGponProfile2DbaControlStatus OBJECT-TYPE
                        SYNTAX FkControlStatusType
                        MAX-ACCESS read-write
                        STATUS current
                        DESCRIPTION
                                "The status of user command"
                        ::= { fkGponProfile2DbaControl 2 }

                
--  1.3.6.1.4.1.10428 9 1.101.23.51.1.2.3
                -- 1.3.6.1.4.1.10428 9 1.101.23.51.1.2.3
                fkGponProfile2DbaControlTimer OBJECT-TYPE
                        SYNTAX Gauge32
                        MAX-ACCESS read-write
                        STATUS current
                        DESCRIPTION
                                "The maximum time for the manager for a long running user command"
                        ::= { fkGponProfile2DbaControl 3 }

                
--  1.3.6.1.4.1.10428 9 1.101.23.51.1.2.4
                -- 1.3.6.1.4.1.10428 9 1.101.23.51.1.2.4
                fkGponProfile2DbaControlTimeStamp OBJECT-TYPE
                        SYNTAX TimeTicks
                        MAX-ACCESS read-write
                        STATUS current
                        DESCRIPTION
                                "The time stamp of the last command(end of command)"
                        ::= { fkGponProfile2DbaControl 4 }

                
--  1.3.6.1.4.1.10428 9 1.101.23.51.1.2.5
                -- 1.3.6.1.4.1.10428 9 1.101.23.51.1.2.5
                fkGponProfile2DbaControlReqResult OBJECT-TYPE
                        SYNTAX FkControlRequestResultType
                        MAX-ACCESS read-write
                        STATUS current
                        DESCRIPTION
                                "The result of the last user command
                                "
                        ::= { fkGponProfile2DbaControl 5 }

                
--  1.3.6.1.4.1.10428 9 1.101.23.51.1.2.6
                -- 1.3.6.1.4.1.10428 9 1.101.23.51.1.2.6
                fkGponProfile2DbaControlName OBJECT-TYPE
                        SYNTAX OCTET STRING
                        MAX-ACCESS read-write
                        STATUS current
                        DESCRIPTION
                                "The DBA profile name."
                        ::= { fkGponProfile2DbaControl 6 }

                
--  1.3.6.1.4.1.10428 9 1.101.23.51.1.2.7
                -- 1.3.6.1.4.1.10428 9 1.101.23.51.1.2.7
                fkGponProfile2DbaControlMode OBJECT-TYPE
                        SYNTAX INTEGER
                                {
                                sr(1),
                                nsr(2),
                                fixedUbr(3),
                                fixedCbr(4)
                                }
                        MAX-ACCESS read-write
                        STATUS current
                        DESCRIPTION
                                "The SLA mode."
                        ::= { fkGponProfile2DbaControl 7 }

                
--  1.3.6.1.4.1.10428 9 1.101.23.51.1.2.8
                -- 1.3.6.1.4.1.10428 9 1.101.23.51.1.2.8
                fkGponProfile2DbaControlSlaAssured OBJECT-TYPE
                        SYNTAX Integer32
                        MAX-ACCESS read-write
                        STATUS current
                        DESCRIPTION
                                "The SLA Assured bandwidth"
                        ::= { fkGponProfile2DbaControl 8 }

                
--  1.3.6.1.4.1.10428 9 1.101.23.51.1.2.9
                -- 1.3.6.1.4.1.10428 9 1.101.23.51.1.2.9
                fkGponProfile2DbaControlSlaFixed OBJECT-TYPE
                        SYNTAX Integer32
                        MAX-ACCESS read-write
                        STATUS current
                        DESCRIPTION
                                "The SLA fixed bandwidth"
                        ::= { fkGponProfile2DbaControl 9 }

                
--  1.3.6.1.4.1.10428 9 1.101.23.51.1.2.10
                -- 1.3.6.1.4.1.10428 9 1.101.23.51.1.2.10
                fkGponProfile2DbaControlSlaMax OBJECT-TYPE
                        SYNTAX Integer32
                        MAX-ACCESS read-write
                        STATUS current
                        DESCRIPTION
                                "The SLA maximum bandwidth"
                        ::= { fkGponProfile2DbaControl 10 }

                
--  1.3.6.1.4.1.10428 9 1.101.23.51.1.2.11
                -- 1.3.6.1.4.1.10428 9 1.101.23.51.1.2.11
                fkGponProfile2DbaControlSlaMaxFlags OBJECT-TYPE
                        SYNTAX INTEGER
                                {
                                nonAssured(1),
                                bestEffort(2),
                                unknown(255)
                                }
                        MAX-ACCESS read-write
                        STATUS current
                        DESCRIPTION
                                "The SLA maximum Flags"
                        ::= { fkGponProfile2DbaControl 11 }

                
--  1.3.6.1.4.1.10428 9 1.101.23.51.1.3
                -- 1.3.6.1.4.1.10428 9 1.101.23.51.1.3
                fkGponProfile2DbaNotification OBJECT IDENTIFIER ::= { fkGponProfile2Dba 3 }

                
--  1.3.6.1.4.1.10428 9 1.101.23.51.1.3.1
                -- 1.3.6.1.4.1.10428 9 1.101.23.51.1.3.1
                fkGponProfile2DbaAdded NOTIFICATION-TYPE
                        OBJECTS { fkGponProfile2DbaControlRequest, fkGponProfile2DbaControlTimeStamp, fkGponProfile2DbaControlReqResult, fkGponProfile2DbaControlName, fkGponProfile2DbaControlMode, 
                                fkGponProfile2DbaControlSlaAssured, fkGponProfile2DbaControlSlaFixed, fkGponProfile2DbaControlSlaMax, fkGponProfile2DbaControlSlaMaxFlags }
                        STATUS current
                        DESCRIPTION 
                                "Description."
                        ::= { fkGponProfile2DbaNotification 1 }

                
--  1.3.6.1.4.1.10428 9 1.101.23.51.1.3.2
                -- 1.3.6.1.4.1.10428 9 1.101.23.51.1.3.2
                fkGponProfile2DbaDeleted NOTIFICATION-TYPE
                        OBJECTS { fkGponProfile2DbaControlRequest, fkGponProfile2DbaControlTimeStamp, fkGponProfile2DbaControlReqResult, fkGponProfile2DbaControlName }
                        STATUS current
                        DESCRIPTION 
                                "Description."
                        ::= { fkGponProfile2DbaNotification 2 }

                
--  1.3.6.1.4.1.10428 9 1.101.23.51.1.3.3
                -- 1.3.6.1.4.1.10428 9 1.101.23.51.1.3.3
                fkGponProfile2DbaSlaChanged NOTIFICATION-TYPE
                        OBJECTS { fkGponProfile2DbaControlRequest, fkGponProfile2DbaControlTimeStamp, fkGponProfile2DbaControlReqResult, fkGponProfile2DbaControlName, fkGponProfile2DbaControlMode, 
                                fkGponProfile2DbaControlSlaAssured, fkGponProfile2DbaControlSlaFixed, fkGponProfile2DbaControlSlaMax, fkGponProfile2DbaControlSlaMaxFlags }
                        STATUS current
                        DESCRIPTION 
                                "Description."
                        ::= { fkGponProfile2DbaNotification 3 }

                
--  1.3.6.1.4.1.10428 9 1.101.23.51.2
                -- 1.3.6.1.4.1.10428 9 1.101.23.51.2
                fkGponProfile2Traffic OBJECT IDENTIFIER ::= { fkGponProfile2 2 }

                
--  1.3.6.1.4.1.10428 9 1.101.23.51.2.1
                -- 1.3.6.1.4.1.10428 9 1.101.23.51.2.1
                fkGponProfile2TrafficTable OBJECT-TYPE
                        SYNTAX SEQUENCE OF FkGponProfile2TrafficEntry
                        MAX-ACCESS not-accessible
                        STATUS current
                        DESCRIPTION
                                "fkGponProfile2TrafficTable"
                        ::= { fkGponProfile2Traffic 1 }
-- fkGponProfile2TrafficTable
                
--  1.3.6.1.4.1.10428 9 1.101.23.51.2.1.1
                -- 1.3.6.1.4.1.10428 9 1.101.23.51.2.1.1
                fkGponProfile2TrafficEntry OBJECT-TYPE
                        SYNTAX FkGponProfile2TrafficEntry
                        MAX-ACCESS not-accessible
                        STATUS current
                        DESCRIPTION
                                "key: fkGponProfile2TrafficIndex"
                        INDEX { fkGponProfile2TrafficIndex }
                        ::= { fkGponProfile2TrafficTable 1 }
-- key: fkGponProfile2TrafficIndex
                
                FkGponProfile2TrafficEntry ::=
                        SEQUENCE { 
                                fkGponProfile2TrafficIndex
                                        Integer32,
                                fkGponProfile2TrafficName
                                        OCTET STRING
                         }

--  1.3.6.1.4.1.10428 9 1.101.23.51.2.1.1.1
                -- 1.3.6.1.4.1.10428 9 1.101.23.51.2.1.1.1
                fkGponProfile2TrafficIndex OBJECT-TYPE
                        SYNTAX Integer32 (1..65535)
                        MAX-ACCESS read-only
                        STATUS current
                        DESCRIPTION
                                "The traffic profile index"
                        ::= { fkGponProfile2TrafficEntry 1 }

                
--  1.3.6.1.4.1.10428 9 1.101.23.51.2.1.1.2
                -- 1.3.6.1.4.1.10428 9 1.101.23.51.2.1.1.2
                fkGponProfile2TrafficName OBJECT-TYPE
                        SYNTAX OCTET STRING
                        MAX-ACCESS read-only
                        STATUS current
                        DESCRIPTION
                                "The traffic profile name."
                        ::= { fkGponProfile2TrafficEntry 2 }

                
--  1.3.6.1.4.1.10428 9 1.101.23.51.2.2
                -- 1.3.6.1.4.1.10428 9 1.101.23.51.2.2
                fkGponProfile2TrafficControl OBJECT IDENTIFIER ::= { fkGponProfile2Traffic 2 }

                
--  1.3.6.1.4.1.10428 9 1.101.23.51.2.2.1
                -- 1.3.6.1.4.1.10428 9 1.101.23.51.2.2.1
                fkGponProfile2TrafficControlRequest OBJECT-TYPE
                        SYNTAX INTEGER
                                {
                                addTrafficProfile(1),
                                delTrafficProfile(2)
                                }
                        MAX-ACCESS read-write
                        STATUS current
                        DESCRIPTION
                                "The request of a user command"
                        ::= { fkGponProfile2TrafficControl 1 }

                
--  1.3.6.1.4.1.10428 9 1.101.23.51.2.2.2
                -- 1.3.6.1.4.1.10428 9 1.101.23.51.2.2.2
                fkGponProfile2TrafficControlStatus OBJECT-TYPE
                        SYNTAX FkControlStatusType
                        MAX-ACCESS read-write
                        STATUS current
                        DESCRIPTION
                                "The status of user command"
                        ::= { fkGponProfile2TrafficControl 2 }

                
--  1.3.6.1.4.1.10428 9 1.101.23.51.2.2.3
                -- 1.3.6.1.4.1.10428 9 1.101.23.51.2.2.3
                fkGponProfile2TrafficControlTimer OBJECT-TYPE
                        SYNTAX Gauge32
                        MAX-ACCESS read-write
                        STATUS current
                        DESCRIPTION
                                "The maximum time for the manager for a long running user command"
                        ::= { fkGponProfile2TrafficControl 3 }

                
--  1.3.6.1.4.1.10428 9 1.101.23.51.2.2.4
                -- 1.3.6.1.4.1.10428 9 1.101.23.51.2.2.4
                fkGponProfile2TrafficControlTimeStamp OBJECT-TYPE
                        SYNTAX TimeTicks
                        MAX-ACCESS read-write
                        STATUS current
                        DESCRIPTION
                                "The time stamp of the last command(end of command)"
                        ::= { fkGponProfile2TrafficControl 4 }

                
--  1.3.6.1.4.1.10428 9 1.101.23.51.2.2.5
                -- 1.3.6.1.4.1.10428 9 1.101.23.51.2.2.5
                fkGponProfile2TrafficControlReqResult OBJECT-TYPE
                        SYNTAX FkControlRequestResultType
                        MAX-ACCESS read-write
                        STATUS current
                        DESCRIPTION
                                "The result of the last user command"
                        ::= { fkGponProfile2TrafficControl 5 }

                
--  1.3.6.1.4.1.10428 9 1.101.23.51.2.2.6
                -- 1.3.6.1.4.1.10428 9 1.101.23.51.2.2.6
                fkGponProfile2TrafficControlName OBJECT-TYPE
                        SYNTAX OCTET STRING
                        MAX-ACCESS read-write
                        STATUS current
                        DESCRIPTION
                                "The Traffic profile name."
                        ::= { fkGponProfile2TrafficControl 6 }

                
--  1.3.6.1.4.1.10428 9 1.101.23.51.2.3
                -- 1.3.6.1.4.1.10428 9 1.101.23.51.2.3
                fkGponProfile2TrafficNotification OBJECT IDENTIFIER ::= { fkGponProfile2Traffic 3 }

                
--  1.3.6.1.4.1.10428 9 1.101.23.51.2.3.1
                -- 1.3.6.1.4.1.10428 9 1.101.23.51.2.3.1
                fkGponProfile2TrafficAdded NOTIFICATION-TYPE
                        OBJECTS { fkGponProfile2TrafficControlRequest, fkGponProfile2TrafficControlStatus, fkGponProfile2TrafficControlTimer, fkGponProfile2TrafficControlTimeStamp, fkGponProfile2TrafficControlReqResult, 
                                fkGponProfile2TrafficControlName }
                        STATUS current
                        DESCRIPTION 
                                "Description."
                        ::= { fkGponProfile2TrafficNotification 1 }

                
--  1.3.6.1.4.1.10428 9 1.101.23.51.2.3.2
                -- 1.3.6.1.4.1.10428 9 1.101.23.51.2.3.2
                fkGponProfile2TrafficDeleted NOTIFICATION-TYPE
                        OBJECTS { fkGponProfile2TrafficControlRequest, fkGponProfile2TrafficControlStatus, fkGponProfile2TrafficControlTimer, fkGponProfile2TrafficControlTimeStamp, fkGponProfile2TrafficControlReqResult, 
                                fkGponProfile2TrafficControlName }
                        STATUS current
                        DESCRIPTION 
                                "Description."
                        ::= { fkGponProfile2TrafficNotification 2 }

                
--  1.3.6.1.4.1.10428 9 1.101.23.51.3
                -- 1.3.6.1.4.1.10428 9 1.101.23.51.3
                fkGponProfile2Mapper OBJECT IDENTIFIER ::= { fkGponProfile2 3 }

                
--  1.3.6.1.4.1.10428 9 1.101.23.51.3.1
                -- 1.3.6.1.4.1.10428 9 1.101.23.51.3.1
                fkGponProfile2MapperTable OBJECT-TYPE
                        SYNTAX SEQUENCE OF FkGponProfile2MapperEntry
                        MAX-ACCESS not-accessible
                        STATUS current
                        DESCRIPTION
                                "fkGponProfile2MapperTable"
                        ::= { fkGponProfile2Mapper 1 }

                
--  1.3.6.1.4.1.10428 9 1.101.23.51.3.1.1
                -- 1.3.6.1.4.1.10428 9 1.101.23.51.3.1.1
                fkGponProfile2MapperEntry OBJECT-TYPE
                        SYNTAX FkGponProfile2MapperEntry
                        MAX-ACCESS not-accessible
                        STATUS current
                        DESCRIPTION
                                "key: fkGponProfile2TrafficIndex, fkGponProfile2MapperId"
                        INDEX { fkGponProfile2TrafficIndex, fkGponProfile2MapperId }
                        ::= { fkGponProfile2MapperTable 1 }

                
                FkGponProfile2MapperEntry ::=
                        SEQUENCE { 
                                fkGponProfile2MapperId
                                        Integer32,
                                fkGponProfile2MapperGemportCount
                                        Integer32,
                                fkGponProfile2MapperDefaultCoS
                                        Integer32,
                                fkGponProfile2MapperDscp2Pbit
                                        EnableFlag,
                                fkGponProfile2MapperCos0
                                        Integer32,
                                fkGponProfile2MapperCos1
                                        Integer32,
                                fkGponProfile2MapperCos2
                                        Integer32,
                                fkGponProfile2MapperCos3
                                        Integer32,
                                fkGponProfile2MapperCos4
                                        Integer32,
                                fkGponProfile2MapperCos5
                                        Integer32,
                                fkGponProfile2MapperCos6
                                        Integer32,
                                fkGponProfile2MapperCos7
                                        Integer32,
                                fkGponProfile2MapperActiveEth
                                        INTEGER
                         }

--  1.3.6.1.4.1.10428 9 1.101.23.51.3.1.1.1
                -- 1.3.6.1.4.1.10428 9 1.101.23.51.3.1.1.1
                fkGponProfile2MapperId OBJECT-TYPE
                        SYNTAX Integer32 (1..65535)
                        MAX-ACCESS read-only
                        STATUS current
                        DESCRIPTION
                                "The mapper ID."
                        ::= { fkGponProfile2MapperEntry 1 }

                
--  1.3.6.1.4.1.10428 9 1.101.23.51.3.1.1.2
                -- 1.3.6.1.4.1.10428 9 1.101.23.51.3.1.1.2
                fkGponProfile2MapperGemportCount OBJECT-TYPE
                        SYNTAX Integer32
                        MAX-ACCESS read-only
                        STATUS current
                        DESCRIPTION
                                "The mapper gemport count (1|2|4|8)"
                        ::= { fkGponProfile2MapperEntry 2 }

                
--  1.3.6.1.4.1.10428 9 1.101.23.51.3.1.1.3
                -- 1.3.6.1.4.1.10428 9 1.101.23.51.3.1.1.3
                fkGponProfile2MapperDefaultCoS OBJECT-TYPE
                        SYNTAX Integer32
                        MAX-ACCESS read-only
                        STATUS current
                        DESCRIPTION
                                "The mapper default CoS."
                        ::= { fkGponProfile2MapperEntry 3 }

                
--  1.3.6.1.4.1.10428 9 1.101.23.51.3.1.1.4
                -- 1.3.6.1.4.1.10428 9 1.101.23.51.3.1.1.4
                fkGponProfile2MapperDscp2Pbit OBJECT-TYPE
                        SYNTAX EnableFlag
                        MAX-ACCESS read-only
                        STATUS current
                        DESCRIPTION
                                "The DSCP to P bit marking"
                        ::= { fkGponProfile2MapperEntry 4 }

                
--  1.3.6.1.4.1.10428 9 1.101.23.51.3.1.1.5
                -- 1.3.6.1.4.1.10428 9 1.101.23.51.3.1.1.5
                fkGponProfile2MapperCos0 OBJECT-TYPE
                        SYNTAX Integer32
                        MAX-ACCESS read-only
                        STATUS current
                        DESCRIPTION
                                "COS to GEM port mapping configuration (Cos0)"
                        ::= { fkGponProfile2MapperEntry 5 }

                
--  1.3.6.1.4.1.10428 9 1.101.23.51.3.1.1.6
                -- 1.3.6.1.4.1.10428 9 1.101.23.51.3.1.1.6
                fkGponProfile2MapperCos1 OBJECT-TYPE
                        SYNTAX Integer32
                        MAX-ACCESS read-only
                        STATUS current
                        DESCRIPTION
                                "COS to GEM port mapping configuration (Cos1)"
                        ::= { fkGponProfile2MapperEntry 6 }

                
--  1.3.6.1.4.1.10428 9 1.101.23.51.3.1.1.7
                -- 1.3.6.1.4.1.10428 9 1.101.23.51.3.1.1.7
                fkGponProfile2MapperCos2 OBJECT-TYPE
                        SYNTAX Integer32
                        MAX-ACCESS read-only
                        STATUS current
                        DESCRIPTION
                                "COS to GEM port mapping configuration (Cos2)"
                        ::= { fkGponProfile2MapperEntry 7 }

                
--  1.3.6.1.4.1.10428 9 1.101.23.51.3.1.1.8
                -- 1.3.6.1.4.1.10428 9 1.101.23.51.3.1.1.8
                fkGponProfile2MapperCos3 OBJECT-TYPE
                        SYNTAX Integer32
                        MAX-ACCESS read-only
                        STATUS current
                        DESCRIPTION
                                "COS to GEM port mapping configuration (Cos3)"
                        ::= { fkGponProfile2MapperEntry 8 }

                
--  1.3.6.1.4.1.10428 9 1.101.23.51.3.1.1.9
                -- 1.3.6.1.4.1.10428 9 1.101.23.51.3.1.1.9
                fkGponProfile2MapperCos4 OBJECT-TYPE
                        SYNTAX Integer32
                        MAX-ACCESS read-only
                        STATUS current
                        DESCRIPTION
                                "COS to GEM port mapping configuration (Cos4)"
                        ::= { fkGponProfile2MapperEntry 9 }

                
--  1.3.6.1.4.1.10428 9 1.101.23.51.3.1.1.10
                -- 1.3.6.1.4.1.10428 9 1.101.23.51.3.1.1.10
                fkGponProfile2MapperCos5 OBJECT-TYPE
                        SYNTAX Integer32
                        MAX-ACCESS read-only
                        STATUS current
                        DESCRIPTION
                                "COS to GEM port mapping configuration (Cos5)"
                        ::= { fkGponProfile2MapperEntry 10 }

                
--  1.3.6.1.4.1.10428 9 1.101.23.51.3.1.1.11
                -- 1.3.6.1.4.1.10428 9 1.101.23.51.3.1.1.11
                fkGponProfile2MapperCos6 OBJECT-TYPE
                        SYNTAX Integer32
                        MAX-ACCESS read-only
                        STATUS current
                        DESCRIPTION
                                "COS to GEM port mapping configuration (Cos6)"
                        ::= { fkGponProfile2MapperEntry 11 }

                
--  1.3.6.1.4.1.10428 9 1.101.23.51.3.1.1.12
                -- 1.3.6.1.4.1.10428 9 1.101.23.51.3.1.1.12
                fkGponProfile2MapperCos7 OBJECT-TYPE
                        SYNTAX Integer32
                        MAX-ACCESS read-only
                        STATUS current
                        DESCRIPTION
                                "COS to GEM port mapping configuration (Cos7)"
                        ::= { fkGponProfile2MapperEntry 12 }

                
                -- 1.3.6.1.4.1.10428 9 1.101.23.51.3.1.1.13
                fkGponProfile2MapperActiveEth OBJECT-TYPE
                        SYNTAX INTEGER
                                {
                                normalMapper(0),
                                activeEthMapper(1)
                                }
                        MAX-ACCESS read-only
                        STATUS current
                        DESCRIPTION
                                "The Active Ethernet type."
                        ::= { fkGponProfile2MapperEntry 13 }

                
--  1.3.6.1.4.1.10428 9 1.101.23.51.3.2
                -- 1.3.6.1.4.1.10428 9 1.101.23.51.3.2
                fkGponProfile2MapperControl OBJECT IDENTIFIER ::= { fkGponProfile2Mapper 2 }

                
--  1.3.6.1.4.1.10428 9 1.101.23.51.3.2.1
                -- 1.3.6.1.4.1.10428 9 1.101.23.51.3.2.1
                fkGponProfile2MapperControlRequest OBJECT-TYPE
                        SYNTAX INTEGER
                                {
                                addMapper(1),
                                delMapper(2),
                                setGemportCount(3),
                                setDefaultCos(4),
                                setDscp2Bit(5),
                                setCosGemport(6),
                                addActiveEthMapper(7),
                                delActiveEthMapper(8)
                                }
                        MAX-ACCESS read-write
                        STATUS current
                        DESCRIPTION
                                "The request of a user command"
                        ::= { fkGponProfile2MapperControl 1 }

                
--  1.3.6.1.4.1.10428 9 1.101.23.51.3.2.2
                -- 1.3.6.1.4.1.10428 9 1.101.23.51.3.2.2
                fkGponProfile2MapperControlStatus OBJECT-TYPE
                        SYNTAX FkControlStatusType
                        MAX-ACCESS read-write
                        STATUS current
                        DESCRIPTION
                                "The status of user command"
                        ::= { fkGponProfile2MapperControl 2 }

                
--  1.3.6.1.4.1.10428 9 1.101.23.51.3.2.3
                -- 1.3.6.1.4.1.10428 9 1.101.23.51.3.2.3
                fkGponProfile2MapperControlTimer OBJECT-TYPE
                        SYNTAX Gauge32
                        MAX-ACCESS read-write
                        STATUS current
                        DESCRIPTION
                                "The maximum time for the manager for a long running user command"
                        ::= { fkGponProfile2MapperControl 3 }

                
--  1.3.6.1.4.1.10428 9 1.101.23.51.3.2.4
                -- 1.3.6.1.4.1.10428 9 1.101.23.51.3.2.4
                fkGponProfile2MapperControlTimeStamp OBJECT-TYPE
                        SYNTAX TimeTicks
                        MAX-ACCESS read-write
                        STATUS current
                        DESCRIPTION
                                "The time stamp of the last command(end of command)"
                        ::= { fkGponProfile2MapperControl 4 }

                
--  1.3.6.1.4.1.10428 9 1.101.23.51.3.2.5
                -- 1.3.6.1.4.1.10428 9 1.101.23.51.3.2.5
                fkGponProfile2MapperControlReqResult OBJECT-TYPE
                        SYNTAX FkControlRequestResultType
                        MAX-ACCESS read-write
                        STATUS current
                        DESCRIPTION
                                "The result of the last user command
                                "
                        ::= { fkGponProfile2MapperControl 5 }

                
--  1.3.6.1.4.1.10428 9 1.101.23.51.3.2.6
                -- 1.3.6.1.4.1.10428 9 1.101.23.51.3.2.6
                fkGponProfile2MapperControlTName OBJECT-TYPE
                        SYNTAX OCTET STRING
                        MAX-ACCESS read-write
                        STATUS current
                        DESCRIPTION
                                "The Traffic profile name."
                        ::= { fkGponProfile2MapperControl 6 }

                
--  1.3.6.1.4.1.10428 9 1.101.23.51.3.2.7
                -- 1.3.6.1.4.1.10428 9 1.101.23.51.3.2.7
                fkGponProfile2MapperControlId OBJECT-TYPE
                        SYNTAX Integer32
                        MAX-ACCESS read-write
                        STATUS current
                        DESCRIPTION
                                "The mapper ID."
                        ::= { fkGponProfile2MapperControl 7 }

                
--  1.3.6.1.4.1.10428 9 1.101.23.51.3.2.8
                -- 1.3.6.1.4.1.10428 9 1.101.23.51.3.2.8
                fkGponProfile2MapperControlGemportCount OBJECT-TYPE
                        SYNTAX Integer32
                        MAX-ACCESS read-write
                        STATUS current
                        DESCRIPTION
                                "The mapper gemport count (1|2|4|8)"
                        ::= { fkGponProfile2MapperControl 8 }

                
--  1.3.6.1.4.1.10428 9 1.101.23.51.3.2.9
                -- 1.3.6.1.4.1.10428 9 1.101.23.51.3.2.9
                fkGponProfile2MapperControlDefaultCoS OBJECT-TYPE
                        SYNTAX Integer32
                        MAX-ACCESS read-write
                        STATUS current
                        DESCRIPTION
                                "The mapper default CoS."
                        ::= { fkGponProfile2MapperControl 9 }

                
--  1.3.6.1.4.1.10428 9 1.101.23.51.3.2.10
                -- 1.3.6.1.4.1.10428 9 1.101.23.51.3.2.10
                fkGponProfile2MapperControlDscp2Pbit OBJECT-TYPE
                        SYNTAX EnableFlag
                        MAX-ACCESS read-write
                        STATUS current
                        DESCRIPTION
                                "The DSCP to P bit marking"
                        ::= { fkGponProfile2MapperControl 10 }

                
--  1.3.6.1.4.1.10428 9 1.101.23.51.3.2.11
                -- 1.3.6.1.4.1.10428 9 1.101.23.51.3.2.11
                fkGponProfile2MapperControlCosIndex OBJECT-TYPE
                        SYNTAX INTEGER
                                {
                                cos0(1),
                                cos1(2),
                                cos2(3),
                                cos3(4),
                                cos4(5),
                                cos5(6),
                                cos6(7),
                                cos7(8)
                                }
                        MAX-ACCESS read-write
                        STATUS current
                        DESCRIPTION
                                "The CoS Index."
                        ::= { fkGponProfile2MapperControl 11 }

                
--  1.3.6.1.4.1.10428 9 1.101.23.51.3.2.12
                -- 1.3.6.1.4.1.10428 9 1.101.23.51.3.2.12
                fkGponProfile2MapperControlCosGemport OBJECT-TYPE
                        SYNTAX Integer32
                        MAX-ACCESS read-write
                        STATUS current
                        DESCRIPTION
                                "The gemport number."
                        ::= { fkGponProfile2MapperControl 12 }

                
--  1.3.6.1.4.1.10428 9 1.101.23.51.3.3
                -- 1.3.6.1.4.1.10428 9 1.101.23.51.3.3
                fkGponProfile2MapperNotification OBJECT IDENTIFIER ::= { fkGponProfile2Mapper 3 }

                
--  1.3.6.1.4.1.10428 9 1.101.23.51.3.3.1
                -- 1.3.6.1.4.1.10428 9 1.101.23.51.3.3.1
                fkGponProfile2MapperAdded NOTIFICATION-TYPE
                        OBJECTS { fkGponProfile2MapperControlRequest, fkGponProfile2MapperControlStatus, fkGponProfile2MapperControlTimer, fkGponProfile2MapperControlTimeStamp, fkGponProfile2MapperControlReqResult, 
                                fkGponProfile2MapperControlTName, fkGponProfile2MapperControlId, fkGponProfile2MapperControlGemportCount, fkGponProfile2MapperControlDefaultCoS, fkGponProfile2MapperControlDscp2Pbit
                                 }
                        STATUS current
                        DESCRIPTION 
                                "addMapper"
                        ::= { fkGponProfile2MapperNotification 1 }

                
--  1.3.6.1.4.1.10428 9 1.101.23.51.3.3.2
                -- 1.3.6.1.4.1.10428 9 1.101.23.51.3.3.2
                fkGponProfile2MapperDeleted NOTIFICATION-TYPE
                        OBJECTS { fkGponProfile2MapperControlRequest, fkGponProfile2MapperControlStatus, fkGponProfile2MapperControlTimer, fkGponProfile2MapperControlTimeStamp, fkGponProfile2MapperControlReqResult, 
                                fkGponProfile2MapperControlTName, fkGponProfile2MapperControlId }
                        STATUS current
                        DESCRIPTION 
                                "Description."
                        ::= { fkGponProfile2MapperNotification 2 }

                
--  1.3.6.1.4.1.10428 9 1.101.23.51.3.3.3
                -- 1.3.6.1.4.1.10428 9 1.101.23.51.3.3.3
                fkGponProfile2MapperGemportCountChanged NOTIFICATION-TYPE
                        OBJECTS { fkGponProfile2MapperControlRequest, fkGponProfile2MapperControlStatus, fkGponProfile2MapperControlTimer, fkGponProfile2MapperControlTimeStamp, fkGponProfile2MapperControlReqResult, 
                                fkGponProfile2MapperControlTName, fkGponProfile2MapperControlId, fkGponProfile2MapperControlGemportCount }
                        STATUS current
                        DESCRIPTION 
                                "Description."
                        ::= { fkGponProfile2MapperNotification 3 }

                
--  1.3.6.1.4.1.10428 9 1.101.23.51.3.3.4
                -- 1.3.6.1.4.1.10428 9 1.101.23.51.3.3.4
                fkGponProfile2MapperDefaultCoSChanged NOTIFICATION-TYPE
                        OBJECTS { fkGponProfile2MapperControlRequest, fkGponProfile2MapperControlStatus, fkGponProfile2MapperControlTimer, fkGponProfile2MapperControlTimeStamp, fkGponProfile2MapperControlReqResult, 
                                fkGponProfile2MapperControlTName, fkGponProfile2MapperControlId, fkGponProfile2MapperControlDefaultCoS }
                        STATUS current
                        DESCRIPTION 
                                "Description."
                        ::= { fkGponProfile2MapperNotification 4 }

                
--  1.3.6.1.4.1.10428 9 1.101.23.51.3.3.5
                -- 1.3.6.1.4.1.10428 9 1.101.23.51.3.3.5
                fkGponProfile2MapperDscp2BitChanged NOTIFICATION-TYPE
                        OBJECTS { fkGponProfile2MapperControlRequest, fkGponProfile2MapperControlStatus, fkGponProfile2MapperControlTimer, fkGponProfile2MapperControlTimeStamp, fkGponProfile2MapperControlReqResult, 
                                fkGponProfile2MapperControlTName, fkGponProfile2MapperControlId, fkGponProfile2MapperControlDefaultCoS }
                        STATUS current
                        DESCRIPTION 
                                "Description."
                        ::= { fkGponProfile2MapperNotification 5 }

                
--  1.3.6.1.4.1.10428 9 1.101.23.51.3.3.6
                -- 1.3.6.1.4.1.10428 9 1.101.23.51.3.3.6
                fkGponProfile2MapperCosGemportChanged NOTIFICATION-TYPE
                        OBJECTS { fkGponProfile2MapperControlRequest, fkGponProfile2MapperControlStatus, fkGponProfile2MapperControlTimer, fkGponProfile2MapperControlTimeStamp, fkGponProfile2MapperControlReqResult, 
                                fkGponProfile2MapperControlTName, fkGponProfile2MapperControlId, fkGponProfile2MapperControlCosIndex, fkGponProfile2MapperControlCosGemport }
                        STATUS current
                        DESCRIPTION 
                                "Description."
                        ::= { fkGponProfile2MapperNotification 6 }

                
--  1.3.6.1.4.1.10428 9 1.101.23.51.3.3.1
                -- 1.3.6.1.4.1.10428 9 1.101.23.51.3.3.7
                fkGponProfile2MapperActiveEthCreated NOTIFICATION-TYPE
                        OBJECTS { fkGponProfile2MapperControlRequest, fkGponProfile2MapperControlTimeStamp, fkGponProfile2MapperControlReqResult, fkGponProfile2MapperControlTName, fkGponProfile2MapperControlId, 
                                fkGponProfile2MapperControlGemportCount, fkGponProfile2MapperControlDefaultCoS, fkGponProfile2MapperControlDscp2Pbit }
                        STATUS current
                        DESCRIPTION 
                                "addActiveEthMapper"
                        ::= { fkGponProfile2MapperNotification 7 }

                
--  1.3.6.1.4.1.10428 9 1.101.23.51.3.3.2
                -- 1.3.6.1.4.1.10428 9 1.101.23.51.3.3.8
                fkGponProfile2MapperActiveEthDeleted NOTIFICATION-TYPE
                        OBJECTS { fkGponProfile2MapperControlRequest, fkGponProfile2MapperControlTimeStamp, fkGponProfile2MapperControlReqResult, fkGponProfile2MapperControlTName, fkGponProfile2MapperControlId
                                 }
                        STATUS current
                        DESCRIPTION 
                                "delActiveEthMapper"
                        ::= { fkGponProfile2MapperNotification 8 }

                
--  1.3.6.1.4.1.10428 9 1.101.23.51.4
                -- 1.3.6.1.4.1.10428 9 1.101.23.51.4
                fkGponProfile2Bridge OBJECT IDENTIFIER ::= { fkGponProfile2 4 }

                
--  1.3.6.1.4.1.10428 9 1.101.23.51.4.1
                -- 1.3.6.1.4.1.10428 9 1.101.23.51.4.1
                fkGponProfile2BridgeTable OBJECT-TYPE
                        SYNTAX SEQUENCE OF FkGponProfile2BridgeEntry
                        MAX-ACCESS not-accessible
                        STATUS current
                        DESCRIPTION
                                "fkGponProfile2BridgeTable"
                        ::= { fkGponProfile2Bridge 1 }

                
--  1.3.6.1.4.1.10428 9 1.101.23.51.4.1.1
                -- 1.3.6.1.4.1.10428 9 1.101.23.51.4.1.1
                fkGponProfile2BridgeEntry OBJECT-TYPE
                        SYNTAX FkGponProfile2BridgeEntry
                        MAX-ACCESS not-accessible
                        STATUS current
                        DESCRIPTION
                                "key: fkGponProfile2TrafficIndex, fkGponProfile2BridgeId"
                        INDEX { fkGponProfile2TrafficIndex, fkGponProfile2BridgeId }
                        ::= { fkGponProfile2BridgeTable 1 }

                
                FkGponProfile2BridgeEntry ::=
                        SEQUENCE { 
                                fkGponProfile2BridgeId
                                        Integer32,
                                fkGponProfile2BridgeMacLearning
                                        EnableFlag,
                                fkGponProfile2BridgeMaxHost
                                        Integer32,
                                fkGponProfile2BridgeMcastFlag
                                        EnableFlag,
                                fkGponProfile2BridgePortBridge
                                        EnableFlag
                         }

--  1.3.6.1.4.1.10428 9 1.101.23.51.4.1.1.1
                -- 1.3.6.1.4.1.10428 9 1.101.23.51.4.1.1.1
                fkGponProfile2BridgeId OBJECT-TYPE
                        SYNTAX Integer32 (1..4094)
                        MAX-ACCESS read-only
                        STATUS current
                        DESCRIPTION
                                "The Bridge ID."
                        ::= { fkGponProfile2BridgeEntry 1 }

                
--  1.3.6.1.4.1.10428 9 1.101.23.51.4.1.1.2
                -- 1.3.6.1.4.1.10428 9 1.101.23.51.4.1.1.2
                fkGponProfile2BridgeMacLearning OBJECT-TYPE
                        SYNTAX EnableFlag
                        MAX-ACCESS read-only
                        STATUS current
                        DESCRIPTION
                                "The Bridge mac learning."
                        ::= { fkGponProfile2BridgeEntry 2 }

                
--  1.3.6.1.4.1.10428 9 1.101.23.51.4.1.1.3
                -- 1.3.6.1.4.1.10428 9 1.101.23.51.4.1.1.3
                fkGponProfile2BridgeMaxHost OBJECT-TYPE
                        SYNTAX Integer32 (0..255)
                        MAX-ACCESS read-only
                        STATUS current
                        DESCRIPTION
                                "The Bridge max host."
                        ::= { fkGponProfile2BridgeEntry 3 }

                
--  1.3.6.1.4.1.10428 9 1.101.23.51.4.1.1.4
                -- 1.3.6.1.4.1.10428 9 1.101.23.51.4.1.1.4
                fkGponProfile2BridgeMcastFlag OBJECT-TYPE
                        SYNTAX EnableFlag
                        MAX-ACCESS read-only
                        STATUS current
                        DESCRIPTION
                                "The Mcast supporting."
                        ::= { fkGponProfile2BridgeEntry 4 }

                
                -- 1.3.6.1.4.1.10428 9 1.101.23.51.4.1.1.5
                fkGponProfile2BridgePortBridge OBJECT-TYPE
                        SYNTAX EnableFlag
                        MAX-ACCESS read-only
                        STATUS current
                        DESCRIPTION
                                "The Port bridge."
                        ::= { fkGponProfile2BridgeEntry 5 }

                
--  1.3.6.1.4.1.10428 9 1.101.23.51.4.2
                -- 1.3.6.1.4.1.10428 9 1.101.23.51.4.2
                fkGponProfile2BridgeControl OBJECT IDENTIFIER ::= { fkGponProfile2Bridge 2 }

                
--  1.3.6.1.4.1.10428 9 1.101.23.51.4.2.1
                -- 1.3.6.1.4.1.10428 9 1.101.23.51.4.2.1
                fkGponProfile2BridgeControlRequest OBJECT-TYPE
                        SYNTAX INTEGER
                                {
                                addBridge(1),
                                delBridge(2),
                                setMacLearning(3),
                                setMaxHost(4),
                                setMcast(5),
                                setPortBridge(6)
                                }
                        MAX-ACCESS read-write
                        STATUS current
                        DESCRIPTION
                                "The request of a user command"
                        ::= { fkGponProfile2BridgeControl 1 }

                
--  1.3.6.1.4.1.10428 9 1.101.23.51.4.2.2
                -- 1.3.6.1.4.1.10428 9 1.101.23.51.4.2.2
                fkGponProfile2BridgeControlStatus OBJECT-TYPE
                        SYNTAX FkControlStatusType
                        MAX-ACCESS read-write
                        STATUS current
                        DESCRIPTION
                                "The status of user command"
                        ::= { fkGponProfile2BridgeControl 2 }

                
--  1.3.6.1.4.1.10428 9 1.101.23.51.4.2.3
                -- 1.3.6.1.4.1.10428 9 1.101.23.51.4.2.3
                fkGponProfile2BridgeControlTimer OBJECT-TYPE
                        SYNTAX Gauge32
                        MAX-ACCESS read-write
                        STATUS current
                        DESCRIPTION
                                "The maximum time for the manager for a long running user command"
                        ::= { fkGponProfile2BridgeControl 3 }

                
--  1.3.6.1.4.1.10428 9 1.101.23.51.4.2.4
                -- 1.3.6.1.4.1.10428 9 1.101.23.51.4.2.4
                fkGponProfile2BridgeControlTimeStamp OBJECT-TYPE
                        SYNTAX TimeTicks
                        MAX-ACCESS read-write
                        STATUS current
                        DESCRIPTION
                                "The time stamp of the last command(end of command)"
                        ::= { fkGponProfile2BridgeControl 4 }

                
--  1.3.6.1.4.1.10428 9 1.101.23.51.4.2.5
                -- 1.3.6.1.4.1.10428 9 1.101.23.51.4.2.5
                fkGponProfile2BridgeControlReqResult OBJECT-TYPE
                        SYNTAX FkControlRequestResultType
                        MAX-ACCESS read-write
                        STATUS current
                        DESCRIPTION
                                "The result of the last user command"
                        ::= { fkGponProfile2BridgeControl 5 }

                
--  1.3.6.1.4.1.10428 9 1.101.23.51.4.2.6
                -- 1.3.6.1.4.1.10428 9 1.101.23.51.4.2.6
                fkGponProfile2BridgeControlTName OBJECT-TYPE
                        SYNTAX OCTET STRING
                        MAX-ACCESS read-write
                        STATUS current
                        DESCRIPTION
                                "The Traffic profile name."
                        ::= { fkGponProfile2BridgeControl 6 }

                
--  1.3.6.1.4.1.10428 9 1.101.23.51.4.2.7
                -- 1.3.6.1.4.1.10428 9 1.101.23.51.4.2.7
                fkGponProfile2BridgeControlId OBJECT-TYPE
                        SYNTAX Integer32
                        MAX-ACCESS read-write
                        STATUS current
                        DESCRIPTION
                                "The bridge ID."
                        ::= { fkGponProfile2BridgeControl 7 }

                
--  1.3.6.1.4.1.10428 9 1.101.23.51.4.2.8
                -- 1.3.6.1.4.1.10428 9 1.101.23.51.4.2.8
                fkGponProfile2BridgeControlMacLearning OBJECT-TYPE
                        SYNTAX EnableFlag
                        MAX-ACCESS read-write
                        STATUS current
                        DESCRIPTION
                                "The Bridge mac learning."
                        ::= { fkGponProfile2BridgeControl 8 }

                
--  1.3.6.1.4.1.10428 9 1.101.23.51.4.2.9
                -- 1.3.6.1.4.1.10428 9 1.101.23.51.4.2.9
                fkGponProfile2BridgeControlMaxHost OBJECT-TYPE
                        SYNTAX Integer32
                        MAX-ACCESS read-write
                        STATUS current
                        DESCRIPTION
                                "The Bridge max host."
                        ::= { fkGponProfile2BridgeControl 9 }

                
--  1.3.6.1.4.1.10428 9 1.101.23.51.4.2.10
                -- 1.3.6.1.4.1.10428 9 1.101.23.51.4.2.10
                fkGponProfile2BridgeControlMcastFlag OBJECT-TYPE
                        SYNTAX EnableFlag
                        MAX-ACCESS read-write
                        STATUS current
                        DESCRIPTION
                                "The Mcast supporting."
                        ::= { fkGponProfile2BridgeControl 10 }

                
                -- 1.3.6.1.4.1.10428 9 1.101.23.51.4.2.11
                fkGponProfile2BridgeControlPortBridge OBJECT-TYPE
                        SYNTAX EnableFlag
                        MAX-ACCESS read-write
                        STATUS current
                        DESCRIPTION
                                "The Mcast supporting."
                        ::= { fkGponProfile2BridgeControl 11 }

                
--  1.3.6.1.4.1.10428 9 1.101.23.51.4.3
                -- 1.3.6.1.4.1.10428 9 1.101.23.51.4.3
                fkGponProfile2BridgeNotification OBJECT IDENTIFIER ::= { fkGponProfile2Bridge 3 }

                
--  1.3.6.1.4.1.10428 9 1.101.23.51.4.3.1
                -- 1.3.6.1.4.1.10428 9 1.101.23.51.4.3.1
                fkGponProfile2BridgeAdded NOTIFICATION-TYPE
                        OBJECTS { fkGponProfile2BridgeControlRequest, fkGponProfile2BridgeControlTimeStamp, fkGponProfile2BridgeControlReqResult, fkGponProfile2BridgeControlTName, fkGponProfile2BridgeControlId, 
                                fkGponProfile2BridgeControlMacLearning, fkGponProfile2BridgeControlMaxHost, fkGponProfile2BridgeControlMcastFlag }
                        STATUS current
                        DESCRIPTION 
                                "Description."
                        ::= { fkGponProfile2BridgeNotification 1 }

                
--  1.3.6.1.4.1.10428 9 1.101.23.51.4.3.2
                -- 1.3.6.1.4.1.10428 9 1.101.23.51.4.3.2
                fkGponProfile2BridgeDeleted NOTIFICATION-TYPE
                        OBJECTS { fkGponProfile2BridgeControlRequest, fkGponProfile2BridgeControlStatus, fkGponProfile2BridgeControlTimer, fkGponProfile2BridgeControlTimeStamp, fkGponProfile2BridgeControlReqResult, 
                                fkGponProfile2BridgeControlTName, fkGponProfile2BridgeControlId }
                        STATUS current
                        DESCRIPTION 
                                "Description."
                        ::= { fkGponProfile2BridgeNotification 2 }

                
--  1.3.6.1.4.1.10428 9 1.101.23.51.4.3.3
                -- 1.3.6.1.4.1.10428 9 1.101.23.51.4.3.3
                fkGponProfile2BridgeMacLearningChanged NOTIFICATION-TYPE
                        OBJECTS { fkGponProfile2BridgeControlRequest, fkGponProfile2BridgeControlTimeStamp, fkGponProfile2BridgeControlReqResult, fkGponProfile2BridgeControlTName, fkGponProfile2BridgeControlId, 
                                fkGponProfile2BridgeControlMacLearning }
                        STATUS current
                        DESCRIPTION 
                                "Description."
                        ::= { fkGponProfile2BridgeNotification 3 }

                
--  1.3.6.1.4.1.10428 9 1.101.23.51.4.3.4
                -- 1.3.6.1.4.1.10428 9 1.101.23.51.4.3.4
                fkGponProfile2BridgeMaxHostChanged NOTIFICATION-TYPE
                        OBJECTS { fkGponProfile2BridgeControlRequest, fkGponProfile2BridgeControlTimeStamp, fkGponProfile2BridgeControlReqResult, fkGponProfile2BridgeControlTName, fkGponProfile2BridgeControlId, 
                                fkGponProfile2BridgeControlMaxHost }
                        STATUS current
                        DESCRIPTION 
                                "Description."
                        ::= { fkGponProfile2BridgeNotification 4 }

                
--  1.3.6.1.4.1.10428 9 1.101.23.51.4.3.5
                -- 1.3.6.1.4.1.10428 9 1.101.23.51.4.3.5
                fkGponProfile2BridgeMcastChanged NOTIFICATION-TYPE
                        OBJECTS { fkGponProfile2BridgeControlRequest, fkGponProfile2BridgeControlStatus, fkGponProfile2BridgeControlTimer, fkGponProfile2BridgeControlTimeStamp, fkGponProfile2BridgeControlReqResult, 
                                fkGponProfile2BridgeControlTName, fkGponProfile2BridgeControlId, fkGponProfile2BridgeControlMcastFlag }
                        STATUS current
                        DESCRIPTION 
                                "Description."
                        ::= { fkGponProfile2BridgeNotification 5 }

                
                -- 1.3.6.1.4.1.10428 9 1.101.23.51.4.3.6
                fkGponProfile2BridgePortBridgeChanged NOTIFICATION-TYPE
                        OBJECTS { fkGponProfile2BridgeControlRequest, fkGponProfile2BridgeControlStatus, fkGponProfile2BridgeControlTimer, fkGponProfile2BridgeControlTimeStamp, fkGponProfile2BridgeControlReqResult, 
                                fkGponProfile2BridgeControlTName, fkGponProfile2BridgeControlId, fkGponProfile2BridgeControlPortBridge }
                        STATUS current
                        DESCRIPTION 
                                "setPortBridge"
                        ::= { fkGponProfile2BridgeNotification 6 }

                
--  1.3.6.1.4.1.10428 9 1.101.23.51.5
                -- 1.3.6.1.4.1.10428 9 1.101.23.51.5
                fkGponProfile2BridgeAni OBJECT IDENTIFIER ::= { fkGponProfile2 5 }

                
--  1.3.6.1.4.1.10428 9 1.101.23.51.5.1
                -- 1.3.6.1.4.1.10428 9 1.101.23.51.5.1
                fkGponProfile2BridgeAniTable OBJECT-TYPE
                        SYNTAX SEQUENCE OF FkGponProfile2BridgeAniEntry
                        MAX-ACCESS not-accessible
                        STATUS current
                        DESCRIPTION
                                "fkGponProfile2BridgeAniTable"
                        ::= { fkGponProfile2BridgeAni 1 }

                
--  1.3.6.1.4.1.10428 9 1.101.23.51.5.1.1
                -- 1.3.6.1.4.1.10428 9 1.101.23.51.5.1.1
                fkGponProfile2BridgeAniEntry OBJECT-TYPE
                        SYNTAX FkGponProfile2BridgeAniEntry
                        MAX-ACCESS not-accessible
                        STATUS current
                        DESCRIPTION
                                "key: fkGponProfile2TrafficIndex, fkGponProfile2BridgeId, fkGponProfile2BridgeAniId"
                        INDEX { fkGponProfile2TrafficIndex, fkGponProfile2BridgeId, fkGponProfile2BridgeAniId }
                        ::= { fkGponProfile2BridgeAniTable 1 }

                
                FkGponProfile2BridgeAniEntry ::=
                        SEQUENCE { 
                                fkGponProfile2BridgeAniId
                                        Integer32,
                                fkGponProfile2BridgeAniVlanFilterMode
                                        INTEGER,
                                fkGponProfile2BridgeAniVlanFilter
                                        OCTET STRING,
                                fkGponProfile2BridgeAniMacFilterPreassign
                                        BITS
                         }

--  1.3.6.1.4.1.10428 9 1.101.23.51.5.1.1.1
                -- 1.3.6.1.4.1.10428 9 1.101.23.51.5.1.1.1
                fkGponProfile2BridgeAniId OBJECT-TYPE
                        SYNTAX Integer32 (1..65535)
                        MAX-ACCESS read-only
                        STATUS current
                        DESCRIPTION
                                "The Bridge ani mapper-ID."
                        ::= { fkGponProfile2BridgeAniEntry 1 }

                
--  1.3.6.1.4.1.10428 9 1.101.23.51.5.1.1.2
                -- 1.3.6.1.4.1.10428 9 1.101.23.51.5.1.1.2
                fkGponProfile2BridgeAniVlanFilterMode OBJECT-TYPE
                        SYNTAX INTEGER
                                {
                                allow(1),
                                deny(2)
                                }
                        MAX-ACCESS read-only
                        STATUS current
                        DESCRIPTION
                                "Allow or deny that untagged fowarding operation "
                        ::= { fkGponProfile2BridgeAniEntry 2 }

                
--  1.3.6.1.4.1.10428 9 1.101.23.51.5.1.1.3
                -- 1.3.6.1.4.1.10428 9 1.101.23.51.5.1.1.3
                fkGponProfile2BridgeAniVlanFilter OBJECT-TYPE
                        SYNTAX OCTET STRING
                        MAX-ACCESS read-only
                        STATUS current
                        DESCRIPTION
                                "The vlan-filter VID list."
                        ::= { fkGponProfile2BridgeAniEntry 3 }

                
                -- 1.3.6.1.4.1.10428 9 1.101.23.51.5.1.1.4
                fkGponProfile2BridgeAniMacFilterPreassign OBJECT-TYPE
                        SYNTAX BITS
                                {
                                ipv4Multicast(0),
                                ipv6Multicast(1),
                                ipv4Broadcast(2),
                                rarp(3),
                                ipx(4),
                                netBEUI(5),
                                appleTalk(6),
                                bridgeManagementInformation(7),
                                arp(8),
                                pppoeBroadcast(9)
                                }
                        MAX-ACCESS read-only
                        STATUS current
                        DESCRIPTION
                                "MAC Filter Preassign Table
                                0 -> forward
                                1 -> filter"
                        ::= { fkGponProfile2BridgeAniEntry 4 }

                
--  1.3.6.1.4.1.10428 9 1.101.23.51.5.2
                -- 1.3.6.1.4.1.10428 9 1.101.23.51.5.2
                fkGponProfile2BridgeAniControl OBJECT IDENTIFIER ::= { fkGponProfile2BridgeAni 2 }

                
--  1.3.6.1.4.1.10428 9 1.101.23.51.5.2.1
                -- 1.3.6.1.4.1.10428 9 1.101.23.51.5.2.1
                fkGponProfile2BridgeAniControlRequest OBJECT-TYPE
                        SYNTAX INTEGER
                                {
                                addBridgeAni(1),
                                delBridgeAni(2),
                                setVlanFilter(3),
                                setAniMacFilterPreassign(4)
                                }
                        MAX-ACCESS read-write
                        STATUS current
                        DESCRIPTION
                                "The request of a user command"
                        ::= { fkGponProfile2BridgeAniControl 1 }

                
--  1.3.6.1.4.1.10428 9 1.101.23.51.5.2.2
                -- 1.3.6.1.4.1.10428 9 1.101.23.51.5.2.2
                fkGponProfile2BridgeAniControlStatus OBJECT-TYPE
                        SYNTAX FkControlStatusType
                        MAX-ACCESS read-write
                        STATUS current
                        DESCRIPTION
                                "The status of user command"
                        ::= { fkGponProfile2BridgeAniControl 2 }

                
--  1.3.6.1.4.1.10428 9 1.101.23.51.5.2.3
                -- 1.3.6.1.4.1.10428 9 1.101.23.51.5.2.3
                fkGponProfile2BridgeAniControlTimer OBJECT-TYPE
                        SYNTAX Gauge32
                        MAX-ACCESS read-write
                        STATUS current
                        DESCRIPTION
                                "The maximum time for the manager for a long running user command"
                        ::= { fkGponProfile2BridgeAniControl 3 }

                
--  1.3.6.1.4.1.10428 9 1.101.23.51.5.2.4
                -- 1.3.6.1.4.1.10428 9 1.101.23.51.5.2.4
                fkGponProfile2BridgeAniControlTimeStamp OBJECT-TYPE
                        SYNTAX TimeTicks
                        MAX-ACCESS read-write
                        STATUS current
                        DESCRIPTION
                                "The time stamp of the last command(end of command)"
                        ::= { fkGponProfile2BridgeAniControl 4 }

                
--  1.3.6.1.4.1.10428 9 1.101.23.51.5.2.5
                -- 1.3.6.1.4.1.10428 9 1.101.23.51.5.2.5
                fkGponProfile2BridgeAniControlReqResult OBJECT-TYPE
                        SYNTAX FkControlRequestResultType
                        MAX-ACCESS read-write
                        STATUS current
                        DESCRIPTION
                                "The result of the last user command"
                        ::= { fkGponProfile2BridgeAniControl 5 }

                
--  1.3.6.1.4.1.10428 9 1.101.23.51.5.2.6
                -- 1.3.6.1.4.1.10428 9 1.101.23.51.5.2.6
                fkGponProfile2BridgeAniControlTName OBJECT-TYPE
                        SYNTAX OCTET STRING
                        MAX-ACCESS read-write
                        STATUS current
                        DESCRIPTION
                                "The Traffic profile name."
                        ::= { fkGponProfile2BridgeAniControl 6 }

                
--  1.3.6.1.4.1.10428 9 1.101.23.51.5.2.7
                -- 1.3.6.1.4.1.10428 9 1.101.23.51.5.2.7
                fkGponProfile2BridgeAniControlBridgeId OBJECT-TYPE
                        SYNTAX Integer32
                        MAX-ACCESS read-write
                        STATUS current
                        DESCRIPTION
                                "The bridge ID."
                        ::= { fkGponProfile2BridgeAniControl 7 }

                
--  1.3.6.1.4.1.10428 9 1.101.23.51.5.2.8
                -- 1.3.6.1.4.1.10428 9 1.101.23.51.5.2.8
                fkGponProfile2BridgeAniControlId OBJECT-TYPE
                        SYNTAX Integer32
                        MAX-ACCESS read-write
                        STATUS current
                        DESCRIPTION
                                "The bridge Ani ID."
                        ::= { fkGponProfile2BridgeAniControl 8 }

                
--  1.3.6.1.4.1.10428 9 1.101.23.51.5.2.9
                -- 1.3.6.1.4.1.10428 9 1.101.23.51.5.2.9
                fkGponProfile2BridgeAniControlVlanFilterMode OBJECT-TYPE
                        SYNTAX INTEGER
                                {
                                allow(1),
                                deny(2)
                                }
                        MAX-ACCESS read-write
                        STATUS current
                        DESCRIPTION
                                "Allow or deny that untagged fowarding operation "
                        ::= { fkGponProfile2BridgeAniControl 9 }

                
--  1.3.6.1.4.1.10428 9 1.101.23.51.5.2.10
                -- 1.3.6.1.4.1.10428 9 1.101.23.51.5.2.10
                fkGponProfile2BridgeAniControlVlanFilter OBJECT-TYPE
                        SYNTAX OCTET STRING
                        MAX-ACCESS read-write
                        STATUS current
                        DESCRIPTION
                                "The vlan-filter VID list."
                        ::= { fkGponProfile2BridgeAniControl 10 }

                
                -- 1.3.6.1.4.1.10428 9 1.101.23.51.5.2.11
                fkGponProfile2BridgeAniControlMacFilterPreassign OBJECT-TYPE
                        SYNTAX BITS
                                {
                                ipv4Multicast(0),
                                ipv6Multicast(1),
                                ipv4Broadcast(2),
                                rarp(3),
                                ipx(4),
                                netBEUI(5),
                                appleTalk(6),
                                bridgeManagementInformation(7),
                                arp(8),
                                pppoeBroadcast(9)
                                }
                        MAX-ACCESS read-write
                        STATUS current
                        DESCRIPTION
                                "MAC Filter Preassign Table
                                0 -> forward
                                1 -> filter"
                        ::= { fkGponProfile2BridgeAniControl 11 }

                
--  1.3.6.1.4.1.10428 9 1.101.23.51.5.3
                -- 1.3.6.1.4.1.10428 9 1.101.23.51.5.3
                fkGponProfile2BridgeAniNotification OBJECT IDENTIFIER ::= { fkGponProfile2BridgeAni 3 }

                
--  1.3.6.1.4.1.10428 9 1.101.23.51.5.3.1
                -- 1.3.6.1.4.1.10428 9 1.101.23.51.5.3.1
                fkGponProfile2BridgeAniAdded NOTIFICATION-TYPE
                        OBJECTS { fkGponProfile2BridgeAniControlRequest, fkGponProfile2BridgeAniControlStatus, fkGponProfile2BridgeAniControlTimer, fkGponProfile2BridgeAniControlTimeStamp, fkGponProfile2BridgeAniControlReqResult, 
                                fkGponProfile2BridgeAniControlTName, fkGponProfile2BridgeAniControlBridgeId, fkGponProfile2BridgeAniControlId }
                        STATUS current
                        DESCRIPTION 
                                "Description."
                        ::= { fkGponProfile2BridgeAniNotification 1 }

                
--  1.3.6.1.4.1.10428 9 1.101.23.51.5.3.2
                -- 1.3.6.1.4.1.10428 9 1.101.23.51.5.3.2
                fkGponProfile2BridgeAniDeleted NOTIFICATION-TYPE
                        OBJECTS { fkGponProfile2BridgeAniControlRequest, fkGponProfile2BridgeAniControlStatus, fkGponProfile2BridgeAniControlTimer, fkGponProfile2BridgeAniControlTimeStamp, fkGponProfile2BridgeAniControlReqResult, 
                                fkGponProfile2BridgeAniControlTName, fkGponProfile2BridgeAniControlBridgeId, fkGponProfile2BridgeAniControlId }
                        STATUS current
                        DESCRIPTION 
                                "Description."
                        ::= { fkGponProfile2BridgeAniNotification 2 }

                
--  1.3.6.1.4.1.10428 9 1.101.23.51.5.3.3
                -- 1.3.6.1.4.1.10428 9 1.101.23.51.5.3.3
                fkGponProfile2BridgeAniVlanFilterChanged NOTIFICATION-TYPE
                        OBJECTS { fkGponProfile2BridgeAniControlRequest, fkGponProfile2BridgeAniControlStatus, fkGponProfile2BridgeAniControlTimer, fkGponProfile2BridgeAniControlTimeStamp, fkGponProfile2BridgeAniControlReqResult, 
                                fkGponProfile2BridgeAniControlTName, fkGponProfile2BridgeAniControlBridgeId, fkGponProfile2BridgeAniControlId, fkGponProfile2BridgeAniControlVlanFilterMode, fkGponProfile2BridgeAniControlVlanFilter
                                 }
                        STATUS current
                        DESCRIPTION 
                                "Description."
                        ::= { fkGponProfile2BridgeAniNotification 3 }

                
                -- 1.3.6.1.4.1.10428 9 1.101.23.51.5.3.4
                fkGponProfile2BridgeAniMacFilterPreassignChanged NOTIFICATION-TYPE
                        OBJECTS { fkGponProfile2BridgeAniControlRequest, fkGponProfile2BridgeAniControlTimeStamp, fkGponProfile2BridgeAniControlReqResult, fkGponProfile2BridgeAniControlTName, fkGponProfile2BridgeAniControlBridgeId, 
                                fkGponProfile2BridgeAniControlId, fkGponProfile2BridgeAniControlMacFilterPreassign }
                        STATUS current
                        DESCRIPTION 
                                "setAniMacFilterPreassign"
                        ::= { fkGponProfile2BridgeAniNotification 4 }

                
--  1.3.6.1.4.1.10428 9 1.101.23.51.6
                -- 1.3.6.1.4.1.10428 9 1.101.23.51.6
                fkGponProfile2BridgeUni OBJECT IDENTIFIER ::= { fkGponProfile2 6 }

                
--  1.3.6.1.4.1.10428 9 1.101.23.51.6.1
                -- 1.3.6.1.4.1.10428 9 1.101.23.51.6.1
                fkGponProfile2BridgeUniTable OBJECT-TYPE
                        SYNTAX SEQUENCE OF FkGponProfile2BridgeUniEntry
                        MAX-ACCESS not-accessible
                        STATUS current
                        DESCRIPTION
                                "fkGponProfile2BridgeUniTable"
                        ::= { fkGponProfile2BridgeUni 1 }

                
--  1.3.6.1.4.1.10428 9 1.101.23.51.6.1.1
                -- 1.3.6.1.4.1.10428 9 1.101.23.51.6.1.1
                fkGponProfile2BridgeUniEntry OBJECT-TYPE
                        SYNTAX FkGponProfile2BridgeUniEntry
                        MAX-ACCESS not-accessible
                        STATUS current
                        DESCRIPTION
                                "key: fkGponProfile2TrafficIndex, fkGponProfile2BridgeId, fkGponProfile2BridgeUniType, fkGponProfile2BridgeUniId"
                        INDEX { fkGponProfile2TrafficIndex, fkGponProfile2BridgeId, fkGponProfile2BridgeUniType, fkGponProfile2BridgeUniId }
                        ::= { fkGponProfile2BridgeUniTable 1 }

                
                FkGponProfile2BridgeUniEntry ::=
                        SEQUENCE { 
                                fkGponProfile2BridgeUniType
                                        INTEGER,
                                fkGponProfile2BridgeUniId
                                        Integer32,
                                fkGponProfile2BridgeUniVlanOpDsOperFlag
                                        INTEGER,
                                fkGponProfile2BridgeUniVlanOpUsOperFlag
                                        INTEGER,
                                fkGponProfile2BridgeUniVlanOpUsOperVid
                                        Integer32,
                                fkGponProfile2BridgeUniVlanOpUsOperCos
                                        Integer32,
                                fkGponProfile2BridgeUniPortAdmin
                                        EnableFlag,
                                fkGponProfile2BridgeUniRateLimitDownSir
                                        Integer32,
                                fkGponProfile2BridgeUniRateLimitDownPir
                                        Integer32,
                                fkGponProfile2BridgeUniRateLimitUpSir
                                        Integer32,
                                fkGponProfile2BridgeUniRateLimitUpPir
                                        Integer32,
                                fkGponProfile2BridgeUniIgmpMaxGroup
                                        Integer32,
                                fkGponProfile2BridgeUniMaxFrame
                                        Integer32,
                                fkGponProfile2BridgeUniMcastProfile
                                        OCTET STRING,
                                fkGponProfile2BridgeUniVlanFilterMode
                                        INTEGER,
                                fkGponProfile2BridgeUniVlanFilter
                                        OCTET STRING,
                                fkGponProfile2BridgeUniIpMode
                                        INTEGER,
                                fkGponProfile2BridgeUniDns1
                                        IpAddress,
                                fkGponProfile2BridgeUniDns2
                                        IpAddress,
                                fkGponProfile2BridgeUniVoIPProfile
                                        OCTET STRING,
                                fkGponProfile2BridgeUniMaxHost
                                        INTEGER,
                                fkGponProfile2BridgeUniExtVlanName
                                        OCTET STRING,
                                fkGponProfile2BridgeUniMcastRateLimit
                                        Integer32,
                                fkGponProfile2BridgeUniMacFilterPreassign
                                        BITS,
                                fkGponProfile2BridgeUniRateLimitProfile
                                        OCTET STRING
                         }

--  1.3.6.1.4.1.10428 9 1.101.23.51.6.1.1.1
                -- 1.3.6.1.4.1.10428 9 1.101.23.51.6.1.1.1
                fkGponProfile2BridgeUniType OBJECT-TYPE
                        SYNTAX INTEGER
                                {
                                eth(1),
                                voip(2),
                                virtualEth(3)
                                }
                        MAX-ACCESS read-only
                        STATUS current
                        DESCRIPTION
                                "The Bridge Uni Type."
                        ::= { fkGponProfile2BridgeUniEntry 1 }

                
--  1.3.6.1.4.1.10428 9 1.101.23.51.6.1.1.2
                -- 1.3.6.1.4.1.10428 9 1.101.23.51.6.1.1.2
                fkGponProfile2BridgeUniId OBJECT-TYPE
                        SYNTAX Integer32 (1..65535)
                        MAX-ACCESS read-only
                        STATUS current
                        DESCRIPTION
                                "The Bridge Uni mapper-ID."
                        ::= { fkGponProfile2BridgeUniEntry 2 }

                
--  1.3.6.1.4.1.10428 9 1.101.23.51.6.1.1.3
                -- 1.3.6.1.4.1.10428 9 1.101.23.51.6.1.1.3
                fkGponProfile2BridgeUniVlanOpDsOperFlag OBJECT-TYPE
                        SYNTAX INTEGER
                                {
                                unused(0),
                                keep(1),
                                remove(2)
                                }
                        MAX-ACCESS read-only
                        STATUS current
                        DESCRIPTION
                                "The VLAN Tagging Operation Data & DS VLAN Tagging Operation mode"
                        ::= { fkGponProfile2BridgeUniEntry 3 }

                
--  1.3.6.1.4.1.10428 9 1.101.23.51.6.1.1.4
                -- 1.3.6.1.4.1.10428 9 1.101.23.51.6.1.1.4
                fkGponProfile2BridgeUniVlanOpUsOperFlag OBJECT-TYPE
                        SYNTAX INTEGER
                                {
                                unused(0),
                                keep(1),
                                overwrite(2),
                                add(3)
                                }
                        MAX-ACCESS read-only
                        STATUS current
                        DESCRIPTION
                                "The VLAN Tagging Operation Data & US VLAN Tagging Operation mode"
                        ::= { fkGponProfile2BridgeUniEntry 4 }

                
--  1.3.6.1.4.1.10428 9 1.101.23.51.6.1.1.5
                -- 1.3.6.1.4.1.10428 9 1.101.23.51.6.1.1.5
                fkGponProfile2BridgeUniVlanOpUsOperVid OBJECT-TYPE
                        SYNTAX Integer32
                        MAX-ACCESS read-only
                        STATUS current
                        DESCRIPTION
                                "The US Oper Vid."
                        ::= { fkGponProfile2BridgeUniEntry 5 }

                
--  1.3.6.1.4.1.10428 9 1.101.23.51.6.1.1.6
                -- 1.3.6.1.4.1.10428 9 1.101.23.51.6.1.1.6
                fkGponProfile2BridgeUniVlanOpUsOperCos OBJECT-TYPE
                        SYNTAX Integer32
                        MAX-ACCESS read-only
                        STATUS current
                        DESCRIPTION
                                "The US Oper tag CoS value"
                        ::= { fkGponProfile2BridgeUniEntry 6 }

                
--  1.3.6.1.4.1.10428 9 1.101.23.51.6.1.1.7
                -- 1.3.6.1.4.1.10428 9 1.101.23.51.6.1.1.7
                fkGponProfile2BridgeUniPortAdmin OBJECT-TYPE
                        SYNTAX EnableFlag
                        MAX-ACCESS read-only
                        STATUS current
                        DESCRIPTION
                                "The port admin status"
                        ::= { fkGponProfile2BridgeUniEntry 7 }

                
--  1.3.6.1.4.1.10428 9 1.101.23.51.6.1.1.8
                -- 1.3.6.1.4.1.10428 9 1.101.23.51.6.1.1.8
                fkGponProfile2BridgeUniRateLimitDownSir OBJECT-TYPE
                        SYNTAX Integer32
                        MAX-ACCESS read-only
                        STATUS current
                        DESCRIPTION
                                "The download rate-limit control : SIR (Bandwidth in steps of 64Kbps)"
                        ::= { fkGponProfile2BridgeUniEntry 8 }

                
--  1.3.6.1.4.1.10428 9 1.101.23.51.6.1.1.9
                -- 1.3.6.1.4.1.10428 9 1.101.23.51.6.1.1.9
                fkGponProfile2BridgeUniRateLimitDownPir OBJECT-TYPE
                        SYNTAX Integer32
                        MAX-ACCESS read-only
                        STATUS current
                        DESCRIPTION
                                "The download rate-limit control : PIR (Bandwidth in steps of 64Kbps)"
                        ::= { fkGponProfile2BridgeUniEntry 9 }

                
--  1.3.6.1.4.1.10428 9 1.101.23.51.6.1.1.10
                -- 1.3.6.1.4.1.10428 9 1.101.23.51.6.1.1.10
                fkGponProfile2BridgeUniRateLimitUpSir OBJECT-TYPE
                        SYNTAX Integer32
                        MAX-ACCESS read-only
                        STATUS current
                        DESCRIPTION
                                "The upload rate-limit control : SIR (Bandwidth in steps of 64Kbps)"
                        ::= { fkGponProfile2BridgeUniEntry 10 }

                
--  1.3.6.1.4.1.10428 9 1.101.23.51.6.1.1.11
                -- 1.3.6.1.4.1.10428 9 1.101.23.51.6.1.1.11
                fkGponProfile2BridgeUniRateLimitUpPir OBJECT-TYPE
                        SYNTAX Integer32
                        MAX-ACCESS read-only
                        STATUS current
                        DESCRIPTION
                                "The upload rate-limit control : SIR (Bandwidth in steps of 64Kbps)"
                        ::= { fkGponProfile2BridgeUniEntry 11 }

                
--  1.3.6.1.4.1.10428 9 1.101.23.51.6.1.1.12
                -- 1.3.6.1.4.1.10428 9 1.101.23.51.6.1.1.12
                fkGponProfile2BridgeUniIgmpMaxGroup OBJECT-TYPE
                        SYNTAX Integer32
                        MAX-ACCESS read-only
                        STATUS current
                        DESCRIPTION
                                "The IGMP max group"
                        ::= { fkGponProfile2BridgeUniEntry 12 }

                
--  1.3.6.1.4.1.10428 9 1.101.23.51.6.1.1.13
                -- 1.3.6.1.4.1.10428 9 1.101.23.51.6.1.1.13
                fkGponProfile2BridgeUniMaxFrame OBJECT-TYPE
                        SYNTAX Integer32
                        MAX-ACCESS read-only
                        STATUS current
                        DESCRIPTION
                                "The max-frame"
                        ::= { fkGponProfile2BridgeUniEntry 13 }

                
--  1.3.6.1.4.1.10428 9 1.101.23.51.6.1.1.14
                -- 1.3.6.1.4.1.10428 9 1.101.23.51.6.1.1.14
                fkGponProfile2BridgeUniMcastProfile OBJECT-TYPE
                        SYNTAX OCTET STRING
                        MAX-ACCESS read-only
                        STATUS current
                        DESCRIPTION
                                "The multicast profile name"
                        ::= { fkGponProfile2BridgeUniEntry 14 }

                
--  1.3.6.1.4.1.10428 9 1.101.23.51.6.1.1.15
                -- 1.3.6.1.4.1.10428 9 1.101.23.51.6.1.1.15
                fkGponProfile2BridgeUniVlanFilterMode OBJECT-TYPE
                        SYNTAX INTEGER
                                {
                                allow(1),
                                deny(2)
                                }
                        MAX-ACCESS read-only
                        STATUS current
                        DESCRIPTION
                                "Allow or deny that untagged fowarding operation "
                        ::= { fkGponProfile2BridgeUniEntry 15 }

                
--  1.3.6.1.4.1.10428 9 1.101.23.51.6.1.1.16
                -- 1.3.6.1.4.1.10428 9 1.101.23.51.6.1.1.16
                fkGponProfile2BridgeUniVlanFilter OBJECT-TYPE
                        SYNTAX OCTET STRING
                        MAX-ACCESS read-only
                        STATUS current
                        DESCRIPTION
                                "The vlan-filter VID list."
                        ::= { fkGponProfile2BridgeUniEntry 16 }

                
--  1.3.6.1.4.1.10428 9 1.101.23.51.6.1.1.17
                -- 1.3.6.1.4.1.10428 9 1.101.23.51.6.1.1.17
                fkGponProfile2BridgeUniIpMode OBJECT-TYPE
                        SYNTAX INTEGER
                                {
                                static(1),
                                dhcp(2),
                                none(3)
                                }
                        MAX-ACCESS read-only
                        STATUS current
                        DESCRIPTION
                                "The UNI IP mode."
                        ::= { fkGponProfile2BridgeUniEntry 17 }

                
--  1.3.6.1.4.1.10428 9 1.101.23.51.6.1.1.18
                -- 1.3.6.1.4.1.10428 9 1.101.23.51.6.1.1.18
                fkGponProfile2BridgeUniDns1 OBJECT-TYPE
                        SYNTAX IpAddress
                        MAX-ACCESS read-only
                        STATUS current
                        DESCRIPTION
                                "The DNS address 1."
                        ::= { fkGponProfile2BridgeUniEntry 18 }

                
--  1.3.6.1.4.1.10428 9 1.101.23.51.6.1.1.19
                -- 1.3.6.1.4.1.10428 9 1.101.23.51.6.1.1.19
                fkGponProfile2BridgeUniDns2 OBJECT-TYPE
                        SYNTAX IpAddress
                        MAX-ACCESS read-only
                        STATUS current
                        DESCRIPTION
                                "The DNS address 2."
                        ::= { fkGponProfile2BridgeUniEntry 19 }

                
--  1.3.6.1.4.1.10428 9 1.101.23.51.6.1.1.20
                -- 1.3.6.1.4.1.10428 9 1.101.23.51.6.1.1.20
                fkGponProfile2BridgeUniVoIPProfile OBJECT-TYPE
                        SYNTAX OCTET STRING
                        MAX-ACCESS read-only
                        STATUS current
                        DESCRIPTION
                                "The VoIP profile name."
                        ::= { fkGponProfile2BridgeUniEntry 20 }

                
                -- 1.3.6.1.4.1.10428 9 1.101.23.51.6.1.1.21
                fkGponProfile2BridgeUniMaxHost OBJECT-TYPE
                        SYNTAX INTEGER (1..65535)
                        MAX-ACCESS read-only
                        STATUS current
                        DESCRIPTION
                                "The UNI max host."
                        ::= { fkGponProfile2BridgeUniEntry 21 }

                
                -- 1.3.6.1.4.1.10428 9 1.101.23.51.6.1.1.22
                fkGponProfile2BridgeUniExtVlanName OBJECT-TYPE
                        SYNTAX OCTET STRING
                        MAX-ACCESS read-only
                        STATUS current
                        DESCRIPTION
                                "The Extended vlan name."
                        ::= { fkGponProfile2BridgeUniEntry 22 }

                
                -- 1.3.6.1.4.1.10428 9 1.101.23.51.6.1.1.23
                fkGponProfile2BridgeUniMcastRateLimit OBJECT-TYPE
                        SYNTAX Integer32 (0..1031616)
                        MAX-ACCESS read-only
                        STATUS current
                        DESCRIPTION
                                "The multicast rate-limit bandwidth (Bandwidth in steps of 8Kbps), 0 is disable"
                        ::= { fkGponProfile2BridgeUniEntry 23 }

                
                -- 1.3.6.1.4.1.10428 9 1.101.23.51.6.1.1.24
                fkGponProfile2BridgeUniMacFilterPreassign OBJECT-TYPE
                        SYNTAX BITS
                                {
                                ipv4Multicast(0),
                                ipv6Multicast(1),
                                ipv4Broadcast(2),
                                rarp(3),
                                ipx(4),
                                netBEUI(5),
                                appleTalk(6),
                                bridgeManagementInformation(7),
                                arp(8),
                                pppoeBroadcast(9)
                                }
                        MAX-ACCESS read-only
                        STATUS current
                        DESCRIPTION
                                "MAC Filter Preassign Table
                                0 -> forward
                                1 -> filter"
                        ::= { fkGponProfile2BridgeUniEntry 24 }

                
                -- 1.3.6.1.4.1.10428 9 1.101.23.51.6.1.1.25
                fkGponProfile2BridgeUniRateLimitProfile OBJECT-TYPE
                        SYNTAX OCTET STRING
                        MAX-ACCESS read-only
                        STATUS current
                        DESCRIPTION
                                "The rate-limit profile name."
                        ::= { fkGponProfile2BridgeUniEntry 25 }

                
--  1.3.6.1.4.1.10428 9 1.101.23.51.6.2
                -- 1.3.6.1.4.1.10428 9 1.101.23.51.6.2
                fkGponProfile2BridgeUniControl OBJECT IDENTIFIER ::= { fkGponProfile2BridgeUni 2 }

                
--  1.3.6.1.4.1.10428 9 1.101.23.51.6.2.1
                -- 1.3.6.1.4.1.10428 9 1.101.23.51.6.2.1
                fkGponProfile2BridgeUniControlRequest OBJECT-TYPE
                        SYNTAX INTEGER
                                {
                                addBridgeUni(1),
                                delBridgeUni(2),
                                setVlanUsOper(3),
                                setVlanDsOper(4),
                                setPortAdmin(5),
                                setRateLimit(6),
                                setIgmpMaxGroup(7),
                                setMaxFrame(8),
                                setMcastProfile(9),
                                setVlanFilter(10),
                                setIpInfo(11),
                                setVoipProfile(12),
                                setMaxHost(13),
                                setExtendedVlan(14),
                                setMcastRateLimit(15),
                                setUniMacFilterPreassign(16),
                                setUniRateLimitProfile(17)
                                }
                        MAX-ACCESS read-write
                        STATUS current
                        DESCRIPTION
                                "The request of a user command"
                        ::= { fkGponProfile2BridgeUniControl 1 }

                
--  1.3.6.1.4.1.10428 9 1.101.23.51.6.2.2
                -- 1.3.6.1.4.1.10428 9 1.101.23.51.6.2.2
                fkGponProfile2BridgeUniControlStatus OBJECT-TYPE
                        SYNTAX FkControlStatusType
                        MAX-ACCESS read-write
                        STATUS current
                        DESCRIPTION
                                "The status of user command"
                        ::= { fkGponProfile2BridgeUniControl 2 }

                
--  1.3.6.1.4.1.10428 9 1.101.23.51.6.2.3
                -- 1.3.6.1.4.1.10428 9 1.101.23.51.6.2.3
                fkGponProfile2BridgeUniControlTimer OBJECT-TYPE
                        SYNTAX Gauge32
                        MAX-ACCESS read-write
                        STATUS current
                        DESCRIPTION
                                "The maximum time for the manager for a long running user command"
                        ::= { fkGponProfile2BridgeUniControl 3 }

                
--  1.3.6.1.4.1.10428 9 1.101.23.51.6.2.4
                -- 1.3.6.1.4.1.10428 9 1.101.23.51.6.2.4
                fkGponProfile2BridgeUniControlTimeStamp OBJECT-TYPE
                        SYNTAX TimeTicks
                        MAX-ACCESS read-write
                        STATUS current
                        DESCRIPTION
                                "The time stamp of the last command(end of command)"
                        ::= { fkGponProfile2BridgeUniControl 4 }

                
--  1.3.6.1.4.1.10428 9 1.101.23.51.6.2.5
                -- 1.3.6.1.4.1.10428 9 1.101.23.51.6.2.5
                fkGponProfile2BridgeUniControlReqResult OBJECT-TYPE
                        SYNTAX FkControlRequestResultType
                        MAX-ACCESS read-write
                        STATUS current
                        DESCRIPTION
                                "The result of the last user command"
                        ::= { fkGponProfile2BridgeUniControl 5 }

                
--  1.3.6.1.4.1.10428 9 1.101.23.51.6.2.6
                -- 1.3.6.1.4.1.10428 9 1.101.23.51.6.2.6
                fkGponProfile2BridgeUniControlTName OBJECT-TYPE
                        SYNTAX OCTET STRING
                        MAX-ACCESS read-write
                        STATUS current
                        DESCRIPTION
                                "The Traffic profile name."
                        ::= { fkGponProfile2BridgeUniControl 6 }

                
--  1.3.6.1.4.1.10428 9 1.101.23.51.6.2.7
                -- 1.3.6.1.4.1.10428 9 1.101.23.51.6.2.7
                fkGponProfile2BridgeUniControlBridgeId OBJECT-TYPE
                        SYNTAX Integer32
                        MAX-ACCESS read-write
                        STATUS current
                        DESCRIPTION
                                "The bridge ID."
                        ::= { fkGponProfile2BridgeUniControl 7 }

                
--  1.3.6.1.4.1.10428 9 1.101.23.51.6.2.8
                -- 1.3.6.1.4.1.10428 9 1.101.23.51.6.2.8
                fkGponProfile2BridgeUniControlType OBJECT-TYPE
                        SYNTAX INTEGER
                                {
                                eth(1),
                                voip(2),
                                virtualEth(3)
                                }
                        MAX-ACCESS read-write
                        STATUS current
                        DESCRIPTION
                                "The Bridge Uni Type."
                        ::= { fkGponProfile2BridgeUniControl 8 }

                
--  1.3.6.1.4.1.10428 9 1.101.23.51.6.2.9
                -- 1.3.6.1.4.1.10428 9 1.101.23.51.6.2.9
                fkGponProfile2BridgeUniControlId OBJECT-TYPE
                        SYNTAX Integer32
                        MAX-ACCESS read-write
                        STATUS current
                        DESCRIPTION
                                "The bridge Uni ID."
                        ::= { fkGponProfile2BridgeUniControl 9 }

                
--  1.3.6.1.4.1.10428 9 1.101.23.51.6.2.10
                -- 1.3.6.1.4.1.10428 9 1.101.23.51.6.2.10
                fkGponProfile2BridgeUniControlVlanOpDsOperFlag OBJECT-TYPE
                        SYNTAX INTEGER
                                {
                                unused(0),
                                keep(1),
                                remove(2)
                                }
                        MAX-ACCESS read-write
                        STATUS current
                        DESCRIPTION
                                "The VLAN Tagging Operation Data & DS VLAN Tagging Operation mode"
                        ::= { fkGponProfile2BridgeUniControl 10 }

                
--  1.3.6.1.4.1.10428 9 1.101.23.51.6.2.11
                -- 1.3.6.1.4.1.10428 9 1.101.23.51.6.2.11
                fkGponProfile2BridgeUniControlVlanOpUsOperFlag OBJECT-TYPE
                        SYNTAX INTEGER
                                {
                                unused(0),
                                keep(1),
                                overwrite(2),
                                add(3)
                                }
                        MAX-ACCESS read-write
                        STATUS current
                        DESCRIPTION
                                "The VLAN Tagging Operation Data & US VLAN Tagging Operation mode"
                        ::= { fkGponProfile2BridgeUniControl 11 }

                
--  1.3.6.1.4.1.10428 9 1.101.23.51.6.2.12
                -- 1.3.6.1.4.1.10428 9 1.101.23.51.6.2.12
                fkGponProfile2BridgeUniControlVlanOpUsOperVid OBJECT-TYPE
                        SYNTAX Integer32
                        MAX-ACCESS read-write
                        STATUS current
                        DESCRIPTION
                                "The US Oper Vid."
                        ::= { fkGponProfile2BridgeUniControl 12 }

                
--  1.3.6.1.4.1.10428 9 1.101.23.51.6.2.13
                -- 1.3.6.1.4.1.10428 9 1.101.23.51.6.2.13
                fkGponProfile2BridgeUniControlVlanOpUsOperCos OBJECT-TYPE
                        SYNTAX Integer32
                        MAX-ACCESS read-write
                        STATUS current
                        DESCRIPTION
                                "The US Oper tag CoS value"
                        ::= { fkGponProfile2BridgeUniControl 13 }

                
--  1.3.6.1.4.1.10428 9 1.101.23.51.6.2.14
                -- 1.3.6.1.4.1.10428 9 1.101.23.51.6.2.14
                fkGponProfile2BridgeUniControlPortAdmin OBJECT-TYPE
                        SYNTAX EnableFlag
                        MAX-ACCESS read-write
                        STATUS current
                        DESCRIPTION
                                "The port admin status"
                        ::= { fkGponProfile2BridgeUniControl 14 }

                
--  1.3.6.1.4.1.10428 9 1.101.23.51.6.2.15
                -- 1.3.6.1.4.1.10428 9 1.101.23.51.6.2.15
                fkGponProfile2BridgeUniControlRateLimitDownSir OBJECT-TYPE
                        SYNTAX Integer32
                        MAX-ACCESS read-write
                        STATUS current
                        DESCRIPTION
                                "The download rate-limit control : SIR (Bandwidth in steps of 64Kbps)"
                        ::= { fkGponProfile2BridgeUniControl 15 }

                
--  1.3.6.1.4.1.10428 9 1.101.23.51.6.2.16
                -- 1.3.6.1.4.1.10428 9 1.101.23.51.6.2.16
                fkGponProfile2BridgeUniControlRateLimitDownPir OBJECT-TYPE
                        SYNTAX Integer32
                        MAX-ACCESS read-write
                        STATUS current
                        DESCRIPTION
                                "The download rate-limit control : PIR (Bandwidth in steps of 64Kbps)"
                        ::= { fkGponProfile2BridgeUniControl 16 }

                
--  1.3.6.1.4.1.10428 9 1.101.23.51.6.2.17
                -- 1.3.6.1.4.1.10428 9 1.101.23.51.6.2.17
                fkGponProfile2BridgeUniControlRateLimitUpSir OBJECT-TYPE
                        SYNTAX Integer32
                        MAX-ACCESS read-write
                        STATUS current
                        DESCRIPTION
                                "The upload rate-limit control : SIR (Bandwidth in steps of 64Kbps)"
                        ::= { fkGponProfile2BridgeUniControl 17 }

                
--  1.3.6.1.4.1.10428 9 1.101.23.51.6.2.18
                -- 1.3.6.1.4.1.10428 9 1.101.23.51.6.2.18
                fkGponProfile2BridgeUniControlRateLimitUpPir OBJECT-TYPE
                        SYNTAX Integer32
                        MAX-ACCESS read-write
                        STATUS current
                        DESCRIPTION
                                "The upload rate-limit control : SIR (Bandwidth in steps of 64Kbps)"
                        ::= { fkGponProfile2BridgeUniControl 18 }

                
--  1.3.6.1.4.1.10428 9 1.101.23.51.6.2.19
                -- 1.3.6.1.4.1.10428 9 1.101.23.51.6.2.19
                fkGponProfile2BridgeUniControlIgmpMaxGroup OBJECT-TYPE
                        SYNTAX Integer32
                        MAX-ACCESS read-write
                        STATUS current
                        DESCRIPTION
                                "The IGMP max group"
                        ::= { fkGponProfile2BridgeUniControl 19 }

                
--  1.3.6.1.4.1.10428 9 1.101.23.51.6.2.20
                -- 1.3.6.1.4.1.10428 9 1.101.23.51.6.2.20
                fkGponProfile2BridgeUniControlMaxFrame OBJECT-TYPE
                        SYNTAX Integer32
                        MAX-ACCESS read-write
                        STATUS current
                        DESCRIPTION
                                "The max-frame"
                        ::= { fkGponProfile2BridgeUniControl 20 }

                
--  1.3.6.1.4.1.10428 9 1.101.23.51.6.2.21
                -- 1.3.6.1.4.1.10428 9 1.101.23.51.6.2.21
                fkGponProfile2BridgeUniControlMcastProfile OBJECT-TYPE
                        SYNTAX OCTET STRING
                        MAX-ACCESS read-write
                        STATUS current
                        DESCRIPTION
                                "The multicast profile name"
                        ::= { fkGponProfile2BridgeUniControl 21 }

                
--  1.3.6.1.4.1.10428 9 1.101.23.51.6.2.22
                -- 1.3.6.1.4.1.10428 9 1.101.23.51.6.2.22
                fkGponProfile2BridgeUniControlVlanFilterMode OBJECT-TYPE
                        SYNTAX INTEGER
                                {
                                allow(1),
                                deny(2)
                                }
                        MAX-ACCESS read-write
                        STATUS current
                        DESCRIPTION
                                "Allow or deny that untagged fowarding operation "
                        ::= { fkGponProfile2BridgeUniControl 22 }

                
--  1.3.6.1.4.1.10428 9 1.101.23.51.6.2.23
                -- 1.3.6.1.4.1.10428 9 1.101.23.51.6.2.23
                fkGponProfile2BridgeUniControlVlanFilter OBJECT-TYPE
                        SYNTAX OCTET STRING
                        MAX-ACCESS read-write
                        STATUS current
                        DESCRIPTION
                                "The vlan-filter VID list."
                        ::= { fkGponProfile2BridgeUniControl 23 }

                
--  1.3.6.1.4.1.10428 9 1.101.23.51.6.2.24
                -- 1.3.6.1.4.1.10428 9 1.101.23.51.6.2.24
                fkGponProfile2BridgeUniControlIpMode OBJECT-TYPE
                        SYNTAX INTEGER
                                {
                                static(1),
                                dhcp(2),
                                none(3)
                                }
                        MAX-ACCESS read-write
                        STATUS current
                        DESCRIPTION
                                "The IP mode."
                        ::= { fkGponProfile2BridgeUniControl 24 }

                
--  1.3.6.1.4.1.10428 9 1.101.23.51.6.2.25
                -- 1.3.6.1.4.1.10428 9 1.101.23.51.6.2.25
                fkGponProfile2BridgeUniControlDns1 OBJECT-TYPE
                        SYNTAX IpAddress
                        MAX-ACCESS read-write
                        STATUS current
                        DESCRIPTION
                                "The DNS address 1."
                        ::= { fkGponProfile2BridgeUniControl 25 }

                
--  1.3.6.1.4.1.10428 9 1.101.23.51.6.2.26
                -- 1.3.6.1.4.1.10428 9 1.101.23.51.6.2.26
                fkGponProfile2BridgeUniControlDns2 OBJECT-TYPE
                        SYNTAX IpAddress
                        MAX-ACCESS read-write
                        STATUS current
                        DESCRIPTION
                                "The DNS address 2."
                        ::= { fkGponProfile2BridgeUniControl 26 }

                
--  1.3.6.1.4.1.10428 9 1.101.23.51.6.2.27
                -- 1.3.6.1.4.1.10428 9 1.101.23.51.6.2.27
                fkGponProfile2BridgeUniControlVoIPProfile OBJECT-TYPE
                        SYNTAX OCTET STRING
                        MAX-ACCESS read-write
                        STATUS current
                        DESCRIPTION
                                "The VoIP profile name."
                        ::= { fkGponProfile2BridgeUniControl 27 }

                
                -- 1.3.6.1.4.1.10428 9 1.101.23.51.6.2.28
                fkGponProfile2BridgeUniControlMaxHost OBJECT-TYPE
                        SYNTAX INTEGER (1..65535)
                        MAX-ACCESS read-write
                        STATUS current
                        DESCRIPTION
                                "The UNI max host."
                        ::= { fkGponProfile2BridgeUniControl 28 }

                
                -- 1.3.6.1.4.1.10428 9 1.101.23.51.6.2.29
                fkGponProfile2BridgeUniControlExtVlanName OBJECT-TYPE
                        SYNTAX OCTET STRING
                        MAX-ACCESS read-write
                        STATUS current
                        DESCRIPTION
                                "The Extended vlan name."
                        ::= { fkGponProfile2BridgeUniControl 29 }

                
                -- 1.3.6.1.4.1.10428 9 1.101.23.51.6.2.30
                fkGponProfile2BridgeUniControlMcastRateLimit OBJECT-TYPE
                        SYNTAX Integer32 (0..1031616)
                        MAX-ACCESS read-write
                        STATUS current
                        DESCRIPTION
                                "The multicast rate-limit bandwidth (Bandwidth in steps of 8Kbps), 0 is disable"
                        ::= { fkGponProfile2BridgeUniControl 30 }

                
                -- 1.3.6.1.4.1.10428 9 1.101.23.51.6.2.31
                fkGponProfile2BridgeUniControlMacFilterPreassign OBJECT-TYPE
                        SYNTAX BITS
                                {
                                ipv4Multicast(0),
                                ipv6Multicast(1),
                                ipv4Broadcast(2),
                                rarp(3),
                                ipx(4),
                                netBEUI(5),
                                appleTalk(6),
                                bridgeManagementInformation(7),
                                arp(8),
                                pppoeBroadcast(9)
                                }
                        MAX-ACCESS read-write
                        STATUS current
                        DESCRIPTION
                                "MAC Filter Preassign Table
                                0 -> forward
                                1 -> filter"
                        ::= { fkGponProfile2BridgeUniControl 31 }

                
                -- 1.3.6.1.4.1.10428 9 1.101.23.51.6.2.32
                fkGponProfile2BridgeUniControlRateLimitProfile OBJECT-TYPE
                        SYNTAX OCTET STRING
                        MAX-ACCESS read-write
                        STATUS current
                        DESCRIPTION
                                "The rate-limit profile name."
                        ::= { fkGponProfile2BridgeUniControl 32 }

                
--  1.3.6.1.4.1.10428 9 1.101.23.51.6.3
                -- 1.3.6.1.4.1.10428 9 1.101.23.51.6.3
                fkGponProfile2BridgeUniNotification OBJECT IDENTIFIER ::= { fkGponProfile2BridgeUni 3 }

                
--  1.3.6.1.4.1.10428 9 1.101.23.51.6.3.1
                -- 1.3.6.1.4.1.10428 9 1.101.23.51.6.3.1
                fkGponProfile2BridgeUniAdded NOTIFICATION-TYPE
                        OBJECTS { fkGponProfile2BridgeUniControlRequest, fkGponProfile2BridgeUniControlStatus, fkGponProfile2BridgeUniControlTimer, fkGponProfile2BridgeUniControlTimeStamp, fkGponProfile2BridgeUniControlReqResult, 
                                fkGponProfile2BridgeUniControlTName, fkGponProfile2BridgeUniControlBridgeId, fkGponProfile2BridgeUniControlType, fkGponProfile2BridgeUniControlId }
                        STATUS current
                        DESCRIPTION 
                                "Description."
                        ::= { fkGponProfile2BridgeUniNotification 1 }

                
--  1.3.6.1.4.1.10428 9 1.101.23.51.6.3.2
                -- 1.3.6.1.4.1.10428 9 1.101.23.51.6.3.2
                fkGponProfile2BridgeUniDeleted NOTIFICATION-TYPE
                        OBJECTS { fkGponProfile2BridgeUniControlRequest, fkGponProfile2BridgeUniControlStatus, fkGponProfile2BridgeUniControlTimer, fkGponProfile2BridgeUniControlTimeStamp, fkGponProfile2BridgeUniControlReqResult, 
                                fkGponProfile2BridgeUniControlTName, fkGponProfile2BridgeUniControlBridgeId, fkGponProfile2BridgeUniControlType, fkGponProfile2BridgeUniControlId }
                        STATUS current
                        DESCRIPTION 
                                "Description."
                        ::= { fkGponProfile2BridgeUniNotification 2 }

                
--  1.3.6.1.4.1.10428 9 1.101.23.51.6.3.3
                -- 1.3.6.1.4.1.10428 9 1.101.23.51.6.3.3
                fkGponProfile2BridgeUniVlanDsOpChanged NOTIFICATION-TYPE
                        OBJECTS { fkGponProfile2BridgeUniControlRequest, fkGponProfile2BridgeUniControlStatus, fkGponProfile2BridgeUniControlTimer, fkGponProfile2BridgeUniControlTimeStamp, fkGponProfile2BridgeUniControlReqResult, 
                                fkGponProfile2BridgeUniControlTName, fkGponProfile2BridgeUniControlBridgeId, fkGponProfile2BridgeUniControlType, fkGponProfile2BridgeUniControlId, fkGponProfile2BridgeUniControlVlanOpDsOperFlag
                                 }
                        STATUS current
                        DESCRIPTION 
                                "Description."
                        ::= { fkGponProfile2BridgeUniNotification 3 }

                
--  1.3.6.1.4.1.10428 9 1.101.23.51.6.3.4
                -- 1.3.6.1.4.1.10428 9 1.101.23.51.6.3.4
                fkGponProfile2BridgeUniVlanUsOpChanged NOTIFICATION-TYPE
                        OBJECTS { fkGponProfile2BridgeUniControlRequest, fkGponProfile2BridgeUniControlStatus, fkGponProfile2BridgeUniControlTimer, fkGponProfile2BridgeUniControlTimeStamp, fkGponProfile2BridgeUniControlReqResult, 
                                fkGponProfile2BridgeUniControlTName, fkGponProfile2BridgeUniControlBridgeId, fkGponProfile2BridgeUniControlType, fkGponProfile2BridgeUniControlId, fkGponProfile2BridgeUniControlVlanOpUsOperFlag, 
                                fkGponProfile2BridgeUniControlVlanOpUsOperVid, fkGponProfile2BridgeUniControlVlanOpUsOperCos }
                        STATUS current
                        DESCRIPTION 
                                "Description."
                        ::= { fkGponProfile2BridgeUniNotification 4 }

                
--  1.3.6.1.4.1.10428 9 1.101.23.51.6.3.5
                -- 1.3.6.1.4.1.10428 9 1.101.23.51.6.3.5
                fkGponProfile2BridgeUniPortAdminChanged NOTIFICATION-TYPE
                        OBJECTS { fkGponProfile2BridgeUniControlRequest, fkGponProfile2BridgeUniControlStatus, fkGponProfile2BridgeUniControlTimer, fkGponProfile2BridgeUniControlTimeStamp, fkGponProfile2BridgeUniControlReqResult, 
                                fkGponProfile2BridgeUniControlTName, fkGponProfile2BridgeUniControlBridgeId, fkGponProfile2BridgeUniControlType, fkGponProfile2BridgeUniControlId, fkGponProfile2BridgeUniControlPortAdmin
                                 }
                        STATUS current
                        DESCRIPTION 
                                "Description."
                        ::= { fkGponProfile2BridgeUniNotification 5 }

                
--  1.3.6.1.4.1.10428 9 1.101.23.51.6.3.6
                -- 1.3.6.1.4.1.10428 9 1.101.23.51.6.3.6
                fkGponProfile2BridgeUniRateLimitChanged NOTIFICATION-TYPE
                        OBJECTS { fkGponProfile2BridgeUniControlRequest, fkGponProfile2BridgeUniControlStatus, fkGponProfile2BridgeUniControlTimer, fkGponProfile2BridgeUniControlTimeStamp, fkGponProfile2BridgeUniControlReqResult, 
                                fkGponProfile2BridgeUniControlTName, fkGponProfile2BridgeUniControlBridgeId, fkGponProfile2BridgeUniControlType, fkGponProfile2BridgeUniControlId, fkGponProfile2BridgeUniControlRateLimitDownSir, 
                                fkGponProfile2BridgeUniControlRateLimitDownPir, fkGponProfile2BridgeUniControlRateLimitUpSir, fkGponProfile2BridgeUniControlRateLimitUpPir }
                        STATUS current
                        DESCRIPTION 
                                "Description."
                        ::= { fkGponProfile2BridgeUniNotification 6 }

                
--  1.3.6.1.4.1.10428 9 1.101.23.51.6.3.7
                -- 1.3.6.1.4.1.10428 9 1.101.23.51.6.3.7
                fkGponProfile2BridgeUniIgmpMaxGroupChanged NOTIFICATION-TYPE
                        OBJECTS { fkGponProfile2BridgeUniControlRequest, fkGponProfile2BridgeUniControlStatus, fkGponProfile2BridgeUniControlTimer, fkGponProfile2BridgeUniControlTimeStamp, fkGponProfile2BridgeUniControlReqResult, 
                                fkGponProfile2BridgeUniControlTName, fkGponProfile2BridgeUniControlBridgeId, fkGponProfile2BridgeUniControlType, fkGponProfile2BridgeUniControlId, fkGponProfile2BridgeUniControlIgmpMaxGroup
                                 }
                        STATUS current
                        DESCRIPTION 
                                "Description."
                        ::= { fkGponProfile2BridgeUniNotification 7 }

                
--  1.3.6.1.4.1.10428 9 1.101.23.51.6.3.8
                -- 1.3.6.1.4.1.10428 9 1.101.23.51.6.3.8
                fkGponProfile2BridgeUniMaxFrameChanged NOTIFICATION-TYPE
                        OBJECTS { fkGponProfile2BridgeUniControlRequest, fkGponProfile2BridgeUniControlStatus, fkGponProfile2BridgeUniControlTimer, fkGponProfile2BridgeUniControlTimeStamp, fkGponProfile2BridgeUniControlReqResult, 
                                fkGponProfile2BridgeUniControlTName, fkGponProfile2BridgeUniControlBridgeId, fkGponProfile2BridgeUniControlType, fkGponProfile2BridgeUniControlId, fkGponProfile2BridgeUniControlMaxFrame
                                 }
                        STATUS current
                        DESCRIPTION 
                                "Description."
                        ::= { fkGponProfile2BridgeUniNotification 8 }

                
--  1.3.6.1.4.1.10428 9 1.101.23.51.6.3.9
                -- 1.3.6.1.4.1.10428 9 1.101.23.51.6.3.9
                fkGponProfile2BridgeUniMcastProfileChanged NOTIFICATION-TYPE
                        OBJECTS { fkGponProfile2BridgeUniControlRequest, fkGponProfile2BridgeUniControlStatus, fkGponProfile2BridgeUniControlTimer, fkGponProfile2BridgeUniControlTimeStamp, fkGponProfile2BridgeUniControlReqResult, 
                                fkGponProfile2BridgeUniControlTName, fkGponProfile2BridgeUniControlBridgeId, fkGponProfile2BridgeUniControlType, fkGponProfile2BridgeUniControlId, fkGponProfile2BridgeUniControlMcastProfile
                                 }
                        STATUS current
                        DESCRIPTION 
                                "Description."
                        ::= { fkGponProfile2BridgeUniNotification 9 }

                
--  1.3.6.1.4.1.10428 9 1.101.23.51.6.3.10
                -- 1.3.6.1.4.1.10428 9 1.101.23.51.6.3.10
                fkGponProfile2BridgeUniVlanFilterChanged NOTIFICATION-TYPE
                        OBJECTS { fkGponProfile2BridgeUniControlRequest, fkGponProfile2BridgeUniControlStatus, fkGponProfile2BridgeUniControlTimer, fkGponProfile2BridgeUniControlTimeStamp, fkGponProfile2BridgeUniControlReqResult, 
                                fkGponProfile2BridgeUniControlTName, fkGponProfile2BridgeUniControlBridgeId, fkGponProfile2BridgeUniControlType, fkGponProfile2BridgeUniControlId, fkGponProfile2BridgeUniControlVlanFilterMode, 
                                fkGponProfile2BridgeUniControlVlanFilter }
                        STATUS current
                        DESCRIPTION 
                                "Description."
                        ::= { fkGponProfile2BridgeUniNotification 10 }

                
--  1.3.6.1.4.1.10428 9 1.101.23.51.6.3.11
                -- 1.3.6.1.4.1.10428 9 1.101.23.51.6.3.11
                fkGponProfile2BridgeUniIpInfoChanged NOTIFICATION-TYPE
                        OBJECTS { fkGponProfile2BridgeUniControlRequest, fkGponProfile2BridgeUniControlTimeStamp, fkGponProfile2BridgeUniControlReqResult, fkGponProfile2BridgeUniControlTName, fkGponProfile2BridgeUniControlBridgeId, 
                                fkGponProfile2BridgeUniControlType, fkGponProfile2BridgeUniControlId, fkGponProfile2BridgeUniControlIpMode, fkGponProfile2BridgeUniControlDns1, fkGponProfile2BridgeUniControlDns2
                                 }
                        STATUS current
                        DESCRIPTION 
                                "Description."
                        ::= { fkGponProfile2BridgeUniNotification 11 }

                
--  1.3.6.1.4.1.10428 9 1.101.23.51.6.3.12
                -- 1.3.6.1.4.1.10428 9 1.101.23.51.6.3.12
                fkGponProfile2BridgeUniVoipProfileChanged NOTIFICATION-TYPE
                        OBJECTS { fkGponProfile2BridgeAniControlRequest, fkGponProfile2BridgeAniControlTimeStamp, fkGponProfile2BridgeAniControlReqResult, fkGponProfile2BridgeAniControlTName, fkGponProfile2BridgeAniControlBridgeId, 
                                fkGponProfile2BridgeAniControlId, fkGponProfile2BridgeUniControlVoIPProfile }
                        STATUS current
                        DESCRIPTION 
                                "Description."
                        ::= { fkGponProfile2BridgeUniNotification 12 }

                
--  1.3.6.1.4.1.10428 9 1.101.23.51.6.3.12
                -- 1.3.6.1.4.1.10428 9 1.101.23.51.6.3.13
                fkGponProfile2BridgeUniMaxHostChanged NOTIFICATION-TYPE
                        OBJECTS { fkGponProfile2BridgeAniControlRequest, fkGponProfile2BridgeAniControlTimeStamp, fkGponProfile2BridgeAniControlReqResult, fkGponProfile2BridgeAniControlTName, fkGponProfile2BridgeAniControlBridgeId, 
                                fkGponProfile2BridgeAniControlId, fkGponProfile2BridgeUniControlMaxHost }
                        STATUS current
                        DESCRIPTION 
                                "Description."
                        ::= { fkGponProfile2BridgeUniNotification 13 }

                
                -- 1.3.6.1.4.1.10428 9 1.101.23.51.6.3.14
                fkGponProfile2BridgeUniExtendedVlanChanged NOTIFICATION-TYPE
                        OBJECTS { fkGponProfile2BridgeUniControlRequest, fkGponProfile2BridgeUniControlTimeStamp, fkGponProfile2BridgeUniControlReqResult, fkGponProfile2BridgeUniControlBridgeId, fkGponProfile2BridgeUniControlType, 
                                fkGponProfile2BridgeUniControlId, fkGponProfile2BridgeUniControlExtVlanName }
                        STATUS current
                        DESCRIPTION 
                                "setExtendedVlan"
                        ::= { fkGponProfile2BridgeUniNotification 14 }

                
                -- 1.3.6.1.4.1.10428 9 1.101.23.51.6.3.15
                fkGponProfile2BridgeUniMcastRateLimitChanged NOTIFICATION-TYPE
                        OBJECTS { fkGponProfile2BridgeUniControlRequest, fkGponProfile2BridgeUniControlTimeStamp, fkGponProfile2BridgeUniControlReqResult, fkGponProfile2BridgeUniControlBridgeId, fkGponProfile2BridgeUniControlType, 
                                fkGponProfile2BridgeUniControlId, fkGponProfile2BridgeUniControlMcastRateLimit }
                        STATUS current
                        DESCRIPTION 
                                "setExtendedVlan"
                        ::= { fkGponProfile2BridgeUniNotification 15 }

                
--  1.3.6.1.4.1.10428 9 1.101.23.51.6.3.5
                -- 1.3.6.1.4.1.10428 9 1.101.23.51.6.3.16
                fkGponProfile2BridgeUniMacFilterPreassignChanged NOTIFICATION-TYPE
                        OBJECTS { fkGponProfile2BridgeUniControlRequest, fkGponProfile2BridgeUniControlTimeStamp, fkGponProfile2BridgeUniControlReqResult, fkGponProfile2BridgeUniControlTName, fkGponProfile2BridgeUniControlBridgeId, 
                                fkGponProfile2BridgeUniControlType, fkGponProfile2BridgeUniControlId, fkGponProfile2BridgeUniControlMacFilterPreassign }
                        STATUS current
                        DESCRIPTION 
                                "setUniMacFilterPreassign"
                        ::= { fkGponProfile2BridgeUniNotification 16 }

                
--  1.3.6.1.4.1.10428 9 1.101.23.51.6.3.5
                -- 1.3.6.1.4.1.10428 9 1.101.23.51.6.3.17
                fkGponProfile2BridgeUniRateLimitProfileChanged NOTIFICATION-TYPE
                        OBJECTS { fkGponProfile2BridgeUniControlRequest, fkGponProfile2BridgeUniControlTimeStamp, fkGponProfile2BridgeUniControlReqResult, fkGponProfile2BridgeUniControlTName, fkGponProfile2BridgeUniControlBridgeId, 
                                fkGponProfile2BridgeUniControlType, fkGponProfile2BridgeUniControlId, fkGponProfile2BridgeUniControlRateLimitProfile }
                        STATUS current
                        DESCRIPTION 
                                "setUniRateLimitProfile"
                        ::= { fkGponProfile2BridgeUniNotification 17 }

                
--  1.3.6.1.4.1.10428 9 1.101.23.51.7
                -- 1.3.6.1.4.1.10428 9 1.101.23.51.7
                fkGponProfile2Tcont OBJECT IDENTIFIER ::= { fkGponProfile2 7 }

                
--  1.3.6.1.4.1.10428 9 1.101.23.51.7.1
                -- 1.3.6.1.4.1.10428 9 1.101.23.51.7.1
                fkGponProfile2TcontTable OBJECT-TYPE
                        SYNTAX SEQUENCE OF FkGponProfile2TcontEntry
                        MAX-ACCESS not-accessible
                        STATUS current
                        DESCRIPTION
                                "fkGponProfile2TcontTable"
                        ::= { fkGponProfile2Tcont 1 }

                
--  1.3.6.1.4.1.10428 9 1.101.23.51.7.1.1
                -- 1.3.6.1.4.1.10428 9 1.101.23.51.7.1.1
                fkGponProfile2TcontEntry OBJECT-TYPE
                        SYNTAX FkGponProfile2TcontEntry
                        MAX-ACCESS not-accessible
                        STATUS current
                        DESCRIPTION
                                "key: fkGponProfile2TrafficIndex, fkGponProfile2TcontId"
                        INDEX { fkGponProfile2TrafficIndex, fkGponProfile2TcontId }
                        ::= { fkGponProfile2TcontTable 1 }

                
                FkGponProfile2TcontEntry ::=
                        SEQUENCE { 
                                fkGponProfile2TcontId
                                        Integer32,
                                fkGponProfile2TcontDbaProfile
                                        OCTET STRING,
                                fkGponProfile2TcontQueue1Weight
                                        Integer32,
                                fkGponProfile2TcontQueue2Weight
                                        Integer32,
                                fkGponProfile2TcontQueue3Weight
                                        Integer32,
                                fkGponProfile2TcontQueue4Weight
                                        Integer32,
                                fkGponProfile2TcontQueue5Weight
                                        Integer32,
                                fkGponProfile2TcontQueue6Weight
                                        Integer32,
                                fkGponProfile2TcontQueue7Weight
                                        Integer32,
                                fkGponProfile2TcontQueue8Weight
                                        Integer32
                         }

--  1.3.6.1.4.1.10428 9 1.101.23.51.7.1.1.1
                -- 1.3.6.1.4.1.10428 9 1.101.23.51.7.1.1.1
                fkGponProfile2TcontId OBJECT-TYPE
                        SYNTAX Integer32 (1..65535)
                        MAX-ACCESS read-only
                        STATUS current
                        DESCRIPTION
                                "The Tcont ID"
                        ::= { fkGponProfile2TcontEntry 1 }

                
--  1.3.6.1.4.1.10428 9 1.101.23.51.7.1.1.2
                -- 1.3.6.1.4.1.10428 9 1.101.23.51.7.1.1.2
                fkGponProfile2TcontDbaProfile OBJECT-TYPE
                        SYNTAX OCTET STRING
                        MAX-ACCESS read-only
                        STATUS current
                        DESCRIPTION
                                "The DBA profile"
                        ::= { fkGponProfile2TcontEntry 2 }

                
                -- 1.3.6.1.4.1.10428 9 1.101.23.51.7.1.1.3
                fkGponProfile2TcontQueue1Weight OBJECT-TYPE
                        SYNTAX Integer32 (1..255)
                        MAX-ACCESS read-only
                        STATUS current
                        DESCRIPTION
                                "The queue weight"
                        ::= { fkGponProfile2TcontEntry 3 }

                
                -- 1.3.6.1.4.1.10428 9 1.101.23.51.7.1.1.4
                fkGponProfile2TcontQueue2Weight OBJECT-TYPE
                        SYNTAX Integer32 (1..255)
                        MAX-ACCESS read-only
                        STATUS current
                        DESCRIPTION
                                "The queue weight"
                        ::= { fkGponProfile2TcontEntry 4 }

                
                -- 1.3.6.1.4.1.10428 9 1.101.23.51.7.1.1.5
                fkGponProfile2TcontQueue3Weight OBJECT-TYPE
                        SYNTAX Integer32 (1..255)
                        MAX-ACCESS read-only
                        STATUS current
                        DESCRIPTION
                                "The queue weight"
                        ::= { fkGponProfile2TcontEntry 5 }

                
                -- 1.3.6.1.4.1.10428 9 1.101.23.51.7.1.1.6
                fkGponProfile2TcontQueue4Weight OBJECT-TYPE
                        SYNTAX Integer32 (1..255)
                        MAX-ACCESS read-only
                        STATUS current
                        DESCRIPTION
                                "The queue weight"
                        ::= { fkGponProfile2TcontEntry 6 }

                
                -- 1.3.6.1.4.1.10428 9 1.101.23.51.7.1.1.7
                fkGponProfile2TcontQueue5Weight OBJECT-TYPE
                        SYNTAX Integer32 (1..255)
                        MAX-ACCESS read-only
                        STATUS current
                        DESCRIPTION
                                "The queue weight"
                        ::= { fkGponProfile2TcontEntry 7 }

                
                -- 1.3.6.1.4.1.10428 9 1.101.23.51.7.1.1.8
                fkGponProfile2TcontQueue6Weight OBJECT-TYPE
                        SYNTAX Integer32 (1..255)
                        MAX-ACCESS read-only
                        STATUS current
                        DESCRIPTION
                                "The queue weight"
                        ::= { fkGponProfile2TcontEntry 8 }

                
                -- 1.3.6.1.4.1.10428 9 1.101.23.51.7.1.1.9
                fkGponProfile2TcontQueue7Weight OBJECT-TYPE
                        SYNTAX Integer32 (1..255)
                        MAX-ACCESS read-only
                        STATUS current
                        DESCRIPTION
                                "The queue weight"
                        ::= { fkGponProfile2TcontEntry 9 }

                
                -- 1.3.6.1.4.1.10428 9 1.101.23.51.7.1.1.10
                fkGponProfile2TcontQueue8Weight OBJECT-TYPE
                        SYNTAX Integer32 (1..255)
                        MAX-ACCESS read-only
                        STATUS current
                        DESCRIPTION
                                "The queue weight"
                        ::= { fkGponProfile2TcontEntry 10 }

                
--  1.3.6.1.4.1.10428 9 1.101.23.51.7.2
                -- 1.3.6.1.4.1.10428 9 1.101.23.51.7.2
                fkGponProfile2TcontControl OBJECT IDENTIFIER ::= { fkGponProfile2Tcont 2 }

                
--  1.3.6.1.4.1.10428 9 1.101.23.51.7.2.1
                -- 1.3.6.1.4.1.10428 9 1.101.23.51.7.2.1
                fkGponProfile2TcontControlRequest OBJECT-TYPE
                        SYNTAX INTEGER
                                {
                                addTcont(1),
                                delTacont(2),
                                setDbaProfile(3),
                                setQueueWeight(4)
                                }
                        MAX-ACCESS read-write
                        STATUS current
                        DESCRIPTION
                                "The request of a user command"
                        ::= { fkGponProfile2TcontControl 1 }

                
--  1.3.6.1.4.1.10428 9 1.101.23.51.7.2.2
                -- 1.3.6.1.4.1.10428 9 1.101.23.51.7.2.2
                fkGponProfile2TcontControlStatus OBJECT-TYPE
                        SYNTAX FkControlStatusType
                        MAX-ACCESS read-write
                        STATUS current
                        DESCRIPTION
                                "The status of user command"
                        ::= { fkGponProfile2TcontControl 2 }

                
--  1.3.6.1.4.1.10428 9 1.101.23.51.7.2.3
                -- 1.3.6.1.4.1.10428 9 1.101.23.51.7.2.3
                fkGponProfile2TcontControlTimer OBJECT-TYPE
                        SYNTAX Gauge32
                        MAX-ACCESS read-write
                        STATUS current
                        DESCRIPTION
                                "The maximum time for the manager for a long running user command"
                        ::= { fkGponProfile2TcontControl 3 }

                
--  1.3.6.1.4.1.10428 9 1.101.23.51.7.2.4
                -- 1.3.6.1.4.1.10428 9 1.101.23.51.7.2.4
                fkGponProfile2TcontControlTimeStamp OBJECT-TYPE
                        SYNTAX TimeTicks
                        MAX-ACCESS read-write
                        STATUS current
                        DESCRIPTION
                                "The time stamp of the last command(end of command)"
                        ::= { fkGponProfile2TcontControl 4 }

                
--  1.3.6.1.4.1.10428 9 1.101.23.51.7.2.5
                -- 1.3.6.1.4.1.10428 9 1.101.23.51.7.2.5
                fkGponProfile2TcontControlReqResult OBJECT-TYPE
                        SYNTAX FkControlRequestResultType
                        MAX-ACCESS read-write
                        STATUS current
                        DESCRIPTION
                                "The result of the last user command"
                        ::= { fkGponProfile2TcontControl 5 }

                
--  1.3.6.1.4.1.10428 9 1.101.23.51.7.2.6
                -- 1.3.6.1.4.1.10428 9 1.101.23.51.7.2.6
                fkGponProfile2TcontControlTName OBJECT-TYPE
                        SYNTAX OCTET STRING
                        MAX-ACCESS read-write
                        STATUS current
                        DESCRIPTION
                                "The Traffic profile name."
                        ::= { fkGponProfile2TcontControl 6 }

                
--  1.3.6.1.4.1.10428 9 1.101.23.51.7.2.7
                -- 1.3.6.1.4.1.10428 9 1.101.23.51.7.2.7
                fkGponProfile2TcontControlID OBJECT-TYPE
                        SYNTAX Integer32
                        MAX-ACCESS read-write
                        STATUS current
                        DESCRIPTION
                                "The tcont ID"
                        ::= { fkGponProfile2TcontControl 7 }

                
--  1.3.6.1.4.1.10428 9 1.101.23.51.7.2.8
                -- 1.3.6.1.4.1.10428 9 1.101.23.51.7.2.8
                fkGponProfile2TcontControlDbaProfile OBJECT-TYPE
                        SYNTAX OCTET STRING
                        MAX-ACCESS read-write
                        STATUS current
                        DESCRIPTION
                                "The DBA profile"
                        ::= { fkGponProfile2TcontControl 8 }

                
                -- 1.3.6.1.4.1.10428 9 1.101.23.51.7.2.9
                fkGponProfile2TcontControlQueue1Weight OBJECT-TYPE
                        SYNTAX Integer32 (1..255)
                        MAX-ACCESS read-write
                        STATUS current
                        DESCRIPTION
                                "The queue weight"
                        ::= { fkGponProfile2TcontControl 9 }

                
                -- 1.3.6.1.4.1.10428 9 1.101.23.51.7.2.10
                fkGponProfile2TcontControlQueue2Weight OBJECT-TYPE
                        SYNTAX Integer32 (1..255)
                        MAX-ACCESS read-write
                        STATUS current
                        DESCRIPTION
                                "The queue weight"
                        ::= { fkGponProfile2TcontControl 10 }

                
                -- 1.3.6.1.4.1.10428 9 1.101.23.51.7.2.11
                fkGponProfile2TcontControlQueue3Weight OBJECT-TYPE
                        SYNTAX Integer32 (1..255)
                        MAX-ACCESS read-write
                        STATUS current
                        DESCRIPTION
                                "The queue weight"
                        ::= { fkGponProfile2TcontControl 11 }

                
                -- 1.3.6.1.4.1.10428 9 1.101.23.51.7.2.12
                fkGponProfile2TcontControlQueue4Weight OBJECT-TYPE
                        SYNTAX Integer32 (1..255)
                        MAX-ACCESS read-write
                        STATUS current
                        DESCRIPTION
                                "The queue weight"
                        ::= { fkGponProfile2TcontControl 12 }

                
                -- 1.3.6.1.4.1.10428 9 1.101.23.51.7.2.13
                fkGponProfile2TcontControlQueue5Weight OBJECT-TYPE
                        SYNTAX Integer32 (1..255)
                        MAX-ACCESS read-write
                        STATUS current
                        DESCRIPTION
                                "The queue weight"
                        ::= { fkGponProfile2TcontControl 13 }

                
                -- 1.3.6.1.4.1.10428 9 1.101.23.51.7.2.14
                fkGponProfile2TcontControlQueue6Weight OBJECT-TYPE
                        SYNTAX Integer32 (1..255)
                        MAX-ACCESS read-write
                        STATUS current
                        DESCRIPTION
                                "The queue weight"
                        ::= { fkGponProfile2TcontControl 14 }

                
                -- 1.3.6.1.4.1.10428 9 1.101.23.51.7.2.15
                fkGponProfile2TcontControlQueue7Weight OBJECT-TYPE
                        SYNTAX Integer32 (1..255)
                        MAX-ACCESS read-write
                        STATUS current
                        DESCRIPTION
                                "The queue weight"
                        ::= { fkGponProfile2TcontControl 15 }

                
                -- 1.3.6.1.4.1.10428 9 1.101.23.51.7.2.16
                fkGponProfile2TcontControlQueue8Weight OBJECT-TYPE
                        SYNTAX Integer32 (1..255)
                        MAX-ACCESS read-write
                        STATUS current
                        DESCRIPTION
                                "The queue weight"
                        ::= { fkGponProfile2TcontControl 16 }

                
--  1.3.6.1.4.1.10428 9 1.101.23.51.7.3
                -- 1.3.6.1.4.1.10428 9 1.101.23.51.7.3
                fkGponProfile2TcontNotification OBJECT IDENTIFIER ::= { fkGponProfile2Tcont 3 }

                
--  1.3.6.1.4.1.10428 9 1.101.23.51.7.3.1
                -- 1.3.6.1.4.1.10428 9 1.101.23.51.7.3.1
                fkGponProfile2TcontAdded NOTIFICATION-TYPE
                        OBJECTS { fkGponProfile2TcontControlRequest, fkGponProfile2TcontControlTimeStamp, fkGponProfile2TcontControlReqResult, fkGponProfile2TcontControlTName, fkGponProfile2TcontControlID, 
                                fkGponProfile2TcontControlDbaProfile }
                        STATUS current
                        DESCRIPTION 
                                "addTcont"
                        ::= { fkGponProfile2TcontNotification 1 }

                
--  1.3.6.1.4.1.10428 9 1.101.23.51.7.3.1
                -- 1.3.6.1.4.1.10428 9 1.101.23.51.7.3.2
                fkGponProfile2TcontDeleted NOTIFICATION-TYPE
                        OBJECTS { fkGponProfile2TcontControlRequest, fkGponProfile2TcontControlTimeStamp, fkGponProfile2TcontControlReqResult, fkGponProfile2TcontControlTName, fkGponProfile2TcontControlID
                                 }
                        STATUS current
                        DESCRIPTION 
                                "delTacont"
                        ::= { fkGponProfile2TcontNotification 2 }

                
--  1.3.6.1.4.1.10428 9 1.101.23.51.7.3.1
                -- 1.3.6.1.4.1.10428 9 1.101.23.51.7.3.3
                fkGponProfile2TcontDbaChanged NOTIFICATION-TYPE
                        OBJECTS { fkGponProfile2TcontControlRequest, fkGponProfile2TcontControlTimeStamp, fkGponProfile2TcontControlReqResult, fkGponProfile2TcontControlTName, fkGponProfile2TcontControlID, 
                                fkGponProfile2TcontControlDbaProfile }
                        STATUS current
                        DESCRIPTION 
                                "setDbaProfile"
                        ::= { fkGponProfile2TcontNotification 3 }

                
                -- 1.3.6.1.4.1.10428 9 1.101.23.51.7.3.4
                fkGponProfile2TcontQueueWeight NOTIFICATION-TYPE
                        OBJECTS { fkGponProfile2TcontControlRequest, fkGponProfile2TcontControlTimeStamp, fkGponProfile2TcontControlReqResult, fkGponProfile2TcontControlTName, fkGponProfile2TcontControlID, 
                                fkGponProfile2TcontControlDbaProfile, fkGponProfile2TcontControlQueue1Weight, fkGponProfile2TcontControlQueue2Weight, fkGponProfile2TcontControlQueue3Weight, fkGponProfile2TcontControlQueue4Weight, 
                                fkGponProfile2TcontControlQueue5Weight, fkGponProfile2TcontControlQueue6Weight, fkGponProfile2TcontControlQueue7Weight, fkGponProfile2TcontControlQueue8Weight }
                        STATUS current
                        DESCRIPTION 
                                "setQueueWeight"
                        ::= { fkGponProfile2TcontNotification 4 }

                
--  1.3.6.1.4.1.10428 9 1.101.23.51.8
                -- 1.3.6.1.4.1.10428 9 1.101.23.51.8
                fkGponProfile2TcontGemport OBJECT IDENTIFIER ::= { fkGponProfile2 8 }

                
--  1.3.6.1.4.1.10428 9 1.101.23.51.8.1
                -- 1.3.6.1.4.1.10428 9 1.101.23.51.8.1
                fkGponProfile2TcontGemportTable OBJECT-TYPE
                        SYNTAX SEQUENCE OF FkGponProfile2TcontGemportEntry
                        MAX-ACCESS not-accessible
                        STATUS current
                        DESCRIPTION
                                "fkGponProfile2TcontGemportTable"
                        ::= { fkGponProfile2TcontGemport 1 }

                
--  1.3.6.1.4.1.10428 9 1.101.23.51.8.1.1
                -- 1.3.6.1.4.1.10428 9 1.101.23.51.8.1.1
                fkGponProfile2TcontGemportEntry OBJECT-TYPE
                        SYNTAX FkGponProfile2TcontGemportEntry
                        MAX-ACCESS not-accessible
                        STATUS current
                        DESCRIPTION
                                "key: fkGponProfile2TrafficIndex, fkGponProfile2TcontId, fkGponProfile2TcontGemportMapperId, fkGponProfile2TcontGemportId"
                        INDEX { fkGponProfile2TrafficIndex, fkGponProfile2TcontId, fkGponProfile2TcontGemportMapperId, fkGponProfile2TcontGemportId }
                        ::= { fkGponProfile2TcontGemportTable 1 }

                
                FkGponProfile2TcontGemportEntry ::=
                        SEQUENCE { 
                                fkGponProfile2TcontGemportMapperId
                                        Integer32,
                                fkGponProfile2TcontGemportId
                                        Integer32,
                                fkGponProfile2TcontGemportQueue
                                        Integer32
                         }

--  1.3.6.1.4.1.10428 9 1.101.23.51.8.1.1.1
                -- 1.3.6.1.4.1.10428 9 1.101.23.51.8.1.1.1
                fkGponProfile2TcontGemportMapperId OBJECT-TYPE
                        SYNTAX Integer32 (1..65535)
                        MAX-ACCESS read-only
                        STATUS current
                        DESCRIPTION
                                "The tcont mapper ID."
                        ::= { fkGponProfile2TcontGemportEntry 1 }

                
--  1.3.6.1.4.1.10428 9 1.101.23.51.8.1.1.2
                -- 1.3.6.1.4.1.10428 9 1.101.23.51.8.1.1.2
                fkGponProfile2TcontGemportId OBJECT-TYPE
                        SYNTAX Integer32 (1..65535)
                        MAX-ACCESS read-only
                        STATUS current
                        DESCRIPTION
                                "The Tcont gemport Id"
                        ::= { fkGponProfile2TcontGemportEntry 2 }

                
--  1.3.6.1.4.1.10428 9 1.101.23.51.8.1.1.3
                -- 1.3.6.1.4.1.10428 9 1.101.23.51.8.1.1.3
                fkGponProfile2TcontGemportQueue OBJECT-TYPE
                        SYNTAX Integer32 (0 | 1..8)
                        MAX-ACCESS read-only
                        STATUS current
                        DESCRIPTION
                                "The Tcont gemport Queue"
                        ::= { fkGponProfile2TcontGemportEntry 3 }

                
--  1.3.6.1.4.1.10428 9 1.101.23.51.8.2
                -- 1.3.6.1.4.1.10428 9 1.101.23.51.8.2
                fkGponProfile2TcontGemportControl OBJECT IDENTIFIER ::= { fkGponProfile2TcontGemport 2 }

                
--  1.3.6.1.4.1.10428 9 1.101.23.51.8.2.1
                -- 1.3.6.1.4.1.10428 9 1.101.23.51.8.2.1
                fkGponProfile2TcontGemportControlRequest OBJECT-TYPE
                        SYNTAX INTEGER
                                {
                                addTcontGemport(1),
                                delTcontGemport(2)
                                }
                        MAX-ACCESS read-write
                        STATUS current
                        DESCRIPTION
                                "The request of a user command"
                        ::= { fkGponProfile2TcontGemportControl 1 }

                
--  1.3.6.1.4.1.10428 9 1.101.23.51.8.2.2
                -- 1.3.6.1.4.1.10428 9 1.101.23.51.8.2.2
                fkGponProfile2TcontGemportControlStatus OBJECT-TYPE
                        SYNTAX FkControlStatusType
                        MAX-ACCESS read-write
                        STATUS current
                        DESCRIPTION
                                "The status of user command"
                        ::= { fkGponProfile2TcontGemportControl 2 }

                
--  1.3.6.1.4.1.10428 9 1.101.23.51.8.2.3
                -- 1.3.6.1.4.1.10428 9 1.101.23.51.8.2.3
                fkGponProfile2TcontGemportControlTimer OBJECT-TYPE
                        SYNTAX Gauge32
                        MAX-ACCESS read-write
                        STATUS current
                        DESCRIPTION
                                "The maximum time for the manager for a long running user command"
                        ::= { fkGponProfile2TcontGemportControl 3 }

                
--  1.3.6.1.4.1.10428 9 1.101.23.51.8.2.4
                -- 1.3.6.1.4.1.10428 9 1.101.23.51.8.2.4
                fkGponProfile2TcontGemportControlTimeStamp OBJECT-TYPE
                        SYNTAX TimeTicks
                        MAX-ACCESS read-write
                        STATUS current
                        DESCRIPTION
                                "The time stamp of the last command(end of command)"
                        ::= { fkGponProfile2TcontGemportControl 4 }

                
--  1.3.6.1.4.1.10428 9 1.101.23.51.8.2.5
                -- 1.3.6.1.4.1.10428 9 1.101.23.51.8.2.5
                fkGponProfile2TcontGemportControlReqResult OBJECT-TYPE
                        SYNTAX FkControlRequestResultType
                        MAX-ACCESS read-write
                        STATUS current
                        DESCRIPTION
                                "The result of the last user command"
                        ::= { fkGponProfile2TcontGemportControl 5 }

                
--  1.3.6.1.4.1.10428 9 1.101.23.51.8.2.6
                -- 1.3.6.1.4.1.10428 9 1.101.23.51.8.2.6
                fkGponProfile2TcontGemportControlTName OBJECT-TYPE
                        SYNTAX OCTET STRING
                        MAX-ACCESS read-write
                        STATUS current
                        DESCRIPTION
                                "The Traffic profile name."
                        ::= { fkGponProfile2TcontGemportControl 6 }

                
--  1.3.6.1.4.1.10428 9 1.101.23.51.8.2.7
                -- 1.3.6.1.4.1.10428 9 1.101.23.51.8.2.7
                fkGponProfile2TcontGemportControlTcontId OBJECT-TYPE
                        SYNTAX Integer32
                        MAX-ACCESS read-write
                        STATUS current
                        DESCRIPTION
                                "The tcont ID"
                        ::= { fkGponProfile2TcontGemportControl 7 }

                
--  1.3.6.1.4.1.10428 9 1.101.23.51.8.2.8
                -- 1.3.6.1.4.1.10428 9 1.101.23.51.8.2.8
                fkGponProfile2TcontGemportControlMapperId OBJECT-TYPE
                        SYNTAX Integer32
                        MAX-ACCESS read-write
                        STATUS current
                        DESCRIPTION
                                "The tcont mapper ID."
                        ::= { fkGponProfile2TcontGemportControl 8 }

                
--  1.3.6.1.4.1.10428 9 1.101.23.51.8.2.9
                -- 1.3.6.1.4.1.10428 9 1.101.23.51.8.2.9
                fkGponProfile2TcontGemportControlId OBJECT-TYPE
                        SYNTAX Integer32
                        MAX-ACCESS read-write
                        STATUS current
                        DESCRIPTION
                                "The gemport ID"
                        ::= { fkGponProfile2TcontGemportControl 9 }

                
--  1.3.6.1.4.1.10428 9 1.101.23.51.8.2.10
                -- 1.3.6.1.4.1.10428 9 1.101.23.51.8.2.10
                fkGponProfile2TcontGemportControlQueue OBJECT-TYPE
                        SYNTAX Integer32 (0 | 1..8)
                        MAX-ACCESS read-write
                        STATUS current
                        DESCRIPTION
                                "The gemport queue"
                        ::= { fkGponProfile2TcontGemportControl 10 }

                
--  1.3.6.1.4.1.10428 9 1.101.23.51.8.3
                -- 1.3.6.1.4.1.10428 9 1.101.23.51.8.3
                fkGponProfile2TcontGemportNotification OBJECT IDENTIFIER ::= { fkGponProfile2TcontGemport 3 }

                
--  1.3.6.1.4.1.10428 9 1.101.23.51.8.3.1
                -- 1.3.6.1.4.1.10428 9 1.101.23.51.8.3.1
                fkGponProfile2TcontGemportAdded NOTIFICATION-TYPE
                        OBJECTS { fkGponProfile2TcontGemportControlRequest, fkGponProfile2TcontGemportControlStatus, fkGponProfile2TcontGemportControlTimer, fkGponProfile2TcontGemportControlTimeStamp, fkGponProfile2TcontGemportControlReqResult, 
                                fkGponProfile2TcontGemportControlTName, fkGponProfile2TcontGemportControlTcontId, fkGponProfile2TcontGemportControlMapperId, fkGponProfile2TcontGemportControlId, fkGponProfile2TcontGemportControlQueue
                                 }
                        STATUS current
                        DESCRIPTION 
                                "Description."
                        ::= { fkGponProfile2TcontGemportNotification 1 }

                
--  1.3.6.1.4.1.10428 9 1.101.23.51.8.3.2
                -- 1.3.6.1.4.1.10428 9 1.101.23.51.8.3.2
                fkGponProfile2TcontGemportDeleted NOTIFICATION-TYPE
                        OBJECTS { fkGponProfile2TcontGemportControlRequest, fkGponProfile2TcontGemportControlTimeStamp, fkGponProfile2TcontGemportControlReqResult, fkGponProfile2TcontGemportControlTName, fkGponProfile2TcontGemportControlTcontId, 
                                fkGponProfile2TcontGemportControlMapperId, fkGponProfile2TcontGemportControlId }
                        STATUS current
                        DESCRIPTION 
                                "Description."
                        ::= { fkGponProfile2TcontGemportNotification 2 }

                
--  1.3.6.1.4.1.10428 9 1.101.23.51.9
                -- 1.3.6.1.4.1.10428 9 1.101.23.51.9
                fkGponProfile2Mcast OBJECT IDENTIFIER ::= { fkGponProfile2 9 }

                
--  1.3.6.1.4.1.10428 9 1.101.23.51.9.1
                -- 1.3.6.1.4.1.10428 9 1.101.23.51.9.1
                fkGponProfile2McastTable OBJECT-TYPE
                        SYNTAX SEQUENCE OF FkGponProfile2McastEntry
                        MAX-ACCESS not-accessible
                        STATUS current
                        DESCRIPTION
                                "fkGponProfile2McastTable"
                        ::= { fkGponProfile2Mcast 1 }

                
--  1.3.6.1.4.1.10428 9 1.101.23.51.9.1.1
                -- 1.3.6.1.4.1.10428 9 1.101.23.51.9.1.1
                fkGponProfile2McastEntry OBJECT-TYPE
                        SYNTAX FkGponProfile2McastEntry
                        MAX-ACCESS not-accessible
                        STATUS current
                        DESCRIPTION
                                "key: fkGponProfile2McastIndex"
                        INDEX { fkGponProfile2McastIndex }
                        ::= { fkGponProfile2McastTable 1 }

                
                FkGponProfile2McastEntry ::=
                        SEQUENCE { 
                                fkGponProfile2McastIndex
                                        Integer32,
                                fkGponProfile2McastName
                                        OCTET STRING,
                                fkGponProfile2McastIgmpFunc
                                        INTEGER,
                                fkGponProfile2McastIgmpImmLeave
                                        EnableFlag,
                                fkGponProfile2McastIgmpRobust
                                        Integer32,
                                fkGponProfile2McastIgmpQuerierAddress
                                        IpAddress,
                                fkGponProfile2McastIgmpQuerierMaxRespTime
                                        Integer32,
                                fkGponProfile2McastIgmpQuerierInterval
                                        Integer32,
                                fkGponProfile2McastIgmpVersion
                                        INTEGER,
                                fkGponProfile2McastIgmpUpRateLimit
                                        Integer32,
                                fkGponProfile2McastIgmpTagCtrl
                                        INTEGER,
                                fkGponProfile2McastIgmpTagCtrlVid
                                        Integer32,
                                fkGponProfile2McastIgmpTagCtrlCos
                                        Integer32
                         }

--  1.3.6.1.4.1.10428 9 1.101.23.51.9.1.1.1
                -- 1.3.6.1.4.1.10428 9 1.101.23.51.9.1.1.1
                fkGponProfile2McastIndex OBJECT-TYPE
                        SYNTAX Integer32 (1..65535)
                        MAX-ACCESS read-only
                        STATUS current
                        DESCRIPTION
                                "The Mcast profile index."
                        ::= { fkGponProfile2McastEntry 1 }

                
--  1.3.6.1.4.1.10428 9 1.101.23.51.9.1.1.2
                -- 1.3.6.1.4.1.10428 9 1.101.23.51.9.1.1.2
                fkGponProfile2McastName OBJECT-TYPE
                        SYNTAX OCTET STRING
                        MAX-ACCESS read-only
                        STATUS current
                        DESCRIPTION
                                "The Mcast profile name."
                        ::= { fkGponProfile2McastEntry 2 }

                
--  1.3.6.1.4.1.10428 9 1.101.23.51.9.1.1.3
                -- 1.3.6.1.4.1.10428 9 1.101.23.51.9.1.1.3
                fkGponProfile2McastIgmpFunc OBJECT-TYPE
                        SYNTAX INTEGER
                                {
                                snooping(1),
                                proxy(2),
                                spr(3)
                                }
                        MAX-ACCESS read-only
                        STATUS current
                        DESCRIPTION
                                "The Igmp function
                                snooping :  Igmp snooping (default)
                                proxy : Igmp proxy
                                spr : Igmp snooping with proxy"
                        ::= { fkGponProfile2McastEntry 3 }

                
--  1.3.6.1.4.1.10428 9 1.101.23.51.9.1.1.4
                -- 1.3.6.1.4.1.10428 9 1.101.23.51.9.1.1.4
                fkGponProfile2McastIgmpImmLeave OBJECT-TYPE
                        SYNTAX EnableFlag
                        MAX-ACCESS read-only
                        STATUS current
                        DESCRIPTION
                                "The immediate leave processing"
                        ::= { fkGponProfile2McastEntry 4 }

                
--  1.3.6.1.4.1.10428 9 1.101.23.51.9.1.1.5
                -- 1.3.6.1.4.1.10428 9 1.101.23.51.9.1.1.5
                fkGponProfile2McastIgmpRobust OBJECT-TYPE
                        SYNTAX Integer32 (0 | 1..7)
                        MAX-ACCESS read-only
                        STATUS current
                        DESCRIPTION
                                "IGMP Snooping robustness variable"
                        ::= { fkGponProfile2McastEntry 5 }

                
--  1.3.6.1.4.1.10428 9 1.101.23.51.9.1.1.6
                -- 1.3.6.1.4.1.10428 9 1.101.23.51.9.1.1.6
                fkGponProfile2McastIgmpQuerierAddress OBJECT-TYPE
                        SYNTAX IpAddress
                        MAX-ACCESS read-only
                        STATUS current
                        DESCRIPTION
                                "The IGMP querier address."
                        ::= { fkGponProfile2McastEntry 6 }

                
--  1.3.6.1.4.1.10428 9 1.101.23.51.9.1.1.7
                -- 1.3.6.1.4.1.10428 9 1.101.23.51.9.1.1.7
                fkGponProfile2McastIgmpQuerierMaxRespTime OBJECT-TYPE
                        SYNTAX Integer32 (1..25)
                        MAX-ACCESS read-only
                        STATUS current
                        DESCRIPTION
                                "The IGMP querier max-response time"
                        ::= { fkGponProfile2McastEntry 7 }

                
--  1.3.6.1.4.1.10428 9 1.101.23.51.9.1.1.8
                -- 1.3.6.1.4.1.10428 9 1.101.23.51.9.1.1.8
                fkGponProfile2McastIgmpQuerierInterval OBJECT-TYPE
                        SYNTAX Integer32 (1..3600)
                        MAX-ACCESS read-only
                        STATUS current
                        DESCRIPTION
                                "The IGMP querier query-interval."
                        ::= { fkGponProfile2McastEntry 8 }

                
--  1.3.6.1.4.1.10428 9 1.101.23.51.9.1.1.9
                -- 1.3.6.1.4.1.10428 9 1.101.23.51.9.1.1.9
                fkGponProfile2McastIgmpVersion OBJECT-TYPE
                        SYNTAX INTEGER
                                {
                                version1(1),
                                version2(2),
                                version3(3)
                                }
                        MAX-ACCESS read-only
                        STATUS current
                        DESCRIPTION
                                "The IGMP version."
                        ::= { fkGponProfile2McastEntry 9 }

                
--  1.3.6.1.4.1.10428 9 1.101.23.51.9.1.1.10
                -- 1.3.6.1.4.1.10428 9 1.101.23.51.9.1.1.10
                fkGponProfile2McastIgmpUpRateLimit OBJECT-TYPE
                        SYNTAX Integer32
                        MAX-ACCESS read-only
                        STATUS current
                        DESCRIPTION
                                "The IGMP upstream rate-limit"
                        ::= { fkGponProfile2McastEntry 10 }

                
--  1.3.6.1.4.1.10428 9 1.101.23.51.9.1.1.11
                -- 1.3.6.1.4.1.10428 9 1.101.23.51.9.1.1.11
                fkGponProfile2McastIgmpTagCtrl OBJECT-TYPE
                        SYNTAX INTEGER
                                {
                                bypass(1),
                                add(2),
                                replaceWithPbit(3),
                                replace(4),
                                unknown(255)
                                }
                        MAX-ACCESS read-only
                        STATUS current
                        DESCRIPTION
                                "The Igmp upstream tag control action. (TCI)"
                        ::= { fkGponProfile2McastEntry 11 }

                
--  1.3.6.1.4.1.10428 9 1.101.23.51.9.1.1.12
                -- 1.3.6.1.4.1.10428 9 1.101.23.51.9.1.1.12
                fkGponProfile2McastIgmpTagCtrlVid OBJECT-TYPE
                        SYNTAX Integer32 (0 | 1..4095)
                        MAX-ACCESS read-only
                        STATUS current
                        DESCRIPTION
                                "The vid of TCI
                                1~4095 are vailable.
                                0 is None"
                        ::= { fkGponProfile2McastEntry 12 }

                
--  1.3.6.1.4.1.10428 9 1.101.23.51.9.1.1.13
                -- 1.3.6.1.4.1.10428 9 1.101.23.51.9.1.1.13
                fkGponProfile2McastIgmpTagCtrlCos OBJECT-TYPE
                        SYNTAX Integer32 (0..7 | 255)
                        MAX-ACCESS read-only
                        STATUS current
                        DESCRIPTION
                                "The Cos of TCI
                                0~7 are available.
                                255 is None."
                        ::= { fkGponProfile2McastEntry 13 }

                
--  1.3.6.1.4.1.10428 9 1.101.23.51.9.2
                -- 1.3.6.1.4.1.10428 9 1.101.23.51.9.2
                fkGponProfile2McastControl OBJECT IDENTIFIER ::= { fkGponProfile2Mcast 2 }

                
--  1.3.6.1.4.1.10428 9 1.101.23.51.9.2.1
                -- 1.3.6.1.4.1.10428 9 1.101.23.51.9.2.1
                fkGponProfile2McastControlRequest OBJECT-TYPE
                        SYNTAX INTEGER
                                {
                                addMcastProfile(1),
                                delMcastProfile(2),
                                setIgmpFunction(3),
                                setIgmpImmLeave(4),
                                setIgmpRobuts(5),
                                setIgmpQueirierInfo(6),
                                setIgmpVersion(7),
                                setIgmpUpRateLimit(8),
                                setIgmpTagCtrl(9)
                                }
                        MAX-ACCESS read-write
                        STATUS current
                        DESCRIPTION
                                "The request of a user command"
                        ::= { fkGponProfile2McastControl 1 }

                
--  1.3.6.1.4.1.10428 9 1.101.23.51.9.2.2
                -- 1.3.6.1.4.1.10428 9 1.101.23.51.9.2.2
                fkGponProfile2McastControlStatus OBJECT-TYPE
                        SYNTAX FkControlStatusType
                        MAX-ACCESS read-write
                        STATUS current
                        DESCRIPTION
                                "The status of user command"
                        ::= { fkGponProfile2McastControl 2 }

                
--  1.3.6.1.4.1.10428 9 1.101.23.51.9.2.3
                -- 1.3.6.1.4.1.10428 9 1.101.23.51.9.2.3
                fkGponProfile2McastControlTimer OBJECT-TYPE
                        SYNTAX Gauge32
                        MAX-ACCESS read-write
                        STATUS current
                        DESCRIPTION
                                "The maximum time for the manager for a long running user command"
                        ::= { fkGponProfile2McastControl 3 }

                
--  1.3.6.1.4.1.10428 9 1.101.23.51.9.2.4
                -- 1.3.6.1.4.1.10428 9 1.101.23.51.9.2.4
                fkGponProfile2McastControlTimeStamp OBJECT-TYPE
                        SYNTAX TimeTicks
                        MAX-ACCESS read-write
                        STATUS current
                        DESCRIPTION
                                "The time stamp of the last command(end of command)"
                        ::= { fkGponProfile2McastControl 4 }

                
--  1.3.6.1.4.1.10428 9 1.101.23.51.9.2.5
                -- 1.3.6.1.4.1.10428 9 1.101.23.51.9.2.5
                fkGponProfile2McastControlReqResult OBJECT-TYPE
                        SYNTAX FkControlRequestResultType
                        MAX-ACCESS read-write
                        STATUS current
                        DESCRIPTION
                                "The result of the last user command"
                        ::= { fkGponProfile2McastControl 5 }

                
--  1.3.6.1.4.1.10428 9 1.101.23.51.9.2.6
                -- 1.3.6.1.4.1.10428 9 1.101.23.51.9.2.6
                fkGponProfile2McastControlName OBJECT-TYPE
                        SYNTAX OCTET STRING
                        MAX-ACCESS read-write
                        STATUS current
                        DESCRIPTION
                                "The Multicast profile name."
                        ::= { fkGponProfile2McastControl 6 }

                
--  1.3.6.1.4.1.10428 9 1.101.23.51.9.2.7
                -- 1.3.6.1.4.1.10428 9 1.101.23.51.9.2.7
                fkGponProfile2McastControlIgmpFunc OBJECT-TYPE
                        SYNTAX INTEGER
                                {
                                snooping(1),
                                proxy(2),
                                spr(3)
                                }
                        MAX-ACCESS read-write
                        STATUS current
                        DESCRIPTION
                                "The Igmp function
                                snooping :  Igmp snooping (default)
                                proxy : Igmp proxy
                                spr : Igmp snooping with proxy"
                        ::= { fkGponProfile2McastControl 7 }

                
--  1.3.6.1.4.1.10428 9 1.101.23.51.9.2.8
                -- 1.3.6.1.4.1.10428 9 1.101.23.51.9.2.8
                fkGponProfile2McastControlIgmpImmLeave OBJECT-TYPE
                        SYNTAX EnableFlag
                        MAX-ACCESS read-write
                        STATUS current
                        DESCRIPTION
                                "The immediate leave processing"
                        ::= { fkGponProfile2McastControl 8 }

                
--  1.3.6.1.4.1.10428 9 1.101.23.51.9.2.9
                -- 1.3.6.1.4.1.10428 9 1.101.23.51.9.2.9
                fkGponProfile2McastControlIgmpRobust OBJECT-TYPE
                        SYNTAX Integer32 (0 | 1..7)
                        MAX-ACCESS read-write
                        STATUS current
                        DESCRIPTION
                                "IGMP Snooping robustness variable
                                "
                        ::= { fkGponProfile2McastControl 9 }

                
--  1.3.6.1.4.1.10428 9 1.101.23.51.9.2.10
                -- 1.3.6.1.4.1.10428 9 1.101.23.51.9.2.10
                fkGponProfile2McastControlIgmpQuerierAddress OBJECT-TYPE
                        SYNTAX IpAddress
                        MAX-ACCESS read-write
                        STATUS current
                        DESCRIPTION
                                "The IGMP querier address."
                        ::= { fkGponProfile2McastControl 10 }

                
--  1.3.6.1.4.1.10428 9 1.101.23.51.9.2.11
                -- 1.3.6.1.4.1.10428 9 1.101.23.51.9.2.11
                fkGponProfile2McastControlIgmpQuerierMaxRespTime OBJECT-TYPE
                        SYNTAX Integer32 (1..25)
                        MAX-ACCESS read-write
                        STATUS current
                        DESCRIPTION
                                "The IGMP querier max-response time"
                        ::= { fkGponProfile2McastControl 11 }

                
--  1.3.6.1.4.1.10428 9 1.101.23.51.9.2.12
                -- 1.3.6.1.4.1.10428 9 1.101.23.51.9.2.12
                fkGponProfile2McastControlIgmpQuerierInterval OBJECT-TYPE
                        SYNTAX Integer32 (1..3600)
                        MAX-ACCESS read-write
                        STATUS current
                        DESCRIPTION
                                "The IGMP querier query-interval."
                        ::= { fkGponProfile2McastControl 12 }

                
--  1.3.6.1.4.1.10428 9 1.101.23.51.9.2.13
                -- 1.3.6.1.4.1.10428 9 1.101.23.51.9.2.13
                fkGponProfile2McastControlIgmpVersion OBJECT-TYPE
                        SYNTAX INTEGER
                                {
                                version1(1),
                                version2(2),
                                version3(3)
                                }
                        MAX-ACCESS read-write
                        STATUS current
                        DESCRIPTION
                                "The IGMP version."
                        ::= { fkGponProfile2McastControl 13 }

                
--  1.3.6.1.4.1.10428 9 1.101.23.51.9.2.14
                -- 1.3.6.1.4.1.10428 9 1.101.23.51.9.2.14
                fkGponProfile2McastControlIgmpUpRateLimit OBJECT-TYPE
                        SYNTAX Integer32
                        MAX-ACCESS read-write
                        STATUS current
                        DESCRIPTION
                                "The IGMP upstream rate-limit"
                        ::= { fkGponProfile2McastControl 14 }

                
--  1.3.6.1.4.1.10428 9 1.101.23.51.9.2.15
                -- 1.3.6.1.4.1.10428 9 1.101.23.51.9.2.15
                fkGponProfile2McastControlIgmpTagCtrl OBJECT-TYPE
                        SYNTAX INTEGER
                                {
                                bypass(1),
                                add(2),
                                replaceWithPbit(3),
                                replace(4),
                                unknown(255)
                                }
                        MAX-ACCESS read-write
                        STATUS current
                        DESCRIPTION
                                "The Igmp upstream tag control action. (TCI)"
                        ::= { fkGponProfile2McastControl 15 }

                
--  1.3.6.1.4.1.10428 9 1.101.23.51.9.2.16
                -- 1.3.6.1.4.1.10428 9 1.101.23.51.9.2.16
                fkGponProfile2McastControlIgmpTagCtrlVid OBJECT-TYPE
                        SYNTAX Integer32 (1..4095)
                        MAX-ACCESS read-write
                        STATUS current
                        DESCRIPTION
                                "The vid of TCI
                                1~4095 are vailable.
                                "
                        ::= { fkGponProfile2McastControl 16 }

                
--  1.3.6.1.4.1.10428 9 1.101.23.51.9.2.17
                -- 1.3.6.1.4.1.10428 9 1.101.23.51.9.2.17
                fkGponProfile2McastControlIgmpTagCtrlCos OBJECT-TYPE
                        SYNTAX Integer32 (0..7)
                        MAX-ACCESS read-write
                        STATUS current
                        DESCRIPTION
                                "The Cos of TCI
                                0~7 are available.
                                "
                        ::= { fkGponProfile2McastControl 17 }

                
--  1.3.6.1.4.1.10428 9 1.101.23.51.9.3
                -- 1.3.6.1.4.1.10428 9 1.101.23.51.9.3
                fkGponProfile2McastNotification OBJECT IDENTIFIER ::= { fkGponProfile2Mcast 3 }

                
--  1.3.6.1.4.1.10428 9 1.101.23.51.9.3.1
                -- 1.3.6.1.4.1.10428 9 1.101.23.51.9.3.1
                fkGponProfile2McastProfileAdded NOTIFICATION-TYPE
                        OBJECTS { fkGponProfile2McastControlRequest, fkGponProfile2McastControlStatus, fkGponProfile2McastControlTimer, fkGponProfile2McastControlTimeStamp, fkGponProfile2McastControlReqResult, 
                                fkGponProfile2McastControlName }
                        STATUS current
                        DESCRIPTION 
                                "Description."
                        ::= { fkGponProfile2McastNotification 1 }

                
--  1.3.6.1.4.1.10428 9 1.101.23.51.9.3.2
                -- 1.3.6.1.4.1.10428 9 1.101.23.51.9.3.2
                fkGponProfile2McastProfileDeleted NOTIFICATION-TYPE
                        OBJECTS { fkGponProfile2McastControlRequest, fkGponProfile2McastControlStatus, fkGponProfile2McastControlTimer, fkGponProfile2McastControlTimeStamp, fkGponProfile2McastControlReqResult, 
                                fkGponProfile2McastControlName }
                        STATUS current
                        DESCRIPTION 
                                "Description."
                        ::= { fkGponProfile2McastNotification 2 }

                
--  1.3.6.1.4.1.10428 9 1.101.23.51.9.3.3
                -- 1.3.6.1.4.1.10428 9 1.101.23.51.9.3.3
                fkGponProfile2McastIgmpFuncChanged NOTIFICATION-TYPE
                        OBJECTS { fkGponProfile2McastControlRequest, fkGponProfile2McastControlStatus, fkGponProfile2McastControlTimer, fkGponProfile2McastControlTimeStamp, fkGponProfile2McastControlReqResult, 
                                fkGponProfile2McastControlName, fkGponProfile2McastControlIgmpFunc }
                        STATUS current
                        DESCRIPTION 
                                "Description."
                        ::= { fkGponProfile2McastNotification 3 }

                
--  1.3.6.1.4.1.10428 9 1.101.23.51.9.3.4
                -- 1.3.6.1.4.1.10428 9 1.101.23.51.9.3.4
                fkGponProfile2McastIgmpImmLeaveChanged NOTIFICATION-TYPE
                        OBJECTS { fkGponProfile2McastControlRequest, fkGponProfile2McastControlStatus, fkGponProfile2McastControlTimer, fkGponProfile2McastControlTimeStamp, fkGponProfile2McastControlReqResult, 
                                fkGponProfile2McastControlName, fkGponProfile2McastControlIgmpImmLeave }
                        STATUS current
                        DESCRIPTION 
                                "Description."
                        ::= { fkGponProfile2McastNotification 4 }

                
--  1.3.6.1.4.1.10428 9 1.101.23.51.9.3.5
                -- 1.3.6.1.4.1.10428 9 1.101.23.51.9.3.5
                fkGponProfile2McastIgmpRobustChanged NOTIFICATION-TYPE
                        OBJECTS { fkGponProfile2McastControlRequest, fkGponProfile2McastControlStatus, fkGponProfile2McastControlTimer, fkGponProfile2McastControlTimeStamp, fkGponProfile2McastControlReqResult, 
                                fkGponProfile2McastControlName, fkGponProfile2McastControlIgmpRobust }
                        STATUS current
                        DESCRIPTION 
                                "Description."
                        ::= { fkGponProfile2McastNotification 5 }

                
--  1.3.6.1.4.1.10428 9 1.101.23.51.9.3.6
                -- 1.3.6.1.4.1.10428 9 1.101.23.51.9.3.6
                fkGponProfile2McastIgmpQuerierInfoChanged NOTIFICATION-TYPE
                        OBJECTS { fkGponProfile2McastControlRequest, fkGponProfile2McastControlStatus, fkGponProfile2McastControlTimer, fkGponProfile2McastControlTimeStamp, fkGponProfile2McastControlReqResult, 
                                fkGponProfile2McastControlName, fkGponProfile2McastControlIgmpQuerierAddress, fkGponProfile2McastControlIgmpQuerierMaxRespTime, fkGponProfile2McastControlIgmpQuerierInterval }
                        STATUS current
                        DESCRIPTION 
                                "Description."
                        ::= { fkGponProfile2McastNotification 6 }

                
--  1.3.6.1.4.1.10428 9 1.101.23.51.9.3.7
                -- 1.3.6.1.4.1.10428 9 1.101.23.51.9.3.7
                fkGponProfile2McastIgmpVersionChanged NOTIFICATION-TYPE
                        OBJECTS { fkGponProfile2McastControlRequest, fkGponProfile2McastControlStatus, fkGponProfile2McastControlTimer, fkGponProfile2McastControlTimeStamp, fkGponProfile2McastControlReqResult, 
                                fkGponProfile2McastControlName, fkGponProfile2McastControlIgmpVersion }
                        STATUS current
                        DESCRIPTION 
                                "Description."
                        ::= { fkGponProfile2McastNotification 7 }

                
--  1.3.6.1.4.1.10428 9 1.101.23.51.9.3.8
                -- 1.3.6.1.4.1.10428 9 1.101.23.51.9.3.8
                fkGponProfile2McastIgmpUpRateLimitChanged NOTIFICATION-TYPE
                        OBJECTS { fkGponProfile2McastControlRequest, fkGponProfile2McastControlStatus, fkGponProfile2McastControlTimer, fkGponProfile2McastControlTimeStamp, fkGponProfile2McastControlReqResult, 
                                fkGponProfile2McastControlName, fkGponProfile2McastControlIgmpUpRateLimit }
                        STATUS current
                        DESCRIPTION 
                                "Description."
                        ::= { fkGponProfile2McastNotification 8 }

                
--  1.3.6.1.4.1.10428 9 1.101.23.51.9.3.9
                -- 1.3.6.1.4.1.10428 9 1.101.23.51.9.3.9
                fkGponProfile2McastIgmpTagCtrlChanged NOTIFICATION-TYPE
                        OBJECTS { fkGponProfile2McastControlRequest, fkGponProfile2McastControlStatus, fkGponProfile2McastControlTimer, fkGponProfile2McastControlTimeStamp, fkGponProfile2McastControlReqResult, 
                                fkGponProfile2McastControlName, fkGponProfile2McastControlIgmpTagCtrl, fkGponProfile2McastControlIgmpTagCtrlVid, fkGponProfile2McastControlIgmpTagCtrlCos }
                        STATUS current
                        DESCRIPTION 
                                "Description."
                        ::= { fkGponProfile2McastNotification 9 }

                
--  1.3.6.1.4.1.10428 9 1.101.23.51.10
                -- 1.3.6.1.4.1.10428 9 1.101.23.51.10
                fkGponProfile2McastACL OBJECT IDENTIFIER ::= { fkGponProfile2 10 }

                
--  1.3.6.1.4.1.10428 9 1.101.23.51.10.1
                -- 1.3.6.1.4.1.10428 9 1.101.23.51.10.1
                fkGponProfile2McastAclTable OBJECT-TYPE
                        SYNTAX SEQUENCE OF FkGponProfile2McastAclEntry
                        MAX-ACCESS not-accessible
                        STATUS current
                        DESCRIPTION
                                "fkGponProfile2McastAclTable"
                        ::= { fkGponProfile2McastACL 1 }

                
--  1.3.6.1.4.1.10428 9 1.101.23.51.10.1.1
                -- 1.3.6.1.4.1.10428 9 1.101.23.51.10.1.1
                fkGponProfile2McastAclEntry OBJECT-TYPE
                        SYNTAX FkGponProfile2McastAclEntry
                        MAX-ACCESS not-accessible
                        STATUS current
                        DESCRIPTION
                                "key: fkGponProfile2McastIndex, fkGponProfile2McastAclIndex"
                        INDEX { fkGponProfile2McastIndex, fkGponProfile2McastAclIndex }
                        ::= { fkGponProfile2McastAclTable 1 }

                
                FkGponProfile2McastAclEntry ::=
                        SEQUENCE { 
                                fkGponProfile2McastAclIndex
                                        Integer32,
                                fkGponProfile2McastAclVid
                                        Integer32,
                                fkGponProfile2McastAclDstIpStart
                                        IpAddress,
                                fkGponProfile2McastAclDstIpEnd
                                        IpAddress,
                                fkGponProfile2McastAclSrcIp
                                        IpAddress,
                                fkGponProfile2McastAclBandwidth
                                        Integer32,
                                fkGponProfile2McastAclGem
                                        Integer32,
                                fkGponProfile2McastAclCos
                                        Integer32
                         }

--  1.3.6.1.4.1.10428 9 1.101.23.51.10.1.1.1
                -- 1.3.6.1.4.1.10428 9 1.101.23.51.10.1.1.1
                fkGponProfile2McastAclIndex OBJECT-TYPE
                        SYNTAX Integer32 (1..65535)
                        MAX-ACCESS read-only
                        STATUS current
                        DESCRIPTION
                                "The Mcast access-list index."
                        ::= { fkGponProfile2McastAclEntry 1 }

                
--  1.3.6.1.4.1.10428 9 1.101.23.51.10.1.1.2
                -- 1.3.6.1.4.1.10428 9 1.101.23.51.10.1.1.2
                fkGponProfile2McastAclVid OBJECT-TYPE
                        SYNTAX Integer32 (0 | 1..4094)
                        MAX-ACCESS read-write
                        STATUS current
                        DESCRIPTION
                                "This specific the VLAN carrying the multicast group DS"
                        ::= { fkGponProfile2McastAclEntry 2 }

                
--  1.3.6.1.4.1.10428 9 1.101.23.51.10.1.1.3
                -- 1.3.6.1.4.1.10428 9 1.101.23.51.10.1.1.3
                fkGponProfile2McastAclDstIpStart OBJECT-TYPE
                        SYNTAX IpAddress
                        MAX-ACCESS read-only
                        STATUS current
                        DESCRIPTION
                                "The destination IP range-start."
                        ::= { fkGponProfile2McastAclEntry 3 }

                
--  1.3.6.1.4.1.10428 9 1.101.23.51.10.1.1.4
                -- 1.3.6.1.4.1.10428 9 1.101.23.51.10.1.1.4
                fkGponProfile2McastAclDstIpEnd OBJECT-TYPE
                        SYNTAX IpAddress
                        MAX-ACCESS read-only
                        STATUS current
                        DESCRIPTION
                                "The destination IP range-end"
                        ::= { fkGponProfile2McastAclEntry 4 }

                
--  1.3.6.1.4.1.10428 9 1.101.23.51.10.1.1.5
                -- 1.3.6.1.4.1.10428 9 1.101.23.51.10.1.1.5
                fkGponProfile2McastAclSrcIp OBJECT-TYPE
                        SYNTAX IpAddress
                        MAX-ACCESS read-only
                        STATUS current
                        DESCRIPTION
                                "The source IP."
                        ::= { fkGponProfile2McastAclEntry 5 }

                
--  1.3.6.1.4.1.10428 9 1.101.23.51.10.1.1.6
                -- 1.3.6.1.4.1.10428 9 1.101.23.51.10.1.1.6
                fkGponProfile2McastAclBandwidth OBJECT-TYPE
                        SYNTAX Integer32
                        MAX-ACCESS read-only
                        STATUS current
                        DESCRIPTION
                                "The Imputed group bandwidth"
                        ::= { fkGponProfile2McastAclEntry 6 }

                
--  1.3.6.1.4.1.10428 9 1.101.23.51.10.1.1.7
                -- 1.3.6.1.4.1.10428 9 1.101.23.51.10.1.1.7
                fkGponProfile2McastAclGem OBJECT-TYPE
                        SYNTAX Integer32 (1..25)
                        MAX-ACCESS read-only
                        STATUS current
                        DESCRIPTION
                                "Th GEM port ID"
                        ::= { fkGponProfile2McastAclEntry 7 }

                
                -- 1.3.6.1.4.1.10428 9 1.101.23.51.10.1.1.8
                fkGponProfile2McastAclCos OBJECT-TYPE
                        SYNTAX Integer32 (0..7)
                        MAX-ACCESS read-only
                        STATUS current
                        DESCRIPTION
                                "The IGMP access-list CoS"
                        ::= { fkGponProfile2McastAclEntry 8 }

                
--  1.3.6.1.4.1.10428 9 1.101.23.51.10.2
                -- 1.3.6.1.4.1.10428 9 1.101.23.51.10.2
                fkGponProfile2McastAclControl OBJECT IDENTIFIER ::= { fkGponProfile2McastACL 2 }

                
--  1.3.6.1.4.1.10428 9 1.101.23.51.10.2.1
                -- 1.3.6.1.4.1.10428 9 1.101.23.51.10.2.1
                fkGponProfile2McastAclControlRequest OBJECT-TYPE
                        SYNTAX INTEGER
                                {
                                addMcastAcl(1),
                                delMcastAcl(2)
                                }
                        MAX-ACCESS read-write
                        STATUS current
                        DESCRIPTION
                                "The request of a user command"
                        ::= { fkGponProfile2McastAclControl 1 }

                
--  1.3.6.1.4.1.10428 9 1.101.23.51.10.2.2
                -- 1.3.6.1.4.1.10428 9 1.101.23.51.10.2.2
                fkGponProfile2McastAclControlStatus OBJECT-TYPE
                        SYNTAX FkControlStatusType
                        MAX-ACCESS read-write
                        STATUS current
                        DESCRIPTION
                                "The status of user command"
                        ::= { fkGponProfile2McastAclControl 2 }

                
--  1.3.6.1.4.1.10428 9 1.101.23.51.10.2.3
                -- 1.3.6.1.4.1.10428 9 1.101.23.51.10.2.3
                fkGponProfile2McastAclControlTimer OBJECT-TYPE
                        SYNTAX Gauge32
                        MAX-ACCESS read-write
                        STATUS current
                        DESCRIPTION
                                "The maximum time for the manager for a long running user command"
                        ::= { fkGponProfile2McastAclControl 3 }

                
--  1.3.6.1.4.1.10428 9 1.101.23.51.10.2.4
                -- 1.3.6.1.4.1.10428 9 1.101.23.51.10.2.4
                fkGponProfile2McastAclControlTimeStamp OBJECT-TYPE
                        SYNTAX TimeTicks
                        MAX-ACCESS read-write
                        STATUS current
                        DESCRIPTION
                                "The time stamp of the last command(end of command)"
                        ::= { fkGponProfile2McastAclControl 4 }

                
--  1.3.6.1.4.1.10428 9 1.101.23.51.10.2.5
                -- 1.3.6.1.4.1.10428 9 1.101.23.51.10.2.5
                fkGponProfile2McastAclControlReqResult OBJECT-TYPE
                        SYNTAX FkControlRequestResultType
                        MAX-ACCESS read-write
                        STATUS current
                        DESCRIPTION
                                "The result of the last user command
                                "
                        ::= { fkGponProfile2McastAclControl 5 }

                
--  1.3.6.1.4.1.10428 9 1.101.23.51.10.2.6
                -- 1.3.6.1.4.1.10428 9 1.101.23.51.10.2.6
                fkGponProfile2McastAclControlIndex OBJECT-TYPE
                        SYNTAX Integer32
                        MAX-ACCESS read-write
                        STATUS current
                        DESCRIPTION
                                "The Mcast access-list index."
                        ::= { fkGponProfile2McastAclControl 6 }

                
--  1.3.6.1.4.1.10428 9 1.101.23.51.10.2.7
                -- 1.3.6.1.4.1.10428 9 1.101.23.51.10.2.7
                fkGponProfile2McastAclControlVid OBJECT-TYPE
                        SYNTAX Integer32 (0 | 1..4094)
                        MAX-ACCESS read-write
                        STATUS current
                        DESCRIPTION
                                "This specific the VLAN carrying the multicast group DS"
                        ::= { fkGponProfile2McastAclControl 7 }

                
--  1.3.6.1.4.1.10428 9 1.101.23.51.10.2.8
                -- 1.3.6.1.4.1.10428 9 1.101.23.51.10.2.8
                fkGponProfile2McastAclControlName OBJECT-TYPE
                        SYNTAX OCTET STRING
                        MAX-ACCESS read-write
                        STATUS current
                        DESCRIPTION
                                "The Mcast profile name."
                        ::= { fkGponProfile2McastAclControl 8 }

                
--  1.3.6.1.4.1.10428 9 1.101.23.51.10.2.9
                -- 1.3.6.1.4.1.10428 9 1.101.23.51.10.2.9
                fkGponProfile2McastAclControlDstIpStart OBJECT-TYPE
                        SYNTAX IpAddress
                        MAX-ACCESS read-write
                        STATUS current
                        DESCRIPTION
                                "The destination IP range-start."
                        ::= { fkGponProfile2McastAclControl 9 }

                
--  1.3.6.1.4.1.10428 9 1.101.23.51.10.2.10
                -- 1.3.6.1.4.1.10428 9 1.101.23.51.10.2.10
                fkGponProfile2McastAclControlDstIpEnd OBJECT-TYPE
                        SYNTAX IpAddress
                        MAX-ACCESS read-write
                        STATUS current
                        DESCRIPTION
                                "The destination IP range-end"
                        ::= { fkGponProfile2McastAclControl 10 }

                
--  1.3.6.1.4.1.10428 9 1.101.23.51.10.2.11
                -- 1.3.6.1.4.1.10428 9 1.101.23.51.10.2.11
                fkGponProfile2McastAclControlSrcIp OBJECT-TYPE
                        SYNTAX IpAddress
                        MAX-ACCESS read-write
                        STATUS current
                        DESCRIPTION
                                "The source IP."
                        ::= { fkGponProfile2McastAclControl 11 }

                
--  1.3.6.1.4.1.10428 9 1.101.23.51.10.2.12
                -- 1.3.6.1.4.1.10428 9 1.101.23.51.10.2.12
                fkGponProfile2McastAclControlBandwidth OBJECT-TYPE
                        SYNTAX Integer32
                        MAX-ACCESS read-write
                        STATUS current
                        DESCRIPTION
                                "The Imputed group bandwidth"
                        ::= { fkGponProfile2McastAclControl 12 }

                
--  1.3.6.1.4.1.10428 9 1.101.23.51.10.2.13
                -- 1.3.6.1.4.1.10428 9 1.101.23.51.10.2.13
                fkGponProfile2McastAclControlGem OBJECT-TYPE
                        SYNTAX Integer32 (1..25)
                        MAX-ACCESS read-write
                        STATUS current
                        DESCRIPTION
                                "The GEM port ID"
                        ::= { fkGponProfile2McastAclControl 13 }

                
                -- 1.3.6.1.4.1.10428 9 1.101.23.51.10.2.14
                fkGponProfile2McastAclControlCos OBJECT-TYPE
                        SYNTAX Integer32 (0..7)
                        MAX-ACCESS read-write
                        STATUS current
                        DESCRIPTION
                                "The IGMP access-list CoS"
                        ::= { fkGponProfile2McastAclControl 14 }

                
--  1.3.6.1.4.1.10428 9 1.101.23.51.10.3
                -- 1.3.6.1.4.1.10428 9 1.101.23.51.10.3
                fkGponProfile2McastAclNotification OBJECT IDENTIFIER ::= { fkGponProfile2McastACL 3 }

                
--  1.3.6.1.4.1.10428 9 1.101.23.51.10.3.1
                -- 1.3.6.1.4.1.10428 9 1.101.23.51.10.3.1
                fkGponProfile2McastAclAdded NOTIFICATION-TYPE
                        OBJECTS { fkGponProfile2McastAclControlRequest, fkGponProfile2McastAclControlStatus, fkGponProfile2McastAclControlTimer, fkGponProfile2McastAclControlTimeStamp, fkGponProfile2McastAclControlReqResult, 
                                fkGponProfile2McastAclControlVid, fkGponProfile2McastAclControlDstIpStart, fkGponProfile2McastAclControlDstIpEnd, fkGponProfile2McastAclControlSrcIp, fkGponProfile2McastAclControlBandwidth, 
                                fkGponProfile2McastAclControlCos, fkGponProfile2McastAclControlGem, fkGponProfile2McastAclControlName }
                        STATUS current
                        DESCRIPTION 
                                "addMcastAcl"
                        ::= { fkGponProfile2McastAclNotification 1 }

                
--  1.3.6.1.4.1.10428 9 1.101.23.51.10.3.2
                -- 1.3.6.1.4.1.10428 9 1.101.23.51.10.3.2
                fkGponProfile2McastAclDeleted NOTIFICATION-TYPE
                        OBJECTS { fkGponProfile2McastAclControlRequest, fkGponProfile2McastAclControlStatus, fkGponProfile2McastAclControlTimer, fkGponProfile2McastAclControlTimeStamp, fkGponProfile2McastAclControlReqResult, 
                                fkGponProfile2McastAclControlVid, fkGponProfile2McastAclControlName }
                        STATUS current
                        DESCRIPTION 
                                "delMcastAcl"
                        ::= { fkGponProfile2McastAclNotification 2 }

                
--  1.3.6.1.4.1.10428 9 1.101.23.51.11
                -- 1.3.6.1.4.1.10428 9 1.101.23.51.11
                fkGponProfile2McastSACL OBJECT IDENTIFIER ::= { fkGponProfile2 11 }

                
--  1.3.6.1.4.1.10428 9 1.101.23.51.11.1
                -- 1.3.6.1.4.1.10428 9 1.101.23.51.11.1
                fkGponProfile2McastSAclTable OBJECT-TYPE
                        SYNTAX SEQUENCE OF FkGponProfile2McastSAclEntry
                        MAX-ACCESS not-accessible
                        STATUS current
                        DESCRIPTION
                                "fkGponProfile2McastSAclTable"
                        ::= { fkGponProfile2McastSACL 1 }

                
--  1.3.6.1.4.1.10428 9 1.101.23.51.11.1.1
                -- 1.3.6.1.4.1.10428 9 1.101.23.51.11.1.1
                fkGponProfile2McastSAclEntry OBJECT-TYPE
                        SYNTAX FkGponProfile2McastSAclEntry
                        MAX-ACCESS not-accessible
                        STATUS current
                        DESCRIPTION
                                "key: fkGponProfile2McastIndex, fkGponProfile2McastSAclIndex"
                        INDEX { fkGponProfile2McastIndex, fkGponProfile2McastSAclIndex }
                        ::= { fkGponProfile2McastSAclTable 1 }

                
                FkGponProfile2McastSAclEntry ::=
                        SEQUENCE { 
                                fkGponProfile2McastSAclIndex
                                        Integer32,
                                fkGponProfile2McastSAclVid
                                        Integer32,
                                fkGponProfile2McastSAclDstIpStart
                                        IpAddress,
                                fkGponProfile2McastSAclDstIpEnd
                                        IpAddress,
                                fkGponProfile2McastSAclSrcIp
                                        IpAddress,
                                fkGponProfile2McastSAclBandwidth
                                        Integer32,
                                fkGponProfile2McastSAclGem
                                        Integer32,
                                fkGponProfile2McastSAclCos
                                        Integer32
                         }

--  1.3.6.1.4.1.10428 9 1.101.23.51.11.1.1.1
                -- 1.3.6.1.4.1.10428 9 1.101.23.51.11.1.1.1
                fkGponProfile2McastSAclIndex OBJECT-TYPE
                        SYNTAX Integer32 (1..65535)
                        MAX-ACCESS read-only
                        STATUS current
                        DESCRIPTION
                                "The Mcast statis access-list index."
                        ::= { fkGponProfile2McastSAclEntry 1 }

                
--  1.3.6.1.4.1.10428 9 1.101.23.51.11.1.1.2
                -- 1.3.6.1.4.1.10428 9 1.101.23.51.11.1.1.2
                fkGponProfile2McastSAclVid OBJECT-TYPE
                        SYNTAX Integer32 (0 | 1..4094)
                        MAX-ACCESS read-only
                        STATUS current
                        DESCRIPTION
                                "This specific the VLAN carrying the multicast group DS"
                        ::= { fkGponProfile2McastSAclEntry 2 }

                
--  1.3.6.1.4.1.10428 9 1.101.23.51.11.1.1.3
                -- 1.3.6.1.4.1.10428 9 1.101.23.51.11.1.1.3
                fkGponProfile2McastSAclDstIpStart OBJECT-TYPE
                        SYNTAX IpAddress
                        MAX-ACCESS read-only
                        STATUS current
                        DESCRIPTION
                                "The destination IP range-start."
                        ::= { fkGponProfile2McastSAclEntry 3 }

                
--  1.3.6.1.4.1.10428 9 1.101.23.51.11.1.1.4
                -- 1.3.6.1.4.1.10428 9 1.101.23.51.11.1.1.4
                fkGponProfile2McastSAclDstIpEnd OBJECT-TYPE
                        SYNTAX IpAddress
                        MAX-ACCESS read-only
                        STATUS current
                        DESCRIPTION
                                "The destination IP range-end"
                        ::= { fkGponProfile2McastSAclEntry 4 }

                
--  1.3.6.1.4.1.10428 9 1.101.23.51.11.1.1.5
                -- 1.3.6.1.4.1.10428 9 1.101.23.51.11.1.1.5
                fkGponProfile2McastSAclSrcIp OBJECT-TYPE
                        SYNTAX IpAddress
                        MAX-ACCESS read-only
                        STATUS current
                        DESCRIPTION
                                "The source IP."
                        ::= { fkGponProfile2McastSAclEntry 5 }

                
--  1.3.6.1.4.1.10428 9 1.101.23.51.11.1.1.6
                -- 1.3.6.1.4.1.10428 9 1.101.23.51.11.1.1.6
                fkGponProfile2McastSAclBandwidth OBJECT-TYPE
                        SYNTAX Integer32
                        MAX-ACCESS read-only
                        STATUS current
                        DESCRIPTION
                                "The Imputed group bandwidth"
                        ::= { fkGponProfile2McastSAclEntry 6 }

                
--  1.3.6.1.4.1.10428 9 1.101.23.51.11.1.1.7
                -- 1.3.6.1.4.1.10428 9 1.101.23.51.11.1.1.7
                fkGponProfile2McastSAclGem OBJECT-TYPE
                        SYNTAX Integer32 (1..25)
                        MAX-ACCESS read-only
                        STATUS current
                        DESCRIPTION
                                "EM port ID"
                        ::= { fkGponProfile2McastSAclEntry 7 }

                
                -- 1.3.6.1.4.1.10428 9 1.101.23.51.11.1.1.8
                fkGponProfile2McastSAclCos OBJECT-TYPE
                        SYNTAX Integer32 (0..7)
                        MAX-ACCESS read-only
                        STATUS current
                        DESCRIPTION
                                "The Multicast access-list CoS"
                        ::= { fkGponProfile2McastSAclEntry 8 }

                
--  1.3.6.1.4.1.10428 9 1.101.23.51.11.2
                -- 1.3.6.1.4.1.10428 9 1.101.23.51.11.2
                fkGponProfile2McastSAclControl OBJECT IDENTIFIER ::= { fkGponProfile2McastSACL 2 }

                
--  1.3.6.1.4.1.10428 9 1.101.23.51.11.2.1
                -- 1.3.6.1.4.1.10428 9 1.101.23.51.11.2.1
                fkGponProfile2McastSAclControlRequest OBJECT-TYPE
                        SYNTAX INTEGER
                                {
                                addMcastSACL(1),
                                delMcastSACL(2)
                                }
                        MAX-ACCESS read-write
                        STATUS current
                        DESCRIPTION
                                "The request of a user command"
                        ::= { fkGponProfile2McastSAclControl 1 }

                
--  1.3.6.1.4.1.10428 9 1.101.23.51.11.2.2
                -- 1.3.6.1.4.1.10428 9 1.101.23.51.11.2.2
                fkGponProfile2McastSAclControlStatus OBJECT-TYPE
                        SYNTAX FkControlStatusType
                        MAX-ACCESS read-write
                        STATUS current
                        DESCRIPTION
                                "The status of user command"
                        ::= { fkGponProfile2McastSAclControl 2 }

                
--  1.3.6.1.4.1.10428 9 1.101.23.51.11.2.3
                -- 1.3.6.1.4.1.10428 9 1.101.23.51.11.2.3
                fkGponProfile2McastSAclControlTimer OBJECT-TYPE
                        SYNTAX Gauge32
                        MAX-ACCESS read-write
                        STATUS current
                        DESCRIPTION
                                "The maximum time for the manager for a long running user command"
                        ::= { fkGponProfile2McastSAclControl 3 }

                
--  1.3.6.1.4.1.10428 9 1.101.23.51.11.2.4
                -- 1.3.6.1.4.1.10428 9 1.101.23.51.11.2.4
                fkGponProfile2McastSAclControlTimeStamp OBJECT-TYPE
                        SYNTAX TimeTicks
                        MAX-ACCESS read-write
                        STATUS current
                        DESCRIPTION
                                "The time stamp of the last command(end of command)"
                        ::= { fkGponProfile2McastSAclControl 4 }

                
--  1.3.6.1.4.1.10428 9 1.101.23.51.11.2.5
                -- 1.3.6.1.4.1.10428 9 1.101.23.51.11.2.5
                fkGponProfile2McastSAclControlReqResult OBJECT-TYPE
                        SYNTAX FkControlRequestResultType
                        MAX-ACCESS read-write
                        STATUS current
                        DESCRIPTION
                                "The result of the last user command"
                        ::= { fkGponProfile2McastSAclControl 5 }

                
--  1.3.6.1.4.1.10428 9 1.101.23.51.11.2.6
                -- 1.3.6.1.4.1.10428 9 1.101.23.51.11.2.6
                fkGponProfile2McastSAclControlIndex OBJECT-TYPE
                        SYNTAX Integer32
                        MAX-ACCESS read-write
                        STATUS current
                        DESCRIPTION
                                "The Mcast statis access-list index."
                        ::= { fkGponProfile2McastSAclControl 6 }

                
--  1.3.6.1.4.1.10428 9 1.101.23.51.11.2.7
                -- 1.3.6.1.4.1.10428 9 1.101.23.51.11.2.7
                fkGponProfile2McastSAclControlVid OBJECT-TYPE
                        SYNTAX Integer32 (0 | 1..4094)
                        MAX-ACCESS read-write
                        STATUS current
                        DESCRIPTION
                                "This specific the VLAN carrying the multicast group DS"
                        ::= { fkGponProfile2McastSAclControl 7 }

                
--  1.3.6.1.4.1.10428 9 1.101.23.51.11.2.8
                -- 1.3.6.1.4.1.10428 9 1.101.23.51.11.2.8
                fkGponProfile2McastSAclControlName OBJECT-TYPE
                        SYNTAX OCTET STRING
                        MAX-ACCESS read-write
                        STATUS current
                        DESCRIPTION
                                "The Mcast statis access-list name."
                        ::= { fkGponProfile2McastSAclControl 8 }

                
--  1.3.6.1.4.1.10428 9 1.101.23.51.11.2.9
                -- 1.3.6.1.4.1.10428 9 1.101.23.51.11.2.9
                fkGponProfile2McastSAclControlDstIpStart OBJECT-TYPE
                        SYNTAX IpAddress
                        MAX-ACCESS read-write
                        STATUS current
                        DESCRIPTION
                                "The destination IP range-start."
                        ::= { fkGponProfile2McastSAclControl 9 }

                
--  1.3.6.1.4.1.10428 9 1.101.23.51.11.2.10
                -- 1.3.6.1.4.1.10428 9 1.101.23.51.11.2.10
                fkGponProfile2McastSAclControlDstIpEnd OBJECT-TYPE
                        SYNTAX IpAddress
                        MAX-ACCESS read-write
                        STATUS current
                        DESCRIPTION
                                "The destination IP range-end"
                        ::= { fkGponProfile2McastSAclControl 10 }

                
--  1.3.6.1.4.1.10428 9 1.101.23.51.11.2.11
                -- 1.3.6.1.4.1.10428 9 1.101.23.51.11.2.11
                fkGponProfile2McastSAclControlSrcIp OBJECT-TYPE
                        SYNTAX IpAddress
                        MAX-ACCESS read-write
                        STATUS current
                        DESCRIPTION
                                "The source IP."
                        ::= { fkGponProfile2McastSAclControl 11 }

                
--  1.3.6.1.4.1.10428 9 1.101.23.51.11.2.12
                -- 1.3.6.1.4.1.10428 9 1.101.23.51.11.2.12
                fkGponProfile2McastSAclControlBandwidth OBJECT-TYPE
                        SYNTAX Integer32
                        MAX-ACCESS read-write
                        STATUS current
                        DESCRIPTION
                                "The Imputed group bandwidth"
                        ::= { fkGponProfile2McastSAclControl 12 }

                
--  1.3.6.1.4.1.10428 9 1.101.23.51.11.2.13
                -- 1.3.6.1.4.1.10428 9 1.101.23.51.11.2.13
                fkGponProfile2McastSAclControlGem OBJECT-TYPE
                        SYNTAX Integer32 (1..25)
                        MAX-ACCESS read-write
                        STATUS current
                        DESCRIPTION
                                "The GEM port ID"
                        ::= { fkGponProfile2McastSAclControl 13 }

                
                -- 1.3.6.1.4.1.10428 9 1.101.23.51.11.2.14
                fkGponProfile2McastSAclControlCos OBJECT-TYPE
                        SYNTAX Integer32 (0..7)
                        MAX-ACCESS read-write
                        STATUS current
                        DESCRIPTION
                                "The Multicast access-list CoS"
                        ::= { fkGponProfile2McastSAclControl 14 }

                
--  1.3.6.1.4.1.10428 9 1.101.23.51.11.3
                -- 1.3.6.1.4.1.10428 9 1.101.23.51.11.3
                fkGponProfile2McastSAclNotification OBJECT IDENTIFIER ::= { fkGponProfile2McastSACL 3 }

                
--  1.3.6.1.4.1.10428 9 1.101.23.51.11.3.1
                -- 1.3.6.1.4.1.10428 9 1.101.23.51.11.3.1
                fkGponProfile2McastSAclAdded NOTIFICATION-TYPE
                        OBJECTS { fkGponProfile2McastSAclControlRequest, fkGponProfile2McastSAclControlTimeStamp, fkGponProfile2McastSAclControlReqResult, fkGponProfile2McastSAclControlVid, fkGponProfile2McastSAclControlName, 
                                fkGponProfile2McastSAclControlDstIpStart, fkGponProfile2McastSAclControlDstIpEnd, fkGponProfile2McastSAclControlSrcIp, fkGponProfile2McastSAclControlBandwidth, fkGponProfile2McastSAclControlGem, 
                                fkGponProfile2McastSAclControlCos }
                        STATUS current
                        DESCRIPTION 
                                "Description."
                        ::= { fkGponProfile2McastSAclNotification 1 }

                
--  1.3.6.1.4.1.10428 9 1.101.23.51.11.3.2
                -- 1.3.6.1.4.1.10428 9 1.101.23.51.11.3.2
                fkGponProfile2McastSAclDeleted NOTIFICATION-TYPE
                        OBJECTS { fkGponProfile2McastSAclControlRequest, fkGponProfile2McastSAclControlTimeStamp, fkGponProfile2McastSAclControlReqResult, fkGponProfile2McastSAclControlName, fkGponProfile2McastSAclControlIndex
                                 }
                        STATUS current
                        DESCRIPTION 
                                "Description."
                        ::= { fkGponProfile2McastSAclNotification 2 }

                
--  1.3.6.1.4.1.10428 9 1.101.23.51.12
                -- 1.3.6.1.4.1.10428 9 1.101.23.51.12
                fkGponProfile2Onu OBJECT IDENTIFIER ::= { fkGponProfile2 12 }

                
--  1.3.6.1.4.1.10428 9 1.101.23.51.12.1
                -- 1.3.6.1.4.1.10428 9 1.101.23.51.12.1
                fkGponProfile2OnuTable OBJECT-TYPE
                        SYNTAX SEQUENCE OF FkGponProfile2OnuEntry
                        MAX-ACCESS not-accessible
                        STATUS current
                        DESCRIPTION
                                "fkGponProfile2OnuTable"
                        ::= { fkGponProfile2Onu 1 }

                
--  1.3.6.1.4.1.10428 9 1.101.23.51.12.1.1
                -- 1.3.6.1.4.1.10428 9 1.101.23.51.12.1.1
                fkGponProfile2OnuEntry OBJECT-TYPE
                        SYNTAX FkGponProfile2OnuEntry
                        MAX-ACCESS not-accessible
                        STATUS current
                        DESCRIPTION
                                "key: fkGponProfile2OnuIndex"
                        INDEX { fkGponProfile2OnuIndex }
                        ::= { fkGponProfile2OnuTable 1 }

                
                FkGponProfile2OnuEntry ::=
                        SEQUENCE { 
                                fkGponProfile2OnuIndex
                                        Integer32,
                                fkGponProfile2OnuName
                                        OCTET STRING,
                                fkGponProfile2OnuRxPowerHighThresh
                                        Integer32,
                                fkGponProfile2OnuRxPowerLowThresh
                                        Integer32,
                                fkGponProfile2OnuRogueAlarmCount
                                        Integer32,
                                fkGponProfile2OnuRoguePollingInterval
                                        Integer32,
                                fkGponProfile2OnuRoguePollingCount
                                        Integer32,
                                fkGponProfile2OnuRogueWaitingTime
                                        Integer32,
                                fkGponProfile2OnuTrafficProfile
                                        OCTET STRING,
                                fkGponProfile2OnuPmProfile
                                        OCTET STRING,
                                fkGponProfile2OnuCircuitPackCardConfigCDs1E1
                                        INTEGER,
                                fkGponProfile2OnuCircuitPackCardConfigCDs1E1J1
                                        INTEGER,
                                fkGponProfile2OnuSWWatchdog
                                        INTEGER,
                                fkGponProfile2OnuLinkPassThrough
                                        INTEGER,
                                fkGponProfile2OnuCpuLoadThr
                                        INTEGER,
                                fkGponProfile2OnuMemoryUsageThr
                                        INTEGER,
                                fkGponProfile2OnuTemperatureHighThr
                                        INTEGER,
                                fkGponProfile2OnuTemperatureLowThr
                                        INTEGER,
                                fkGponProfile2OnuLoopDetectStatus
                                        INTEGER,
                                fkGponProfile2OnuLoopDetectSendPeriod
                                        Integer32,
                                fkGponProfile2OnuLoopDetectDetectedAction
                                        INTEGER,
                                fkGponProfile2OnuLoopDetectBlcokTimer
                                        Integer32,
                                fkGponProfile2OnuTr069Url
                                        OCTET STRING,
                                fkGponProfile2OnuTr069AccessId
                                        OCTET STRING,
                                fkGponProfile2OnuTr069AccessPassword
                                        OCTET STRING,
                                fkGponProfile2OnuTr069Status
                                        INTEGER,
                                fkGponProfile2OnuTr069Tag
                                        Integer32,
                                fkGponProfile2OnuSwitchControlUplinkMacLearning
                                        INTEGER,
                                fkGponPorifle2OnuAniVoltageHighThr
                                        Integer32,
                                fkGponPorifle2OnuAniVoltageLowThr
                                        Integer32,
                                fkGponPorifle2OnuAniTemperatureHighThr
                                        Integer32,
                                fkGponPorifle2OnuAniTemperatureLowThr
                                        Integer32,
                                fkGponPorifle2OnuAniTxBiasHighThr
                                        Integer32,
                                fkGponPorifle2OnuAniTxBiasLowThr
                                        Integer32,
                                fkGponPorifle2OnuAniTxpowerHighThr
                                        Integer32,
                                fkGponPorifle2OnuAniTxpowerLowThr
                                        Integer32,
                                fkGponProfile2OnuIgmpMaxGroups
                                        Integer32,
                                fkGponProfile2OnuIgmpUpRateLimit
                                        Integer32,
                                fkGponProfile2OnuIgmpHostTracking
                                        INTEGER,
                                fkGponProfile2OnuMacFullPolicy
                                        INTEGER,
                                fkGponProfile2OnuCpuPacketLimitBroadcast
                                        Integer32,
                                fkGponProfile2OnuCpuPacketLimitMulticast
                                        Integer32,
                                fkGponProfile2OnuCpuPacketLimitDlf
                                        Integer32
                         }

--  1.3.6.1.4.1.10428 9 1.101.23.51.12.1.1.1
                -- 1.3.6.1.4.1.10428 9 1.101.23.51.12.1.1.1
                fkGponProfile2OnuIndex OBJECT-TYPE
                        SYNTAX Integer32 (1..65535)
                        MAX-ACCESS read-only
                        STATUS current
                        DESCRIPTION
                                "The ONU profile index."
                        ::= { fkGponProfile2OnuEntry 1 }

                
--  1.3.6.1.4.1.10428 9 1.101.23.51.12.1.1.2
                -- 1.3.6.1.4.1.10428 9 1.101.23.51.12.1.1.2
                fkGponProfile2OnuName OBJECT-TYPE
                        SYNTAX OCTET STRING
                        MAX-ACCESS read-only
                        STATUS current
                        DESCRIPTION
                                "The Onu profile name."
                        ::= { fkGponProfile2OnuEntry 2 }

                
--  1.3.6.1.4.1.10428 9 1.101.23.51.12.1.1.3
                -- 1.3.6.1.4.1.10428 9 1.101.23.51.12.1.1.3
                fkGponProfile2OnuRxPowerHighThresh OBJECT-TYPE
                        SYNTAX Integer32 (-127..0 | 255)
                        UNITS "dBm"
                        MAX-ACCESS read-only
                        STATUS current
                        DESCRIPTION
                                "ONU Receive power configuration : high threshold
                                "
                        ::= { fkGponProfile2OnuEntry 3 }

                
--  1.3.6.1.4.1.10428 9 1.101.23.51.12.1.1.4
                -- 1.3.6.1.4.1.10428 9 1.101.23.51.12.1.1.4
                fkGponProfile2OnuRxPowerLowThresh OBJECT-TYPE
                        SYNTAX Integer32 (-127..0 | 255)
                        UNITS "dBm"
                        MAX-ACCESS read-write
                        STATUS current
                        DESCRIPTION
                                "ONU Receive power configuration : low threshold
                                "
                        ::= { fkGponProfile2OnuEntry 4 }

                
--  1.3.6.1.4.1.10428 9 1.101.23.51.12.1.1.5
                -- 1.3.6.1.4.1.10428 9 1.101.23.51.12.1.1.5
                fkGponProfile2OnuRogueAlarmCount OBJECT-TYPE
                        SYNTAX Integer32 (-1 | 1..5)
                        MAX-ACCESS read-only
                        STATUS current
                        DESCRIPTION
                                "The count of rogue onu alarm.
                                "
                        ::= { fkGponProfile2OnuEntry 5 }

                
--  1.3.6.1.4.1.10428 9 1.101.23.51.12.1.1.6
                -- 1.3.6.1.4.1.10428 9 1.101.23.51.12.1.1.6
                fkGponProfile2OnuRoguePollingInterval OBJECT-TYPE
                        SYNTAX Integer32 (-1 | 10..60000)
                        MAX-ACCESS read-only
                        STATUS current
                        DESCRIPTION
                                "The polling interval of rogue alarm.
                                "
                        ::= { fkGponProfile2OnuEntry 6 }

                
--  1.3.6.1.4.1.10428 9 1.101.23.51.12.1.1.7
                -- 1.3.6.1.4.1.10428 9 1.101.23.51.12.1.1.7
                fkGponProfile2OnuRoguePollingCount OBJECT-TYPE
                        SYNTAX Integer32 (1..250)
                        MAX-ACCESS read-only
                        STATUS current
                        DESCRIPTION
                                "The polling count of rogue ONU."
                        ::= { fkGponProfile2OnuEntry 7 }

                
--  1.3.6.1.4.1.10428 9 1.101.23.51.12.1.1.8
                -- 1.3.6.1.4.1.10428 9 1.101.23.51.12.1.1.8
                fkGponProfile2OnuRogueWaitingTime OBJECT-TYPE
                        SYNTAX Integer32 (-1 | 100..50000)
                        UNITS "msec"
                        MAX-ACCESS read-only
                        STATUS current
                        DESCRIPTION
                                "The waiting time of rogue onu alarm
                                "
                        ::= { fkGponProfile2OnuEntry 8 }

                
--  1.3.6.1.4.1.10428 9 1.101.23.51.12.1.1.9
                -- 1.3.6.1.4.1.10428 9 1.101.23.51.12.1.1.9
                fkGponProfile2OnuTrafficProfile OBJECT-TYPE
                        SYNTAX OCTET STRING
                        MAX-ACCESS read-only
                        STATUS current
                        DESCRIPTION
                                "The traffic profile name.
                                "
                        ::= { fkGponProfile2OnuEntry 9 }

                
--  1.3.6.1.4.1.10428 9 1.101.23.51.12.1.1.10
                -- 1.3.6.1.4.1.10428 9 1.101.23.51.12.1.1.10
                fkGponProfile2OnuPmProfile OBJECT-TYPE
                        SYNTAX OCTET STRING
                        MAX-ACCESS read-only
                        STATUS current
                        DESCRIPTION
                                "The PM profile assigned to ONU profile."
                        ::= { fkGponProfile2OnuEntry 10 }

                
                -- 1.3.6.1.4.1.10428 9 1.101.23.51.12.1.1.11
                fkGponProfile2OnuCircuitPackCardConfigCDs1E1 OBJECT-TYPE
                        SYNTAX INTEGER
                                {
                                ds1(0),
                                e1(1),
                                unUsed(255)
                                }
                        MAX-ACCESS read-only
                        STATUS current
                        DESCRIPTION
                                "Card Configuration value in Circuit Pack ME. 
                                                  CDs1E1 -> Configurable DS1/E1
                                                  CDs1E1J1 -> Configurable DS1/E1/J1
                                "
                        ::= { fkGponProfile2OnuEntry 11 }

                
                -- 1.3.6.1.4.1.10428 9 1.101.23.51.12.1.1.12
                fkGponProfile2OnuCircuitPackCardConfigCDs1E1J1 OBJECT-TYPE
                        SYNTAX INTEGER
                                {
                                ds1(0),
                                e1(1),
                                j1(2),
                                unUsed(255)
                                }
                        MAX-ACCESS read-only
                        STATUS current
                        DESCRIPTION
                                "Card Configuration value in Circuit Pack ME. 
                                                  CDs1E1 -> Configurable DS1/E1
                                                  CDs1E1J1 -> Configurable DS1/E1/J1
                                "
                        ::= { fkGponProfile2OnuEntry 12 }

                
                -- 1.3.6.1.4.1.10428 9 1.101.23.51.12.1.1.13
                fkGponProfile2OnuSWWatchdog OBJECT-TYPE
                        SYNTAX INTEGER
                                {
                                disable(0),
                                enable(1)
                                }
                        MAX-ACCESS read-only
                        STATUS current
                        DESCRIPTION
                                "gpon-sw-watchdog (enable|disable)"
                        ::= { fkGponProfile2OnuEntry 13 }

                
                -- 1.3.6.1.4.1.10428 9 1.101.23.51.12.1.1.14
                fkGponProfile2OnuLinkPassThrough OBJECT-TYPE
                        SYNTAX INTEGER
                                {
                                disable(0),
                                enable(1)
                                }
                        MAX-ACCESS read-only
                        STATUS current
                        DESCRIPTION
                                "link-pass-through (enable|disable)"
                        ::= { fkGponProfile2OnuEntry 14 }

                
                -- 1.3.6.1.4.1.10428 9 1.101.23.51.12.1.1.15
                fkGponProfile2OnuCpuLoadThr OBJECT-TYPE
                        SYNTAX INTEGER (0..100)
                        MAX-ACCESS read-only
                        STATUS current
                        DESCRIPTION
                                "The cpu load threshold "
                        ::= { fkGponProfile2OnuEntry 15 }

                
                -- 1.3.6.1.4.1.10428 9 1.101.23.51.12.1.1.16
                fkGponProfile2OnuMemoryUsageThr OBJECT-TYPE
                        SYNTAX INTEGER (0..100)
                        MAX-ACCESS read-only
                        STATUS current
                        DESCRIPTION
                                "The memory usage threshold."
                        ::= { fkGponProfile2OnuEntry 16 }

                
                -- 1.3.6.1.4.1.10428 9 1.101.23.51.12.1.1.17
                fkGponProfile2OnuTemperatureHighThr OBJECT-TYPE
                        SYNTAX INTEGER (-40..0 | 1..100)
                        MAX-ACCESS read-only
                        STATUS current
                        DESCRIPTION
                                "The temperature high threshold"
                        ::= { fkGponProfile2OnuEntry 17 }

                
                -- 1.3.6.1.4.1.10428 9 1.101.23.51.12.1.1.18
                fkGponProfile2OnuTemperatureLowThr OBJECT-TYPE
                        SYNTAX INTEGER (-40..0 | 1..100)
                        MAX-ACCESS read-only
                        STATUS current
                        DESCRIPTION
                                "The temperature low threshold"
                        ::= { fkGponProfile2OnuEntry 18 }

                
                -- 1.3.6.1.4.1.10428 9 1.101.23.51.12.1.1.19
                fkGponProfile2OnuLoopDetectStatus OBJECT-TYPE
                        SYNTAX INTEGER
                                {
                                disable(0),
                                enable(1)
                                }
                        MAX-ACCESS read-only
                        STATUS current
                        DESCRIPTION
                                "The loop detect status."
                        ::= { fkGponProfile2OnuEntry 19 }

                
                -- 1.3.6.1.4.1.10428 9 1.101.23.51.12.1.1.20
                fkGponProfile2OnuLoopDetectSendPeriod OBJECT-TYPE
                        SYNTAX Integer32 (0..65535)
                        MAX-ACCESS read-only
                        STATUS current
                        DESCRIPTION
                                "The sending period configuration for loop dectect. (default:10 sec)
                                0: disable"
                        ::= { fkGponProfile2OnuEntry 20 }

                
                -- 1.3.6.1.4.1.10428 9 1.101.23.51.12.1.1.21
                fkGponProfile2OnuLoopDetectDetectedAction OBJECT-TYPE
                        SYNTAX INTEGER
                                {
                                check(0),
                                block(1)
                                }
                        MAX-ACCESS read-only
                        STATUS current
                        DESCRIPTION
                                "The detected action."
                        ::= { fkGponProfile2OnuEntry 21 }

                
                -- 1.3.6.1.4.1.10428 9 1.101.23.51.12.1.1.22
                fkGponProfile2OnuLoopDetectBlcokTimer OBJECT-TYPE
                        SYNTAX Integer32 (0..65535)
                        MAX-ACCESS read-only
                        STATUS current
                        DESCRIPTION
                                "the block timer. (default:600 sec)
                                0: unlimited."
                        ::= { fkGponProfile2OnuEntry 22 }

                
                -- 1.3.6.1.4.1.10428 9 1.101.23.51.12.1.1.23
                fkGponProfile2OnuTr069Url OBJECT-TYPE
                        SYNTAX OCTET STRING
                        MAX-ACCESS read-only
                        STATUS current
                        DESCRIPTION
                                "The tr-069 management URL"
                        ::= { fkGponProfile2OnuEntry 23 }

                
                -- 1.3.6.1.4.1.10428 9 1.101.23.51.12.1.1.24
                fkGponProfile2OnuTr069AccessId OBJECT-TYPE
                        SYNTAX OCTET STRING
                        MAX-ACCESS read-only
                        STATUS current
                        DESCRIPTION
                                "The tr-069 management Access ID"
                        ::= { fkGponProfile2OnuEntry 24 }

                
                -- 1.3.6.1.4.1.10428 9 1.101.23.51.12.1.1.25
                fkGponProfile2OnuTr069AccessPassword OBJECT-TYPE
                        SYNTAX OCTET STRING
                        MAX-ACCESS read-only
                        STATUS current
                        DESCRIPTION
                                "The tr-069 management Access password"
                        ::= { fkGponProfile2OnuEntry 25 }

                
                -- 1.3.6.1.4.1.10428 9 1.101.23.51.12.1.1.26
                fkGponProfile2OnuTr069Status OBJECT-TYPE
                        SYNTAX INTEGER
                                {
                                disable(0),
                                enable(1)
                                }
                        MAX-ACCESS read-only
                        STATUS current
                        DESCRIPTION
                                "The tr-069 management status"
                        ::= { fkGponProfile2OnuEntry 26 }

                
                -- 1.3.6.1.4.1.10428 9 1.101.23.51.12.1.1.27
                fkGponProfile2OnuTr069Tag OBJECT-TYPE
                        SYNTAX Integer32 (1..4094)
                        MAX-ACCESS read-only
                        STATUS current
                        DESCRIPTION
                                "The Tr069 Vlan tag."
                        ::= { fkGponProfile2OnuEntry 27 }

                
                -- 1.3.6.1.4.1.10428 9 1.101.23.51.12.1.1.28
                fkGponProfile2OnuSwitchControlUplinkMacLearning OBJECT-TYPE
                        SYNTAX INTEGER
                                {
                                disable(0),
                                enable(1)
                                }
                        MAX-ACCESS read-only
                        STATUS current
                        DESCRIPTION
                                "The ONT switch uplink MAC learning"
                        ::= { fkGponProfile2OnuEntry 28 }

                
                -- 1.3.6.1.4.1.10428 9 1.101.23.51.12.1.1.29
                fkGponPorifle2OnuAniVoltageHighThr OBJECT-TYPE
                        SYNTAX Integer32
                        MAX-ACCESS read-only
                        STATUS current
                        DESCRIPTION
                                "The voltage high threshold. (0.1 V)"
                        ::= { fkGponProfile2OnuEntry 29 }

                
                -- 1.3.6.1.4.1.10428 9 1.101.23.51.12.1.1.30
                fkGponPorifle2OnuAniVoltageLowThr OBJECT-TYPE
                        SYNTAX Integer32
                        MAX-ACCESS read-only
                        STATUS current
                        DESCRIPTION
                                "The voltage low threshold. (0.1 V)"
                        ::= { fkGponProfile2OnuEntry 30 }

                
                -- 1.3.6.1.4.1.10428 9 1.101.23.51.12.1.1.31
                fkGponPorifle2OnuAniTemperatureHighThr OBJECT-TYPE
                        SYNTAX Integer32
                        MAX-ACCESS read-only
                        STATUS current
                        DESCRIPTION
                                "The temperature high threshold."
                        ::= { fkGponProfile2OnuEntry 31 }

                
                -- 1.3.6.1.4.1.10428 9 1.101.23.51.12.1.1.32
                fkGponPorifle2OnuAniTemperatureLowThr OBJECT-TYPE
                        SYNTAX Integer32
                        MAX-ACCESS read-only
                        STATUS current
                        DESCRIPTION
                                "The temperature low threshold."
                        ::= { fkGponProfile2OnuEntry 32 }

                
                -- 1.3.6.1.4.1.10428 9 1.101.23.51.12.1.1.33
                fkGponPorifle2OnuAniTxBiasHighThr OBJECT-TYPE
                        SYNTAX Integer32
                        MAX-ACCESS read-only
                        STATUS current
                        DESCRIPTION
                                "The TX-bias high threshold."
                        ::= { fkGponProfile2OnuEntry 33 }

                
                -- 1.3.6.1.4.1.10428 9 1.101.23.51.12.1.1.34
                fkGponPorifle2OnuAniTxBiasLowThr OBJECT-TYPE
                        SYNTAX Integer32
                        MAX-ACCESS read-only
                        STATUS current
                        DESCRIPTION
                                "The TX-bias low threshold."
                        ::= { fkGponProfile2OnuEntry 34 }

                
                -- 1.3.6.1.4.1.10428 9 1.101.23.51.12.1.1.35
                fkGponPorifle2OnuAniTxpowerHighThr OBJECT-TYPE
                        SYNTAX Integer32
                        MAX-ACCESS read-only
                        STATUS current
                        DESCRIPTION
                                "The TX power high threshold. (0.1 dBm)"
                        ::= { fkGponProfile2OnuEntry 35 }

                
                -- 1.3.6.1.4.1.10428 9 1.101.23.51.12.1.1.36
                fkGponPorifle2OnuAniTxpowerLowThr OBJECT-TYPE
                        SYNTAX Integer32
                        MAX-ACCESS read-only
                        STATUS current
                        DESCRIPTION
                                "The TX power low threshold. (0.1 dBm)"
                        ::= { fkGponProfile2OnuEntry 36 }

                
                -- 1.3.6.1.4.1.10428 9 1.101.23.51.12.1.1.37
                fkGponProfile2OnuIgmpMaxGroups OBJECT-TYPE
                        SYNTAX Integer32 (0..255)
                        MAX-ACCESS read-only
                        STATUS current
                        DESCRIPTION
                                "The max count of IGMP group. (0:unlimited)"
                        ::= { fkGponProfile2OnuEntry 37 }

                
                -- 1.3.6.1.4.1.10428 9 1.101.23.51.12.1.1.38
                fkGponProfile2OnuIgmpUpRateLimit OBJECT-TYPE
                        SYNTAX Integer32 (0..65535)
                        MAX-ACCESS read-only
                        STATUS current
                        DESCRIPTION
                                "The IGMP upstream rate limit.(0:unlimited)"
                        ::= { fkGponProfile2OnuEntry 38 }

                
                -- 1.3.6.1.4.1.10428 9 1.101.23.51.12.1.1.39
                fkGponProfile2OnuIgmpHostTracking OBJECT-TYPE
                        SYNTAX INTEGER
                                {
                                disable(0),
                                enable(1)
                                }
                        MAX-ACCESS read-only
                        STATUS current
                        DESCRIPTION
                                "Igmp Host Tracking (enable|disable)"
                        ::= { fkGponProfile2OnuEntry 39 }

                
                -- 1.3.6.1.4.1.10428 9 1.101.23.51.12.1.1.40
                fkGponProfile2OnuMacFullPolicy OBJECT-TYPE
                        SYNTAX INTEGER
                                {
                                drop(0),
                                forward(1)
                                }
                        MAX-ACCESS read-only
                        STATUS current
                        DESCRIPTION
                                "Mac Full Policy (drop|forward)"
                        ::= { fkGponProfile2OnuEntry 40 }

                
                -- 1.3.6.1.4.1.10428 9 1.101.23.51.12.1.1.41
                fkGponProfile2OnuCpuPacketLimitBroadcast OBJECT-TYPE
                        SYNTAX Integer32 (0..65535)
                        MAX-ACCESS read-only
                        STATUS current
                        DESCRIPTION
                                "CPU Packet Limit Broadcast"
                        ::= { fkGponProfile2OnuEntry 41 }

                
                -- 1.3.6.1.4.1.10428 9 1.101.23.51.12.1.1.42
                fkGponProfile2OnuCpuPacketLimitMulticast OBJECT-TYPE
                        SYNTAX Integer32 (0..65535)
                        MAX-ACCESS read-only
                        STATUS current
                        DESCRIPTION
                                "CPU Packet Limit Multicast"
                        ::= { fkGponProfile2OnuEntry 42 }

                
                -- 1.3.6.1.4.1.10428 9 1.101.23.51.12.1.1.43
                fkGponProfile2OnuCpuPacketLimitDlf OBJECT-TYPE
                        SYNTAX Integer32 (0..65535)
                        MAX-ACCESS read-only
                        STATUS current
                        DESCRIPTION
                                "CPU Packet Limit L2 DLF"
                        ::= { fkGponProfile2OnuEntry 43 }

                
--  1.3.6.1.4.1.10428 9 1.101.23.51.12.2
                -- 1.3.6.1.4.1.10428 9 1.101.23.51.12.2
                fkGponProfile2OnuControl OBJECT IDENTIFIER ::= { fkGponProfile2Onu 2 }

                
--  1.3.6.1.4.1.10428 9 1.101.23.51.12.2.1
                -- 1.3.6.1.4.1.10428 9 1.101.23.51.12.2.1
                fkGponProfile2OnuControlRequest OBJECT-TYPE
                        SYNTAX INTEGER
                                {
                                addOnuProfile(1),
                                delOnuProfile(2),
                                setRogueOnuInfo(3),
                                setRxPower(4),
                                setTrafficProfile(5),
                                setPmProfile(6),
                                setCircuitPack(7),
                                setSWWatchdog(8),
                                setLinkPassThrough(9),
                                setCpuLoadThr(10),
                                setMemoryUsageThr(11),
                                setTemperatureHighThr(12),
                                setTemperatureLowThr(13),
                                setLoopDetect(14),
                                setTr069Url(15),
                                clearTr069Url(16),
                                setTr069Status(17),
                                setTr069Access(18),
                                clearTr069Access(19),
                                setTr069Tag(20),
                                clearTr069Tag(21),
                                setSwitchControl(22),
                                setAniVoltageHighThr(23),
                                setAniVoltageLowThr(24),
                                setAniTemperatureHighThr(25),
                                setAniTemperatureLowThr(26),
                                setAniTxBiasHighThr(27),
                                setAniTxBiasLowThr(28),
                                setAniTxpowerHighThr(29),
                                setAniTxpowerLowThr(30),
                                setIgmpMaxGroups(31),
                                setIgmpUpRateLimit(32),
                                setIgmpHostTracking(33),
                                setMacFullPolicy(34),
                                setCpuPacketLimitBroadcast(35),
                                setCpuPacketLimitMulticast(36),
                                setCpuPacketLimitDlf(37)
                                }
                        MAX-ACCESS read-write
                        STATUS current
                        DESCRIPTION
                                "The request of a user command"
                        ::= { fkGponProfile2OnuControl 1 }

                
--  1.3.6.1.4.1.10428 9 1.101.23.51.12.2.2
                -- 1.3.6.1.4.1.10428 9 1.101.23.51.12.2.2
                fkGponProfile2OnuControlStatus OBJECT-TYPE
                        SYNTAX FkControlStatusType
                        MAX-ACCESS read-only
                        STATUS current
                        DESCRIPTION
                                "The status of user command"
                        ::= { fkGponProfile2OnuControl 2 }

                
--  1.3.6.1.4.1.10428 9 1.101.23.51.12.2.3
                -- 1.3.6.1.4.1.10428 9 1.101.23.51.12.2.3
                fkGponProfile2OnuControlTimer OBJECT-TYPE
                        SYNTAX Gauge32
                        MAX-ACCESS read-write
                        STATUS current
                        DESCRIPTION
                                "The maximum time for the manager for a long running user command"
                        ::= { fkGponProfile2OnuControl 3 }

                
--  1.3.6.1.4.1.10428 9 1.101.23.51.12.2.4
                -- 1.3.6.1.4.1.10428 9 1.101.23.51.12.2.4
                fkGponProfile2OnuControlTimeStamp OBJECT-TYPE
                        SYNTAX TimeTicks
                        MAX-ACCESS read-only
                        STATUS current
                        DESCRIPTION
                                "The time stamp of the last command(end of command)"
                        ::= { fkGponProfile2OnuControl 4 }

                
--  1.3.6.1.4.1.10428 9 1.101.23.51.12.2.5
                -- 1.3.6.1.4.1.10428 9 1.101.23.51.12.2.5
                fkGponProfile2OnuControlReqResult OBJECT-TYPE
                        SYNTAX FkControlRequestResultType
                        MAX-ACCESS read-write
                        STATUS current
                        DESCRIPTION
                                "The result of the last user command
                                "
                        ::= { fkGponProfile2OnuControl 5 }

                
--  1.3.6.1.4.1.10428 9 1.101.23.51.12.2.6
                -- 1.3.6.1.4.1.10428 9 1.101.23.51.12.2.6
                fkGponProfile2OnuControlName OBJECT-TYPE
                        SYNTAX OCTET STRING
                        MAX-ACCESS read-write
                        STATUS current
                        DESCRIPTION
                                "The Onu profile name."
                        ::= { fkGponProfile2OnuControl 6 }

                
--  1.3.6.1.4.1.10428 9 1.101.23.51.12.2.7
                -- 1.3.6.1.4.1.10428 9 1.101.23.51.12.2.7
                fkGponProfile2OnuControlRxPowerHighThresh OBJECT-TYPE
                        SYNTAX Integer32 (-127..0 | 255)
                        MAX-ACCESS read-write
                        STATUS current
                        DESCRIPTION
                                "ONU Receive power configuration : high threshold"
                        ::= { fkGponProfile2OnuControl 7 }

                
--  1.3.6.1.4.1.10428 9 1.101.23.51.12.2.8
                -- 1.3.6.1.4.1.10428 9 1.101.23.51.12.2.8
                fkGponProfile2OnuControlRxPowerLowThresh OBJECT-TYPE
                        SYNTAX Integer32 (-127..0 | 255)
                        MAX-ACCESS read-write
                        STATUS current
                        DESCRIPTION
                                "ONU Receive power configuration : low threshold"
                        ::= { fkGponProfile2OnuControl 8 }

                
--  1.3.6.1.4.1.10428 9 1.101.23.51.12.2.9
                -- 1.3.6.1.4.1.10428 9 1.101.23.51.12.2.9
                fkGponProfile2OnuControlRogueAlarmCount OBJECT-TYPE
                        SYNTAX Integer32 (-1 | 1..5)
                        MAX-ACCESS read-write
                        STATUS current
                        DESCRIPTION
                                "The count of rogue onu alarm."
                        ::= { fkGponProfile2OnuControl 9 }

                
--  1.3.6.1.4.1.10428 9 1.101.23.51.12.2.10
                -- 1.3.6.1.4.1.10428 9 1.101.23.51.12.2.10
                fkGponProfile2OnuControlRoguePollingInterval OBJECT-TYPE
                        SYNTAX Integer32 (-1 | 10..60000)
                        MAX-ACCESS read-write
                        STATUS current
                        DESCRIPTION
                                "The polling interval of rogue alarm.
                                "
                        ::= { fkGponProfile2OnuControl 10 }

                
--  1.3.6.1.4.1.10428 9 1.101.23.51.12.2.11
                -- 1.3.6.1.4.1.10428 9 1.101.23.51.12.2.11
                fkGponProfile2OnuControlRoguePollingCount OBJECT-TYPE
                        SYNTAX Integer32 (1..250)
                        MAX-ACCESS read-write
                        STATUS current
                        DESCRIPTION
                                "he polling count of rogue ONU."
                        ::= { fkGponProfile2OnuControl 11 }

                
--  1.3.6.1.4.1.10428 9 1.101.23.51.12.2.12
                -- 1.3.6.1.4.1.10428 9 1.101.23.51.12.2.12
                fkGponProfile2OnuControlRogueWaitingTime OBJECT-TYPE
                        SYNTAX Integer32 (-1 | 100..50000)
                        MAX-ACCESS read-write
                        STATUS current
                        DESCRIPTION
                                "The waiting time of rogue onu alarm"
                        ::= { fkGponProfile2OnuControl 12 }

                
--  1.3.6.1.4.1.10428 9 1.101.23.51.12.2.13
                -- 1.3.6.1.4.1.10428 9 1.101.23.51.12.2.13
                fkGponProfile2OnuControlTrafficProfile OBJECT-TYPE
                        SYNTAX OCTET STRING
                        MAX-ACCESS read-write
                        STATUS current
                        DESCRIPTION
                                "The traffic profile name."
                        ::= { fkGponProfile2OnuControl 13 }

                
--  1.3.6.1.4.1.10428 9 1.101.23.51.12.2.14
                -- 1.3.6.1.4.1.10428 9 1.101.23.51.12.2.14
                fkGponProfile2OnuControlPmProfile OBJECT-TYPE
                        SYNTAX OCTET STRING
                        MAX-ACCESS read-write
                        STATUS current
                        DESCRIPTION
                                "The PM profile assigned to ONU profile."
                        ::= { fkGponProfile2OnuControl 14 }

                
                -- 1.3.6.1.4.1.10428 9 1.101.23.51.12.2.15
                fkGponProfile2OnuControlCircuitPackCardConfigCDs1E1 OBJECT-TYPE
                        SYNTAX INTEGER
                                {
                                ds1(0),
                                e1(1),
                                unUsed(255)
                                }
                        MAX-ACCESS read-write
                        STATUS current
                        DESCRIPTION
                                "Card Configuration value in Circuit Pack ME. 
                                                  CDs1E1 -> Configurable DS1/E1
                                                  CDs1E1J1 -> Configurable DS1/E1/J1
                                "
                        ::= { fkGponProfile2OnuControl 15 }

                
                -- 1.3.6.1.4.1.10428 9 1.101.23.51.12.2.16
                fkGponProfile2OnuControlCircuitPackCardConfigCDs1E1J1 OBJECT-TYPE
                        SYNTAX INTEGER
                                {
                                ds1(0),
                                e1(1),
                                j1(2),
                                unUsed(255)
                                }
                        MAX-ACCESS read-write
                        STATUS current
                        DESCRIPTION
                                "Card Configuration value in Circuit Pack ME. 
                                                  CDs1E1 -> Configurable DS1/E1
                                                  CDs1E1J1 -> Configurable DS1/E1/J1
                                "
                        ::= { fkGponProfile2OnuControl 16 }

                
                -- 1.3.6.1.4.1.10428 9 1.101.23.51.12.2.17
                fkGponProfile2OnuControlSWWatchdog OBJECT-TYPE
                        SYNTAX INTEGER
                                {
                                disable(0),
                                enable(1)
                                }
                        MAX-ACCESS read-write
                        STATUS current
                        DESCRIPTION
                                "gpon-sw-watchdog (enable|disable)"
                        ::= { fkGponProfile2OnuControl 17 }

                
                -- 1.3.6.1.4.1.10428 9 1.101.23.51.12.2.18
                fkGponProfile2OnuControlLinkPassThrough OBJECT-TYPE
                        SYNTAX INTEGER
                                {
                                disable(0),
                                enable(1)
                                }
                        MAX-ACCESS read-write
                        STATUS current
                        DESCRIPTION
                                "link-pass-through (enable|disable)"
                        ::= { fkGponProfile2OnuControl 18 }

                
                -- 1.3.6.1.4.1.10428 9 1.101.23.51.12.2.19
                fkGponProfile2OnuControlCpuLoadThr OBJECT-TYPE
                        SYNTAX INTEGER (0..100)
                        MAX-ACCESS read-write
                        STATUS current
                        DESCRIPTION
                                "The cpu load threshold "
                        ::= { fkGponProfile2OnuControl 19 }

                
                -- 1.3.6.1.4.1.10428 9 1.101.23.51.12.2.20
                fkGponProfile2OnuControlMemoryUsageThr OBJECT-TYPE
                        SYNTAX INTEGER (0..100)
                        MAX-ACCESS read-write
                        STATUS current
                        DESCRIPTION
                                "The memory usage threshold."
                        ::= { fkGponProfile2OnuControl 20 }

                
                -- 1.3.6.1.4.1.10428 9 1.101.23.51.12.2.21
                fkGponProfile2OnuControlTemperatureHighThr OBJECT-TYPE
                        SYNTAX INTEGER (-40..0 | 1..100)
                        MAX-ACCESS read-write
                        STATUS current
                        DESCRIPTION
                                "The temperature high threshold"
                        ::= { fkGponProfile2OnuControl 21 }

                
                -- 1.3.6.1.4.1.10428 9 1.101.23.51.12.2.22
                fkGponProfile2OnuControlTemperatureLowThr OBJECT-TYPE
                        SYNTAX INTEGER (-40..0 | 1..100)
                        MAX-ACCESS read-write
                        STATUS current
                        DESCRIPTION
                                "The temperature low threshold"
                        ::= { fkGponProfile2OnuControl 22 }

                
                -- 1.3.6.1.4.1.10428 9 1.101.23.51.12.2.23
                fkGponProfile2OnuControlLoopDetectStatus OBJECT-TYPE
                        SYNTAX INTEGER
                                {
                                disable(0),
                                enable(1)
                                }
                        MAX-ACCESS read-write
                        STATUS current
                        DESCRIPTION
                                "The loop detect status."
                        ::= { fkGponProfile2OnuControl 23 }

                
                -- 1.3.6.1.4.1.10428 9 1.101.23.51.12.2.24
                fkGponProfile2OnuControlLoopDetectSendPeriod OBJECT-TYPE
                        SYNTAX Integer32 (0..65535)
                        MAX-ACCESS read-write
                        STATUS current
                        DESCRIPTION
                                "The sending period configuration for loop dectect. (default:10 sec)
                                0: disable
                                
                                "
                        ::= { fkGponProfile2OnuControl 24 }

                
                -- 1.3.6.1.4.1.10428 9 1.101.23.51.12.2.25
                fkGponProfile2OnuControlLoopDetectDetectedAction OBJECT-TYPE
                        SYNTAX INTEGER
                                {
                                check(0),
                                block(1)
                                }
                        MAX-ACCESS read-write
                        STATUS current
                        DESCRIPTION
                                "The detected action."
                        ::= { fkGponProfile2OnuControl 25 }

                
                -- 1.3.6.1.4.1.10428 9 1.101.23.51.12.2.26
                fkGponProfile2OnuControlLoopDetectBlcokTimer OBJECT-TYPE
                        SYNTAX Integer32 (0..65535)
                        MAX-ACCESS read-write
                        STATUS current
                        DESCRIPTION
                                "the block timer. (default:600 sec)
                                0: unlimited."
                        ::= { fkGponProfile2OnuControl 26 }

                
                -- 1.3.6.1.4.1.10428 9 1.101.23.51.12.2.27
                fkGponProfile2OnuControlTr069Url OBJECT-TYPE
                        SYNTAX OCTET STRING
                        MAX-ACCESS read-write
                        STATUS current
                        DESCRIPTION
                                "The tr-069 management URL"
                        ::= { fkGponProfile2OnuControl 27 }

                
                -- 1.3.6.1.4.1.10428 9 1.101.23.51.12.2.28
                fkGponProfile2OnuControlTr069AccessId OBJECT-TYPE
                        SYNTAX OCTET STRING
                        MAX-ACCESS read-write
                        STATUS current
                        DESCRIPTION
                                "The tr-069 management Access ID"
                        ::= { fkGponProfile2OnuControl 28 }

                
                -- 1.3.6.1.4.1.10428 9 1.101.23.51.12.2.29
                fkGponProfile2OnuControlTr069AccessPassword OBJECT-TYPE
                        SYNTAX OCTET STRING
                        MAX-ACCESS read-write
                        STATUS current
                        DESCRIPTION
                                "The tr-069 management Access password"
                        ::= { fkGponProfile2OnuControl 29 }

                
                -- 1.3.6.1.4.1.10428 9 1.101.23.51.12.2.30
                fkGponProfile2OnuControlTr069Status OBJECT-TYPE
                        SYNTAX INTEGER
                                {
                                disable(0),
                                enable(1)
                                }
                        MAX-ACCESS read-write
                        STATUS current
                        DESCRIPTION
                                "The tr-069 management status"
                        ::= { fkGponProfile2OnuControl 30 }

                
                -- 1.3.6.1.4.1.10428 9 1.101.23.51.12.2.31
                fkGponProfile2OnuControlTr069Tag OBJECT-TYPE
                        SYNTAX Integer32 (1..4094)
                        MAX-ACCESS read-write
                        STATUS current
                        DESCRIPTION
                                "Description."
                        ::= { fkGponProfile2OnuControl 31 }

                
                -- 1.3.6.1.4.1.10428 9 1.101.23.51.12.2.32
                fkGponProfile2OnuControlSwitchControlUplinkMacLearning OBJECT-TYPE
                        SYNTAX INTEGER
                                {
                                disable(0),
                                enable(1)
                                }
                        MAX-ACCESS read-write
                        STATUS current
                        DESCRIPTION
                                "The ONT switch uplink MAC learning"
                        ::= { fkGponProfile2OnuControl 32 }

                
                -- 1.3.6.1.4.1.10428 9 1.101.23.51.12.2.33
                fkGponPorifle2OnuControlAniVoltageHighThr OBJECT-TYPE
                        SYNTAX Integer32
                        MAX-ACCESS read-write
                        STATUS current
                        DESCRIPTION
                                "The voltage high threshold (0.1 V)"
                        ::= { fkGponProfile2OnuControl 33 }

                
                -- 1.3.6.1.4.1.10428 9 1.101.23.51.12.2.34
                fkGponPorifle2OnuControlAniVoltageLowThr OBJECT-TYPE
                        SYNTAX Integer32
                        MAX-ACCESS read-write
                        STATUS current
                        DESCRIPTION
                                "The voltage low threshold (0.1 V)"
                        ::= { fkGponProfile2OnuControl 34 }

                
                -- 1.3.6.1.4.1.10428 9 1.101.23.51.12.2.35
                fkGponPorifle2OnuControlAniTemperatureHighThr OBJECT-TYPE
                        SYNTAX Integer32
                        MAX-ACCESS read-write
                        STATUS current
                        DESCRIPTION
                                "The temperature high threshold"
                        ::= { fkGponProfile2OnuControl 35 }

                
                -- 1.3.6.1.4.1.10428 9 1.101.23.51.12.2.36
                fkGponPorifle2OnuControlAniTemperatureLowThr OBJECT-TYPE
                        SYNTAX Integer32
                        MAX-ACCESS read-write
                        STATUS current
                        DESCRIPTION
                                "The temperature low threshold"
                        ::= { fkGponProfile2OnuControl 36 }

                
                -- 1.3.6.1.4.1.10428 9 1.101.23.51.12.2.37
                fkGponPorifle2OnuControlAniTxBiasHighThr OBJECT-TYPE
                        SYNTAX Integer32
                        MAX-ACCESS read-write
                        STATUS current
                        DESCRIPTION
                                "The tx-bias high threshold"
                        ::= { fkGponProfile2OnuControl 37 }

                
                -- 1.3.6.1.4.1.10428 9 1.101.23.51.12.2.38
                fkGponPorifle2OnuControlAniTxBiasLowThr OBJECT-TYPE
                        SYNTAX Integer32
                        MAX-ACCESS read-write
                        STATUS current
                        DESCRIPTION
                                "The tx-bias low threshold"
                        ::= { fkGponProfile2OnuControl 38 }

                
                -- 1.3.6.1.4.1.10428 9 1.101.23.51.12.2.39
                fkGponPorifle2OnuControlAniTxpowerHighThr OBJECT-TYPE
                        SYNTAX Integer32
                        MAX-ACCESS read-write
                        STATUS current
                        DESCRIPTION
                                "The TX power high threshold (0.1 dBm)"
                        ::= { fkGponProfile2OnuControl 39 }

                
                -- 1.3.6.1.4.1.10428 9 1.101.23.51.12.2.40
                fkGponPorifle2OnuControlAniTxpowerLowThr OBJECT-TYPE
                        SYNTAX Integer32
                        MAX-ACCESS read-write
                        STATUS current
                        DESCRIPTION
                                "The TX power low threshold (0.1 dBm)"
                        ::= { fkGponProfile2OnuControl 40 }

                
                -- 1.3.6.1.4.1.10428 9 1.101.23.51.12.2.41
                fkGponProfile2OnuControlIgmpMaxGroups OBJECT-TYPE
                        SYNTAX Integer32 (0..255)
                        MAX-ACCESS read-write
                        STATUS current
                        DESCRIPTION
                                "The max count of IGMP group. (0:unlimited)"
                        ::= { fkGponProfile2OnuControl 41 }

                
                -- 1.3.6.1.4.1.10428 9 1.101.23.51.12.2.42
                fkGponProfile2OnuControlIgmpUpRateLimit OBJECT-TYPE
                        SYNTAX Integer32 (0..65535)
                        MAX-ACCESS read-write
                        STATUS current
                        DESCRIPTION
                                "The IGMP upstream rate limit.(0:unlimited)"
                        ::= { fkGponProfile2OnuControl 42 }

                
                -- 1.3.6.1.4.1.10428 9 1.101.23.51.12.2.43
                fkGponProfile2OnuControlIgmpHostTracking OBJECT-TYPE
                        SYNTAX INTEGER
                                {
                                disable(0),
                                enable(1)
                                }
                        MAX-ACCESS read-write
                        STATUS current
                        DESCRIPTION
                                "Igmp Host Tracking (enable|disable)"
                        ::= { fkGponProfile2OnuControl 43 }

                
                -- 1.3.6.1.4.1.10428 9 1.101.23.51.12.2.44
                fkGponProfile2OnuControlMacFullPolicy OBJECT-TYPE
                        SYNTAX INTEGER
                                {
                                drop(0),
                                forward(1)
                                }
                        MAX-ACCESS read-write
                        STATUS current
                        DESCRIPTION
                                "The mac table full policy (drop|forward)"
                        ::= { fkGponProfile2OnuControl 44 }

                
                -- 1.3.6.1.4.1.10428 9 1.101.23.51.12.2.45
                fkGponProfile2OnuControlCpuPacketLimitBroadcast OBJECT-TYPE
                        SYNTAX Integer32 (0..65535)
                        MAX-ACCESS read-write
                        STATUS current
                        DESCRIPTION
                                "The cpu packet rate broadcast limit.(0:unlimited)"
                        ::= { fkGponProfile2OnuControl 45 }

                
                -- 1.3.6.1.4.1.10428 9 1.101.23.51.12.2.46
                fkGponProfile2OnuControlCpuPacketLimitMulticast OBJECT-TYPE
                        SYNTAX Integer32 (0..65535)
                        MAX-ACCESS read-write
                        STATUS current
                        DESCRIPTION
                                "The cpu packet rate multicast limit.(0:unlimited)"
                        ::= { fkGponProfile2OnuControl 46 }

                
                -- 1.3.6.1.4.1.10428 9 1.101.23.51.12.2.47
                fkGponProfile2OnuControlCpuPacketLimitDlf OBJECT-TYPE
                        SYNTAX Integer32 (0..65535)
                        MAX-ACCESS read-write
                        STATUS current
                        DESCRIPTION
                                "The cpu packet rate L2 dlf limit.(0:unlimited)"
                        ::= { fkGponProfile2OnuControl 47 }

                
--  1.3.6.1.4.1.10428 9 1.101.23.51.12.3
                -- 1.3.6.1.4.1.10428 9 1.101.23.51.12.3
                fkGponProfile2OnuNotification OBJECT IDENTIFIER ::= { fkGponProfile2Onu 3 }

                
--  1.3.6.1.4.1.10428 9 1.101.23.51.12.3.1
                -- 1.3.6.1.4.1.10428 9 1.101.23.51.12.3.1
                fkGponProfile2OnuAdded NOTIFICATION-TYPE
                        OBJECTS { fkGponProfile2OnuControlRequest, fkGponProfile2OnuControlTimeStamp, fkGponProfile2OnuControlReqResult, fkGponProfile2OnuControlName }
                        STATUS current
                        DESCRIPTION 
                                "Description."
                        ::= { fkGponProfile2OnuNotification 1 }

                
--  1.3.6.1.4.1.10428 9 1.101.23.51.12.3.2
                -- 1.3.6.1.4.1.10428 9 1.101.23.51.12.3.2
                fkGponProfile2OnuDeleted NOTIFICATION-TYPE
                        OBJECTS { fkGponProfile2OnuControlRequest, fkGponProfile2OnuControlTimeStamp, fkGponProfile2OnuControlReqResult, fkGponProfile2OnuControlName }
                        STATUS current
                        DESCRIPTION 
                                "Description."
                        ::= { fkGponProfile2OnuNotification 2 }

                
--  1.3.6.1.4.1.10428 9 1.101.23.51.12.3.3
                -- 1.3.6.1.4.1.10428 9 1.101.23.51.12.3.3
                fkGponProfile2OnuRogueInfoChanged NOTIFICATION-TYPE
                        OBJECTS { fkGponProfile2OnuControlRequest, fkGponProfile2OnuControlTimeStamp, fkGponProfile2OnuControlReqResult, fkGponProfile2OnuControlName, fkGponProfile2OnuControlRogueAlarmCount, 
                                fkGponProfile2OnuControlRoguePollingInterval, fkGponProfile2OnuControlRogueWaitingTime, fkGponProfile2OnuControlRoguePollingCount }
                        STATUS current
                        DESCRIPTION 
                                "Description."
                        ::= { fkGponProfile2OnuNotification 3 }

                
--  1.3.6.1.4.1.10428 9 1.101.23.51.12.3.4
                -- 1.3.6.1.4.1.10428 9 1.101.23.51.12.3.4
                fkGponProfile2OnuRxPowerChanged NOTIFICATION-TYPE
                        OBJECTS { fkGponProfile2OnuControlRequest, fkGponProfile2OnuControlTimeStamp, fkGponProfile2OnuControlReqResult, fkGponProfile2OnuControlName, fkGponProfile2OnuControlRxPowerHighThresh, 
                                fkGponProfile2OnuControlRxPowerLowThresh }
                        STATUS current
                        DESCRIPTION 
                                "Description."
                        ::= { fkGponProfile2OnuNotification 4 }

                
--  1.3.6.1.4.1.10428 9 1.101.23.51.12.3.5
                -- 1.3.6.1.4.1.10428 9 1.101.23.51.12.3.5
                fkGponProfile2OnuTrafficProfileChanged NOTIFICATION-TYPE
                        OBJECTS { fkGponProfile2OnuControlRequest, fkGponProfile2OnuControlTimeStamp, fkGponProfile2OnuControlReqResult, fkGponProfile2OnuControlName, fkGponProfile2OnuControlTrafficProfile
                                 }
                        STATUS current
                        DESCRIPTION 
                                "Description."
                        ::= { fkGponProfile2OnuNotification 5 }

                
--  1.3.6.1.4.1.10428 9 1.101.23.51.12.3.6
                -- 1.3.6.1.4.1.10428 9 1.101.23.51.12.3.6
                fkGponProfile2OnuPmProfileChanged NOTIFICATION-TYPE
                        OBJECTS { fkGponProfile2OnuControlRequest, fkGponProfile2OnuControlTimeStamp, fkGponProfile2OnuControlReqResult, fkGponProfile2OnuControlName, fkGponProfile2OnuControlPmProfile
                                 }
                        STATUS current
                        DESCRIPTION 
                                "Description."
                        ::= { fkGponProfile2OnuNotification 6 }

                
--  1.3.6.1.4.1.10428 9 1.101.23.51.12.3.6
                -- 1.3.6.1.4.1.10428 9 1.101.23.51.12.3.7
                fkGponProfile2OnuCircuitPackChanged NOTIFICATION-TYPE
                        OBJECTS { fkGponProfile2OnuControlRequest, fkGponProfile2OnuControlTimeStamp, fkGponProfile2OnuControlReqResult, fkGponProfile2OnuControlName, fkGponProfile2OnuControlCircuitPackCardConfigCDs1E1, 
                                fkGponProfile2OnuControlCircuitPackCardConfigCDs1E1J1 }
                        STATUS current
                        DESCRIPTION 
                                "Card Configuration value in Circuit Pack ME. 
                                                  CDs1E1 -> Configurable DS1/E1
                                                  CDs1E1J1 -> Configurable DS1/E1/J1
                                "
                        ::= { fkGponProfile2OnuNotification 7 }

                
                -- 1.3.6.1.4.1.10428 9 1.101.23.51.12.3.8
                fkGponProfile2OnuSWWatchdogChanged NOTIFICATION-TYPE
                        OBJECTS { fkGponProfile2OnuControlRequest, fkGponProfile2OnuControlTimeStamp, fkGponProfile2OnuControlReqResult, fkGponProfile2OnuControlSWWatchdog }
                        STATUS current
                        DESCRIPTION 
                                "setSWWatchdog"
                        ::= { fkGponProfile2OnuNotification 8 }

                
                -- 1.3.6.1.4.1.10428 9 1.101.23.51.12.3.9
                fkGponProfile2OnuLinkPassThroughChanged NOTIFICATION-TYPE
                        OBJECTS { fkGponProfile2OnuControlRequest, fkGponProfile2OnuControlTimeStamp, fkGponProfile2OnuControlReqResult, fkGponProfile2OnuControlLinkPassThrough }
                        STATUS current
                        DESCRIPTION 
                                "setLinkPassThrough "
                        ::= { fkGponProfile2OnuNotification 9 }

                
                -- 1.3.6.1.4.1.10428 9 1.101.23.51.12.3.10
                fkGponProfile2OnuCpuLoadThrChanged NOTIFICATION-TYPE
                        OBJECTS { fkGponProfile2OnuControlRequest, fkGponProfile2OnuControlTimeStamp, fkGponProfile2OnuControlReqResult, fkGponProfile2OnuControlCpuLoadThr }
                        STATUS current
                        DESCRIPTION 
                                "setCpuLoadThr"
                        ::= { fkGponProfile2OnuNotification 10 }

                
                -- 1.3.6.1.4.1.10428 9 1.101.23.51.12.3.11
                fkGponProfile2OnuMemoryUsageThrChanged NOTIFICATION-TYPE
                        OBJECTS { fkGponProfile2OnuControlRequest, fkGponProfile2OnuControlTimeStamp, fkGponProfile2OnuControlReqResult, fkGponProfile2OnuControlMemoryUsageThr }
                        STATUS current
                        DESCRIPTION 
                                "setMemoryUsageThr"
                        ::= { fkGponProfile2OnuNotification 11 }

                
                -- 1.3.6.1.4.1.10428 9 1.101.23.51.12.3.12
                fkGponProfile2OnuTemperatureHighThrChanged NOTIFICATION-TYPE
                        OBJECTS { fkGponProfile2OnuControlRequest, fkGponProfile2OnuControlTimeStamp, fkGponProfile2OnuControlReqResult, fkGponProfile2OnuControlTemperatureHighThr }
                        STATUS current
                        DESCRIPTION 
                                "setTemperatureHighThr"
                        ::= { fkGponProfile2OnuNotification 12 }

                
                -- 1.3.6.1.4.1.10428 9 1.101.23.51.12.3.13
                fkGponProfile2OnuTemperatureThrChanged NOTIFICATION-TYPE
                        OBJECTS { fkGponProfile2OnuControlRequest, fkGponProfile2OnuControlTimeStamp, fkGponProfile2OnuControlReqResult, fkGponProfile2OnuControlTemperatureLowThr }
                        STATUS current
                        DESCRIPTION 
                                "setTemperatureLowThr"
                        ::= { fkGponProfile2OnuNotification 13 }

                
                -- 1.3.6.1.4.1.10428 9 1.101.23.51.12.3.14
                fkGponProfile2OnuLoopDetectChanged NOTIFICATION-TYPE
                        OBJECTS { fkGponProfile2OnuControlRequest, fkGponProfile2OnuControlTimeStamp, fkGponProfile2OnuControlReqResult, fkGponProfile2OnuIndex, fkGponProfile2OnuControlName, 
                                fkGponProfile2OnuControlLoopDetectStatus, fkGponProfile2OnuControlLoopDetectSendPeriod, fkGponProfile2OnuControlLoopDetectDetectedAction, fkGponProfile2OnuControlLoopDetectBlcokTimer }
                        STATUS current
                        DESCRIPTION 
                                "setLoopDetect"
                        ::= { fkGponProfile2OnuNotification 14 }

                
                -- 1.3.6.1.4.1.10428 9 1.101.23.51.12.3.15
                fkGponProfile2OnuTr069UrlChanged NOTIFICATION-TYPE
                        OBJECTS { fkGponProfile2OnuControlRequest, fkGponProfile2OnuControlTimeStamp, fkGponProfile2OnuControlReqResult, fkGponProfile2OnuControlTr069Url }
                        STATUS current
                        DESCRIPTION 
                                "setTr069Url "
                        ::= { fkGponProfile2OnuNotification 15 }

                
                -- 1.3.6.1.4.1.10428 9 1.101.23.51.12.3.16
                fkGponProfile2OnuTr069UrlCleared NOTIFICATION-TYPE
                        OBJECTS { fkGponProfile2OnuControlRequest, fkGponProfile2OnuControlTimeStamp, fkGponProfile2OnuControlReqResult, fkGponProfile2OnuControlTr069Url }
                        STATUS current
                        DESCRIPTION 
                                "clearTr069Url "
                        ::= { fkGponProfile2OnuNotification 16 }

                
                -- 1.3.6.1.4.1.10428 9 1.101.23.51.12.3.17
                fkGponProfile2OnuTr069StatusChanged NOTIFICATION-TYPE
                        OBJECTS { fkGponProfile2OnuControlRequest, fkGponProfile2OnuControlTimeStamp, fkGponProfile2OnuControlReqResult, fkGponProfile2OnuControlTr069Status }
                        STATUS current
                        DESCRIPTION 
                                "setTr069Status "
                        ::= { fkGponProfile2OnuNotification 17 }

                
                -- 1.3.6.1.4.1.10428 9 1.101.23.51.12.3.18
                fkGponProfile2OnuTr069AccessChanged NOTIFICATION-TYPE
                        OBJECTS { fkGponProfile2OnuControlRequest, fkGponProfile2OnuControlTimeStamp, fkGponProfile2OnuControlReqResult, fkGponProfile2OnuControlTr069AccessId, fkGponProfile2OnuControlTr069AccessPassword
                                 }
                        STATUS current
                        DESCRIPTION 
                                "setTr069Access"
                        ::= { fkGponProfile2OnuNotification 18 }

                
                -- 1.3.6.1.4.1.10428 9 1.101.23.51.12.3.19
                fkGponProfile2OnuTr069AccessCleared NOTIFICATION-TYPE
                        OBJECTS { fkGponProfile2OnuControlRequest, fkGponProfile2OnuControlTimeStamp, fkGponProfile2OnuControlReqResult, fkGponProfile2OnuControlTr069AccessId, fkGponProfile2OnuControlTr069AccessPassword
                                 }
                        STATUS current
                        DESCRIPTION 
                                "clearTr069Access"
                        ::= { fkGponProfile2OnuNotification 19 }

                
                -- 1.3.6.1.4.1.10428 9 1.101.23.51.12.3.20
                fkGponProfile2OnuTr069TagChanged NOTIFICATION-TYPE
                        OBJECTS { fkGponProfile2OnuControlRequest, fkGponProfile2OnuControlTimeStamp, fkGponProfile2OnuControlReqResult, fkGponProfile2OnuControlTr069Tag }
                        STATUS current
                        DESCRIPTION 
                                "setTr069Tag"
                        ::= { fkGponProfile2OnuNotification 20 }

                
                -- 1.3.6.1.4.1.10428 9 1.101.23.51.12.3.21
                fkGponProfile2OnuTr069TagCleared NOTIFICATION-TYPE
                        OBJECTS { fkGponProfile2OnuControlRequest, fkGponProfile2OnuControlTimeStamp, fkGponProfile2OnuControlReqResult, fkGponProfile2OnuControlTr069Tag }
                        STATUS current
                        DESCRIPTION 
                                "clearTr069Tag"
                        ::= { fkGponProfile2OnuNotification 21 }

                
                -- 1.3.6.1.4.1.10428 9 1.101.23.51.12.3.22
                fkGponProfile2OnuSwitchControlChanged NOTIFICATION-TYPE
                        OBJECTS { fkGponProfile2OnuControlRequest, fkGponProfile2OnuControlTimeStamp, fkGponProfile2OnuControlReqResult, fkGponProfile2OnuIndex, fkGponProfile2OnuControlName, 
                                fkGponProfile2OnuControlSwitchControlUplinkMacLearning }
                        STATUS current
                        DESCRIPTION 
                                "setSwitchControl"
                        ::= { fkGponProfile2OnuNotification 22 }

                
                -- 1.3.6.1.4.1.10428 9 1.101.23.51.12.3.23
                fkGponProfile2OnuAniVoltageHighThrChanged NOTIFICATION-TYPE
                        OBJECTS { fkGponProfile2OnuControlRequest, fkGponProfile2OnuControlTimeStamp, fkGponProfile2OnuControlReqResult, fkGponProfile2OnuIndex, fkGponProfile2OnuControlName, 
                                fkGponPorifle2OnuControlAniVoltageHighThr }
                        STATUS current
                        DESCRIPTION 
                                "setAniVoltageHighThr"
                        ::= { fkGponProfile2OnuNotification 23 }

                
                -- 1.3.6.1.4.1.10428 9 1.101.23.51.12.3.24
                fkGponProfile2OnuAniVoltageLowThrChanged NOTIFICATION-TYPE
                        OBJECTS { fkGponProfile2OnuControlRequest, fkGponProfile2OnuControlTimeStamp, fkGponProfile2OnuControlReqResult, fkGponProfile2OnuIndex, fkGponProfile2OnuControlName, 
                                fkGponPorifle2OnuControlAniVoltageLowThr }
                        STATUS current
                        DESCRIPTION 
                                "setAniVoltageLowThr"
                        ::= { fkGponProfile2OnuNotification 24 }

                
                -- 1.3.6.1.4.1.10428 9 1.101.23.51.12.3.25
                fkGponProfile2OnuAniTemperatureHighThrChanged NOTIFICATION-TYPE
                        OBJECTS { fkGponProfile2OnuControlRequest, fkGponProfile2OnuControlTimeStamp, fkGponProfile2OnuControlReqResult, fkGponProfile2OnuIndex, fkGponProfile2OnuControlName, 
                                fkGponPorifle2OnuControlAniTemperatureHighThr }
                        STATUS current
                        DESCRIPTION 
                                "setAniTemperatureHighThr"
                        ::= { fkGponProfile2OnuNotification 25 }

                
                -- 1.3.6.1.4.1.10428 9 1.101.23.51.12.3.26
                fkGponProfile2OnuAniTemperatureLowThrChanged NOTIFICATION-TYPE
                        OBJECTS { fkGponProfile2OnuControlRequest, fkGponProfile2OnuControlTimeStamp, fkGponProfile2OnuControlReqResult, fkGponProfile2OnuIndex, fkGponProfile2OnuControlName, 
                                fkGponPorifle2OnuControlAniTemperatureLowThr }
                        STATUS current
                        DESCRIPTION 
                                "setAniTemperatureLowThr"
                        ::= { fkGponProfile2OnuNotification 26 }

                
                -- 1.3.6.1.4.1.10428 9 1.101.23.51.12.3.27
                fkGponProfile2OnuAniTxBiasHighThrChanged NOTIFICATION-TYPE
                        OBJECTS { fkGponProfile2OnuControlRequest, fkGponProfile2OnuControlTimeStamp, fkGponProfile2OnuControlReqResult, fkGponProfile2OnuIndex, fkGponProfile2OnuControlName, 
                                fkGponPorifle2OnuControlAniTxBiasHighThr }
                        STATUS current
                        DESCRIPTION 
                                "setAniTxBiasHighThr"
                        ::= { fkGponProfile2OnuNotification 27 }

                
                -- 1.3.6.1.4.1.10428 9 1.101.23.51.12.3.28
                fkGponProfile2OnuAniTxBiasLowThrChanged NOTIFICATION-TYPE
                        OBJECTS { fkGponProfile2OnuControlRequest, fkGponProfile2OnuControlTimeStamp, fkGponProfile2OnuControlReqResult, fkGponProfile2OnuIndex, fkGponProfile2OnuControlName, 
                                fkGponPorifle2OnuControlAniTxBiasLowThr }
                        STATUS current
                        DESCRIPTION 
                                "setAniTxBiasLowThr"
                        ::= { fkGponProfile2OnuNotification 28 }

                
                -- 1.3.6.1.4.1.10428 9 1.101.23.51.12.3.29
                fkGponProfile2OnuAniTxpowerHighThrChanged NOTIFICATION-TYPE
                        OBJECTS { fkGponProfile2OnuControlRequest, fkGponProfile2OnuControlTimeStamp, fkGponProfile2OnuControlReqResult, fkGponProfile2OnuIndex, fkGponProfile2OnuControlName, 
                                fkGponPorifle2OnuControlAniTxpowerHighThr }
                        STATUS current
                        DESCRIPTION 
                                "setAniTxpowerHighThr"
                        ::= { fkGponProfile2OnuNotification 29 }

                
                -- 1.3.6.1.4.1.10428 9 1.101.23.51.12.3.30
                fkGponProfile2OnuAniTxpowerLowThrChanged NOTIFICATION-TYPE
                        OBJECTS { fkGponProfile2OnuControlRequest, fkGponProfile2OnuControlTimeStamp, fkGponProfile2OnuControlReqResult, fkGponProfile2OnuIndex, fkGponProfile2OnuControlName, 
                                fkGponPorifle2OnuControlAniTxpowerLowThr }
                        STATUS current
                        DESCRIPTION 
                                "setAniTxpowerLowThr"
                        ::= { fkGponProfile2OnuNotification 30 }

                
                -- 1.3.6.1.4.1.10428 9 1.101.23.51.12.3.31
                fkGponProfile2OnuIgmpMaxGroupsChanged NOTIFICATION-TYPE
                        OBJECTS { fkGponProfile2OnuControlRequest, fkGponProfile2OnuControlTimeStamp, fkGponProfile2OnuControlReqResult, fkGponProfile2OnuControlName, fkGponProfile2OnuControlIgmpMaxGroups
                                 }
                        STATUS current
                        DESCRIPTION 
                                "setIgmpMaxGroups"
                        ::= { fkGponProfile2OnuNotification 31 }

                
                -- 1.3.6.1.4.1.10428 9 1.101.23.51.12.3.32
                fkGponProfile2OnuIgmpUpRateLimitChanged NOTIFICATION-TYPE
                        OBJECTS { fkGponProfile2OnuControlRequest, fkGponProfile2OnuControlTimeStamp, fkGponProfile2OnuControlReqResult, fkGponProfile2OnuControlName, fkGponProfile2OnuControlIgmpUpRateLimit
                                 }
                        STATUS current
                        DESCRIPTION 
                                "setIgmpUpRateLimit"
                        ::= { fkGponProfile2OnuNotification 32 }

                
                -- 1.3.6.1.4.1.10428 9 1.101.23.51.12.3.33
                fkGponProfile2OnuIgmpHostTrackingChanged NOTIFICATION-TYPE
                        OBJECTS { fkGponProfile2OnuControlRequest, fkGponProfile2OnuControlTimeStamp, fkGponProfile2OnuControlReqResult, fkGponProfile2OnuControlName, fkGponProfile2OnuControlIgmpHostTracking
                                 }
                        STATUS current
                        DESCRIPTION 
                                "setIgmpHostTracking"
                        ::= { fkGponProfile2OnuNotification 33 }

                
                -- 1.3.6.1.4.1.10428 9 1.101.23.51.12.3.34
                fkGponProfile2OnuMacFullPolicyChanged NOTIFICATION-TYPE
                        OBJECTS { fkGponProfile2OnuControlRequest, fkGponProfile2OnuControlTimeStamp, fkGponProfile2OnuControlReqResult, fkGponProfile2OnuControlName, fkGponProfile2OnuControlMacFullPolicy
                                 }
                        STATUS current
                        DESCRIPTION 
                                "setMacFullPolicy"
                        ::= { fkGponProfile2OnuNotification 34 }

                
                -- 1.3.6.1.4.1.10428 9 1.101.23.51.12.3.35
                fkGponProfile2OnuCpuPacketLimitBroadcastChanged NOTIFICATION-TYPE
                        OBJECTS { fkGponProfile2OnuControlRequest, fkGponProfile2OnuControlTimeStamp, fkGponProfile2OnuControlReqResult, fkGponProfile2OnuControlName, fkGponProfile2OnuControlCpuPacketLimitBroadcast
                                 }
                        STATUS current
                        DESCRIPTION 
                                "setCpuPacketLimitBroadcast"
                        ::= { fkGponProfile2OnuNotification 35 }

                
                -- 1.3.6.1.4.1.10428 9 1.101.23.51.12.3.36
                fkGponProfile2OnuCpuPacketLimitMulticastChanged NOTIFICATION-TYPE
                        OBJECTS { fkGponProfile2OnuControlRequest, fkGponProfile2OnuControlTimeStamp, fkGponProfile2OnuControlReqResult, fkGponProfile2OnuControlName, fkGponProfile2OnuControlCpuPacketLimitMulticast
                                 }
                        STATUS current
                        DESCRIPTION 
                                "setOnuCpuPacketLimitMulticast"
                        ::= { fkGponProfile2OnuNotification 36 }

                
                -- 1.3.6.1.4.1.10428 9 1.101.23.51.12.3.37
                fkGponProfile2OnuCpuPacketLimitDlfChanged NOTIFICATION-TYPE
                        OBJECTS { fkGponProfile2OnuControlRequest, fkGponProfile2OnuControlTimeStamp, fkGponProfile2OnuControlReqResult, fkGponProfile2OnuControlName, fkGponProfile2OnuControlCpuPacketLimitDlf
                                 }
                        STATUS current
                        DESCRIPTION 
                                "setOnuCpuPacketLimitDlf"
                        ::= { fkGponProfile2OnuNotification 37 }

                
--  1.3.6.1.4.1.10428 9 1.101.23.51.13
                -- 1.3.6.1.4.1.10428 9 1.101.23.51.13
                fkGponProfile2OnuUni OBJECT IDENTIFIER ::= { fkGponProfile2 13 }

                
--  1.3.6.1.4.1.10428 9 1.101.23.51.13.1
                -- 1.3.6.1.4.1.10428 9 1.101.23.51.13.1
                fkGponProfile2OnuUniTable OBJECT-TYPE
                        SYNTAX SEQUENCE OF FkGponProfile2OnuUniEntry
                        MAX-ACCESS not-accessible
                        STATUS current
                        DESCRIPTION
                                "fkGponProfile2OnuUniTable"
                        ::= { fkGponProfile2OnuUni 1 }

                
--  1.3.6.1.4.1.10428 9 1.101.23.51.13.1.1
                -- 1.3.6.1.4.1.10428 9 1.101.23.51.13.1.1
                fkGponProfile2OnuUniEntry OBJECT-TYPE
                        SYNTAX FkGponProfile2OnuUniEntry
                        MAX-ACCESS not-accessible
                        STATUS current
                        DESCRIPTION
                                "key: fkGponProfile2OnuIndex, fkGponProfile2OnuUniId, fkGponProfile2OnuUniType"
                        INDEX { fkGponProfile2OnuIndex, fkGponProfile2OnuUniId, fkGponProfile2OnuUniType }
                        ::= { fkGponProfile2OnuUniTable 1 }

                
                FkGponProfile2OnuUniEntry ::=
                        SEQUENCE { 
                                fkGponProfile2OnuUniId
                                        Integer32,
                                fkGponProfile2OnuUniType
                                        INTEGER,
                                fkGponProfile2OnuUniDownSir
                                        Integer32,
                                fkGponProfile2OnuUniDownPir
                                        Integer32,
                                fkGponProfile2OnuUniVlanDsOper
                                        INTEGER,
                                fkGponProfile2OnuUniVlanUSOper
                                        INTEGER,
                                fkGponProfile2OnuUniVlanUsOperVID
                                        Integer32,
                                fkGponProfile2OnuUniVlanUsOperCoS
                                        Integer32,
                                fkGponProfile2OnuUniIgmpMaxGroup
                                        Integer32,
                                fkGponProfile2OnuUniPortAdmin
                                        INTEGER
                         }

--  1.3.6.1.4.1.10428 9 1.101.23.51.13.1.1.1
                -- 1.3.6.1.4.1.10428 9 1.101.23.51.13.1.1.1
                fkGponProfile2OnuUniId OBJECT-TYPE
                        SYNTAX Integer32 (1..65535)
                        MAX-ACCESS read-only
                        STATUS current
                        DESCRIPTION
                                "The UNI configuration : UNI Id
                                "
                        ::= { fkGponProfile2OnuUniEntry 1 }

                
--  1.3.6.1.4.1.10428 9 1.101.23.51.13.1.1.2
                -- 1.3.6.1.4.1.10428 9 1.101.23.51.13.1.1.2
                fkGponProfile2OnuUniType OBJECT-TYPE
                        SYNTAX INTEGER { eth(1) }
                        MAX-ACCESS read-only
                        STATUS current
                        DESCRIPTION
                                "The UNI configuration : UNI type
                                "
                        ::= { fkGponProfile2OnuUniEntry 2 }

                
--  1.3.6.1.4.1.10428 9 1.101.23.51.13.1.1.3
                -- 1.3.6.1.4.1.10428 9 1.101.23.51.13.1.1.3
                fkGponProfile2OnuUniDownSir OBJECT-TYPE
                        SYNTAX Integer32
                        MAX-ACCESS read-only
                        STATUS current
                        DESCRIPTION
                                "The UNI configuration : rate-limit downstream SIR
                                "
                        ::= { fkGponProfile2OnuUniEntry 3 }

                
--  1.3.6.1.4.1.10428 9 1.101.23.51.13.1.1.4
                -- 1.3.6.1.4.1.10428 9 1.101.23.51.13.1.1.4
                fkGponProfile2OnuUniDownPir OBJECT-TYPE
                        SYNTAX Integer32
                        MAX-ACCESS read-only
                        STATUS current
                        DESCRIPTION
                                "The UNI configuration : rate-limit downstream PIR
                                "
                        ::= { fkGponProfile2OnuUniEntry 4 }

                
--  1.3.6.1.4.1.10428 9 1.101.23.51.13.1.1.5
                -- 1.3.6.1.4.1.10428 9 1.101.23.51.13.1.1.5
                fkGponProfile2OnuUniVlanDsOper OBJECT-TYPE
                        SYNTAX INTEGER
                                {
                                keep(1),
                                overwrite(2),
                                add(3),
                                remove(4),
                                unused(255)
                                }
                        MAX-ACCESS read-only
                        STATUS current
                        DESCRIPTION
                                " VLAN Tagging Operation Data : DS VLAN Tagging Operation mode"
                        ::= { fkGponProfile2OnuUniEntry 5 }

                
--  1.3.6.1.4.1.10428 9 1.101.23.51.13.1.1.6
                -- 1.3.6.1.4.1.10428 9 1.101.23.51.13.1.1.6
                fkGponProfile2OnuUniVlanUSOper OBJECT-TYPE
                        SYNTAX INTEGER
                                {
                                keep(1),
                                overwrite(2),
                                add(3),
                                unused(255)
                                }
                        MAX-ACCESS read-only
                        STATUS current
                        DESCRIPTION
                                " VLAN Tagging Operation Data : US VLAN Tagging Operation mode"
                        ::= { fkGponProfile2OnuUniEntry 6 }

                
--  1.3.6.1.4.1.10428 9 1.101.23.51.13.1.1.7
                -- 1.3.6.1.4.1.10428 9 1.101.23.51.13.1.1.7
                fkGponProfile2OnuUniVlanUsOperVID OBJECT-TYPE
                        SYNTAX Integer32 (0 | 1..4096)
                        MAX-ACCESS read-only
                        STATUS current
                        DESCRIPTION
                                "US VLAN tag VID value"
                        ::= { fkGponProfile2OnuUniEntry 7 }

                
--  1.3.6.1.4.1.10428 9 1.101.23.51.13.1.1.8
                -- 1.3.6.1.4.1.10428 9 1.101.23.51.13.1.1.8
                fkGponProfile2OnuUniVlanUsOperCoS OBJECT-TYPE
                        SYNTAX Integer32 (-1 | 0..7)
                        MAX-ACCESS read-only
                        STATUS current
                        DESCRIPTION
                                " US VLAN tag COS value"
                        ::= { fkGponProfile2OnuUniEntry 8 }

                
--  1.3.6.1.4.1.10428 9 1.101.23.51.13.1.1.9
                -- 1.3.6.1.4.1.10428 9 1.101.23.51.13.1.1.9
                fkGponProfile2OnuUniIgmpMaxGroup OBJECT-TYPE
                        SYNTAX Integer32 (-1 | 0..255)
                        MAX-ACCESS read-only
                        STATUS current
                        DESCRIPTION
                                "The maximum number of IGMP groups"
                        ::= { fkGponProfile2OnuUniEntry 9 }

                
--  1.3.6.1.4.1.10428 9 1.101.23.51.13.1.1.10
                -- 1.3.6.1.4.1.10428 9 1.101.23.51.13.1.1.10
                fkGponProfile2OnuUniPortAdmin OBJECT-TYPE
                        SYNTAX INTEGER
                                {
                                enable(1),
                                disable(2),
                                unknown(255)
                                }
                        MAX-ACCESS read-only
                        STATUS current
                        DESCRIPTION
                                "The port's admin-status."
                        ::= { fkGponProfile2OnuUniEntry 10 }

                
--  1.3.6.1.4.1.10428 9 1.101.23.51.13.2
                -- 1.3.6.1.4.1.10428 9 1.101.23.51.13.2
                fkGponProfile2OnuUniControl OBJECT IDENTIFIER ::= { fkGponProfile2OnuUni 2 }

                
--  1.3.6.1.4.1.10428 9 1.101.23.51.13.2.1
                -- 1.3.6.1.4.1.10428 9 1.101.23.51.13.2.1
                fkGponProfile2OnuUniControlRequest OBJECT-TYPE
                        SYNTAX INTEGER
                                {
                                setUniRateLimit(1),
                                setUniVlanDsOper(2),
                                setUniVlanUsOper(3),
                                setUniIgmpMaxGroup(4),
                                setUniPortAdmin(5)
                                }
                        MAX-ACCESS read-write
                        STATUS current
                        DESCRIPTION
                                "The request of a user command"
                        ::= { fkGponProfile2OnuUniControl 1 }

                
--  1.3.6.1.4.1.10428 9 1.101.23.51.13.2.2
                -- 1.3.6.1.4.1.10428 9 1.101.23.51.13.2.2
                fkGponProfile2OnuUniControlStatus OBJECT-TYPE
                        SYNTAX FkControlStatusType
                        MAX-ACCESS read-only
                        STATUS current
                        DESCRIPTION
                                "The status of user command"
                        ::= { fkGponProfile2OnuUniControl 2 }

                
--  1.3.6.1.4.1.10428 9 1.101.23.51.13.2.3
                -- 1.3.6.1.4.1.10428 9 1.101.23.51.13.2.3
                fkGponProfile2OnuUniControlTimer OBJECT-TYPE
                        SYNTAX Gauge32
                        MAX-ACCESS read-write
                        STATUS current
                        DESCRIPTION
                                "The maximum time for the manager for a long running user command"
                        ::= { fkGponProfile2OnuUniControl 3 }

                
--  1.3.6.1.4.1.10428 9 1.101.23.51.13.2.4
                -- 1.3.6.1.4.1.10428 9 1.101.23.51.13.2.4
                fkGponProfile2OnuUniControlTimeStamp OBJECT-TYPE
                        SYNTAX TimeTicks
                        MAX-ACCESS read-only
                        STATUS current
                        DESCRIPTION
                                "The time stamp of the last command(end of command)"
                        ::= { fkGponProfile2OnuUniControl 4 }

                
--  1.3.6.1.4.1.10428 9 1.101.23.51.13.2.5
                -- 1.3.6.1.4.1.10428 9 1.101.23.51.13.2.5
                fkGponProfile2OnuUniControlReqResult OBJECT-TYPE
                        SYNTAX FkControlRequestResultType
                        MAX-ACCESS read-only
                        STATUS current
                        DESCRIPTION
                                "The result of the last user command"
                        ::= { fkGponProfile2OnuUniControl 5 }

                
--  1.3.6.1.4.1.10428 9 1.101.23.51.13.2.6
                -- 1.3.6.1.4.1.10428 9 1.101.23.51.13.2.6
                fkGponProfile2OnuUniControlOnuProfile OBJECT-TYPE
                        SYNTAX OCTET STRING
                        MAX-ACCESS read-write
                        STATUS current
                        DESCRIPTION
                                "The ONU profile name"
                        ::= { fkGponProfile2OnuUniControl 6 }

                
--  1.3.6.1.4.1.10428 9 1.101.23.51.13.2.7
                -- 1.3.6.1.4.1.10428 9 1.101.23.51.13.2.7
                fkGponProfile2OnuUniControlId OBJECT-TYPE
                        SYNTAX Integer32
                        MAX-ACCESS read-write
                        STATUS current
                        DESCRIPTION
                                "The UNI configuration : UNI Id"
                        ::= { fkGponProfile2OnuUniControl 7 }

                
--  1.3.6.1.4.1.10428 9 1.101.23.51.13.2.8
                -- 1.3.6.1.4.1.10428 9 1.101.23.51.13.2.8
                fkGponProfile2OnuUniControlType OBJECT-TYPE
                        SYNTAX INTEGER { eth(1) }
                        MAX-ACCESS read-write
                        STATUS current
                        DESCRIPTION
                                "The UNI configuration : UNI type"
                        ::= { fkGponProfile2OnuUniControl 8 }

                
--  1.3.6.1.4.1.10428 9 1.101.23.51.13.2.9
                -- 1.3.6.1.4.1.10428 9 1.101.23.51.13.2.9
                fkGponProfile2OnuUniControlDownSir OBJECT-TYPE
                        SYNTAX Integer32
                        MAX-ACCESS read-write
                        STATUS current
                        DESCRIPTION
                                "The UNI configuration : rate-limit downstream SIR
                                "
                        ::= { fkGponProfile2OnuUniControl 9 }

                
--  1.3.6.1.4.1.10428 9 1.101.23.51.13.2.10
                -- 1.3.6.1.4.1.10428 9 1.101.23.51.13.2.10
                fkGponProfile2OnuUniControlDownPir OBJECT-TYPE
                        SYNTAX Integer32
                        MAX-ACCESS read-write
                        STATUS current
                        DESCRIPTION
                                "The UNI configuration : rate-limit downstream PIR"
                        ::= { fkGponProfile2OnuUniControl 10 }

                
--  1.3.6.1.4.1.10428 9 1.101.23.51.13.2.11
                -- 1.3.6.1.4.1.10428 9 1.101.23.51.13.2.11
                fkGponProfile2OnuUniControlVlanDsOper OBJECT-TYPE
                        SYNTAX INTEGER
                                {
                                keep(1),
                                overwrite(2),
                                add(3),
                                remove(4),
                                unused(255)
                                }
                        MAX-ACCESS read-write
                        STATUS current
                        DESCRIPTION
                                " VLAN Tagging Operation Data : DS VLAN Tagging Operation mode"
                        ::= { fkGponProfile2OnuUniControl 11 }

                
--  1.3.6.1.4.1.10428 9 1.101.23.51.13.2.12
                -- 1.3.6.1.4.1.10428 9 1.101.23.51.13.2.12
                fkGponProfile2OnuUniControlVlanUsOper OBJECT-TYPE
                        SYNTAX INTEGER
                                {
                                keep(1),
                                overwrite(2),
                                add(3),
                                unused(255)
                                }
                        MAX-ACCESS read-write
                        STATUS current
                        DESCRIPTION
                                " VLAN Tagging Operation Data : US VLAN Tagging Operation mode"
                        ::= { fkGponProfile2OnuUniControl 12 }

                
--  1.3.6.1.4.1.10428 9 1.101.23.51.13.2.13
                -- 1.3.6.1.4.1.10428 9 1.101.23.51.13.2.13
                fkGponProfile2OnuUniControlVlanUsOperVID OBJECT-TYPE
                        SYNTAX Integer32 (0 | 1..4096)
                        MAX-ACCESS read-write
                        STATUS current
                        DESCRIPTION
                                "US VLAN tag VID value"
                        ::= { fkGponProfile2OnuUniControl 13 }

                
--  1.3.6.1.4.1.10428 9 1.101.23.51.13.2.14
                -- 1.3.6.1.4.1.10428 9 1.101.23.51.13.2.14
                fkGponProfile2OnuUniControlVlanUsOperCoS OBJECT-TYPE
                        SYNTAX Integer32 (-1 | 0..7)
                        MAX-ACCESS read-write
                        STATUS current
                        DESCRIPTION
                                " US VLAN tag COS value"
                        ::= { fkGponProfile2OnuUniControl 14 }

                
--  1.3.6.1.4.1.10428 9 1.101.23.51.13.2.15
                -- 1.3.6.1.4.1.10428 9 1.101.23.51.13.2.15
                fkGponProfile2OnuUniControlIgmpMaxGroup OBJECT-TYPE
                        SYNTAX Integer32 (-1 | 0..255)
                        MAX-ACCESS read-write
                        STATUS current
                        DESCRIPTION
                                "The maximum number of IGMP groups"
                        ::= { fkGponProfile2OnuUniControl 15 }

                
--  1.3.6.1.4.1.10428 9 1.101.23.51.13.2.16
                -- 1.3.6.1.4.1.10428 9 1.101.23.51.13.2.16
                fkGponProfile2OnuUniControlPortAdmin OBJECT-TYPE
                        SYNTAX INTEGER
                                {
                                enable(1),
                                disable(2),
                                unknown(3)
                                }
                        MAX-ACCESS read-write
                        STATUS current
                        DESCRIPTION
                                "The port's admin-status."
                        ::= { fkGponProfile2OnuUniControl 16 }

                
--  1.3.6.1.4.1.10428 9 1.101.23.51.13.3
                -- 1.3.6.1.4.1.10428 9 1.101.23.51.13.3
                fkGponProfile2OnuUniNotification OBJECT IDENTIFIER ::= { fkGponProfile2OnuUni 3 }

                
--  1.3.6.1.4.1.10428 9 1.101.23.51.13.3.1
                -- 1.3.6.1.4.1.10428 9 1.101.23.51.13.3.1
                fkGponProfile2OnuUniRateLimitChanged NOTIFICATION-TYPE
                        OBJECTS { fkGponProfile2OnuUniControlRequest, fkGponProfile2OnuUniControlTimeStamp, fkGponProfile2OnuUniControlReqResult, fkGponProfile2OnuUniControlOnuProfile, fkGponProfile2OnuUniControlId, 
                                fkGponProfile2OnuUniControlType, fkGponProfile2OnuUniControlDownSir, fkGponProfile2OnuUniControlDownPir }
                        STATUS current
                        DESCRIPTION 
                                "Description."
                        ::= { fkGponProfile2OnuUniNotification 1 }

                
--  1.3.6.1.4.1.10428 9 1.101.23.51.13.3.2
                -- 1.3.6.1.4.1.10428 9 1.101.23.51.13.3.2
                fkGponProfile2OnuUniVlanDsOperChanged NOTIFICATION-TYPE
                        OBJECTS { fkGponProfile2OnuUniControlRequest, fkGponProfile2OnuUniControlTimeStamp, fkGponProfile2OnuUniControlReqResult, fkGponProfile2OnuUniControlOnuProfile, fkGponProfile2OnuUniControlId, 
                                fkGponProfile2OnuUniControlType, fkGponProfile2OnuUniControlVlanDsOper }
                        STATUS current
                        DESCRIPTION 
                                "Description."
                        ::= { fkGponProfile2OnuUniNotification 2 }

                
--  1.3.6.1.4.1.10428 9 1.101.23.51.13.3.3
                -- 1.3.6.1.4.1.10428 9 1.101.23.51.13.3.3
                fkGponProfile2OnuUniVlanUsOperChanged NOTIFICATION-TYPE
                        OBJECTS { fkGponProfile2OnuUniControlRequest, fkGponProfile2OnuUniControlTimeStamp, fkGponProfile2OnuUniControlReqResult, fkGponProfile2OnuUniControlOnuProfile, fkGponProfile2OnuUniControlId, 
                                fkGponProfile2OnuUniControlType, fkGponProfile2OnuUniControlVlanUsOper, fkGponProfile2OnuUniControlVlanUsOperVID, fkGponProfile2OnuUniControlVlanUsOperCoS }
                        STATUS current
                        DESCRIPTION 
                                "Description."
                        ::= { fkGponProfile2OnuUniNotification 3 }

                
--  1.3.6.1.4.1.10428 9 1.101.23.51.13.3.4
                -- 1.3.6.1.4.1.10428 9 1.101.23.51.13.3.4
                fkGponProfile2OnuUniIgmpMaxGroupChanged NOTIFICATION-TYPE
                        OBJECTS { fkGponProfile2OnuUniControlRequest, fkGponProfile2OnuUniControlTimeStamp, fkGponProfile2OnuUniControlReqResult, fkGponProfile2OnuUniControlOnuProfile, fkGponProfile2OnuUniControlId, 
                                fkGponProfile2OnuUniControlType, fkGponProfile2OnuUniControlIgmpMaxGroup }
                        STATUS current
                        DESCRIPTION 
                                "Description."
                        ::= { fkGponProfile2OnuUniNotification 4 }

                
--  1.3.6.1.4.1.10428 9 1.101.23.51.13.3.5
                -- 1.3.6.1.4.1.10428 9 1.101.23.51.13.3.5
                fkGponProfile2OnuUniPortAdminChanged NOTIFICATION-TYPE
                        OBJECTS { fkGponProfile2OnuUniControlStatus, fkGponProfile2OnuUniControlTimeStamp, fkGponProfile2OnuUniControlReqResult, fkGponProfile2OnuUniControlOnuProfile, fkGponProfile2OnuUniControlId, 
                                fkGponProfile2OnuUniControlType, fkGponProfile2OnuUniControlPortAdmin }
                        STATUS current
                        DESCRIPTION 
                                "Description."
                        ::= { fkGponProfile2OnuUniNotification 5 }

                
--  1.3.6.1.4.1.10428 9 1.101.23.51.14
                -- 1.3.6.1.4.1.10428 9 1.101.23.51.14
                fkGponProfile2PM OBJECT IDENTIFIER ::= { fkGponProfile2 14 }

                
--  1.3.6.1.4.1.10428 9 1.101.23.51.14.1
                -- 1.3.6.1.4.1.10428 9 1.101.23.51.14.1
                fkGponProfile2PMProfileTable OBJECT-TYPE
                        SYNTAX SEQUENCE OF FkGponProfile2PMProfileEntry
                        MAX-ACCESS not-accessible
                        STATUS current
                        DESCRIPTION
                                "fkGponProfile2PMProfileTable"
                        ::= { fkGponProfile2PM 1 }

                
--  1.3.6.1.4.1.10428 9 1.101.23.51.14.1.1
                -- 1.3.6.1.4.1.10428 9 1.101.23.51.14.1.1
                fkGponProfile2PMProfileEntry OBJECT-TYPE
                        SYNTAX FkGponProfile2PMProfileEntry
                        MAX-ACCESS not-accessible
                        STATUS current
                        DESCRIPTION
                                "key: fkGponProfile2PMProfileIndex"
                        INDEX { fkGponProfile2PMProfileIndex }
                        ::= { fkGponProfile2PMProfileTable 1 }

                
                FkGponProfile2PMProfileEntry ::=
                        SEQUENCE { 
                                fkGponProfile2PMProfileIndex
                                        Integer32,
                                fkGponProfile2PMProfileName
                                        OCTET STRING,
                                fkGponProfile2PMProfilePMGemPort
                                        EnableFlag,
                                fkGponProfile2PMProfilePMAniPort
                                        EnableFlag,
                                fkGponProfile2PMProfilePMUniEthFrameUp
                                        EnableFlag,
                                fkGponProfile2PMProfilePMUniEthFrameDown
                                        EnableFlag,
                                fkGponProfile2PMProfilePMUniEth3
                                        EnableFlag,
                                fkGponProfile2PMProfilePMPseduowire
                                        EnableFlag,
                                fkGponProfile2PMProfilePMUniCes
                                        EnableFlag
                         }

--  1.3.6.1.4.1.10428 9 1.101.23.51.14.1.1.1
                -- 1.3.6.1.4.1.10428 9 1.101.23.51.14.1.1.1
                fkGponProfile2PMProfileIndex OBJECT-TYPE
                        SYNTAX Integer32 (1..65535)
                        MAX-ACCESS read-only
                        STATUS current
                        DESCRIPTION
                                "The PM profile Index"
                        ::= { fkGponProfile2PMProfileEntry 1 }

                
--  1.3.6.1.4.1.10428 9 1.101.23.51.14.1.1.2
                -- 1.3.6.1.4.1.10428 9 1.101.23.51.14.1.1.2
                fkGponProfile2PMProfileName OBJECT-TYPE
                        SYNTAX OCTET STRING
                        MAX-ACCESS read-only
                        STATUS current
                        DESCRIPTION
                                "The Performace Monitoring profile name.
                                "
                        ::= { fkGponProfile2PMProfileEntry 2 }

                
--  1.3.6.1.4.1.10428 9 1.101.23.51.14.1.1.3
                -- 1.3.6.1.4.1.10428 9 1.101.23.51.14.1.1.3
                fkGponProfile2PMProfilePMGemPort OBJECT-TYPE
                        SYNTAX EnableFlag
                        MAX-ACCESS read-only
                        STATUS current
                        DESCRIPTION
                                "The Gemport block counter : enable|disable
                                "
                        ::= { fkGponProfile2PMProfileEntry 3 }

                
--  1.3.6.1.4.1.10428 9 1.101.23.51.14.1.1.4
                -- 1.3.6.1.4.1.10428 9 1.101.23.51.14.1.1.4
                fkGponProfile2PMProfilePMAniPort OBJECT-TYPE
                        SYNTAX EnableFlag
                        MAX-ACCESS read-only
                        STATUS current
                        DESCRIPTION
                                "The ANI port counter : enable|disable
                                "
                        ::= { fkGponProfile2PMProfileEntry 4 }

                
--  1.3.6.1.4.1.10428 9 1.101.23.51.14.1.1.5
                -- 1.3.6.1.4.1.10428 9 1.101.23.51.14.1.1.5
                fkGponProfile2PMProfilePMUniEthFrameUp OBJECT-TYPE
                        SYNTAX EnableFlag
                        MAX-ACCESS read-only
                        STATUS current
                        DESCRIPTION
                                "The Performace Monitoring: UNI Ethernet frame up"
                        ::= { fkGponProfile2PMProfileEntry 5 }

                
--  1.3.6.1.4.1.10428 9 1.101.23.51.14.1.1.6
                -- 1.3.6.1.4.1.10428 9 1.101.23.51.14.1.1.6
                fkGponProfile2PMProfilePMUniEthFrameDown OBJECT-TYPE
                        SYNTAX EnableFlag
                        MAX-ACCESS read-only
                        STATUS current
                        DESCRIPTION
                                "The Performace Monitoring: UNI Ethernet frame down"
                        ::= { fkGponProfile2PMProfileEntry 6 }

                
--  1.3.6.1.4.1.10428 9 1.101.23.51.14.1.1.7
                -- 1.3.6.1.4.1.10428 9 1.101.23.51.14.1.1.7
                fkGponProfile2PMProfilePMUniEth3 OBJECT-TYPE
                        SYNTAX EnableFlag
                        MAX-ACCESS read-only
                        STATUS current
                        DESCRIPTION
                                "The Performace Monitoring: UNI Ethernet 3 flag"
                        ::= { fkGponProfile2PMProfileEntry 7 }

                
                -- 1.3.6.1.4.1.10428 9 1.101.23.51.14.1.1.8
                fkGponProfile2PMProfilePMPseduowire OBJECT-TYPE
                        SYNTAX EnableFlag
                        MAX-ACCESS read-only
                        STATUS current
                        DESCRIPTION
                                "The Pseudowire PM history data counter"
                        ::= { fkGponProfile2PMProfileEntry 8 }

                
                -- 1.3.6.1.4.1.10428 9 1.101.23.51.14.1.1.9
                fkGponProfile2PMProfilePMUniCes OBJECT-TYPE
                        SYNTAX EnableFlag
                        MAX-ACCESS read-only
                        STATUS current
                        DESCRIPTION
                                "Thr UNI CES PM history data counter"
                        ::= { fkGponProfile2PMProfileEntry 9 }

                
--  1.3.6.1.4.1.10428 9 1.101.23.51.14.2
                -- 1.3.6.1.4.1.10428 9 1.101.23.51.14.2
                fkGponProfile2PMProfileControl OBJECT IDENTIFIER ::= { fkGponProfile2PM 2 }

                
--  1.3.6.1.4.1.10428 9 1.101.23.51.14.2.1
                -- 1.3.6.1.4.1.10428 9 1.101.23.51.14.2.1
                fkGponProfile2PMProfileControlRequest OBJECT-TYPE
                        SYNTAX INTEGER
                                {
                                addPmProfile(1),
                                delPmProfile(2),
                                updatePmProfile(3)
                                }
                        MAX-ACCESS read-write
                        STATUS current
                        DESCRIPTION
                                "The request of a user command"
                        ::= { fkGponProfile2PMProfileControl 1 }

                
--  1.3.6.1.4.1.10428 9 1.101.23.51.14.2.2
                -- 1.3.6.1.4.1.10428 9 1.101.23.51.14.2.2
                fkGponProfile2PMProfileControlStatus OBJECT-TYPE
                        SYNTAX FkControlStatusType
                        MAX-ACCESS read-only
                        STATUS current
                        DESCRIPTION
                                "The status of user command"
                        ::= { fkGponProfile2PMProfileControl 2 }

                
--  1.3.6.1.4.1.10428 9 1.101.23.51.14.2.3
                -- 1.3.6.1.4.1.10428 9 1.101.23.51.14.2.3
                fkGponProfile2PMProfileControlTimer OBJECT-TYPE
                        SYNTAX Gauge32
                        MAX-ACCESS read-write
                        STATUS current
                        DESCRIPTION
                                "The maximum time for the manager for a long running user command"
                        ::= { fkGponProfile2PMProfileControl 3 }

                
--  1.3.6.1.4.1.10428 9 1.101.23.51.14.2.4
                -- 1.3.6.1.4.1.10428 9 1.101.23.51.14.2.4
                fkGponProfile2PMProfileControlTimeStamp OBJECT-TYPE
                        SYNTAX TimeTicks
                        MAX-ACCESS read-only
                        STATUS current
                        DESCRIPTION
                                "The time stamp of the last command(end of command)"
                        ::= { fkGponProfile2PMProfileControl 4 }

                
--  1.3.6.1.4.1.10428 9 1.101.23.51.14.2.5
                -- 1.3.6.1.4.1.10428 9 1.101.23.51.14.2.5
                fkGponProfile2PMProfileControlReqResult OBJECT-TYPE
                        SYNTAX FkControlRequestResultType
                        MAX-ACCESS read-only
                        STATUS current
                        DESCRIPTION
                                "The result of the last user command
                                "
                        ::= { fkGponProfile2PMProfileControl 5 }

                
--  1.3.6.1.4.1.10428 9 1.101.23.51.14.2.6
                -- 1.3.6.1.4.1.10428 9 1.101.23.51.14.2.6
                fkGponProfile2PMProfileControlName OBJECT-TYPE
                        SYNTAX OCTET STRING
                        MAX-ACCESS read-write
                        STATUS current
                        DESCRIPTION
                                "The Performace Monitoring profile name.
                                "
                        ::= { fkGponProfile2PMProfileControl 6 }

                
--  1.3.6.1.4.1.10428 9 1.101.23.51.14.2.7
                -- 1.3.6.1.4.1.10428 9 1.101.23.51.14.2.7
                fkGponProfile2PMProfileControlPMGemPort OBJECT-TYPE
                        SYNTAX EnableFlag
                        MAX-ACCESS read-write
                        STATUS current
                        DESCRIPTION
                                "The Gemport block counter : enable|disable"
                        ::= { fkGponProfile2PMProfileControl 7 }

                
--  1.3.6.1.4.1.10428 9 1.101.23.51.14.2.8
                -- 1.3.6.1.4.1.10428 9 1.101.23.51.14.2.8
                fkGponProfile2PMProfileControlPMAniPort OBJECT-TYPE
                        SYNTAX EnableFlag
                        MAX-ACCESS read-write
                        STATUS current
                        DESCRIPTION
                                "The ANI port counter : enable|disable
                                "
                        ::= { fkGponProfile2PMProfileControl 8 }

                
--  1.3.6.1.4.1.10428 9 1.101.23.51.14.2.9
                -- 1.3.6.1.4.1.10428 9 1.101.23.51.14.2.9
                fkGponProfile2PMProfileControlPMUniEthFrameUp OBJECT-TYPE
                        SYNTAX EnableFlag
                        MAX-ACCESS read-write
                        STATUS current
                        DESCRIPTION
                                "The Performace Monitoring: UNI Ethernet frame up"
                        ::= { fkGponProfile2PMProfileControl 9 }

                
--  1.3.6.1.4.1.10428 9 1.101.23.51.14.2.10
                -- 1.3.6.1.4.1.10428 9 1.101.23.51.14.2.10
                fkGponProfile2PMProfileControlPMUniEthFrameDown OBJECT-TYPE
                        SYNTAX EnableFlag
                        MAX-ACCESS read-write
                        STATUS current
                        DESCRIPTION
                                "The Performace Monitoring: UNI Ethernet frame down"
                        ::= { fkGponProfile2PMProfileControl 10 }

                
--  1.3.6.1.4.1.10428 9 1.101.23.51.14.2.11
                -- 1.3.6.1.4.1.10428 9 1.101.23.51.14.2.11
                fkGponProfile2PMProfileControlPMUniEth3 OBJECT-TYPE
                        SYNTAX EnableFlag
                        MAX-ACCESS read-write
                        STATUS current
                        DESCRIPTION
                                "The Performace Monitoring: UNI Ethernet 3 flag"
                        ::= { fkGponProfile2PMProfileControl 11 }

                
                -- 1.3.6.1.4.1.10428 9 1.101.23.51.14.2.12
                fkGponProfile2PMProfileControlPMPseduowire OBJECT-TYPE
                        SYNTAX EnableFlag
                        MAX-ACCESS read-write
                        STATUS current
                        DESCRIPTION
                                "The Pseudowire PM history data counter"
                        ::= { fkGponProfile2PMProfileControl 12 }

                
                -- 1.3.6.1.4.1.10428 9 1.101.23.51.14.2.13
                fkGponProfile2PMProfileControlPMUniCes OBJECT-TYPE
                        SYNTAX EnableFlag
                        MAX-ACCESS read-write
                        STATUS current
                        DESCRIPTION
                                "Thr UNI CES PM history data counter"
                        ::= { fkGponProfile2PMProfileControl 13 }

                
--  1.3.6.1.4.1.10428 9 1.101.23.51.14.3
                -- 1.3.6.1.4.1.10428 9 1.101.23.51.14.3
                fkGponProfile2PMProfileNotification OBJECT IDENTIFIER ::= { fkGponProfile2PM 3 }

                
--  1.3.6.1.4.1.10428 9 1.101.23.51.14.3.1
                -- 1.3.6.1.4.1.10428 9 1.101.23.51.14.3.1
                fkGponProfile2PMProfileAdded NOTIFICATION-TYPE
                        OBJECTS { fkGponProfile2PMProfileControlRequest, fkGponProfile2PMProfileControlTimeStamp, fkGponProfile2PMProfileControlReqResult, fkGponProfile2PMProfileControlName, fkGponProfile2PMProfileControlPMGemPort, 
                                fkGponProfile2PMProfileControlPMAniPort, fkGponProfile2PMProfileControlPMPseduowire, fkGponProfile2PMProfileControlPMUniCes, fkGponProfile2PMProfileControlPMUniEth3, fkGponProfile2PMProfileControlPMUniEthFrameUp, 
                                fkGponProfile2PMProfileControlPMUniEthFrameDown }
                        STATUS current
                        DESCRIPTION 
                                "Description."
                        ::= { fkGponProfile2PMProfileNotification 1 }

                
--  1.3.6.1.4.1.10428 9 1.101.23.51.14.3.2
                -- 1.3.6.1.4.1.10428 9 1.101.23.51.14.3.2
                fkGponProfile2PMProfileDeleted NOTIFICATION-TYPE
                        OBJECTS { fkGponProfile2PMProfileControlRequest, fkGponProfile2PMProfileControlTimeStamp, fkGponProfile2PMProfileControlReqResult, fkGponProfile2PMProfileControlName }
                        STATUS current
                        DESCRIPTION 
                                "Description."
                        ::= { fkGponProfile2PMProfileNotification 2 }

                
                -- 1.3.6.1.4.1.10428 9 1.101.23.51.14.3.3
                fkGponProfile2PMProfileChanged NOTIFICATION-TYPE
                        OBJECTS { fkGponProfile2PMProfileControlRequest, fkGponProfile2PMProfileControlTimeStamp, fkGponProfile2PMProfileControlReqResult, fkGponProfile2PMProfileControlName, fkGponProfile2PMProfileControlPMGemPort, 
                                fkGponProfile2PMProfileControlPMAniPort, fkGponProfile2PMProfileControlPMUniEthFrameUp, fkGponProfile2PMProfileControlPMUniEthFrameDown, fkGponProfile2PMProfileControlPMUniEth3, fkGponProfile2PMProfileControlPMPseduowire, 
                                fkGponProfile2PMProfileControlPMUniCes }
                        STATUS current
                        DESCRIPTION 
                                "Description."
                        ::= { fkGponProfile2PMProfileNotification 3 }

                
--  1.3.6.1.4.1.10428 9 1.101.23.51.15
                -- 1.3.6.1.4.1.10428 9 1.101.23.51.15
                fkGponProfile2OnuBridge OBJECT IDENTIFIER ::= { fkGponProfile2 15 }

                
--  1.3.6.1.4.1.10428 9 1.101.23.51.15.1
                -- 1.3.6.1.4.1.10428 9 1.101.23.51.15.1
                fkGponProfile2OnuBridgeTable OBJECT-TYPE
                        SYNTAX SEQUENCE OF FkGponProfile2OnuBridgeEntry
                        MAX-ACCESS not-accessible
                        STATUS current
                        DESCRIPTION
                                "fkGponProfile2OnuBridgeTable"
                        ::= { fkGponProfile2OnuBridge 1 }

                
--  1.3.6.1.4.1.10428 9 1.101.23.51.15.1.1
                -- 1.3.6.1.4.1.10428 9 1.101.23.51.15.1.1
                fkGponProfile2OnuBridgeEntry OBJECT-TYPE
                        SYNTAX FkGponProfile2OnuBridgeEntry
                        MAX-ACCESS not-accessible
                        STATUS current
                        DESCRIPTION
                                "key: fkGponProfile2OnuIndex, fkGponProfile2OnuBridgeId"
                        INDEX { fkGponProfile2OnuIndex, fkGponProfile2OnuBridgeId }
                        ::= { fkGponProfile2OnuBridgeTable 1 }

                
                FkGponProfile2OnuBridgeEntry ::=
                        SEQUENCE { 
                                fkGponProfile2OnuBridgeId
                                        Integer32,
                                fkGponProfile2OnuBridgeMaxHost
                                        Integer32
                         }

--  1.3.6.1.4.1.10428 9 1.101.23.51.15.1.1.1
                -- 1.3.6.1.4.1.10428 9 1.101.23.51.15.1.1.1
                fkGponProfile2OnuBridgeId OBJECT-TYPE
                        SYNTAX Integer32 (1..65535)
                        MAX-ACCESS read-only
                        STATUS current
                        DESCRIPTION
                                "The MAC bridge id of Onu profile."
                        ::= { fkGponProfile2OnuBridgeEntry 1 }

                
--  1.3.6.1.4.1.10428 9 1.101.23.51.15.1.1.2
                -- 1.3.6.1.4.1.10428 9 1.101.23.51.15.1.1.2
                fkGponProfile2OnuBridgeMaxHost OBJECT-TYPE
                        SYNTAX Integer32 (-1 | 0..255)
                        MAX-ACCESS read-only
                        STATUS current
                        DESCRIPTION
                                "The max-host of MAC bridge."
                        ::= { fkGponProfile2OnuBridgeEntry 2 }

                
--  1.3.6.1.4.1.10428 9 1.101.23.51.15.2
                -- 1.3.6.1.4.1.10428 9 1.101.23.51.15.2
                fkGponProfile2OnuBridgeControl OBJECT IDENTIFIER ::= { fkGponProfile2OnuBridge 2 }

                
--  1.3.6.1.4.1.10428 9 1.101.23.51.15.2.1
                -- 1.3.6.1.4.1.10428 9 1.101.23.51.15.2.1
                fkGponProfile2OnuBridgeControlRequest OBJECT-TYPE
                        SYNTAX INTEGER { setMaxHost(1) }
                        MAX-ACCESS read-write
                        STATUS current
                        DESCRIPTION
                                "The request of a user command"
                        ::= { fkGponProfile2OnuBridgeControl 1 }

                
--  1.3.6.1.4.1.10428 9 1.101.23.51.15.2.2
                -- 1.3.6.1.4.1.10428 9 1.101.23.51.15.2.2
                fkGponProfile2OnuBridgeControlStatus OBJECT-TYPE
                        SYNTAX FkControlStatusType
                        MAX-ACCESS read-only
                        STATUS current
                        DESCRIPTION
                                "The status of user command"
                        ::= { fkGponProfile2OnuBridgeControl 2 }

                
--  1.3.6.1.4.1.10428 9 1.101.23.51.15.2.3
                -- 1.3.6.1.4.1.10428 9 1.101.23.51.15.2.3
                fkGponProfile2OnuBridgeControlTimer OBJECT-TYPE
                        SYNTAX Gauge32
                        MAX-ACCESS read-write
                        STATUS current
                        DESCRIPTION
                                "The maximum time for the manager for a long running user command"
                        ::= { fkGponProfile2OnuBridgeControl 3 }

                
--  1.3.6.1.4.1.10428 9 1.101.23.51.15.2.4
                -- 1.3.6.1.4.1.10428 9 1.101.23.51.15.2.4
                fkGponProfile2OnuBridgeControlTimeStamp OBJECT-TYPE
                        SYNTAX TimeTicks
                        MAX-ACCESS read-only
                        STATUS current
                        DESCRIPTION
                                "The time stamp of the last command(end of command)"
                        ::= { fkGponProfile2OnuBridgeControl 4 }

                
--  1.3.6.1.4.1.10428 9 1.101.23.51.15.2.5
                -- 1.3.6.1.4.1.10428 9 1.101.23.51.15.2.5
                fkGponProfile2OnuBridgeControlReqResult OBJECT-TYPE
                        SYNTAX FkControlRequestResultType
                        MAX-ACCESS read-only
                        STATUS current
                        DESCRIPTION
                                "The result of the last user command
                                "
                        ::= { fkGponProfile2OnuBridgeControl 5 }

                
--  1.3.6.1.4.1.10428 9 1.101.23.51.15.2.6
                -- 1.3.6.1.4.1.10428 9 1.101.23.51.15.2.6
                fkGponProfile2OnuBridgeControlOnuProfile OBJECT-TYPE
                        SYNTAX OCTET STRING
                        MAX-ACCESS read-write
                        STATUS current
                        DESCRIPTION
                                "The ONU profile name."
                        ::= { fkGponProfile2OnuBridgeControl 6 }

                
--  The ONU profile name.
-- 1.3.6.1.4.1.10428 9 1.101.23.51.15.2.7
                -- 1.3.6.1.4.1.10428 9 1.101.23.51.15.2.7
                fkGponProfile2OnuBridgeControlId OBJECT-TYPE
                        SYNTAX Integer32
                        MAX-ACCESS read-write
                        STATUS current
                        DESCRIPTION
                                "The MAC bridge id of Onu profile."
                        ::= { fkGponProfile2OnuBridgeControl 7 }

                
--  1.3.6.1.4.1.10428 9 1.101.23.51.15.2.8
                -- 1.3.6.1.4.1.10428 9 1.101.23.51.15.2.8
                fkGponProfile2OnuBridgeControlMaxHost OBJECT-TYPE
                        SYNTAX Integer32 (-1 | 0..255)
                        MAX-ACCESS read-write
                        STATUS current
                        DESCRIPTION
                                "The max-host of MAC bridge."
                        ::= { fkGponProfile2OnuBridgeControl 8 }

                
--  1.3.6.1.4.1.10428 9 1.101.23.51.15.3
                -- 1.3.6.1.4.1.10428 9 1.101.23.51.15.3
                fkGponProfile2OnuBridgeNotification OBJECT IDENTIFIER ::= { fkGponProfile2OnuBridge 3 }

                
--  1.3.6.1.4.1.10428 9 1.101.23.51.15.3.1
                -- 1.3.6.1.4.1.10428 9 1.101.23.51.15.3.1
                fkGponProfile2OnuBridgeMaxHostChanged NOTIFICATION-TYPE
                        OBJECTS { fkGponProfile2OnuBridgeControlRequest, fkGponProfile2OnuBridgeControlTimeStamp, fkGponProfile2OnuBridgeControlReqResult, fkGponProfile2OnuBridgeControlOnuProfile, fkGponProfile2OnuBridgeControlId, 
                                fkGponProfile2OnuBridgeControlMaxHost }
                        STATUS current
                        DESCRIPTION 
                                "Description."
                        ::= { fkGponProfile2OnuBridgeNotification 1 }

                
--  1.3.6.1.4.1.10428 9 1.101.23.51.16
                -- 1.3.6.1.4.1.10428 9 1.101.23.51.16
                fkGponProfile2OnuTcont OBJECT IDENTIFIER ::= { fkGponProfile2 16 }

                
--  1.3.6.1.4.1.10428 9 1.101.23.51.16.1
                -- 1.3.6.1.4.1.10428 9 1.101.23.51.16.1
                fkGponProfile2OnuTcontTable OBJECT-TYPE
                        SYNTAX SEQUENCE OF FkGponProfile2OnuTcontEntry
                        MAX-ACCESS not-accessible
                        STATUS current
                        DESCRIPTION
                                "fkGponProfile2OnuTcontTable"
                        ::= { fkGponProfile2OnuTcont 1 }

                
--  1.3.6.1.4.1.10428 9 1.101.23.51.16.1.1
                -- 1.3.6.1.4.1.10428 9 1.101.23.51.16.1.1
                fkGponProfile2OnuTcontEntry OBJECT-TYPE
                        SYNTAX FkGponProfile2OnuTcontEntry
                        MAX-ACCESS not-accessible
                        STATUS current
                        DESCRIPTION
                                "key: fkGponProfile2OnuIndex, fkGponProfile2OnuTcontId"
                        INDEX { fkGponProfile2OnuIndex, fkGponProfile2OnuTcontId }
                        ::= { fkGponProfile2OnuTcontTable 1 }

                
                FkGponProfile2OnuTcontEntry ::=
                        SEQUENCE { 
                                fkGponProfile2OnuTcontId
                                        Integer32,
                                fkGponProfile2OnuTcontDbaProfile
                                        OCTET STRING
                         }

--  1.3.6.1.4.1.10428 9 1.101.23.51.16.1.1.1
                -- 1.3.6.1.4.1.10428 9 1.101.23.51.16.1.1.1
                fkGponProfile2OnuTcontId OBJECT-TYPE
                        SYNTAX Integer32 (1..65535)
                        MAX-ACCESS read-only
                        STATUS current
                        DESCRIPTION
                                "The Tcont id of Onu profile."
                        ::= { fkGponProfile2OnuTcontEntry 1 }

                
--  1.3.6.1.4.1.10428 9 1.101.23.51.16.1.1.2
                -- 1.3.6.1.4.1.10428 9 1.101.23.51.16.1.1.2
                fkGponProfile2OnuTcontDbaProfile OBJECT-TYPE
                        SYNTAX OCTET STRING
                        MAX-ACCESS read-only
                        STATUS current
                        DESCRIPTION
                                "The DBA profile name."
                        ::= { fkGponProfile2OnuTcontEntry 2 }

                
--  1.3.6.1.4.1.10428 9 1.101.23.51.16.2
                -- 1.3.6.1.4.1.10428 9 1.101.23.51.16.2
                fkGponProfile2OnuTcontControl OBJECT IDENTIFIER ::= { fkGponProfile2OnuTcont 2 }

                
--  1.3.6.1.4.1.10428 9 1.101.23.51.16.2.1
                -- 1.3.6.1.4.1.10428 9 1.101.23.51.16.2.1
                fkGponProfile2OnuTcontControlRequest OBJECT-TYPE
                        SYNTAX INTEGER { setDbaProfile(1) }
                        MAX-ACCESS read-write
                        STATUS current
                        DESCRIPTION
                                "The request of a user command"
                        ::= { fkGponProfile2OnuTcontControl 1 }

                
--  1.3.6.1.4.1.10428 9 1.101.23.51.16.2.2
                -- 1.3.6.1.4.1.10428 9 1.101.23.51.16.2.2
                fkGponProfile2OnuTcontControlStatus OBJECT-TYPE
                        SYNTAX FkControlStatusType
                        MAX-ACCESS read-only
                        STATUS current
                        DESCRIPTION
                                "The status of user command"
                        ::= { fkGponProfile2OnuTcontControl 2 }

                
--  1.3.6.1.4.1.10428 9 1.101.23.51.16.2.3
                -- 1.3.6.1.4.1.10428 9 1.101.23.51.16.2.3
                fkGponProfile2OnuTcontControlTimer OBJECT-TYPE
                        SYNTAX Gauge32
                        MAX-ACCESS read-write
                        STATUS current
                        DESCRIPTION
                                "The maximum time for the manager for a long running user command"
                        ::= { fkGponProfile2OnuTcontControl 3 }

                
--  1.3.6.1.4.1.10428 9 1.101.23.51.16.2.4
                -- 1.3.6.1.4.1.10428 9 1.101.23.51.16.2.4
                fkGponProfile2OnuTcontControlTimeStamp OBJECT-TYPE
                        SYNTAX TimeTicks
                        MAX-ACCESS read-only
                        STATUS current
                        DESCRIPTION
                                "The time stamp of the last command(end of command)"
                        ::= { fkGponProfile2OnuTcontControl 4 }

                
--  1.3.6.1.4.1.10428 9 1.101.23.51.16.2.5
                -- 1.3.6.1.4.1.10428 9 1.101.23.51.16.2.5
                fkGponProfile2OnuTcontControlReqResult OBJECT-TYPE
                        SYNTAX FkControlRequestResultType
                        MAX-ACCESS read-only
                        STATUS current
                        DESCRIPTION
                                "The result of the last user command"
                        ::= { fkGponProfile2OnuTcontControl 5 }

                
--  1.3.6.1.4.1.10428 9 1.101.23.51.16.2.6
                -- 1.3.6.1.4.1.10428 9 1.101.23.51.16.2.6
                fkGponProfile2OnuTcontControlOnuProfile OBJECT-TYPE
                        SYNTAX OCTET STRING
                        MAX-ACCESS read-write
                        STATUS current
                        DESCRIPTION
                                "The ONU profile name."
                        ::= { fkGponProfile2OnuTcontControl 6 }

                
--  The ONU profile name.
-- 1.3.6.1.4.1.10428 9 1.101.23.51.16.2.7
                -- 1.3.6.1.4.1.10428 9 1.101.23.51.16.2.7
                fkGponProfile2OnuTcontControlId OBJECT-TYPE
                        SYNTAX Integer32
                        MAX-ACCESS read-write
                        STATUS current
                        DESCRIPTION
                                "The Tcont id of Onu profile."
                        ::= { fkGponProfile2OnuTcontControl 7 }

                
--  1.3.6.1.4.1.10428 9 1.101.23.51.16.2.8
                -- 1.3.6.1.4.1.10428 9 1.101.23.51.16.2.8
                fkGponProfile2OnuTcontControlDbaProfile OBJECT-TYPE
                        SYNTAX OCTET STRING
                        MAX-ACCESS read-write
                        STATUS current
                        DESCRIPTION
                                "The DBA profile name."
                        ::= { fkGponProfile2OnuTcontControl 8 }

                
--  1.3.6.1.4.1.10428 9 1.101.23.51.16.3
                -- 1.3.6.1.4.1.10428 9 1.101.23.51.16.3
                fkGponProfile2OnuTcontNotification OBJECT IDENTIFIER ::= { fkGponProfile2OnuTcont 3 }

                
--  1.3.6.1.4.1.10428 9 1.101.23.51.16.3.1
                -- 1.3.6.1.4.1.10428 9 1.101.23.51.16.3.1
                fkGponProfile2OnuTcontDbaProfileChanged NOTIFICATION-TYPE
                        OBJECTS { fkGponProfile2OnuTcontControlRequest, fkGponProfile2OnuTcontControlTimeStamp, fkGponProfile2OnuTcontControlReqResult, fkGponProfile2OnuTcontControlOnuProfile, fkGponProfile2OnuTcontControlId, 
                                fkGponProfile2OnuTcontControlDbaProfile }
                        STATUS current
                        DESCRIPTION 
                                "Description."
                        ::= { fkGponProfile2OnuTcontNotification 1 }

                
                -- 1.3.6.1.4.1.10428 9 1.101.23.51.17
                fkGponProfile2IpHost OBJECT IDENTIFIER ::= { fkGponProfile2 17 }

                
                -- 1.3.6.1.4.1.10428 9 1.101.23.51.17.1
                fkGponProfile2IpHostSvc OBJECT IDENTIFIER ::= { fkGponProfile2IpHost 1 }

                
                -- 1.3.6.1.4.1.10428 9 1.101.23.51.17.1.1
                fkGponProfile2IpHostSvcTable OBJECT-TYPE
                        SYNTAX SEQUENCE OF FkGponProfile2IpHostSvcEntry
                        MAX-ACCESS not-accessible
                        STATUS current
                        DESCRIPTION
                                "fkGponProfile2IpHostSvcTable"
                        ::= { fkGponProfile2IpHostSvc 1 }

                
                -- 1.3.6.1.4.1.10428 9 1.101.23.51.17.1.1.1
                fkGponProfile2IpHostSvcEntry OBJECT-TYPE
                        SYNTAX FkGponProfile2IpHostSvcEntry
                        MAX-ACCESS not-accessible
                        STATUS current
                        DESCRIPTION
                                "key: fkGponProfile2TrafficIndex, fkGponProfile2IpHostSvcId"
                        INDEX { fkGponProfile2TrafficIndex, fkGponProfile2IpHostSvcId }
                        ::= { fkGponProfile2IpHostSvcTable 1 }

                
                FkGponProfile2IpHostSvcEntry ::=
                        SEQUENCE { 
                                fkGponProfile2IpHostSvcId
                                        INTEGER,
                                fkGponProfile2IpHostSvcAddressType
                                        INTEGER,
                                fkGponProfile2IpHostSvcPriDns
                                        IpAddress,
                                fkGponProfile2IpHostSvcSecDns
                                        IpAddress,
                                fkGponProfile2IpHostSvcVlanFilterMode
                                        INTEGER,
                                fkGponProfile2IpHostSvcVlanFilter
                                        OCTET STRING,
                                fkGponProfile2IpHostSvcVlanOpDsOperFlag
                                        INTEGER,
                                fkGponProfile2IpHostSvcVlanOpUsOperFlag
                                        INTEGER,
                                fkGponProfile2IpHostSvcVlanOpUsOperVid
                                        INTEGER,
                                fkGponProfile2IpHostSvcVlanOpUsOperCos
                                        INTEGER,
                                fkGponProfile2IpHostSvcExtVlanName
                                        OCTET STRING
                         }

                -- 1.3.6.1.4.1.10428 9 1.101.23.51.17.1.1.1.1
                fkGponProfile2IpHostSvcId OBJECT-TYPE
                        SYNTAX INTEGER (1..65535)
                        MAX-ACCESS read-only
                        STATUS current
                        DESCRIPTION
                                "The IP host service id of GPON profile."
                        ::= { fkGponProfile2IpHostSvcEntry 1 }

                
                -- 1.3.6.1.4.1.10428 9 1.101.23.51.17.1.1.1.2
                fkGponProfile2IpHostSvcAddressType OBJECT-TYPE
                        SYNTAX INTEGER
                                {
                                unUsed(0),
                                static(1),
                                dhcp(2)
                                }
                        MAX-ACCESS read-only
                        STATUS current
                        DESCRIPTION
                                "The address type.
                                0: unused
                                1: static
                                2: DHCP"
                        ::= { fkGponProfile2IpHostSvcEntry 2 }

                
                -- 1.3.6.1.4.1.10428 9 1.101.23.51.17.1.1.1.3
                fkGponProfile2IpHostSvcPriDns OBJECT-TYPE
                        SYNTAX IpAddress
                        MAX-ACCESS read-only
                        STATUS current
                        DESCRIPTION
                                "The primary DNS address."
                        ::= { fkGponProfile2IpHostSvcEntry 3 }

                
                -- 1.3.6.1.4.1.10428 9 1.101.23.51.17.1.1.1.4
                fkGponProfile2IpHostSvcSecDns OBJECT-TYPE
                        SYNTAX IpAddress
                        MAX-ACCESS read-only
                        STATUS current
                        DESCRIPTION
                                "The second DNS address."
                        ::= { fkGponProfile2IpHostSvcEntry 4 }

                
                -- 1.3.6.1.4.1.10428 9 1.101.23.51.17.1.1.1.5
                fkGponProfile2IpHostSvcVlanFilterMode OBJECT-TYPE
                        SYNTAX INTEGER
                                {
                                unUsed(0),
                                allow(1),
                                deny(2)
                                }
                        MAX-ACCESS read-only
                        STATUS current
                        DESCRIPTION
                                "The VLAN filter mode
                                0: unused
                                1: allow
                                2: deny"
                        ::= { fkGponProfile2IpHostSvcEntry 5 }

                
                -- 1.3.6.1.4.1.10428 9 1.101.23.51.17.1.1.1.6
                fkGponProfile2IpHostSvcVlanFilter OBJECT-TYPE
                        SYNTAX OCTET STRING
                        MAX-ACCESS read-only
                        STATUS current
                        DESCRIPTION
                                "The VLAN filter name."
                        ::= { fkGponProfile2IpHostSvcEntry 6 }

                
                -- 1.3.6.1.4.1.10428 9 1.101.23.51.17.1.1.1.7
                fkGponProfile2IpHostSvcVlanOpDsOperFlag OBJECT-TYPE
                        SYNTAX INTEGER
                                {
                                unUsed(0),
                                keep(1),
                                overwrite(2),
                                add(3),
                                remove(4)
                                }
                        MAX-ACCESS read-only
                        STATUS current
                        DESCRIPTION
                                "The VLAN down stream operation flag
                                "
                        ::= { fkGponProfile2IpHostSvcEntry 7 }

                
                -- 1.3.6.1.4.1.10428 9 1.101.23.51.17.1.1.1.8
                fkGponProfile2IpHostSvcVlanOpUsOperFlag OBJECT-TYPE
                        SYNTAX INTEGER
                                {
                                unUsed(0),
                                keep(1),
                                overwrite(2),
                                add(3),
                                remove(4)
                                }
                        MAX-ACCESS read-only
                        STATUS current
                        DESCRIPTION
                                "The VLAN up stream operation flag"
                        ::= { fkGponProfile2IpHostSvcEntry 8 }

                
                -- 1.3.6.1.4.1.10428 9 1.101.23.51.17.1.1.1.9
                fkGponProfile2IpHostSvcVlanOpUsOperVid OBJECT-TYPE
                        SYNTAX INTEGER (1..65535)
                        MAX-ACCESS read-only
                        STATUS current
                        DESCRIPTION
                                "The VLAN Up stream operation VID."
                        ::= { fkGponProfile2IpHostSvcEntry 9 }

                
                -- 1.3.6.1.4.1.10428 9 1.101.23.51.17.1.1.1.10
                fkGponProfile2IpHostSvcVlanOpUsOperCos OBJECT-TYPE
                        SYNTAX INTEGER (1..65535)
                        MAX-ACCESS read-only
                        STATUS current
                        DESCRIPTION
                                "The VLAN Up stream operation COS."
                        ::= { fkGponProfile2IpHostSvcEntry 10 }

                
                -- 1.3.6.1.4.1.10428 9 1.101.23.51.17.1.1.1.11
                fkGponProfile2IpHostSvcExtVlanName OBJECT-TYPE
                        SYNTAX OCTET STRING
                        MAX-ACCESS read-only
                        STATUS current
                        DESCRIPTION
                                "The Extended vlan name."
                        ::= { fkGponProfile2IpHostSvcEntry 11 }

                
                -- 1.3.6.1.4.1.10428 9 1.101.23.51.17.1.2
                fkGponProfile2IpHostSvcControl OBJECT IDENTIFIER ::= { fkGponProfile2IpHostSvc 2 }

                
                -- 1.3.6.1.4.1.10428 9 1.101.23.51.17.1.2.1
                fkGponProfile2IpHostSvcControlRequest OBJECT-TYPE
                        SYNTAX INTEGER
                                {
                                addIpHostSvc(1),
                                delIpHostSvc(2),
                                setAddressType(3),
                                setDns(4),
                                setVlanFilter(5),
                                setVlanDsOper(6),
                                setVlanUsOper(7),
                                setExtendedVlan(8)
                                }
                        MAX-ACCESS read-write
                        STATUS current
                        DESCRIPTION
                                "The request of a user command"
                        ::= { fkGponProfile2IpHostSvcControl 1 }

                
                -- 1.3.6.1.4.1.10428 9 1.101.23.51.17.1.2.2
                fkGponProfile2IpHostSvcControlStatus OBJECT-TYPE
                        SYNTAX FkControlStatusType
                        MAX-ACCESS read-only
                        STATUS current
                        DESCRIPTION
                                "The status of user command"
                        ::= { fkGponProfile2IpHostSvcControl 2 }

                
                -- 1.3.6.1.4.1.10428 9 1.101.23.51.17.1.2.3
                fkGponProfile2IpHostSvcControlTimer OBJECT-TYPE
                        SYNTAX Gauge32
                        MAX-ACCESS read-write
                        STATUS current
                        DESCRIPTION
                                "The maximum time for the manager for a long running user command"
                        ::= { fkGponProfile2IpHostSvcControl 3 }

                
                -- 1.3.6.1.4.1.10428 9 1.101.23.51.17.1.2.4
                fkGponProfile2IpHostSvcControlTimeStamp OBJECT-TYPE
                        SYNTAX TimeTicks
                        MAX-ACCESS read-only
                        STATUS current
                        DESCRIPTION
                                "The time stamp of the last command(end of command)"
                        ::= { fkGponProfile2IpHostSvcControl 4 }

                
                -- 1.3.6.1.4.1.10428 9 1.101.23.51.17.1.2.5
                fkGponProfile2IpHostSvcControlReqResult OBJECT-TYPE
                        SYNTAX FkControlRequestResultType
                        MAX-ACCESS read-only
                        STATUS current
                        DESCRIPTION
                                "The result of the last user command"
                        ::= { fkGponProfile2IpHostSvcControl 5 }

                
                -- 1.3.6.1.4.1.10428 9 1.101.23.51.17.1.2.6
                fkGponProfile2IpHostSvcControlTName OBJECT-TYPE
                        SYNTAX OCTET STRING
                        MAX-ACCESS read-write
                        STATUS current
                        DESCRIPTION
                                "The Traffic profile name."
                        ::= { fkGponProfile2IpHostSvcControl 6 }
-- The ONU profile name.
                
                -- 1.3.6.1.4.1.10428 9 1.101.23.51.17.1.2.7
                fkGponProfile2IpHostSvcControlId OBJECT-TYPE
                        SYNTAX INTEGER (1..65535)
                        MAX-ACCESS read-write
                        STATUS current
                        DESCRIPTION
                                "The IP host service id of GPON profile."
                        ::= { fkGponProfile2IpHostSvcControl 7 }

                
                -- 1.3.6.1.4.1.10428 9 1.101.23.51.17.1.2.8
                fkGponProfile2IpHostSvcControlAddressType OBJECT-TYPE
                        SYNTAX INTEGER
                                {
                                unUsed(0),
                                static(1),
                                dhcp(2)
                                }
                        MAX-ACCESS read-write
                        STATUS current
                        DESCRIPTION
                                "The address type.
                                0: unused
                                1: static
                                2: DHCP"
                        ::= { fkGponProfile2IpHostSvcControl 8 }

                
                -- 1.3.6.1.4.1.10428 9 1.101.23.51.17.1.2.9
                fkGponProfile2IpHostSvcControlPriDns OBJECT-TYPE
                        SYNTAX IpAddress
                        MAX-ACCESS read-write
                        STATUS current
                        DESCRIPTION
                                "The primary DNS address."
                        ::= { fkGponProfile2IpHostSvcControl 9 }

                
                -- 1.3.6.1.4.1.10428 9 1.101.23.51.17.1.2.10
                fkGponProfile2IpHostSvcControlSecDns OBJECT-TYPE
                        SYNTAX IpAddress
                        MAX-ACCESS read-write
                        STATUS current
                        DESCRIPTION
                                "The second DNS address."
                        ::= { fkGponProfile2IpHostSvcControl 10 }

                
                -- 1.3.6.1.4.1.10428 9 1.101.23.51.17.1.2.11
                fkGponProfile2IpHostSvcControlVlanFilterMode OBJECT-TYPE
                        SYNTAX INTEGER
                                {
                                unUsed(0),
                                allow(1),
                                deny(2)
                                }
                        MAX-ACCESS read-write
                        STATUS current
                        DESCRIPTION
                                "The VLAN filter mode
                                0: unused
                                1: allow
                                2: deny"
                        ::= { fkGponProfile2IpHostSvcControl 11 }

                
                -- 1.3.6.1.4.1.10428 9 1.101.23.51.17.1.2.12
                fkGponProfile2IpHostSvcControlVlanFilter OBJECT-TYPE
                        SYNTAX OCTET STRING
                        MAX-ACCESS read-write
                        STATUS current
                        DESCRIPTION
                                "The VLAN filter name."
                        ::= { fkGponProfile2IpHostSvcControl 12 }

                
                -- 1.3.6.1.4.1.10428 9 1.101.23.51.17.1.2.13
                fkGponProfile2IpHostSvcControlVlanOpDsOperFlag OBJECT-TYPE
                        SYNTAX INTEGER
                                {
                                unUsed(0),
                                keep(1),
                                overwrite(2),
                                add(3),
                                remove(4)
                                }
                        MAX-ACCESS read-write
                        STATUS current
                        DESCRIPTION
                                "The VLAN down stream operation flag
                                "
                        ::= { fkGponProfile2IpHostSvcControl 13 }

                
                -- 1.3.6.1.4.1.10428 9 1.101.23.51.17.1.2.14
                fkGponProfile2IpHostSvcControlVlanOpUsOperFlag OBJECT-TYPE
                        SYNTAX INTEGER
                                {
                                unUsed(0),
                                keep(1),
                                overwrite(2),
                                add(3),
                                remove(4)
                                }
                        MAX-ACCESS read-write
                        STATUS current
                        DESCRIPTION
                                "The VLAN up stream operation flag"
                        ::= { fkGponProfile2IpHostSvcControl 14 }

                
                -- 1.3.6.1.4.1.10428 9 1.101.23.51.17.1.2.15
                fkGponProfile2IpHostSvcControlVlanOpUsOperVid OBJECT-TYPE
                        SYNTAX INTEGER (1..65535)
                        MAX-ACCESS read-write
                        STATUS current
                        DESCRIPTION
                                "The VLAN Up stream operation VID."
                        ::= { fkGponProfile2IpHostSvcControl 15 }

                
                -- 1.3.6.1.4.1.10428 9 1.101.23.51.17.1.2.16
                fkGponProfile2IpHostSvcControlVlanOpUsOperCos OBJECT-TYPE
                        SYNTAX INTEGER (1..65535)
                        MAX-ACCESS read-write
                        STATUS current
                        DESCRIPTION
                                "The VLAN Up stream operation COS."
                        ::= { fkGponProfile2IpHostSvcControl 16 }

                
                -- 1.3.6.1.4.1.10428 9 1.101.23.51.17.1.2.17
                fkGponProfile2IpHostSvcControlExtVlanName OBJECT-TYPE
                        SYNTAX OCTET STRING
                        MAX-ACCESS read-write
                        STATUS current
                        DESCRIPTION
                                "The Extended vlan name."
                        ::= { fkGponProfile2IpHostSvcControl 17 }

                
                -- 1.3.6.1.4.1.10428 9 1.101.23.51.17.1.3
                fkGponProfile2IpHostSvcNotification OBJECT IDENTIFIER ::= { fkGponProfile2IpHostSvc 3 }

                
                -- 1.3.6.1.4.1.10428 9 1.101.23.51.17.1.3.1
                fkGponProfile2IpHostSvcIpHostSvcCreated NOTIFICATION-TYPE
                        OBJECTS { fkGponProfile2IpHostSvcControlRequest, fkGponProfile2IpHostSvcControlTimeStamp, fkGponProfile2IpHostSvcControlReqResult, fkGponProfile2IpHostSvcControlTName, fkGponProfile2IpHostSvcControlId
                                 }
                        STATUS current
                        DESCRIPTION 
                                "Description."
                        ::= { fkGponProfile2IpHostSvcNotification 1 }

                
                -- 1.3.6.1.4.1.10428 9 1.101.23.51.17.1.3.2
                fkGponProfile2IpHostSvcIpHostSvcDeleted NOTIFICATION-TYPE
                        OBJECTS { fkGponProfile2IpHostSvcControlRequest, fkGponProfile2IpHostSvcControlTimeStamp, fkGponProfile2IpHostSvcControlReqResult, fkGponProfile2IpHostSvcControlTName, fkGponProfile2IpHostSvcControlId
                                 }
                        STATUS current
                        DESCRIPTION 
                                "Description."
                        ::= { fkGponProfile2IpHostSvcNotification 2 }

                
                -- 1.3.6.1.4.1.10428 9 1.101.23.51.17.1.3.3
                fkGponProfile2IpHostSvcAddressTypeChanged NOTIFICATION-TYPE
                        OBJECTS { fkGponProfile2IpHostSvcControlRequest, fkGponProfile2IpHostSvcControlTimeStamp, fkGponProfile2IpHostSvcControlReqResult, fkGponProfile2IpHostSvcControlId, fkGponProfile2IpHostSvcControlAddressType
                                 }
                        STATUS current
                        DESCRIPTION 
                                "Description."
                        ::= { fkGponProfile2IpHostSvcNotification 3 }

                
                -- 1.3.6.1.4.1.10428 9 1.101.23.51.17.1.3.4
                fkGponProfile2IpHostSvcDnsChanged NOTIFICATION-TYPE
                        OBJECTS { fkGponProfile2IpHostSvcControlRequest, fkGponProfile2IpHostSvcControlTimeStamp, fkGponProfile2IpHostSvcControlReqResult, fkGponProfile2IpHostSvcControlId, fkGponProfile2IpHostSvcControlPriDns, 
                                fkGponProfile2IpHostSvcControlSecDns }
                        STATUS current
                        DESCRIPTION 
                                "Description."
                        ::= { fkGponProfile2IpHostSvcNotification 4 }

                
                -- 1.3.6.1.4.1.10428 9 1.101.23.51.17.1.3.5
                fkGponProfile2IpHostSvcVlanFilterChanged NOTIFICATION-TYPE
                        OBJECTS { fkGponProfile2IpHostSvcControlRequest, fkGponProfile2IpHostSvcControlTimeStamp, fkGponProfile2IpHostSvcControlReqResult, fkGponProfile2IpHostSvcControlId, fkGponProfile2IpHostSvcControlVlanFilterMode, 
                                fkGponProfile2IpHostSvcControlVlanFilter }
                        STATUS current
                        DESCRIPTION 
                                "Description."
                        ::= { fkGponProfile2IpHostSvcNotification 5 }

                
                -- 1.3.6.1.4.1.10428 9 1.101.23.51.17.1.3.6
                fkGponProfile2IpHostSvcVlanDsOperChanged NOTIFICATION-TYPE
                        OBJECTS { fkGponProfile2IpHostSvcControlRequest, fkGponProfile2IpHostSvcControlTimeStamp, fkGponProfile2IpHostSvcControlReqResult, fkGponProfile2IpHostSvcControlId, fkGponProfile2IpHostSvcControlVlanOpDsOperFlag
                                 }
                        STATUS current
                        DESCRIPTION 
                                "Description."
                        ::= { fkGponProfile2IpHostSvcNotification 6 }

                
                -- 1.3.6.1.4.1.10428 9 1.101.23.51.17.1.3.7
                fkGponProfile2IpHostSvcVlanUsOperChanged NOTIFICATION-TYPE
                        OBJECTS { fkGponProfile2IpHostSvcControlRequest, fkGponProfile2IpHostSvcControlTimeStamp, fkGponProfile2IpHostSvcControlReqResult, fkGponProfile2IpHostSvcControlId, fkGponProfile2IpHostSvcControlVlanOpUsOperFlag, 
                                fkGponProfile2IpHostSvcControlVlanOpUsOperVid, fkGponProfile2IpHostSvcControlVlanOpUsOperCos }
                        STATUS current
                        DESCRIPTION 
                                "Description."
                        ::= { fkGponProfile2IpHostSvcNotification 7 }

                
                -- 1.3.6.1.4.1.10428 9 1.101.23.51.17.1.3.8
                fkGponProfile2IpHostSvcExtendedVlanChanged NOTIFICATION-TYPE
                        OBJECTS { fkGponProfile2IpHostSvcControlRequest, fkGponProfile2IpHostSvcControlTimeStamp, fkGponProfile2IpHostSvcControlReqResult, fkGponProfile2IpHostSvcControlId, fkGponProfile2IpHostSvcControlExtVlanName
                                 }
                        STATUS current
                        DESCRIPTION 
                                "setExtendedVlan"
                        ::= { fkGponProfile2IpHostSvcNotification 8 }

                
                -- 1.3.6.1.4.1.10428 9 1.101.23.51.17.2
                fkGponProfile2IpHostVoip OBJECT IDENTIFIER ::= { fkGponProfile2IpHost 2 }

                
                -- 1.3.6.1.4.1.10428 9 1.101.23.51.17.2.1
                fkGponProfile2IpHostVoipTable OBJECT-TYPE
                        SYNTAX SEQUENCE OF FkGponProfile2IpHostVoipEntry
                        MAX-ACCESS not-accessible
                        STATUS current
                        DESCRIPTION
                                "fkGponProfile2IpHostVoipTable"
                        ::= { fkGponProfile2IpHostVoip 1 }

                
                -- 1.3.6.1.4.1.10428 9 1.101.23.51.17.2.1.1
                fkGponProfile2IpHostVoipEntry OBJECT-TYPE
                        SYNTAX FkGponProfile2IpHostVoipEntry
                        MAX-ACCESS not-accessible
                        STATUS current
                        DESCRIPTION
                                "fkGponProfile2TrafficIndex, fkGponProfile2IpHostSvcId, fkGponProfile2IpHostVoipId"
                        INDEX { fkGponProfile2TrafficIndex, fkGponProfile2IpHostSvcId, fkGponProfile2IpHostVoipId }
                        ::= { fkGponProfile2IpHostVoipTable 1 }

                
                FkGponProfile2IpHostVoipEntry ::=
                        SEQUENCE { 
                                fkGponProfile2IpHostVoipId
                                        INTEGER
                         }

                -- 1.3.6.1.4.1.10428 9 1.101.23.51.17.2.1.1.1
                fkGponProfile2IpHostVoipId OBJECT-TYPE
                        SYNTAX INTEGER (1..65535)
                        MAX-ACCESS read-only
                        STATUS current
                        DESCRIPTION
                                "The VoIP id of GPON profile."
                        ::= { fkGponProfile2IpHostVoipEntry 1 }

                
                -- 1.3.6.1.4.1.10428 9 1.101.23.51.17.2.2
                fkGponProfile2IpHostVoipControl OBJECT IDENTIFIER ::= { fkGponProfile2IpHostVoip 2 }

                
                -- 1.3.6.1.4.1.10428 9 1.101.23.51.17.2.2.1
                fkGponProfile2IpHostVoipControlRequest OBJECT-TYPE
                        SYNTAX INTEGER
                                {
                                addVoipSvc(1),
                                delVoipSvc(2)
                                }
                        MAX-ACCESS read-write
                        STATUS current
                        DESCRIPTION
                                "The request of a user command"
                        ::= { fkGponProfile2IpHostVoipControl 1 }

                
                -- 1.3.6.1.4.1.10428 9 1.101.23.51.17.2.2.2
                fkGponProfile2IpHostVoipControlStatus OBJECT-TYPE
                        SYNTAX FkControlStatusType
                        MAX-ACCESS read-only
                        STATUS current
                        DESCRIPTION
                                "The status of user command"
                        ::= { fkGponProfile2IpHostVoipControl 2 }

                
                -- 1.3.6.1.4.1.10428 9 1.101.23.51.17.2.2.3
                fkGponProfile2IpHostVoipControlTimer OBJECT-TYPE
                        SYNTAX Gauge32
                        MAX-ACCESS read-write
                        STATUS current
                        DESCRIPTION
                                "The maximum time for the manager for a long running user command"
                        ::= { fkGponProfile2IpHostVoipControl 3 }

                
                -- 1.3.6.1.4.1.10428 9 1.101.23.51.17.2.2.4
                fkGponProfile2IpHostVoipControlTimeStamp OBJECT-TYPE
                        SYNTAX TimeTicks
                        MAX-ACCESS read-only
                        STATUS current
                        DESCRIPTION
                                "The time stamp of the last command(end of command)"
                        ::= { fkGponProfile2IpHostVoipControl 4 }

                
                -- 1.3.6.1.4.1.10428 9 1.101.23.51.17.2.2.5
                fkGponProfile2IpHostVoipControlReqResult OBJECT-TYPE
                        SYNTAX FkControlRequestResultType
                        MAX-ACCESS read-only
                        STATUS current
                        DESCRIPTION
                                "The result of the last user command"
                        ::= { fkGponProfile2IpHostVoipControl 5 }

                
                -- 1.3.6.1.4.1.10428 9 1.101.23.51.17.2.2.6
                fkGponProfile2IpHostVoipControlTName OBJECT-TYPE
                        SYNTAX OCTET STRING
                        MAX-ACCESS read-write
                        STATUS current
                        DESCRIPTION
                                "The Traffic profile name."
                        ::= { fkGponProfile2IpHostVoipControl 6 }
-- The ONU profile name.
                
                -- 1.3.6.1.4.1.10428 9 1.101.23.51.17.2.2.7
                fkGponProfile2IpHostVoipControlIpHostSvcId OBJECT-TYPE
                        SYNTAX INTEGER (1..65535)
                        MAX-ACCESS read-write
                        STATUS current
                        DESCRIPTION
                                "The IP host service id of GPON profile."
                        ::= { fkGponProfile2IpHostVoipControl 7 }

                
                -- 1.3.6.1.4.1.10428 9 1.101.23.51.17.2.2.8
                fkGponProfile2IpHostVoipControlId OBJECT-TYPE
                        SYNTAX INTEGER (1..65535)
                        MAX-ACCESS read-write
                        STATUS current
                        DESCRIPTION
                                "The VoIP id of GPON profile."
                        ::= { fkGponProfile2IpHostVoipControl 8 }

                
                -- 1.3.6.1.4.1.10428 9 1.101.23.51.17.2.3
                fkGponProfile2IpHostVoipNotification OBJECT IDENTIFIER ::= { fkGponProfile2IpHostVoip 3 }

                
                -- 1.3.6.1.4.1.10428 9 1.101.23.51.17.2.3.1
                fkGponProfile2IpHostVoipVoipSvcCreated NOTIFICATION-TYPE
                        OBJECTS { fkGponProfile2IpHostVoipControlRequest, fkGponProfile2IpHostVoipControlTimeStamp, fkGponProfile2IpHostVoipControlReqResult, fkGponProfile2IpHostVoipControlTName, fkGponProfile2IpHostVoipControlIpHostSvcId, 
                                fkGponProfile2IpHostVoipControlId }
                        STATUS current
                        DESCRIPTION 
                                "Description."
                        ::= { fkGponProfile2IpHostVoipNotification 1 }

                
                -- 1.3.6.1.4.1.10428 9 1.101.23.51.17.2.3.2
                fkGponProfile2IpHostVoipVoipSvcDeleted NOTIFICATION-TYPE
                        OBJECTS { fkGponProfile2IpHostVoipControlRequest, fkGponProfile2IpHostVoipControlTimeStamp, fkGponProfile2IpHostVoipControlReqResult, fkGponProfile2IpHostVoipControlTName, fkGponProfile2IpHostVoipControlIpHostSvcId, 
                                fkGponProfile2IpHostVoipControlId }
                        STATUS current
                        DESCRIPTION 
                                "Description."
                        ::= { fkGponProfile2IpHostVoipNotification 2 }

                
                -- 1.3.6.1.4.1.10428 9 1.101.23.51.17.3
                fkGponProfile2IpHostTdm OBJECT IDENTIFIER ::= { fkGponProfile2IpHost 3 }

                
                -- 1.3.6.1.4.1.10428 9 1.101.23.51.17.3.1
                fkGponProfile2IpHostTdmTable OBJECT-TYPE
                        SYNTAX SEQUENCE OF FkGponProfile2IpHostTdmEntry
                        MAX-ACCESS not-accessible
                        STATUS current
                        DESCRIPTION
                                "fkGponProfile2IpHostTdmTable"
                        ::= { fkGponProfile2IpHostTdm 1 }

                
                -- 1.3.6.1.4.1.10428 9 1.101.23.51.17.3.1.1
                fkGponProfile2IpHostTdmEntry OBJECT-TYPE
                        SYNTAX FkGponProfile2IpHostTdmEntry
                        MAX-ACCESS not-accessible
                        STATUS current
                        DESCRIPTION
                                "key: fkGponProfile2TrafficIndex, fkGponProfile2IpHostSvcId, fkGponProfile2IpHostTdmId"
                        INDEX { fkGponProfile2TrafficIndex, fkGponProfile2IpHostSvcId, fkGponProfile2IpHostTdmId }
                        ::= { fkGponProfile2IpHostTdmTable 1 }

                
                FkGponProfile2IpHostTdmEntry ::=
                        SEQUENCE { 
                                fkGponProfile2IpHostTdmId
                                        INTEGER
                         }

                -- 1.3.6.1.4.1.10428 9 1.101.23.51.17.3.1.1.1
                fkGponProfile2IpHostTdmId OBJECT-TYPE
                        SYNTAX INTEGER (1..65535)
                        MAX-ACCESS read-only
                        STATUS current
                        DESCRIPTION
                                "The TDM id of GPON profile."
                        ::= { fkGponProfile2IpHostTdmEntry 1 }

                
                -- 1.3.6.1.4.1.10428 9 1.101.23.51.17.3.2
                fkGponProfile2IpHostTdmControl OBJECT IDENTIFIER ::= { fkGponProfile2IpHostTdm 2 }

                
                -- 1.3.6.1.4.1.10428 9 1.101.23.51.17.3.2.1
                fkGponProfile2IpHostTdmControlRequest OBJECT-TYPE
                        SYNTAX INTEGER
                                {
                                addVoipSvc(1),
                                delVoipSvc(2)
                                }
                        MAX-ACCESS read-write
                        STATUS current
                        DESCRIPTION
                                "The request of a user command"
                        ::= { fkGponProfile2IpHostTdmControl 1 }

                
                -- 1.3.6.1.4.1.10428 9 1.101.23.51.17.3.2.2
                fkGponProfile2IpHostTdmControlStatus OBJECT-TYPE
                        SYNTAX FkControlStatusType
                        MAX-ACCESS read-only
                        STATUS current
                        DESCRIPTION
                                "The status of user command"
                        ::= { fkGponProfile2IpHostTdmControl 2 }

                
                -- 1.3.6.1.4.1.10428 9 1.101.23.51.17.3.2.3
                fkGponProfile2IpHostTdmControlTimer OBJECT-TYPE
                        SYNTAX Gauge32
                        MAX-ACCESS read-write
                        STATUS current
                        DESCRIPTION
                                "The maximum time for the manager for a long running user command"
                        ::= { fkGponProfile2IpHostTdmControl 3 }

                
                -- 1.3.6.1.4.1.10428 9 1.101.23.51.17.3.2.4
                fkGponProfile2IpHostTdmControlTimeStamp OBJECT-TYPE
                        SYNTAX TimeTicks
                        MAX-ACCESS read-only
                        STATUS current
                        DESCRIPTION
                                "The time stamp of the last command(end of command)"
                        ::= { fkGponProfile2IpHostTdmControl 4 }

                
                -- 1.3.6.1.4.1.10428 9 1.101.23.51.17.3.2.5
                fkGponProfile2IpHostTdmControlReqResult OBJECT-TYPE
                        SYNTAX FkControlRequestResultType
                        MAX-ACCESS read-only
                        STATUS current
                        DESCRIPTION
                                "The result of the last user command"
                        ::= { fkGponProfile2IpHostTdmControl 5 }

                
                -- 1.3.6.1.4.1.10428 9 1.101.23.51.17.3.2.6
                fkGponProfile2IpHostTdmControlTName OBJECT-TYPE
                        SYNTAX OCTET STRING
                        MAX-ACCESS read-write
                        STATUS current
                        DESCRIPTION
                                "The Traffic profile name."
                        ::= { fkGponProfile2IpHostTdmControl 6 }
-- The ONU profile name.
                
                -- 1.3.6.1.4.1.10428 9 1.101.23.51.17.3.2.7
                fkGponProfile2IpHostTdmControlIpHostSvcId OBJECT-TYPE
                        SYNTAX INTEGER (1..65535)
                        MAX-ACCESS read-write
                        STATUS current
                        DESCRIPTION
                                "The IP host service id of GPON profile."
                        ::= { fkGponProfile2IpHostTdmControl 7 }

                
                -- 1.3.6.1.4.1.10428 9 1.101.23.51.17.3.2.8
                fkGponProfile2IpHostTdmControlId OBJECT-TYPE
                        SYNTAX INTEGER (1..65535)
                        MAX-ACCESS read-write
                        STATUS current
                        DESCRIPTION
                                "The TDM id of GPON profile."
                        ::= { fkGponProfile2IpHostTdmControl 8 }

                
                -- 1.3.6.1.4.1.10428 9 1.101.23.51.17.3.3
                fkGponProfile2IpHostTdmNotification OBJECT IDENTIFIER ::= { fkGponProfile2IpHostTdm 3 }

                
                -- 1.3.6.1.4.1.10428 9 1.101.23.51.17.3.3.1
                fkGponProfile2IpHostTdmSvcCreated NOTIFICATION-TYPE
                        OBJECTS { fkGponProfile2IpHostTdmControlRequest, fkGponProfile2IpHostTdmControlTimeStamp, fkGponProfile2IpHostTdmControlReqResult, fkGponProfile2IpHostTdmControlTName, fkGponProfile2IpHostTdmControlIpHostSvcId, 
                                fkGponProfile2IpHostTdmControlId }
                        STATUS current
                        DESCRIPTION 
                                "Description."
                        ::= { fkGponProfile2IpHostTdmNotification 1 }

                
                -- 1.3.6.1.4.1.10428 9 1.101.23.51.17.3.3.2
                fkGponProfile2IpHostTdmSvcDeleted NOTIFICATION-TYPE
                        OBJECTS { fkGponProfile2IpHostTdmControlRequest, fkGponProfile2IpHostTdmControlTimeStamp, fkGponProfile2IpHostTdmControlReqResult, fkGponProfile2IpHostTdmControlTName, fkGponProfile2IpHostTdmControlIpHostSvcId, 
                                fkGponProfile2IpHostTdmControlId }
                        STATUS current
                        DESCRIPTION 
                                "Description."
                        ::= { fkGponProfile2IpHostTdmNotification 2 }

                
                -- 1.3.6.1.4.1.10428 9 1.101.23.51.18
                fkGponProfile2Voip OBJECT IDENTIFIER ::= { fkGponProfile2 18 }

                
                -- 1.3.6.1.4.1.10428 9 1.101.23.51.18.1
                fkGponProfile2VoipSvc OBJECT IDENTIFIER ::= { fkGponProfile2Voip 1 }

                
                -- 1.3.6.1.4.1.10428 9 1.101.23.51.18.1.1
                fkGponProfile2VoipSvcTable OBJECT-TYPE
                        SYNTAX SEQUENCE OF FkGponProfile2VoipSvcEntry
                        MAX-ACCESS not-accessible
                        STATUS current
                        DESCRIPTION
                                "fkGponProfile2VoipSvcTable"
                        ::= { fkGponProfile2VoipSvc 1 }

                
                -- 1.3.6.1.4.1.10428 9 1.101.23.51.18.1.1.1
                fkGponProfile2VoipSvcEntry OBJECT-TYPE
                        SYNTAX FkGponProfile2VoipSvcEntry
                        MAX-ACCESS not-accessible
                        STATUS current
                        DESCRIPTION
                                "key: fkGponProfile2TrafficIndex, fkGponProfile2VoipSvcId"
                        INDEX { fkGponProfile2TrafficIndex, fkGponProfile2VoipSvcId }
                        ::= { fkGponProfile2VoipSvcTable 1 }

                
                FkGponProfile2VoipSvcEntry ::=
                        SEQUENCE { 
                                fkGponProfile2VoipSvcId
                                        INTEGER,
                                fkGponProfile2VoipSvcProtocolPort
                                        INTEGER,
                                fkGponProfile2VoipSvcProtocolTos
                                        INTEGER,
                                fkGponProfile2VoipSvcManageMethod
                                        INTEGER,
                                fkGponProfile2VoipSvcProtocol
                                        INTEGER,
                                fkGponProfile2VoipSvcIppathUrl
                                        OCTET STRING,
                                fkGponProfile2VoipSvcIppathUser
                                        OCTET STRING,
                                fkGponProfile2VoipSvcIppathPasswd
                                        OCTET STRING,
                                fkGponProfile2VoipSvcVoipProfile
                                        OCTET STRING,
                                fkGponProfile2VoipSvcProtocolType
                                        INTEGER
                         }

                -- 1.3.6.1.4.1.10428 9 1.101.23.51.18.1.1.1.1
                fkGponProfile2VoipSvcId OBJECT-TYPE
                        SYNTAX INTEGER (1..65535)
                        MAX-ACCESS read-only
                        STATUS current
                        DESCRIPTION
                                "The VoIP service id."
                        ::= { fkGponProfile2VoipSvcEntry 1 }

                
                -- 1.3.6.1.4.1.10428 9 1.101.23.51.18.1.1.1.2
                fkGponProfile2VoipSvcProtocolPort OBJECT-TYPE
                        SYNTAX INTEGER (1..65535)
                        MAX-ACCESS read-only
                        STATUS current
                        DESCRIPTION
                                "UDP port in port"
                        ::= { fkGponProfile2VoipSvcEntry 2 }

                
                -- 1.3.6.1.4.1.10428 9 1.101.23.51.18.1.1.1.3
                fkGponProfile2VoipSvcProtocolTos OBJECT-TYPE
                        SYNTAX INTEGER (1..65535)
                        MAX-ACCESS read-only
                        STATUS current
                        DESCRIPTION
                                "The UDP port TOS."
                        ::= { fkGponProfile2VoipSvcEntry 3 }

                
                -- 1.3.6.1.4.1.10428 9 1.101.23.51.18.1.1.1.4
                fkGponProfile2VoipSvcManageMethod OBJECT-TYPE
                        SYNTAX INTEGER
                                {
                                unUsed(0),
                                omci(1),
                                ipPath(2)
                                }
                        MAX-ACCESS read-only
                        STATUS current
                        DESCRIPTION
                                "The management method
                                0: unused
                                1: omci
                                2: ippath"
                        ::= { fkGponProfile2VoipSvcEntry 4 }

                
                -- 1.3.6.1.4.1.10428 9 1.101.23.51.18.1.1.1.5
                fkGponProfile2VoipSvcProtocol OBJECT-TYPE
                        SYNTAX INTEGER
                                {
                                sip(1),
                                h248(2),
                                mgcp(3),
                                unUsed(255)
                                }
                        MAX-ACCESS read-only
                        STATUS current
                        DESCRIPTION
                                "The VoIP service protocol
                                1: sip
                                2: h248
                                3: mgcp
                                255: unused"
                        ::= { fkGponProfile2VoipSvcEntry 5 }

                
                -- 1.3.6.1.4.1.10428 9 1.101.23.51.18.1.1.1.6
                fkGponProfile2VoipSvcIppathUrl OBJECT-TYPE
                        SYNTAX OCTET STRING
                        MAX-ACCESS read-only
                        STATUS current
                        DESCRIPTION
                                "The IP path URL."
                        ::= { fkGponProfile2VoipSvcEntry 6 }

                
                -- 1.3.6.1.4.1.10428 9 1.101.23.51.18.1.1.1.7
                fkGponProfile2VoipSvcIppathUser OBJECT-TYPE
                        SYNTAX OCTET STRING
                        MAX-ACCESS read-only
                        STATUS current
                        DESCRIPTION
                                "The IP path user name."
                        ::= { fkGponProfile2VoipSvcEntry 7 }

                
                -- 1.3.6.1.4.1.10428 9 1.101.23.51.18.1.1.1.8
                fkGponProfile2VoipSvcIppathPasswd OBJECT-TYPE
                        SYNTAX OCTET STRING
                        MAX-ACCESS read-only
                        STATUS current
                        DESCRIPTION
                                "The IP path password."
                        ::= { fkGponProfile2VoipSvcEntry 8 }

                
                -- 1.3.6.1.4.1.10428 9 1.101.23.51.18.1.1.1.9
                fkGponProfile2VoipSvcVoipProfile OBJECT-TYPE
                        SYNTAX OCTET STRING
                        MAX-ACCESS read-only
                        STATUS current
                        DESCRIPTION
                                "The VoIP profile name."
                        ::= { fkGponProfile2VoipSvcEntry 9 }

                
                -- 1.3.6.1.4.1.10428 9 1.101.23.51.18.1.1.1.10
                fkGponProfile2VoipSvcProtocolType OBJECT-TYPE
                        SYNTAX INTEGER
                                {
                                tcp(6),
                                udp(17),
                                tlsp(56)
                                }
                        MAX-ACCESS read-only
                        STATUS current
                        DESCRIPTION
                                "The IP protocol type."
                        ::= { fkGponProfile2VoipSvcEntry 10 }

                
                -- 1.3.6.1.4.1.10428 9 1.101.23.51.18.1.2
                fkGponProfile2VoipSvcControl OBJECT IDENTIFIER ::= { fkGponProfile2VoipSvc 2 }

                
                -- 1.3.6.1.4.1.10428 9 1.101.23.51.18.1.2.1
                fkGponProfile2VoipSvcControlRequest OBJECT-TYPE
                        SYNTAX INTEGER
                                {
                                addVoipSvc(1),
                                delVoipSvc(2),
                                setUdpPort(3),
                                setManageMethod(4),
                                setProtocol(5),
                                setIppathUrl(6),
                                setIppathAuth(7),
                                setVoipProfile(8)
                                }
                        MAX-ACCESS read-write
                        STATUS current
                        DESCRIPTION
                                "The request of a user command"
                        ::= { fkGponProfile2VoipSvcControl 1 }

                
                -- 1.3.6.1.4.1.10428 9 1.101.23.51.18.1.2.2
                fkGponProfile2VoipSvcControlStatus OBJECT-TYPE
                        SYNTAX FkControlStatusType
                        MAX-ACCESS read-only
                        STATUS current
                        DESCRIPTION
                                "The status of user command"
                        ::= { fkGponProfile2VoipSvcControl 2 }

                
                -- 1.3.6.1.4.1.10428 9 1.101.23.51.18.1.2.3
                fkGponProfile2VoipSvcControlTimer OBJECT-TYPE
                        SYNTAX Gauge32
                        MAX-ACCESS read-write
                        STATUS current
                        DESCRIPTION
                                "The maximum time for the manager for a long running user command"
                        ::= { fkGponProfile2VoipSvcControl 3 }

                
                -- 1.3.6.1.4.1.10428 9 1.101.23.51.18.1.2.4
                fkGponProfile2VoipSvcControlTimeStamp OBJECT-TYPE
                        SYNTAX TimeTicks
                        MAX-ACCESS read-only
                        STATUS current
                        DESCRIPTION
                                "The time stamp of the last command(end of command)"
                        ::= { fkGponProfile2VoipSvcControl 4 }

                
                -- 1.3.6.1.4.1.10428 9 1.101.23.51.18.1.2.5
                fkGponProfile2VoipSvcControlReqResult OBJECT-TYPE
                        SYNTAX FkControlRequestResultType
                        MAX-ACCESS read-only
                        STATUS current
                        DESCRIPTION
                                "The result of the last user command"
                        ::= { fkGponProfile2VoipSvcControl 5 }

                
                -- 1.3.6.1.4.1.10428 9 1.101.23.51.18.1.2.6
                fkGponProfile2VoipSvcControlTName OBJECT-TYPE
                        SYNTAX OCTET STRING
                        MAX-ACCESS read-write
                        STATUS current
                        DESCRIPTION
                                "The Traffic profile name."
                        ::= { fkGponProfile2VoipSvcControl 6 }
-- The ONU profile name.
                
                -- 1.3.6.1.4.1.10428 9 1.101.23.51.18.1.2.7
                fkGponProfile2VoipSvcControlId OBJECT-TYPE
                        SYNTAX INTEGER (1..65535)
                        MAX-ACCESS read-write
                        STATUS current
                        DESCRIPTION
                                "The VoIP service id."
                        ::= { fkGponProfile2VoipSvcControl 7 }

                
                -- 1.3.6.1.4.1.10428 9 1.101.23.51.18.1.2.8
                fkGponProfile2VoipSvcControlProtocolPort OBJECT-TYPE
                        SYNTAX INTEGER (1..65535)
                        MAX-ACCESS read-write
                        STATUS current
                        DESCRIPTION
                                "UDP port in port"
                        ::= { fkGponProfile2VoipSvcControl 8 }

                
                -- 1.3.6.1.4.1.10428 9 1.101.23.51.18.1.2.9
                fkGponProfile2VoipSvcControlProtocolTos OBJECT-TYPE
                        SYNTAX INTEGER (1..65535)
                        MAX-ACCESS read-write
                        STATUS current
                        DESCRIPTION
                                "The UDP port TOS."
                        ::= { fkGponProfile2VoipSvcControl 9 }

                
                -- 1.3.6.1.4.1.10428 9 1.101.23.51.18.1.2.10
                fkGponProfile2VoipSvcControlManageMethod OBJECT-TYPE
                        SYNTAX INTEGER
                                {
                                unUsed(0),
                                omci(1),
                                ipPath(2)
                                }
                        MAX-ACCESS read-write
                        STATUS current
                        DESCRIPTION
                                "The management method
                                0: unused
                                1: omci
                                2: ippath"
                        ::= { fkGponProfile2VoipSvcControl 10 }

                
                -- 1.3.6.1.4.1.10428 9 1.101.23.51.18.1.2.11
                fkGponProfile2VoipSvcControlProtocol OBJECT-TYPE
                        SYNTAX INTEGER
                                {
                                sip(1),
                                h248(2),
                                mgcp(3),
                                unUsed(255)
                                }
                        MAX-ACCESS read-write
                        STATUS current
                        DESCRIPTION
                                "The VoIP service protocol
                                1: sip
                                2: h248
                                3: mgcp
                                255: unused"
                        ::= { fkGponProfile2VoipSvcControl 11 }

                
                -- 1.3.6.1.4.1.10428 9 1.101.23.51.18.1.2.12
                fkGponProfile2VoipSvcControlIppathUrl OBJECT-TYPE
                        SYNTAX OCTET STRING
                        MAX-ACCESS read-write
                        STATUS current
                        DESCRIPTION
                                "The IP path URL."
                        ::= { fkGponProfile2VoipSvcControl 12 }

                
                -- 1.3.6.1.4.1.10428 9 1.101.23.51.18.1.2.13
                fkGponProfile2VoipSvcControlIppathUser OBJECT-TYPE
                        SYNTAX OCTET STRING
                        MAX-ACCESS read-write
                        STATUS current
                        DESCRIPTION
                                "The IP path user name."
                        ::= { fkGponProfile2VoipSvcControl 13 }

                
                -- 1.3.6.1.4.1.10428 9 1.101.23.51.18.1.2.14
                fkGponProfile2VoipSvcControlIppathPasswd OBJECT-TYPE
                        SYNTAX OCTET STRING
                        MAX-ACCESS read-write
                        STATUS current
                        DESCRIPTION
                                "The IP path password."
                        ::= { fkGponProfile2VoipSvcControl 14 }

                
                -- 1.3.6.1.4.1.10428 9 1.101.23.51.18.1.2.15
                fkGponProfile2VoipSvcControlVoipProfile OBJECT-TYPE
                        SYNTAX OCTET STRING
                        MAX-ACCESS read-write
                        STATUS current
                        DESCRIPTION
                                "The VoIP profile name."
                        ::= { fkGponProfile2VoipSvcControl 15 }

                
                -- 1.3.6.1.4.1.10428 9 1.101.23.51.18.1.2.16
                fkGponProfile2VoipSvcControlProtocolType OBJECT-TYPE
                        SYNTAX INTEGER
                                {
                                tcp(6),
                                udp(17),
                                tlsp(56)
                                }
                        MAX-ACCESS read-write
                        STATUS current
                        DESCRIPTION
                                "The IP protocol type."
                        ::= { fkGponProfile2VoipSvcControl 16 }

                
                -- 1.3.6.1.4.1.10428 9 1.101.23.51.18.1.3
                fkGponProfile2VoipSvcNotification OBJECT IDENTIFIER ::= { fkGponProfile2VoipSvc 3 }

                
                -- 1.3.6.1.4.1.10428 9 1.101.23.51.18.1.3.1
                fkGponProfile2VoipSvcVoipSvcCreated NOTIFICATION-TYPE
                        OBJECTS { fkGponProfile2VoipSvcControlRequest, fkGponProfile2VoipSvcControlTimeStamp, fkGponProfile2VoipSvcControlReqResult, fkGponProfile2VoipSvcControlTName, fkGponProfile2VoipSvcControlId
                                 }
                        STATUS current
                        DESCRIPTION 
                                "Description."
                        ::= { fkGponProfile2VoipSvcNotification 1 }

                
                -- 1.3.6.1.4.1.10428 9 1.101.23.51.18.1.3.2
                fkGponProfile2VoipSvcVoipSvcDeleted NOTIFICATION-TYPE
                        OBJECTS { fkGponProfile2TdmSvcControlRequest, fkGponProfile2TdmSvcControlTimeStamp, fkGponProfile2TdmSvcControlReqResult, fkGponProfile2TdmSvcControlTName, fkGponProfile2TdmSvcControlId
                                 }
                        STATUS current
                        DESCRIPTION 
                                "Description."
                        ::= { fkGponProfile2VoipSvcNotification 2 }

                
                -- 1.3.6.1.4.1.10428 9 1.101.23.51.18.1.3.3
                fkGponProfile2VoipSvcUdpPortChanged NOTIFICATION-TYPE
                        OBJECTS { fkGponProfile2VoipSvcControlRequest, fkGponProfile2VoipSvcControlTimeStamp, fkGponProfile2VoipSvcControlReqResult, fkGponProfile2VoipSvcControlId, fkGponProfile2VoipSvcControlTName, 
                                fkGponProfile2VoipSvcControlProtocolPort, fkGponProfile2VoipSvcControlProtocolTos, fkGponProfile2VoipSvcControlProtocolType }
                        STATUS current
                        DESCRIPTION 
                                "Description."
                        ::= { fkGponProfile2VoipSvcNotification 3 }

                
                -- 1.3.6.1.4.1.10428 9 1.101.23.51.18.1.3.4
                fkGponProfile2VoipSvcManageMethodChanged NOTIFICATION-TYPE
                        OBJECTS { fkGponProfile2VoipSvcControlRequest, fkGponProfile2VoipSvcControlTimeStamp, fkGponProfile2VoipSvcControlReqResult, fkGponProfile2VoipSvcControlId, fkGponProfile2VoipSvcControlManageMethod, 
                                fkGponProfile2VoipSvcControlTName }
                        STATUS current
                        DESCRIPTION 
                                "Description."
                        ::= { fkGponProfile2VoipSvcNotification 4 }

                
                -- 1.3.6.1.4.1.10428 9 1.101.23.51.18.1.3.5
                fkGponProfile2VoipSvcProtocolChanged NOTIFICATION-TYPE
                        OBJECTS { fkGponProfile2VoipSvcControlRequest, fkGponProfile2VoipSvcControlTimeStamp, fkGponProfile2VoipSvcControlReqResult, fkGponProfile2VoipSvcControlId, fkGponProfile2VoipSvcControlProtocol, 
                                fkGponProfile2VoipSvcControlTName }
                        STATUS current
                        DESCRIPTION 
                                "Description."
                        ::= { fkGponProfile2VoipSvcNotification 5 }

                
                -- 1.3.6.1.4.1.10428 9 1.101.23.51.18.1.3.6
                fkGponProfile2VoipSvcIppathUrlChanged NOTIFICATION-TYPE
                        OBJECTS { fkGponProfile2VoipSvcControlRequest, fkGponProfile2VoipSvcControlTimeStamp, fkGponProfile2VoipSvcControlReqResult, fkGponProfile2VoipSvcControlId, fkGponProfile2VoipSvcControlIppathUrl, 
                                fkGponProfile2VoipSvcControlTName }
                        STATUS current
                        DESCRIPTION 
                                "Description."
                        ::= { fkGponProfile2VoipSvcNotification 6 }

                
                -- 1.3.6.1.4.1.10428 9 1.101.23.51.18.1.3.7
                fkGponProfile2VoipSvcIppathAuthChanged NOTIFICATION-TYPE
                        OBJECTS { fkGponProfile2VoipSvcControlRequest, fkGponProfile2VoipSvcControlTimeStamp, fkGponProfile2VoipSvcControlReqResult, fkGponProfile2VoipSvcControlId, fkGponProfile2VoipSvcControlIppathUser, 
                                fkGponProfile2VoipSvcControlIppathPasswd, fkGponProfile2VoipSvcControlTName }
                        STATUS current
                        DESCRIPTION 
                                "Description."
                        ::= { fkGponProfile2VoipSvcNotification 7 }

                
                -- 1.3.6.1.4.1.10428 9 1.101.23.51.18.1.3.8
                fkGponProfile2VoipSvcVoipProfileChanged NOTIFICATION-TYPE
                        OBJECTS { fkGponProfile2VoipSvcControlRequest, fkGponProfile2VoipSvcControlTimeStamp, fkGponProfile2VoipSvcControlReqResult, fkGponProfile2VoipSvcControlId, fkGponProfile2VoipSvcControlVoipProfile, 
                                fkGponProfile2VoipSvcControlTName }
                        STATUS current
                        DESCRIPTION 
                                "Description."
                        ::= { fkGponProfile2VoipSvcNotification 8 }

                
                -- 1.3.6.1.4.1.10428 9 1.101.23.51.18.2
                fkGponProfile2VoipSvcUni OBJECT IDENTIFIER ::= { fkGponProfile2Voip 2 }

                
                -- 1.3.6.1.4.1.10428 9 1.101.23.51.18.2.1
                fkGponProfile2VoipSvcUniTable OBJECT-TYPE
                        SYNTAX SEQUENCE OF FkGponProfile2VoipSvcUniEntry
                        MAX-ACCESS not-accessible
                        STATUS current
                        DESCRIPTION
                                "fkGponProfile2VoipSvcUniTable"
                        ::= { fkGponProfile2VoipSvcUni 1 }

                
                -- 1.3.6.1.4.1.10428 9 1.101.23.51.18.2.1.1
                fkGponProfile2VoipSvcUniEntry OBJECT-TYPE
                        SYNTAX FkGponProfile2VoipSvcUniEntry
                        MAX-ACCESS not-accessible
                        STATUS current
                        DESCRIPTION
                                "key: fkGponProfile2TrafficIndex, fkGponProfile2VoipSvcId, fkGponProfile2VoipSvcUniType, fkGponProfile2VoipSvcUniId"
                        INDEX { fkGponProfile2TrafficIndex, fkGponProfile2VoipSvcId, fkGponProfile2VoipSvcUniType, fkGponProfile2VoipSvcUniId }
                        ::= { fkGponProfile2VoipSvcUniTable 1 }

                
                FkGponProfile2VoipSvcUniEntry ::=
                        SEQUENCE { 
                                fkGponProfile2VoipSvcUniType
                                        INTEGER,
                                fkGponProfile2VoipSvcUniId
                                        INTEGER,
                                fkGponProfile2VoipSvcUniImpedance
                                        INTEGER,
                                fkGponProfile2VoipSvcUniTransmissionPath
                                        INTEGER,
                                fkGponProfile2VoipSvcUniGainRx
                                        INTEGER,
                                fkGponProfile2VoipSvcUniGainTx
                                        INTEGER,
                                fkGponProfile2VoipSvcUniHoldOverTime
                                        INTEGER
                         }

                -- 1.3.6.1.4.1.10428 9 1.101.23.51.18.2.1.1.1
                fkGponProfile2VoipSvcUniType OBJECT-TYPE
                        SYNTAX INTEGER
                                {
                                pots(1),
                                isdn(2)
                                }
                        MAX-ACCESS read-only
                        STATUS current
                        DESCRIPTION
                                "The UNI type."
                        ::= { fkGponProfile2VoipSvcUniEntry 1 }

                
                -- 1.3.6.1.4.1.10428 9 1.101.23.51.18.2.1.1.2
                fkGponProfile2VoipSvcUniId OBJECT-TYPE
                        SYNTAX INTEGER (1..65535)
                        MAX-ACCESS read-only
                        STATUS current
                        DESCRIPTION
                                "The UNI id."
                        ::= { fkGponProfile2VoipSvcUniEntry 2 }

                
                -- 1.3.6.1.4.1.10428 9 1.101.23.51.18.2.1.1.3
                fkGponProfile2VoipSvcUniImpedance OBJECT-TYPE
                        SYNTAX INTEGER
                                {
                                impedance600(0),
                                impedance900(1),
                                impedance750(2),
                                impedance820(3),
                                impedance1050(4)
                                }
                        MAX-ACCESS read-only
                        STATUS current
                        DESCRIPTION
                                "The UNI impedance."
                        ::= { fkGponProfile2VoipSvcUniEntry 3 }

                
                -- 1.3.6.1.4.1.10428 9 1.101.23.51.18.2.1.1.4
                fkGponProfile2VoipSvcUniTransmissionPath OBJECT-TYPE
                        SYNTAX INTEGER
                                {
                                fullTime(0),
                                partTime(1)
                                }
                        MAX-ACCESS read-only
                        STATUS current
                        DESCRIPTION
                                "The transmission path."
                        ::= { fkGponProfile2VoipSvcUniEntry 4 }

                
                -- 1.3.6.1.4.1.10428 9 1.101.23.51.18.2.1.1.5
                fkGponProfile2VoipSvcUniGainRx OBJECT-TYPE
                        SYNTAX INTEGER (1..65535)
                        MAX-ACCESS read-only
                        STATUS current
                        DESCRIPTION
                                "The UNI gain RX."
                        ::= { fkGponProfile2VoipSvcUniEntry 5 }

                
                -- 1.3.6.1.4.1.10428 9 1.101.23.51.18.2.1.1.6
                fkGponProfile2VoipSvcUniGainTx OBJECT-TYPE
                        SYNTAX INTEGER (1..65535)
                        MAX-ACCESS read-only
                        STATUS current
                        DESCRIPTION
                                "The UNI gain TX."
                        ::= { fkGponProfile2VoipSvcUniEntry 6 }

                
                -- 1.3.6.1.4.1.10428 9 1.101.23.51.18.2.1.1.7
                fkGponProfile2VoipSvcUniHoldOverTime OBJECT-TYPE
                        SYNTAX INTEGER (1..65535)
                        MAX-ACCESS read-only
                        STATUS current
                        DESCRIPTION
                                "The hold over time."
                        ::= { fkGponProfile2VoipSvcUniEntry 7 }

                
                -- 1.3.6.1.4.1.10428 9 1.101.23.51.18.2.2
                fkGponProfile2VoipSvcUniControl OBJECT IDENTIFIER ::= { fkGponProfile2VoipSvcUni 2 }

                
                -- 1.3.6.1.4.1.10428 9 1.101.23.51.18.2.2.1
                fkGponProfile2VoipSvcUniControlRequest OBJECT-TYPE
                        SYNTAX INTEGER
                                {
                                addVoipSvcUni(1),
                                delVoipSvcUni(2),
                                setImpedance(3),
                                setTransmissionPath(4),
                                setGain(5),
                                setHoldOverTime(6)
                                }
                        MAX-ACCESS read-write
                        STATUS current
                        DESCRIPTION
                                "The request of a user command"
                        ::= { fkGponProfile2VoipSvcUniControl 1 }

                
                -- 1.3.6.1.4.1.10428 9 1.101.23.51.18.2.2.2
                fkGponProfile2VoipSvcUniControlStatus OBJECT-TYPE
                        SYNTAX FkControlStatusType
                        MAX-ACCESS read-only
                        STATUS current
                        DESCRIPTION
                                "The status of user command"
                        ::= { fkGponProfile2VoipSvcUniControl 2 }

                
                -- 1.3.6.1.4.1.10428 9 1.101.23.51.18.2.2.3
                fkGponProfile2VoipSvcUniControlTimer OBJECT-TYPE
                        SYNTAX Gauge32
                        MAX-ACCESS read-write
                        STATUS current
                        DESCRIPTION
                                "The maximum time for the manager for a long running user command"
                        ::= { fkGponProfile2VoipSvcUniControl 3 }

                
                -- 1.3.6.1.4.1.10428 9 1.101.23.51.18.2.2.4
                fkGponProfile2VoipSvcUniControlTimeStamp OBJECT-TYPE
                        SYNTAX TimeTicks
                        MAX-ACCESS read-only
                        STATUS current
                        DESCRIPTION
                                "The time stamp of the last command(end of command)"
                        ::= { fkGponProfile2VoipSvcUniControl 4 }

                
                -- 1.3.6.1.4.1.10428 9 1.101.23.51.18.2.2.5
                fkGponProfile2VoipSvcUniControlReqResult OBJECT-TYPE
                        SYNTAX FkControlRequestResultType
                        MAX-ACCESS read-only
                        STATUS current
                        DESCRIPTION
                                "The result of the last user command"
                        ::= { fkGponProfile2VoipSvcUniControl 5 }

                
                -- 1.3.6.1.4.1.10428 9 1.101.23.51.18.2.2.6
                fkGponProfile2VoipSvcUniControlTName OBJECT-TYPE
                        SYNTAX OCTET STRING
                        MAX-ACCESS read-write
                        STATUS current
                        DESCRIPTION
                                "The Traffic profile name."
                        ::= { fkGponProfile2VoipSvcUniControl 6 }
-- The ONU profile name.
                
                -- 1.3.6.1.4.1.10428 9 1.101.23.51.18.2.2.7
                fkGponProfile2VoipSvcUniControlVoipSvcId OBJECT-TYPE
                        SYNTAX INTEGER (1..65535)
                        MAX-ACCESS read-write
                        STATUS current
                        DESCRIPTION
                                "The VoIP service id."
                        ::= { fkGponProfile2VoipSvcUniControl 7 }

                
                -- 1.3.6.1.4.1.10428 9 1.101.23.51.18.2.2.8
                fkGponProfile2VoipSvcUniControlType OBJECT-TYPE
                        SYNTAX INTEGER
                                {
                                pots(1),
                                isdn(2)
                                }
                        MAX-ACCESS read-write
                        STATUS current
                        DESCRIPTION
                                "The UNI type."
                        ::= { fkGponProfile2VoipSvcUniControl 8 }

                
                -- 1.3.6.1.4.1.10428 9 1.101.23.51.18.2.2.9
                fkGponProfile2VoipSvcUniControlId OBJECT-TYPE
                        SYNTAX INTEGER (1..65535)
                        MAX-ACCESS read-write
                        STATUS current
                        DESCRIPTION
                                "The UNI id."
                        ::= { fkGponProfile2VoipSvcUniControl 9 }

                
                -- 1.3.6.1.4.1.10428 9 1.101.23.51.18.2.2.10
                fkGponProfile2VoipSvcUniControlImpedance OBJECT-TYPE
                        SYNTAX INTEGER
                                {
                                impedance600(0),
                                impedance900(1),
                                impedance750(2),
                                impedance820(3),
                                impedance1050(4)
                                }
                        MAX-ACCESS read-write
                        STATUS current
                        DESCRIPTION
                                "The UNI impedance."
                        ::= { fkGponProfile2VoipSvcUniControl 10 }

                
                -- 1.3.6.1.4.1.10428 9 1.101.23.51.18.2.2.11
                fkGponProfile2VoipSvcUniControlTransmissionPath OBJECT-TYPE
                        SYNTAX INTEGER
                                {
                                fullTime(0),
                                partTime(1)
                                }
                        MAX-ACCESS read-write
                        STATUS current
                        DESCRIPTION
                                "The transmission path."
                        ::= { fkGponProfile2VoipSvcUniControl 11 }

                
                -- 1.3.6.1.4.1.10428 9 1.101.23.51.18.2.2.12
                fkGponProfile2VoipSvcUniControlGainRx OBJECT-TYPE
                        SYNTAX INTEGER (1..65535)
                        MAX-ACCESS read-write
                        STATUS current
                        DESCRIPTION
                                "The UNI gain RX."
                        ::= { fkGponProfile2VoipSvcUniControl 12 }

                
                -- 1.3.6.1.4.1.10428 9 1.101.23.51.18.2.2.13
                fkGponProfile2VoipSvcUniControlGainTx OBJECT-TYPE
                        SYNTAX INTEGER (1..65535)
                        MAX-ACCESS read-write
                        STATUS current
                        DESCRIPTION
                                "The UNI gain TX."
                        ::= { fkGponProfile2VoipSvcUniControl 13 }

                
                -- 1.3.6.1.4.1.10428 9 1.101.23.51.18.2.2.14
                fkGponProfile2VoipSvcUniControlHoldOverTime OBJECT-TYPE
                        SYNTAX INTEGER (1..65535)
                        MAX-ACCESS read-write
                        STATUS current
                        DESCRIPTION
                                "The hold over time."
                        ::= { fkGponProfile2VoipSvcUniControl 14 }

                
                -- 1.3.6.1.4.1.10428 9 1.101.23.51.18.2.3
                fkGponProfile2VoipSvcUniNotification OBJECT IDENTIFIER ::= { fkGponProfile2VoipSvcUni 3 }

                
                -- 1.3.6.1.4.1.10428 9 1.101.23.51.18.2.3.1
                fkGponProfile2VoipSvcUniVoipSvcUniCreated NOTIFICATION-TYPE
                        OBJECTS { fkGponProfile2VoipSvcUniControlRequest, fkGponProfile2VoipSvcUniControlTimeStamp, fkGponProfile2VoipSvcUniControlReqResult, fkGponProfile2VoipSvcUniControlTName, fkGponProfile2VoipSvcUniControlVoipSvcId, 
                                fkGponProfile2VoipSvcUniControlType, fkGponProfile2VoipSvcUniControlId }
                        STATUS current
                        DESCRIPTION 
                                "Description."
                        ::= { fkGponProfile2VoipSvcUniNotification 1 }

                
                -- 1.3.6.1.4.1.10428 9 1.101.23.51.18.2.3.2
                fkGponProfile2VoipSvcUniVoipSvcUniDeleted NOTIFICATION-TYPE
                        OBJECTS { fkGponProfile2VoipSvcUniControlRequest, fkGponProfile2VoipSvcUniControlTimeStamp, fkGponProfile2VoipSvcUniControlReqResult, fkGponProfile2VoipSvcUniControlTName, fkGponProfile2VoipSvcUniControlVoipSvcId, 
                                fkGponProfile2VoipSvcUniControlType, fkGponProfile2VoipSvcUniControlId }
                        STATUS current
                        DESCRIPTION 
                                "Description."
                        ::= { fkGponProfile2VoipSvcUniNotification 2 }

                
                -- 1.3.6.1.4.1.10428 9 1.101.23.51.18.2.3.3
                fkGponProfile2VoipSvcUniImpedanceChanged NOTIFICATION-TYPE
                        OBJECTS { fkGponProfile2VoipSvcUniControlRequest, fkGponProfile2VoipSvcUniControlTimeStamp, fkGponProfile2VoipSvcUniControlReqResult, fkGponProfile2VoipSvcUniControlVoipSvcId, fkGponProfile2VoipSvcUniControlId, 
                                fkGponProfile2VoipSvcUniControlImpedance, fkGponProfile2VoipSvcUniControlTName, fkGponProfile2VoipSvcUniControlType }
                        STATUS current
                        DESCRIPTION 
                                "Description."
                        ::= { fkGponProfile2VoipSvcUniNotification 3 }

                
                -- 1.3.6.1.4.1.10428 9 1.101.23.51.18.2.3.4
                fkGponProfile2VoipSvcUniTransmissionPathChanged NOTIFICATION-TYPE
                        OBJECTS { fkGponProfile2VoipSvcUniControlRequest, fkGponProfile2VoipSvcUniControlTimeStamp, fkGponProfile2VoipSvcUniControlReqResult, fkGponProfile2VoipSvcUniControlVoipSvcId, fkGponProfile2VoipSvcUniControlId, 
                                fkGponProfile2VoipSvcUniControlTransmissionPath, fkGponProfile2VoipSvcUniControlTName, fkGponProfile2VoipSvcUniControlType }
                        STATUS current
                        DESCRIPTION 
                                "Description."
                        ::= { fkGponProfile2VoipSvcUniNotification 4 }

                
                -- 1.3.6.1.4.1.10428 9 1.101.23.51.18.2.3.5
                fkGponProfile2VoipSvcUniGainChanged NOTIFICATION-TYPE
                        OBJECTS { fkGponProfile2VoipSvcUniControlRequest, fkGponProfile2VoipSvcUniControlTimeStamp, fkGponProfile2VoipSvcUniControlReqResult, fkGponProfile2VoipSvcUniControlVoipSvcId, fkGponProfile2VoipSvcUniControlId, 
                                fkGponProfile2VoipSvcUniControlGainRx, fkGponProfile2VoipSvcUniControlGainTx, fkGponProfile2VoipSvcUniControlTName, fkGponProfile2VoipSvcUniControlType }
                        STATUS current
                        DESCRIPTION 
                                "Description."
                        ::= { fkGponProfile2VoipSvcUniNotification 5 }

                
                -- 1.3.6.1.4.1.10428 9 1.101.23.51.18.2.3.6
                fkGponProfile2VoipSvcUniHoldOverTimeChanged NOTIFICATION-TYPE
                        OBJECTS { fkGponProfile2VoipSvcUniControlRequest, fkGponProfile2VoipSvcUniControlTimeStamp, fkGponProfile2VoipSvcUniControlReqResult, fkGponProfile2VoipSvcUniControlVoipSvcId, fkGponProfile2VoipSvcUniControlId, 
                                fkGponProfile2VoipSvcUniControlHoldOverTime, fkGponProfile2VoipSvcUniControlTName, fkGponProfile2VoipSvcUniControlType }
                        STATUS current
                        DESCRIPTION 
                                "Description."
                        ::= { fkGponProfile2VoipSvcUniNotification 6 }

                
                -- 1.3.6.1.4.1.10428 9 1.101.23.51.19
                fkGponProfile2Tdm OBJECT IDENTIFIER ::= { fkGponProfile2 19 }

                
                -- 1.3.6.1.4.1.10428 9 1.101.23.51.19.1
                fkGponProfile2TdmTable OBJECT-TYPE
                        SYNTAX SEQUENCE OF FkGponProfile2TdmEntry
                        MAX-ACCESS not-accessible
                        STATUS current
                        DESCRIPTION
                                "fkGponProfile2TdmTable"
                        ::= { fkGponProfile2Tdm 1 }

                
                -- 1.3.6.1.4.1.10428 9 1.101.23.51.19.1.1
                fkGponProfile2TdmEntry OBJECT-TYPE
                        SYNTAX FkGponProfile2TdmEntry
                        MAX-ACCESS not-accessible
                        STATUS current
                        DESCRIPTION
                                "key: fkGponProfile2TrafficIndex, fkGponProfile2TdmId"
                        INDEX { fkGponProfile2TrafficIndex, fkGponProfile2TdmId }
                        ::= { fkGponProfile2TdmTable 1 }

                
                FkGponProfile2TdmEntry ::=
                        SEQUENCE { 
                                fkGponProfile2TdmId
                                        INTEGER,
                                fkGponProfile2TdmExpectedType
                                        INTEGER,
                                fkGponProfile2TdmFraming
                                        INTEGER,
                                fkGponProfile2TdmEncoding
                                        INTEGER,
                                fkGponProfile2TdmLineLengthPowerFeed
                                        INTEGER,
                                fkGponProfile2TdmDs1Mode
                                        INTEGER,
                                fkGponProfile2TdmLineType
                                        INTEGER
                         }

                -- 1.3.6.1.4.1.10428 9 1.101.23.51.19.1.1.1
                fkGponProfile2TdmId OBJECT-TYPE
                        SYNTAX INTEGER (1..65535)
                        MAX-ACCESS read-only
                        STATUS current
                        DESCRIPTION
                                "The TDM index."
                        ::= { fkGponProfile2TdmEntry 1 }

                
                -- 1.3.6.1.4.1.10428 9 1.101.23.51.19.1.1.2
                fkGponProfile2TdmExpectedType OBJECT-TYPE
                        SYNTAX INTEGER
                                {
                                auto(0),
                                ds1(13),
                                e1(14),
                                cDs1E1(16)
                                }
                        MAX-ACCESS read-only
                        STATUS current
                        DESCRIPTION
                                "The expected type.
                                0: auto 
                                13: ds1
                                14: e1
                                16: cDs1E1 "
                        ::= { fkGponProfile2TdmEntry 2 }

                
                -- 1.3.6.1.4.1.10428 9 1.101.23.51.19.1.1.3
                fkGponProfile2TdmFraming OBJECT-TYPE
                        SYNTAX INTEGER
                                {
                                extendSuperframe(0),
                                superframe(1),
                                unframed(2),
                                g704(3),
                                jtG7604(4),
                                basigG704(5),
                                basigCrc(6),
                                basicTs16(7),
                                basigCrcTs16(8)
                                }
                        MAX-ACCESS read-only
                        STATUS current
                        DESCRIPTION
                                "The TDM framing.
                                1: extendSuperframe(0)
                                2: superframe(1)
                                3: unframed(2)
                                4: g704(3)
                                5: jtG7604(4)
                                6: basigG704(5)
                                7: basigCrc(6)
                                8: basicTs16(7)
                                9: basigCrcTs16(8)"
                        ::= { fkGponProfile2TdmEntry 3 }

                
                -- 1.3.6.1.4.1.10428 9 1.101.23.51.19.1.1.4
                fkGponProfile2TdmEncoding OBJECT-TYPE
                        SYNTAX INTEGER
                                {
                                b8zs(0),
                                ami(1),
                                hdb3(2),
                                b3zs(3)
                                }
                        MAX-ACCESS read-only
                        STATUS current
                        DESCRIPTION
                                "The TDM encoding.
                                1: b8zs(0)
                                2: ami(1)
                                3: hdb3(2)
                                4: b3zs(3)
                                "
                        ::= { fkGponProfile2TdmEntry 4 }

                
                -- 1.3.6.1.4.1.10428 9 1.101.23.51.19.1.1.5
                fkGponProfile2TdmLineLengthPowerFeed OBJECT-TYPE
                        SYNTAX INTEGER
                                {
                                ds1Nonpower110(0),
                                ds1Nonpower220(1),
                                ds1Nonpower330(2),
                                ds1Nonpower440(3),
                                ds1Nonpower550(4),
                                ds1Nonpower660(5),
                                ds1Shortpower133(6),
                                ds1Shortpowert266(7),
                                ds1Shortpower399(8),
                                ds1Shortpowert533(9),
                                ds1Shortpowert655(10),
                                ds1Longpowert0(11),
                                ds1Longpowert7dot5(12),
                                ds1Longpowert15(13),
                                ds1Longpowert22dot5(14),
                                ds3powert225(15),
                                ds3powert450(16),
                                lengthMax(17),
                                unUsed(255)
                                }
                        MAX-ACCESS read-only
                        STATUS current
                        DESCRIPTION
                                "The line length power feedback."
                        ::= { fkGponProfile2TdmEntry 5 }

                
                -- 1.3.6.1.4.1.10428 9 1.101.23.51.19.1.1.6
                fkGponProfile2TdmDs1Mode OBJECT-TYPE
                        SYNTAX INTEGER
                                {
                                ds1CpeShort(0),
                                ds1CpeLong(1),
                                ds1NiuCpeNoPower(2),
                                ds1NiuCpewithPower(3),
                                unUsed(255)
                                }
                        MAX-ACCESS read-only
                        STATUS current
                        DESCRIPTION
                                "The TDM down stream 1 mode.
                                1: ds1CpeShort(0)
                                2: ds1CpeLong(1)
                                3: ds1NiuCpeNoPower(2)
                                4: ds1NiuCpewithPower(3)
                                5: unUsed(255)
                                "
                        ::= { fkGponProfile2TdmEntry 6 }

                
                -- 1.3.6.1.4.1.10428 9 1.101.23.51.19.1.1.7
                fkGponProfile2TdmLineType OBJECT-TYPE
                        SYNTAX INTEGER
                                {
                                other(0),
                                ds3M23(1),
                                ds3Syntran(2),
                                ds3CbitPartity(3),
                                ds3ClearChannel(4),
                                e3Framed(5),
                                e3Plcp(6)
                                }
                        MAX-ACCESS read-only
                        STATUS current
                        DESCRIPTION
                                "The TDM line type.
                                1: other(0)
                                2: ds3M23(1)
                                3: ds3Syntran(2)
                                4: ds3CbitPartity(3)
                                5: ds3ClearChannel(4)
                                6: e3Framed(5)
                                7: e3Plcp(6)"
                        ::= { fkGponProfile2TdmEntry 7 }

                
                -- 1.3.6.1.4.1.10428 9 1.101.23.51.19.2
                fkGponProfile2TdmControl OBJECT IDENTIFIER ::= { fkGponProfile2Tdm 2 }

                
                -- 1.3.6.1.4.1.10428 9 1.101.23.51.19.2.1
                fkGponProfile2TdmControlRequest OBJECT-TYPE
                        SYNTAX INTEGER
                                {
                                addtdmPort(1),
                                delTdmPort(2),
                                setExpectedType(3),
                                setFraming(4),
                                setEncoding(5),
                                setLineLengthPowerFeed(6),
                                setDs1Mode(7),
                                setLineType(8)
                                }
                        MAX-ACCESS read-write
                        STATUS current
                        DESCRIPTION
                                "The request of a user command"
                        ::= { fkGponProfile2TdmControl 1 }

                
                -- 1.3.6.1.4.1.10428 9 1.101.23.51.19.2.2
                fkGponProfile2TdmControlStatus OBJECT-TYPE
                        SYNTAX FkControlStatusType
                        MAX-ACCESS read-only
                        STATUS current
                        DESCRIPTION
                                "The status of user command"
                        ::= { fkGponProfile2TdmControl 2 }

                
                -- 1.3.6.1.4.1.10428 9 1.101.23.51.19.2.3
                fkGponProfile2TdmControlTimer OBJECT-TYPE
                        SYNTAX Gauge32
                        MAX-ACCESS read-write
                        STATUS current
                        DESCRIPTION
                                "The maximum time for the manager for a long running user command"
                        ::= { fkGponProfile2TdmControl 3 }

                
                -- 1.3.6.1.4.1.10428 9 1.101.23.51.19.2.4
                fkGponProfile2TdmControlTimeStamp OBJECT-TYPE
                        SYNTAX TimeTicks
                        MAX-ACCESS read-only
                        STATUS current
                        DESCRIPTION
                                "The time stamp of the last command(end of command)"
                        ::= { fkGponProfile2TdmControl 4 }

                
                -- 1.3.6.1.4.1.10428 9 1.101.23.51.19.2.5
                fkGponProfile2TdmControlReqResult OBJECT-TYPE
                        SYNTAX FkControlRequestResultType
                        MAX-ACCESS read-only
                        STATUS current
                        DESCRIPTION
                                "The result of the last user command
                                "
                        ::= { fkGponProfile2TdmControl 5 }

                
                -- 1.3.6.1.4.1.10428 9 1.101.23.51.19.2.6
                fkGponProfile2TdmControlTName OBJECT-TYPE
                        SYNTAX OCTET STRING
                        MAX-ACCESS read-write
                        STATUS current
                        DESCRIPTION
                                "CES Name"
                        ::= { fkGponProfile2TdmControl 6 }
-- The ONU profile name.
                
                -- 1.3.6.1.4.1.10428 9 1.101.23.51.19.2.7
                fkGponProfile2TdmControlId OBJECT-TYPE
                        SYNTAX Integer32
                        MAX-ACCESS read-write
                        STATUS current
                        DESCRIPTION
                                "TDM (CES) Port Number"
                        ::= { fkGponProfile2TdmControl 7 }

                
                -- 1.3.6.1.4.1.10428 9 1.101.23.51.19.2.8
                fkGponProfile2TdmControlExpectedType OBJECT-TYPE
                        SYNTAX INTEGER
                                {
                                auto(0),
                                ds1(1),
                                e1(2),
                                cDs1E1(3)
                                }
                        MAX-ACCESS read-write
                        STATUS current
                        DESCRIPTION
                                "CES Port Expected Type
                                Autosense (Default value)
                                DS1 (value 13 : 1.544 Mbit/s local (T-interface) module))
                                E1 (value 14 : 2.048 Mbit/s local (T-interface) module))
                                C-DS1/E1 (value 16 : Configurable DS1/E1)"
                        ::= { fkGponProfile2TdmControl 8 }

                
                -- 1.3.6.1.4.1.10428 9 1.101.23.51.19.2.9
                fkGponProfile2TdmControlFramig OBJECT-TYPE
                        SYNTAX INTEGER
                                {
                                extendSuperframe(0),
                                superframe(1),
                                unframed(2),
                                g704(3),
                                jtG7604(4),
                                basigG704(5),
                                basigCrc(6),
                                basicTs16(7),
                                basigCrcTs16(8)
                                }
                        MAX-ACCESS read-write
                        STATUS current
                        DESCRIPTION
                                "CES Port DS1 Framing"
                        ::= { fkGponProfile2TdmControl 9 }

                
                -- 1.3.6.1.4.1.10428 9 1.101.23.51.19.2.10
                fkGponProfile2TdmControlEncoding OBJECT-TYPE
                        SYNTAX INTEGER
                                {
                                b8zs(0),
                                ami(1),
                                hdb3(2),
                                b3zs(3)
                                }
                        MAX-ACCESS read-write
                        STATUS current
                        DESCRIPTION
                                "CES Port Encoding for DS1 and DS3 interface"
                        ::= { fkGponProfile2TdmControl 10 }

                
                -- 1.3.6.1.4.1.10428 9 1.101.23.51.19.2.11
                fkGponProfile2TdmControlLineLengthPowerFeed OBJECT-TYPE
                        SYNTAX INTEGER
                                {
                                ds1Nonpower110(0),
                                ds1Nonpower220(1),
                                ds1Nonpower330(2),
                                ds1Nonpower440(3),
                                ds1Nonpower550(4),
                                ds1Nonpower660(5),
                                ds1Nonpower133(6),
                                ds1Nonpower266(7),
                                ds1Nonpower399(8),
                                ds1Nonpower533(9),
                                ds1Nonpower655(10),
                                ds1Longpowert0(11),
                                ds1Longpowert7dot5(12),
                                ds1Longpowert15(13),
                                ds1Longpowert22dot5(14),
                                ds1Longpowert225(15),
                                ds1Longpowert450(16),
                                lengthMax(17),
                                unUsed(255)
                                }
                        MAX-ACCESS read-write
                        STATUS current
                        DESCRIPTION
                                "CES Port line length of the twisted pair cable Power Feed Option (db)"
                        ::= { fkGponProfile2TdmControl 11 }

                
                -- 1.3.6.1.4.1.10428 9 1.101.23.51.19.2.12
                fkGponProfile2TdmControlDs1Mode OBJECT-TYPE
                        SYNTAX INTEGER
                                {
                                ds1CpeShort(0),
                                ds1CpeLong(1),
                                ds1NiuCpeNoPower(2),
                                ds1NiuCpewithPower(3),
                                unUsed(255)
                                }
                        MAX-ACCESS read-write
                        STATUS current
                        DESCRIPTION
                                "Select connect CES Port DS1 mode"
                        ::= { fkGponProfile2TdmControl 12 }

                
                -- 1.3.6.1.4.1.10428 9 1.101.23.51.19.2.13
                fkGponProfile2TdmControlLineType OBJECT-TYPE
                        SYNTAX INTEGER
                                {
                                other(0),
                                ds3M23(1),
                                ds3Syntran(2),
                                ds3CbitPartity(3),
                                ds3ClearChannel(4),
                                e3Framed(5),
                                e3Plcp(6)
                                }
                        MAX-ACCESS read-write
                        STATUS current
                        DESCRIPTION
                                "CES Port line type for DS3 for E3 interface"
                        ::= { fkGponProfile2TdmControl 13 }

                
                -- 1.3.6.1.4.1.10428 9 1.101.23.51.19.3
                fkGponProfile2TdmNotification OBJECT IDENTIFIER ::= { fkGponProfile2Tdm 3 }

                
                -- 1.3.6.1.4.1.10428 9 1.101.23.51.19.3.1
                fkGponProfile2TdmPortCreated NOTIFICATION-TYPE
                        OBJECTS { fkGponProfile2TdmControlRequest, fkGponProfile2TdmControlTimeStamp, fkGponProfile2TdmControlReqResult, fkGponProfile2TdmControlId, fkGponProfile2TdmControlTName
                                 }
                        STATUS current
                        DESCRIPTION 
                                "Description."
                        ::= { fkGponProfile2TdmNotification 1 }

                
                -- 1.3.6.1.4.1.10428 9 1.101.23.51.19.3.2
                fkGponProfile2TdmPortDeleted NOTIFICATION-TYPE
                        OBJECTS { fkGponProfile2TdmControlRequest, fkGponProfile2TdmControlTimeStamp, fkGponProfile2TdmControlReqResult, fkGponProfile2TdmControlId, fkGponProfile2TdmControlTName
                                 }
                        STATUS current
                        DESCRIPTION 
                                "Description."
                        ::= { fkGponProfile2TdmNotification 2 }

                
                -- 1.3.6.1.4.1.10428 9 1.101.23.51.19.3.3
                fkGponProfile2TdmExpectedTypeChanged NOTIFICATION-TYPE
                        OBJECTS { fkGponProfile2TdmControlRequest, fkGponProfile2TdmControlTimeStamp, fkGponProfile2TdmControlReqResult, fkGponProfile2TdmControlId, fkGponProfile2TdmControlExpectedType
                                 }
                        STATUS current
                        DESCRIPTION 
                                "Description."
                        ::= { fkGponProfile2TdmNotification 3 }

                
                -- 1.3.6.1.4.1.10428 9 1.101.23.51.19.3.4
                fkGponProfile2TdmFramingChanged NOTIFICATION-TYPE
                        OBJECTS { fkGponProfile2TdmControlRequest, fkGponProfile2TdmControlTimeStamp, fkGponProfile2TdmControlReqResult, fkGponProfile2TdmControlId, fkGponProfile2TdmControlFramig
                                 }
                        STATUS current
                        DESCRIPTION 
                                "Description."
                        ::= { fkGponProfile2TdmNotification 4 }

                
                -- 1.3.6.1.4.1.10428 9 1.101.23.51.19.3.5
                fkGponProfile2TdmEncodingChanged NOTIFICATION-TYPE
                        OBJECTS { fkGponProfile2TdmControlRequest, fkGponProfile2TdmControlTimeStamp, fkGponProfile2TdmControlReqResult, fkGponProfile2TdmControlId, fkGponProfile2TdmControlEncoding
                                 }
                        STATUS current
                        DESCRIPTION 
                                "Description."
                        ::= { fkGponProfile2TdmNotification 5 }

                
                -- 1.3.6.1.4.1.10428 9 1.101.23.51.19.3.6
                fkGponProfile2TdmLineLengthPowerFeedChanged NOTIFICATION-TYPE
                        OBJECTS { fkGponProfile2TdmControlRequest, fkGponProfile2TdmControlTimeStamp, fkGponProfile2TdmControlReqResult, fkGponProfile2TdmControlId, fkGponProfile2TdmControlLineLengthPowerFeed
                                 }
                        STATUS current
                        DESCRIPTION 
                                "Description."
                        ::= { fkGponProfile2TdmNotification 6 }

                
                -- 1.3.6.1.4.1.10428 9 1.101.23.51.19.3.7
                fkGponProfile2TdmDs1ModeChanged NOTIFICATION-TYPE
                        OBJECTS { fkGponProfile2TdmControlRequest, fkGponProfile2TdmControlTimeStamp, fkGponProfile2TdmControlReqResult, fkGponProfile2TdmControlId, fkGponProfile2TdmControlDs1Mode
                                 }
                        STATUS current
                        DESCRIPTION 
                                "Description."
                        ::= { fkGponProfile2TdmNotification 7 }

                
                -- 1.3.6.1.4.1.10428 9 1.101.23.51.19.3.8
                fkGponProfile2TdmLineTypeChanged NOTIFICATION-TYPE
                        OBJECTS { fkGponProfile2TdmControlRequest, fkGponProfile2TdmControlTimeStamp, fkGponProfile2TdmControlReqResult, fkGponProfile2TdmControlId, fkGponProfile2TdmControlLineType
                                 }
                        STATUS current
                        DESCRIPTION 
                                "Description."
                        ::= { fkGponProfile2TdmNotification 8 }

                
                -- 1.3.6.1.4.1.10428 9 1.101.23.51.20
                fkGponProfile2TdmSvc OBJECT IDENTIFIER ::= { fkGponProfile2 20 }

                
                -- 1.3.6.1.4.1.10428 9 1.101.23.51.20.1
                fkGponProfile2TdmSvcTable OBJECT-TYPE
                        SYNTAX SEQUENCE OF FkGponProfile2TdmSvcEntry
                        MAX-ACCESS not-accessible
                        STATUS current
                        DESCRIPTION
                                "fkGponProfile2TdmSvcTable"
                        ::= { fkGponProfile2TdmSvc 1 }

                
                -- 1.3.6.1.4.1.10428 9 1.101.23.51.20.1.1
                fkGponProfile2TdmSvcEntry OBJECT-TYPE
                        SYNTAX FkGponProfile2TdmSvcEntry
                        MAX-ACCESS not-accessible
                        STATUS current
                        DESCRIPTION
                                "key: fkGponProfile2TrafficIndex, fkGponProfile2TdmSvcId, fkGponProfile2IpHostTdmId"
                        INDEX { fkGponProfile2TrafficIndex, fkGponProfile2TdmSvcId, fkGponProfile2IpHostTdmId }
                        ::= { fkGponProfile2TdmSvcTable 1 }

                
                FkGponProfile2TdmSvcEntry ::=
                        SEQUENCE { 
                                fkGponProfile2TdmSvcId
                                        INTEGER,
                                fkGponProfile2TdmSvcMode
                                        INTEGER,
                                fkGponProfile2TdmSvcTdmPwProfileName
                                        OCTET STRING,
                                fkGponProfile2TdmSvcTimeSlot
                                        OCTET STRING,
                                fkGponProfile2TdmSvcFilterMode
                                        INTEGER,
                                fkGponProfile2TdmSvcFilter
                                        OCTET STRING,
                                fkGponProfile2TdmSvcEthDestMac
                                        OCTET STRING,
                                fkGponProfile2TdmSvcEthVid
                                        INTEGER,
                                fkGponProfile2TdmSvcEthCoS
                                        INTEGER,
                                fkGponProfile2TdmSvcTranPayloadEcid
                                        INTEGER,
                                fkGponProfile2TdmSvcTranSignallingEcid
                                        INTEGER,
                                fkGponProfile2TdmSvcRecvPayloadEcid
                                        INTEGER,
                                fkGponProfile2TdmSvcRecvSignallingEcid
                                        INTEGER,
                                fkGponProfile2TdmSvcExpectPayloadEcid
                                        INTEGER,
                                fkGponProfile2TdmSvcExpectSignallingEcid
                                        INTEGER,
                                fkGponProfile2TdmSvcProtocolPort
                                        INTEGER,
                                fkGponProfile2TdmSvcProtocolTos
                                        INTEGER,
                                fkGponProfile2TdmSvcFarEndIpURL
                                        OCTET STRING,
                                fkGponProfile2TdmSvcMplsLabelIndicator
                                        INTEGER,
                                fkGponProfile2TdmSvcMplsPwDirection
                                        INTEGER,
                                fkGponProfile2TdmSvcMplsPwLabelUp
                                        INTEGER,
                                fkGponProfile2TdmSvcMplsPwLabelDown
                                        INTEGER,
                                fkGponProfile2TdmSvcMplsPwLabelExp
                                        INTEGER,
                                fkGponProfile2TdmSvcMplsPwTunnelDirection
                                        INTEGER,
                                fkGponProfile2TdmSvcMplsPwTunnelLabelUp
                                        INTEGER,
                                fkGponProfile2TdmSvcMplsPwTunnelLabelDown
                                        INTEGER,
                                fkGponProfile2TdmSvcMplsPwTunnelLabelExp
                                        INTEGER,
                                fkGponProfile2TdmSvcCesBuffCdvTolerance
                                        INTEGER,
                                fkGponProfile2TdmSvcCesChannelAssociateSignal
                                        INTEGER,
                                fkGponProfile2TdmSvcProtocolType
                                        INTEGER
                         }

                -- 1.3.6.1.4.1.10428 9 1.101.23.51.20.1.1.1
                fkGponProfile2TdmSvcId OBJECT-TYPE
                        SYNTAX INTEGER (1..65535)
                        MAX-ACCESS read-only
                        STATUS current
                        DESCRIPTION
                                "Select TDM mode"
                        ::= { fkGponProfile2TdmSvcEntry 1 }

                
                -- 1.3.6.1.4.1.10428 9 1.101.23.51.20.1.1.2
                fkGponProfile2TdmSvcMode OBJECT-TYPE
                        SYNTAX INTEGER
                                {
                                pwMef8(1),
                                pwIp(2),
                                pwMpls(3),
                                pwMplsGem(4),
                                sdh(5)
                                }
                        MAX-ACCESS read-only
                        STATUS current
                        DESCRIPTION
                                "The TDM service mode.
                                1: pwMef8(1)
                                2: pwIp(2)
                                3: pwMpls(3)
                                4: pwMplsGem(4)
                                5: sdh(5)"
                        ::= { fkGponProfile2TdmSvcEntry 2 }

                
                -- 1.3.6.1.4.1.10428 9 1.101.23.51.20.1.1.3
                fkGponProfile2TdmSvcTdmPwProfileName OBJECT-TYPE
                        SYNTAX OCTET STRING
                        MAX-ACCESS read-only
                        STATUS current
                        DESCRIPTION
                                "TDM Pseudowire Profile Name"
                        ::= { fkGponProfile2TdmSvcEntry 3 }

                
                -- 1.3.6.1.4.1.10428 9 1.101.23.51.20.1.1.4
                fkGponProfile2TdmSvcTimeSlot OBJECT-TYPE
                        SYNTAX OCTET STRING
                        MAX-ACCESS read-only
                        STATUS current
                        DESCRIPTION
                                "The time slot."
                        ::= { fkGponProfile2TdmSvcEntry 4 }

                
                -- 1.3.6.1.4.1.10428 9 1.101.23.51.20.1.1.5
                fkGponProfile2TdmSvcFilterMode OBJECT-TYPE
                        SYNTAX INTEGER
                                {
                                unUsed(0),
                                allow(1),
                                deny(2)
                                }
                        MAX-ACCESS read-only
                        STATUS current
                        DESCRIPTION
                                "Allow or deny that untagged fowarding operation"
                        ::= { fkGponProfile2TdmSvcEntry 5 }

                
                -- 1.3.6.1.4.1.10428 9 1.101.23.51.20.1.1.6
                fkGponProfile2TdmSvcFilter OBJECT-TYPE
                        SYNTAX OCTET STRING
                        MAX-ACCESS read-only
                        STATUS current
                        DESCRIPTION
                                "VLAN Tagging Filter Data"
                        ::= { fkGponProfile2TdmSvcEntry 6 }

                
                -- 1.3.6.1.4.1.10428 9 1.101.23.51.20.1.1.7
                fkGponProfile2TdmSvcEthDestMac OBJECT-TYPE
                        SYNTAX OCTET STRING
                        MAX-ACCESS read-only
                        STATUS current
                        DESCRIPTION
                                "The Destination MAC address"
                        ::= { fkGponProfile2TdmSvcEntry 7 }

                
                -- 1.3.6.1.4.1.10428 9 1.101.23.51.20.1.1.8
                fkGponProfile2TdmSvcEthVid OBJECT-TYPE
                        SYNTAX INTEGER (1..65535)
                        MAX-ACCESS read-only
                        STATUS current
                        DESCRIPTION
                                "The Ethernet Flow Tag Policy VID Value"
                        ::= { fkGponProfile2TdmSvcEntry 8 }

                
                -- 1.3.6.1.4.1.10428 9 1.101.23.51.20.1.1.9
                fkGponProfile2TdmSvcEthCoS OBJECT-TYPE
                        SYNTAX INTEGER (1..65535)
                        MAX-ACCESS read-only
                        STATUS current
                        DESCRIPTION
                                "The Ethernet Flow Tag Policy COS Value"
                        ::= { fkGponProfile2TdmSvcEntry 9 }

                
                -- 1.3.6.1.4.1.10428 9 1.101.23.51.20.1.1.10
                fkGponProfile2TdmSvcTranPayloadEcid OBJECT-TYPE
                        SYNTAX INTEGER (1..65535)
                        MAX-ACCESS read-only
                        STATUS current
                        DESCRIPTION
                                "The Trasmit Payload ECID"
                        ::= { fkGponProfile2TdmSvcEntry 10 }

                
                -- 1.3.6.1.4.1.10428 9 1.101.23.51.20.1.1.11
                fkGponProfile2TdmSvcTranSignallingEcid OBJECT-TYPE
                        SYNTAX INTEGER (1..65535)
                        MAX-ACCESS read-only
                        STATUS current
                        DESCRIPTION
                                "The Trasmit Signalling ECID"
                        ::= { fkGponProfile2TdmSvcEntry 11 }

                
                -- 1.3.6.1.4.1.10428 9 1.101.23.51.20.1.1.12
                fkGponProfile2TdmSvcRecvPayloadEcid OBJECT-TYPE
                        SYNTAX INTEGER (1..65535)
                        MAX-ACCESS read-only
                        STATUS current
                        DESCRIPTION
                                "The Recive Payload ECID"
                        ::= { fkGponProfile2TdmSvcEntry 12 }

                
                -- 1.3.6.1.4.1.10428 9 1.101.23.51.20.1.1.13
                fkGponProfile2TdmSvcRecvSignallingEcid OBJECT-TYPE
                        SYNTAX INTEGER (1..65535)
                        MAX-ACCESS read-only
                        STATUS current
                        DESCRIPTION
                                "The Recive Signalling ECID"
                        ::= { fkGponProfile2TdmSvcEntry 13 }

                
                -- 1.3.6.1.4.1.10428 9 1.101.23.51.20.1.1.14
                fkGponProfile2TdmSvcExpectPayloadEcid OBJECT-TYPE
                        SYNTAX INTEGER (1..65535)
                        MAX-ACCESS read-only
                        STATUS current
                        DESCRIPTION
                                "The Expected Payload ECID"
                        ::= { fkGponProfile2TdmSvcEntry 14 }

                
                -- 1.3.6.1.4.1.10428 9 1.101.23.51.20.1.1.15
                fkGponProfile2TdmSvcExpectSignallingEcid OBJECT-TYPE
                        SYNTAX INTEGER (1..65535)
                        MAX-ACCESS read-only
                        STATUS current
                        DESCRIPTION
                                "The Expected Signalling ECID"
                        ::= { fkGponProfile2TdmSvcEntry 15 }

                
                -- 1.3.6.1.4.1.10428 9 1.101.23.51.20.1.1.16
                fkGponProfile2TdmSvcProtocolPort OBJECT-TYPE
                        SYNTAX INTEGER (1..65535)
                        MAX-ACCESS read-only
                        STATUS current
                        DESCRIPTION
                                "The UDP port number"
                        ::= { fkGponProfile2TdmSvcEntry 16 }

                
                -- 1.3.6.1.4.1.10428 9 1.101.23.51.20.1.1.17
                fkGponProfile2TdmSvcProtocolTos OBJECT-TYPE
                        SYNTAX INTEGER (1..65535)
                        MAX-ACCESS read-only
                        STATUS current
                        DESCRIPTION
                                "The UDP TOS value"
                        ::= { fkGponProfile2TdmSvcEntry 17 }

                
                -- 1.3.6.1.4.1.10428 9 1.101.23.51.20.1.1.18
                fkGponProfile2TdmSvcFarEndIpURL OBJECT-TYPE
                        SYNTAX OCTET STRING
                        MAX-ACCESS read-only
                        STATUS current
                        DESCRIPTION
                                "The PW IP mode far end termination IP URL"
                        ::= { fkGponProfile2TdmSvcEntry 18 }

                
                -- 1.3.6.1.4.1.10428 9 1.101.23.51.20.1.1.19
                fkGponProfile2TdmSvcMplsLabelIndicator OBJECT-TYPE
                        SYNTAX INTEGER
                                {
                                single(0),
                                double(1),
                                unUsed(255)
                                }
                        MAX-ACCESS read-only
                        STATUS current
                        DESCRIPTION
                                "The MPLS Label stacking situation"
                        ::= { fkGponProfile2TdmSvcEntry 19 }

                
                -- 1.3.6.1.4.1.10428 9 1.101.23.51.20.1.1.20
                fkGponProfile2TdmSvcMplsPwDirection OBJECT-TYPE
                        SYNTAX INTEGER
                                {
                                usOnly(0),
                                dsOnly(1),
                                bidirectional(2),
                                unUsed(255)
                                }
                        MAX-ACCESS read-only
                        STATUS current
                        DESCRIPTION
                                "The Inner MPLS direction"
                        ::= { fkGponProfile2TdmSvcEntry 20 }

                
                -- 1.3.6.1.4.1.10428 9 1.101.23.51.20.1.1.21
                fkGponProfile2TdmSvcMplsPwLabelUp OBJECT-TYPE
                        SYNTAX INTEGER (1..65535)
                        MAX-ACCESS read-only
                        STATUS current
                        DESCRIPTION
                                "The Label of the Inner MPLS pseudowire (Uplink)"
                        ::= { fkGponProfile2TdmSvcEntry 21 }

                
                -- 1.3.6.1.4.1.10428 9 1.101.23.51.20.1.1.22
                fkGponProfile2TdmSvcMplsPwLabelDown OBJECT-TYPE
                        SYNTAX INTEGER (1..65535)
                        MAX-ACCESS read-only
                        STATUS current
                        DESCRIPTION
                                "The Label of the Inner MPLS pseudowire (Downlink)"
                        ::= { fkGponProfile2TdmSvcEntry 22 }

                
                -- 1.3.6.1.4.1.10428 9 1.101.23.51.20.1.1.23
                fkGponProfile2TdmSvcMplsPwLabelExp OBJECT-TYPE
                        SYNTAX INTEGER (1..65535)
                        MAX-ACCESS read-only
                        STATUS current
                        DESCRIPTION
                                "The Label of the Inner MPLS pseudowire (Expert)"
                        ::= { fkGponProfile2TdmSvcEntry 23 }

                
                -- 1.3.6.1.4.1.10428 9 1.101.23.51.20.1.1.24
                fkGponProfile2TdmSvcMplsPwTunnelDirection OBJECT-TYPE
                        SYNTAX INTEGER
                                {
                                usOnly(0),
                                dsOnly(1),
                                bidirectional(2)
                                }
                        MAX-ACCESS read-only
                        STATUS current
                        DESCRIPTION
                                "The Outer MPLS direction"
                        ::= { fkGponProfile2TdmSvcEntry 24 }

                
                -- 1.3.6.1.4.1.10428 9 1.101.23.51.20.1.1.25
                fkGponProfile2TdmSvcMplsPwTunnelLabelUp OBJECT-TYPE
                        SYNTAX INTEGER (1..65535)
                        MAX-ACCESS read-only
                        STATUS current
                        DESCRIPTION
                                "The Label of the Outer label for MPLS tunnel (Uplink)"
                        ::= { fkGponProfile2TdmSvcEntry 25 }

                
                -- 1.3.6.1.4.1.10428 9 1.101.23.51.20.1.1.26
                fkGponProfile2TdmSvcMplsPwTunnelLabelDown OBJECT-TYPE
                        SYNTAX INTEGER (1..65535)
                        MAX-ACCESS read-only
                        STATUS current
                        DESCRIPTION
                                "The Label of the Outer label for MPLS tunnel (Downlink)"
                        ::= { fkGponProfile2TdmSvcEntry 26 }

                
                -- 1.3.6.1.4.1.10428 9 1.101.23.51.20.1.1.27
                fkGponProfile2TdmSvcMplsPwTunnelLabelExp OBJECT-TYPE
                        SYNTAX INTEGER (1..65535)
                        MAX-ACCESS read-only
                        STATUS current
                        DESCRIPTION
                                "The Label of the Outer label for MPLS tunnel (Expert)"
                        ::= { fkGponProfile2TdmSvcEntry 27 }

                
                -- 1.3.6.1.4.1.10428 9 1.101.23.51.20.1.1.28
                fkGponProfile2TdmSvcCesBuffCdvTolerance OBJECT-TYPE
                        SYNTAX INTEGER (1..65535)
                        MAX-ACCESS read-only
                        STATUS current
                        DESCRIPTION
                                "fkGponProfile2TdmSvcCesBuffCdvTolerance"
                        ::= { fkGponProfile2TdmSvcEntry 28 }

                
                -- 1.3.6.1.4.1.10428 9 1.101.23.51.20.1.1.29
                fkGponProfile2TdmSvcCesChannelAssociateSignal OBJECT-TYPE
                        SYNTAX INTEGER
                                {
                                basic(0),
                                e1Cas(1),
                                sfCas(2),
                                ds1EsfCas(3),
                                j2Cas(4),
                                unUsed(255)
                                }
                        MAX-ACCESS read-only
                        STATUS current
                        DESCRIPTION
                                "fkGponProfile2TdmSvcCesChannelAssociateSignal"
                        ::= { fkGponProfile2TdmSvcEntry 29 }

                
                -- 1.3.6.1.4.1.10428 9 1.101.23.51.20.1.1.30
                fkGponProfile2TdmSvcProtocolType OBJECT-TYPE
                        SYNTAX INTEGER
                                {
                                tcp(6),
                                udp(17),
                                tlsp(56)
                                }
                        MAX-ACCESS read-write
                        STATUS current
                        DESCRIPTION
                                "The IP protocol type."
                        ::= { fkGponProfile2TdmSvcEntry 30 }

                
                -- 1.3.6.1.4.1.10428 9 1.101.23.51.20.2
                fkGponProfile2TdmSvcControl OBJECT IDENTIFIER ::= { fkGponProfile2TdmSvc 2 }

                
                -- 1.3.6.1.4.1.10428 9 1.101.23.51.20.2.1
                fkGponProfile2TdmSvcControlRequest OBJECT-TYPE
                        SYNTAX INTEGER
                                {
                                addTdmService(1),
                                delTemService(2),
                                setTdmPwProfile(3),
                                setVlanFilter(4),
                                setEthDestMac(5),
                                setEthTagPolicy(6),
                                setTranEcid(7),
                                setRecvEcid(8),
                                setExpectEcid(9),
                                setUdpPort(10),
                                setFarEndIp(11),
                                setMplsLabelIndicator(12),
                                setMplsPwDirection(13),
                                setMplsPwLabel(14),
                                setMplsPwTunnelDirection(15),
                                setMplsPwTunnelLabel(16),
                                setCesBuffCdvTolerance(17),
                                setCesChannelAssociateSignal(18)
                                }
                        MAX-ACCESS read-write
                        STATUS current
                        DESCRIPTION
                                "The request of a user command"
                        ::= { fkGponProfile2TdmSvcControl 1 }

                
                -- 1.3.6.1.4.1.10428 9 1.101.23.51.20.2.2
                fkGponProfile2TdmSvcControlStatus OBJECT-TYPE
                        SYNTAX FkControlStatusType
                        MAX-ACCESS read-only
                        STATUS current
                        DESCRIPTION
                                "The status of user command"
                        ::= { fkGponProfile2TdmSvcControl 2 }

                
                -- 1.3.6.1.4.1.10428 9 1.101.23.51.20.2.3
                fkGponProfile2TdmSvcControlTimer OBJECT-TYPE
                        SYNTAX Gauge32
                        MAX-ACCESS read-write
                        STATUS current
                        DESCRIPTION
                                "The maximum time for the manager for a long running user command"
                        ::= { fkGponProfile2TdmSvcControl 3 }

                
                -- 1.3.6.1.4.1.10428 9 1.101.23.51.20.2.4
                fkGponProfile2TdmSvcControlTimeStamp OBJECT-TYPE
                        SYNTAX TimeTicks
                        MAX-ACCESS read-only
                        STATUS current
                        DESCRIPTION
                                "The time stamp of the last command(end of command)"
                        ::= { fkGponProfile2TdmSvcControl 4 }

                
                -- 1.3.6.1.4.1.10428 9 1.101.23.51.20.2.5
                fkGponProfile2TdmSvcControlReqResult OBJECT-TYPE
                        SYNTAX FkControlRequestResultType
                        MAX-ACCESS read-only
                        STATUS current
                        DESCRIPTION
                                "The result of the last user command"
                        ::= { fkGponProfile2TdmSvcControl 5 }

                
                -- 1.3.6.1.4.1.10428 9 1.101.23.51.20.2.6
                fkGponProfile2TdmSvcControlTName OBJECT-TYPE
                        SYNTAX OCTET STRING
                        MAX-ACCESS read-write
                        STATUS current
                        DESCRIPTION
                                "TDM Service Name"
                        ::= { fkGponProfile2TdmSvcControl 6 }
-- The ONU profile name.
                
                -- 1.3.6.1.4.1.10428 9 1.101.23.51.20.2.7
                fkGponProfile2TdmSvcControlTdmId OBJECT-TYPE
                        SYNTAX Integer32
                        MAX-ACCESS read-write
                        STATUS current
                        DESCRIPTION
                                "TDM (CES) Port Number"
                        ::= { fkGponProfile2TdmSvcControl 7 }

                
                -- 1.3.6.1.4.1.10428 9 1.101.23.51.20.2.8
                fkGponProfile2TdmSvcControlId OBJECT-TYPE
                        SYNTAX INTEGER (1..65535)
                        MAX-ACCESS read-write
                        STATUS current
                        DESCRIPTION
                                "TDM Service ID"
                        ::= { fkGponProfile2TdmSvcControl 8 }

                
                -- 1.3.6.1.4.1.10428 9 1.101.23.51.20.2.9
                fkGponProfile2TdmSvcControlMode OBJECT-TYPE
                        SYNTAX INTEGER
                                {
                                pwMef8(1),
                                pwIp(2),
                                pwMpls(3),
                                pwMplsGem(4),
                                sdh(5)
                                }
                        MAX-ACCESS read-write
                        STATUS current
                        DESCRIPTION
                                "Select TDM mode"
                        ::= { fkGponProfile2TdmSvcControl 9 }

                
                -- 1.3.6.1.4.1.10428 9 1.101.23.51.20.2.10
                fkGponProfile2TdmSvcControlTdmPwProfileName OBJECT-TYPE
                        SYNTAX OCTET STRING
                        MAX-ACCESS read-write
                        STATUS current
                        DESCRIPTION
                                "TDM Pseudowire Profile Name"
                        ::= { fkGponProfile2TdmSvcControl 10 }

                
                -- 1.3.6.1.4.1.10428 9 1.101.23.51.20.2.11
                fkGponProfile2TdmSvcControlTimeSlot OBJECT-TYPE
                        SYNTAX OCTET STRING
                        MAX-ACCESS read-write
                        STATUS current
                        DESCRIPTION
                                "Time slot"
                        ::= { fkGponProfile2TdmSvcControl 11 }

                
                -- 1.3.6.1.4.1.10428 9 1.101.23.51.20.2.12
                fkGponProfile2TdmSvcControlFilterMode OBJECT-TYPE
                        SYNTAX INTEGER
                                {
                                unUsed(0),
                                allow(1),
                                deny(2)
                                }
                        MAX-ACCESS read-write
                        STATUS current
                        DESCRIPTION
                                "Allow or deny that untagged fowarding operation"
                        ::= { fkGponProfile2TdmSvcControl 12 }

                
                -- 1.3.6.1.4.1.10428 9 1.101.23.51.20.2.13
                fkGponProfile2TdmSvcControlFilter OBJECT-TYPE
                        SYNTAX OCTET STRING
                        MAX-ACCESS read-write
                        STATUS current
                        DESCRIPTION
                                "VLAN Tagging Filter Data"
                        ::= { fkGponProfile2TdmSvcControl 13 }

                
                -- 1.3.6.1.4.1.10428 9 1.101.23.51.20.2.14
                fkGponProfile2TdmSvcControlEthDestMac OBJECT-TYPE
                        SYNTAX OCTET STRING
                        MAX-ACCESS read-write
                        STATUS current
                        DESCRIPTION
                                "Destination MAC address"
                        ::= { fkGponProfile2TdmSvcControl 14 }

                
                -- 1.3.6.1.4.1.10428 9 1.101.23.51.20.2.15
                fkGponProfile2TdmSvcControlEthVid OBJECT-TYPE
                        SYNTAX INTEGER (1..65535)
                        MAX-ACCESS read-write
                        STATUS current
                        DESCRIPTION
                                "Ethernet Flow Tag Policy VID Value"
                        ::= { fkGponProfile2TdmSvcControl 15 }

                
                -- 1.3.6.1.4.1.10428 9 1.101.23.51.20.2.16
                fkGponProfile2TdmSvcControlEthCoS OBJECT-TYPE
                        SYNTAX INTEGER (1..65535)
                        MAX-ACCESS read-write
                        STATUS current
                        DESCRIPTION
                                "Ethernet Flow Tag Policy COS Value"
                        ::= { fkGponProfile2TdmSvcControl 16 }

                
                -- 1.3.6.1.4.1.10428 9 1.101.23.51.20.2.17
                fkGponProfile2TdmSvcControlTranPayloadEcid OBJECT-TYPE
                        SYNTAX INTEGER (1..65535)
                        MAX-ACCESS read-write
                        STATUS current
                        DESCRIPTION
                                "Trasmit Payload ECID"
                        ::= { fkGponProfile2TdmSvcControl 17 }

                
                -- 1.3.6.1.4.1.10428 9 1.101.23.51.20.2.18
                fkGponProfile2TdmSvcControlTranSignallingEcid OBJECT-TYPE
                        SYNTAX INTEGER (1..65535)
                        MAX-ACCESS read-write
                        STATUS current
                        DESCRIPTION
                                "Trasmit Signalling ECID"
                        ::= { fkGponProfile2TdmSvcControl 18 }

                
                -- 1.3.6.1.4.1.10428 9 1.101.23.51.20.2.19
                fkGponProfile2TdmSvcControlRecvPayloadEcid OBJECT-TYPE
                        SYNTAX INTEGER (1..65535)
                        MAX-ACCESS read-write
                        STATUS current
                        DESCRIPTION
                                "Recive Payload ECID"
                        ::= { fkGponProfile2TdmSvcControl 19 }

                
                -- 1.3.6.1.4.1.10428 9 1.101.23.51.20.2.20
                fkGponProfile2TdmSvcControlRecvSignallingEcid OBJECT-TYPE
                        SYNTAX INTEGER (1..65535)
                        MAX-ACCESS read-write
                        STATUS current
                        DESCRIPTION
                                "Recive Signalling ECID"
                        ::= { fkGponProfile2TdmSvcControl 20 }

                
                -- 1.3.6.1.4.1.10428 9 1.101.23.51.20.2.21
                fkGponProfile2TdmSvcControlExpectPayloadEcid OBJECT-TYPE
                        SYNTAX INTEGER (1..65535)
                        MAX-ACCESS read-write
                        STATUS current
                        DESCRIPTION
                                "Expected Payload ECID"
                        ::= { fkGponProfile2TdmSvcControl 21 }

                
                -- 1.3.6.1.4.1.10428 9 1.101.23.51.20.2.22
                fkGponProfile2TdmSvcControlExpectSignallingEcid OBJECT-TYPE
                        SYNTAX INTEGER (1..65535)
                        MAX-ACCESS read-write
                        STATUS current
                        DESCRIPTION
                                "Expected Signalling ECID"
                        ::= { fkGponProfile2TdmSvcControl 22 }

                
                -- 1.3.6.1.4.1.10428 9 1.101.23.51.20.2.23
                fkGponProfile2TdmSvcControlProtocolPort OBJECT-TYPE
                        SYNTAX INTEGER (1..65535)
                        MAX-ACCESS read-write
                        STATUS current
                        DESCRIPTION
                                "UDP port number"
                        ::= { fkGponProfile2TdmSvcControl 23 }

                
                -- 1.3.6.1.4.1.10428 9 1.101.23.51.20.2.24
                fkGponProfile2TdmSvcControlProtocolTos OBJECT-TYPE
                        SYNTAX INTEGER (1..65535)
                        MAX-ACCESS read-write
                        STATUS current
                        DESCRIPTION
                                "UDP TOS value"
                        ::= { fkGponProfile2TdmSvcControl 24 }

                
                -- 1.3.6.1.4.1.10428 9 1.101.23.51.20.2.25
                fkGponProfile2TdmSvcControlFarEndIpURL OBJECT-TYPE
                        SYNTAX OCTET STRING
                        MAX-ACCESS read-write
                        STATUS current
                        DESCRIPTION
                                "PW IP mode far end termination IP URL"
                        ::= { fkGponProfile2TdmSvcControl 25 }

                
                -- 1.3.6.1.4.1.10428 9 1.101.23.51.20.2.26
                fkGponProfile2TdmSvcControlMplsLabelIndicator OBJECT-TYPE
                        SYNTAX INTEGER
                                {
                                single(0),
                                double(1),
                                unUsed(255)
                                }
                        MAX-ACCESS read-write
                        STATUS current
                        DESCRIPTION
                                "MPLS Label stacking situation"
                        ::= { fkGponProfile2TdmSvcControl 26 }

                
                -- 1.3.6.1.4.1.10428 9 1.101.23.51.20.2.27
                fkGponProfile2TdmSvcControlMplsPwDirection OBJECT-TYPE
                        SYNTAX INTEGER
                                {
                                usOnly(0),
                                dsOnly(1),
                                bidirectional(2),
                                unUsed(255)
                                }
                        MAX-ACCESS read-write
                        STATUS current
                        DESCRIPTION
                                "Inner MPLS direction"
                        ::= { fkGponProfile2TdmSvcControl 27 }

                
                -- 1.3.6.1.4.1.10428 9 1.101.23.51.20.2.28
                fkGponProfile2TdmSvcControlMplsPwLabelUp OBJECT-TYPE
                        SYNTAX INTEGER (1..65535)
                        MAX-ACCESS read-write
                        STATUS current
                        DESCRIPTION
                                "Label of the Inner MPLS pseudowire (Uplink)"
                        ::= { fkGponProfile2TdmSvcControl 28 }

                
                -- 1.3.6.1.4.1.10428 9 1.101.23.51.20.2.29
                fkGponProfile2TdmSvcControlMplsPwLabelDown OBJECT-TYPE
                        SYNTAX INTEGER (1..65535)
                        MAX-ACCESS read-write
                        STATUS current
                        DESCRIPTION
                                "Label of the Inner MPLS pseudowire (Downlink)"
                        ::= { fkGponProfile2TdmSvcControl 29 }

                
                -- 1.3.6.1.4.1.10428 9 1.101.23.51.20.2.30
                fkGponProfile2TdmSvcControlMplsPwLabelExp OBJECT-TYPE
                        SYNTAX INTEGER (1..65535)
                        MAX-ACCESS read-write
                        STATUS current
                        DESCRIPTION
                                "Label of the Inner MPLS pseudowire (Expert)"
                        ::= { fkGponProfile2TdmSvcControl 30 }

                
                -- 1.3.6.1.4.1.10428 9 1.101.23.51.20.2.31
                fkGponProfile2TdmSvcControlMplsPwTunnelDirection OBJECT-TYPE
                        SYNTAX INTEGER
                                {
                                usOnly(0),
                                dsOnly(1),
                                bidirectional(2)
                                }
                        MAX-ACCESS read-write
                        STATUS current
                        DESCRIPTION
                                "Outer MPLS direction"
                        ::= { fkGponProfile2TdmSvcControl 31 }

                
                -- 1.3.6.1.4.1.10428 9 1.101.23.51.20.2.32
                fkGponProfile2TdmSvcControlMplsPwTunnelLabelUp OBJECT-TYPE
                        SYNTAX INTEGER (1..65535)
                        MAX-ACCESS read-write
                        STATUS current
                        DESCRIPTION
                                "Label of the Outer label for MPLS tunnel (Uplink)"
                        ::= { fkGponProfile2TdmSvcControl 32 }

                
                -- 1.3.6.1.4.1.10428 9 1.101.23.51.20.2.33
                fkGponProfile2TdmSvcControlMplsPwTunnelLabelDown OBJECT-TYPE
                        SYNTAX INTEGER (1..65535)
                        MAX-ACCESS read-write
                        STATUS current
                        DESCRIPTION
                                "Label of the Outer label for MPLS tunnel (Downlink)"
                        ::= { fkGponProfile2TdmSvcControl 33 }

                
                -- 1.3.6.1.4.1.10428 9 1.101.23.51.20.2.34
                fkGponProfile2TdmSvcControlMplsPwTunnelLabelExp OBJECT-TYPE
                        SYNTAX INTEGER (1..65535)
                        MAX-ACCESS read-write
                        STATUS current
                        DESCRIPTION
                                "Label of the Outer label for MPLS tunnel (Expert)"
                        ::= { fkGponProfile2TdmSvcControl 34 }

                
                -- 1.3.6.1.4.1.10428 9 1.101.23.51.20.2.35
                fkGponProfile2TdmSvcControlCesBuffCdvTolerance OBJECT-TYPE
                        SYNTAX INTEGER (1..65535)
                        MAX-ACCESS read-write
                        STATUS current
                        DESCRIPTION
                                "fkGponProfile2TdmSvcControlCesBuffCdvTolerance (unused)"
                        ::= { fkGponProfile2TdmSvcControl 35 }

                
                -- 1.3.6.1.4.1.10428 9 1.101.23.51.20.2.36
                fkGponProfile2TdmSvcControlCesChannelAssociateSignal OBJECT-TYPE
                        SYNTAX INTEGER
                                {
                                basic(0),
                                e1Cas(1),
                                sfCas(2),
                                ds1EsfCas(3),
                                j2Cas(4),
                                unUsed(255)
                                }
                        MAX-ACCESS read-write
                        STATUS current
                        DESCRIPTION
                                "fkGponProfile2TdmSvcControlCesChannelAssociateSignal (unused)"
                        ::= { fkGponProfile2TdmSvcControl 36 }

                
                -- 1.3.6.1.4.1.10428 9 1.101.23.51.20.2.37
                fkGponProfile2TdmSvcControlProtocolType OBJECT-TYPE
                        SYNTAX INTEGER
                                {
                                tcp(6),
                                udp(17),
                                tlsp(56)
                                }
                        MAX-ACCESS read-write
                        STATUS current
                        DESCRIPTION
                                "The IP protocol type."
                        ::= { fkGponProfile2TdmSvcControl 37 }

                
                -- 1.3.6.1.4.1.10428 9 1.101.23.51.20.3
                fkGponProfile2TdmSvcNotification OBJECT IDENTIFIER ::= { fkGponProfile2TdmSvc 3 }

                
                -- 1.3.6.1.4.1.10428 9 1.101.23.51.20.3.1
                fkGponProfile2TdmSvcTdmServiceCreated NOTIFICATION-TYPE
                        OBJECTS { fkGponProfile2TdmSvcControlRequest, fkGponProfile2TdmSvcControlTimeStamp, fkGponProfile2TdmSvcControlReqResult, fkGponProfile2TdmSvcControlId, fkGponProfile2TdmSvcControlTdmId, 
                                fkGponProfile2TdmSvcControlMode }
                        STATUS current
                        DESCRIPTION 
                                "Description."
                        ::= { fkGponProfile2TdmSvcNotification 1 }

                
                -- 1.3.6.1.4.1.10428 9 1.101.23.51.20.3.2
                fkGponProfile2TdmSvcTdmServiceDeleted NOTIFICATION-TYPE
                        OBJECTS { fkGponProfile2TdmSvcControlId, fkGponProfile2TdmSvcControlTName, fkGponProfile2TdmSvcControlTdmId, fkGponProfile2TdmSvcControlMode, fkGponProfile2TdmSvcControlRequest, 
                                fkGponProfile2TdmSvcControlTimeStamp, fkGponProfile2TdmSvcControlReqResult }
                        STATUS current
                        DESCRIPTION 
                                "Description."
                        ::= { fkGponProfile2TdmSvcNotification 2 }

                
                -- 1.3.6.1.4.1.10428 9 1.101.23.51.20.3.3
                fkGponProfile2TdmSvcTdmPwProfileChanged NOTIFICATION-TYPE
                        OBJECTS { fkGponProfile2TdmSvcControlTdmId, fkGponProfile2TdmSvcControlId, fkGponProfile2TdmSvcControlTdmPwProfileName, fkGponProfile2TdmSvcControlTimeSlot, fkGponProfile2TdmSvcControlRequest, 
                                fkGponProfile2TdmSvcControlTimeStamp, fkGponProfile2TdmSvcControlReqResult }
                        STATUS current
                        DESCRIPTION 
                                "Description."
                        ::= { fkGponProfile2TdmSvcNotification 3 }

                
                -- 1.3.6.1.4.1.10428 9 1.101.23.51.20.3.4
                fkGponProfile2TdmSvcTdmVlanFilterChanged NOTIFICATION-TYPE
                        OBJECTS { fkGponProfile2TdmSvcControlId, fkGponProfile2TdmSvcControlRequest, fkGponProfile2TdmSvcControlTimeStamp, fkGponProfile2TdmSvcControlReqResult, fkGponProfile2TdmSvcControlFilterMode, 
                                fkGponProfile2TdmSvcControlFilter }
                        STATUS current
                        DESCRIPTION 
                                "Description."
                        ::= { fkGponProfile2TdmSvcNotification 4 }

                
                -- 1.3.6.1.4.1.10428 9 1.101.23.51.20.3.5
                fkGponProfile2TdmSvcTdmEthDestMacChanged NOTIFICATION-TYPE
                        OBJECTS { fkGponProfile2TdmSvcControlTdmId, fkGponProfile2TdmSvcControlId, fkGponProfile2TdmSvcControlEthDestMac, fkGponProfile2TdmSvcControlRequest, fkGponProfile2TdmSvcControlTimeStamp, 
                                fkGponProfile2TdmSvcControlReqResult }
                        STATUS current
                        DESCRIPTION 
                                "Description."
                        ::= { fkGponProfile2TdmSvcNotification 5 }

                
                -- 1.3.6.1.4.1.10428 9 1.101.23.51.20.3.6
                fkGponProfile2TdmSvcTdmEthTagPolicyChanged NOTIFICATION-TYPE
                        OBJECTS { fkGponProfile2TdmSvcControlTdmId, fkGponProfile2TdmSvcControlId, fkGponProfile2TdmSvcControlEthVid, fkGponProfile2TdmSvcControlEthCoS, fkGponProfile2TdmSvcControlRequest, 
                                fkGponProfile2TdmSvcControlTimeStamp, fkGponProfile2TdmSvcControlReqResult }
                        STATUS current
                        DESCRIPTION 
                                "Description."
                        ::= { fkGponProfile2TdmSvcNotification 6 }

                
                -- 1.3.6.1.4.1.10428 9 1.101.23.51.20.3.7
                fkGponProfile2TdmSvcTdmTranEcidChanged NOTIFICATION-TYPE
                        OBJECTS { fkGponProfile2TdmSvcControlTranPayloadEcid, fkGponProfile2TdmSvcControlTranSignallingEcid, fkGponProfile2TdmSvcControlTdmId, fkGponProfile2TdmSvcControlId, fkGponProfile2TdmSvcControlRequest, 
                                fkGponProfile2TdmSvcControlTimeStamp, fkGponProfile2TdmSvcControlReqResult }
                        STATUS current
                        DESCRIPTION 
                                "Description."
                        ::= { fkGponProfile2TdmSvcNotification 7 }

                
                -- 1.3.6.1.4.1.10428 9 1.101.23.51.20.3.8
                fkGponProfile2TdmSvcTdmRecvEcidChanged NOTIFICATION-TYPE
                        OBJECTS { fkGponProfile2TdmSvcControlTdmId, fkGponProfile2TdmSvcControlId, fkGponProfile2TdmSvcControlRecvPayloadEcid, fkGponProfile2TdmSvcControlRecvSignallingEcid, fkGponProfile2TdmSvcControlRequest, 
                                fkGponProfile2TdmSvcControlTimeStamp, fkGponProfile2TdmSvcControlReqResult }
                        STATUS current
                        DESCRIPTION 
                                "Description."
                        ::= { fkGponProfile2TdmSvcNotification 8 }

                
                -- 1.3.6.1.4.1.10428 9 1.101.23.51.20.3.9
                fkGponProfile2TdmSvcTdmExpectEcidChanged NOTIFICATION-TYPE
                        OBJECTS { fkGponProfile2TdmSvcControlTdmId, fkGponProfile2TdmSvcControlId, fkGponProfile2TdmSvcControlExpectPayloadEcid, fkGponProfile2TdmSvcControlExpectSignallingEcid, fkGponProfile2TdmSvcControlRequest, 
                                fkGponProfile2TdmSvcControlTimeStamp, fkGponProfile2TdmSvcControlReqResult }
                        STATUS current
                        DESCRIPTION 
                                "Description."
                        ::= { fkGponProfile2TdmSvcNotification 9 }

                
                -- 1.3.6.1.4.1.10428 9 1.101.23.51.20.3.10
                fkGponProfile2TdmSvcTdmUdpPortChanged NOTIFICATION-TYPE
                        OBJECTS { fkGponProfile2TdmSvcControlTdmId, fkGponProfile2TdmSvcControlId, fkGponProfile2TdmSvcControlRequest, fkGponProfile2TdmSvcControlTimeStamp, fkGponProfile2TdmSvcControlReqResult, 
                                fkGponProfile2TdmSvcControlProtocolPort, fkGponProfile2TdmSvcControlProtocolTos, fkGponProfile2TdmSvcControlProtocolType }
                        STATUS current
                        DESCRIPTION 
                                "Description."
                        ::= { fkGponProfile2TdmSvcNotification 10 }

                
                -- 1.3.6.1.4.1.10428 9 1.101.23.51.20.3.11
                fkGponProfile2TdmSvcTdmFarEndIpChanged NOTIFICATION-TYPE
                        OBJECTS { fkGponProfile2TdmSvcControlTdmId, fkGponProfile2TdmSvcControlId, fkGponProfile2TdmSvcControlFarEndIpURL, fkGponProfile2TdmSvcControlRequest, fkGponProfile2TdmSvcControlTimeStamp, 
                                fkGponProfile2TdmSvcControlReqResult }
                        STATUS current
                        DESCRIPTION 
                                "Description."
                        ::= { fkGponProfile2TdmSvcNotification 11 }

                
                -- 1.3.6.1.4.1.10428 9 1.101.23.51.20.3.12
                fkGponProfile2TdmSvcMplsLabelIndicatorChanged NOTIFICATION-TYPE
                        OBJECTS { fkGponProfile2TdmSvcControlTdmId, fkGponProfile2TdmSvcControlId, fkGponProfile2TdmSvcControlMplsLabelIndicator, fkGponProfile2TdmSvcControlRequest, fkGponProfile2TdmSvcControlTimeStamp, 
                                fkGponProfile2TdmSvcControlReqResult }
                        STATUS current
                        DESCRIPTION 
                                "Description."
                        ::= { fkGponProfile2TdmSvcNotification 12 }

                
                -- 1.3.6.1.4.1.10428 9 1.101.23.51.20.3.13
                fkGponProfile2TdmSvcMplsPwDirectionChanged NOTIFICATION-TYPE
                        OBJECTS { fkGponProfile2TdmSvcControlTdmId, fkGponProfile2TdmSvcControlId, fkGponProfile2TdmSvcControlMplsPwDirection, fkGponProfile2TdmSvcControlRequest, fkGponProfile2TdmSvcControlTimeStamp, 
                                fkGponProfile2TdmSvcControlReqResult }
                        STATUS current
                        DESCRIPTION 
                                "Description."
                        ::= { fkGponProfile2TdmSvcNotification 13 }

                
                -- 1.3.6.1.4.1.10428 9 1.101.23.51.20.3.14
                fkGponProfile2TdmSvcMplsPwLabelChanged NOTIFICATION-TYPE
                        OBJECTS { fkGponProfile2TdmSvcControlTdmId, fkGponProfile2TdmSvcControlId, fkGponProfile2TdmSvcControlMplsPwLabelUp, fkGponProfile2TdmSvcControlMplsPwLabelDown, fkGponProfile2TdmSvcControlMplsPwLabelExp, 
                                fkGponProfile2TdmSvcControlRequest, fkGponProfile2TdmSvcControlTimeStamp, fkGponProfile2TdmSvcControlReqResult }
                        STATUS current
                        DESCRIPTION 
                                "Description."
                        ::= { fkGponProfile2TdmSvcNotification 14 }

                
                -- 1.3.6.1.4.1.10428 9 1.101.23.51.20.3.15
                fkGponProfile2TdmSvcMplsPwTunnelDirectionChanged NOTIFICATION-TYPE
                        OBJECTS { fkGponProfile2TdmSvcControlTdmId, fkGponProfile2TdmSvcControlId, fkGponProfile2TdmSvcControlMplsPwTunnelDirection, fkGponProfile2TdmSvcControlRequest, fkGponProfile2TdmSvcControlTimeStamp, 
                                fkGponProfile2TdmSvcControlReqResult }
                        STATUS current
                        DESCRIPTION 
                                "Description."
                        ::= { fkGponProfile2TdmSvcNotification 15 }

                
                -- 1.3.6.1.4.1.10428 9 1.101.23.51.20.3.16
                fkGponProfile2TdmSvcMplsPwTunnelLabelChanged NOTIFICATION-TYPE
                        OBJECTS { fkGponProfile2TdmSvcControlTdmId, fkGponProfile2TdmSvcControlId, fkGponProfile2TdmSvcControlMplsPwTunnelLabelUp, fkGponProfile2TdmSvcControlMplsPwTunnelLabelDown, fkGponProfile2TdmSvcControlMplsPwTunnelLabelExp, 
                                fkGponProfile2TdmSvcControlRequest, fkGponProfile2TdmSvcControlTimeStamp, fkGponProfile2TdmSvcControlReqResult }
                        STATUS current
                        DESCRIPTION 
                                "Description."
                        ::= { fkGponProfile2TdmSvcNotification 16 }

                
                -- 1.3.6.1.4.1.10428 9 1.101.23.51.20.3.17
                fkGponProfile2TdmSvcCesBuffCdvToleranceChanged NOTIFICATION-TYPE
                        OBJECTS { fkGponProfile2TdmSvcControlTdmId, fkGponProfile2TdmSvcControlId, fkGponProfile2TdmSvcControlCesBuffCdvTolerance, fkGponProfile2TdmSvcControlRequest, fkGponProfile2TdmSvcControlTimeStamp, 
                                fkGponProfile2TdmSvcControlReqResult }
                        STATUS current
                        DESCRIPTION 
                                "Description."
                        ::= { fkGponProfile2TdmSvcNotification 17 }

                
                -- 1.3.6.1.4.1.10428 9 1.101.23.51.20.3.18
                fkGponProfile2TdmSvcCesChannelAssociateSignalChanged NOTIFICATION-TYPE
                        OBJECTS { fkGponProfile2TdmSvcControlTdmId, fkGponProfile2TdmSvcControlId, fkGponProfile2TdmSvcControlCesChannelAssociateSignal, fkGponProfile2TdmSvcControlRequest, fkGponProfile2TdmSvcControlTimeStamp, 
                                fkGponProfile2TdmSvcControlReqResult }
                        STATUS current
                        DESCRIPTION 
                                "Description."
                        ::= { fkGponProfile2TdmSvcNotification 18 }

                
                -- 1.3.6.1.4.1.10428 9 1.101.23.51.21
                fkGponProfile2BridgeGem OBJECT IDENTIFIER ::= { fkGponProfile2 21 }

                
                -- 1.3.6.1.4.1.10428 9 1.101.23.51.21.1
                fkGponProfile2BridgeGemTable OBJECT-TYPE
                        SYNTAX SEQUENCE OF FkGponProfile2BridgeGemEntry
                        MAX-ACCESS not-accessible
                        STATUS current
                        DESCRIPTION
                                "fkGponProfile2BridgeGemTable"
                        ::= { fkGponProfile2BridgeGem 1 }

                
                -- 1.3.6.1.4.1.10428 9 1.101.23.51.21.1.1
                fkGponProfile2BridgeGemEntry OBJECT-TYPE
                        SYNTAX FkGponProfile2BridgeGemEntry
                        MAX-ACCESS not-accessible
                        STATUS current
                        DESCRIPTION
                                "key: fkGponProfile2TrafficIndex, fkGponProfile2BridgeId, fkGponProfile2BridgeGemId"
                        INDEX { fkGponProfile2TrafficIndex, fkGponProfile2BridgeId, fkGponProfile2BridgeGemId }
                        ::= { fkGponProfile2BridgeGemTable 1 }

                
                FkGponProfile2BridgeGemEntry ::=
                        SEQUENCE { 
                                fkGponProfile2BridgeGemId
                                        INTEGER,
                                fkGponProfile2BridgeGemVlanFilterMode
                                        INTEGER,
                                fkGponProfile2BridgeGemVlanFilter
                                        INTEGER
                         }

                -- 1.3.6.1.4.1.10428 9 1.101.23.51.21.1.1.1
                fkGponProfile2BridgeGemId OBJECT-TYPE
                        SYNTAX INTEGER (1..65535)
                        MAX-ACCESS read-only
                        STATUS current
                        DESCRIPTION
                                "The Gem ID"
                        ::= { fkGponProfile2BridgeGemEntry 1 }

                
                -- 1.3.6.1.4.1.10428 9 1.101.23.51.21.1.1.2
                fkGponProfile2BridgeGemVlanFilterMode OBJECT-TYPE
                        SYNTAX INTEGER
                                {
                                unUsed(0),
                                allow(1),
                                derny(2)
                                }
                        MAX-ACCESS read-only
                        STATUS current
                        DESCRIPTION
                                "Allow or deny that untagged fowarding operation"
                        ::= { fkGponProfile2BridgeGemEntry 2 }

                
                -- 1.3.6.1.4.1.10428 9 1.101.23.51.21.1.1.3
                fkGponProfile2BridgeGemVlanFilter OBJECT-TYPE
                        SYNTAX INTEGER (1..65535)
                        MAX-ACCESS read-only
                        STATUS current
                        DESCRIPTION
                                "The Vlan filter."
                        ::= { fkGponProfile2BridgeGemEntry 3 }

                
                -- 1.3.6.1.4.1.10428 9 1.101.23.51.21.2
                fkGponProfile2BridgeGemControl OBJECT IDENTIFIER ::= { fkGponProfile2BridgeGem 2 }

                
                -- 1.3.6.1.4.1.10428 9 1.101.23.51.21.2.1
                fkGponProfile2BridgeGemControlRequest OBJECT-TYPE
                        SYNTAX INTEGER
                                {
                                addBridgeGem(1),
                                delBridgeGem(2),
                                setVlanFilter(3)
                                }
                        MAX-ACCESS read-write
                        STATUS current
                        DESCRIPTION
                                "The request of a user command"
                        ::= { fkGponProfile2BridgeGemControl 1 }

                
                -- 1.3.6.1.4.1.10428 9 1.101.23.51.21.2.2
                fkGponProfile2BridgeGemControlStatus OBJECT-TYPE
                        SYNTAX FkControlStatusType
                        MAX-ACCESS read-only
                        STATUS current
                        DESCRIPTION
                                "The status of user command"
                        ::= { fkGponProfile2BridgeGemControl 2 }

                
                -- 1.3.6.1.4.1.10428 9 1.101.23.51.21.2.3
                fkGponProfile2BridgeGemControlTimer OBJECT-TYPE
                        SYNTAX Gauge32
                        MAX-ACCESS read-write
                        STATUS current
                        DESCRIPTION
                                "The maximum time for the manager for a long running user command"
                        ::= { fkGponProfile2BridgeGemControl 3 }

                
                -- 1.3.6.1.4.1.10428 9 1.101.23.51.21.2.4
                fkGponProfile2BridgeGemControlTimeStamp OBJECT-TYPE
                        SYNTAX TimeTicks
                        MAX-ACCESS read-only
                        STATUS current
                        DESCRIPTION
                                "The time stamp of the last command(end of command)"
                        ::= { fkGponProfile2BridgeGemControl 4 }

                
                -- 1.3.6.1.4.1.10428 9 1.101.23.51.21.2.5
                fkGponProfile2BridgeGemControlReqResult OBJECT-TYPE
                        SYNTAX FkControlRequestResultType
                        MAX-ACCESS read-only
                        STATUS current
                        DESCRIPTION
                                "The result of the last user command"
                        ::= { fkGponProfile2BridgeGemControl 5 }

                
                -- 1.3.6.1.4.1.10428 9 1.101.23.51.21.2.6
                fkGponProfile2BridgeGemControlTName OBJECT-TYPE
                        SYNTAX OCTET STRING
                        MAX-ACCESS read-write
                        STATUS current
                        DESCRIPTION
                                "The Traffic profile name."
                        ::= { fkGponProfile2BridgeGemControl 6 }
-- The ONU profile name.
                
                -- 1.3.6.1.4.1.10428 9 1.101.23.51.21.2.7
                fkGponProfile2BridgeGemControlBridgeId OBJECT-TYPE
                        SYNTAX INTEGER (1..65535)
                        MAX-ACCESS read-write
                        STATUS current
                        DESCRIPTION
                                "The Bridge ID."
                        ::= { fkGponProfile2BridgeGemControl 7 }

                
                -- 1.3.6.1.4.1.10428 9 1.101.23.51.21.2.8
                fkGponProfile2BridgeGemControlId OBJECT-TYPE
                        SYNTAX INTEGER (1..65535)
                        MAX-ACCESS read-write
                        STATUS current
                        DESCRIPTION
                                "The Gem ID"
                        ::= { fkGponProfile2BridgeGemControl 8 }

                
                -- 1.3.6.1.4.1.10428 9 1.101.23.51.21.2.9
                fkGponProfile2BridgeGemControlVlanFilterMode OBJECT-TYPE
                        SYNTAX INTEGER
                                {
                                unUsed(0),
                                allow(1),
                                derny(2)
                                }
                        MAX-ACCESS read-write
                        STATUS current
                        DESCRIPTION
                                "Allow or deny that untagged fowarding operation"
                        ::= { fkGponProfile2BridgeGemControl 9 }

                
                -- 1.3.6.1.4.1.10428 9 1.101.23.51.21.2.10
                fkGponProfile2BridgeGemControlVlanFilter OBJECT-TYPE
                        SYNTAX INTEGER (1..65535)
                        MAX-ACCESS read-write
                        STATUS current
                        DESCRIPTION
                                "The VLAN Tagging Filter Data"
                        ::= { fkGponProfile2BridgeGemControl 10 }

                
                -- 1.3.6.1.4.1.10428 9 1.101.23.51.21.3
                fkGponProfile2BridgeGemNotification OBJECT IDENTIFIER ::= { fkGponProfile2BridgeGem 3 }

                
                -- 1.3.6.1.4.1.10428 9 1.101.23.51.21.3.1
                fkGponProfile2BridgeGemBridgeGemCreated NOTIFICATION-TYPE
                        OBJECTS { fkGponProfile2BridgeGemControlRequest, fkGponProfile2BridgeGemControlTimeStamp, fkGponProfile2BridgeGemControlReqResult, fkGponProfile2BridgeGemControlTName, fkGponProfile2BridgeGemControlBridgeId, 
                                fkGponProfile2BridgeGemControlId }
                        STATUS current
                        DESCRIPTION 
                                "Description."
                        ::= { fkGponProfile2BridgeGemNotification 1 }

                
                -- 1.3.6.1.4.1.10428 9 1.101.23.51.21.3.2
                fkGponProfile2BridgeGemBridgeGemDeleted NOTIFICATION-TYPE
                        OBJECTS { fkGponProfile2BridgeGemControlRequest, fkGponProfile2BridgeGemControlTimeStamp, fkGponProfile2BridgeGemControlReqResult, fkGponProfile2BridgeGemControlTName, fkGponProfile2BridgeGemControlBridgeId, 
                                fkGponProfile2BridgeGemControlId }
                        STATUS current
                        DESCRIPTION 
                                "Description."
                        ::= { fkGponProfile2BridgeGemNotification 2 }

                
                -- 1.3.6.1.4.1.10428 9 1.101.23.51.21.3.3
                fkGponProfile2BridgeGemVlanFilterChanged NOTIFICATION-TYPE
                        OBJECTS { fkGponProfile2BridgeGemControlRequest, fkGponProfile2BridgeGemControlTimeStamp, fkGponProfile2BridgeGemControlReqResult, fkGponProfile2BridgeGemControlBridgeId, fkGponProfile2BridgeGemControlId, 
                                fkGponProfile2BridgeGemControlVlanFilterMode, fkGponProfile2BridgeGemControlVlanFilter }
                        STATUS current
                        DESCRIPTION 
                                "Description."
                        ::= { fkGponProfile2BridgeGemNotification 3 }

                
                -- 1.3.6.1.4.1.10428 9 1.101.23.51.22
                fkGponProfile2BridgeTdm OBJECT IDENTIFIER ::= { fkGponProfile2 22 }

                
                -- 1.3.6.1.4.1.10428 9 1.101.23.51.22.1
                fkGponProfile2BridgeTdmTable OBJECT-TYPE
                        SYNTAX SEQUENCE OF FkGponProfile2BridgeTdmEntry
                        MAX-ACCESS not-accessible
                        STATUS current
                        DESCRIPTION
                                "fkGponProfile2BridgeTdmTable"
                        ::= { fkGponProfile2BridgeTdm 1 }

                
                -- 1.3.6.1.4.1.10428 9 1.101.23.51.22.1.1
                fkGponProfile2BridgeTdmEntry OBJECT-TYPE
                        SYNTAX FkGponProfile2BridgeTdmEntry
                        MAX-ACCESS not-accessible
                        STATUS current
                        DESCRIPTION
                                "key: fkGponProfile2TrafficIndex, fkGponProfile2BridgeId, fkGponProfile2BridgeTdmId"
                        INDEX { fkGponProfile2TrafficIndex, fkGponProfile2BridgeId, fkGponProfile2BridgeTdmId }
                        ::= { fkGponProfile2BridgeTdmTable 1 }

                
                FkGponProfile2BridgeTdmEntry ::=
                        SEQUENCE { 
                                fkGponProfile2BridgeTdmId
                                        INTEGER
                         }

                -- 1.3.6.1.4.1.10428 9 1.101.23.51.22.1.1.1
                fkGponProfile2BridgeTdmId OBJECT-TYPE
                        SYNTAX INTEGER (1..65535)
                        MAX-ACCESS read-only
                        STATUS current
                        DESCRIPTION
                                "The TDM Service link."
                        ::= { fkGponProfile2BridgeTdmEntry 1 }

                
                -- 1.3.6.1.4.1.10428 9 1.101.23.51.22.2
                fkGponProfile2BridgeTdmControl OBJECT IDENTIFIER ::= { fkGponProfile2BridgeTdm 2 }

                
                -- 1.3.6.1.4.1.10428 9 1.101.23.51.22.2.1
                fkGponProfile2BridgeTdmControlRequest OBJECT-TYPE
                        SYNTAX INTEGER
                                {
                                addBridgeTdm(1),
                                delBridgeTdm(2)
                                }
                        MAX-ACCESS read-write
                        STATUS current
                        DESCRIPTION
                                "The request of a user command"
                        ::= { fkGponProfile2BridgeTdmControl 1 }

                
                -- 1.3.6.1.4.1.10428 9 1.101.23.51.22.2.2
                fkGponProfile2BridgeTdmControlStatus OBJECT-TYPE
                        SYNTAX FkControlStatusType
                        MAX-ACCESS read-only
                        STATUS current
                        DESCRIPTION
                                "The status of user command"
                        ::= { fkGponProfile2BridgeTdmControl 2 }

                
                -- 1.3.6.1.4.1.10428 9 1.101.23.51.22.2.3
                fkGponProfile2BridgeTdmControlTimer OBJECT-TYPE
                        SYNTAX Gauge32
                        MAX-ACCESS read-write
                        STATUS current
                        DESCRIPTION
                                "The maximum time for the manager for a long running user command"
                        ::= { fkGponProfile2BridgeTdmControl 3 }

                
                -- 1.3.6.1.4.1.10428 9 1.101.23.51.22.2.4
                fkGponProfile2BridgeTdmControlTimeStamp OBJECT-TYPE
                        SYNTAX TimeTicks
                        MAX-ACCESS read-only
                        STATUS current
                        DESCRIPTION
                                "The time stamp of the last command(end of command)"
                        ::= { fkGponProfile2BridgeTdmControl 4 }

                
                -- 1.3.6.1.4.1.10428 9 1.101.23.51.22.2.5
                fkGponProfile2BridgeTdmControlReqResult OBJECT-TYPE
                        SYNTAX FkControlRequestResultType
                        MAX-ACCESS read-only
                        STATUS current
                        DESCRIPTION
                                "The result of the last user command"
                        ::= { fkGponProfile2BridgeTdmControl 5 }

                
                -- 1.3.6.1.4.1.10428 9 1.101.23.51.22.2.6
                fkGponProfile2BridgeTdmControlTName OBJECT-TYPE
                        SYNTAX OCTET STRING
                        MAX-ACCESS read-write
                        STATUS current
                        DESCRIPTION
                                "The Traffic profile name."
                        ::= { fkGponProfile2BridgeTdmControl 6 }
-- The ONU profile name.
                
                -- 1.3.6.1.4.1.10428 9 1.101.23.51.22.2.7
                fkGponProfile2BridgeTdmControlBridgeId OBJECT-TYPE
                        SYNTAX INTEGER (1..65535)
                        MAX-ACCESS read-write
                        STATUS current
                        DESCRIPTION
                                "The Bridge ID."
                        ::= { fkGponProfile2BridgeTdmControl 7 }

                
                -- 1.3.6.1.4.1.10428 9 1.101.23.51.22.2.8
                fkGponProfile2BridgeTdmControlId OBJECT-TYPE
                        SYNTAX INTEGER (1..65535)
                        MAX-ACCESS read-write
                        STATUS current
                        DESCRIPTION
                                "The TDM Service link."
                        ::= { fkGponProfile2BridgeTdmControl 8 }

                
                -- 1.3.6.1.4.1.10428 9 1.101.23.51.22.3
                fkGponProfile2BridgeTdmNotification OBJECT IDENTIFIER ::= { fkGponProfile2BridgeTdm 3 }

                
                -- 1.3.6.1.4.1.10428 9 1.101.23.51.22.3.1
                fkGponProfile2BridgeTdmBridgeTdmCreated NOTIFICATION-TYPE
                        OBJECTS { fkGponProfile2BridgeTdmControlTName, fkGponProfile2BridgeTdmControlBridgeId, fkGponProfile2BridgeTdmControlId, fkGponProfile2BridgeTdmControlRequest, fkGponProfile2BridgeTdmControlTimeStamp, 
                                fkGponProfile2BridgeTdmControlReqResult }
                        STATUS current
                        DESCRIPTION 
                                "Description."
                        ::= { fkGponProfile2BridgeTdmNotification 1 }

                
                -- 1.3.6.1.4.1.10428 9 1.101.23.51.22.3.2
                fkGponProfile2BridgeTdmBridgeTdmDeleted NOTIFICATION-TYPE
                        OBJECTS { fkGponProfile2BridgeTdmControlTName, fkGponProfile2BridgeTdmControlBridgeId, fkGponProfile2BridgeTdmControlId, fkGponProfile2BridgeTdmControlRequest, fkGponProfile2BridgeTdmControlTimeStamp, 
                                fkGponProfile2BridgeTdmControlReqResult }
                        STATUS current
                        DESCRIPTION 
                                "Description."
                        ::= { fkGponProfile2BridgeTdmNotification 2 }

                
                -- 1.3.6.1.4.1.10428 9 1.101.23.51.23
                fkGponProfile2BridgeIpHost OBJECT IDENTIFIER ::= { fkGponProfile2 23 }

                
                -- 1.3.6.1.4.1.10428 9 1.101.23.51.23.1
                fkGponProfile2BridgeIpHostTable OBJECT-TYPE
                        SYNTAX SEQUENCE OF FkGponProfile2BridgeIpHostEntry
                        MAX-ACCESS not-accessible
                        STATUS current
                        DESCRIPTION
                                "fkGponProfile2BridgeIpHostTable"
                        ::= { fkGponProfile2BridgeIpHost 1 }

                
                -- 1.3.6.1.4.1.10428 9 1.101.23.51.23.1.1
                fkGponProfile2BridgeIpHostEntry OBJECT-TYPE
                        SYNTAX FkGponProfile2BridgeIpHostEntry
                        MAX-ACCESS not-accessible
                        STATUS current
                        DESCRIPTION
                                "key: fkGponProfile2TrafficIndex, fkGponProfile2BridgeId, fkGponProfile2BridgeIpHostId"
                        INDEX { fkGponProfile2TrafficIndex, fkGponProfile2BridgeId, fkGponProfile2BridgeIpHostId }
                        ::= { fkGponProfile2BridgeIpHostTable 1 }

                
                FkGponProfile2BridgeIpHostEntry ::=
                        SEQUENCE { 
                                fkGponProfile2BridgeIpHostId
                                        INTEGER
                         }

                -- 1.3.6.1.4.1.10428 9 1.101.23.51.23.1.1.1
                fkGponProfile2BridgeIpHostId OBJECT-TYPE
                        SYNTAX INTEGER (1..65535)
                        MAX-ACCESS read-only
                        STATUS current
                        DESCRIPTION
                                "The Host ID"
                        ::= { fkGponProfile2BridgeIpHostEntry 1 }

                
                -- 1.3.6.1.4.1.10428 9 1.101.23.51.23.2
                fkGponProfile2BridgeIpHostControl OBJECT IDENTIFIER ::= { fkGponProfile2BridgeIpHost 2 }

                
                -- 1.3.6.1.4.1.10428 9 1.101.23.51.23.2.1
                fkGponProfile2BridgeIpHostControlRequest OBJECT-TYPE
                        SYNTAX INTEGER
                                {
                                addBridgeIpHost(1),
                                delBridgeIpHost(2)
                                }
                        MAX-ACCESS read-write
                        STATUS current
                        DESCRIPTION
                                "The request of a user command"
                        ::= { fkGponProfile2BridgeIpHostControl 1 }

                
                -- 1.3.6.1.4.1.10428 9 1.101.23.51.23.2.2
                fkGponProfile2BridgeIpHostControlStatus OBJECT-TYPE
                        SYNTAX FkControlStatusType
                        MAX-ACCESS read-only
                        STATUS current
                        DESCRIPTION
                                "The status of user command"
                        ::= { fkGponProfile2BridgeIpHostControl 2 }

                
                -- 1.3.6.1.4.1.10428 9 1.101.23.51.23.2.3
                fkGponProfile2BridgeIpHostControlTimer OBJECT-TYPE
                        SYNTAX Gauge32
                        MAX-ACCESS read-write
                        STATUS current
                        DESCRIPTION
                                "The maximum time for the manager for a long running user command"
                        ::= { fkGponProfile2BridgeIpHostControl 3 }

                
                -- 1.3.6.1.4.1.10428 9 1.101.23.51.23.2.4
                fkGponProfile2BridgeIpHostControlTimeStamp OBJECT-TYPE
                        SYNTAX TimeTicks
                        MAX-ACCESS read-only
                        STATUS current
                        DESCRIPTION
                                "The time stamp of the last command(end of command)"
                        ::= { fkGponProfile2BridgeIpHostControl 4 }

                
                -- 1.3.6.1.4.1.10428 9 1.101.23.51.23.2.5
                fkGponProfile2BridgeIpHostControlReqResult OBJECT-TYPE
                        SYNTAX FkControlRequestResultType
                        MAX-ACCESS read-only
                        STATUS current
                        DESCRIPTION
                                "The result of the last user command"
                        ::= { fkGponProfile2BridgeIpHostControl 5 }

                
                -- 1.3.6.1.4.1.10428 9 1.101.23.51.23.2.6
                fkGponProfile2BridgeIpHostControlTName OBJECT-TYPE
                        SYNTAX OCTET STRING
                        MAX-ACCESS read-write
                        STATUS current
                        DESCRIPTION
                                "The Traffic profile name."
                        ::= { fkGponProfile2BridgeIpHostControl 6 }
-- The ONU profile name.
                
                -- 1.3.6.1.4.1.10428 9 1.101.23.51.23.2.7
                fkGponProfile2BridgeIpHostControlBridgeId OBJECT-TYPE
                        SYNTAX INTEGER (1..65535)
                        MAX-ACCESS read-write
                        STATUS current
                        DESCRIPTION
                                "The Bridge ID."
                        ::= { fkGponProfile2BridgeIpHostControl 7 }

                
                -- 1.3.6.1.4.1.10428 9 1.101.23.51.23.2.8
                fkGponProfile2BridgeIpHostControlId OBJECT-TYPE
                        SYNTAX INTEGER (1..65535)
                        MAX-ACCESS read-write
                        STATUS current
                        DESCRIPTION
                                "The Host ID"
                        ::= { fkGponProfile2BridgeIpHostControl 8 }

                
                -- 1.3.6.1.4.1.10428 9 1.101.23.51.23.3
                fkGponProfile2BridgeIpHostNotification OBJECT IDENTIFIER ::= { fkGponProfile2BridgeIpHost 3 }

                
                -- 1.3.6.1.4.1.10428 9 1.101.23.51.23.3.1
                fkGponProfile2BridgeIpHostBridgeIpHostCreated NOTIFICATION-TYPE
                        OBJECTS { fkGponProfile2BridgeIpHostControlRequest, fkGponProfile2BridgeIpHostControlTimeStamp, fkGponProfile2BridgeIpHostControlReqResult, fkGponProfile2BridgeIpHostControlTName, fkGponProfile2BridgeIpHostControlBridgeId, 
                                fkGponProfile2BridgeIpHostControlId }
                        STATUS current
                        DESCRIPTION 
                                "Description."
                        ::= { fkGponProfile2BridgeIpHostNotification 1 }

                
                -- 1.3.6.1.4.1.10428 9 1.101.23.51.23.3.2
                fkGponProfile2BridgeIpHostBridgeIpHostDeleted NOTIFICATION-TYPE
                        OBJECTS { fkGponProfile2BridgeIpHostControlRequest, fkGponProfile2BridgeIpHostControlTimeStamp, fkGponProfile2BridgeIpHostControlReqResult, fkGponProfile2BridgeIpHostControlTName, fkGponProfile2BridgeIpHostControlBridgeId, 
                                fkGponProfile2BridgeIpHostControlId }
                        STATUS current
                        DESCRIPTION 
                                "Description."
                        ::= { fkGponProfile2BridgeIpHostNotification 2 }

                
                -- 1.3.6.1.4.1.10428 9 1.101.23.51.24
                fkGponProfile2ExtVlan OBJECT IDENTIFIER ::= { fkGponProfile2 24 }

                
                -- 1.3.6.1.4.1.10428 9 1.101.23.51.24.1
                fkGponProfile2ExtVlanBasic OBJECT IDENTIFIER ::= { fkGponProfile2ExtVlan 1 }

                
                -- 1.3.6.1.4.1.10428 9 1.101.23.51.24.1.1
                fkGponProfile2ExtVlanTable OBJECT-TYPE
                        SYNTAX SEQUENCE OF FkGponProfile2ExtVlanEntry
                        MAX-ACCESS not-accessible
                        STATUS current
                        DESCRIPTION
                                "Description."
                        ::= { fkGponProfile2ExtVlanBasic 1 }

                
                -- 1.3.6.1.4.1.10428 9 1.101.23.51.24.1.1.1
                fkGponProfile2ExtVlanEntry OBJECT-TYPE
                        SYNTAX FkGponProfile2ExtVlanEntry
                        MAX-ACCESS not-accessible
                        STATUS current
                        DESCRIPTION
                                "Description."
                        INDEX { fkGponProfile2ExtVlanIndex }
                        ::= { fkGponProfile2ExtVlanTable 1 }

                
                FkGponProfile2ExtVlanEntry ::=
                        SEQUENCE { 
                                fkGponProfile2ExtVlanIndex
                                        INTEGER,
                                fkGponProfile2ExtVlanName
                                        OCTET STRING,
                                fkGponProfile2ExtVlanDownStreamMode
                                        INTEGER,
                                fkGponProfile2ExtVlanDscpToCosMapTable
                                        OCTET STRING,
                                fkGponProfile2ExtVlanTpidInput
                                        INTEGER,
                                fkGponProfile2ExtVlanTpidOutput
                                        INTEGER
                         }

                -- 1.3.6.1.4.1.10428 9 1.101.23.51.24.1.1.1.1
                fkGponProfile2ExtVlanIndex OBJECT-TYPE
                        SYNTAX INTEGER (1..65535)
                        MAX-ACCESS read-only
                        STATUS current
                        DESCRIPTION
                                "Description."
                        ::= { fkGponProfile2ExtVlanEntry 1 }

                
                -- 1.3.6.1.4.1.10428 9 1.101.23.51.24.1.1.1.2
                fkGponProfile2ExtVlanName OBJECT-TYPE
                        SYNTAX OCTET STRING
                        MAX-ACCESS read-only
                        STATUS current
                        DESCRIPTION
                                "Description."
                        ::= { fkGponProfile2ExtVlanEntry 2 }

                
                -- 1.3.6.1.4.1.10428 9 1.101.23.51.24.1.1.1.3
                fkGponProfile2ExtVlanDownStreamMode OBJECT-TYPE
                        SYNTAX INTEGER
                                {
                                enable(0),
                                disable(1)
                                }
                        MAX-ACCESS read-write
                        STATUS current
                        DESCRIPTION
                                "Description."
                        ::= { fkGponProfile2ExtVlanEntry 3 }

                
                -- 1.3.6.1.4.1.10428 9 1.101.23.51.24.1.1.1.4
                fkGponProfile2ExtVlanDscpToCosMapTable OBJECT-TYPE
                        SYNTAX OCTET STRING
                        MAX-ACCESS read-only
                        STATUS current
                        DESCRIPTION
                                "Description."
                        ::= { fkGponProfile2ExtVlanEntry 4 }

                
                -- 1.3.6.1.4.1.10428 9 1.101.23.51.24.1.1.1.5
                fkGponProfile2ExtVlanTpidInput OBJECT-TYPE
                        SYNTAX INTEGER (1..65535)
                        MAX-ACCESS read-only
                        STATUS current
                        DESCRIPTION
                                "Description."
                        ::= { fkGponProfile2ExtVlanEntry 5 }

                
                -- 1.3.6.1.4.1.10428 9 1.101.23.51.24.1.1.1.6
                fkGponProfile2ExtVlanTpidOutput OBJECT-TYPE
                        SYNTAX INTEGER (1..65535)
                        MAX-ACCESS read-only
                        STATUS current
                        DESCRIPTION
                                "Description."
                        ::= { fkGponProfile2ExtVlanEntry 6 }

                
                -- 1.3.6.1.4.1.10428 9 1.101.23.51.24.1.2
                fkGponProfile2ExtVlanControl OBJECT IDENTIFIER ::= { fkGponProfile2ExtVlanBasic 2 }

                
                -- 1.3.6.1.4.1.10428 9 1.101.23.51.24.1.2.1
                fkGponProfile2ExtVlanControlRequest OBJECT-TYPE
                        SYNTAX INTEGER
                                {
                                addExtendedVlanProfile(1),
                                delExtendedVlanProfile(2),
                                setDownstreamMode(3),
                                setDscpToCosMapTable(4),
                                setTpid(5)
                                }
                        MAX-ACCESS read-write
                        STATUS current
                        DESCRIPTION
                                "The request of a user command"
                        ::= { fkGponProfile2ExtVlanControl 1 }

                
                -- 1.3.6.1.4.1.10428 9 1.101.23.51.24.1.2.2
                fkGponProfile2ExtVlanControlStatus OBJECT-TYPE
                        SYNTAX FkControlStatusType
                        MAX-ACCESS read-only
                        STATUS current
                        DESCRIPTION
                                "The status of user command"
                        ::= { fkGponProfile2ExtVlanControl 2 }

                
                -- 1.3.6.1.4.1.10428 9 1.101.23.51.24.1.2.3
                fkGponProfile2ExtVlanControlTimer OBJECT-TYPE
                        SYNTAX Gauge32
                        MAX-ACCESS read-write
                        STATUS current
                        DESCRIPTION
                                "The maximum time for the manager for a long running user command"
                        ::= { fkGponProfile2ExtVlanControl 3 }

                
                -- 1.3.6.1.4.1.10428 9 1.101.23.51.24.1.2.4
                fkGponProfile2ExtVlanControlTimeStamp OBJECT-TYPE
                        SYNTAX TimeTicks
                        MAX-ACCESS read-only
                        STATUS current
                        DESCRIPTION
                                "The time stamp of the last command(end of command)"
                        ::= { fkGponProfile2ExtVlanControl 4 }

                
                -- 1.3.6.1.4.1.10428 9 1.101.23.51.24.1.2.5
                fkGponProfile2ExtVlanControlReqResult OBJECT-TYPE
                        SYNTAX FkControlRequestResultType
                        MAX-ACCESS read-only
                        STATUS current
                        DESCRIPTION
                                "The result of the last user command"
                        ::= { fkGponProfile2ExtVlanControl 5 }

                
                -- 1.3.6.1.4.1.10428 9 1.101.23.51.24.1.2.6
                fkGponProfile2ExtVlanControlName OBJECT-TYPE
                        SYNTAX OCTET STRING
                        MAX-ACCESS read-write
                        STATUS current
                        DESCRIPTION
                                "Description."
                        ::= { fkGponProfile2ExtVlanControl 6 }

                
                -- 1.3.6.1.4.1.10428 9 1.101.23.51.24.1.2.7
                fkGponProfile2ExtVlanControlDownStreamMode OBJECT-TYPE
                        SYNTAX INTEGER
                                {
                                enable(0),
                                disable(1)
                                }
                        MAX-ACCESS read-write
                        STATUS current
                        DESCRIPTION
                                "Description."
                        ::= { fkGponProfile2ExtVlanControl 7 }

                
                -- 1.3.6.1.4.1.10428 9 1.101.23.51.24.1.2.8
                fkGponProfile2ExtVlanControlDscpToCosMapTable OBJECT-TYPE
                        SYNTAX OCTET STRING
                        MAX-ACCESS read-write
                        STATUS current
                        DESCRIPTION
                                "Description."
                        ::= { fkGponProfile2ExtVlanControl 8 }

                
                -- 1.3.6.1.4.1.10428 9 1.101.23.51.24.1.2.9
                fkGponProfile2ExtVlanControlTpidInput OBJECT-TYPE
                        SYNTAX INTEGER (1..65535)
                        MAX-ACCESS read-write
                        STATUS current
                        DESCRIPTION
                                "Description."
                        ::= { fkGponProfile2ExtVlanControl 9 }

                
                -- 1.3.6.1.4.1.10428 9 1.101.23.51.24.1.2.10
                fkGponProfile2ExtVlanControlTpidOutput OBJECT-TYPE
                        SYNTAX INTEGER (1..65535)
                        MAX-ACCESS read-write
                        STATUS current
                        DESCRIPTION
                                "Description."
                        ::= { fkGponProfile2ExtVlanControl 10 }

                
                -- 1.3.6.1.4.1.10428 9 1.101.23.51.24.1.3
                fkGponProfile2ExtVlanNotification OBJECT IDENTIFIER ::= { fkGponProfile2ExtVlanBasic 3 }

                
                -- 1.3.6.1.4.1.10428 9 1.101.23.51.24.1.3.1
                fkGponProfile2ExtVlanProfileAdded NOTIFICATION-TYPE
                        OBJECTS { fkGponProfile2ExtVlanControlRequest, fkGponProfile2ExtVlanControlTimeStamp, fkGponProfile2ExtVlanControlReqResult, fkGponProfile2ExtVlanControlName }
                        STATUS current
                        DESCRIPTION 
                                "Description."
                        ::= { fkGponProfile2ExtVlanNotification 1 }

                
                -- 1.3.6.1.4.1.10428 9 1.101.23.51.24.1.3.2
                fkGponProfile2ExtVlanProfileDeleted NOTIFICATION-TYPE
                        OBJECTS { fkGponProfile2ExtVlanControlRequest, fkGponProfile2ExtVlanControlTimeStamp, fkGponProfile2ExtVlanControlReqResult, fkGponProfile2ExtVlanControlName }
                        STATUS current
                        DESCRIPTION 
                                "Description."
                        ::= { fkGponProfile2ExtVlanNotification 2 }

                
                -- 1.3.6.1.4.1.10428 9 1.101.23.51.24.1.3.3
                fkGponProfile2ExtVlanDownStreamModeChanged NOTIFICATION-TYPE
                        OBJECTS { fkGponProfile2ExtVlanControlRequest, fkGponProfile2ExtVlanControlTimeStamp, fkGponProfile2ExtVlanControlReqResult, fkGponProfile2ExtVlanControlName, fkGponProfile2ExtVlanControlDownStreamMode
                                 }
                        STATUS current
                        DESCRIPTION 
                                "Description."
                        ::= { fkGponProfile2ExtVlanNotification 3 }

                
                -- 1.3.6.1.4.1.10428 9 1.101.23.51.24.1.3.4
                fkGponProfile2ExtVlanDscpToCosMapTableChanged NOTIFICATION-TYPE
                        OBJECTS { fkGponProfile2ExtVlanControlRequest, fkGponProfile2ExtVlanControlTimeStamp, fkGponProfile2ExtVlanControlReqResult, fkGponProfile2ExtVlanControlName, fkGponProfile2ExtVlanControlDscpToCosMapTable
                                 }
                        STATUS current
                        DESCRIPTION 
                                "Description."
                        ::= { fkGponProfile2ExtVlanNotification 4 }

                
                -- 1.3.6.1.4.1.10428 9 1.101.23.51.24.1.3.5
                fkGponProfile2ExtVlanTpidChanged NOTIFICATION-TYPE
                        OBJECTS { fkGponProfile2ExtVlanControlRequest, fkGponProfile2ExtVlanControlTimeStamp, fkGponProfile2ExtVlanControlReqResult, fkGponProfile2ExtVlanControlName, fkGponProfile2ExtVlanControlTpidInput, 
                                fkGponProfile2ExtVlanControlTpidOutput }
                        STATUS current
                        DESCRIPTION 
                                "Description."
                        ::= { fkGponProfile2ExtVlanNotification 5 }

                
                -- 1.3.6.1.4.1.10428 9 1.101.23.51.24.2
                fkGponProfile2ExtVlanTag OBJECT IDENTIFIER ::= { fkGponProfile2ExtVlan 2 }

                
                -- 1.3.6.1.4.1.10428 9 1.101.23.51.24.2.1
                fkGponProfile2ExtVlanTagTable OBJECT-TYPE
                        SYNTAX SEQUENCE OF FkGponProfile2ExtVlanTagEntry
                        MAX-ACCESS not-accessible
                        STATUS current
                        DESCRIPTION
                                "Description."
                        ::= { fkGponProfile2ExtVlanTag 1 }

                
                -- 1.3.6.1.4.1.10428 9 1.101.23.51.24.2.1.1
                fkGponProfile2ExtVlanTagEntry OBJECT-TYPE
                        SYNTAX FkGponProfile2ExtVlanTagEntry
                        MAX-ACCESS not-accessible
                        STATUS current
                        DESCRIPTION
                                "Description."
                        INDEX { fkGponProfile2ExtVlanIndex, fkGponProfile2ExtVlanTagType, fkGponProfile2ExtVlanTagIndex }
                        ::= { fkGponProfile2ExtVlanTagTable 1 }

                
                FkGponProfile2ExtVlanTagEntry ::=
                        SEQUENCE { 
                                fkGponProfile2ExtVlanTagType
                                        INTEGER,
                                fkGponProfile2ExtVlanTagIndex
                                        INTEGER,
                                fkGponProfile2ExtVlanTagTreatTag
                                        INTEGER,
                                fkGponProfile2ExtVlanTagTreatInnerCopyVid
                                        INTEGER,
                                fkGponProfile2ExtVlanTagTreatInnerCopyCos
                                        INTEGER,
                                fkGponProfile2ExtVlanTagTreatInnerTpidDei
                                        INTEGER,
                                fkGponProfile2ExtVlanTagTreatOuterCopyVid
                                        INTEGER,
                                fkGponProfile2ExtVlanTagTreatOuterCopyCos
                                        INTEGER,
                                fkGponProfile2ExtVlanTagTreatOuterTpidDei
                                        INTEGER,
                                fkGponProfile2ExtVlanTagFilterEtherType
                                        INTEGER,
                                fkGponProfile2ExtVlanTagFilterInnerVid
                                        INTEGER,
                                fkGponProfile2ExtVlanTagFilterInnerCos
                                        INTEGER,
                                fkGponProfile2ExtVlanTagFilterInnerTpidDei
                                        INTEGER,
                                fkGponProfile2ExtVlanTagFilterOuterVid
                                        INTEGER,
                                fkGponProfile2ExtVlanTagFilterOuterCos
                                        INTEGER,
                                fkGponProfile2ExtVlanTagFilterOuterTpidDei
                                        INTEGER
                         }

                -- 1.3.6.1.4.1.10428 9 1.101.23.51.24.2.1.1.1
                fkGponProfile2ExtVlanTagType OBJECT-TYPE
                        SYNTAX INTEGER
                                {
                                unTaggedFrame(1),
                                singleTaggedFrame(2),
                                doubleTaggedFrame(3)
                                }
                        MAX-ACCESS read-only
                        STATUS current
                        DESCRIPTION
                                "Description."
                        ::= { fkGponProfile2ExtVlanTagEntry 1 }

                
                -- 1.3.6.1.4.1.10428 9 1.101.23.51.24.2.1.1.2
                fkGponProfile2ExtVlanTagIndex OBJECT-TYPE
                        SYNTAX INTEGER (1..65535)
                        MAX-ACCESS read-only
                        STATUS current
                        DESCRIPTION
                                "Description."
                        ::= { fkGponProfile2ExtVlanTagEntry 2 }

                
                -- 1.3.6.1.4.1.10428 9 1.101.23.51.24.2.1.1.3
                fkGponProfile2ExtVlanTagTreatTag OBJECT-TYPE
                        SYNTAX INTEGER
                                {
                                notRemove(0),
                                remove(1),
                                both(2),
                                notMatchDiscardInDs(3)
                                }
                        MAX-ACCESS read-only
                        STATUS current
                        DESCRIPTION
                                "Description."
                        ::= { fkGponProfile2ExtVlanTagEntry 3 }

                
                -- 1.3.6.1.4.1.10428 9 1.101.23.51.24.2.1.1.4
                fkGponProfile2ExtVlanTagTreatInnerCopyVid OBJECT-TYPE
                        SYNTAX INTEGER (0..4094 | 4096 | 4097)
                        MAX-ACCESS read-only
                        STATUS current
                        DESCRIPTION
                                "Description."
                        ::= { fkGponProfile2ExtVlanTagEntry 4 }

                
                -- 1.3.6.1.4.1.10428 9 1.101.23.51.24.2.1.1.5
                fkGponProfile2ExtVlanTagTreatInnerCopyCos OBJECT-TYPE
                        SYNTAX INTEGER (0..7 | 8 | 9 | 10 | 15)
                        MAX-ACCESS read-only
                        STATUS current
                        DESCRIPTION
                                "Description."
                        ::= { fkGponProfile2ExtVlanTagEntry 5 }

                
                -- 1.3.6.1.4.1.10428 9 1.101.23.51.24.2.1.1.6
                fkGponProfile2ExtVlanTagTreatInnerTpidDei OBJECT-TYPE
                        SYNTAX INTEGER
                                {
                                tpidCopyInner(0),
                                tpidCopyOuter(1),
                                tpidOutputDeiCopyInner(2),
                                tpidOutputDeiOuter(3),
                                tpid0x8100(4),
                                tpidReserved(5),
                                tpidOutputDei0(6),
                                tpidOutputDei1(7)
                                }
                        MAX-ACCESS read-only
                        STATUS current
                        DESCRIPTION
                                "Description."
                        ::= { fkGponProfile2ExtVlanTagEntry 6 }

                
                -- 1.3.6.1.4.1.10428 9 1.101.23.51.24.2.1.1.7
                fkGponProfile2ExtVlanTagTreatOuterCopyVid OBJECT-TYPE
                        SYNTAX INTEGER (0..4094 | 4096 | 4097)
                        MAX-ACCESS read-only
                        STATUS current
                        DESCRIPTION
                                "Description."
                        ::= { fkGponProfile2ExtVlanTagEntry 7 }

                
                -- 1.3.6.1.4.1.10428 9 1.101.23.51.24.2.1.1.8
                fkGponProfile2ExtVlanTagTreatOuterCopyCos OBJECT-TYPE
                        SYNTAX INTEGER (0..7 | 8 | 9 | 10 | 15)
                        MAX-ACCESS read-only
                        STATUS current
                        DESCRIPTION
                                "Description."
                        ::= { fkGponProfile2ExtVlanTagEntry 8 }

                
                -- 1.3.6.1.4.1.10428 9 1.101.23.51.24.2.1.1.9
                fkGponProfile2ExtVlanTagTreatOuterTpidDei OBJECT-TYPE
                        SYNTAX INTEGER
                                {
                                tpidCopyInner(0),
                                tpidCopyOuter(1),
                                tpidOutputDeiCopyInner(2),
                                tpidOutputDeiOuter(3),
                                tpid0x8100(4),
                                tpidReserved(5),
                                tpidOutputDei0(6),
                                tpidOutputDei1(7)
                                }
                        MAX-ACCESS read-only
                        STATUS current
                        DESCRIPTION
                                "Description."
                        ::= { fkGponProfile2ExtVlanTagEntry 9 }

                
                -- 1.3.6.1.4.1.10428 9 1.101.23.51.24.2.1.1.10
                fkGponProfile2ExtVlanTagFilterEtherType OBJECT-TYPE
                        SYNTAX INTEGER
                                {
                                unused(0),
                                ipoe(1),
                                pppoe(2),
                                arp(3),
                                ipv6Ipoe(4)
                                }
                        MAX-ACCESS read-only
                        STATUS current
                        DESCRIPTION
                                "Description."
                        ::= { fkGponProfile2ExtVlanTagEntry 10 }

                
                -- 1.3.6.1.4.1.10428 9 1.101.23.51.24.2.1.1.11
                fkGponProfile2ExtVlanTagFilterInnerVid OBJECT-TYPE
                        SYNTAX INTEGER (0..4094 | 4096)
                        MAX-ACCESS read-only
                        STATUS current
                        DESCRIPTION
                                "Description."
                        ::= { fkGponProfile2ExtVlanTagEntry 11 }

                
                -- 1.3.6.1.4.1.10428 9 1.101.23.51.24.2.1.1.12
                fkGponProfile2ExtVlanTagFilterInnerCos OBJECT-TYPE
                        SYNTAX INTEGER (0..7 | 8)
                        MAX-ACCESS read-only
                        STATUS current
                        DESCRIPTION
                                "Description."
                        ::= { fkGponProfile2ExtVlanTagEntry 12 }

                
                -- 1.3.6.1.4.1.10428 9 1.101.23.51.24.2.1.1.13
                fkGponProfile2ExtVlanTagFilterInnerTpidDei OBJECT-TYPE
                        SYNTAX INTEGER
                                {
                                tpidany(0),
                                tpid0x8100(4),
                                tpidInput(5),
                                tpidInputDei0(6),
                                tpidInputDei1(7)
                                }
                        MAX-ACCESS read-only
                        STATUS current
                        DESCRIPTION
                                "Description."
                        ::= { fkGponProfile2ExtVlanTagEntry 13 }

                
                -- 1.3.6.1.4.1.10428 9 1.101.23.51.24.2.1.1.14
                fkGponProfile2ExtVlanTagFilterOuterVid OBJECT-TYPE
                        SYNTAX INTEGER (0..4094 | 4096)
                        MAX-ACCESS read-only
                        STATUS current
                        DESCRIPTION
                                "Description."
                        ::= { fkGponProfile2ExtVlanTagEntry 14 }

                
                -- 1.3.6.1.4.1.10428 9 1.101.23.51.24.2.1.1.15
                fkGponProfile2ExtVlanTagFilterOuterCos OBJECT-TYPE
                        SYNTAX INTEGER (0..7 | 8)
                        MAX-ACCESS read-only
                        STATUS current
                        DESCRIPTION
                                "Description."
                        ::= { fkGponProfile2ExtVlanTagEntry 15 }

                
                -- 1.3.6.1.4.1.10428 9 1.101.23.51.24.2.1.1.16
                fkGponProfile2ExtVlanTagFilterOuterTpidDei OBJECT-TYPE
                        SYNTAX INTEGER
                                {
                                tpidany(0),
                                tpid0x8100(4),
                                tpidInput(5),
                                tpidInputDei0(6),
                                tpidInputDei1(7)
                                }
                        MAX-ACCESS read-only
                        STATUS current
                        DESCRIPTION
                                "Description."
                        ::= { fkGponProfile2ExtVlanTagEntry 16 }

                
                -- 1.3.6.1.4.1.10428 9 1.101.23.51.24.2.2
                fkGponProfile2ExtVlanTagControl OBJECT IDENTIFIER ::= { fkGponProfile2ExtVlanTag 2 }

                
                -- 1.3.6.1.4.1.10428 9 1.101.23.51.24.2.2.1
                fkGponProfile2ExtVlanTagControlRequest OBJECT-TYPE
                        SYNTAX INTEGER
                                {
                                addExtendedVlanTag(1),
                                delExtendedVlanTag(2),
                                setTreatmentTag(3),
                                setTreatmentInner(4),
                                setTreatmentOuter(5),
                                setFilterEtherType(6),
                                setFilterInner(7),
                                setFilterOuter(8)
                                }
                        MAX-ACCESS read-write
                        STATUS current
                        DESCRIPTION
                                "The request of a user command"
                        ::= { fkGponProfile2ExtVlanTagControl 1 }

                
                -- 1.3.6.1.4.1.10428 9 1.101.23.51.24.2.2.2
                fkGponProfile2ExtVlanTagControlStatus OBJECT-TYPE
                        SYNTAX FkControlStatusType
                        MAX-ACCESS read-only
                        STATUS current
                        DESCRIPTION
                                "The status of user command"
                        ::= { fkGponProfile2ExtVlanTagControl 2 }

                
                -- 1.3.6.1.4.1.10428 9 1.101.23.51.24.2.2.3
                fkGponProfile2ExtVlanTagControlTimer OBJECT-TYPE
                        SYNTAX Gauge32
                        MAX-ACCESS read-write
                        STATUS current
                        DESCRIPTION
                                "The maximum time for the manager for a long running user command"
                        ::= { fkGponProfile2ExtVlanTagControl 3 }

                
                -- 1.3.6.1.4.1.10428 9 1.101.23.51.24.2.2.4
                fkGponProfile2ExtVlanTagControlTimeStamp OBJECT-TYPE
                        SYNTAX TimeTicks
                        MAX-ACCESS read-only
                        STATUS current
                        DESCRIPTION
                                "The time stamp of the last command(end of command)"
                        ::= { fkGponProfile2ExtVlanTagControl 4 }

                
                -- 1.3.6.1.4.1.10428 9 1.101.23.51.24.2.2.5
                fkGponProfile2ExtVlanTagControlReqResult OBJECT-TYPE
                        SYNTAX FkControlRequestResultType
                        MAX-ACCESS read-only
                        STATUS current
                        DESCRIPTION
                                "The result of the last user command"
                        ::= { fkGponProfile2ExtVlanTagControl 5 }

                
                -- 1.3.6.1.4.1.10428 9 1.101.23.51.24.2.2.6
                fkGponProfile2ExtVlanTagControlName OBJECT-TYPE
                        SYNTAX OCTET STRING
                        MAX-ACCESS read-write
                        STATUS current
                        DESCRIPTION
                                "Description."
                        ::= { fkGponProfile2ExtVlanTagControl 6 }

                
                -- 1.3.6.1.4.1.10428 9 1.101.23.51.24.2.2.7
                fkGponProfile2ExtVlanTagControlType OBJECT-TYPE
                        SYNTAX INTEGER
                                {
                                unTaggedFrame(1),
                                singleTaggedFrame(2),
                                doubleTaggedFrame(3)
                                }
                        MAX-ACCESS read-write
                        STATUS current
                        DESCRIPTION
                                "Description."
                        ::= { fkGponProfile2ExtVlanTagControl 7 }

                
                -- 1.3.6.1.4.1.10428 9 1.101.23.51.24.2.2.8
                fkGponProfile2ExtVlanTagControlIndex OBJECT-TYPE
                        SYNTAX INTEGER (1..65535)
                        MAX-ACCESS read-write
                        STATUS current
                        DESCRIPTION
                                "Description."
                        ::= { fkGponProfile2ExtVlanTagControl 8 }

                
                -- 1.3.6.1.4.1.10428 9 1.101.23.51.24.2.2.9
                fkGponProfile2ExtVlanTagControlTreatTag OBJECT-TYPE
                        SYNTAX INTEGER
                                {
                                notRemove(0),
                                remove(1),
                                both(2),
                                notMatchDiscardInDs(3)
                                }
                        MAX-ACCESS read-write
                        STATUS current
                        DESCRIPTION
                                "Description."
                        ::= { fkGponProfile2ExtVlanTagControl 9 }

                
                -- 1.3.6.1.4.1.10428 9 1.101.23.51.24.2.2.10
                fkGponProfile2ExtVlanTagControlTreatInnerCopyVid OBJECT-TYPE
                        SYNTAX INTEGER (0..4094 | 4096 | 4097)
                        MAX-ACCESS read-write
                        STATUS current
                        DESCRIPTION
                                "(0-4094) | 4096(copy_inner) | 4097(copy_outer)"
                        ::= { fkGponProfile2ExtVlanTagControl 10 }

                
                -- 1.3.6.1.4.1.10428 9 1.101.23.51.24.2.2.11
                fkGponProfile2ExtVlanTagControlTreatInnerCopyCos OBJECT-TYPE
                        SYNTAX INTEGER (0..7 | 8 | 9 | 10 | 15)
                        MAX-ACCESS read-write
                        STATUS current
                        DESCRIPTION
                                "(0-7) | 8(copy_inner) | 9(copy_outer)|10(dscpToPbit)15(unused) "
                        ::= { fkGponProfile2ExtVlanTagControl 11 }

                
                -- 1.3.6.1.4.1.10428 9 1.101.23.51.24.2.2.12
                fkGponProfile2ExtVlanTagControlTreatInnerTpidDei OBJECT-TYPE
                        SYNTAX INTEGER
                                {
                                tpidCopyInner(0),
                                tpidCopyOuter(1),
                                tpidOutputDeiCopyInner(2),
                                tpidOutputDeiOuter(3),
                                tpid0x8100(4),
                                tpidReserved(5),
                                tpidOutputDei0(6),
                                tpidOutputDei1(7)
                                }
                        MAX-ACCESS read-write
                        STATUS current
                        DESCRIPTION
                                "Description."
                        ::= { fkGponProfile2ExtVlanTagControl 12 }

                
                -- 1.3.6.1.4.1.10428 9 1.101.23.51.24.2.2.13
                fkGponProfile2ExtVlanTagControlTreatOuterCopyVid OBJECT-TYPE
                        SYNTAX INTEGER (0..4094 | 4096 | 4097)
                        MAX-ACCESS read-write
                        STATUS current
                        DESCRIPTION
                                "(0-4094) | 4096(copy_inner) | 4097(copy_outer)"
                        ::= { fkGponProfile2ExtVlanTagControl 13 }

                
                -- 1.3.6.1.4.1.10428 9 1.101.23.51.24.2.2.14
                fkGponProfile2ExtVlanTagControlTreatOuterCopyCos OBJECT-TYPE
                        SYNTAX INTEGER (0..7 | 8 | 9 | 10 | 15)
                        MAX-ACCESS read-write
                        STATUS current
                        DESCRIPTION
                                "(0-7) | 8(copy_inner) | 9(copy_outer)|10(dscpToPbit)15(unused) "
                        ::= { fkGponProfile2ExtVlanTagControl 14 }

                
                -- 1.3.6.1.4.1.10428 9 1.101.23.51.24.2.2.15
                fkGponProfile2ExtVlanTagControlTreatOuterTpidDei OBJECT-TYPE
                        SYNTAX INTEGER
                                {
                                tpidCopyInner(0),
                                tpidCopyOuter(1),
                                tpidOutputDeiCopyInner(2),
                                tpidOutputDeiOuter(3),
                                tpid0x8100(4),
                                tpidReserved(5),
                                tpidOutputDei0(6),
                                tpidOutputDei1(7)
                                }
                        MAX-ACCESS read-write
                        STATUS current
                        DESCRIPTION
                                "Description."
                        ::= { fkGponProfile2ExtVlanTagControl 15 }

                
                -- 1.3.6.1.4.1.10428 9 1.101.23.51.24.2.2.16
                fkGponProfile2ExtVlanTagControlFilterEtherType OBJECT-TYPE
                        SYNTAX INTEGER
                                {
                                unused(0),
                                ipoe(1),
                                pppoe(2),
                                arp(3),
                                ipv6Ipoe(4)
                                }
                        MAX-ACCESS read-write
                        STATUS current
                        DESCRIPTION
                                "Description."
                        ::= { fkGponProfile2ExtVlanTagControl 16 }

                
                -- 1.3.6.1.4.1.10428 9 1.101.23.51.24.2.2.17
                fkGponProfile2ExtVlanTagControlFilterInnerVid OBJECT-TYPE
                        SYNTAX INTEGER (0..4094 | 4096)
                        MAX-ACCESS read-write
                        STATUS current
                        DESCRIPTION
                                "(0-4094) | any(4096"
                        ::= { fkGponProfile2ExtVlanTagControl 17 }

                
                -- 1.3.6.1.4.1.10428 9 1.101.23.51.24.2.2.18
                fkGponProfile2ExtVlanTagControlFilterInnerCos OBJECT-TYPE
                        SYNTAX INTEGER (0..7 | 8)
                        MAX-ACCESS read-write
                        STATUS current
                        DESCRIPTION
                                "(0-7) | 8(any)"
                        ::= { fkGponProfile2ExtVlanTagControl 18 }

                
                -- 1.3.6.1.4.1.10428 9 1.101.23.51.24.2.2.19
                fkGponProfile2ExtVlanTagControlFilterInnerTpidDei OBJECT-TYPE
                        SYNTAX INTEGER
                                {
                                tpidany(0),
                                tpid0x8100(4),
                                tpidInput(5),
                                tpidInputDei0(6),
                                tpidInputDei1(7)
                                }
                        MAX-ACCESS read-write
                        STATUS current
                        DESCRIPTION
                                "0(Tpidany) |  4(TpidDefault) 5(TpidInput), 6(TpidInputDei0), 7 (TpidInputDei1)"
                        ::= { fkGponProfile2ExtVlanTagControl 19 }

                
                -- 1.3.6.1.4.1.10428 9 1.101.23.51.24.2.2.20
                fkGponProfile2ExtVlanTagControlFilterOuterVid OBJECT-TYPE
                        SYNTAX INTEGER (0..4094 | 4096)
                        MAX-ACCESS read-write
                        STATUS current
                        DESCRIPTION
                                "(0-4094) | any(4096"
                        ::= { fkGponProfile2ExtVlanTagControl 20 }

                
                -- 1.3.6.1.4.1.10428 9 1.101.23.51.24.2.2.21
                fkGponProfile2ExtVlanTagControlFilterOuterCos OBJECT-TYPE
                        SYNTAX INTEGER (0..7 | 8)
                        MAX-ACCESS read-write
                        STATUS current
                        DESCRIPTION
                                "(0-7) | 8(any)"
                        ::= { fkGponProfile2ExtVlanTagControl 21 }

                
                -- 1.3.6.1.4.1.10428 9 1.101.23.51.24.2.2.22
                fkGponProfile2ExtVlanTagControlFilterOuterTpidDei OBJECT-TYPE
                        SYNTAX INTEGER
                                {
                                tpidany(0),
                                tpid0x8100(4),
                                tpidInput(5),
                                tpidInputDei0(6),
                                tpidInputDei1(7)
                                }
                        MAX-ACCESS read-write
                        STATUS current
                        DESCRIPTION
                                "0(Tpidany) |  4(TpidDefault) 5(TpidInput), 6(TpidInputDei0), 7 (TpidInputDei1)"
                        ::= { fkGponProfile2ExtVlanTagControl 22 }

                
                -- 1.3.6.1.4.1.10428 9 1.101.23.51.24.2.3
                fkGponProfile2ExtVlanTagNotification OBJECT IDENTIFIER ::= { fkGponProfile2ExtVlanTag 3 }

                
                -- 1.3.6.1.4.1.10428 9 1.101.23.51.24.2.3.1
                fkGponProfile2ExtVlanTagAdded NOTIFICATION-TYPE
                        OBJECTS { fkGponProfile2ExtVlanTagControlRequest, fkGponProfile2ExtVlanTagControlTimeStamp, fkGponProfile2ExtVlanTagControlReqResult, fkGponProfile2ExtVlanTagControlName, fkGponProfile2ExtVlanTagControlType, 
                                fkGponProfile2ExtVlanTagControlIndex }
                        STATUS current
                        DESCRIPTION 
                                "Description."
                        ::= { fkGponProfile2ExtVlanTagNotification 1 }

                
                -- 1.3.6.1.4.1.10428 9 1.101.23.51.24.2.3.2
                fkGponProfile2ExtVlanTagDeleted NOTIFICATION-TYPE
                        OBJECTS { fkGponProfile2ExtVlanTagControlRequest, fkGponProfile2ExtVlanTagControlTimeStamp, fkGponProfile2ExtVlanTagControlReqResult, fkGponProfile2ExtVlanTagControlName, fkGponProfile2ExtVlanTagControlType, 
                                fkGponProfile2ExtVlanTagControlIndex }
                        STATUS current
                        DESCRIPTION 
                                "Description."
                        ::= { fkGponProfile2ExtVlanTagNotification 2 }

                
                -- 1.3.6.1.4.1.10428 9 1.101.23.51.24.2.3.3
                fkGponProfile2ExtVlanTagTreatmentTag NOTIFICATION-TYPE
                        OBJECTS { fkGponProfile2ExtVlanTagControlRequest, fkGponProfile2ExtVlanTagControlTimeStamp, fkGponProfile2ExtVlanTagControlReqResult, fkGponProfile2ExtVlanTagControlName, fkGponProfile2ExtVlanTagControlType, 
                                fkGponProfile2ExtVlanTagControlIndex, fkGponProfile2ExtVlanTagControlTreatTag }
                        STATUS current
                        DESCRIPTION 
                                "Description."
                        ::= { fkGponProfile2ExtVlanTagNotification 3 }

                
                -- 1.3.6.1.4.1.10428 9 1.101.23.51.24.2.3.4
                fkGponProfile2ExtVlanTagTreatmentInnerChanged NOTIFICATION-TYPE
                        OBJECTS { fkGponProfile2ExtVlanTagControlRequest, fkGponProfile2ExtVlanTagControlTimeStamp, fkGponProfile2ExtVlanTagControlReqResult, fkGponProfile2ExtVlanTagControlName, fkGponProfile2ExtVlanTagControlType, 
                                fkGponProfile2ExtVlanTagControlIndex, fkGponProfile2ExtVlanTagControlTreatInnerCopyVid, fkGponProfile2ExtVlanTagControlTreatInnerCopyCos, fkGponProfile2ExtVlanTagControlTreatInnerTpidDei }
                        STATUS current
                        DESCRIPTION 
                                "Description."
                        ::= { fkGponProfile2ExtVlanTagNotification 4 }

                
                -- 1.3.6.1.4.1.10428 9 1.101.23.51.24.2.3.5
                fkGponProfile2ExtVlanTagTreatmentOuterChanged NOTIFICATION-TYPE
                        OBJECTS { fkGponProfile2ExtVlanTagControlRequest, fkGponProfile2ExtVlanTagControlTimeStamp, fkGponProfile2ExtVlanTagControlReqResult, fkGponProfile2ExtVlanTagControlName, fkGponProfile2ExtVlanTagControlType, 
                                fkGponProfile2ExtVlanTagControlIndex, fkGponProfile2ExtVlanTagControlTreatOuterCopyVid, fkGponProfile2ExtVlanTagControlTreatOuterCopyCos, fkGponProfile2ExtVlanTagControlTreatOuterTpidDei }
                        STATUS current
                        DESCRIPTION 
                                "Description."
                        ::= { fkGponProfile2ExtVlanTagNotification 5 }

                
                -- 1.3.6.1.4.1.10428 9 1.101.23.51.24.2.3.6
                fkGponProfile2ExtVlanTagFilterEtherTypeChanged NOTIFICATION-TYPE
                        OBJECTS { fkGponProfile2ExtVlanTagControlRequest, fkGponProfile2ExtVlanTagControlTimeStamp, fkGponProfile2ExtVlanTagControlReqResult, fkGponProfile2ExtVlanTagControlName, fkGponProfile2ExtVlanTagControlType, 
                                fkGponProfile2ExtVlanTagControlIndex, fkGponProfile2ExtVlanTagControlFilterEtherType }
                        STATUS current
                        DESCRIPTION 
                                "Description."
                        ::= { fkGponProfile2ExtVlanTagNotification 6 }

                
                -- 1.3.6.1.4.1.10428 9 1.101.23.51.24.2.3.7
                fkGponProfile2ExtVlanTagFilterInnerChanged NOTIFICATION-TYPE
                        OBJECTS { fkGponProfile2ExtVlanTagControlRequest, fkGponProfile2ExtVlanTagControlTimeStamp, fkGponProfile2ExtVlanTagControlReqResult, fkGponProfile2ExtVlanTagControlName, fkGponProfile2ExtVlanTagControlType, 
                                fkGponProfile2ExtVlanTagControlIndex, fkGponProfile2ExtVlanTagControlFilterInnerVid, fkGponProfile2ExtVlanTagControlFilterInnerCos, fkGponProfile2ExtVlanTagControlFilterInnerTpidDei }
                        STATUS current
                        DESCRIPTION 
                                "Description."
                        ::= { fkGponProfile2ExtVlanTagNotification 7 }

                
                -- 1.3.6.1.4.1.10428 9 1.101.23.51.24.2.3.8
                fkGponProfile2ExtVlanTagFilterOuterChanged NOTIFICATION-TYPE
                        OBJECTS { fkGponProfile2ExtVlanTagControlRequest, fkGponProfile2ExtVlanTagControlTimeStamp, fkGponProfile2ExtVlanTagControlReqResult, fkGponProfile2ExtVlanTagControlName, fkGponProfile2ExtVlanTagControlType, 
                                fkGponProfile2ExtVlanTagControlIndex, fkGponProfile2ExtVlanTagControlFilterOuterVid, fkGponProfile2ExtVlanTagControlFilterOuterCos, fkGponProfile2ExtVlanTagControlFilterOuterTpidDei }
                        STATUS current
                        DESCRIPTION 
                                "Description."
                        ::= { fkGponProfile2ExtVlanTagNotification 8 }

                
                -- 1.3.6.1.4.1.10428 9 1.101.23.51.25
                fkGponProfile2MapperGem OBJECT IDENTIFIER ::= { fkGponProfile2 25 }

                
                -- 1.3.6.1.4.1.10428 9 1.101.23.51.25.1
                fkGponProfile2MapperGemTable OBJECT-TYPE
                        SYNTAX SEQUENCE OF FkGponProfile2MapperGemEntry
                        MAX-ACCESS not-accessible
                        STATUS current
                        DESCRIPTION
                                "Description."
                        ::= { fkGponProfile2MapperGem 1 }

                
                -- 1.3.6.1.4.1.10428 9 1.101.23.51.25.1.1
                fkGponProfile2MapperGemEntry OBJECT-TYPE
                        SYNTAX FkGponProfile2MapperGemEntry
                        MAX-ACCESS not-accessible
                        STATUS current
                        DESCRIPTION
                                "Description."
                        INDEX { fkGponProfile2TrafficIndex, fkGponProfile2MapperIndex, fkGponProfile2MapperGemId }
                        ::= { fkGponProfile2MapperGemTable 1 }

                
                FkGponProfile2MapperGemEntry ::=
                        SEQUENCE { 
                                fkGponProfile2MapperIndex
                                        Integer32,
                                fkGponProfile2MapperGemId
                                        Integer32,
                                fkGponProfile2MapperGemRateLimitDownSir
                                        Integer32,
                                fkGponProfile2MapperGemRateLimitDownPir
                                        Integer32,
                                fkGponProfile2MapperGemRateLimitUpSir
                                        Integer32,
                                fkGponProfile2MapperGemRateLimitUpPir
                                        Integer32,
                                fkGponProfile2MapperGemRateLimitProfile
                                        OCTET STRING
                         }

                -- 1.3.6.1.4.1.10428 9 1.101.23.51.25.1.1.1
                fkGponProfile2MapperIndex OBJECT-TYPE
                        SYNTAX Integer32 (1..65535)
                        MAX-ACCESS read-only
                        STATUS current
                        DESCRIPTION
                                "The mapper index."
                        ::= { fkGponProfile2MapperGemEntry 1 }

                
                -- 1.3.6.1.4.1.10428 9 1.101.23.51.25.1.1.2
                fkGponProfile2MapperGemId OBJECT-TYPE
                        SYNTAX Integer32 (1..65535)
                        MAX-ACCESS read-only
                        STATUS current
                        DESCRIPTION
                                "The GEM index."
                        ::= { fkGponProfile2MapperGemEntry 2 }

                
                -- 1.3.6.1.4.1.10428 9 1.101.23.51.25.1.1.3
                fkGponProfile2MapperGemRateLimitDownSir OBJECT-TYPE
                        SYNTAX Integer32
                        MAX-ACCESS read-only
                        STATUS current
                        DESCRIPTION
                                "The downstream rate-limit control : SIR (Bandwidth in steps of 64Kbps)"
                        ::= { fkGponProfile2MapperGemEntry 3 }

                
                -- 1.3.6.1.4.1.10428 9 1.101.23.51.25.1.1.4
                fkGponProfile2MapperGemRateLimitDownPir OBJECT-TYPE
                        SYNTAX Integer32
                        MAX-ACCESS read-only
                        STATUS current
                        DESCRIPTION
                                "The downstream rate-limit control : PIR (Bandwidth in steps of 64Kbps)"
                        ::= { fkGponProfile2MapperGemEntry 4 }

                
                -- 1.3.6.1.4.1.10428 9 1.101.23.51.25.1.1.5
                fkGponProfile2MapperGemRateLimitUpSir OBJECT-TYPE
                        SYNTAX Integer32
                        MAX-ACCESS read-only
                        STATUS current
                        DESCRIPTION
                                "The upstream rate-limit control : SIR (Bandwidth in steps of 64Kbps)"
                        ::= { fkGponProfile2MapperGemEntry 5 }

                
                -- 1.3.6.1.4.1.10428 9 1.101.23.51.25.1.1.6
                fkGponProfile2MapperGemRateLimitUpPir OBJECT-TYPE
                        SYNTAX Integer32
                        MAX-ACCESS read-only
                        STATUS current
                        DESCRIPTION
                                "The upstream rate-limit control : PIR (Bandwidth in steps of 64Kbps)"
                        ::= { fkGponProfile2MapperGemEntry 6 }

                
                -- 1.3.6.1.4.1.10428 9 1.101.23.51.25.1.1.7
                fkGponProfile2MapperGemRateLimitProfile OBJECT-TYPE
                        SYNTAX OCTET STRING
                        MAX-ACCESS read-only
                        STATUS current
                        DESCRIPTION
                                "The rate-limit profile name."
                        ::= { fkGponProfile2MapperGemEntry 7 }

                
                -- 1.3.6.1.4.1.10428 9 1.101.23.51.25.2
                fkGponProfile2MapperGemControl OBJECT IDENTIFIER ::= { fkGponProfile2MapperGem 2 }

                
                -- 1.3.6.1.4.1.10428 9 1.101.23.51.25.2.1
                fkGponProfile2MapperGemControlRequest OBJECT-TYPE
                        SYNTAX INTEGER
                                {
                                setGemRateLimit(1),
                                delGemRateLimit(2),
                                setGemRatelimitProfile(3)
                                }
                        MAX-ACCESS read-write
                        STATUS current
                        DESCRIPTION
                                "The request of a user command"
                        ::= { fkGponProfile2MapperGemControl 1 }

                
                -- 1.3.6.1.4.1.10428 9 1.101.23.51.25.2.2
                fkGponProfile2MapperGemControlStatus OBJECT-TYPE
                        SYNTAX FkControlStatusType
                        MAX-ACCESS read-only
                        STATUS current
                        DESCRIPTION
                                "The status of user command"
                        ::= { fkGponProfile2MapperGemControl 2 }

                
                -- 1.3.6.1.4.1.10428 9 1.101.23.51.25.2.3
                fkGponProfile2MapperGemControlTimer OBJECT-TYPE
                        SYNTAX Gauge32
                        MAX-ACCESS read-write
                        STATUS current
                        DESCRIPTION
                                "The maximum time for the manager for a long running user command"
                        ::= { fkGponProfile2MapperGemControl 3 }

                
                -- 1.3.6.1.4.1.10428 9 1.101.23.51.25.2.4
                fkGponProfile2MapperGemControlTimeStamp OBJECT-TYPE
                        SYNTAX TimeTicks
                        MAX-ACCESS read-only
                        STATUS current
                        DESCRIPTION
                                "The time stamp of the last command(end of command)"
                        ::= { fkGponProfile2MapperGemControl 4 }

                
                -- 1.3.6.1.4.1.10428 9 1.101.23.51.25.2.5
                fkGponProfile2MapperGemControlReqResult OBJECT-TYPE
                        SYNTAX FkControlRequestResultType
                        MAX-ACCESS read-only
                        STATUS current
                        DESCRIPTION
                                "The result of the last user command"
                        ::= { fkGponProfile2MapperGemControl 5 }

                
                -- 1.3.6.1.4.1.10428 9 1.101.23.51.25.2.6
                fkGponProfile2MapperGemControlTrafficName OBJECT-TYPE
                        SYNTAX OCTET STRING
                        MAX-ACCESS read-write
                        STATUS current
                        DESCRIPTION
                                "The Traffic profile name."
                        ::= { fkGponProfile2MapperGemControl 6 }

                
                -- 1.3.6.1.4.1.10428 9 1.101.23.51.25.2.7
                fkGponProfile2MapperGemControlIndex OBJECT-TYPE
                        SYNTAX Integer32
                        MAX-ACCESS read-write
                        STATUS current
                        DESCRIPTION
                                "The mapper index."
                        ::= { fkGponProfile2MapperGemControl 7 }

                
                -- 1.3.6.1.4.1.10428 9 1.101.23.51.25.2.8
                fkGponProfile2MapperGemControlGemIndex OBJECT-TYPE
                        SYNTAX Integer32
                        MAX-ACCESS read-write
                        STATUS current
                        DESCRIPTION
                                "The GEM index."
                        ::= { fkGponProfile2MapperGemControl 8 }

                
                -- 1.3.6.1.4.1.10428 9 1.101.23.51.25.2.9
                fkGponProfile2MapperGemControlRateLimitDownSir OBJECT-TYPE
                        SYNTAX Integer32
                        MAX-ACCESS read-write
                        STATUS current
                        DESCRIPTION
                                "The downstream rate-limit control : SIR (Bandwidth in steps of 64Kbps)"
                        ::= { fkGponProfile2MapperGemControl 9 }

                
                -- 1.3.6.1.4.1.10428 9 1.101.23.51.25.2.10
                fkGponProfile2MapperGemControlRateLimitDownPir OBJECT-TYPE
                        SYNTAX Integer32
                        MAX-ACCESS read-write
                        STATUS current
                        DESCRIPTION
                                "The downstream rate-limit control : PIR (Bandwidth in steps of 64Kbps)"
                        ::= { fkGponProfile2MapperGemControl 10 }

                
                -- 1.3.6.1.4.1.10428 9 1.101.23.51.25.2.11
                fkGponProfile2MapperGemControlRateLimitUpSir OBJECT-TYPE
                        SYNTAX Integer32
                        MAX-ACCESS read-write
                        STATUS current
                        DESCRIPTION
                                "The upstream rate-limit control : SIR (Bandwidth in steps of 64Kbps)"
                        ::= { fkGponProfile2MapperGemControl 11 }

                
                -- 1.3.6.1.4.1.10428 9 1.101.23.51.25.2.12
                fkGponProfile2MapperGemControlRateLimitUpPir OBJECT-TYPE
                        SYNTAX Integer32
                        MAX-ACCESS read-write
                        STATUS current
                        DESCRIPTION
                                "The upstream rate-limit control : PIR (Bandwidth in steps of 64Kbps)"
                        ::= { fkGponProfile2MapperGemControl 12 }

                
                -- 1.3.6.1.4.1.10428 9 1.101.23.51.25.2.13
                fkGponProfile2MapperGemControlRateLimitProfile OBJECT-TYPE
                        SYNTAX OCTET STRING
                        MAX-ACCESS read-write
                        STATUS current
                        DESCRIPTION
                                "The rate-limit profile name."
                        ::= { fkGponProfile2MapperGemControl 13 }

                
                -- 1.3.6.1.4.1.10428 9 1.101.23.51.25.3
                fkGponProfile2MapperGemNotification OBJECT IDENTIFIER ::= { fkGponProfile2MapperGem 3 }

                
                -- 1.3.6.1.4.1.10428 9 1.101.23.51.25.3.1
                fkGponProfile2MapperGemRateLimitChanged NOTIFICATION-TYPE
                        OBJECTS { fkGponProfile2MapperGemControlRequest, fkGponProfile2MapperGemControlTimeStamp, fkGponProfile2MapperGemControlReqResult, fkGponProfile2MapperGemControlTrafficName, fkGponProfile2MapperGemControlIndex, 
                                fkGponProfile2MapperGemControlGemIndex, fkGponProfile2MapperGemControlRateLimitDownSir, fkGponProfile2MapperGemControlRateLimitDownPir, fkGponProfile2MapperGemControlRateLimitUpSir, fkGponProfile2MapperGemControlRateLimitUpPir
                                 }
                        STATUS current
                        DESCRIPTION 
                                "setGemRateLimit"
                        ::= { fkGponProfile2MapperGemNotification 1 }

                
                -- 1.3.6.1.4.1.10428 9 1.101.23.51.25.3.2
                fkGponProfile2MapperGemRateLimitDeleted NOTIFICATION-TYPE
                        OBJECTS { fkGponProfile2MapperGemControlRequest, fkGponProfile2MapperGemControlTimeStamp, fkGponProfile2MapperGemControlReqResult, fkGponProfile2MapperGemControlTrafficName, fkGponProfile2MapperGemControlIndex, 
                                fkGponProfile2MapperGemControlGemIndex }
                        STATUS current
                        DESCRIPTION 
                                "delGemRateLimit"
                        ::= { fkGponProfile2MapperGemNotification 2 }

                
                -- 1.3.6.1.4.1.10428 9 1.101.23.51.25.3.3
                fkGponProfile2MapperGemRateLimitProfileChanged NOTIFICATION-TYPE
                        OBJECTS { fkGponProfile2MapperGemControlRequest, fkGponProfile2MapperGemControlTimeStamp, fkGponProfile2MapperGemControlReqResult, fkGponProfile2MapperGemControlTrafficName, fkGponProfile2MapperGemControlIndex, 
                                fkGponProfile2MapperGemControlGemIndex, fkGponProfile2MapperGemControlRateLimitProfile }
                        STATUS current
                        DESCRIPTION 
                                "setGemRatelimitProfile"
                        ::= { fkGponProfile2MapperGemNotification 3 }

                
                -- 1.3.6.1.4.1.10428 9 1.101.23.51.26
                fkGponProfile2GemNctp OBJECT IDENTIFIER ::= { fkGponProfile2 26 }

                
                -- 1.3.6.1.4.1.10428 9 1.101.23.51.26.1
                fkGponProfile2GemNctpTable OBJECT-TYPE
                        SYNTAX SEQUENCE OF FkGponProfile2GemNctpEntry
                        MAX-ACCESS not-accessible
                        STATUS current
                        DESCRIPTION
                                "Description."
                        ::= { fkGponProfile2GemNctp 1 }

                
                -- 1.3.6.1.4.1.10428 9 1.101.23.51.26.1.1
                fkGponProfile2GemNctpEntry OBJECT-TYPE
                        SYNTAX FkGponProfile2GemNctpEntry
                        MAX-ACCESS not-accessible
                        STATUS current
                        DESCRIPTION
                                "Description."
                        INDEX { fkGponProfile2TrafficIndex, fkGponProfile2GemNctpIndex }
                        ::= { fkGponProfile2GemNctpTable 1 }

                
                FkGponProfile2GemNctpEntry ::=
                        SEQUENCE { 
                                fkGponProfile2GemNctpIndex
                                        Integer32,
                                fkGponProfile2GemNctpServiceId
                                        Integer32,
                                fkGponProfile2GemNctpServiceType
                                        INTEGER
                         }

                -- 1.3.6.1.4.1.10428 9 1.101.23.51.26.1.1.1
                fkGponProfile2GemNctpIndex OBJECT-TYPE
                        SYNTAX Integer32 (1..65535)
                        MAX-ACCESS read-only
                        STATUS current
                        DESCRIPTION
                                "The NCTP index."
                        ::= { fkGponProfile2GemNctpEntry 1 }

                
                -- 1.3.6.1.4.1.10428 9 1.101.23.51.26.1.1.2
                fkGponProfile2GemNctpServiceId OBJECT-TYPE
                        SYNTAX Integer32
                        MAX-ACCESS read-only
                        STATUS current
                        DESCRIPTION
                                "The NCTP service index."
                        ::= { fkGponProfile2GemNctpEntry 2 }

                
                -- 1.3.6.1.4.1.10428 9 1.101.23.51.26.1.1.3
                fkGponProfile2GemNctpServiceType OBJECT-TYPE
                        SYNTAX INTEGER
                                {
                                svcTypeBridge(1),
                                svcTypeIphost(2),
                                svcTypeVRP(3)
                                }
                        MAX-ACCESS read-write
                        STATUS current
                        DESCRIPTION
                                "The NCTP service type"
                        ::= { fkGponProfile2GemNctpEntry 3 }

                
                -- 1.3.6.1.4.1.10428 9 1.101.23.51.26.2
                fkGponProfile2GemNctpControl OBJECT IDENTIFIER ::= { fkGponProfile2GemNctp 2 }

                
                -- 1.3.6.1.4.1.10428 9 1.101.23.51.26.2.1
                fkGponProfile2GemNctpControlRequest OBJECT-TYPE
                        SYNTAX INTEGER
                                {
                                addNCTPService(1),
                                delNCTPService(2),
                                setNCTPService(3)
                                }
                        MAX-ACCESS read-write
                        STATUS current
                        DESCRIPTION
                                "The request of a user command"
                        ::= { fkGponProfile2GemNctpControl 1 }

                
                -- 1.3.6.1.4.1.10428 9 1.101.23.51.26.2.2
                fkGponProfile2GemNctpControlStatus OBJECT-TYPE
                        SYNTAX FkControlStatusType
                        MAX-ACCESS read-only
                        STATUS current
                        DESCRIPTION
                                "The status of user command"
                        ::= { fkGponProfile2GemNctpControl 2 }

                
                -- 1.3.6.1.4.1.10428 9 1.101.23.51.26.2.3
                fkGponProfile2GemNctpControlTimer OBJECT-TYPE
                        SYNTAX Gauge32
                        MAX-ACCESS read-write
                        STATUS current
                        DESCRIPTION
                                "The maximum time for the manager for a long running user command"
                        ::= { fkGponProfile2GemNctpControl 3 }

                
                -- 1.3.6.1.4.1.10428 9 1.101.23.51.26.2.4
                fkGponProfile2GemNctpControlTimeStamp OBJECT-TYPE
                        SYNTAX TimeTicks
                        MAX-ACCESS read-only
                        STATUS current
                        DESCRIPTION
                                "The time stamp of the last command(end of command)"
                        ::= { fkGponProfile2GemNctpControl 4 }

                
                -- 1.3.6.1.4.1.10428 9 1.101.23.51.26.2.5
                fkGponProfile2GemNctpControlReqResult OBJECT-TYPE
                        SYNTAX FkControlRequestResultType
                        MAX-ACCESS read-only
                        STATUS current
                        DESCRIPTION
                                "The result of the last user command"
                        ::= { fkGponProfile2GemNctpControl 5 }

                
                -- 1.3.6.1.4.1.10428 9 1.101.23.51.26.2.6
                fkGponProfile2GemNctpControlTname OBJECT-TYPE
                        SYNTAX OCTET STRING
                        MAX-ACCESS read-write
                        STATUS current
                        DESCRIPTION
                                "The Traffic profile name."
                        ::= { fkGponProfile2GemNctpControl 6 }

                
                -- 1.3.6.1.4.1.10428 9 1.101.23.51.26.2.7
                fkGponProfile2GemNctpControlIndex OBJECT-TYPE
                        SYNTAX Integer32
                        MAX-ACCESS read-write
                        STATUS current
                        DESCRIPTION
                                "The NCTP index."
                        ::= { fkGponProfile2GemNctpControl 7 }

                
                -- 1.3.6.1.4.1.10428 9 1.101.23.51.26.2.8
                fkGponProfile2GemNctpControlServiceId OBJECT-TYPE
                        SYNTAX Integer32
                        MAX-ACCESS read-write
                        STATUS current
                        DESCRIPTION
                                "The NCTP service index."
                        ::= { fkGponProfile2GemNctpControl 8 }

                
                -- 1.3.6.1.4.1.10428 9 1.101.23.51.26.2.9
                fkGponProfile2GemNctpControlServiceType OBJECT-TYPE
                        SYNTAX INTEGER
                                {
                                svcTypeBridge(1),
                                svcTypeIphost(2),
                                svcTypeVRP(3)
                                }
                        MAX-ACCESS read-write
                        STATUS current
                        DESCRIPTION
                                "The NCTP service type"
                        ::= { fkGponProfile2GemNctpControl 9 }

                
                -- 1.3.6.1.4.1.10428 9 1.101.23.51.26.3
                fkGponProfile2GemNctpNotification OBJECT IDENTIFIER ::= { fkGponProfile2GemNctp 3 }

                
                -- 1.3.6.1.4.1.10428 9 1.101.23.51.26.3.1
                fkGponProfile2GemNctpServiceAdded NOTIFICATION-TYPE
                        OBJECTS { fkGponProfile2GemNctpControlRequest, fkGponProfile2GemNctpControlTimeStamp, fkGponProfile2GemNctpControlReqResult, fkGponProfile2GemNctpControlTname, fkGponProfile2GemNctpControlIndex, 
                                fkGponProfile2GemNctpControlServiceId, fkGponProfile2GemNctpControlServiceType }
                        STATUS current
                        DESCRIPTION 
                                "addNCTPService"
                        ::= { fkGponProfile2GemNctpNotification 1 }

                
                -- 1.3.6.1.4.1.10428 9 1.101.23.51.26.3.2
                fkGponProfile2GemNctpServiceDeleted NOTIFICATION-TYPE
                        OBJECTS { fkGponProfile2GemNctpControlRequest, fkGponProfile2GemNctpControlTimeStamp, fkGponProfile2GemNctpControlReqResult, fkGponProfile2GemNctpControlTname, fkGponProfile2GemNctpControlIndex
                                 }
                        STATUS current
                        DESCRIPTION 
                                "delNCTPService"
                        ::= { fkGponProfile2GemNctpNotification 2 }

                
                -- 1.3.6.1.4.1.10428 9 1.101.23.51.26.3.3
                fkGponProfile2GemNctpServiceChanged NOTIFICATION-TYPE
                        OBJECTS { fkGponProfile2GemNctpControlRequest, fkGponProfile2GemNctpControlTimeStamp, fkGponProfile2GemNctpControlReqResult, fkGponProfile2GemNctpControlTname, fkGponProfile2GemNctpControlIndex, 
                                fkGponProfile2GemNctpControlServiceId, fkGponProfile2GemNctpControlServiceType }
                        STATUS current
                        DESCRIPTION 
                                "setNCTPService"
                        ::= { fkGponProfile2GemNctpNotification 3 }

                
                -- 1.3.6.1.4.1.10428 9 1.101.23.51.27
                fkGponProfile2VideoReturnPathSvc OBJECT IDENTIFIER ::= { fkGponProfile2 27 }

                
                -- 1.3.6.1.4.1.10428 9 1.101.23.51.27.1
                fkGponProfile2VideoReturnPathSvcTable OBJECT-TYPE
                        SYNTAX SEQUENCE OF FkGponProfile2VideoReturnPathSvcEntry
                        MAX-ACCESS not-accessible
                        STATUS current
                        DESCRIPTION
                                "Description."
                        ::= { fkGponProfile2VideoReturnPathSvc 1 }

                
                -- 1.3.6.1.4.1.10428 9 1.101.23.51.27.1.1
                fkGponProfile2VideoReturnPathSvcEntry OBJECT-TYPE
                        SYNTAX FkGponProfile2VideoReturnPathSvcEntry
                        MAX-ACCESS not-accessible
                        STATUS current
                        DESCRIPTION
                                "Description."
                        INDEX { fkGponProfile2TrafficIndex, fkGponProfile2VideoReturnPathSvcIndex }
                        ::= { fkGponProfile2VideoReturnPathSvcTable 1 }

                
                FkGponProfile2VideoReturnPathSvcEntry ::=
                        SEQUENCE { 
                                fkGponProfile2VideoReturnPathSvcIndex
                                        Integer32,
                                fkGponProfile2VideoReturnPathSvcMode
                                        INTEGER,
                                fkGponProfile2VideoReturnPathSvcFrequency
                                        Integer32,
                                fkGponProfile2VideoReturnPathSvcPhysical
                                        BITS
                         }

                -- 1.3.6.1.4.1.10428 9 1.101.23.51.27.1.1.1
                fkGponProfile2VideoReturnPathSvcIndex OBJECT-TYPE
                        SYNTAX Integer32 (1..65535)
                        MAX-ACCESS read-only
                        STATUS current
                        DESCRIPTION
                                "The SVC index."
                        ::= { fkGponProfile2VideoReturnPathSvcEntry 1 }

                
                -- 1.3.6.1.4.1.10428 9 1.101.23.51.27.1.1.2
                fkGponProfile2VideoReturnPathSvcMode OBJECT-TYPE
                        SYNTAX INTEGER
                                {
                                mode1VRP256k(0),
                                mode2VRP256k(1),
                                mode2VRP1M(2),
                                mode2VRP3M(3)
                                }
                        MAX-ACCESS read-only
                        STATUS current
                        DESCRIPTION
                                "The SVC mode."
                        ::= { fkGponProfile2VideoReturnPathSvcEntry 2 }

                
                -- 1.3.6.1.4.1.10428 9 1.101.23.51.27.1.1.3
                fkGponProfile2VideoReturnPathSvcFrequency OBJECT-TYPE
                        SYNTAX Integer32
                        MAX-ACCESS read-only
                        STATUS current
                        DESCRIPTION
                                "The SVC frequency"
                        ::= { fkGponProfile2VideoReturnPathSvcEntry 3 }

                
                -- 1.3.6.1.4.1.10428 9 1.101.23.51.27.1.1.4
                fkGponProfile2VideoReturnPathSvcPhysical OBJECT-TYPE
                        SYNTAX BITS
                                {
                                vrpStage13(0),
                                vrpStage12(1),
                                vrpStage11(2),
                                vrpStage10(3),
                                vrpStage9(4),
                                vrpStage8(5),
                                vrpStage7(6),
                                vrpStage6(7),
                                vrpDQPSKmode(8)
                                }
                        MAX-ACCESS read-write
                        STATUS current
                        DESCRIPTION
                                "The SVC physical."
                        ::= { fkGponProfile2VideoReturnPathSvcEntry 4 }

                
                -- 1.3.6.1.4.1.10428 9 1.101.23.51.27.2
                fkGponProfile2VideoReturnPathSvcControl OBJECT IDENTIFIER ::= { fkGponProfile2VideoReturnPathSvc 2 }

                
                -- 1.3.6.1.4.1.10428 9 1.101.23.51.27.2.1
                fkGponProfile2VideoReturnPathSvcControlRequest OBJECT-TYPE
                        SYNTAX INTEGER
                                {
                                addVrp(1),
                                delVrp(2),
                                setVrpMode(3),
                                setVrpFrequency(4),
                                setVrpPhysical(5)
                                }
                        MAX-ACCESS read-write
                        STATUS current
                        DESCRIPTION
                                "The request of a user command"
                        ::= { fkGponProfile2VideoReturnPathSvcControl 1 }

                
                -- 1.3.6.1.4.1.10428 9 1.101.23.51.27.2.2
                fkGponProfile2VideoReturnPathSvcControlStatus OBJECT-TYPE
                        SYNTAX FkControlStatusType
                        MAX-ACCESS read-only
                        STATUS current
                        DESCRIPTION
                                "The status of user command"
                        ::= { fkGponProfile2VideoReturnPathSvcControl 2 }

                
                -- 1.3.6.1.4.1.10428 9 1.101.23.51.27.2.3
                fkGponProfile2VideoReturnPathSvcControlTimer OBJECT-TYPE
                        SYNTAX Gauge32
                        MAX-ACCESS read-write
                        STATUS current
                        DESCRIPTION
                                "The maximum time for the manager for a long running user command"
                        ::= { fkGponProfile2VideoReturnPathSvcControl 3 }

                
                -- 1.3.6.1.4.1.10428 9 1.101.23.51.27.2.4
                fkGponProfile2VideoReturnPathSvcControlTimeStamp OBJECT-TYPE
                        SYNTAX TimeTicks
                        MAX-ACCESS read-only
                        STATUS current
                        DESCRIPTION
                                "The time stamp of the last command(end of command)"
                        ::= { fkGponProfile2VideoReturnPathSvcControl 4 }

                
                -- 1.3.6.1.4.1.10428 9 1.101.23.51.27.2.5
                fkGponProfile2VideoReturnPathSvcControlReqResult OBJECT-TYPE
                        SYNTAX FkControlRequestResultType
                        MAX-ACCESS read-only
                        STATUS current
                        DESCRIPTION
                                "The result of the last user command"
                        ::= { fkGponProfile2VideoReturnPathSvcControl 5 }

                
                -- 1.3.6.1.4.1.10428 9 1.101.23.51.27.2.6
                fkGponProfile2VideoReturnPathSvcControlTname OBJECT-TYPE
                        SYNTAX OCTET STRING
                        MAX-ACCESS read-write
                        STATUS current
                        DESCRIPTION
                                "The Traffic profile name."
                        ::= { fkGponProfile2VideoReturnPathSvcControl 6 }

                
                -- 1.3.6.1.4.1.10428 9 1.101.23.51.27.2.7
                fkGponProfile2VideoReturnPathSvcControlIndex OBJECT-TYPE
                        SYNTAX Integer32
                        MAX-ACCESS read-write
                        STATUS current
                        DESCRIPTION
                                "The SVC index."
                        ::= { fkGponProfile2VideoReturnPathSvcControl 7 }

                
                -- 1.3.6.1.4.1.10428 9 1.101.23.51.27.2.8
                fkGponProfile2VideoReturnPathSvcControlMode OBJECT-TYPE
                        SYNTAX INTEGER
                                {
                                mode1VRP256k(0),
                                mode2VRP256k(1),
                                mode2VRP1M(2),
                                mode2VRP3M(3)
                                }
                        MAX-ACCESS read-write
                        STATUS current
                        DESCRIPTION
                                "The SVC mode."
                        ::= { fkGponProfile2VideoReturnPathSvcControl 8 }

                
                -- 1.3.6.1.4.1.10428 9 1.101.23.51.27.2.9
                fkGponProfile2VideoReturnPathSvcControlFrequency OBJECT-TYPE
                        SYNTAX Integer32
                        MAX-ACCESS read-write
                        STATUS current
                        DESCRIPTION
                                "The SVC frequency"
                        ::= { fkGponProfile2VideoReturnPathSvcControl 9 }

                
                -- 1.3.6.1.4.1.10428 9 1.101.23.51.27.2.10
                fkGponProfile2VideoReturnPathSvcControlPhysical OBJECT-TYPE
                        SYNTAX BITS
                                {
                                vrpStage13(0),
                                vrpStage12(1),
                                vrpStage11(2),
                                vrpStage10(3),
                                vrpStage9(4),
                                vrpStage8(5),
                                vrpStage7(6),
                                vrpStage6(7),
                                vrpDQPSKmode(8)
                                }
                        MAX-ACCESS read-write
                        STATUS current
                        DESCRIPTION
                                "The SVC physical."
                        ::= { fkGponProfile2VideoReturnPathSvcControl 10 }

                
                -- 1.3.6.1.4.1.10428 9 1.101.23.51.27.3
                fkGponProfile2VideoReturnPathSvcNotification OBJECT IDENTIFIER ::= { fkGponProfile2VideoReturnPathSvc 3 }

                
                -- 1.3.6.1.4.1.10428 9 1.101.23.51.27.3.1
                fkGponProfile2VideoReturnPathSvcAdded NOTIFICATION-TYPE
                        OBJECTS { fkGponProfile2VideoReturnPathSvcControlRequest, fkGponProfile2VideoReturnPathSvcControlTimeStamp, fkGponProfile2VideoReturnPathSvcControlReqResult, fkGponProfile2VideoReturnPathSvcControlTname, fkGponProfile2VideoReturnPathSvcControlIndex, 
                                fkGponProfile2VideoReturnPathSvcControlMode, fkGponProfile2VideoReturnPathSvcControlFrequency, fkGponProfile2VideoReturnPathSvcControlPhysical }
                        STATUS current
                        DESCRIPTION 
                                "addVrp "
                        ::= { fkGponProfile2VideoReturnPathSvcNotification 1 }

                
                -- 1.3.6.1.4.1.10428 9 1.101.23.51.27.3.2
                fkGponProfile2VideoReturnPathSvcDeleted NOTIFICATION-TYPE
                        OBJECTS { fkGponProfile2VideoReturnPathSvcControlRequest, fkGponProfile2VideoReturnPathSvcControlTimeStamp, fkGponProfile2VideoReturnPathSvcControlReqResult, fkGponProfile2VideoReturnPathSvcControlTname, fkGponProfile2VideoReturnPathSvcControlIndex
                                 }
                        STATUS current
                        DESCRIPTION 
                                "delVrp "
                        ::= { fkGponProfile2VideoReturnPathSvcNotification 2 }

                
                -- 1.3.6.1.4.1.10428 9 1.101.23.51.27.3.3
                fkGponProfile2VideoReturnPathSvcModeChanged NOTIFICATION-TYPE
                        OBJECTS { fkGponProfile2VideoReturnPathSvcControlRequest, fkGponProfile2VideoReturnPathSvcControlTimeStamp, fkGponProfile2VideoReturnPathSvcControlReqResult, fkGponProfile2VideoReturnPathSvcControlTname, fkGponProfile2VideoReturnPathSvcControlIndex, 
                                fkGponProfile2VideoReturnPathSvcControlMode }
                        STATUS current
                        DESCRIPTION 
                                "setVrpMode"
                        ::= { fkGponProfile2VideoReturnPathSvcNotification 3 }

                
                -- 1.3.6.1.4.1.10428 9 1.101.23.51.27.3.4
                fkGponProfile2VideoReturnPathSvcFrequencyChanged NOTIFICATION-TYPE
                        OBJECTS { fkGponProfile2VideoReturnPathSvcControlRequest, fkGponProfile2VideoReturnPathSvcControlTimeStamp, fkGponProfile2VideoReturnPathSvcControlReqResult, fkGponProfile2VideoReturnPathSvcControlTname, fkGponProfile2VideoReturnPathSvcControlIndex, 
                                fkGponProfile2VideoReturnPathSvcControlFrequency }
                        STATUS current
                        DESCRIPTION 
                                "setVrpFrequency"
                        ::= { fkGponProfile2VideoReturnPathSvcNotification 4 }

                
                -- 1.3.6.1.4.1.10428 9 1.101.23.51.27.3.5
                fkGponProfile2VideoReturnPathSvcPhysicalChanged NOTIFICATION-TYPE
                        OBJECTS { fkGponProfile2VideoReturnPathSvcControlRequest, fkGponProfile2VideoReturnPathSvcControlTimeStamp, fkGponProfile2VideoReturnPathSvcControlReqResult, fkGponProfile2VideoReturnPathSvcControlTname, fkGponProfile2VideoReturnPathSvcControlIndex, 
                                fkGponProfile2VideoReturnPathSvcControlPhysical }
                        STATUS current
                        DESCRIPTION 
                                "setVrpPhysical"
                        ::= { fkGponProfile2VideoReturnPathSvcNotification 5 }

                
                -- 1.3.6.1.4.1.10428 9 1.101.23.51.28
                fkGponProfile2PortMgmt OBJECT IDENTIFIER ::= { fkGponProfile2 28 }

                
                -- 1.3.6.1.4.1.10428 9 1.101.23.51.28.1
                fkGponProfile2PortMgmtTable OBJECT-TYPE
                        SYNTAX SEQUENCE OF FkGponProfile2PortMgmtEntry
                        MAX-ACCESS not-accessible
                        STATUS current
                        DESCRIPTION
                                "Description."
                        ::= { fkGponProfile2PortMgmt 1 }

                
                -- 1.3.6.1.4.1.10428 9 1.101.23.51.28.1.1
                fkGponProfile2PortMgmtEntry OBJECT-TYPE
                        SYNTAX FkGponProfile2PortMgmtEntry
                        MAX-ACCESS not-accessible
                        STATUS current
                        DESCRIPTION
                                "Description."
                        INDEX { fkGponProfile2TrafficIndex, fkGponProfile2PortMgmtSlotId, fkGponProfile2PortMgmtPortId }
                        ::= { fkGponProfile2PortMgmtTable 1 }

                
                FkGponProfile2PortMgmtEntry ::=
                        SEQUENCE { 
                                fkGponProfile2PortMgmtSlotId
                                        INTEGER,
                                fkGponProfile2PortMgmtPortId
                                        Integer32,
                                fkGponProfile2PortMgmtMode
                                        INTEGER,
                                fkGponProfile2PotMgmtVirtualEthNum
                                        Integer32
                         }

                -- 1.3.6.1.4.1.10428 9 1.101.23.51.28.1.1.1
                fkGponProfile2PortMgmtSlotId OBJECT-TYPE
                        SYNTAX INTEGER
                                {
                                ethernet(1),
                                pots(2),
                                ces(3),
                                video(4)
                                }
                        MAX-ACCESS read-only
                        STATUS current
                        DESCRIPTION
                                "The Slot ID"
                        ::= { fkGponProfile2PortMgmtEntry 1 }

                
                -- 1.3.6.1.4.1.10428 9 1.101.23.51.28.1.1.2
                fkGponProfile2PortMgmtPortId OBJECT-TYPE
                        SYNTAX Integer32 (1..32)
                        MAX-ACCESS read-only
                        STATUS current
                        DESCRIPTION
                                "The Port ID"
                        ::= { fkGponProfile2PortMgmtEntry 2 }

                
                -- 1.3.6.1.4.1.10428 9 1.101.23.51.28.1.1.3
                fkGponProfile2PortMgmtMode OBJECT-TYPE
                        SYNTAX INTEGER
                                {
                                modeOMCI(0),
                                modeNonOMCI(1)
                                }
                        MAX-ACCESS read-only
                        STATUS current
                        DESCRIPTION
                                "The Mgmt mode.
                                0 : OMCI mode
                                1 : Non-OMCI mode
                                "
                        ::= { fkGponProfile2PortMgmtEntry 3 }

                
                -- 1.3.6.1.4.1.10428 9 1.101.23.51.28.1.1.4
                fkGponProfile2PotMgmtVirtualEthNum OBJECT-TYPE
                        SYNTAX Integer32 (1..32)
                        MAX-ACCESS read-only
                        STATUS current
                        DESCRIPTION
                                "Virtual Eth Number"
                        ::= { fkGponProfile2PortMgmtEntry 4 }

                
                -- 1.3.6.1.4.1.10428 9 1.101.23.51.28.2
                fkGponProfile2PortMgmtControl OBJECT IDENTIFIER ::= { fkGponProfile2PortMgmt 2 }

                
                -- 1.3.6.1.4.1.10428 9 1.101.23.51.28.2.1
                fkGponProfile2PortMgmtControlRequest OBJECT-TYPE
                        SYNTAX INTEGER
                                {
                                setPortMgmtMode(1),
                                unsetPortMgmtMode(2)
                                }
                        MAX-ACCESS read-write
                        STATUS current
                        DESCRIPTION
                                "The request of a user command"
                        ::= { fkGponProfile2PortMgmtControl 1 }

                
                -- 1.3.6.1.4.1.10428 9 1.101.23.51.28.2.2
                fkGponProfile2PortMgmtControlStatus OBJECT-TYPE
                        SYNTAX FkControlStatusType
                        MAX-ACCESS read-only
                        STATUS current
                        DESCRIPTION
                                "The status of user command"
                        ::= { fkGponProfile2PortMgmtControl 2 }

                
                -- 1.3.6.1.4.1.10428 9 1.101.23.51.28.2.3
                fkGponProfile2PortMgmtControlTimer OBJECT-TYPE
                        SYNTAX Gauge32
                        MAX-ACCESS read-write
                        STATUS current
                        DESCRIPTION
                                "The maximum time for the manager for a long running user command"
                        ::= { fkGponProfile2PortMgmtControl 3 }

                
                -- 1.3.6.1.4.1.10428 9 1.101.23.51.28.2.4
                fkGponProfile2PortMgmtControlTimeStamp OBJECT-TYPE
                        SYNTAX TimeTicks
                        MAX-ACCESS read-only
                        STATUS current
                        DESCRIPTION
                                "The time stamp of the last command(end of command)"
                        ::= { fkGponProfile2PortMgmtControl 4 }

                
                -- 1.3.6.1.4.1.10428 9 1.101.23.51.28.2.5
                fkGponProfile2PortMgmtControlReqResult OBJECT-TYPE
                        SYNTAX FkControlRequestResultType
                        MAX-ACCESS read-only
                        STATUS current
                        DESCRIPTION
                                "The result of the last user command"
                        ::= { fkGponProfile2PortMgmtControl 5 }

                
                -- 1.3.6.1.4.1.10428 9 1.101.23.51.28.2.6
                fkGponProfile2PortMgmtControlTName OBJECT-TYPE
                        SYNTAX OCTET STRING
                        MAX-ACCESS read-write
                        STATUS current
                        DESCRIPTION
                                "The Traffic profile name."
                        ::= { fkGponProfile2PortMgmtControl 6 }

                
                -- 1.3.6.1.4.1.10428 9 1.101.23.51.28.2.7
                fkGponProfile2PortMgmtControlSlotId OBJECT-TYPE
                        SYNTAX INTEGER
                                {
                                ethernet(1),
                                pots(2),
                                ces(3),
                                video(4)
                                }
                        MAX-ACCESS read-write
                        STATUS current
                        DESCRIPTION
                                "The Slot ID"
                        ::= { fkGponProfile2PortMgmtControl 7 }

                
                -- 1.3.6.1.4.1.10428 9 1.101.23.51.28.2.8
                fkGponProfile2PortMgmtControlPortId OBJECT-TYPE
                        SYNTAX Integer32 (1..32)
                        MAX-ACCESS read-write
                        STATUS current
                        DESCRIPTION
                                "The Port ID"
                        ::= { fkGponProfile2PortMgmtControl 8 }

                
                -- 1.3.6.1.4.1.10428 9 1.101.23.51.28.2.9
                fkGponProfile2PortMgmtControlMode OBJECT-TYPE
                        SYNTAX INTEGER
                                {
                                modeOMCI(0),
                                modeNonOMCI(1)
                                }
                        MAX-ACCESS read-write
                        STATUS current
                        DESCRIPTION
                                "The Mgmt mode.
                                0 : OMCI mode
                                1 : Non-OMCI mode"
                        ::= { fkGponProfile2PortMgmtControl 9 }

                
                -- 1.3.6.1.4.1.10428 9 1.101.23.51.28.2.10
                fkGponProfile2PortMgmtControlVirtualEthNum OBJECT-TYPE
                        SYNTAX Integer32 (1..32)
                        MAX-ACCESS read-write
                        STATUS current
                        DESCRIPTION
                                "Virtual Eth Number"
                        ::= { fkGponProfile2PortMgmtControl 10 }

                
                -- 1.3.6.1.4.1.10428 9 1.101.23.51.28.3
                fkGponProfile2PortMgmtNotification OBJECT IDENTIFIER ::= { fkGponProfile2PortMgmt 3 }

                
                -- 1.3.6.1.4.1.10428 9 1.101.23.51.28.3.1
                fkGponProfile2PortMgmtSetted NOTIFICATION-TYPE
                        OBJECTS { fkGponProfile2PortMgmtControlRequest, fkGponProfile2PortMgmtControlTimeStamp, fkGponProfile2PortMgmtControlReqResult, fkGponProfile2PortMgmtControlTName, fkGponProfile2PortMgmtControlSlotId, 
                                fkGponProfile2PortMgmtControlPortId, fkGponProfile2PortMgmtControlMode, fkGponProfile2PortMgmtControlVirtualEthNum }
                        STATUS current
                        DESCRIPTION 
                                "setPortMgmtMode"
                        ::= { fkGponProfile2PortMgmtNotification 1 }

                
                -- 1.3.6.1.4.1.10428 9 1.101.23.51.28.3.2
                fkGponProfile2PortMgmtUnsetted NOTIFICATION-TYPE
                        OBJECTS { fkGponProfile2PortMgmtControlRequest, fkGponProfile2PortMgmtControlTimeStamp, fkGponProfile2PortMgmtControlReqResult, fkGponProfile2PortMgmtControlTName, fkGponProfile2PortMgmtControlSlotId, 
                                fkGponProfile2PortMgmtControlPortId }
                        STATUS current
                        DESCRIPTION 
                                "unsetPortMgmtMode"
                        ::= { fkGponProfile2PortMgmtNotification 2 }

                
--  1.3.6.1.4.1.10428 9 1.101.23.51.9
                -- 1.3.6.1.4.1.10428 9 1.101.23.51.29
                fkGponProfile2McastAccessList OBJECT IDENTIFIER ::= { fkGponProfile2 29 }

                
--  1.3.6.1.4.1.10428 9 1.101.23.51.9.1
                -- 1.3.6.1.4.1.10428 9 1.101.23.51.29.1
                fkGponProfile2McastAccessListTable OBJECT-TYPE
                        SYNTAX SEQUENCE OF FkGponProfile2McastAccessListEntry
                        MAX-ACCESS not-accessible
                        STATUS current
                        DESCRIPTION
                                "fkGponProfile2McastTable"
                        ::= { fkGponProfile2McastAccessList 1 }

                
--  1.3.6.1.4.1.10428 9 1.101.23.51.9.1.1
                -- 1.3.6.1.4.1.10428 9 1.101.23.51.29.1.1
                fkGponProfile2McastAccessListEntry OBJECT-TYPE
                        SYNTAX FkGponProfile2McastAccessListEntry
                        MAX-ACCESS not-accessible
                        STATUS current
                        DESCRIPTION
                                "key: fkGponProfile2McastIndex"
                        INDEX { fkGponProfile2McastAccessListIndex }
                        ::= { fkGponProfile2McastAccessListTable 1 }

                
                FkGponProfile2McastAccessListEntry ::=
                        SEQUENCE { 
                                fkGponProfile2McastAccessListIndex
                                        Integer32,
                                fkGponProfile2McastAccessListName
                                        OCTET STRING
                         }

--  1.3.6.1.4.1.10428 9 1.101.23.51.9.1.1.1
                -- 1.3.6.1.4.1.10428 9 1.101.23.51.29.1.1.1
                fkGponProfile2McastAccessListIndex OBJECT-TYPE
                        SYNTAX Integer32 (1..65535)
                        MAX-ACCESS read-only
                        STATUS current
                        DESCRIPTION
                                "The Mcast access-list profile index."
                        ::= { fkGponProfile2McastAccessListEntry 1 }

                
--  1.3.6.1.4.1.10428 9 1.101.23.51.9.1.1.2
                -- 1.3.6.1.4.1.10428 9 1.101.23.51.29.1.1.2
                fkGponProfile2McastAccessListName OBJECT-TYPE
                        SYNTAX OCTET STRING
                        MAX-ACCESS read-only
                        STATUS current
                        DESCRIPTION
                                "The Mcast access-list profile name."
                        ::= { fkGponProfile2McastAccessListEntry 2 }

                
--  1.3.6.1.4.1.10428 9 1.101.23.51.9.2
                -- 1.3.6.1.4.1.10428 9 1.101.23.51.29.2
                fkGponProfile2McastAccessListControl OBJECT IDENTIFIER ::= { fkGponProfile2McastAccessList 2 }

                
--  1.3.6.1.4.1.10428 9 1.101.23.51.9.2.1
                -- 1.3.6.1.4.1.10428 9 1.101.23.51.29.2.1
                fkGponProfile2McastAccessListControlRequest OBJECT-TYPE
                        SYNTAX INTEGER
                                {
                                addMcastACL(1),
                                delMcastACL(2)
                                }
                        MAX-ACCESS read-write
                        STATUS current
                        DESCRIPTION
                                "The request of a user command"
                        ::= { fkGponProfile2McastAccessListControl 1 }

                
--  1.3.6.1.4.1.10428 9 1.101.23.51.9.2.2
                -- 1.3.6.1.4.1.10428 9 1.101.23.51.29.2.2
                fkGponProfile2McastAccessListControlStatus OBJECT-TYPE
                        SYNTAX FkControlStatusType
                        MAX-ACCESS read-write
                        STATUS current
                        DESCRIPTION
                                "The status of user command"
                        ::= { fkGponProfile2McastAccessListControl 2 }

                
--  1.3.6.1.4.1.10428 9 1.101.23.51.9.2.3
                -- 1.3.6.1.4.1.10428 9 1.101.23.51.29.2.3
                fkGponProfile2McastAccessListControlTimer OBJECT-TYPE
                        SYNTAX Gauge32
                        MAX-ACCESS read-write
                        STATUS current
                        DESCRIPTION
                                "The maximum time for the manager for a long running user command"
                        ::= { fkGponProfile2McastAccessListControl 3 }

                
--  1.3.6.1.4.1.10428 9 1.101.23.51.9.2.4
                -- 1.3.6.1.4.1.10428 9 1.101.23.51.29.2.4
                fkGponProfile2McastAccessListControlTimeStamp OBJECT-TYPE
                        SYNTAX TimeTicks
                        MAX-ACCESS read-write
                        STATUS current
                        DESCRIPTION
                                "The time stamp of the last command(end of command)"
                        ::= { fkGponProfile2McastAccessListControl 4 }

                
--  1.3.6.1.4.1.10428 9 1.101.23.51.9.2.5
                -- 1.3.6.1.4.1.10428 9 1.101.23.51.29.2.5
                fkGponProfile2McastAccessListControlReqResult OBJECT-TYPE
                        SYNTAX FkControlRequestResultType
                        MAX-ACCESS read-write
                        STATUS current
                        DESCRIPTION
                                "The result of the last user command"
                        ::= { fkGponProfile2McastAccessListControl 5 }

                
--  1.3.6.1.4.1.10428 9 1.101.23.51.9.2.6
                -- 1.3.6.1.4.1.10428 9 1.101.23.51.29.2.6
                fkGponProfile2McastAccessListControlName OBJECT-TYPE
                        SYNTAX OCTET STRING
                        MAX-ACCESS read-write
                        STATUS current
                        DESCRIPTION
                                "The Mcast access-list profile name."
                        ::= { fkGponProfile2McastAccessListControl 6 }

                
--  1.3.6.1.4.1.10428 9 1.101.23.51.9.3
                -- 1.3.6.1.4.1.10428 9 1.101.23.51.29.3
                fkGponProfile2McastAccessListNotification OBJECT IDENTIFIER ::= { fkGponProfile2McastAccessList 3 }

                
--  1.3.6.1.4.1.10428 9 1.101.23.51.9.3.1
                -- 1.3.6.1.4.1.10428 9 1.101.23.51.29.3.1
                fkGponProfile2McastAccessListAdded NOTIFICATION-TYPE
                        OBJECTS { fkGponProfile2McastControlRequest, fkGponProfile2McastControlTimeStamp, fkGponProfile2McastControlReqResult, fkGponProfile2McastControlName }
                        STATUS current
                        DESCRIPTION 
                                "addMcastACL"
                        ::= { fkGponProfile2McastAccessListNotification 1 }

                
--  1.3.6.1.4.1.10428 9 1.101.23.51.9.3.1
                -- 1.3.6.1.4.1.10428 9 1.101.23.51.29.3.2
                fkGponProfile2McastAccessListDeleted NOTIFICATION-TYPE
                        OBJECTS { fkGponProfile2McastControlRequest, fkGponProfile2McastControlTimeStamp, fkGponProfile2McastControlReqResult, fkGponProfile2McastControlName }
                        STATUS current
                        DESCRIPTION 
                                "delMcastACL"
                        ::= { fkGponProfile2McastAccessListNotification 2 }

                
--  1.3.6.1.4.1.10428 9 1.101.23.51.10
                -- 1.3.6.1.4.1.10428 9 1.101.23.51.30
                fkGponProfile2McastAccessListDynamic OBJECT IDENTIFIER ::= { fkGponProfile2 30 }

                
--  1.3.6.1.4.1.10428 9 1.101.23.51.10.1
                -- 1.3.6.1.4.1.10428 9 1.101.23.51.30.1
                fkGponProfile2McastAccessListDynamicTable OBJECT-TYPE
                        SYNTAX SEQUENCE OF FkGponProfile2McastAccessListDynamicEntry
                        MAX-ACCESS not-accessible
                        STATUS current
                        DESCRIPTION
                                "fkGponProfile2McastAclTable"
                        ::= { fkGponProfile2McastAccessListDynamic 1 }

                
--  1.3.6.1.4.1.10428 9 1.101.23.51.10.1.1
                -- 1.3.6.1.4.1.10428 9 1.101.23.51.30.1.1
                fkGponProfile2McastAccessListDynamicEntry OBJECT-TYPE
                        SYNTAX FkGponProfile2McastAccessListDynamicEntry
                        MAX-ACCESS not-accessible
                        STATUS current
                        DESCRIPTION
                                "key: fkGponProfile2McastIndex, fkGponProfile2McastAclIndex"
                        INDEX { fkGponProfile2McastAccessListIndex, fkGponProfile2McastAccessListDynamicIndex }
                        ::= { fkGponProfile2McastAccessListDynamicTable 1 }

                
                FkGponProfile2McastAccessListDynamicEntry ::=
                        SEQUENCE { 
                                fkGponProfile2McastAccessListDynamicIndex
                                        Integer32,
                                fkGponProfile2McastAccessListDynamicVid
                                        Integer32,
                                fkGponProfile2McastAccessListDynamicDstIpStart
                                        IpAddress,
                                fkGponProfile2McastAccessListDynamicDstIpEnd
                                        IpAddress,
                                fkGponProfile2McastAccessListDynamicSrcIp
                                        IpAddress,
                                fkGponProfile2McastAccessListDynamicBandwidth
                                        Integer32,
                                fkGponProfile2McastAccessListDynamicGem
                                        Integer32,
                                fkGponProfile2McastAccessListDynamicCos
                                        Integer32
                         }

--  1.3.6.1.4.1.10428 9 1.101.23.51.10.1.1.1
                -- 1.3.6.1.4.1.10428 9 1.101.23.51.30.1.1.1
                fkGponProfile2McastAccessListDynamicIndex OBJECT-TYPE
                        SYNTAX Integer32 (1..65535)
                        MAX-ACCESS read-only
                        STATUS current
                        DESCRIPTION
                                "The Mcast access-list dynamic index."
                        ::= { fkGponProfile2McastAccessListDynamicEntry 1 }

                
--  1.3.6.1.4.1.10428 9 1.101.23.51.10.1.1.2
                -- 1.3.6.1.4.1.10428 9 1.101.23.51.30.1.1.2
                fkGponProfile2McastAccessListDynamicVid OBJECT-TYPE
                        SYNTAX Integer32 (0 | 1..4094)
                        MAX-ACCESS read-write
                        STATUS current
                        DESCRIPTION
                                "This specific the VLAN carrying the multicast group DS"
                        ::= { fkGponProfile2McastAccessListDynamicEntry 2 }

                
--  1.3.6.1.4.1.10428 9 1.101.23.51.10.1.1.3
                -- 1.3.6.1.4.1.10428 9 1.101.23.51.30.1.1.3
                fkGponProfile2McastAccessListDynamicDstIpStart OBJECT-TYPE
                        SYNTAX IpAddress
                        MAX-ACCESS read-only
                        STATUS current
                        DESCRIPTION
                                "The destination IP range-start."
                        ::= { fkGponProfile2McastAccessListDynamicEntry 3 }

                
--  1.3.6.1.4.1.10428 9 1.101.23.51.10.1.1.4
                -- 1.3.6.1.4.1.10428 9 1.101.23.51.30.1.1.4
                fkGponProfile2McastAccessListDynamicDstIpEnd OBJECT-TYPE
                        SYNTAX IpAddress
                        MAX-ACCESS read-only
                        STATUS current
                        DESCRIPTION
                                "The destination IP range-end"
                        ::= { fkGponProfile2McastAccessListDynamicEntry 4 }

                
--  1.3.6.1.4.1.10428 9 1.101.23.51.10.1.1.5
                -- 1.3.6.1.4.1.10428 9 1.101.23.51.30.1.1.5
                fkGponProfile2McastAccessListDynamicSrcIp OBJECT-TYPE
                        SYNTAX IpAddress
                        MAX-ACCESS read-only
                        STATUS current
                        DESCRIPTION
                                "The source IP."
                        ::= { fkGponProfile2McastAccessListDynamicEntry 5 }

                
--  1.3.6.1.4.1.10428 9 1.101.23.51.10.1.1.6
                -- 1.3.6.1.4.1.10428 9 1.101.23.51.30.1.1.6
                fkGponProfile2McastAccessListDynamicBandwidth OBJECT-TYPE
                        SYNTAX Integer32
                        MAX-ACCESS read-only
                        STATUS current
                        DESCRIPTION
                                "The Imputed group bandwidth"
                        ::= { fkGponProfile2McastAccessListDynamicEntry 6 }

                
--  1.3.6.1.4.1.10428 9 1.101.23.51.10.1.1.7
                -- 1.3.6.1.4.1.10428 9 1.101.23.51.30.1.1.7
                fkGponProfile2McastAccessListDynamicGem OBJECT-TYPE
                        SYNTAX Integer32 (1..25)
                        MAX-ACCESS read-only
                        STATUS current
                        DESCRIPTION
                                "Th GEM port ID"
                        ::= { fkGponProfile2McastAccessListDynamicEntry 7 }

                
                -- 1.3.6.1.4.1.10428 9 1.101.23.51.30.1.1.8
                fkGponProfile2McastAccessListDynamicCos OBJECT-TYPE
                        SYNTAX Integer32 (0..7)
                        MAX-ACCESS read-only
                        STATUS current
                        DESCRIPTION
                                "The access-list CoS"
                        ::= { fkGponProfile2McastAccessListDynamicEntry 8 }

                
--  1.3.6.1.4.1.10428 9 1.101.23.51.10.2
                -- 1.3.6.1.4.1.10428 9 1.101.23.51.30.2
                fkGponProfile2McastAccessListDynamicControl OBJECT IDENTIFIER ::= { fkGponProfile2McastAccessListDynamic 2 }

                
--  1.3.6.1.4.1.10428 9 1.101.23.51.10.2.1
                -- 1.3.6.1.4.1.10428 9 1.101.23.51.30.2.1
                fkGponProfile2McastAccessListDynamicControlRequest OBJECT-TYPE
                        SYNTAX INTEGER
                                {
                                addMcastAclDynamic(1),
                                delMcastAclDynamic(2)
                                }
                        MAX-ACCESS read-write
                        STATUS current
                        DESCRIPTION
                                "The request of a user command"
                        ::= { fkGponProfile2McastAccessListDynamicControl 1 }

                
--  1.3.6.1.4.1.10428 9 1.101.23.51.10.2.2
                -- 1.3.6.1.4.1.10428 9 1.101.23.51.30.2.2
                fkGponProfile2McastAccessListDynamicControlStatus OBJECT-TYPE
                        SYNTAX FkControlStatusType
                        MAX-ACCESS read-write
                        STATUS current
                        DESCRIPTION
                                "The status of user command"
                        ::= { fkGponProfile2McastAccessListDynamicControl 2 }

                
--  1.3.6.1.4.1.10428 9 1.101.23.51.10.2.3
                -- 1.3.6.1.4.1.10428 9 1.101.23.51.30.2.3
                fkGponProfile2McastAccessListDynamicControlTimer OBJECT-TYPE
                        SYNTAX Gauge32
                        MAX-ACCESS read-write
                        STATUS current
                        DESCRIPTION
                                "The maximum time for the manager for a long running user command"
                        ::= { fkGponProfile2McastAccessListDynamicControl 3 }

                
--  1.3.6.1.4.1.10428 9 1.101.23.51.10.2.4
                -- 1.3.6.1.4.1.10428 9 1.101.23.51.30.2.4
                fkGponProfile2McastAccessListDynamicControlTimeStamp OBJECT-TYPE
                        SYNTAX TimeTicks
                        MAX-ACCESS read-write
                        STATUS current
                        DESCRIPTION
                                "The time stamp of the last command(end of command)"
                        ::= { fkGponProfile2McastAccessListDynamicControl 4 }

                
--  1.3.6.1.4.1.10428 9 1.101.23.51.10.2.5
                -- 1.3.6.1.4.1.10428 9 1.101.23.51.30.2.5
                fkGponProfile2McastAccessListDynamicControlReqResult OBJECT-TYPE
                        SYNTAX FkControlRequestResultType
                        MAX-ACCESS read-write
                        STATUS current
                        DESCRIPTION
                                "The result of the last user command
                                "
                        ::= { fkGponProfile2McastAccessListDynamicControl 5 }

                
--  1.3.6.1.4.1.10428 9 1.101.23.51.10.2.6
                -- 1.3.6.1.4.1.10428 9 1.101.23.51.30.2.6
                fkGponProfile2McastAccessListDynamicControlIndex OBJECT-TYPE
                        SYNTAX Integer32
                        MAX-ACCESS read-write
                        STATUS current
                        DESCRIPTION
                                "The Mcast access-list  dynamic index."
                        ::= { fkGponProfile2McastAccessListDynamicControl 6 }

                
--  1.3.6.1.4.1.10428 9 1.101.23.51.10.2.7
                -- 1.3.6.1.4.1.10428 9 1.101.23.51.30.2.7
                fkGponProfile2McastAccessListDynamicControlVid OBJECT-TYPE
                        SYNTAX Integer32 (0 | 1..4094)
                        MAX-ACCESS read-write
                        STATUS current
                        DESCRIPTION
                                "This specific the VLAN carrying the multicast group DS"
                        ::= { fkGponProfile2McastAccessListDynamicControl 7 }

                
--  1.3.6.1.4.1.10428 9 1.101.23.51.10.2.8
                -- 1.3.6.1.4.1.10428 9 1.101.23.51.30.2.8
                fkGponProfile2McastAccessListDynamicControlName OBJECT-TYPE
                        SYNTAX OCTET STRING
                        MAX-ACCESS read-write
                        STATUS current
                        DESCRIPTION
                                "The Mcast profile name."
                        ::= { fkGponProfile2McastAccessListDynamicControl 8 }

                
--  1.3.6.1.4.1.10428 9 1.101.23.51.10.2.9
                -- 1.3.6.1.4.1.10428 9 1.101.23.51.30.2.9
                fkGponProfile2McastAccessListDynamicControlDstIpStart OBJECT-TYPE
                        SYNTAX IpAddress
                        MAX-ACCESS read-write
                        STATUS current
                        DESCRIPTION
                                "The destination IP range-start."
                        ::= { fkGponProfile2McastAccessListDynamicControl 9 }

                
--  1.3.6.1.4.1.10428 9 1.101.23.51.10.2.10
                -- 1.3.6.1.4.1.10428 9 1.101.23.51.30.2.10
                fkGponProfile2McastAccessListDynamicControlDstIpEnd OBJECT-TYPE
                        SYNTAX IpAddress
                        MAX-ACCESS read-write
                        STATUS current
                        DESCRIPTION
                                "The destination IP range-end"
                        ::= { fkGponProfile2McastAccessListDynamicControl 10 }

                
--  1.3.6.1.4.1.10428 9 1.101.23.51.10.2.11
                -- 1.3.6.1.4.1.10428 9 1.101.23.51.30.2.11
                fkGponProfile2McastAccessListDynamicControlSrcIp OBJECT-TYPE
                        SYNTAX IpAddress
                        MAX-ACCESS read-write
                        STATUS current
                        DESCRIPTION
                                "The source IP."
                        ::= { fkGponProfile2McastAccessListDynamicControl 11 }

                
--  1.3.6.1.4.1.10428 9 1.101.23.51.10.2.12
                -- 1.3.6.1.4.1.10428 9 1.101.23.51.30.2.12
                fkGponProfile2McastAccessListDynamicControlBandwidth OBJECT-TYPE
                        SYNTAX Integer32
                        MAX-ACCESS read-write
                        STATUS current
                        DESCRIPTION
                                "The Imputed group bandwidth"
                        ::= { fkGponProfile2McastAccessListDynamicControl 12 }

                
--  1.3.6.1.4.1.10428 9 1.101.23.51.10.2.13
                -- 1.3.6.1.4.1.10428 9 1.101.23.51.30.2.13
                fkGponProfile2McastAccessListDynamicControlGem OBJECT-TYPE
                        SYNTAX Integer32 (1..25)
                        MAX-ACCESS read-write
                        STATUS current
                        DESCRIPTION
                                "The GEM port ID"
                        ::= { fkGponProfile2McastAccessListDynamicControl 13 }

                
                -- 1.3.6.1.4.1.10428 9 1.101.23.51.30.2.14
                fkGponProfile2McastAccessListDynamicControlCos OBJECT-TYPE
                        SYNTAX Integer32 (0..7)
                        MAX-ACCESS read-write
                        STATUS current
                        DESCRIPTION
                                "The access-list CoS"
                        ::= { fkGponProfile2McastAccessListDynamicControl 14 }

                
--  1.3.6.1.4.1.10428 9 1.101.23.51.10.3
                -- 1.3.6.1.4.1.10428 9 1.101.23.51.30.3
                fkGponProfile2McastAccessListDynamicNotification OBJECT IDENTIFIER ::= { fkGponProfile2McastAccessListDynamic 3 }

                
--  1.3.6.1.4.1.10428 9 1.101.23.51.10.3.1
                -- 1.3.6.1.4.1.10428 9 1.101.23.51.30.3.1
                fkGponProfile2McastAccessListDynamicAdded NOTIFICATION-TYPE
                        OBJECTS { fkGponProfile2McastAccessListDynamicControlRequest, fkGponProfile2McastAccessListDynamicControlTimeStamp, fkGponProfile2McastAccessListDynamicControlReqResult, fkGponProfile2McastAccessListDynamicControlVid, fkGponProfile2McastAccessListDynamicControlName, 
                                fkGponProfile2McastAccessListDynamicControlDstIpStart, fkGponProfile2McastAccessListDynamicControlDstIpEnd, fkGponProfile2McastAccessListDynamicControlSrcIp, fkGponProfile2McastAccessListDynamicControlBandwidth, fkGponProfile2McastAccessListDynamicControlGem, 
                                fkGponProfile2McastAccessListDynamicControlCos }
                        STATUS current
                        DESCRIPTION 
                                "addMcastAclDynamic"
                        ::= { fkGponProfile2McastAccessListDynamicNotification 1 }

                
--  1.3.6.1.4.1.10428 9 1.101.23.51.10.3.1
                -- 1.3.6.1.4.1.10428 9 1.101.23.51.30.3.2
                fkGponProfile2McastAccessListDynamicDeleted NOTIFICATION-TYPE
                        OBJECTS { fkGponProfile2McastAccessListDynamicControlRequest, fkGponProfile2McastAccessListDynamicControlTimeStamp, fkGponProfile2McastAccessListDynamicControlReqResult, fkGponProfile2McastAccessListDynamicControlVid, fkGponProfile2McastAccessListDynamicControlName
                                 }
                        STATUS current
                        DESCRIPTION 
                                "delMcastAclDynamic"
                        ::= { fkGponProfile2McastAccessListDynamicNotification 2 }

                
--  1.3.6.1.4.1.10428 9 1.101.23.51.10
                -- 1.3.6.1.4.1.10428 9 1.101.23.51.31
                fkGponProfile2McastAccessListStatic OBJECT IDENTIFIER ::= { fkGponProfile2 31 }

                
--  1.3.6.1.4.1.10428 9 1.101.23.51.10.1
                -- 1.3.6.1.4.1.10428 9 1.101.23.51.31.1
                fkGponProfile2McastAccessListStaticTable OBJECT-TYPE
                        SYNTAX SEQUENCE OF FkGponProfile2McastAccessListStaticEntry
                        MAX-ACCESS not-accessible
                        STATUS current
                        DESCRIPTION
                                "fkGponProfile2McastAclTable"
                        ::= { fkGponProfile2McastAccessListStatic 1 }

                
--  1.3.6.1.4.1.10428 9 1.101.23.51.10.1.1
                -- 1.3.6.1.4.1.10428 9 1.101.23.51.31.1.1
                fkGponProfile2McastAccessListStaticEntry OBJECT-TYPE
                        SYNTAX FkGponProfile2McastAccessListStaticEntry
                        MAX-ACCESS not-accessible
                        STATUS current
                        DESCRIPTION
                                "key: fkGponProfile2McastIndex, fkGponProfile2McastAclIndex"
                        INDEX { fkGponProfile2McastAccessListIndex, fkGponProfile2McastAccessListStaticIndex }
                        ::= { fkGponProfile2McastAccessListStaticTable 1 }

                
                FkGponProfile2McastAccessListStaticEntry ::=
                        SEQUENCE { 
                                fkGponProfile2McastAccessListStaticIndex
                                        Integer32,
                                fkGponProfile2McastAccessListStaticVid
                                        Integer32,
                                fkGponProfile2McastAccessListStaticDstIpStart
                                        IpAddress,
                                fkGponProfile2McastAccessListStaticDstIpEnd
                                        IpAddress,
                                fkGponProfile2McastAccessListStaticSrcIp
                                        IpAddress,
                                fkGponProfile2McastAccessListStaticBandwidth
                                        Integer32,
                                fkGponProfile2McastAccessListStaticGem
                                        Integer32,
                                fkGponProfile2McastAccessListStaticCos
                                        Integer32
                         }

--  1.3.6.1.4.1.10428 9 1.101.23.51.10.1.1.1
                -- 1.3.6.1.4.1.10428 9 1.101.23.51.31.1.1.1
                fkGponProfile2McastAccessListStaticIndex OBJECT-TYPE
                        SYNTAX Integer32 (1..65535)
                        MAX-ACCESS read-only
                        STATUS current
                        DESCRIPTION
                                "The Mcast access-list static index."
                        ::= { fkGponProfile2McastAccessListStaticEntry 1 }

                
--  1.3.6.1.4.1.10428 9 1.101.23.51.10.1.1.2
                -- 1.3.6.1.4.1.10428 9 1.101.23.51.31.1.1.2
                fkGponProfile2McastAccessListStaticVid OBJECT-TYPE
                        SYNTAX Integer32 (0 | 1..4094)
                        MAX-ACCESS read-write
                        STATUS current
                        DESCRIPTION
                                "This specific the VLAN carrying the multicast group DS"
                        ::= { fkGponProfile2McastAccessListStaticEntry 2 }

                
--  1.3.6.1.4.1.10428 9 1.101.23.51.10.1.1.3
                -- 1.3.6.1.4.1.10428 9 1.101.23.51.31.1.1.3
                fkGponProfile2McastAccessListStaticDstIpStart OBJECT-TYPE
                        SYNTAX IpAddress
                        MAX-ACCESS read-only
                        STATUS current
                        DESCRIPTION
                                "The destination IP range-start."
                        ::= { fkGponProfile2McastAccessListStaticEntry 3 }

                
--  1.3.6.1.4.1.10428 9 1.101.23.51.10.1.1.4
                -- 1.3.6.1.4.1.10428 9 1.101.23.51.31.1.1.4
                fkGponProfile2McastAccessListStaticDstIpEnd OBJECT-TYPE
                        SYNTAX IpAddress
                        MAX-ACCESS read-only
                        STATUS current
                        DESCRIPTION
                                "The destination IP range-end"
                        ::= { fkGponProfile2McastAccessListStaticEntry 4 }

                
--  1.3.6.1.4.1.10428 9 1.101.23.51.10.1.1.5
                -- 1.3.6.1.4.1.10428 9 1.101.23.51.31.1.1.5
                fkGponProfile2McastAccessListStaticSrcIp OBJECT-TYPE
                        SYNTAX IpAddress
                        MAX-ACCESS read-only
                        STATUS current
                        DESCRIPTION
                                "The source IP."
                        ::= { fkGponProfile2McastAccessListStaticEntry 5 }

                
--  1.3.6.1.4.1.10428 9 1.101.23.51.10.1.1.6
                -- 1.3.6.1.4.1.10428 9 1.101.23.51.31.1.1.6
                fkGponProfile2McastAccessListStaticBandwidth OBJECT-TYPE
                        SYNTAX Integer32
                        MAX-ACCESS read-only
                        STATUS current
                        DESCRIPTION
                                "The Imputed group bandwidth"
                        ::= { fkGponProfile2McastAccessListStaticEntry 6 }

                
--  1.3.6.1.4.1.10428 9 1.101.23.51.10.1.1.7
                -- 1.3.6.1.4.1.10428 9 1.101.23.51.31.1.1.7
                fkGponProfile2McastAccessListStaticGem OBJECT-TYPE
                        SYNTAX Integer32 (1..25)
                        MAX-ACCESS read-only
                        STATUS current
                        DESCRIPTION
                                "Th GEM port ID"
                        ::= { fkGponProfile2McastAccessListStaticEntry 7 }

                
                -- 1.3.6.1.4.1.10428 9 1.101.23.51.31.1.1.8
                fkGponProfile2McastAccessListStaticCos OBJECT-TYPE
                        SYNTAX Integer32 (0..7)
                        MAX-ACCESS read-only
                        STATUS current
                        DESCRIPTION
                                "The access-list CoS"
                        ::= { fkGponProfile2McastAccessListStaticEntry 8 }

                
--  1.3.6.1.4.1.10428 9 1.101.23.51.10.2
                -- 1.3.6.1.4.1.10428 9 1.101.23.51.31.2
                fkGponProfile2McastAccessListStaticControl OBJECT IDENTIFIER ::= { fkGponProfile2McastAccessListStatic 2 }

                
--  1.3.6.1.4.1.10428 9 1.101.23.51.10.2.1
                -- 1.3.6.1.4.1.10428 9 1.101.23.51.31.2.1
                fkGponProfile2McastAccessListStaticControlRequest OBJECT-TYPE
                        SYNTAX INTEGER
                                {
                                addMcastAclStatic(1),
                                delMcastAclStatic(2)
                                }
                        MAX-ACCESS read-write
                        STATUS current
                        DESCRIPTION
                                "The request of a user command"
                        ::= { fkGponProfile2McastAccessListStaticControl 1 }

                
--  1.3.6.1.4.1.10428 9 1.101.23.51.10.2.2
                -- 1.3.6.1.4.1.10428 9 1.101.23.51.31.2.2
                fkGponProfile2McastAccessListStaticControlStatus OBJECT-TYPE
                        SYNTAX FkControlStatusType
                        MAX-ACCESS read-write
                        STATUS current
                        DESCRIPTION
                                "The status of user command"
                        ::= { fkGponProfile2McastAccessListStaticControl 2 }

                
--  1.3.6.1.4.1.10428 9 1.101.23.51.10.2.3
                -- 1.3.6.1.4.1.10428 9 1.101.23.51.31.2.3
                fkGponProfile2McastAccessListStaticControlTimer OBJECT-TYPE
                        SYNTAX Gauge32
                        MAX-ACCESS read-write
                        STATUS current
                        DESCRIPTION
                                "The maximum time for the manager for a long running user command"
                        ::= { fkGponProfile2McastAccessListStaticControl 3 }

                
--  1.3.6.1.4.1.10428 9 1.101.23.51.10.2.4
                -- 1.3.6.1.4.1.10428 9 1.101.23.51.31.2.4
                fkGponProfile2McastAccessListStaticControlTimeStamp OBJECT-TYPE
                        SYNTAX TimeTicks
                        MAX-ACCESS read-write
                        STATUS current
                        DESCRIPTION
                                "The time stamp of the last command(end of command)"
                        ::= { fkGponProfile2McastAccessListStaticControl 4 }

                
--  1.3.6.1.4.1.10428 9 1.101.23.51.10.2.5
                -- 1.3.6.1.4.1.10428 9 1.101.23.51.31.2.5
                fkGponProfile2McastAccessListStaticControlReqResult OBJECT-TYPE
                        SYNTAX FkControlRequestResultType
                        MAX-ACCESS read-write
                        STATUS current
                        DESCRIPTION
                                "The result of the last user command
                                "
                        ::= { fkGponProfile2McastAccessListStaticControl 5 }

                
--  1.3.6.1.4.1.10428 9 1.101.23.51.10.2.6
                -- 1.3.6.1.4.1.10428 9 1.101.23.51.31.2.6
                fkGponProfile2McastAccessListStaticControlIndex OBJECT-TYPE
                        SYNTAX Integer32
                        MAX-ACCESS read-write
                        STATUS current
                        DESCRIPTION
                                "The Mcast access-list  static index."
                        ::= { fkGponProfile2McastAccessListStaticControl 6 }

                
--  1.3.6.1.4.1.10428 9 1.101.23.51.10.2.7
                -- 1.3.6.1.4.1.10428 9 1.101.23.51.31.2.7
                fkGponProfile2McastAccessListStaticControlVid OBJECT-TYPE
                        SYNTAX Integer32 (0 | 1..4094)
                        MAX-ACCESS read-write
                        STATUS current
                        DESCRIPTION
                                "This specific the VLAN carrying the multicast group DS"
                        ::= { fkGponProfile2McastAccessListStaticControl 7 }

                
--  1.3.6.1.4.1.10428 9 1.101.23.51.10.2.8
                -- 1.3.6.1.4.1.10428 9 1.101.23.51.31.2.8
                fkGponProfile2McastAccessListStaticControlName OBJECT-TYPE
                        SYNTAX OCTET STRING
                        MAX-ACCESS read-write
                        STATUS current
                        DESCRIPTION
                                "The Mcast profile name."
                        ::= { fkGponProfile2McastAccessListStaticControl 8 }

                
--  1.3.6.1.4.1.10428 9 1.101.23.51.10.2.9
                -- 1.3.6.1.4.1.10428 9 1.101.23.51.31.2.9
                fkGponProfile2McastAccessListStaticControlDstIpStart OBJECT-TYPE
                        SYNTAX IpAddress
                        MAX-ACCESS read-write
                        STATUS current
                        DESCRIPTION
                                "The destination IP range-start."
                        ::= { fkGponProfile2McastAccessListStaticControl 9 }

                
--  1.3.6.1.4.1.10428 9 1.101.23.51.10.2.10
                -- 1.3.6.1.4.1.10428 9 1.101.23.51.31.2.10
                fkGponProfile2McastAccessListStaticControlDstIpEnd OBJECT-TYPE
                        SYNTAX IpAddress
                        MAX-ACCESS read-write
                        STATUS current
                        DESCRIPTION
                                "The destination IP range-end"
                        ::= { fkGponProfile2McastAccessListStaticControl 10 }

                
--  1.3.6.1.4.1.10428 9 1.101.23.51.10.2.11
                -- 1.3.6.1.4.1.10428 9 1.101.23.51.31.2.11
                fkGponProfile2McastAccessListStaticControlSrcIp OBJECT-TYPE
                        SYNTAX IpAddress
                        MAX-ACCESS read-write
                        STATUS current
                        DESCRIPTION
                                "The source IP."
                        ::= { fkGponProfile2McastAccessListStaticControl 11 }

                
--  1.3.6.1.4.1.10428 9 1.101.23.51.10.2.12
                -- 1.3.6.1.4.1.10428 9 1.101.23.51.31.2.12
                fkGponProfile2McastAccessListStaticControlBandwidth OBJECT-TYPE
                        SYNTAX Integer32
                        MAX-ACCESS read-write
                        STATUS current
                        DESCRIPTION
                                "The Imputed group bandwidth"
                        ::= { fkGponProfile2McastAccessListStaticControl 12 }

                
--  1.3.6.1.4.1.10428 9 1.101.23.51.10.2.13
                -- 1.3.6.1.4.1.10428 9 1.101.23.51.31.2.13
                fkGponProfile2McastAccessListStaticControlGem OBJECT-TYPE
                        SYNTAX Integer32 (1..25)
                        MAX-ACCESS read-write
                        STATUS current
                        DESCRIPTION
                                "The GEM port ID"
                        ::= { fkGponProfile2McastAccessListStaticControl 13 }

                
                -- 1.3.6.1.4.1.10428 9 1.101.23.51.31.2.14
                fkGponProfile2McastAccessListStaticControlCos OBJECT-TYPE
                        SYNTAX Integer32 (0..7)
                        MAX-ACCESS read-write
                        STATUS current
                        DESCRIPTION
                                "The access-list CoS"
                        ::= { fkGponProfile2McastAccessListStaticControl 14 }

                
--  1.3.6.1.4.1.10428 9 1.101.23.51.10.3
                -- 1.3.6.1.4.1.10428 9 1.101.23.51.31.3
                fkGponProfile2McastAccessListStaticControlNotification OBJECT IDENTIFIER ::= { fkGponProfile2McastAccessListStatic 3 }

                
--  1.3.6.1.4.1.10428 9 1.101.23.51.10.3.1
                -- 1.3.6.1.4.1.10428 9 1.101.23.51.31.3.1
                fkGponProfile2McastAccessListStaticControlAdded NOTIFICATION-TYPE
                        OBJECTS { fkGponProfile2McastAccessListStaticControlRequest, fkGponProfile2McastAccessListStaticControlTimeStamp, fkGponProfile2McastAccessListStaticControlReqResult, fkGponProfile2McastAccessListStaticControlVid, fkGponProfile2McastAccessListStaticControlName, 
                                fkGponProfile2McastAccessListStaticControlDstIpStart, fkGponProfile2McastAccessListStaticControlDstIpEnd, fkGponProfile2McastAccessListStaticControlSrcIp, fkGponProfile2McastAccessListStaticControlBandwidth, fkGponProfile2McastAccessListStaticControlGem, 
                                fkGponProfile2McastAccessListStaticControlCos }
                        STATUS current
                        DESCRIPTION 
                                "addMcastAclStatic"
                        ::= { fkGponProfile2McastAccessListStaticControlNotification 1 }

                
--  1.3.6.1.4.1.10428 9 1.101.23.51.10.3.1
                -- 1.3.6.1.4.1.10428 9 1.101.23.51.31.3.2
                fkGponProfile2McastAccessListStaticControlDeleted NOTIFICATION-TYPE
                        OBJECTS { fkGponProfile2McastAccessListStaticControlRequest, fkGponProfile2McastAccessListStaticControlTimeStamp, fkGponProfile2McastAccessListStaticControlReqResult, fkGponProfile2McastAccessListStaticControlVid, fkGponProfile2McastAccessListStaticControlName
                                 }
                        STATUS current
                        DESCRIPTION 
                                "delMcastAclStatic"
                        ::= { fkGponProfile2McastAccessListStaticControlNotification 2 }

                
                -- 1.3.6.1.4.1.10428 9 1.101.23.51.32
                fkGponProfile2RateLimit OBJECT IDENTIFIER ::= { fkGponProfile2 32 }

                
                -- 1.3.6.1.4.1.10428 9 1.101.23.51.32.1
                fkGponProfile2RateLimitTable OBJECT-TYPE
                        SYNTAX SEQUENCE OF FkGponProfile2RateLimitEntry
                        MAX-ACCESS not-accessible
                        STATUS current
                        DESCRIPTION
                                "Description."
                        ::= { fkGponProfile2RateLimit 1 }

                
                -- 1.3.6.1.4.1.10428 9 1.101.23.51.32.1.1
                fkGponProfile2RateLimitEntry OBJECT-TYPE
                        SYNTAX FkGponProfile2RateLimitEntry
                        MAX-ACCESS not-accessible
                        STATUS current
                        DESCRIPTION
                                "Description."
                        INDEX { fkGponProfile2RateLimitIndex }
                        ::= { fkGponProfile2RateLimitTable 1 }

                
                FkGponProfile2RateLimitEntry ::=
                        SEQUENCE { 
                                fkGponProfile2RateLimitIndex
                                        Integer32,
                                fkGponProfile2RateLimitName
                                        Integer32,
                                fkGponProfile2RateLimitUpPir
                                        Integer32,
                                fkGponProfile2RateLimitUpSir
                                        Integer32,
                                fkGponProfile2RateLimitDownPir
                                        Integer32,
                                fkGponProfile2RateLimitDownSir
                                        Integer32
                         }

                -- 1.3.6.1.4.1.10428 9 1.101.23.51.32.1.1.1
                fkGponProfile2RateLimitIndex OBJECT-TYPE
                        SYNTAX Integer32 (0..65535)
                        MAX-ACCESS read-only
                        STATUS current
                        DESCRIPTION
                                "The rate limit index."
                        ::= { fkGponProfile2RateLimitEntry 1 }

                
                -- 1.3.6.1.4.1.10428 9 1.101.23.51.32.1.1.2
                fkGponProfile2RateLimitName OBJECT-TYPE
                        SYNTAX Integer32
                        MAX-ACCESS read-only
                        STATUS current
                        DESCRIPTION
                                "The rate limit name."
                        ::= { fkGponProfile2RateLimitEntry 2 }

                
--  1.3.6.1.4.1.10428 9 1.101.23.51.6.1.1.11
                -- 1.3.6.1.4.1.10428 9 1.101.23.51.32.1.1.3
                fkGponProfile2RateLimitUpPir OBJECT-TYPE
                        SYNTAX Integer32
                        MAX-ACCESS read-only
                        STATUS current
                        DESCRIPTION
                                "The upload rate-limit control : SIR (Bandwidth in steps of 64Kbps)"
                        ::= { fkGponProfile2RateLimitEntry 3 }

                
--  1.3.6.1.4.1.10428 9 1.101.23.51.6.1.1.10
                -- 1.3.6.1.4.1.10428 9 1.101.23.51.32.1.1.4
                fkGponProfile2RateLimitUpSir OBJECT-TYPE
                        SYNTAX Integer32
                        MAX-ACCESS read-only
                        STATUS current
                        DESCRIPTION
                                "The upload rate-limit control : SIR (Bandwidth in steps of 64Kbps)"
                        ::= { fkGponProfile2RateLimitEntry 4 }

                
--  1.3.6.1.4.1.10428 9 1.101.23.51.6.1.1.9
                -- 1.3.6.1.4.1.10428 9 1.101.23.51.32.1.1.5
                fkGponProfile2RateLimitDownPir OBJECT-TYPE
                        SYNTAX Integer32
                        MAX-ACCESS read-only
                        STATUS current
                        DESCRIPTION
                                "The download rate-limit control : PIR (Bandwidth in steps of 64Kbps)"
                        ::= { fkGponProfile2RateLimitEntry 5 }

                
--  1.3.6.1.4.1.10428 9 1.101.23.51.6.1.1.8
                -- 1.3.6.1.4.1.10428 9 1.101.23.51.32.1.1.6
                fkGponProfile2RateLimitDownSir OBJECT-TYPE
                        SYNTAX Integer32
                        MAX-ACCESS read-only
                        STATUS current
                        DESCRIPTION
                                "The download rate-limit control : SIR (Bandwidth in steps of 64Kbps)"
                        ::= { fkGponProfile2RateLimitEntry 6 }

                
--  1.3.6.1.4.1.10428 9 1.101.23.51.6.2
                -- 1.3.6.1.4.1.10428 9 1.101.23.51.32.2
                fkGponProfile2RateLimitControl OBJECT IDENTIFIER ::= { fkGponProfile2RateLimit 2 }

                
--  1.3.6.1.4.1.10428 9 1.101.23.51.6.2.1
                -- 1.3.6.1.4.1.10428 9 1.101.23.51.32.2.1
                fkGponProfile2RateLimitControlRequest OBJECT-TYPE
                        SYNTAX INTEGER
                                {
                                addRateLimitProfile(1),
                                delRateLimitProfile(2),
                                setRateLimitProfile(3)
                                }
                        MAX-ACCESS read-write
                        STATUS current
                        DESCRIPTION
                                "The request of a user command"
                        ::= { fkGponProfile2RateLimitControl 1 }

                
--  1.3.6.1.4.1.10428 9 1.101.23.51.6.2.2
                -- 1.3.6.1.4.1.10428 9 1.101.23.51.32.2.2
                fkGponProfile2RateLimitControlStatus OBJECT-TYPE
                        SYNTAX FkControlStatusType
                        MAX-ACCESS read-write
                        STATUS current
                        DESCRIPTION
                                "The status of user command"
                        ::= { fkGponProfile2RateLimitControl 2 }

                
--  1.3.6.1.4.1.10428 9 1.101.23.51.6.2.3
                -- 1.3.6.1.4.1.10428 9 1.101.23.51.32.2.3
                fkGponProfile2RateLimitControlTimer OBJECT-TYPE
                        SYNTAX Gauge32
                        MAX-ACCESS read-write
                        STATUS current
                        DESCRIPTION
                                "The maximum time for the manager for a long running user command"
                        ::= { fkGponProfile2RateLimitControl 3 }

                
--  1.3.6.1.4.1.10428 9 1.101.23.51.6.2.4
                -- 1.3.6.1.4.1.10428 9 1.101.23.51.32.2.4
                fkGponProfile2RateLimitControlTimeStamp OBJECT-TYPE
                        SYNTAX TimeTicks
                        MAX-ACCESS read-write
                        STATUS current
                        DESCRIPTION
                                "The time stamp of the last command(end of command)"
                        ::= { fkGponProfile2RateLimitControl 4 }

                
--  1.3.6.1.4.1.10428 9 1.101.23.51.6.2.5
                -- 1.3.6.1.4.1.10428 9 1.101.23.51.32.2.5
                fkGponProfile2RateLimitControlReqResult OBJECT-TYPE
                        SYNTAX FkControlRequestResultType
                        MAX-ACCESS read-write
                        STATUS current
                        DESCRIPTION
                                "The result of the last user command"
                        ::= { fkGponProfile2RateLimitControl 5 }

                
--  1.3.6.1.4.1.10428 9 1.101.23.51.6.2.6
                -- 1.3.6.1.4.1.10428 9 1.101.23.51.32.2.6
                fkGponProfile2RateLimitControlName OBJECT-TYPE
                        SYNTAX OCTET STRING
                        MAX-ACCESS read-write
                        STATUS current
                        DESCRIPTION
                                "The rate limit name."
                        ::= { fkGponProfile2RateLimitControl 6 }

                
--  1.3.6.1.4.1.10428 9 1.101.23.51.6.2.18
                -- 1.3.6.1.4.1.10428 9 1.101.23.51.32.2.7
                fkGponProfile2RateLimitControlUpPir OBJECT-TYPE
                        SYNTAX Integer32
                        MAX-ACCESS read-write
                        STATUS current
                        DESCRIPTION
                                "The upload rate-limit control : SIR (Bandwidth in steps of 64Kbps)"
                        ::= { fkGponProfile2RateLimitControl 7 }

                
--  1.3.6.1.4.1.10428 9 1.101.23.51.6.2.17
                -- 1.3.6.1.4.1.10428 9 1.101.23.51.32.2.8
                fkGponProfile2RateLimitControlUpSir OBJECT-TYPE
                        SYNTAX Integer32
                        MAX-ACCESS read-write
                        STATUS current
                        DESCRIPTION
                                "The upload rate-limit control : SIR (Bandwidth in steps of 64Kbps)"
                        ::= { fkGponProfile2RateLimitControl 8 }

                
--  1.3.6.1.4.1.10428 9 1.101.23.51.6.2.16
                -- 1.3.6.1.4.1.10428 9 1.101.23.51.32.2.9
                fkGponProfile2RateLimitControlDownPir OBJECT-TYPE
                        SYNTAX Integer32
                        MAX-ACCESS read-write
                        STATUS current
                        DESCRIPTION
                                "The download rate-limit control : PIR (Bandwidth in steps of 64Kbps)"
                        ::= { fkGponProfile2RateLimitControl 9 }

                
--  1.3.6.1.4.1.10428 9 1.101.23.51.6.2.15
                -- 1.3.6.1.4.1.10428 9 1.101.23.51.32.2.10
                fkGponProfile2RateLimitControlDownSir OBJECT-TYPE
                        SYNTAX Integer32
                        MAX-ACCESS read-write
                        STATUS current
                        DESCRIPTION
                                "The download rate-limit control : SIR (Bandwidth in steps of 64Kbps)"
                        ::= { fkGponProfile2RateLimitControl 10 }

                
                -- 1.3.6.1.4.1.10428 9 1.101.23.51.32.3
                fkGponProfile2RateLimitNotification OBJECT IDENTIFIER ::= { fkGponProfile2RateLimit 3 }

                
                -- 1.3.6.1.4.1.10428 9 1.101.23.51.32.3.1
                fkGponProfile2RateLimitProfileCreated NOTIFICATION-TYPE
                        OBJECTS { fkGponProfile2RateLimitControlRequest, fkGponProfile2RateLimitControlTimeStamp, fkGponProfile2RateLimitControlReqResult, fkGponProfile2RateLimitControlName, fkGponProfile2RateLimitControlDownSir, 
                                fkGponProfile2RateLimitControlDownPir, fkGponProfile2RateLimitControlUpSir, fkGponProfile2RateLimitControlUpPir }
                        STATUS current
                        DESCRIPTION 
                                "addRateLimitProfile"
                        ::= { fkGponProfile2RateLimitNotification 1 }

                
                -- 1.3.6.1.4.1.10428 9 1.101.23.51.32.3.2
                fkGponProfile2RateLimitProfileDeleted NOTIFICATION-TYPE
                        OBJECTS { fkGponProfile2RateLimitControlRequest, fkGponProfile2RateLimitControlTimeStamp, fkGponProfile2RateLimitControlReqResult, fkGponProfile2RateLimitControlName }
                        STATUS current
                        DESCRIPTION 
                                "delRateLimitProfile"
                        ::= { fkGponProfile2RateLimitNotification 2 }

                
                -- 1.3.6.1.4.1.10428 9 1.101.23.51.32.3.3
                fkGponProfile2RateLimitProfileChanged NOTIFICATION-TYPE
                        OBJECTS { fkGponProfile2RateLimitControlRequest, fkGponProfile2RateLimitControlTimeStamp, fkGponProfile2RateLimitControlReqResult, fkGponProfile2RateLimitControlName, fkGponProfile2RateLimitControlDownSir, 
                                fkGponProfile2RateLimitControlDownPir, fkGponProfile2RateLimitControlUpSir, fkGponProfile2RateLimitControlUpPir }
                        STATUS current
                        DESCRIPTION 
                                "setRateLimitProfile"
                        ::= { fkGponProfile2RateLimitNotification 3 }

                
--   1.3.6.1.4.1.10428 9 1.101.23.12
-- 1.3.6.1.4.1.10428 9 1.101.23.53
                -- 1.3.6.1.4.1.10428 9 1.101.23.53
                fkGponGroup OBJECT-GROUP
                        OBJECTS { fkGponProfile2DbaName, fkGponProfile2DbaMode, fkGponProfile2DbaSlaAssured, fkGponProfile2DbaSlaFixed, fkGponProfile2DbaSlaMax, 
                                fkGponProfile2DbaSlaMaxFlags, fkGponProfile2DbaControlRequest, fkGponProfile2DbaControlStatus, fkGponProfile2DbaControlTimer, fkGponProfile2DbaControlTimeStamp, 
                                fkGponProfile2DbaControlReqResult, fkGponProfile2DbaControlName, fkGponProfile2DbaControlMode, fkGponProfile2DbaControlSlaAssured, fkGponProfile2DbaControlSlaFixed, 
                                fkGponProfile2DbaControlSlaMax, fkGponProfile2DbaControlSlaMaxFlags, fkGponProfile2TrafficName, fkGponProfile2TrafficControlRequest, fkGponProfile2TrafficControlStatus, 
                                fkGponProfile2TrafficControlTimer, fkGponProfile2TrafficControlTimeStamp, fkGponProfile2TrafficControlReqResult, fkGponProfile2TrafficControlName, fkGponProfile2MapperId, 
                                fkGponProfile2MapperGemportCount, fkGponProfile2MapperDefaultCoS, fkGponProfile2MapperDscp2Pbit, fkGponProfile2MapperCos0, fkGponProfile2MapperCos1, 
                                fkGponProfile2MapperCos2, fkGponProfile2MapperCos3, fkGponProfile2MapperCos4, fkGponProfile2MapperCos5, fkGponProfile2MapperCos6, 
                                fkGponProfile2MapperCos7, fkGponProfile2MapperControlRequest, fkGponProfile2MapperControlStatus, fkGponProfile2MapperControlTimer, fkGponProfile2MapperControlTimeStamp, 
                                fkGponProfile2MapperControlReqResult, fkGponProfile2MapperControlTName, fkGponProfile2MapperControlId, fkGponProfile2MapperControlGemportCount, fkGponProfile2MapperControlDefaultCoS, 
                                fkGponProfile2MapperControlDscp2Pbit, fkGponProfile2MapperControlCosIndex, fkGponProfile2MapperControlCosGemport, fkGponProfile2BridgeId, fkGponProfile2BridgeMacLearning, 
                                fkGponProfile2BridgeMaxHost, fkGponProfile2BridgeMcastFlag, fkGponProfile2BridgeControlRequest, fkGponProfile2BridgeControlStatus, fkGponProfile2BridgeControlTimer, 
                                fkGponProfile2BridgeControlTimeStamp, fkGponProfile2BridgeControlReqResult, fkGponProfile2BridgeControlTName, fkGponProfile2BridgeControlId, fkGponProfile2BridgeControlMacLearning, 
                                fkGponProfile2BridgeAniId, fkGponProfile2BridgeAniVlanFilterMode, fkGponProfile2BridgeAniVlanFilter, fkGponProfile2BridgeAniControlRequest, fkGponProfile2BridgeAniControlStatus, 
                                fkGponProfile2BridgeAniControlTimer, fkGponProfile2BridgeAniControlTimeStamp, fkGponProfile2BridgeAniControlReqResult, fkGponProfile2BridgeAniControlTName, fkGponProfile2BridgeAniControlBridgeId, 
                                fkGponProfile2BridgeAniControlId, fkGponProfile2BridgeAniControlVlanFilterMode, fkGponProfile2BridgeAniControlVlanFilter, fkGponProfile2BridgeUniType, fkGponProfile2BridgeUniId, 
                                fkGponProfile2BridgeUniVlanOpDsOperFlag, fkGponProfile2BridgeUniVlanOpUsOperFlag, fkGponProfile2BridgeUniVlanOpUsOperVid, fkGponProfile2BridgeUniVlanOpUsOperCos, fkGponProfile2BridgeUniPortAdmin, 
                                fkGponProfile2BridgeUniRateLimitDownSir, fkGponProfile2BridgeUniRateLimitDownPir, fkGponProfile2BridgeUniRateLimitUpSir, fkGponProfile2BridgeUniRateLimitUpPir, fkGponProfile2BridgeUniIgmpMaxGroup, 
                                fkGponProfile2BridgeUniMaxFrame, fkGponProfile2BridgeUniMcastProfile, fkGponProfile2BridgeUniVlanFilterMode, fkGponProfile2BridgeUniVlanFilter, fkGponProfile2BridgeUniControlRequest, 
                                fkGponProfile2BridgeUniControlStatus, fkGponProfile2BridgeUniControlTimer, fkGponProfile2BridgeUniControlTimeStamp, fkGponProfile2BridgeUniControlReqResult, fkGponProfile2BridgeUniControlTName, 
                                fkGponProfile2BridgeUniControlBridgeId, fkGponProfile2BridgeUniControlType, fkGponProfile2BridgeUniControlId, fkGponProfile2BridgeUniControlVlanOpDsOperFlag, fkGponProfile2BridgeUniControlVlanOpUsOperFlag, 
                                fkGponProfile2BridgeUniControlVlanOpUsOperVid, fkGponProfile2BridgeUniControlVlanOpUsOperCos, fkGponProfile2BridgeUniControlPortAdmin, fkGponProfile2BridgeUniControlRateLimitDownSir, fkGponProfile2BridgeUniControlRateLimitDownPir, 
                                fkGponProfile2BridgeUniControlRateLimitUpSir, fkGponProfile2BridgeUniControlRateLimitUpPir, fkGponProfile2BridgeUniControlIgmpMaxGroup, fkGponProfile2BridgeUniControlMaxFrame, fkGponProfile2BridgeUniControlMcastProfile, 
                                fkGponProfile2BridgeUniControlVlanFilterMode, fkGponProfile2BridgeUniControlVlanFilter, fkGponProfile2TcontId, fkGponProfile2TcontDbaProfile, fkGponProfile2TcontGemportId, 
                                fkGponProfile2TcontGemportQueue, fkGponProfile2TcontGemportControlRequest, fkGponProfile2TcontGemportControlStatus, fkGponProfile2TcontGemportControlTimer, fkGponProfile2TcontGemportControlTimeStamp, 
                                fkGponProfile2TcontGemportControlReqResult, fkGponProfile2TcontGemportControlTName, fkGponProfile2TcontGemportControlTcontId, fkGponProfile2TcontGemportControlId, fkGponProfile2TcontGemportControlQueue, 
                                fkGponProfile2McastName, fkGponProfile2McastIgmpFunc, fkGponProfile2McastIgmpImmLeave, fkGponProfile2McastIgmpRobust, fkGponProfile2McastIgmpQuerierAddress, 
                                fkGponProfile2McastIgmpQuerierMaxRespTime, fkGponProfile2McastIgmpQuerierInterval, fkGponProfile2McastIgmpVersion, fkGponProfile2McastIgmpUpRateLimit, fkGponProfile2McastIgmpTagCtrl, 
                                fkGponProfile2McastIgmpTagCtrlVid, fkGponProfile2McastIgmpTagCtrlCos, fkGponProfile2McastControlRequest, fkGponProfile2McastControlStatus, fkGponProfile2McastControlTimer, 
                                fkGponProfile2McastControlTimeStamp, fkGponProfile2McastControlReqResult, fkGponProfile2McastControlName, fkGponProfile2McastControlIgmpFunc, fkGponProfile2McastControlIgmpImmLeave, 
                                fkGponProfile2McastControlIgmpRobust, fkGponProfile2McastControlIgmpQuerierAddress, fkGponProfile2McastControlIgmpQuerierMaxRespTime, fkGponProfile2McastControlIgmpQuerierInterval, fkGponProfile2McastControlIgmpVersion, 
                                fkGponProfile2McastControlIgmpUpRateLimit, fkGponProfile2McastControlIgmpTagCtrl, fkGponProfile2McastControlIgmpTagCtrlVid, fkGponProfile2McastControlIgmpTagCtrlCos, fkGponProfile2McastAclVid, 
                                fkGponProfile2McastAclDstIpStart, fkGponProfile2McastAclDstIpEnd, fkGponProfile2McastAclSrcIp, fkGponProfile2McastAclBandwidth, fkGponProfile2McastAclGem, 
                                fkGponProfile2McastAclControlRequest, fkGponProfile2McastAclControlStatus, fkGponProfile2McastAclControlTimer, fkGponProfile2McastAclControlTimeStamp, fkGponProfile2McastAclControlReqResult, 
                                fkGponProfile2McastAclControlVid, fkGponProfile2McastAclControlDstIpStart, fkGponProfile2McastAclControlDstIpEnd, fkGponProfile2McastAclControlSrcIp, fkGponProfile2McastAclControlBandwidth, 
                                fkGponProfile2McastAclControlGem, fkGponProfile2McastSAclVid, fkGponProfile2McastSAclDstIpStart, fkGponProfile2McastSAclDstIpEnd, fkGponProfile2McastSAclSrcIp, 
                                fkGponProfile2McastSAclBandwidth, fkGponProfile2McastSAclGem, fkGponProfile2McastSAclControlRequest, fkGponProfile2McastSAclControlStatus, fkGponProfile2McastSAclControlTimer, 
                                fkGponProfile2McastSAclControlTimeStamp, fkGponProfile2McastSAclControlReqResult, fkGponProfile2McastSAclControlVid, fkGponProfile2McastSAclControlDstIpStart, fkGponProfile2McastSAclControlDstIpEnd, 
                                fkGponProfile2McastSAclControlSrcIp, fkGponProfile2McastSAclControlBandwidth, fkGponProfile2McastSAclControlGem, fkGponCableDownStatus, fkGponCableDownRefCount, 
                                fkGponBaseControlRequest, fkGponBaseControlStatus, fkGponBaseControlTimer, fkGponBaseControlTimeStamp, fkGponBaseControlReqResult, 
                                fkGponBaseControlCableDownStatus, fkGponBaseControlCableDwonRefCnt, fkGponOltId, fkGponOltStatus, fkGponOltDiscoverySerialStart, 
                                fkGponOltLinkMaxDistance, fkGponOltKeyExchange, fkGponOltSignalCheck, fkGponOltSignalCheckAutoOnuBlock, fkGponOltDescription, 
                                fkGponOltAutoToManual, fkGponOltDefaultTcontDBAMode, fkGponOltDefaultTcontFixedBw, fkGponOltDefaultTcontAssuredBw, fkGponOltDefaultTcontMaxBw, 
                                fkGponOltDefaultProfileName, fkGponOltControlRequest, fkGponOltControlStatus, fkGponOltControlTimer, fkGponOltControlTimeStamp, 
                                fkGponOltControlReqResult, fkGponOltControllndex, fkGponOltControlDiscoverySerialStart, fkGponOltControlLinkMaxDistance, fkGponOltControlKeyExchange, 
                                fkGponOltControlSignalCheck, fkGponOltControlSignalCheckAutoOnuBlock, fkGponOltControlDescription, fkGponOltControlAutoToManual, fkGponOltControlDefaultTcontDBAMode, 
                                fkGponOltControlDefaultTcontFixedBw, fkGponOltControlDefaultTcontAssuredBw, fkGponOltControlDefaultTcontMaxBw, fkGponOltControlDefaultProfileName, fkGponOnuId, 
                                fkGponOnuStatus, fkGponOnuMode, fkGponOnuSerial, fkGponOnuPasswd, fkGponOnuPasswdMode, 
                                fkGponOnuEncMode, fkGponOnuProfile, fkGponOnuHostname, fkGponOnuDistance, fkGponOnuHwAddress, 
                                fkGponOnuNosActiveVersion, fkGponOnuNosStandbyVersion, fkGponOnuNosUpgradeStatus, fkGponOnuIsFirst, fkGponOnuRxPower, 
                                fkGponOnuModelName, fkGponOnuDescription, fkGponOnuNosAutoUpgradeWaitStatus, fkGponOnuNosAutoUpgradeFailCount, fkGponOnuControlRequest, 
                                fkGponOnuControlStatus, fkGponOnuControlTimer, fkGponOnuControlTimeStamp, fkGponOnuControlReqResult, fkGponOnuControlOltId, 
                                fkGponOnuControlId, fkGponOnuControlSerial, fkGponOnuControlPasswd, fkGponOnuControlPasswdMode, fkGponOnuControlEncMode, 
                                fkGponOnuControlProfile, fkGponOnuControlNosUpgradePath, fkGponOnuControlHwAddr, fkGponOnuControlTxOffOptic, fkGponOnuControlDescription, 
                                fkGponTcontId, fkGponTcontOnuId, fkGponTcontDBAMode, fkGponTcontFixedBw, fkGponTcontAssuredBw, 
                                fkGponTcontMaxBw, fkGponTcontControlRequest, fkGponTcontControlStatus, fkGponTcontControlTimer, fkGponTcontControlTimeStamp, 
                                fkGponTcontControlReqResult, fkGponTcontControlId, fkGponTcontControlOltId, fkGponTcontControlOnuId, fkGponTcontControlDBAMode, 
                                fkGponTcontControlFixedBw, fkGponTcontControlAssuredBw, fkGponTcontControlMaxBw, fkGponTcontControlOnuSerial, fkGponProfileId, 
                                fkGponProfileName, fkGponProfileDscpToPbit, fkGponProfileBaseControlRequest, fkGponProfileBaseControlStatus, fkGponProfileBaseControlTimer, 
                                fkGponProfileBaseControlTimeStamp, fkGponProfileBaseControlReqResult, fkGponProfileBaseControlName, fkGponProfileBaseControlDscpToPbit, fkGponProfilePortId, 
                                fkGponProfilePortRateLimit, fkGponProfilePortMaxHost, fkGponProfilePortVlan, fkGponProfilePortCosValue, fkGponProfilePortVlanMode, 
                                fkGponProfilePortVlanFilter, fkGponProfilePortControlRequest, fkGponProfilePortControlStatus, fkGponProfilePortControlTimer, fkGponProfilePortControlTimeStamp, 
                                fkGponProfilePortControlReqResult, fkGponProfilePortControlId, fkGponProfilePortControlPortId, fkGponProfilePortControlRateLimit, fkGponProfilePortControlMaxHost, 
                                fkGponProfilePortControlVlan, fkGponProfilePortControlCosValue, fkGponProfilePortControlVlanMode, fkGponProfilePortControlVlanFilter, fkGponOnuPortSlotId, 
                                fkGponOnuPortSlotType, fkGponOnuPortAdminStatus, fkGponOnuPortOperStatus, fkGponOnuPortControlRequest, fkGponOnuPortControlStatus, 
                                fkGponOnuPortControlTimer, fkGponOnuPortControlTimeStamp, fkGponOnuPortControlReqResult, fkGponOnuPortControlOltId, fkGponOnuPortControlOnuId, 
                                fkGponOnuPortControlSlotId, fkGponOnuPortControlPortId, fkGponOnuPortControlAdminStatus, fkGponOnuPortControlOnuSerial, fkGponOltStatsPonValidEthPacketsRx, 
                                fkGponOltStatsPonCpuPacketsRx, fkGponOltStatsPonPloamsRx, fkGponOltStatsPonInvalidPacketsRx, fkGponOltStatsPonValidEthPacketsTx, fkGponOltStatsPonCpuPacketsTx, 
                                fkGponOltStatsPonPloamsTx, fkGponOltStatsPonInvalidPacketsTx, fkGponOltStatsPerfRxValidPackets, fkGponOltStatsPerfRxErroredPackets, fkGponOltStatsPerfCRCdroppedPackets, 
                                fkGponOltStatsAllocId, fkGponOltStatsAllocDataRx, fkGponOltStatsOnuPonUnreceivedBursts, fkGponOltStatsOnuPonPositiveDrift, fkGponOltStatsOnuNegativeDrift, 
                                fkGponOltStatsOnuPonBip8Errors, fkGponOltStatsControlRequest, fkGponOltStatsControlStatus, fkGponOltStatsControlTimer, fkGponOltStatsControlTimeStamp, 
                                fkGponOltStatsControlReqResult, fkGponOltStatsControlOltIndex, fkGponOltStatsControlOnuIndex, fkGponFirmwareType, fkGponFirmwareName, 
                                fkGponFirmwareControlRequest, fkGponFirmwareControlStatus, fkGponFirmwareControlTimer, fkGponFirmwareControlTimeStamp, fkGponFirmwareControlReqResult, 
                                fkGponFirmwareControlName, fkGponFirmwareControlUpgradeMethod, fkGponFirmwareControlUpgradeMode, fkGponFirmwareControlServerAddress, fkGponFirmwareControlUser, 
                                fkGponFirmwareControlPasswd, fkGponOnuFWAutoUpgradeMode, fkGponOnuFWAutoUpgradeVersionMatch, fkGponOnuFWAutoUpgradeInvalidVersionMatch, fkGponOnuFWAutoUpgradeStatus, 
                                fkGponOnuFWAutoUpgradeCurrentUgradingFWName, fkGponOnuFWAutoUpgradeControlRequest, fkGponOnuFWAutoUpgradeControlStatus, fkGponOnuFWAutoUpgradeControlTimer, fkGponOnuFWAutoUpgradeControlTimeStamp, 
                                fkGponOnuFWAutoUpgradeControlReqResult, fkGponOnuFWAutoUpgradeControlOltId, fkGponOnuFWAutoUpgradeControlMode, fkGponOnuFWAutoUpgradeControlVersionMatch, fkGponOnuFWAutoUpgradeControlInvalidVersionMatch, 
                                fkGponOnuFWAutoUpgradeStartTime, fkGponOnuFWAutoUpgradeEndTime, fkGponOnuFWAutoUpgradeRebootTime, fkGponOnuFWAutoUpgradeTimeControlRequest, fkGponOnuFWAutoUpgradeTimeControlStatus, 
                                fkGponOnuFWAutoUpgradeTimeControlTimer, fkGponOnuFWAutoUpgradeTimeControlTimeStamp, fkGponOnuFWAutoUpgradeTimeControlReqResult, fkGponOnuFWAutoUpgradeTimeControlStartTime, fkGponOnuFWAutoUpgradeTimeControlEndTime, 
                                fkGponOnuFWAutoUpgradeTimeControlRebootTime, fkGponOnuFWAutoUpgradeModelId, fkGponOnuFWAutoUpgradeModelName, fkGponOnuFWAutoUpgradeModelFWName, fkGponOnuFWAutoUpgradeModelFWVersion, 
                                fkGponOnuFWAutoUpgradeModelStatus, fkGponOnuFWAutoUpgradeModelMethod, fkGponOnuFWAutoUpgradeModelServerAddress, fkGponOnuFWAutoUpgradeModelUser, fkGponOnuFWAutoUpgradeModelPasswd, 
                                fkGponOnuFWAutoUpgradeModelControlRequest, fkGponOnuFWAutoUpgradeModelControlStatus, fkGponOnuFWAutoUpgradeModelControlTimer, fkGponOnuFWAutoUpgradeModelControlTimeStamp, fkGponOnuFWAutoUpgradeModelControlReqResult, 
                                fkGponOnuFWAutoUpgradeModelControlName, fkGponOnuFWAutoUpgradeModelControlFWName, fkGponOnuFWAutoUpgradeModelControlMethod, fkGponOnuFWAutoUpgradeModelControlServerAddress, fkGponOnuFWAutoUpgradeModelControlUser, 
                                fkGponOnuFWAutoUpgradeModelControlPasswd, fkGponOnuOltRxPower, fkGponOnuLinkUpTime, fkGponOnuPortLinkUptime, fkGponOnuPortAutoNego, 
                                fkGponOnuPortSpeed, fkGponOnuPortControlAutoNego, fkGponOnuPortControlSpeed, fkGponOltStatsOnuPonFecCorrectedBytes, fkGponOltStatsOnuPonFecUncorrectedCodewords, 
                                fkGponOltStatsOnuPonFecCorrectedCodewords, fkGponOltStatsOnuPonFecReceivedCodewords, fkGponOnuAuthenticationStatus, fkGponOnuNetmask, fkGponOnuHWType, 
                                fkGponOnuRegistrationCnt, fkGponOnuAuthAcceptedCnt, fkGponOnuAuthRejectedCnt, fkGponOntFirmwareIndex, fkGponOntFirmwareType, 
                                fkGponOntFirmwareName, fkGponOntiFirmwareSize, fkGponOntFirmwareMd5, fkGponOntFirmwareOntId, fkGponOntFirmwareOntOs1Ver, 
                                fkGponOntFirmwareOntOs2Ver, fkGponOntFirmwareOntBLVer, fkGponOntFirmeareOntDefaultOS, fkGponOntFirmeareOntRunningOS, fkGponOntFirmwareOntGponOs1Ver, 
                                fkGponOntFirmwareOntGponOs2Ver, fkGponOntFirmwareOntOsStatus, fkGponOntFirmwareOntBLStatus, fkGponOntFirmwareOsUpgrdStatus, fkGponOntFirmwareOsUpgrdResult, 
                                fkGponOntFirmwareBLUpgrdStatus, fkGponOntFirmwareBLUpgrdResult, fkGponOntFirmwareControlRequest, fkGponOntFirmwareControlStatus, fkGponOntFirmwareControlTimer, 
                                fkGponOntFirmwareControlTimeStamp, fkGponOntFirmwareControlReqResult, fkGponOntFirmwareControlOltId, fkGponOntFirmwareControlOntId, fkGponOntFirmwareControlType, 
                                fkGponOntFirmwareControlFwName, fkGponOntFirmwareControlMethod, fkGponOntFirmwareControlServer, fkGponOntFirmwareControlUser, fkGponOntFirmwareControlPasswd, 
                                fkGponOnuAuthChallengedCnt, fkGponOnuVlanID, fkGponOnuRTD, fkGponOntFirmwareOltId, fkGponOltFecModeUS, 
                                fkGponOltFecModeDS, fkGponOltMacAgingTime, fkGponOltTransceiverPort, fkGponOltControlFecModeUS, fkGponOltControlFecModeDS, 
                                fkGponOltControlMacAgingTime, fkGponOltControlTransceiverPort, fkGponOnuFecModeUS, fkGponOnuIPMode, fkGponOnuIpAddress, 
                                fkGponOnuIPMask, fkGponOnuIPGw, fkGponOnuIPDns1, fkGponOnuIPDns2, fkGponOnuControlFecModeUS, 
                                fkGponOnuControlIPMode, fkGponOnuControlIPMask, fkGponOnuControlIPGw, fkGponOnuControlIPDns1, fkGponOnuControlIPDns2, 
                                fkGponProfileTcontProfileCnt, fkGponProfileTcontProfile, fkGponProfileVoIPProfileCnt, fkGponProfileVoIPProfile, fkGponProfileControlTcontProfileCnt, 
                                fkGponProfileControlTcontProfile, fkGponProfileControlVoipProfileCnt, fkGponProfileControlVoipProfile, fkGponProfileDbaId, fkGponProfileDbaName, 
                                fkGponProfileDbaMode, fkGponProfileDbaSlaFixedBw, fkGponProfileDbaSlaAssuredBw, fkGponProfileDbaSlaMaxBw, fkGponProfileDbaControlRequest, 
                                fkGponProfileDbaControlStatus, fkGponProfileDbaControlTimer, fkGponProfileDbaControlTimeStamp, fkGponProfileDbaControlReqResult, fkGponProfileDbaControlId, 
                                fkGponProfileDbaControlName, fkGponProfileDbaControlMode, fkGponProfileDbaControlSlaFixedBw, fkGponProfileDbaControlSlaAssuredBw, fkGponProfileDbaControlSlaMaxBw, 
                                fkGponProfileMultiTcontIndex, fkGponProfileMultiTcontName, fkGponProfileMultiTconTDscp2Pbit, fkGponProfileMultiTconTPriQWeightCnt, fkGponProfileMultiTconTPriQWeight, 
                                fkGponProfileMultiTcontGemPortType, fkGponProfileMultiTcontGemportUniPortList, fkGponProfileMultiTcontGemPortVlanCnt, fkGponProfileMultiTcontGemPortVlanList, fkGponProfileMultiTcontGemPortCount, 
                                fkGponProfileMultiTcontGemPortDbaProfileName1, fkGponProfileMultiTcontGemPortDbaProfileMask1, fkGponProfileMultiTcontGemPortDbaProfileName2, fkGponProfileMultiTcontGemPortDbaProfileMask2, fkGponProfileMultiTcontGemPortDbaProfileName3, 
                                fkGponProfileMultiTcontGemPortDbaProfileMask3, fkGponProfileMultiTcontGemPortDbaProfileName4, fkGponProfileMultiTcontGemPortDbaProfileMask4, fkGponProfileMultiTcontGemPortDbaProfileName5, fkGponProfileMultiTcontGemPortDbaProfileMask5, 
                                fkGponProfileMultiTcontGemPortDbaProfileName6, fkGponProfileMultiTcontGemPortDbaProfileMask6, fkGponProfileMultiTcontGemPortDbaProfileName7, fkGponProfileMultiTcontGemPortDbaProfileMask7, fkGponProfileMultiTcontGemPortDbaProfileName8, 
                                fkGponProfileMultiTcontGemPortDbaProfileMask8, fkGponProfileMultiTcontControllRequest, fkGponProfileMultiTcontControlStatus, fkGponProfileMultiTcontControlTimer, fkGponProfileMultiTcontControlTimeStamp, 
                                fkGponProfileMultiTcontControlReqResult, fkGponProfileMultiTcontControlIndex, fkGponProfileMultiTcontControlName, fkGponProfileMultiTcontControlDscp2Pbit, fkGponProfileMultiTcontControlPriQWeightCnt, 
                                fkGponProfileMultiTcontControlPriQWeight, fkGponProfileMultiTcontControlGemPortType, fkGponProfileMultiTcontControlGemportUniPortList, fkGponProfileMultiTcontControlGemPortVlanCnt, fkGponProfileMultiTcontControlGemPortVlanList, 
                                fkGponProfileMultiTcontControlGemPortCount, fkGponProfileMultiTcontControlGemPortDbaProfileName1, fkGponProfileMultiTcontControlGemPortDbaProfileMask1, fkGponProfileMultiTcontControlGemPortDbaProfileName2, fkGponProfileMultiTcontControlGemPortDbaProfileMask2, 
                                fkGponProfileMultiTcontControlGemPortDbaProfileName3, fkGponProfileMultiTcontControlGemPortDbaProfileMask3, fkGponProfileMultiTcontControlGemPortDbaProfileName4, fkGponProfileMultiTcontControlGemPortDbaProfileMask4, fkGponProfileMultiTcontControlGemPortDbaProfileName5, 
                                fkGponProfileMultiTcontControlGemPortDbaProfileMask5, fkGponProfileMultiTcontControlGemPortDbaProfileName6, fkGponProfileMultiTcontControlGemPortDbaProfileMask6, fkGponProfileMultiTcontControlGemPortDbaProfileName7, fkGponProfileMultiTcontControlGemPortDbaProfileMask7, 
                                fkGponProfileMultiTcontControlGemPortDbaProfileName8, fkGponProfileMultiTcontControlGemPortDbaProfileMask8, fkGponProfileVoIPIndex, fkGponProfileVoIPName, fkGponProfileVoIPServiceMode, 
                                fkGponProfileVoIPServiceProtocol, fkGponProfileVoIPOmciAgentURL, fkGponProfileVoIPOmciAgentProxy, fkGponProfileVoIPOmciAgentDns1, fkGponProfileVoIPOmciAgentDns2, 
                                fkGponProfileVoIPControlStatus, fkGponProfileVoIPControlTimer, fkGponProfileVoIPControlTimeStamp, fkGponProfileVoIPControlReqResult, fkGponProfileVoIPControlIndex, 
                                fkGponProfileVoIPControlName, fkGponProfileVoIPControlServiceMode, fkGponProfileVoIPControlServiceProtocol, fkGponProfileVoIPControlOmciAgentURL, fkGponProfileVoIPControlOmciAgentProxy, 
                                fkGponProfileVoIPControlOmciAgentDns1, fkGponProfileVoIPControlOmciAgentDns2, fkGponProfileVoIPOmciUniPortId, fkGponProfileVoIPOmciAuthName, fkGponProfileVoIPOmciAuthPasswd, 
                                fkGponProfileVoIPOmciPhoneNumber, fkGponProfileVoIPOmciDisplay, fkGponProfileVoIPOmciControlStatus, fkGponProfileVoIPOmciControlTimer, fkGponProfileVoIPOmciControlTimeStamp, 
                                fkGponProfileVoIPOmciControlReqResult, fkGponProfileVoIPOmciControlOltIndex, fkGponProfileVoIPOmciControlOnuIndex, fkGponProfileVoIPOmciControlUniId, fkGponProfileVoIPOmciControlAuthName, 
                                fkGponProfileVoIPOmciControlAuthPasswd, fkGponProfileVoIPOmciControlPhoneNumber, fkGponProfileVoIPOmciControlDisplay, fkGponProfileVoIPIpPathControlStatus, fkGponProfileVoIPIpPathControlTimer, 
                                fkGponProfileVoIPIpPathControlTimeStamp, fkGponProfileVoIPIpPathControlReqResult, fkGponProfileVoIPIpPathControlOltIndex, fkGponProfileVoIPIpPathControlOnuIndex, fkGponProfileVoIPIpPathControlAuthName, 
                                fkGponProfileVoIPIpPathControlAuthPasswd, fkGponOnuBatteryStatus, fkGponOnuMgmtSerialNo, fkGponProfileVoIPControlRequest, fkGponProfileVoIPOmciControlRequest, 
                                fkGponOnuUserMacCnt, fkGponOnuUserMacAddress, fkGponOnuUserMacVlanId, fkGponOnuUserMacPortId, fkGponProfilePortAdmin, 
                                fkGponProfilePortDuplex, fkGponProfilePortSpeed, fkGponProfilePortControlPortAdmin, fkGponProfilePortControlPortDuplex, fkGponProfilePortControlPortSpeed, 
                                fkGponOnuUserMacOltId, fkGponOnuUserMacOnuId, fkGponBridgeVoIPInfoOltId, fkGponBridgeVoIPInfoOnuId, fkGponBridgeVoIPInfoDHCP, 
                                fkGponBridgeVoIPInfoIpAddress, fkGponBridgeVoIPInfoMethods, fkGponBridgeVoIPInfoCurrMethods, fkGponBridgeVoIPInfoProtocols, fkGponBridgeVoIPInfoCurrProtocols, 
                                fkGponBridgeVoIPLineOltId, fkGponBridgeVoIPLineOnuId, fkGponBridgeVoIPLinePots, fkGponBridgeVoIPLineAdminStatus, fkGponBridgeVoIPLineOperStatus, 
                                fkGponBridgeVoIPLineStatus, fkGponOnuPortDuplex, fkGponOltActivateStatus, fkGponOltControlActivateStatus, fkGponOnuDeactiveReason, 
                                fkGponOnuFWAutoUpgradeModelControlFWTargetVersion, fkGponOnuFWAutoUpgradeModelFWTargetVersion, fkGponOnuFWAutoUpgradeMTimeControlModelName, fkGponOnuFWAutoUpgradeMTimeControlEndTime, fkGponOnuFWAutoUpgradeMTimeControlStartTime, 
                                fkGponOnuFWAutoUpgradeMTimeControlReqResult, fkGponOnuFWAutoUpgradeMTimeControlTimeStamp, fkGponOnuFWAutoUpgradeMTimeControlTimer, fkGponOnuFWAutoUpgradeMTimeControlStatus, fkGponOnuFWAutoUpgradeMTimeControlRequest, 
                                fkGponOnuFWAutoUpgradeMTimeModelName, fkGponOnuFWAutoUpgradeMTimeEndTime, fkGponOnuFWAutoUpgradeMTimeStartTime, fkGponOnuFWAutoUpgradeMTimeIndex, fkGponOnuFWAutoUpgradeSActiveVer, 
                                fkGponOnuFWAutoUpgradeSFailCnt, fkGponOnuFWAutoUpgradeSStatus, fkGponOnuFWAutoUpgradeSModelName, fkGponOnuFWAutoUpgradeSOnuID, fkGponOnuFWAutoUpgradeSOltID, 
                                fkGponOnuFWAutoUpgradeSIndex, fkGponOltProtection, fkGponOltActiveOnuCount, fkGponOltInactiveOnuCount, fkGponOltControlProtection, 
                                fkGponOnuControlActiveStatus, fkGponBridgeSlotIndex, fkGponBridgeSlotConnectionStatus, fkGponBridgeSlotFlags, fkGponRedGroupIndex, 
                                fkGponRedGroupOltAIndex, fkGponRedGroupOltAStatus, fkGponRedGroupOltBIndex, fkGponRedGroupOltBStatus, fkGponRedLastReason, 
                                fkGponRedGroupControlRequest, fkGponRedGroupControlStatus, fkGponRedGroupControlTimer, fkGponRedGroupControlTimeStamp, fkGponRedGroupControlReqResult, 
                                fkGponRedGroupControlGroupIndex, fkGponRedGroupControlOltAIndex, fkGponRedGroupControlOltBIndex, fkGponProfilePortPause, fkGponProfilePortControlPortPause, 
                                fkGponOnuControlPathIpAddr, fkGponOnuControlPathMacAddr, fkGponOnuControlPathStatus, fkGponOnuControlPathUptime, fkGponProfile2OnuName, 
                                fkGponProfile2OnuRxPowerHighThresh, fkGponProfile2OnuRxPowerLowThresh, fkGponProfile2OnuRogueAlarmCount, fkGponProfile2OnuRoguePollingInterval, fkGponProfile2OnuRogueWaitingTime, 
                                fkGponProfile2OnuTrafficProfile, fkGponProfile2OnuControlRequest, fkGponProfile2OnuControlStatus, fkGponProfile2OnuControlTimer, fkGponProfile2OnuControlTimeStamp, 
                                fkGponProfile2OnuControlReqResult, fkGponProfile2OnuControlName, fkGponProfile2OnuControlRxPowerHighThresh, fkGponProfile2OnuControlRxPowerLowThresh, fkGponProfile2OnuControlRogueAlarmCount, 
                                fkGponProfile2OnuControlRoguePollingInterval, fkGponProfile2OnuControlRogueWaitingTime, fkGponProfile2OnuControlTrafficProfile, fkGponProfile2OnuUniId, fkGponProfile2OnuUniType, 
                                fkGponProfile2OnuUniDownSir, fkGponProfile2OnuUniDownPir, fkGponProfile2OnuUniControlRequest, fkGponProfile2OnuUniControlStatus, fkGponProfile2OnuUniControlTimer, 
                                fkGponProfile2OnuUniControlTimeStamp, fkGponProfile2OnuUniControlReqResult, fkGponProfile2OnuUniControlId, fkGponProfile2OnuUniControlType, fkGponProfile2OnuUniControlDownSir, 
                                fkGponProfile2OnuUniControlDownPir, fkGponProfile2McastAclIndex, fkGponProfile2McastAclControlIndex, fkGponProfile2McastAclControlName, fkGponProfile2McastSAclIndex, 
                                fkGponProfile2McastSAclControlIndex, fkGponProfile2McastSAclControlName, fkGponOltLinkUpCount, fkGponOltLinkDownCount, fkGponOltAuthenCount, 
                                fkGponOltElapsedTimeAfterClearAuthStats, fkGponOnuPortGemblockRx, fkGponOnuPortGemblockTx, fkGponOnuPortDiscardFrames, fkGponProfileVoIPIpPathControlRequest, 
                                fkGponOnuIPAddr, fkGponOnuControlIPAddr, fkGponOnuPMProfile, fkGponOnuControlPMProfile, fkGponProfile2PMProfileName, 
                                fkGponProfile2PMProfilePMGemPort, fkGponProfile2PMProfileControlRequest, fkGponProfile2PMProfileControlStatus, fkGponProfile2PMProfileControlTimer, fkGponProfile2PMProfileControlTimeStamp, 
                                fkGponProfile2PMProfileControlReqResult, fkGponProfile2PMProfileControlName, fkGponProfile2TcontGemportMapperId, fkGponProfile2TcontGemportControlMapperId, fkGponProfile2OnuUniControlOnuProfile, 
                                fkGponProfile2PMProfileControlPMGemPort, fkGponProfile2PMProfilePMAniPort, fkGponProfile2PMProfileControlPMAniPort, fkGponOltUpElapsedTime, fkGponOltDownElapsedTime, 
                                fkGponOltOpticParam, fkGponOltControlOpticParam, fkGponOnuUpCount, fkGponOnuDownCount, fkGponOnuControlNosPartition, 
                                fkGponOnuPortElapsedTimeAfterClearStats, fkGponOnuPMStatsPrev15mLostPackets, fkGponOnuPMStatsPrev15mMisInsertedPackets, fkGponOnuPMStatsPrev15mReceivedPackets, fkGponOnuPMStatsPrev15mReceivedBlocks, 
                                fkGponOnuPMStatsPrev15mTransmittedBlocks, fkGponOnuPMStatsPrev15mImpairedBlocks, fkGponOnuPMStatsPrev15mDiscardedFrames, fkGponOnuPMStatsPrev30mLostPackets, fkGponOnuPMStatsPrev30mMisInsertedPackets, 
                                fkGponOnuPMStatsPrev30mReceivedPackets, fkGponOnuPMStatsPrev30mReceivedBlocks, fkGponOnuPMStatsPrev30mTransmittedBlocks, fkGponOnuPMStatsPrev30mImpairedBlocks, fkGponOnuPMStatsPrev30mDiscardedFrames, 
                                fkGponOnuPMStatsTotalLostPackets, fkGponOnuPMStatsTotalMisInsertedPackets, fkGponOnuPMStatsTotalReceivedPackets, fkGponOnuPMStatsTotalReceivedBlocks, fkGponOnuPMStatsTotalTransmittedBlocks, 
                                fkGponOnuPMStatsTotalImpairedBlocks, fkGponOnuPMStatsTotalDiscardedFrames, fkGponOnuPMStatsElapsedTimeAfterClear, fkGponOnuPMStatsElapsedTimeAfterUpdate, fkGponOnuPMStatsControlRequest, 
                                fkGponOnuPMStatsControlStatus, fkGponOnuPMStatsControlTimer, fkGponOnuPMStatsControlTimeStamp, fkGponOnuPMStatsControlReqResult, fkGponOnuPMStatsControlOltIndex, 
                                fkGponOnuPMStatsControlOnuIndex, fkGponProfile2DbaIndex, fkGponProfile2TrafficIndex, fkGponProfile2McastIndex, fkGponProfile2OnuIndex, 
                                fkGponProfile2OnuRoguePollingCount, fkGponProfile2OnuPmProfile, fkGponProfile2OnuControlRoguePollingCount, fkGponProfile2OnuControlPmProfile, fkGponProfile2OnuUniVlanDsOper, 
                                fkGponProfile2OnuUniVlanUSOper, fkGponProfile2OnuUniVlanUsOperVID, fkGponProfile2OnuUniVlanUsOperCoS, fkGponProfile2OnuUniIgmpMaxGroup, fkGponProfile2OnuUniPortAdmin, 
                                fkGponProfile2OnuUniControlVlanDsOper, fkGponProfile2OnuUniControlVlanUsOper, fkGponProfile2OnuUniControlVlanUsOperVID, fkGponProfile2OnuUniControlVlanUsOperCoS, fkGponProfile2OnuUniControlIgmpMaxGroup, 
                                fkGponProfile2OnuUniControlPortAdmin, fkGponProfile2PMProfileIndex, fkGponProfile2OnuBridgeId, fkGponProfile2OnuBridgeMaxHost, fkGponProfile2OnuBridgeControlRequest, 
                                fkGponProfile2OnuBridgeControlStatus, fkGponProfile2OnuBridgeControlTimer, fkGponProfile2OnuBridgeControlTimeStamp, fkGponProfile2OnuBridgeControlReqResult, fkGponProfile2OnuBridgeControlOnuProfile, 
                                fkGponProfile2OnuBridgeControlId, fkGponProfile2OnuBridgeControlMaxHost, fkGponProfile2OnuTcontId, fkGponProfile2OnuTcontDbaProfile, fkGponProfile2OnuTcontControlRequest, 
                                fkGponProfile2OnuTcontControlStatus, fkGponProfile2OnuTcontControlTimer, fkGponProfile2OnuTcontControlTimeStamp, fkGponProfile2OnuTcontControlReqResult, fkGponProfile2OnuTcontControlOnuProfile, 
                                fkGponProfile2OnuTcontControlId, fkGponProfile2OnuTcontControlDbaProfile, fkGponOnuNosDefaultPartition, fkGponOnuNosActivePartition, fkGponProfile2BridgeUniIpMode, 
                                fkGponProfile2BridgeUniDns1, fkGponProfile2BridgeUniDns2, fkGponProfile2BridgeUniVoIPProfile, fkGponProfile2BridgeUniControlIpMode, fkGponProfile2BridgeUniControlDns1, 
                                fkGponProfile2BridgeUniControlDns2, fkGponProfile2BridgeUniControlVoIPProfile, fkGponOnuHostOltId, fkGponOnuHostOnuId, fkGponOnuHostId, 
                                fkGponOnuHostIPAddr, fkGponOnuHostMask, fkGponOnuHostGW, fkGponOnuHostControlRequest, fkGponOnuHostControlStatus, 
                                fkGponOnuHostControlTimer, fkGponOnuHostControlTimeStamp, fkGponOnuHostControlReqResult, fkGponOnuHostControlOltId, fkGponOnuHostControlOnuId, 
                                fkGponOnuHostControlId, fkGponOnuHostControlIPAddr, fkGponOnuHostControlMask, fkGponOnuHostControlGW, fkGponBaseControlDeaultServiceProfile, 
                                fkGponOltSrcMacMonitorStatus, fkGponOltSrcMacMonitorAutoBlock, fkGponOltSrcMacMonitoEexpireTimeout, fkGponOltTotalUsBw, fkGponOltControlSrcMacMonitorStatus, 
                                fkGponOltControlSrcMacMonitorAutoBlock, fkGponOltControlSrcMacMonitoEexpireTimeout, fkGponOltControlTotalUsBw, fkGponOnuBlockStatus, fkGponOnuBlockReason, 
                                fkGponOnuLastActiveFailReason, fkGponOnuEqD, fkGponOnuMaxTcont, fkGponOnuMaxUsQueuePerTcont, fkGponOnuSysUpTime, 
                                fkGponOnuVenderProduct, fkGponOnuSlotId, fkGponOnuOperStatus, fkGponOnuMapperID, fkGponOnuControlBlock, 
                                fkGponServiceProfileModelName, fkGponServiceProfileProfileName, fkGponServiceProfileControlRequest, fkGponServiceProfileControlStatus, fkGponServiceProfileControlTimer, 
                                fkGponServiceProfileControlTimeStamp, fkGponServiceProfileControlReqResult, fkGponServiceProfileControlModelName, fkGponServiceProfileControlProfileName, fkGponOnuUserMacControlRequest, 
                                fkGponOnuUserMacControlStatus, fkGponOnuUserMacControlTimer, fkGponOnuUserMacControlTimeStamp, fkGponOnuUserMacControlReqResult, fkGponOnuUserMacControlOltId, 
                                fkGponOnuUserMacControlOnuId, fkGponOnuUserMacControlAddress, fkGponOnuUserMacControlVlanId, fkGponOntFirmwareControlOnuId, fkGponIgmpGroupOltId, 
                                fkGponIgmpGroupOnuId, fkGponIgmpGroupUniId, fkGponIgmpGroupUniType, fkGponIgmpGroupIndex, fkGponIgmpGroupSrcIPAddr, 
                                fkGponIgmpGroupDstIPAddr, fkGponIgmpGroupRptIPAddr, fkGponIgmpGroupJoinTime, fkGponProfileVoIPPotsPIndex, fkGponProfileVoIPPotsIndex, 
                                fkGponProfileVoIPPotsAdmin, fkGponProfileVoIPPotsControlRequest, fkGponProfileVoIPPotsControlStatus, fkGponProfileVoIPPotsControlTimer, fkGponProfileVoIPPotsControlTimeStamp, 
                                fkGponProfileVoIPPotsControlReqResult, fkGponProfileVoIPPotsControlProfileIndex, fkGponProfileVoIPPotsControlPotsIndex, fkGponProfileVoIPPotsControlAdmin, fkGponServiceProfileIndex, 
                                fkGponDefaultServiceProfile, fkGponProfileTdmPwMtIndex, fkGponProfileTdmPwMtName, fkGponProfileTdmPwMtMaxDepth, fkGponProfileTdmPwMtDesiredDepth, 
                                fkGponProfileTdmPwMtFillPolicy, fkGponProfileTdmPwMtMisconnectDeclarePolicy, fkGponProfileTdmPwMtMisconnectClearPolicy, fkGponProfileTdmPwMtLossDeclarePolicy, fkGponProfileTdmPwMtLossClearPolicy, 
                                fkGponProfileTdmPwMtBuffUnderrunDeclarePolicy, fkGponProfileTdmPwMtBuffUnderrunClearPolicy, fkGponProfileTdmPwMtMalformedDeclarePolicy, fkGponProfileTdmPwMtMalformedClearPolicy, fkGponProfileTdmPwMtRBitTransmitPolicy, 
                                fkGponProfileTdmPwMtRBitReceivePolicy, fkGponProfileTdmPwMtLBitReceivePolicy, fkGponProfileTdmPwMtSesThreshold, fkGponProfileTdmPwMtControlRequest, fkGponProfileTdmPwMtControlStatus, 
                                fkGponProfileTdmPwMtControlTimer, fkGponProfileTdmPwMtControlTimeStamp, fkGponProfileTdmPwMtControlReqResult, fkGponProfileTdmPwMtControlIndex, fkGponProfileTdmPwMtControlName, 
                                fkGponProfileTdmPwMtControlMaxDepth, fkGponProfileTdmPwMtControlDesiredDepth, fkGponProfileTdmPwMtControlFillPolicy, fkGponProfileTdmPwMtControlMisconnectDeclarePolicy, fkGponProfileTdmPwMtControlMisconnectClearPolicy, 
                                fkGponProfileTdmPwMtControlLossDeclarePolicy, fkGponProfileTdmPwMtControlLossClearPolicy, fkGponProfileTdmPwMtControlBuffUnderrunDeclarePolicy, fkGponProfileTdmPwMtControlBuffUnderrunClearPolicy, fkGponProfileTdmPwMtControlMalformedDeclarePolicy, 
                                fkGponProfileTdmPwMtControlMalformedClearPolicy, fkGponProfileTdmPwMtControlRBitTransmitPolicy, fkGponProfileTdmPwMtControlRBitReceivePolicy, fkGponProfileTdmPwMtControlLBitReceivePolicy, fkGponProfileTdmPwMtControlSesThreshold, 
                                fkGponProfileTdmPwIndex, fkGponProfileTdmPwName, fkGponProfileTdmPwServiceType, fkGponProfileTdmPwSignalling, fkGponProfileTdmPwPayloadSize, 
                                fkGponProfileTdmPwPayloadEncapulationDelay, fkGponProfileTdmPwTimingMode, fkGponProfileTdmPwRtpClockRefernce, fkGponProfileTdmPwRtpTimeStampMode, fkGponProfileTdmPwRtpPayloadChannel, 
                                fkGponProfileTdmPwRtpPayloadSignalling, fkGponProfileTdmPwRtpSyncSourceChannel, fkGponProfileTdmPwRtpSyncSourceSignalling, fkGponProfileTdmPwRtpExpectPayloadChannel, fkGponProfileTdmPwRtpExpectPaloadSignalling, 
                                fkGponProfileTdmPwRtpExpectSyncSourceChannel, fkGponProfileTdmPwRtpExpectSyncSourceSignalling, fkGponProfileTdmPwMtProfileName, fkGponProfileTdmPwControlRequest, fkGponProfileTdmPwControlStatus, 
                                fkGponProfileTdmPwControlTimer, fkGponProfileTdmPwControlTimeStamp, fkGponProfileTdmPwControlReqResult, fkGponProfileTdmPwControlIndex, fkGponProfileTdmPwControlName, 
                                fkGponProfileTdmPwControlServiceType, fkGponProfileTdmPwControlSignalling, fkGponProfileTdmPwControlPayloadSize, fkGponProfileTdmPwControlPayloadEncapulationDelay, fkGponProfileTdmPwControlTimingMode, 
                                fkGponProfileTdmPwControlRtpClockRefernce, fkGponProfileTdmPwControlRtpTimeStampMode, fkGponProfileTdmPwControlRtpPayloadChannel, fkGponProfileTdmPwControlRtpPayloadSignalling, fkGponProfileTdmPwControlRtpSyncSourceChannel, 
                                fkGponProfileTdmPwControlRtpSyncSourceSignalling, fkGponProfileTdmPwControlRtpExpectPayloadChannel, fkGponProfileTdmPwControlRtpExpectPaloadSignalling, fkGponProfileTdmPwControlRtpExpectSyncSourceChannel, fkGponProfileTdmPwControlRtpExpectSyncSourceSignalling, 
                                fkGponProfileTdmPwControlMtProfileName, fkGponProfile2TdmSvcId, fkGponProfile2TdmSvcMode, fkGponProfile2TdmSvcTdmPwProfileName, fkGponProfile2TdmSvcTimeSlot, 
                                fkGponProfile2TdmSvcEthDestMac, fkGponProfile2TdmSvcEthVid, fkGponProfile2TdmSvcEthCoS, fkGponProfile2TdmSvcTranPayloadEcid, fkGponProfile2TdmSvcTranSignallingEcid, 
                                fkGponProfile2TdmSvcRecvPayloadEcid, fkGponProfile2TdmSvcRecvSignallingEcid, fkGponProfile2TdmSvcExpectPayloadEcid, fkGponProfile2TdmSvcExpectSignallingEcid, fkGponProfile2TdmSvcFarEndIpURL, 
                                fkGponProfile2TdmSvcMplsLabelIndicator, fkGponProfile2TdmSvcMplsPwDirection, fkGponProfile2TdmSvcMplsPwLabelUp, fkGponProfile2TdmSvcMplsPwLabelDown, fkGponProfile2TdmSvcMplsPwLabelExp, 
                                fkGponProfile2TdmSvcMplsPwTunnelDirection, fkGponProfile2TdmSvcMplsPwTunnelLabelUp, fkGponProfile2TdmSvcMplsPwTunnelLabelDown, fkGponProfile2TdmSvcMplsPwTunnelLabelExp, fkGponProfile2TdmSvcCesBuffCdvTolerance, 
                                fkGponProfile2TdmSvcCesChannelAssociateSignal, fkGponProfile2TdmSvcControlRequest, fkGponProfile2TdmSvcControlStatus, fkGponProfile2TdmSvcControlTimer, fkGponProfile2TdmSvcControlTimeStamp, 
                                fkGponProfile2TdmSvcControlReqResult, fkGponProfile2TdmSvcControlTName, fkGponProfile2TdmSvcControlTdmId, fkGponProfile2TdmSvcControlId, fkGponProfile2TdmSvcControlMode, 
                                fkGponProfile2TdmSvcControlTdmPwProfileName, fkGponProfile2TdmSvcControlTimeSlot, fkGponProfile2TdmSvcControlEthDestMac, fkGponProfile2TdmSvcControlEthVid, fkGponProfile2TdmSvcControlEthCoS, 
                                fkGponProfile2TdmSvcControlTranPayloadEcid, fkGponProfile2TdmSvcControlTranSignallingEcid, fkGponProfile2TdmSvcControlRecvPayloadEcid, fkGponProfile2TdmSvcControlRecvSignallingEcid, fkGponProfile2TdmSvcControlExpectPayloadEcid, 
                                fkGponProfile2TdmSvcControlExpectSignallingEcid, fkGponProfile2TdmSvcControlFarEndIpURL, fkGponProfile2TdmSvcControlMplsLabelIndicator, fkGponProfile2TdmSvcControlMplsPwDirection, fkGponProfile2TdmSvcControlMplsPwLabelUp, 
                                fkGponProfile2TdmSvcControlMplsPwLabelDown, fkGponProfile2TdmSvcControlMplsPwLabelExp, fkGponProfile2TdmSvcControlMplsPwTunnelDirection, fkGponProfile2TdmSvcControlMplsPwTunnelLabelUp, fkGponProfile2TdmSvcControlMplsPwTunnelLabelDown, 
                                fkGponProfile2TdmSvcControlMplsPwTunnelLabelExp, fkGponProfile2TdmSvcControlCesBuffCdvTolerance, fkGponProfile2TdmSvcControlCesChannelAssociateSignal, fkGponProfileTdmSdhIndex, fkGponProfileTdmSdhName, 
                                fkGponProfileTdmSdhTuType, fkGponProfileTdmSdhGemLossIntergrationPeriod, fkGponProfileTdmSdhTransmitJ1J2, fkGponProfileTdmSdhExpectJ1J2, fkGponProfileTdmSdhReceiveJ1J2, 
                                fkGponProfileTdmSdhTimMonitor, fkGponProfileTdmSdhTimAis, fkGponProfileTdmSdhControlRequest, fkGponProfileTdmSdhControlStatus, fkGponProfileTdmSdhControlTimer, 
                                fkGponProfileTdmSdhControlTimeStamp, fkGponProfileTdmSdhControlReqResult, fkGponProfileTdmSdhControlIndex, fkGponProfileTdmSdhControlName, fkGponProfileTdmSdhControlTuType, 
                                fkGponProfileTdmSdhControlGemLossIntergrationPeriod, fkGponProfileTdmSdhControlTransmitJ1J2, fkGponProfileTdmSdhControlExpectJ1J2, fkGponProfileTdmSdhControlReceiveJ1J2, fkGponProfileTdmSdhControlTimMonitor, 
                                fkGponProfileTdmSdhControlTimAis, fkGponOnuPortId, fkGponOnuPMStatsDetailGEMPort, fkGponOnuPMStatsDetailGEMPre15mLostPackets, fkGponOnuPMStatsDetailGEMPre15mMisInsertedPackets, 
                                fkGponOnuPMStatsDetailGEMPre15mReceivedPackets, fkGponOnuPMStatsDetailGEMPre15mReceivedBlocks, fkGponOnuPMStatsDetailGEMPre15mTransmittedBlocks, fkGponOnuPMStatsDetailGEMPre15mImpairedBlocks, fkGponOnuPMStatsDetailGEMHourLostPackets, 
                                fkGponOnuPMStatsDetailGEMHourMisInsertedPackets, fkGponOnuPMStatsDetailGEMHourReceivedPackets, fkGponOnuPMStatsDetailGEMHourReceivedBlocks, fkGponOnuPMStatsDetailGEMHourTransmittedBlocks, fkGponOnuPMStatsDetailGEMHourImpairedBlocks, 
                                fkGponOnuPMStatsDetailGEMDayLostPackets, fkGponOnuPMStatsDetailGEMDayMisInsertedPackets, fkGponOnuPMStatsDetailGEMDayReceivedPackets, fkGponOnuPMStatsDetailGEMDayReceivedBlocks, fkGponOnuPMStatsDetailGEMDayTransmittedBlocks, 
                                fkGponOnuPMStatsDetailGEMDayImpairedBlocks, fkGponOnuPMStatsDetailGEMTotalLostPackets, fkGponOnuPMStatsDetailGEMTotalMisInsertedPackets, fkGponOnuPMStatsDetailGEMTotalReceivedPackets, fkGponOnuPMStatsDetailGEMTotalReceivedBlocks, 
                                fkGponOnuPMStatsDetailGEMTotalTransmittedBlocks, fkGponOnuPMStatsDetailGEMTotalImpairedBlocks, fkGponOnuPMStatsDetailGEMElapsedTimeAfterClear, fkGponOnuPMStatsDetailGEMElapsedTimeAfterUpdate, fkGponOnuPMStatsDetailAniPort, 
                                fkGponOnuPMStatsDetailAniPre15mDiscardedFrames, fkGponOnuPMStatsDetailAniHourDiscardedFrames, fkGponOnuPMStatsDetailAniDayDiscardedFrames, fkGponOnuPMStatsDetailAniTotalDiscardedFrames, fkGponOnuPMStatsDetailAniElapsedTimeAfterClear, 
                                fkGponOnuPMStatsDetailAniElapsedTimeAfterUpdate, fkGponOnuPMStatsDetailUniEthFrameUpUniPort, fkGponOnuPMStatsDetailUniEthFrameUpPre15mDropEvents, fkGponOnuPMStatsDetailUniEthFrameUpPre15mOctets, fkGponOnuPMStatsDetailUniEthFrameUpPre15mPackets, 
                                fkGponOnuPMStatsDetailUniEthFrameUpPre15mBcastPackets, fkGponOnuPMStatsDetailUniEthFrameUpPre15mMcastPackets, fkGponOnuPMStatsDetailUniEthFrameUpPre15mUcastPackets, fkGponOnuPMStatsDetailUniEthFrameUpPre15mCRCErroredPackets, fkGponOnuPMStatsDetailUniEthFrameUpPre15mUndersizePackets, 
                                fkGponOnuPMStatsDetailUniEthFrameUpPre15mOversizePackets, fkGponOnuPMStatsDetailUniEthFrameUpPre15mPkt64Octets, fkGponOnuPMStatsDetailUniEthFrameUpPre15mPkt65To127Octets, fkGponOnuPMStatsDetailUniEthFrameUpPre15mPkt128To255Octets, fkGponOnuPMStatsDetailUniEthFrameUpPre15mPkt256To511Octets, 
                                fkGponOnuPMStatsDetailUniEthFrameUpPre15mPkt512To1023Octets, fkGponOnuPMStatsDetailUniEthFrameUpPre15mPkt1024To1518Octets, fkGponOnuPMStatsDetailUniEthFrameUpHourDropEvents, fkGponOnuPMStatsDetailUniEthFrameUpHourOctets, fkGponOnuPMStatsDetailUniEthFrameUpHourPackets, 
                                fkGponOnuPMStatsDetailUniEthFrameUpHourBcastPackets, fkGponOnuPMStatsDetailUniEthFrameUpHourMcastPackets, fkGponOnuPMStatsDetailUniEthFrameUpHourUcastPackets, fkGponOnuPMStatsDetailUniEthFrameUpHourCRCErroredPackets, fkGponOnuPMStatsDetailUniEthFrameUpHourUndersizePackets, 
                                fkGponOnuPMStatsDetailUniEthFrameUpHourOversizePackets, fkGponOnuPMStatsDetailUniEthFrameUpHourPkt64Octets, fkGponOnuPMStatsDetailUniEthFrameUpHourPkt65To127Octets, fkGponOnuPMStatsDetailUniEthFrameUpHourPkt128To255Octets, fkGponOnuPMStatsDetailUniEthFrameUpHourPkt256To511Octets, 
                                fkGponOnuPMStatsDetailUniEthFrameUpHourPkt512To1023Octets, fkGponOnuPMStatsDetailUniEthFrameUpHourPkt1024To1518Octets, fkGponOnuPMStatsDetailUniEthFrameUpDayDropEvents, fkGponOnuPMStatsDetailUniEthFrameUpDayOctets, fkGponOnuPMStatsDetailUniEthFrameUpDayPackets, 
                                fkGponOnuPMStatsDetailUniEthFrameUpDayBcastPackets, fkGponOnuPMStatsDetailUniEthFrameUpDayMcastPackets, fkGponOnuPMStatsDetailUniEthFrameUpDayUcastPackets, fkGponOnuPMStatsDetailUniEthFrameUpDayCRCErroredPackets, fkGponOnuPMStatsDetailUniEthFrameUpDayUndersizePackets, 
                                fkGponOnuPMStatsDetailUniEthFrameUpDayOversizePackets, fkGponOnuPMStatsDetailUniEthFrameUpDayPkt64Octets, fkGponOnuPMStatsDetailUniEthFrameUpDayPkt65To127Octets, fkGponOnuPMStatsDetailUniEthFrameUpDayPkt128To255Octets, fkGponOnuPMStatsDetailUniEthFrameUpDayPkt256To511Octets, 
                                fkGponOnuPMStatsDetailUniEthFrameUpDayPkt512To1023Octets, fkGponOnuPMStatsDetailUniEthFrameUpDayPkt1024To1518Octets, fkGponOnuPMStatsDetailUniEthFrameUpTotalDropEvents, fkGponOnuPMStatsDetailUniEthFrameUpTotalOctets, fkGponOnuPMStatsDetailUniEthFrameUpTotalPackets, 
                                fkGponOnuPMStatsDetailUniEthFrameUpTotalBcastPackets, fkGponOnuPMStatsDetailUniEthFrameUpTotalMcastPackets, fkGponOnuPMStatsDetailUniEthFrameUpTotalUcastPackets, fkGponOnuPMStatsDetailUniEthFrameUpTotalCRCErroredPackets, fkGponOnuPMStatsDetailUniEthFrameUpTotalUndersizePackets, 
                                fkGponOnuPMStatsDetailUniEthFrameUpTotalOversizePackets, fkGponOnuPMStatsDetailUniEthFrameUpTotalPkt64Octets, fkGponOnuPMStatsDetailUniEthFrameUpTotalPkt65To127Octets, fkGponOnuPMStatsDetailUniEthFrameUpTotalPkt128To255Octets, fkGponOnuPMStatsDetailUniEthFrameUpTotalPkt256To511Octets, 
                                fkGponOnuPMStatsDetailUniEthFrameUpTotalPkt512To1023Octets, fkGponOnuPMStatsDetailUniEthFrameUpTotalPkt1024To1518Octets, fkGponOnuPMStatsDetailUniEthFrameUpElapsedTimeAfterClear, fkGponOnuPMStatsDetailUniEthFrameUpElapsedTimeAfterUpdate, fkGponOnuPMStatsDetailUniEthFrameDownUniPort, 
                                fkGponOnuPMStatsDetailUniEthFrameDownPre15mDropEvents, fkGponOnuPMStatsDetailUniEthFrameDownPre15mOctets, fkGponOnuPMStatsDetailUniEthFrameDownPre15mPackets, fkGponOnuPMStatsDetailUniEthFrameDownPre15mBcastPackets, fkGponOnuPMStatsDetailUniEthFrameDownPre15mMcastPackets, 
                                fkGponOnuPMStatsDetailUniEthFrameDownPre15mUcastPackets, fkGponOnuPMStatsDetailUniEthFrameDownPre15mCRCErroredPackets, fkGponOnuPMStatsDetailUniEthFrameDownPre15mUndersizePackets, fkGponOnuPMStatsDetailUniEthFrameDownPre15mOversizePackets, fkGponOnuPMStatsDetailUniEthFrameDownPre15mPkt64Octets, 
                                fkGponOnuPMStatsDetailUniEthFrameDownPre15mPkt65To127Octets, fkGponOnuPMStatsDetailUniEthFrameDownPre15mPkt128To255Octets, fkGponOnuPMStatsDetailUniEthFrameDownPre15mPkt256To511Octets, fkGponOnuPMStatsDetailUniEthFrameDownPre15mPkt512To1023Octets, fkGponOnuPMStatsDetailUniEthFrameDownPre15mPkt1024To1518Octets, 
                                fkGponOnuPMStatsDetailUniEthFrameDownHourDropEvents, fkGponOnuPMStatsDetailUniEthFrameDownHourOctets, fkGponOnuPMStatsDetailUniEthFrameDownHourPackets, fkGponOnuPMStatsDetailUniEthFrameDownHourBcastPackets, fkGponOnuPMStatsDetailUniEthFrameDownHourMcastPackets, 
                                fkGponOnuPMStatsDetailUniEthFrameDownHourUcastPackets, fkGponOnuPMStatsDetailUniEthFrameDownHourCRCErroredPackets, fkGponOnuPMStatsDetailUniEthFrameDownHourUndersizePackets, fkGponOnuPMStatsDetailUniEthFrameDownHourOversizePackets, fkGponOnuPMStatsDetailUniEthFrameDownHourPkt64Octets, 
                                fkGponOnuPMStatsDetailUniEthFrameDownHourPkt65To127Octets, fkGponOnuPMStatsDetailUniEthFrameDownHourPkt128To255Octets, fkGponOnuPMStatsDetailUniEthFrameDownHourPkt256To511Octets, fkGponOnuPMStatsDetailUniEthFrameDownHourPkt512To1023Octets, fkGponOnuPMStatsDetailUniEthFrameDownHourPkt1024To1518Octets, 
                                fkGponOnuPMStatsDetailUniEthFrameDownDayDropEvents, fkGponOnuPMStatsDetailUniEthFrameDownDayOctets, fkGponOnuPMStatsDetailUniEthFrameDownDayPackets, fkGponOnuPMStatsDetailUniEthFrameDownDayBcastPackets, fkGponOnuPMStatsDetailUniEthFrameDownDayMcastPackets, 
                                fkGponOnuPMStatsDetailUniEthFrameDownDayUcastPackets, fkGponOnuPMStatsDetailUniEthFrameDownDayCRCErroredPackets, fkGponOnuPMStatsDetailUniEthFrameDownDayUndersizePackets, fkGponOnuPMStatsDetailUniEthFrameDownDayOversizePackets, fkGponOnuPMStatsDetailUniEthFrameDownDayPkt64Octets, 
                                fkGponOnuPMStatsDetailUniEthFrameDownDayPkt65To127Octets, fkGponOnuPMStatsDetailUniEthFrameDownDayPkt128To255Octets, fkGponOnuPMStatsDetailUniEthFrameDownDayPkt256To511Octets, fkGponOnuPMStatsDetailUniEthFrameDownDayPkt512To1023Octets, fkGponOnuPMStatsDetailUniEthFrameDownDayPkt1024To1518Octets, 
                                fkGponOnuPMStatsDetailUniEthFrameDownTotalDropEvents, fkGponOnuPMStatsDetailUniEthFrameDownTotalOctets, fkGponOnuPMStatsDetailUniEthFrameDownTotalPackets, fkGponOnuPMStatsDetailUniEthFrameDownTotalBcastPackets, fkGponOnuPMStatsDetailUniEthFrameDownTotalMcastPackets, 
                                fkGponOnuPMStatsDetailUniEthFrameDownTotalUcastPackets, fkGponOnuPMStatsDetailUniEthFrameDownTotalCRCErroredPackets, fkGponOnuPMStatsDetailUniEthFrameDownTotalUndersizePackets, fkGponOnuPMStatsDetailUniEthFrameDownTotalOversizePackets, fkGponOnuPMStatsDetailUniEthFrameDownTotalPkt64Octets, 
                                fkGponOnuPMStatsDetailUniEthFrameDownTotalPkt65To127Octets, fkGponOnuPMStatsDetailUniEthFrameDownTotalPkt128To255Octets, fkGponOnuPMStatsDetailUniEthFrameDownTotalPkt256To511Octets, fkGponOnuPMStatsDetailUniEthFrameDownTotalPkt512To1023Octets, fkGponOnuPMStatsDetailUniEthFrameDownTotalPkt1024To1518Octets, 
                                fkGponOnuPMStatsDetailUniEthFrameDownElapsedTimeAfterClear, fkGponOnuPMStatsDetailUniEthFrameDownElapsedTimeAfterUpdate, fkGponOnuPMStatsDetailUniEth3UniPort, fkGponOnuPMStatsDetailUniEth3Pre15mDropEvents, fkGponOnuPMStatsDetailUniEth3Pre15mOctets, 
                                fkGponOnuPMStatsDetailUniEth3Pre15mPackets, fkGponOnuPMStatsDetailUniEth3Pre15mBcastPackets, fkGponOnuPMStatsDetailUniEth3Pre15mMcastPackets, fkGponOnuPMStatsDetailUniEth3Pre15mUcastPackets, fkGponOnuPMStatsDetailUniEth3Pre15mUndersizePackets, 
                                fkGponOnuPMStatsDetailUniEth3Pre15mFragments, fkGponOnuPMStatsDetailUniEth3Pre15mJabbers, fkGponOnuPMStatsDetailUniEth3Pre15mPkt64Octets, fkGponOnuPMStatsDetailUniEth3Pre15mPkt65To127Octets, fkGponOnuPMStatsDetailUniEth3Pre15mPkt128To255Octets, 
                                fkGponOnuPMStatsDetailUniEth3Pre15mPkt256To511Octets, fkGponOnuPMStatsDetailUniEth3Pre15mPkt512To1023Octets, fkGponOnuPMStatsDetailUniEth3Pre15mPkt1024To1518Octets, fkGponOnuPMStatsDetailUniEth3HourDropEvents, fkGponOnuPMStatsDetailUniEth3HourOctets, 
                                fkGponOnuPMStatsDetailUniEth3HourPackets, fkGponOnuPMStatsDetailUniEth3HourBcastPackets, fkGponOnuPMStatsDetailUniEth3HourMcastPackets, fkGponOnuPMStatsDetailUniEth3HourUcastPackets, fkGponOnuPMStatsDetailUniEth3HourUndersizePackets, 
                                fkGponOnuPMStatsDetailUniEth3HourFragments, fkGponOnuPMStatsDetailUniEth3HourJabbers, fkGponOnuPMStatsDetailUniEth3HourPkt64Octets, fkGponOnuPMStatsDetailUniEth3HourPkt65To127Octets, fkGponOnuPMStatsDetailUniEth3HourPkt128To255Octets, 
                                fkGponOnuPMStatsDetailUniEth3HourPkt256To511Octets, fkGponOnuPMStatsDetailUniEth3HourPkt512To1023Octets, fkGponOnuPMStatsDetailUniEth3HourPkt1024To1518Octets, fkGponOnuPMStatsDetailUniEth3DayDropEvents, fkGponOnuPMStatsDetailUniEth3DayOctets, 
                                fkGponOnuPMStatsDetailUniEth3DayPackets, fkGponOnuPMStatsDetailUniEth3DayBcastPackets, fkGponOnuPMStatsDetailUniEth3DayMcastPackets, fkGponOnuPMStatsDetailUniEth3DayUcastPackets, fkGponOnuPMStatsDetailUniEth3DayUndersizePackets, 
                                fkGponOnuPMStatsDetailUniEth3DayFragments, fkGponOnuPMStatsDetailUniEth3DayJabbers, fkGponOnuPMStatsDetailUniEth3DayPkt64Octets, fkGponOnuPMStatsDetailUniEth3DayPkt65To127Octets, fkGponOnuPMStatsDetailUniEth3DayPkt128To255Octets, 
                                fkGponOnuPMStatsDetailUniEth3DayPkt256To511Octets, fkGponOnuPMStatsDetailUniEth3DayPkt512To1023Octets, fkGponOnuPMStatsDetailUniEth3DayPkt1024To1518Octets, fkGponOnuPMStatsDetailUniEth3TotalDropEvents, fkGponOnuPMStatsDetailUniEth3TotalOctets, 
                                fkGponOnuPMStatsDetailUniEth3TotalPackets, fkGponOnuPMStatsDetailUniEth3TotalBcastPackets, fkGponOnuPMStatsDetailUniEth3TotalMcastPackets, fkGponOnuPMStatsDetailUniEth3TotalUcastPackets, fkGponOnuPMStatsDetailUniEth3TotalUndersizePackets, 
                                fkGponOnuPMStatsDetailUniEth3TotalFragments, fkGponOnuPMStatsDetailUniEth3TotalJabbers, fkGponOnuPMStatsDetailUniEth3TotalPkt64Octets, fkGponOnuPMStatsDetailUniEth3TotalPkt65To127Octets, fkGponOnuPMStatsDetailUniEth3TotalPkt128To255Octets, 
                                fkGponOnuPMStatsDetailUniEth3TotalPkt256To511Octets, fkGponOnuPMStatsDetailUniEth3TotalPkt512To1023Octets, fkGponOnuPMStatsDetailUniEth3TotalPkt1024To1518Octets, fkGponOnuPMStatsDetailUniEth3ElapsedTimeAfterClear, fkGponOnuPMStatsDetailUniEth3ElapsedTimeAfterUpdate, 
                                fkGponProfile2PMProfilePMUniEthFrameUp, fkGponProfile2PMProfilePMUniEthFrameDown, fkGponProfile2PMProfilePMUniEth3, fkGponProfile2PMProfileControlPMUniEthFrameUp, fkGponProfile2PMProfileControlPMUniEthFrameDown, 
                                fkGponProfile2PMProfileControlPMUniEth3, fkGponOnuPortsID, fkGponProfileVoIPIpPathAuthName, fkGponProfileVoIPIpPathAuthPasswd, fkGponProfileVoIPIpwayAuthName, 
                                fkGponProfileVoIPIpwayAuthPasswd, fkGponProfileVoIPIpwayURL, fkGponProfileVoIPControlIpwayAuthName, fkGponProfileVoIPControlIpwayAuthPasswd, fkGponProfileVoIPControlIpwayURL, 
                                fkGponProfileVoIPDetailIndex, fkGponProfileVoIPDetailName, fkGponProfileVoIPDetailFaxMode, fkGponProfileVoIPDetailCodecType1st, fkGponProfileVoIPDetailCodecPeriod1st, 
                                fkGponProfileVoIPDetailCodecSilenceSuppression1st, fkGponProfileVoIPDetailCodecType2nd, fkGponProfileVoIPDetailCodecPeriod2nd, fkGponProfileVoIPDetailCodecSilenceSuppression2nd, fkGponProfileVoIPDetailCodecType3rd, 
                                fkGponProfileVoIPDetailCodecPeriod3rd, fkGponProfileVoIPDetailCodecSilenceSuppression3rd, fkGponProfileVoIPDetailCodecType4th, fkGponProfileVoIPDetailCodecPeriod4th, fkGponProfileVoIPDetailCodecSilenceSuppression4th, 
                                fkGponProfileVoIPDetailOobdtmf, fkGponProfileVoIPDetailAnnouncementType, fkGponProfileVoIPDetailJitterTarget, fkGponProfileVoIPDetailJitterBuffMax, fkGponProfileVoIPDetailEchoCancel, 
                                fkGponProfileVoIPDetailPstnProtoVariant, fkGponProfileVoIPDetailDtmfDigitLevels, fkGponProfileVoIPDetailDtmfDigitDuration, fkGponProfileVoIPDetailHookFlashTimeMin, fkGponProfileVoIPDetailHookFlashTimeMax, 
                                fkGponProfileVoIPDetailSignalingCode, fkGponProfileVoIPDetailRtpLocalPortMin, fkGponProfileVoIPDetailRtpLocalPortMax, fkGponProfileVoIPDetailRtpDscpMark, fkGponProfileVoIPDetailRtpPiggybackEvent, 
                                fkGponProfileVoIPDetailRtpToneEvent, fkGponProfileVoIPDetailRtpDtmfEvent, fkGponProfileVoIPDetailRtpCasEvent, fkGponProfileVoIPDetailProtocol, fkGponProfileVoIPDetailMgcPriServer, 
                                fkGponProfileVoIPDetailMgcSecServer, fkGponProfileVoIPDetailMgcMsgVersion, fkGponProfileVoIPDetailMgcMsgFormat, fkGponProfileVoIPDetailMgcMaxRetryTime, fkGponProfileVoIPDetailMgcSvcChangeDelay, 
                                fkGponProfileVoIPDetailMgcTerminationId, fkGponProfileVoIPDetailMgcSoftswitch, fkGponProfileVoIPDetailVoicemailServer, fkGponProfileVoIPDetailVoicemmailExpireTime, fkGponProfileVoIPDetailReleaseTime, 
                                fkGponProfileVoIPDetailRohTimer, fkGponProfileVoIPDetailProxyServer, fkGponProfileVoIPDetailOutboundProxyServer, fkGponProfileVoIPDetailRegisterServer, fkGponProfileVoIPDetailHostPartServer, 
                                fkGponProfileVoIPDetailPriDns, fkGponProfileVoIPDetailSecDns, fkGponProfileVoIPDetailRegExpTime, fkGponProfileVoIPDetailReregHeadStartTime, fkGponProfileVoIPDetailSoftSwitchVendor, 
                                fkGponProfileVoIPDetailSipOptionTransmitCtl, fkGponProfileVoIPDetailSipUriFormat, fkGponProfileVoIPDetailCallerId, fkGponProfileVoIPDetailCallWaiting, fkGponProfileVoIPDetailCallProgressTransfer, 
                                fkGponProfileVoIPDetailCallPresent, fkGponProfileVoIPDetailDirectConnect, fkGponProfileVoIPDetailDirectConnectUri, fkGponProfileVoIPDetailBridgedLineAgentUri, fkGponProfileVoIPDetailConferenceFactoryUri, 
                                fkGponProfileVoIPDetailCancelCallWait, fkGponProfileVoIPDetailCallPark, fkGponProfileVoIPDetailCallerIdAct, fkGponProfileVoIPDetailCallerIdDeact, fkGponProfileVoIPDetailDoNotDisturbAct, 
                                fkGponProfileVoIPDetailDoNotDisturbDeact, fkGponProfileVoIPDetailDoNotDisturbPinChange, fkGponProfileVoIPDetailEmergServiceNumber, fkGponProfileVoIPDetailIntercomService, fkGponProfileVoIPDetailControlRequest, 
                                fkGponProfileVoIPDetailControlStatus, fkGponProfileVoIPDetailControlTimer, fkGponProfileVoIPDetailControlTimeStamp, fkGponProfileVoIPDetailControlReqResult, fkGponProfileVoIPDetailControlIndex, 
                                fkGponProfileVoIPDetailControlName, fkGponProfileVoIPDetailControlFaxMode, fkGponProfileVoIPDetailControlOobdtmf, fkGponProfileVoIPDetailControlAnnouncementType, fkGponProfileVoIPDetailControlJitterTarget, 
                                fkGponProfileVoIPDetailControlJitterBuffMax, fkGponProfileVoIPDetailControlEchoCancel, fkGponProfileVoIPDetailControlPstnProtoVariant, fkGponProfileVoIPDetailControlDtmfDigitLevels, fkGponProfileVoIPDetailControlDtmfDigitDuration, 
                                fkGponProfileVoIPDetailControlHookFlashTimeMin, fkGponProfileVoIPDetailControlHookFlashTimeMax, fkGponProfileVoIPDetailControlSignalingCode, fkGponProfileVoIPDetailControlRtpLocalPortMin, fkGponProfileVoIPDetailControlRtpLocalPortMax, 
                                fkGponProfileVoIPDetailControlRtpDscpMark, fkGponProfileVoIPDetailControlRtpPiggybackEvent, fkGponProfileVoIPDetailControlRtpToneEvent, fkGponProfileVoIPDetailControlRtpDtmfEvent, fkGponProfileVoIPDetailControlRtpCasEvent, 
                                fkGponProfileVoIPDetailControlProtocol, fkGponProfileVoIPDetailControlMgcPriServer, fkGponProfileVoIPDetailControlMgcSecServer, fkGponProfileVoIPDetailControlMgcMsgVersion, fkGponProfileVoIPDetailControlMgcMsgFormat, 
                                fkGponProfileVoIPDetailControlMgcMaxRetryTime, fkGponProfileVoIPDetailControlMgcSvcChangeDelay, fkGponProfileVoIPDetailControlMgcTerminationId, fkGponProfileVoIPDetailControlMgcSoftswitch, fkGponProfileVoIPDetailControlVoicemailServer, 
                                fkGponProfileVoIPDetailControlVoicemmailExpireTime, fkGponProfileVoIPDetailControlReleaseTime, fkGponProfileVoIPDetailControlRohTimer, fkGponProfileVoIPDetailControlProxyServer, fkGponProfileVoIPDetailControlOutboundProxyServer, 
                                fkGponProfileVoIPDetailControlRegisterServer, fkGponProfileVoIPDetailControlHostPartServer, fkGponProfileVoIPDetailControlPriDns, fkGponProfileVoIPDetailControlSecDns, fkGponProfileVoIPDetailControlRegExpTime, 
                                fkGponProfileVoIPDetailControlReregHeadStartTime, fkGponProfileVoIPDetailControlSoftSwitchVendor, fkGponProfileVoIPDetailControlSipOptionTransmitCtl, fkGponProfileVoIPDetailControlSipUriFormat, fkGponProfileVoIPDetailControlCallerId, 
                                fkGponProfileVoIPDetailControlCallWaiting, fkGponProfileVoIPDetailControlCallProgressTransfer, fkGponProfileVoIPDetailControlCallPresent, fkGponProfileVoIPDetailControlDirectConnect, fkGponProfileVoIPDetailControlDirectConnectUri, 
                                fkGponProfileVoIPDetailControlBridgedLineAgentUri, fkGponProfileVoIPDetailControlConferenceFactoryUri, fkGponProfileVoIPDetailControlCancelCallWait, fkGponProfileVoIPDetailControlCallerIdAct, fkGponProfileVoIPDetailControlCallerIdDeact, 
                                fkGponProfileVoIPDetailControlDoNotDisturbAct, fkGponProfileVoIPDetailControlDoNotDisturbDeact, fkGponProfileVoIPDetailControlDoNotDisturbPinChange, fkGponProfileVoIPDetailControlEmergServiceNumber, fkGponProfileVoIPDetailControlIntercomService, 
                                fkGponProfile2BridgeUniMaxHost, fkGponProfile2BridgeUniControlMaxHost, fkGponProfile2BridgeGemId, fkGponProfile2BridgeGemVlanFilterMode, fkGponProfile2BridgeGemVlanFilter, 
                                fkGponProfile2BridgeGemControlRequest, fkGponProfile2BridgeGemControlStatus, fkGponProfile2BridgeGemControlTimer, fkGponProfile2BridgeGemControlTimeStamp, fkGponProfile2BridgeGemControlReqResult, 
                                fkGponProfile2BridgeGemControlTName, fkGponProfile2BridgeGemControlBridgeId, fkGponProfile2BridgeGemControlId, fkGponProfile2BridgeGemControlVlanFilterMode, fkGponProfile2BridgeGemControlVlanFilter, 
                                fkGponProfile2BridgeTdmId, fkGponProfile2BridgeTdmControlRequest, fkGponProfile2BridgeTdmControlStatus, fkGponProfile2BridgeTdmControlTimer, fkGponProfile2BridgeTdmControlTimeStamp, 
                                fkGponProfile2BridgeTdmControlReqResult, fkGponProfile2BridgeTdmControlTName, fkGponProfile2BridgeTdmControlBridgeId, fkGponProfile2BridgeTdmControlId, fkGponProfileVoIPIpPathURL, 
                                fkGponProfile2IpHostSvcId, fkGponProfile2IpHostSvcAddressType, fkGponProfile2IpHostSvcPriDns, fkGponProfile2IpHostSvcSecDns, fkGponProfile2IpHostSvcVlanFilterMode, 
                                fkGponProfile2IpHostSvcVlanFilter, fkGponProfile2IpHostSvcVlanOpDsOperFlag, fkGponProfile2IpHostSvcVlanOpUsOperFlag, fkGponProfile2IpHostSvcVlanOpUsOperVid, fkGponProfile2IpHostSvcVlanOpUsOperCos, 
                                fkGponProfile2IpHostSvcControlRequest, fkGponProfile2IpHostSvcControlStatus, fkGponProfile2IpHostSvcControlTimer, fkGponProfile2IpHostSvcControlTimeStamp, fkGponProfile2IpHostSvcControlReqResult, 
                                fkGponProfile2IpHostSvcControlTName, fkGponProfile2IpHostSvcControlId, fkGponProfile2IpHostSvcControlAddressType, fkGponProfile2IpHostSvcControlPriDns, fkGponProfile2IpHostSvcControlSecDns, 
                                fkGponProfile2IpHostSvcControlVlanFilterMode, fkGponProfile2IpHostSvcControlVlanFilter, fkGponProfile2IpHostSvcControlVlanOpDsOperFlag, fkGponProfile2IpHostSvcControlVlanOpUsOperFlag, fkGponProfile2IpHostSvcControlVlanOpUsOperVid, 
                                fkGponProfile2IpHostSvcControlVlanOpUsOperCos, fkGponProfile2IpHostTdmId, fkGponProfile2IpHostTdmControlRequest, fkGponProfile2IpHostTdmControlTimer, fkGponProfile2IpHostTdmControlTimeStamp, 
                                fkGponProfile2IpHostTdmControlReqResult, fkGponProfile2IpHostTdmControlTName, fkGponProfile2IpHostVoipControlRequest, fkGponProfile2IpHostVoipControlStatus, fkGponProfile2IpHostVoipControlTimer, 
                                fkGponProfile2IpHostVoipControlTimeStamp, fkGponProfile2IpHostVoipControlReqResult, fkGponProfile2IpHostVoipControlTName, fkGponProfile2IpHostVoipControlIpHostSvcId, fkGponProfile2IpHostVoipControlId, 
                                fkGponProfile2IpHostVoipId, fkGponProfile2IpHostTdmControlStatus, fkGponProfile2IpHostTdmControlIpHostSvcId, fkGponProfile2VoipSvcId, fkGponProfile2VoipSvcManageMethod, 
                                fkGponProfile2VoipSvcProtocol, fkGponProfile2VoipSvcIppathUrl, fkGponProfile2VoipSvcIppathUser, fkGponProfile2VoipSvcIppathPasswd, fkGponProfile2VoipSvcControlRequest, 
                                fkGponProfile2VoipSvcControlStatus, fkGponProfile2VoipSvcControlTimer, fkGponProfile2VoipSvcControlTimeStamp, fkGponProfile2VoipSvcControlReqResult, fkGponProfile2VoipSvcControlTName, 
                                fkGponProfile2VoipSvcControlId, fkGponProfile2VoipSvcControlManageMethod, fkGponProfile2VoipSvcControlProtocol, fkGponProfile2VoipSvcControlIppathUrl, fkGponProfile2VoipSvcControlIppathUser, 
                                fkGponProfile2VoipSvcControlIppathPasswd, fkGponProfile2VoipSvcUniType, fkGponProfile2VoipSvcUniId, fkGponProfile2VoipSvcUniImpedance, fkGponProfile2VoipSvcUniTransmissionPath, 
                                fkGponProfile2VoipSvcUniGainRx, fkGponProfile2VoipSvcUniGainTx, fkGponProfile2VoipSvcUniHoldOverTime, fkGponProfile2VoipSvcUniControlRequest, fkGponProfile2VoipSvcUniControlStatus, 
                                fkGponProfile2VoipSvcUniControlTimer, fkGponProfile2VoipSvcUniControlTimeStamp, fkGponProfile2VoipSvcUniControlReqResult, fkGponProfile2VoipSvcUniControlTName, fkGponProfile2VoipSvcUniControlVoipSvcId, 
                                fkGponProfile2VoipSvcUniControlType, fkGponProfile2VoipSvcUniControlId, fkGponProfile2VoipSvcUniControlImpedance, fkGponProfile2VoipSvcUniControlTransmissionPath, fkGponProfile2VoipSvcUniControlGainRx, 
                                fkGponProfile2VoipSvcUniControlGainTx, fkGponProfile2VoipSvcUniControlHoldOverTime, fkGponProfile2TdmId, fkGponProfile2TdmExpectedType, fkGponProfile2TdmEncoding, 
                                fkGponProfile2TdmLineLengthPowerFeed, fkGponProfile2TdmDs1Mode, fkGponProfile2TdmLineType, fkGponProfile2TdmControlRequest, fkGponProfile2TdmControlStatus, 
                                fkGponProfile2TdmControlTimer, fkGponProfile2TdmControlTimeStamp, fkGponProfile2TdmControlReqResult, fkGponProfile2TdmControlTName, fkGponProfile2TdmControlId, 
                                fkGponProfile2TdmControlExpectedType, fkGponProfile2TdmControlFramig, fkGponProfile2TdmControlEncoding, fkGponProfile2TdmControlLineLengthPowerFeed, fkGponProfile2TdmControlDs1Mode, 
                                fkGponProfile2TdmControlLineType, fkGponProfile2IpHostTdmControlId, fkGponProfileVoIPDetailControlCallPark, fkGponProfile2TdmSvcFilterMode, fkGponProfile2TdmSvcFilter, 
                                fkGponProfileVoIPDetailCallHold, fkGponProfileVoIPDetailControlCallHold, fkGponProfileVoIPDetailMgcMaxRetryAttempts, fkGponProfileVoIPDetailControlMgcMaxRetryAttempts, fkGponProfile2OnuCircuitPackCardConfigCDs1E1, 
                                fkGponProfile2OnuCircuitPackCardConfigCDs1E1J1, fkGponProfile2OnuControlCircuitPackCardConfigCDs1E1, fkGponProfile2BridgeIpHostId, fkGponProfile2BridgeIpHostControlRequest, fkGponProfile2BridgeIpHostControlStatus, 
                                fkGponProfile2BridgeIpHostControlTimer, fkGponProfile2BridgeIpHostControlTimeStamp, fkGponProfile2BridgeIpHostControlReqResult, fkGponProfile2BridgeIpHostControlTName, fkGponProfile2BridgeIpHostControlBridgeId, 
                                fkGponProfile2BridgeIpHostControlId, fkGponSystemOltVendorId, fkGponSystemOltVersion, fkGponProfile2OnuControlCircuitPackCardConfigCDs1E1J1, fkGponProfileVoIPDetailControlCodecType1st, 
                                fkGponProfileVoIPDetailControlCodecPeriod1st, fkGponProfileVoIPDetailControlCodecSilenceSuppression1st, fkGponProfileVoIPDetailControlCodecType2nd, fkGponProfileVoIPDetailControlCodecPeriod2nd, fkGponProfileVoIPDetailControlCodecSilenceSuppression2nd, 
                                fkGponProfileVoIPDetailControlCodecType3rd, fkGponProfileVoIPDetailControlCodecPeriod3rd, fkGponProfileVoIPDetailControlCodecSilenceSuppression3rd, fkGponProfileVoIPDetailControlCodecType4th, fkGponProfileVoIPDetailCodecControlPeriod4th, 
                                fkGponProfileVoIPDetailControlCodecSilenceSuppression4th, fkGponProfile2VoipSvcVoipProfile, fkGponProfile2VoipSvcControlVoipProfile, fkGponProfile2TdmSvcControlFilterMode, fkGponOnuVoipAvailSignalProtocol, 
                                fkGponOnuVoipAvailConfigMethod, fkGponOltAntiSpoofingFilter, fkGponOltControlAntiSpoofingFilter, fkGponOltControlAntiSpoofingExpireTime, fkGponIgmpGroupControlRequest, 
                                fkGponIgmpGroupControlStatus, fkGponIgmpGroupControlTimer, fkGponIgmpGroupControlTimeStamp, fkGponIgmpGroupControlReqResult, fkGponIgmpGroupControlOltId, 
                                fkGponIgmpGroupControlOnuId, fkGponProfile2PMProfilePMPseduowire, fkGponProfile2PMProfilePMUniCes, fkGponProfile2PMProfileControlPMPseduowire, fkGponProfile2PMProfileControlPMUniCes, 
                                fkGponProfile2TdmSvcControlFilter, fkGponSystemOltModel, fkGponSystemOltMac, fkGponSystemOltSlot, fkGponSystemOltPort, 
                                fkGponSystemOltOnuId, fkGponOltMaxOnuCount, fkGponOltControlMaxOnuCount, fkGponOnuPortHookState, fkGponOnuPortSensedType, 
                                fkGponOnuVoipLineOltId, fkGponOnuVoipLineOnuId, fkGponOnuVoipLineId, fkGponOnuVoipLineStatus, fkGponOnuVoipLineUsedCodec, 
                                fkGponOnuVoipLineSessionType, fkGponOnuVoipLine1stProtocolPeriod, fkGponOnuVoipLine1stDestAddr, fkGponOnuVoipLine2ndProtocolPeriod, fkGponOnuVoipLine2ndDestAddr, 
                                fkGponOnuVoipLineControlRequest, fkGponOnuVoipLineControlStatus, fkGponOnuVoipLineControlTimer, fkGponOnuVoipLineControlTimeStamp, fkGponOnuVoipLineControlReqResult, 
                                fkGponOnuVoipLineControlOltId, fkGponOnuFWAutoUpgradeModelExclude, fkGponOnuFWAutoUpgradeModelControlExclude, fkGponAntiSpoofingOltId, fkGponAntiSpoofingOnuId, 
                                fkGponAntiSpoofingVlanId, fkGponAntiSpoofingMacIndex, fkGponAntiSpoofingMac, fkGponAntiSpoofingPortId, fkGponAntiSpoofingDupPortId, 
                                fkGponAntiSpoofingTimerStatus, fkGponAntiSpoofingControlRequest, fkGponAntiSpoofingControlStatus, fkGponAntiSpoofingControlTimer, fkGponAntiSpoofingControlTimeStamp, 
                                fkGponAntiSpoofingControlReqResult, fkGponAntiSpoofingControlOltId, fkGponAntiSpoofingControlOnuId, fkGponAntiSpoofingControlVlanId, fkGponAntiSpoofingControlMac, 
                                fkGponAntiSpoofingControlPortId, fkGponAntiSpoofingControlTimerStatus, fkGponOnuHostPriDns, fkGponOnuHostSecDns, fkGponOnuHostIpOption, 
                                fkGponOnuHostMacAddress, fkGponOnuHostDomainName, fkGponOnuHostHostName, fkGponOnuHostCurIpAddr, fkGponOnuHostCurMask, 
                                fkGponOnuHostCurGW, fkGponOnuHostCurPriDns, fkGponOnuHostCurSecDns, fkGponAntiSpoofingFilterStatus, fkGponProfileVoIPDetailDialplanCritTimeout, 
                                fkGponProfileVoIPDetailDialplanPartTimeout, fkGponProfileVoIPDetailDialplanFormat, fkGponProfileVoIPDetailControlDialplanCritTimeout, fkGponProfileVoIPDetailControlDialplanPartTimeout, fkGponProfileVoIPDetailControlDialplanFormat, 
                                fkGponProfileVoIPDetailDialPlanTableIndex, fkGponProfileVoIPDetailDialPlanTableToken, fkGponProfileVoIPDetailDialPlanControlRequest, fkGponProfileVoIPDetailDialPlanControlStatus, fkGponProfileVoIPDetailDialPlanControlTimer, 
                                fkGponProfileVoIPDetailDialPlanControlTimeStamp, fkGponProfileVoIPDetailDialPlanControlReqResult, fkGponProfileVoIPDetailDialPlanControlTableIndex, fkGponProfileVoIPDetailDialPlanControlTableToken, fkGponProfileVoIPDetailDialPlanControlProfileIndex, 
                                fkGponRedGroupStandbyLinkStatus, fkGponRedGroupSlaveOltAdminStatus, fkGponRedGroupControlStandbyOptic, fkGponRedGroupControlStandbyOpticEnableTime, fkGponRedGroupControlSlaveAdminStatus, 
                                fkGponRedGroupControlTrigger, fkGponRedGroupTrigger, fkGponIgmpGroupVlanId, fkGponOnuPortUniDescription, fkGponOnuPortControlUniDescription, 
                                fkGponOnuPortConfSpeed, fkGponOnuPortConfDuplex, fkGponOnuPortControlDuplex, fkGponOnuPortMediumMode, fkGponOnuPortControlMediumMode, 
                                fkGponOnuVoipLineControlOnuId, fkGponOltAntiSpoofingExpireTime, fkGponOnuFWAutoUpgradeBaseRetryCounts, fkGponOnuFWAutoUpgradeControlBaseRequest, fkGponOnuFWAutoUpgradeControlBaseStatus, 
                                fkGponOnuFWAutoUpgradeControlBaseTimer, fkGponOnuFWAutoUpgradeControlBaseReqResult, fkGponOnuFWAutoUpgradeControlBaseCount, fkGponOltBwBEMethod, fkGponOltDsGemMapping, 
                                fkGponOltControlBwBEMethod, fkGponOltControlDsGemMapping, fkGponProfile2BridgeUniExtVlanName, fkGponProfile2BridgeUniControlExtVlanName, fkGponProfile2IpHostSvcExtVlanName, 
                                fkGponProfile2IpHostSvcControlExtVlanName, fkGponVlanGemMappingVid, fkGponVlanGemMappingMapperId, fkGponVlanGemMappingControlRequest, fkGponVlanGemMappingControlStatus, 
                                fkGponVlanGemMappingControlTimer, fkGponVlanGemMappingControlTimeStamp, fkGponVlanGemMappingControlReqResult, fkGponVlanGemMappingControlOltId, fkGponVlanGemMappingControlOnuId, 
                                fkGponProfile2ExtVlanIndex, fkGponProfile2ExtVlanName, fkGponProfile2ExtVlanDownStreamMode, fkGponProfile2ExtVlanDscpToCosMapTable, fkGponProfile2ExtVlanTpidInput, 
                                fkGponProfile2ExtVlanTpidOutput, fkGponProfile2ExtVlanControlRequest, fkGponProfile2ExtVlanControlStatus, fkGponProfile2ExtVlanControlTimer, fkGponProfile2ExtVlanControlTimeStamp, 
                                fkGponProfile2ExtVlanControlReqResult, fkGponProfile2ExtVlanControlName, fkGponProfile2ExtVlanControlDownStreamMode, fkGponProfile2ExtVlanControlDscpToCosMapTable, fkGponProfile2ExtVlanControlTpidInput, 
                                fkGponProfile2ExtVlanControlTpidOutput, fkGponProfile2TdmFraming, fkGponOnuPortLoopbackStatus, fkGponOnuPortControlLoopbackStatus, fkGponProfile2ExtVlanTagType, 
                                fkGponProfile2ExtVlanTagIndex, fkGponProfile2ExtVlanTagFilterEtherType, fkGponProfile2ExtVlanTagTreatInnerCopyVid, fkGponProfile2ExtVlanTagTreatInnerCopyCos, fkGponProfile2ExtVlanTagTreatOuterCopyVid, 
                                fkGponProfile2ExtVlanTagTreatOuterCopyCos, fkGponProfile2ExtVlanTagTreatTag, fkGponProfile2ExtVlanTagFilterInnerVid, fkGponProfile2ExtVlanTagFilterInnerCos, fkGponProfile2ExtVlanTagFilterInnerTpidDei, 
                                fkGponProfile2ExtVlanTagFilterOuterVid, fkGponProfile2ExtVlanTagFilterOuterCos, fkGponProfile2ExtVlanTagFilterOuterTpidDei, fkGponProfile2ExtVlanTagControlRequest, fkGponProfile2ExtVlanTagControlStatus, 
                                fkGponProfile2ExtVlanTagControlTimer, fkGponProfile2ExtVlanTagControlTimeStamp, fkGponProfile2ExtVlanTagControlReqResult, fkGponProfile2ExtVlanTagControlType, fkGponProfile2ExtVlanTagControlIndex, 
                                fkGponProfile2ExtVlanTagControlFilterEtherType, fkGponProfile2ExtVlanTagControlTreatInnerCopyVid, fkGponProfile2ExtVlanTagControlTreatInnerCopyCos, fkGponProfile2ExtVlanTagControlTreatOuterCopyVid, fkGponProfile2ExtVlanTagControlTreatOuterCopyCos, 
                                fkGponProfile2ExtVlanTagControlTreatTag, fkGponProfile2ExtVlanTagControlFilterInnerCos, fkGponProfile2ExtVlanTagControlFilterInnerTpidDei, fkGponProfile2ExtVlanTagControlFilterOuterVid, fkGponProfile2ExtVlanTagControlFilterOuterCos, 
                                fkGponGemPortId, fkGponGemPortMapperId, fkGponGemPortCos, fkGponProfile2ExtVlanTagTreatInnerTpidDei, fkGponProfile2ExtVlanTagTreatOuterTpidDei, 
                                fkGponProfile2ExtVlanTagControlTreatInnerTpidDei, fkGponProfile2ExtVlanTagControlTreatOuterTpidDei, fkGponGemPortNum, fkGponVlanGemMappingOnuid, fkGponVlanGemMappingGemPort, 
                                fkGponOnuPMStatsDetailGEMPortIndex, fkGponOnuPMStatsDetailAniPortIndex, fkGponOnuPasswordType, fkGponOnuSupplierSerial, fkGponOnuHWRevision, 
                                fkGponOnuCPULoad, fkGponOnuCPULoadThreshold, fkGponOnuMemoryUsage, fkGponOnuMemoryThreshold, fkGponOnuTemperature, 
                                fkGponOnuTemperatureHighThreshold, fkGponOnuTemperatureLowThreshold, fkGponProfile2OnuSWWatchdog, fkGponProfile2OnuLinkPassThrough, fkGponProfile2OnuControlSWWatchdog, 
                                fkGponProfile2OnuControlLinkPassThrough, fkGponProfile2ExtVlanTagControlFilterOuterTpidDei, fkGponProfile2ExtVlanTagControlName, fkGponOnuPortOpticModuleSpeed, fkGponOnuPortOpticModuleWavelength, 
                                fkGponOnuPortOpticModuleConnecterType, fkGponOnuPortOpticModuleVendorName, fkGponOnuPortOpticModuleVendorPartName, fkGponOnuPortOpticModuleVendorRevision, fkGponProfile2ExtVlanTagControlFilterInnerVid, 
                                fkGponOnuPortOpticModuleInstall, fkGponOnuPortOpticModuleTransceiverType, fkGponOnuPortOpticModuleLengthMode, fkGponProfile2OnuCpuLoadThr, fkGponProfile2OnuMemoryUsageThr, 
                                fkGponProfile2OnuTemperatureHighThr, fkGponProfile2OnuTemperatureLowThr, fkGponProfile2OnuControlCpuLoadThr, fkGponProfile2OnuControlMemoryUsageThr, fkGponProfile2OnuControlTemperatureHighThr, 
                                fkGponProfile2OnuControlTemperatureLowThr, fkGponOnuPMStatsCurrentDetailGEMPortIndex, fkGponOnuPMStatsCurrentDetailGEMPort, fkGponOnuPMStatsCurrentDetailGEMLostPackets, fkGponOnuPMStatsCurrentDetailGEMMisInsertedPackets, 
                                fkGponOnuPMStatsCurrentDetailGEMReceivedPackets, fkGponOnuPMStatsCurrentDetailGEMReceivedBlocks, fkGponOnuPMStatsCurrentDetailGEMTransmittedBlocks, fkGponOnuPMStatsCurrentDetailGEMImpairedBlocks, fkGponOnuPMStatsCurrentDetailAniPortIndex, 
                                fkGponOnuPMStatsCurrentDetailAniPort, fkGponOnuPMStatsCurrentDetailAniDiscardedFrames, fkGponOnuPMStatsCurrentDetailUniEthFrameUpUniPort, fkGponOnuPMStatsCurrentDetailUniEthFrameUpDropEvents, fkGponOnuPMStatsCurrentDetailUniEthFrameUpOctets, 
                                fkGponOnuPMStatsCurrentDetailUniEthFrameUpPackets, fkGponOnuPMStatsCurrentDetailUniEthFrameUpBcastPackets, fkGponOnuPMStatsCurrentDetailUniEthFrameUpMcastPackets, fkGponOnuPMStatsCurrentDetailUniEthFrameUpUcastPackets, fkGponOnuPMStatsCurrentDetailUniEthFrameUpCRCErroredPackets, 
                                fkGponOnuPMStatsCurrentDetailUniEthFrameUpUndersizePackets, fkGponOnuPMStatsCurrentDetailUniEthFrameUpOversizePackets, fkGponOnuPMStatsCurrentDetailUniEthFrameUpPkt64Octets, fkGponOnuPMStatsCurrentDetailUniEthFrameUpPkt65To127Octets, fkGponOnuPMStatsCurrentDetailUniEthFrameUpPkt128To255, 
                                fkGponOnuPMStatsCurrentDetailUniEthFrameUpPkt256To511, fkGponOnuPMStatsCurrentDetailUniEthFrameUpPkt512To1023, fkGponOnuPMStatsCurrentDetailUniEthFrameUpPkt1024To1518, fkGponOnuPMStatsCurrentDetailUniEthFrameDownUniPort, fkGponOnuPMStatsCurrentDetailUniEthFrameDownDropEvents, 
                                fkGponOnuPMStatsCurrentDetailUniEthFrameDownOctets, fkGponOnuPMStatsCurrentDetailUniEthFrameDownPackets, fkGponOnuPMStatsCurrentDetailUniEthFrameDownBcastPackets, fkGponOnuPMStatsCurrentDetailUniEthFrameDownMcastPackets, fkGponOnuPMStatsCurrentDetailUniEthFrameDownUcastPackets, 
                                fkGponOnuPMStatsCurrentDetailUniEthFrameDownCRCErroredPackets, fkGponOnuPMStatsCurrentDetailUniEthFrameDownUndersizePackets, fkGponOnuPMStatsCurrentDetailUniEthFrameDownOversizePackets, fkGponOnuPMStatsCurrentDetailUniEthFrameDownPkt64Octets, fkGponOnuPMStatsCurrentDetailUniEthFrameDownPkt65To127Octets, 
                                fkGponOnuPMStatsCurrentDetailUniEthFrameDownPkt128To255Octets, fkGponOnuPMStatsCurrentDetailUniEthFrameDownmPkt256To511Octets, fkGponOnuPMStatsCurrentDetailUniEthFrameDownmPkt512To1023Octets, fkGponOnuPMStatsCurrentDetailUniEthFrameDownPkt1024To1518Octets, fkGponOnuPMStatsCurrentDetailUniEth3UniPort, 
                                fkGponOnuPMStatsCurrentDetailUniEth3DropEvents, fkGponOnuPMStatsCurrentDetailUniEth3Octets, fkGponOnuPMStatsCurrentDetailUniEth3Packets, fkGponOnuPMStatsCurrentDetailUniEth3BcastPackets, fkGponOnuPMStatsCurrentDetailUniEth3McastPackets, 
                                fkGponOnuPMStatsCurrentDetailUniEth3UcastPackets, fkGponOnuPMStatsCurrentDetailUniEth3UndersizePackets, fkGponOnuPMStatsCurrentDetailUniEth3Fragments, fkGponOnuPMStatsCurrentDetailUniEth3Jabbers, fkGponOnuPMStatsCurrentDetailUniEth3Pkt64Octets, 
                                fkGponOnuPMStatsCurrentDetailUniEth3Pkt65To127Octets, fkGponOnuPMStatsCurrentDetailUniEth3Pkt128To255Octets, fkGponOnuPMStatsCurrentDetailUniEth3Pkt256To511Octets, fkGponOnuPMStatsCurrentDetailUniEth3Pkt512To1023Octets, fkGponOnuPMStatsCurrentDetailUniEth3Pkt1024To1518Octets, 
                                fkGponRedGroupDbSyncStatus, fkGponOnuPortLinkUpCount, fkGponOnuPortLinkDownCount, fkGponProfileVoIPOmciMgcTerminationId, fkGponProfileVoIPOmciControlMgcTerminationId, 
                                fkGponOnuPortOpticModuleLength, fkGponOnuPortOpticModuleTransceiverDetailType, fkGponOnuPortOpticModuleVendorSerialNumber, fkGponOnuPortOpticModuleProductDate, fkGponProfile2TcontQueue1Weight, 
                                fkGponProfile2TcontQueue2Weight, fkGponProfile2TcontQueue3Weight, fkGponProfile2TcontQueue4Weight, fkGponProfile2TcontQueue5Weight, fkGponProfile2TcontQueue6Weight, 
                                fkGponProfile2TcontQueue7Weight, fkGponProfile2TcontQueue8Weight, fkGponProfile2TcontControlRequest, fkGponProfile2TcontControlStatus, fkGponProfile2TcontControlTimer, 
                                fkGponProfile2TcontControlTimeStamp, fkGponProfile2TcontControlReqResult, fkGponProfile2TcontControlTName, fkGponProfile2TcontControlID, fkGponProfile2TcontControlDbaProfile, 
                                fkGponProfile2TcontControlQueue1Weight, fkGponProfile2TcontControlQueue2Weight, fkGponProfile2TcontControlQueue3Weight, fkGponProfile2TcontControlQueue4Weight, fkGponProfile2TcontControlQueue5Weight, 
                                fkGponProfile2TcontControlQueue6Weight, fkGponProfile2TcontControlQueue7Weight, fkGponProfile2TcontControlQueue8Weight, fkGponProfileVoIPServiceMgcMessageId, fkGponProfileVoIPServiceControlRequest, 
                                fkGponProfileVoIPServiceControlStatus, fkGponProfileVoIPServiceControlTimer, fkGponProfileVoIPServiceControlTimeStamp, fkGponProfileVoIPServiceControlReqResult, fkGponProfileVoIPServiceControlIndex, 
                                fkGponOnuLoopDetectStateSupport, fkGponOnuLoopDetectStateDetect, fkGponOnuLoopDetectStateBlock, fkGponOnuLoopDetectUnblockReason, fkGponProfile2OnuLoopDetectStatus, 
                                fkGponProfile2OnuLoopDetectSendPeriod, fkGponProfile2OnuLoopDetectDetectedAction, fkGponProfile2OnuLoopDetectBlcokTimer, fkGponProfile2OnuControlLoopDetectStatus, fkGponProfile2OnuControlLoopDetectSendPeriod, 
                                fkGponProfile2OnuControlLoopDetectDetectedAction, fkGponProfile2OnuControlLoopDetectBlcokTimer, fkGponProfileVoIPServiceControlMgcMessageId, fkGponProfileVoIPServiceIndex, fkGponProfileVoIPServiceControlOltId, 
                                fkGponProfileVoIPServiceControlOnuId, fkGponBaseControlOnuPasswordType, fkGponOnuPortOpticModuleTemper, fkGponOnuPortOpticModuleVoltage, fkGponOnuPortOpticModuleTxbias, 
                                fkGponOnuPortOpticModuleTxPower, fkGponOnuPortOpticModuleRxPower, fkGponOnuAniId, fkGponOnuAniType, fkGponOnuAniOpticModuleInstall, 
                                fkGponOnuAniOpticModuleTransceiverType, fkGponOnuAniOpticModuleTransceiverDetailType, fkGponOnuAniOpticModuleLengthMode, fkGponOnuAniOpticModuleLength, fkGponOnuAniOpticModuleSpeed, 
                                fkGponOnuAniOpticModuleWavelength, fkGponOnuAniOpticModuleConnecterType, fkGponOnuAniOpticModuleVendorName, fkGponOnuAniOpticModuleVendorPartName, fkGponOnuAniOpticModuleVendorRevision, 
                                fkGponOnuAniOpticModuleVendorSerialNumber, fkGponOnuAniOpticModuleProductDate, fkGponOnuAniOpticModuleTemper, fkGponOnuAniOpticModuleVoltage, fkGponOnuAniOpticModuleTxbias, 
                                fkGponOnuAniOpticModuleTxPower, fkGponOnuAniOpticModuleRxPower, fkGponOnuAniControlRequest, fkGponOnuAniControlStatus, fkGponOnuAniControlTimer, 
                                fkGponOnuAniControlTimeStamp, fkGponOnuAniControlReqResult, fkGponOnuAniControlOltId, fkGponOnuAniControlOnuId, fkGponOnuAniControlAniId, 
                                fkGponProfile2BridgeUniMcastRateLimit, fkGponProfile2BridgeUniControlMcastRateLimit, fkGponOltFixedTcontCount, fkGponOltDynamicTcontCount, fkGponOltPortCount, 
                                fkGponOltControlFixedTcontCount, fkGponOltControlDynamicTcontCount, fkGponOltControlPortCount, fkGponOltDeactiveMonitorStatus, fkGponOltDeactiveMonitorRaisePercent, 
                                fkGponOltDeactiveMonitorClearPercent, fkGponOltDeactiveMonitorPeriod, fkGponOltControlDeactiveMonitorStatus, fkGponOltControlDeactiveMonitorRaisePercent, fkGponOltControlDeactiveMonitorClearPercent, 
                                fkGponOltControlDeactiveMonitorPeriod, fkGponOltDeactiveMonitorActiveOnuCount, fkGponOltDeactiveMonitorCurrentPercent, fkGponOltDeactiveMonitorInAlamStatus, fkGponOnuMcastAclOltId, 
                                fkGponOnuMcastAclOnuId, fkGponOnuMcastAclMcastIndex, fkGponOnuMcastAclMcastName, fkGponOnuMcastAclTableIndex, fkGponOnuMcastAclVid, 
                                fkGponOnuMcastAclDstIpStart, fkGponOnuMcastAclDstIpEnd, fkGponOnuMcastAclSrcIp, fkGponOnuMcastAclBandwidth, fkGponOnuMcastAclGem, 
                                fkGponOnuMcastAclControlRequest, fkGponOnuMcastAclControlStatus, fkGponOnuMcastAclControlTimer, fkGponOnuMcastAclControlTimeStamp, fkGponOnuMcastAclControlReqResult, 
                                fkGponOnuMcastAclControlOltId, fkGponOnuMcastAclControlOnuId, fkGponOnuMcastAclControlMcastName, fkGponOnuMcastAclControlTableIndex, fkGponOnuMcastAclControlVid, 
                                fkGponOnuMcastAclControlDstIpStart, fkGponOnuMcastAclControlDstIpEnd, fkGponOnuMcastAclControlSrcIp, fkGponOnuMcastAclControlBandwidth, fkGponOnuMcastAclControlGem, 
                                fkGponFlowMappingMethodType, fkGponFlowMappingMethodVid, fkGponFlowMappingMethodControlRequest, fkGponFlowMappingMethodControlStatus, fkGponFlowMappingMethodControlTimer, 
                                fkGponFlowMappingMethodControlTimeStamp, fkGponFlowMappingMethodControlReqResult, fkGponFlowMappingMethodControlOltId, fkGponFlowMappingMethodControlVid, fkGponFlowMappingMethodControlType, 
                                fkGponProfile2OnuTr069Status, fkGponProfile2OnuControlTr069Status, fkGponProfile2OnuTr069Url, fkGponProfile2OnuControlTr069Url, fkGponOnuFWAutoUpgradeControlBaseTimeStamp, 
                                fkGponOnuRxPowerUpdateTime, fkGponBaseControlOnuRxPowerUpdateTime, fkGponOnuFWAutoUpgradeMTimeRebootTime, fkGponOnuFWAutoUpgradeMTimeControlRebootTime, fkGponProfile2OnuTr069AccessId, 
                                fkGponProfile2OnuTr069AccessPassword, fkGponProfile2OnuControlTr069AccessId, fkGponProfile2OnuControlTr069AccessPassword, fkGponOnuSupportFunction, fkGponOltMulticastGem, 
                                fkGponOltInterworkIgmpSnooping, fkGponBaseControlOltMulticastGem, fkGponBaseControlOltInterworkIgmpSnooping, fkGponOnuUserMacStatus, fkGponStaticMacListId, 
                                fkGponStaticMacStartAddr, fkGponStaticMacEndAddr, fkGponStaticMacTrafficId, fkGponStaticMacVlanId, fkGponStaticMacPortId, 
                                fkGponStaticMacCount, fkGponStaticMacControlRequest, fkGponStaticMacControlStatus, fkGponStaticMacControlTimer, fkGponStaticMacControlTimeStamp, 
                                fkGponStaticMacControlReqResult, fkGponStaticMacControlOltId, fkGponStaticMacControlStartAddr, fkGponStaticMacControlEndAddr, fkGponStaticMacControlTrafficId, 
                                fkGponStaticMacControlVlanId, fkGponOnuVideoAniIndex, fkGponOnuVideoAniAdminState, fkGponOnuVideoAniOperState, fkGponOnuVideoAniArc, 
                                fkGponOnuVideoAniArcInterval, fkGponOnuVideoAniFreqRangeLow, fkGponOnuVideoAniFreqRangeHigh, fkGponOnuVideoAniSignalCapability, fkGponOnuVideoAniOpticalSignalLevel, 
                                fkGponOnuVideoAniPilotSignalLevel, fkGponOnuVideoAniSignalLevelMin, fkGponOnuVideoAniSignalLevelMax, fkGponOnuVideoAniPilotFreq, fkGponOnuVideoAniAgcMode, 
                                fkGponOnuVideoAniAgcSetting, fkGponOnuVideoAniVideoLowerOpticalThr, fkGponOnuVideoAniVideoUpperOpticalThr, fkGponOnuVideoAniConfAgcSetting, fkGponOnuVideoAniControlRequest, 
                                fkGponOnuVideoAniControlStatus, fkGponOnuVideoAniControlTimer, fkGponOnuVideoAniControlTimeStamp, fkGponOnuVideoAniControlReqResult, fkGponOnuVideoAniControlOltIndex, 
                                fkGponOnuVideoAniControlOnuIndex, fkGponOnuVideoAniControlAniIndex, fkGponOnuVideoAniControlConfAgcSetting, fkGponOnuRFPseudowireMode, fkGponOnuRFPseudowireDstMac, 
                                fkGponBaseControlOnuRFPseudowireMode, fkGponBaseControlOnuRFPseudowireDstMac, fkGponOnuAccountUserName, fkGponOnuAccountPassword, fkGponOnuControlAccountUserName, 
                                fkGponOnuControlAccountPassword, fkGponOnuMacSlotIndex, fkGponOnuMacPortIndex, fkGponOnuMacIndex, fkGponOnuMacPolicy, 
                                fkGponOnuMacStatus, fkGponOnuMacAge, fkGponOnuMacControlRequest, fkGponOnuMacControlStatus, fkGponOnuMacControlTimer, 
                                fkGponOnuMacControlTimeStamp, fkGponOnuMacControlReqResult, fkGponOnuMacControlOltIndex, fkGponOnuMacControlOnuIndex, fkGponOnuMacControlSlotIndex, 
                                fkGponOnuMacControlPortIndex, fkGponOltBerUpInterval, fkGponOltBerDownInterval, fkGponOltBerSfThreshold, fkGponOltBerSdThreshold, 
                                fkGponOltControlBerUpInterval, fkGponOltControlBerDownInterval, fkGponOltControlBerSfThreshold, fkGponOltControlBerSdThreshold, fkGponOnuIgmpPmStatisticsSlotType, 
                                fkGponOnuIgmpPmStatisticsPortIndex, fkGponOnuIgmpPmStatisticsSuccessfulJoins, fkGponOnuIgmpPmStatisticsUnsuccessfulJoins, fkGponOnuIgmpPmStatisticsLeaveMessages, fkGponOnuIgmpPmStatisticsGeneralQueries, 
                                fkGponOnuIgmpPmStatisticsSpecificQueries, fkGponOnuIgmpPmStatisticsInvalidIGMPMessages, fkGponOnuIgmpPmStatisticsControlRequest, fkGponOnuIgmpPmStatisticsControlStatus, fkGponOnuIgmpPmStatisticsControlTimer, 
                                fkGponOnuIgmpPmStatisticsControlTimeStamp, fkGponOnuIgmpPmStatisticsControlReqResult, fkGponOnuIgmpPmStatisticsControlOltIndex, fkGponOnuIgmpPmStatisticsControlOnuIndex, fkGponOnuIgmpPmStatisticsControlSlotType, 
                                fkGponOnuIgmpPmStatisticsControlPortIndex, fkGponOnuMacFilterOltId, fkGponOnuMacFilterOnuId, fkGponOnuMacFilterSlotType, fkGponOnuMacFilterPortId, 
                                fkGponOnuMacFilterMac, fkGponOnuMacFilterType, fkGponOnuMacFilterControlRequest, fkGponOnuMacFilterControlStatus, fkGponOnuMacFilterControlTimer, 
                                fkGponOnuMacFilterControlTimeStamp, fkGponOnuMacFilterControlReqResult, fkGponOnuMacFilterControlOltIndex, fkGponOnuMacFilterControlOnuIndex, fkGponOnuMacFilterControlSlotType, 
                                fkGponOnuMacFilterControlPortIndex, fkGponOnuMacFilterControlMac, fkGponOnuMacFilterControlType, fkGponProfile2BridgeAniMacFilterPreassign, fkGponProfile2BridgeAniControlMacFilterPreassign, 
                                fkGponProfile2BridgeUniMacFilterPreassign, fkGponProfile2BridgeUniControlMacFilterPreassign, fkGponOnuActiveMode, fkGponbaseControlOnuActiveMode, fkGponOltUsFlowMapping, 
                                fkGponOltControlUsFlowMapping, fkGponOnuMacAddress, fkGponProfile2MapperIndex, fkGponProfile2OnuControlTr069Tag, fkGponOnuOmciPingTestResult, 
                                fkGponOnuOmciPingTestResultAvg, fkGponOnuControlOmciPingTestTimeout, fkGponProfile2VoipSvcProtocolPort, fkGponProfile2VoipSvcProtocolTos, fkGponProfile2VoipSvcProtocolType, 
                                fkGponProfile2VoipSvcControlProtocolPort, fkGponProfile2VoipSvcControlProtocolTos, fkGponProfile2VoipSvcControlProtocolType, fkGponProfile2TdmSvcProtocolPort, fkGponProfile2TdmSvcProtocolTos, 
                                fkGponProfile2TdmSvcProtocolType, fkGponProfile2TdmSvcControlProtocolPort, fkGponProfile2TdmSvcControlProtocolTos, fkGponProfile2TdmSvcControlProtocolType, fkGponProfile2MapperGemId, 
                                fkGponProfile2MapperGemRateLimitDownSir, fkGponProfile2MapperGemRateLimitDownPir, fkGponProfile2MapperGemRateLimitUpSir, fkGponProfile2MapperGemRateLimitUpPir, fkGponProfile2MapperGemControlRequest, 
                                fkGponProfile2MapperGemControlStatus, fkGponProfile2MapperGemControlTimer, fkGponProfile2MapperGemControlTimeStamp, fkGponProfile2MapperGemControlReqResult, fkGponProfile2MapperGemControlIndex, 
                                fkGponProfile2MapperGemControlGemIndex, fkGponProfile2MapperGemControlRateLimitDownSir, fkGponProfile2MapperGemControlRateLimitDownPir, fkGponProfile2MapperGemControlRateLimitUpSir, fkGponOltStatsOnuAlarmSf, 
                                fkGponOltStatsOnuAlarmSd, fkGponOltStatsOnuElapsedTimeAfterClear, fkGponOnuRFPseudowireEthType, fkGponOnuRFPseudowireVlanId, fkGponBaseControlOnuRFPseudowireEthType, 
                                fkGponBaseControlOnuRFPseudowireVlanId, fkGponProfile2MapperActiveEth, fkGponProfile2GemNctpIndex, fkGponProfile2GemNctpServiceId, fkGponProfile2GemNctpServiceType, 
                                fkGponProfile2GemNctpControlRequest, fkGponProfile2GemNctpControlStatus, fkGponProfile2GemNctpControlTimer, fkGponProfile2GemNctpControlTimeStamp, fkGponProfile2GemNctpControlReqResult, 
                                fkGponProfile2GemNctpControlTname, fkGponProfile2GemNctpControlIndex, fkGponProfile2GemNctpControlServiceId, fkGponProfile2GemNctpControlServiceType, fkGponProfile2VideoReturnPathSvcIndex, 
                                fkGponProfile2VideoReturnPathSvcMode, fkGponProfile2VideoReturnPathSvcFrequency, fkGponProfile2VideoReturnPathSvcPhysical, fkGponProfile2VideoReturnPathSvcControlRequest, fkGponProfile2VideoReturnPathSvcControlStatus, 
                                fkGponProfile2VideoReturnPathSvcControlTimer, fkGponProfile2VideoReturnPathSvcControlTimeStamp, fkGponProfile2VideoReturnPathSvcControlReqResult, fkGponProfile2VideoReturnPathSvcControlTname, fkGponProfile2VideoReturnPathSvcControlIndex, 
                                fkGponProfile2VideoReturnPathSvcControlMode, fkGponProfile2VideoReturnPathSvcControlFrequency, fkGponProfile2VideoReturnPathSvcControlPhysical, fkGponOnuPortMgmtAdminStatus, fkGponOnuPortMgmtCapability, 
                                fkGponOnuPortMgmtMethod, fkGponProfile2PortMgmtSlotId, fkGponProfile2PortMgmtPortId, fkGponProfile2PortMgmtMode, fkGponProfile2PotMgmtVirtualEthNum, 
                                fkGponProfile2PortMgmtControlRequest, fkGponProfile2PortMgmtControlStatus, fkGponProfile2PortMgmtControlTimer, fkGponProfile2PortMgmtControlTimeStamp, fkGponProfile2PortMgmtControlReqResult, 
                                fkGponProfile2PortMgmtControlTName, fkGponProfile2PortMgmtControlSlotId, fkGponProfile2PortMgmtControlPortId, fkGponProfile2PortMgmtControlMode, fkGponProfile2PortMgmtControlVirtualEthNum, 
                                fkGponProfileVoIPDetailSpecialLineService, fkGponProfileVoIPDetailWarmLineTimeout, fkGponProfileVoIPDetailLineNumber, fkGponProfileVoIPDetailThreeWaySSWMixing, fkGponProfileVoIPDetailSIPDNSCache, 
                                fkGponProfileVoIPDetailSIPTimerT1, fkGponProfileVoIPDetailSIPTimerT2, fkGponProfileVoIPDetailSIPTimerTd, fkGponProfileVoIPDetailSIPSessionTimer, fkGponProfileVoIPDetailSIPSessionTimeout, 
                                fkGponProfileVoIPDetailSIPEndOfDigit, fkGponProfileVoIPDetailSIPEndSharpToken, fkGponProfileVoIPDetailControlSpecialLineService, fkGponProfileVoIPDetailControlWarmLineTimeout, fkGponProfileVoIPDetailControlLineNumber, 
                                fkGponProfileVoIPDetailControlThreeWaySSWMixing, fkGponProfileVoIPDetailControlSIPDNSCache, fkGponProfileVoIPDetailControlSIPTimerT1, fkGponProfileVoIPDetailControlSIPTimerT2, fkGponProfileVoIPDetailControlSIPTimerTd, 
                                fkGponProfileVoIPDetailControlSIPSessionTimer, fkGponProfileVoIPDetailControlSIPSessionTimeout, fkGponProfileVoIPDetailControlSIPEndOfDigit, fkGponProfileVoIPDetailControlSIPEndSharpToken, fkGponProfile2OnuSwitchControlUplinkMacLearning, 
                                fkGponProfile2OnuControlSwitchControlUplinkMacLearning, fkGponProfile2MapperGemControlRateLimitUpPir, fkGponOnuPMStatsCurrentDetailUniEthFrameUpAvgPackets, fkGponOnuPMStatsCurrentDetailUniEthFrameUpAvgBits, fkGponOnuPMStatsCurrentDetailUniEthFrameTotalUpAvgPackets, 
                                fkGponOnuPMStatsCurrentDetailUniEthFrameTotalUpAvgBits, fkGponOnuPMStatsCurrentDetailUniEthFrameDownAvgPackets, fkGponOnuPMStatsCurrentDetailUniEthFrameDownAvgBits, fkGponOnuPMStatsCurrentDetailUniEthFrameTotalDownAvgPackets, fkGponOnuPMStatsCurrentDetailUniEthFrameTotalDownAvgBits, 
                                fkGponProfile2McastAccessListIndex, fkGponProfile2McastAccessListName, fkGponProfile2McastAccessListControlRequest, fkGponProfile2McastAccessListControlStatus, fkGponProfile2McastAccessListControlTimer, 
                                fkGponProfile2McastAccessListControlTimeStamp, fkGponProfile2McastAccessListControlReqResult, fkGponProfile2McastAccessListControlName, fkGponProfile2McastAccessListDynamicIndex, fkGponProfile2McastAccessListDynamicVid, 
                                fkGponProfile2McastAccessListDynamicDstIpStart, fkGponProfile2McastAccessListDynamicDstIpEnd, fkGponProfile2McastAccessListDynamicSrcIp, fkGponProfile2McastAccessListDynamicBandwidth, fkGponProfile2McastAccessListDynamicGem, 
                                fkGponProfile2McastAccessListDynamicControlRequest, fkGponProfile2McastAccessListDynamicControlStatus, fkGponProfile2McastAccessListDynamicControlTimer, fkGponProfile2McastAccessListDynamicControlTimeStamp, fkGponProfile2McastAccessListDynamicControlReqResult, 
                                fkGponProfile2McastAccessListDynamicControlIndex, fkGponProfile2McastAccessListDynamicControlVid, fkGponProfile2McastAccessListDynamicControlName, fkGponProfile2McastAccessListDynamicControlDstIpStart, fkGponProfile2McastAccessListDynamicControlDstIpEnd, 
                                fkGponProfile2McastAccessListDynamicControlSrcIp, fkGponProfile2McastAccessListDynamicControlBandwidth, fkGponProfile2McastAccessListDynamicControlGem, fkGponProfile2McastAccessListStaticIndex, fkGponProfile2McastAccessListStaticVid, 
                                fkGponProfile2McastAccessListStaticDstIpStart, fkGponProfile2McastAccessListStaticDstIpEnd, fkGponProfile2McastAccessListStaticSrcIp, fkGponProfile2McastAccessListStaticBandwidth, fkGponProfile2McastAccessListStaticGem, 
                                fkGponProfile2McastAccessListStaticControlRequest, fkGponProfile2McastAccessListStaticControlStatus, fkGponProfile2McastAccessListStaticControlTimer, fkGponProfile2McastAccessListStaticControlTimeStamp, fkGponProfile2McastAccessListStaticControlReqResult, 
                                fkGponProfile2McastAccessListStaticControlIndex, fkGponProfile2McastAccessListStaticControlVid, fkGponProfile2McastAccessListStaticControlName, fkGponProfile2McastAccessListStaticControlDstIpStart, fkGponProfile2McastAccessListStaticControlDstIpEnd, 
                                fkGponProfile2McastAccessListStaticControlSrcIp, fkGponProfile2McastAccessListStaticControlBandwidth, fkGponProfile2McastAccessListStaticControlGem, fkGponOnuMcastAccessListOltId, fkGponOnuMcastAccessListOnuId, 
                                fkGponOnuMcastAccessListIndex, fkGponOnuMcastAccessListName, fkGponOnuMcastAccessListProfileName, fkGponOnuMcastAccessListControlRequest, fkGponOnuMcastAccessListControlStatus, 
                                fkGponOnuMcastAccessListControlTimer, fkGponOnuMcastAccessListControlTimeStamp, fkGponOnuMcastAccessListControlReqResult, fkGponOnuMcastAccessListControlOltIndex, fkGponOnuMcastAccessListControlOnuIndex, 
                                fkGponOnuMcastAccessListControlName, fkGponOnuMcastAccessListControlProfileName, fkGponProfile2MapperGemControlTrafficName, fkGponProfile2OnuTr069Tag, fkGponOnuAniOpticModuleTemperHighThr, 
                                fkGponOnuAniOpticModuleTemperLowThr, fkGponOnuAniOpticModuleVoltageHighThr, fkGponOnuAniOpticModuleVoltageLowThr, fkGponOnuAniOpticModuleTxbiasHighThr, fkGponOnuAniOpticModuleTxbiasLowThr, 
                                fkGponOnuAniOpticModuleTxPowerHighThr, fkGponOnuAniOpticModuleTxPowerLowThr, fkGponOnuAniOpticModuleRxPowerHighThr, fkGponOnuAniOpticModuleRxPowerLowThr, fkGponPorifle2OnuAniVoltageHighThr, 
                                fkGponPorifle2OnuAniVoltageLowThr, fkGponPorifle2OnuAniTemperatureHighThr, fkGponPorifle2OnuAniTemperatureLowThr, fkGponPorifle2OnuAniTxBiasHighThr, fkGponPorifle2OnuAniTxBiasLowThr, 
                                fkGponPorifle2OnuAniTxpowerHighThr, fkGponPorifle2OnuAniTxpowerLowThr, fkGponPorifle2OnuControlAniVoltageHighThr, fkGponPorifle2OnuControlAniVoltageLowThr, fkGponPorifle2OnuControlAniTemperatureHighThr, 
                                fkGponPorifle2OnuControlAniTemperatureLowThr, fkGponPorifle2OnuControlAniTxBiasHighThr, fkGponPorifle2OnuControlAniTxBiasLowThr, fkGponPorifle2OnuControlAniTxpowerHighThr, fkGponPorifle2OnuControlAniTxpowerLowThr, 
                                fkGponProfile2OnuIgmpMaxGroups, fkGponProfile2OnuControlIgmpMaxGroups, fkGponProfile2OnuIgmpUpRateLimit, fkGponProfile2OnuControlIgmpUpRateLimit, fkGponProfile2McastAclCos, 
                                fkGponProfile2McastAclControlCos, fkGponProfile2McastSAclCos, fkGponProfile2McastSAclControlCos, fkGponProfile2McastAccessListDynamicCos, fkGponProfile2McastAccessListDynamicControlCos, 
                                fkGponProfile2McastAccessListStaticCos, fkGponProfile2McastAccessListStaticControlCos, fkGponProfile2OnuIgmpHostTracking, fkGponProfile2OnuControlIgmpHostTracking, fkGponOnuPmStatsUniAvgPort, 
                                fkGponOnuPmStatsUniAvgEthFrameUpPackets, fkGponOnuPmStatsUniAvgEthFrameUpBits, fkGponOnuPmStatsUniAvgEthFrameDownPackets, fkGponOnuPmStatsUniAvgEthFrameDownBits, fkGponOnuPmStatsUniAvgControlRequest, 
                                fkGponOnuPmStatsUniAvgControlStatus, fkGponOnuPmStatsUniAvgControlTimer, fkGponOnuPmStatsUniAvgControlTimeStamp, fkGponOnuPmStatsUniAvgControlReqResult, fkGponOnuPmStatsUniAvgControlOltindex, 
                                fkGponOnuPmStatsUniAvgControlOnuIndex, fkGponOnuPmStatsUniAvgControlPort, fkGponOltPortServiceStatus, fkGponProfile2BridgeUniRateLimitProfile, fkGponProfile2BridgeUniControlRateLimitProfile, 
                                fkGponProfile2MapperGemRateLimitProfile, fkGponProfile2MapperGemControlRateLimitProfile, fkGponProfile2RateLimitIndex, fkGponProfile2RateLimitName, fkGponProfile2RateLimitUpPir, 
                                fkGponProfile2RateLimitUpSir, fkGponProfile2RateLimitDownPir, fkGponProfile2RateLimitDownSir, fkGponProfile2RateLimitControlRequest, fkGponProfile2RateLimitControlStatus, 
                                fkGponProfile2RateLimitControlTimer, fkGponProfile2RateLimitControlTimeStamp, fkGponProfile2RateLimitControlReqResult, fkGponProfile2RateLimitControlName, fkGponProfile2RateLimitControlDownSir, 
                                fkGponProfile2RateLimitControlDownPir, fkGponProfile2RateLimitControlUpSir, fkGponProfile2RateLimitControlUpPir, fkGponProfile2BridgeControlMcastFlag, fkGponProfile2BridgeControlPortBridge, 
                                fkGponProfile2OnuMacFullPolicy, fkGponProfile2OnuCpuPacketLimitBroadcast, fkGponProfile2OnuCpuPacketLimitMulticast, fkGponProfile2OnuCpuPacketLimitDlf, fkGponProfile2OnuControlMacFullPolicy, 
                                fkGponProfile2OnuControlCpuPacketLimitBroadcast, fkGponProfile2OnuControlCpuPacketLimitMulticast, fkGponProfile2OnuControlCpuPacketLimitDlf, fkGponOnuMcastAccessListProfileIndex, fkGponOltDsQosMappingQueueCount, 
                                fkGponOltDsQosMappingCos0Queue, fkGponOltDsQosMappingCos1Queue, fkGponOltDsQosMappingCos2Queue, fkGponOltDsQosMappingCos3Queue, fkGponOltDsQosMappingCos4Queue, 
                                fkGponOltDsQosMappingCos5Queue, fkGponOltDsQosMappingCos6Queue, fkGponOltDsQosMappingCos7Queue, fkGponOltDsQosMappingMode, fkGponOltControlDsQosMappingQueueCount, 
                                fkGponOltControlDsQosMappingCos0Queue, fkGponOltControlDsQosMappingCos1Queue, fkGponOltControlDsQosMappingCos2Queue, fkGponOltControlDsQosMappingCos3Queue, fkGponOltControlDsQosMappingCos4Queue, 
                                fkGponOltControlDsQosMappingCos5Queue, fkGponOltControlDsQosMappingCos6Queue, fkGponOltControlDsQosMappingCos7Queue, fkGponOltControlDsQosMappingMode, fkGponVlanGemMappingControlVid, 
                                fkGponVlanGemMappingControlMapperId, fkGponVlanGemMappingControlVidTo, fkGponProfile2BridgePortBridge, fkGponProfile2BridgeControlMaxHost }
                        STATUS current
                        DESCRIPTION 
                                "Description."
                        ::= { fkGpon 53 }

                
--   1.3.6.1.4.1.10428 9 1.101.23.13
-- 1.3.6.1.4.1.10428 9 1.101.23.54
                -- 1.3.6.1.4.1.10428 9 1.101.23.54
                fkGponNotificationGroup NOTIFICATION-GROUP
                        NOTIFICATIONS { fkGponProfile2DbaAdded, fkGponProfile2DbaDeleted, fkGponProfile2DbaSlaChanged, fkGponProfile2TrafficAdded, fkGponProfile2TrafficDeleted, 
                                fkGponProfile2MapperAdded, fkGponProfile2MapperDeleted, fkGponProfile2MapperGemportCountChanged, fkGponProfile2MapperDefaultCoSChanged, fkGponProfile2MapperDscp2BitChanged, 
                                fkGponProfile2MapperCosGemportChanged, fkGponProfile2BridgeAdded, fkGponProfile2BridgeDeleted, fkGponProfile2BridgeMacLearningChanged, fkGponProfile2BridgeMaxHostChanged, 
                                fkGponProfile2BridgeMcastChanged, fkGponProfile2BridgeAniAdded, fkGponProfile2BridgeAniDeleted, fkGponProfile2BridgeAniVlanFilterChanged, fkGponProfile2BridgeUniAdded, 
                                fkGponProfile2BridgeUniDeleted, fkGponProfile2BridgeUniVlanDsOpChanged, fkGponProfile2BridgeUniVlanUsOpChanged, fkGponProfile2BridgeUniPortAdminChanged, fkGponProfile2BridgeUniRateLimitChanged, 
                                fkGponProfile2BridgeUniIgmpMaxGroupChanged, fkGponProfile2BridgeUniMaxFrameChanged, fkGponProfile2BridgeUniMcastProfileChanged, fkGponProfile2BridgeUniVlanFilterChanged, fkGponProfile2McastProfileAdded, 
                                fkGponProfile2McastProfileDeleted, fkGponProfile2McastIgmpFuncChanged, fkGponProfile2McastIgmpImmLeaveChanged, fkGponProfile2McastIgmpRobustChanged, fkGponProfile2McastIgmpQuerierInfoChanged, 
                                fkGponProfile2McastIgmpVersionChanged, fkGponProfile2McastIgmpUpRateLimitChanged, fkGponProfile2McastIgmpTagCtrlChanged, fkGponProfile2McastAclAdded, fkGponProfile2McastAclDeleted, 
                                fkGponProfile2McastSAclAdded, fkGponProfile2McastSAclDeleted, fkGponBaseCableDownStatusChanged, fkGponBaseCableDownRefCntChanged, fkGponOltDiscoverySerialStarted, 
                                fkGponOltDiscoverySerialStopped, fkGponOltLinkMaxDistanceChanged, fkGponOltKeyExchangeStarted, fkGponOltKeyExchangeStopped, fkGponOltSignalCheckChanged, 
                                fkGponOltSignalCheckAutoOnuBlockChanged, fkGponOltDescriptionChanged, fkGponOltAutoToManualChanged, fkGponOltDefaultTcontChanged, fkGponOltDefaultTcontRemoved, 
                                fkGponOltDefaultProfileChanged, fkGponOltDefaultProfileRemoved, fkGponOnuRegistered, fkGponOnuDeregistered, fkGponOnuProfileChanged, 
                                fkGponOnuFixed, fkGponOnuUpgradeNosChanged, fkGponOnuNosActiveChanged, fkGponOnuEncModeChanged, fkGponOnuReset, 
                                fkGponOnuTxOffOpticChanged, fkGponOnuDescriptionChanged, fkGponTcontCreated, fkGponTcontDestroyed, fkGponProfileBaseCreated, 
                                fkGponProfileBaseModified, fkGponProfileBaseDestroyed, fkGponProfilePortRateLimitChanged, fkGponProfilePortMaxHostChanged, fkGponProfilePortVlanOperChanged, 
                                fkGponProfilePortVlanFilterChanged, fkGponOnuPortAdminChanged, fkGponOltStatsCleared, fkGponFirmwareUpgradeProfileChanged, fkGponFirmwareDeleted, 
                                fkGponOnuFWAutoUpgradeModeChanged, fkGponOnuFWAutoUpgradeVersionMatchChanged, fkGponOnuFWAutoUpgradeInvalidVersionMatchChanged, fkGponOnuFWAutoUpgradeStartEndTimeChanged, fkGponOnuFWAutoUpgradeRebootTimeChanged, 
                                fkGponOnuFWAutoUpgradeModelProfileChanged, gponOntFwDownloaded, gponOntFwUpgraded, gponOntFwOntReseted, gponOntFwDeleted, 
                                gponOntFwDeleteAll, fkGponOltFecModeUSChanged, fkGponOltFecModeDSChanged, fkGponOltMacAgingTimeChanged, fkGponOltTransceiverPortChanged, 
                                fkGponOnuFecModeChanged, fkGponOnuIPInfoChanged, fkGponProfileTcontProfileChanged, fkGponProfileBaseVoIPProfileChanged, fkGponProfileDbaCreated, 
                                fkGponProfileDbaDestroyed, fkGponProfileMultiTcontProfileCreated, fkGponProfileMultiTcontProfileDestroyed, fkGponProfileMultiTcontProfileDscp2PbitChanged, fkGponProfileMultiTcontProfilePriQWeightChanged, 
                                fkGponProfileMultiTcontProfileGemportChanged, fkGponProfileVoIPProfileCreated, fkGponProfileVoIPProfileDestroyed, fkGponProfilVoIPProfileServiceChanged, fkGponProfileVoIPProfileOmciChanged, 
                                fkGponProfileVoIPOmciSIPAuthChanged, fkGponProfileVoIPOmciSIPPhoneChnaged, fkGponProfileVoIPIpPathInfoChanged, fkGponOnuFWAutoUpgradeModelDeleted, fkGponOnuPortAutoNegoChanged, 
                                fkGponProfilePortAdminChanged, fkGponProfilePortDuplexChanged, fkGponProfilePortSpeedChanged, fkGponOnuPortSpeedChanged, fkGponOnuFWAutoUpgradeMTimeDeleted, 
                                fkGponOnuFWAutoUpgradeModelModifyTargetVer, fkGponOltProtectionChanged, fkGponOnuActivationChanged, fkGponRedGroupChanged, fkGponRedGroupCleared, 
                                fkGponRedGroupForceSwitchovered, fkGponProfilePorPauseChanged, fkGponProfile2OnuAdded, fkGponProfile2OnuDeleted, fkGponProfile2OnuRogueInfoChanged, 
                                fkGponProfile2OnuRxPowerChanged, fkGponProfile2OnuTrafficProfileChanged, fkGponOltAuthStatsCleared, fkGponOnuPortStatisticsCleared, fkGponProfileDbaChanged, 
                                fkGponOltActivateStatusChanged, fkGponOnuFWAutoUpgradeMTimeChanged, fkGponOnuPMProfileChanged, fkGponProfile2PMProfileAdded, fkGponProfile2PMProfileDeleted, 
                                fkGponProfile2TcontGemportAdded, fkGponProfile2BridgeUniIpInfoChanged, fkGponProfile2BridgeUniVoipProfileChanged, fkGponProfile2TcontGemportDeleted, fkGponOltOpticParamChanged, 
                                fkGponOnuUpgradeNosPartitionChanged, fkGponOnuUpgradeNosCommited, fkGponOnuUpgradeNosActiveChanged, fkGponOnuPMStatsCleared, fkGponProfile2OnuPmProfileChanged, 
                                fkGponProfile2OnuUniRateLimitChanged, fkGponProfile2OnuUniVlanDsOperChanged, fkGponProfile2OnuUniVlanUsOperChanged, fkGponProfile2OnuUniIgmpMaxGroupChanged, fkGponProfile2OnuUniPortAdminChanged, 
                                fkGponProfile2OnuBridgeMaxHostChanged, fkGponOnuHostIPInfoChanged, fkGponBaseDefaultServiceProfileChanged, fkGponOltSrcMacMonitorChanged, fkGponOltTotalUsBwChanged, 
                                fkGponOnuBlockChanged, fkGponServiceProfileModelChanged, fkGponOnuUserMacOltMacChanged, fkGponOnuUserMacOltMacOnuChanged, fkGponFirmwareDownloadChanged, 
                                fkGponOnuFWAutoUpgradeModelTargetVerDeleted, fkGponProfileTdmPwMtProfileCreated, fkGponProfileTdmPwMtProfileDeleted, fkGponProfileTdmPwMtMaxDepthChanged, fkGponProfileTdmDesiredDepthChanged, 
                                fkGponProfileTdmFillPolicyChanged, fkGponProfileTdmMisconnectDeclarePolicyChanged, fkGponProfileTdmMisconnectClearPolicyChanged, fkGponProfileTdmLossDeclarePolicyChanged, fkGponProfileTdmLossClearPolicyChanged, 
                                fkGponProfileTdmBuffUnderrunDeclarePolicyChanged, fkGponProfileTdmbuffUnderrunClearPolicyChanged, fkGponProfileTdmMalformedDeclarePolicyChanged, fkGponProfileTdmMalformedClearPolicyChanged, fkGponProfileTdmRBitTransmitPolicyChanged, 
                                fkGponProfileTdmRBitReceivePolicyChanged, fkGponProfileTdmLBitReceivePolicyChanged, fkGponProfileTdmSesThresholdChanged, fkGponProfileTdmPwProfileCreated, fkGponProfileTdmPwProfileDeleted, 
                                fkGponProfileTdmPwServiceTypeChanged, fkGponProfileTdmPwSignallingChanged, fkGponProfileTdmPwPayloadSizeChanged, fkGponProfileTdmPwPayloadEncapsulationDelayChanged, fkGponProfileTdmPwTimingModeChanged, 
                                fkGponProfile2TdmSvcTdmServiceCreated, fkGponProfile2TdmSvcTdmServiceDeleted, fkGponProfile2TdmSvcTdmPwProfileChanged, fkGponProfile2TdmSvcTdmVlanFilterChanged, fkGponProfile2TdmSvcTdmEthDestMacChanged, 
                                fkGponProfile2TdmSvcTdmEthTagPolicyChanged, fkGponProfile2TdmSvcTdmTranEcidChanged, fkGponProfile2TdmSvcTdmRecvEcidChanged, fkGponProfile2TdmSvcTdmExpectEcidChanged, fkGponProfile2TdmSvcTdmUdpPortChanged, 
                                fkGponProfile2TdmSvcTdmFarEndIpChanged, fkGponProfile2TdmSvcMplsLabelIndicatorChanged, fkGponProfile2TdmSvcMplsPwDirectionChanged, fkGponProfile2TdmSvcMplsPwLabelChanged, fkGponProfile2TdmSvcMplsPwTunnelDirectionChanged, 
                                fkGponProfile2TdmSvcMplsPwTunnelLabelChanged, fkGponProfile2TdmSvcCesBuffCdvToleranceChanged, fkGponProfile2TdmSvcCesChannelAssociateSignalChanged, fkGponProfileTdmSdhProfileCreated, fkGponProfileTdmSdhProfileDeleted, 
                                fkGponProfileTdmSdhTuTypeChanged, fkGponProfileTdmSdhGemLossIntergrationPeriodChanged, fkGponProfileTdmSdhTransmitJ1J2Changed, fkGponProfileTdmSdhExpectJ1J2Changed, fkGponProfileTdmSdhreceiveJ1J2Changed, 
                                fkGponProfileTdmSdhTimMonitorChanged, fkGponProfileTdmSdhTimAisChanged, fkGponProfile2IpHostSvcIpHostSvcCreated, fkGponProfile2IpHostSvcIpHostSvcDeleted, fkGponProfile2IpHostSvcAddressTypeChanged, 
                                fkGponProfile2IpHostSvcDnsChanged, fkGponProfile2IpHostSvcVlanFilterChanged, fkGponProfile2IpHostSvcVlanDsOperChanged, fkGponProfile2IpHostSvcVlanUsOperChanged, fkGponProfileVoIPProfileIpwayChanged, 
                                fkGponProfileVoIPDetailProfileCreated, fkGponProfileVoIPDetailProfileDeleted, fkGponProfileVoIPDetailFaxModeChanged, fkGponProfileVoIPDetailOobDtmfChanged, fkGponProfileVoIPDetailAnnouncementTypeChanged, 
                                fkGponProfileVoIPDetailJitterTargetChanged, fkGponProfileVoIPDetailJitterBuffMaxChanged, fkGponProfileVoIPDetailEchoCancelChanged, fkGponProfileVoIPDetailPstnProtoChanged, fkGponProfileVoIPDetailDtmfDigitChanged, 
                                fkGponProfileVoIPDetailHookFlashTimeMinChanged, fkGponProfileVoIPDetailHookFlashTimeMaxChanged, fkGponProfileVoIPDetailSignalingCodeChanged, fkGponProfileVoIPDetailRtpLocalPortChanged, fkGponProfileVoIPDetailRtpDscpMarkChanged, 
                                fkGponProfileVoIPDetailRtpPiggybackEventChanged, fkGponProfileVoIPDetailRtpToneEventChanged, fkGponProfileVoIPDetailRtpDtmfEventChanged, fkGponProfileVoIPDetailRtpCasEventChanged, fkGponProfileVoIPDetailProtocolChanged, 
                                fkGponProfileVoIPDetailMgcPriServerChanged, fkGponProfileVoIPDetailMgcSecServerChanged, fkGponProfileVoIPDetailMgcVersionChanged, fkGponProfileVoIPDetailMgcFormatChanged, fkGponProfileVoIPDetailMgcMaxRetryTimeChanged, 
                                fkGponProfileVoIPDetailMgcRetryAttemptsChanged, fkGponProfileVoIPDetailMgcServiceChangeDelayChanged, fkGponProfileVoIPDetailMgcTerminationIdChanged, fkGponProfileVoIPDetailMgcSoftswitchChanged, fkGponProfileVoIPDetailVoicemailServerChanged, 
                                fkGponProfileVoIPDetailVoicemailExpireTimeChanged, fkGponProfileVoIPDetailReleaseTimeChanged, fkGponProfileVoIPDetailRohTimerChanged, fkGponProfileVoIPDetailProxyServerChanged, fkGponProfileVoIPDetailOutboundProxyServerChanged, 
                                fkGponProfileVoIPDetailRegisterServerChanged, fkGponProfileVoIPDetailHostpartServerChanged, fkGponProfileVoIPDetailDnsChanged, fkGponProfileVoIPDetailRegExpTimeChanged, fkGponProfileVoIPDetailReregHeadStartTimeChanged, 
                                fkGponProfileVoIPDetailSoftSwitchChanged, fkGponProfileVoIPDetailSipOptionTransmitCtlChanged, fkGponProfileVoIPDetailSipUriFormatChanged, fkGponProfileVoIPDetailCallerIdChanged, fkGponProfileVoIPDetailCallWaitingChanged, 
                                fkGponProfileVoIPDetailCallProgressTransferChanged, fkGponProfileVoIPDetailCallPresentChanged, fkGponProfileVoIPDetailDirectConnectChanged, fkGponProfileVoIPDetailDirectConnectUriChanged, fkGponProfileVoIPDetailBridgedLineAgentUriChanged, 
                                fkGponProfileVoIPDetailConferenceFactoryUriChanged, fkGponProfileVoIPDetailCancelCallWaitChanged, fkGponProfileVoIPDetailCallParkChanged, fkGponProfileVoIPDetailCallerIdActChanged, fkGponProfileVoIPDetailCallerIdDeactChanged, 
                                fkGponProfileVoIPDetailDoNotDisturbActChanged, fkGponProfileVoIPDetailDoNotDisturbDeactChanged, fkGponProfileVoIPDetailDoNotDisturbPinChangeChanged, fkGponProfileVoIPDetailEmergServiceNumberChanged, fkGponProfileVoIPDetailIntercomServiceChanged, 
                                fkGponProfile2BridgeGemBridgeGemCreated, fkGponProfile2BridgeGemBridgeGemDeleted, fkGponProfile2BridgeGemVlanFilterChanged, fkGponProfile2BridgeTdmBridgeTdmCreated, fkGponProfile2BridgeTdmBridgeTdmDeleted, 
                                fkGponProfile2IpHostVoipVoipSvcCreated, fkGponProfile2IpHostVoipVoipSvcDeleted, fkGponProfile2IpHostTdmSvcCreated, fkGponProfile2IpHostTdmSvcDeleted, fkGponProfile2VoipSvcVoipSvcCreated, 
                                fkGponProfile2VoipSvcVoipSvcDeleted, fkGponProfile2VoipSvcUdpPortChanged, fkGponProfile2VoipSvcManageMethodChanged, fkGponProfile2VoipSvcProtocolChanged, fkGponProfile2VoipSvcIppathUrlChanged, 
                                fkGponProfile2VoipSvcIppathAuthChanged, fkGponProfile2VoipSvcUniVoipSvcUniCreated, fkGponProfile2VoipSvcUniVoipSvcUniDeleted, fkGponProfile2VoipSvcUniImpedanceChanged, fkGponProfile2VoipSvcUniTransmissionPathChanged, 
                                fkGponProfile2VoipSvcUniGainChanged, fkGponProfile2VoipSvcUniHoldOverTimeChanged, fkGponProfile2TdmPortCreated, fkGponProfile2TdmPortDeleted, fkGponProfile2TdmExpectedTypeChanged, 
                                fkGponProfile2TdmFramingChanged, fkGponProfile2TdmEncodingChanged, fkGponProfile2TdmLineLengthPowerFeedChanged, fkGponProfile2TdmDs1ModeChanged, fkGponProfile2TdmLineTypeChanged, 
                                fkGponProfile2BridgeUniMaxHostChanged, fkGponProfile2OnuTcontDbaProfileChanged, fkGponProfileVoIPPotsAdded, fkGponProfileVoIPPotsDeleted, fkGponProfileTdmPwRtpClockReferenceChanged, 
                                fkGponProfileTdmPwRtpTimeStampmodeChanged, fkGponProfileTdmPwRtpPayloadTypeChanged, fkGponProfileTdmPwRtpSyncSourceChanged, fkGponProfileTdmPwRtpExpectPayloadTypeChanged, fkGponProfileTdmPwRtpExpectSyncSourceChanged, 
                                fkGponProfile2OnuCircuitPackChanged, fkGponProfileTdmPwMtProfileChanged, fkGponProfile2BridgeIpHostBridgeIpHostCreated, fkGponProfile2BridgeIpHostBridgeIpHostDeleted, fkGponProfileVoIPDetailCallHoldChanged, 
                                fkGponProfileVoIPDetailCodec1stChanged, fkGponProfileVoIPDetailCodec2ndChanged, fkGponProfileVoIPDetailCodec3rdChanged, fkGponProfileVoIPDetailCodec4thChanged, fkGponOltAntiSpoofingFilterChanged, 
                                fkGponProfile2PMProfileChanged, fkGponAntiSpoofingAntiSpoofingStatusChanged, fkGponAntiSpoofingAntiSpoofingOltCleared, fkGponAntiSpoofingAntiSpoofingOnuCleared, fkGponAntiSpoofingAntiSpoofingOneCleared, 
                                fkGponOnuHostInfoChanged, fkGponProfileVoIPDetailDialPlanCritTimeOutChanged, fkGponProfileVoIPDetailDialPlanPartTimeOutChanged, fkGponProfileVoIPDetailDialPlanFormatChanged, fkGponProfileVoIPDetailDialPlanTableCreated, 
                                fkGponProfileVoIPDetailDialPlanTableDeleted, fkGponRedGroupStandbyOpticChanged, fkGponRedGroupSlaveAdminStatusChanged, fkGponRedGroupTriggerChanged, fkGponOnuUpdateOltRxPowerChanged, 
                                fkGponOnuPortUniDescriptionChanged, fkGponOnuPortAutoDetectionChanged, fkGponOnuPortMediumModeChanged, fkGponProfile2VoipSvcVoipProfileChanged, fkGponOltMaxOnuCountChanged, 
                                fkGponOnuVoipLineVoipInfoChanged, fkGponOltBwBEMethodChanged, fkGponOltDsGemMappingChanged, fkGponProfile2BridgeUniExtendedVlanChanged, fkGponProfile2IpHostSvcExtendedVlanChanged, 
                                fkGponVlanGemMappingChagned, fkGponVlanGemMappingCleared, fkGponProfile2ExtVlanProfileAdded, fkGponProfile2ExtVlanProfileDeleted, fkGponProfile2ExtVlanDownStreamModeChanged, 
                                fkGponProfile2ExtVlanDscpToCosMapTableChanged, fkGponProfile2ExtVlanTpidChanged, fkGponOnuFWAutoUpgradeBaseRetryCountChanged, fkGponOnuPortLoopbackStatusChanged, fkGponProfile2ExtVlanTagAdded, 
                                fkGponProfile2ExtVlanTagDeleted, fkGponProfile2ExtVlanTagFilterEtherTypeChanged, fkGponProfile2ExtVlanTagTreatmentInnerChanged, fkGponOnuVlanGemMappingCleared, fkGponOltVlanGemMappingCleared, 
                                fkGponBasePasswordTypeChanged, fkGponProfile2OnuSWWatchdogChanged, fkGponProfile2OnuLinkPassThroughChanged, fkGponOnuSystemInfoUpdated, fkGponOnuTxOnOptic, 
                                fkGponOnuPortOpticModuleInfoUpdated, fkGponProfile2OnuCpuLoadThrChanged, fkGponProfile2OnuMemoryUsageThrChanged, fkGponProfile2OnuTemperatureHighThrChanged, fkGponProfile2OnuTemperatureThrChanged, 
                                fkGponProfile2ExtVlanTagTreatmentOuterChanged, fkGponProfile2ExtVlanTagTreatmentTag, fkGponProfile2ExtVlanTagFilterInnerChanged, fkGponRedGroupSafeSwitchOverChanged, fkGponRedGroupDbSyncCheckChanged, 
                                fkGponRedGroupDbResyncChanged, fkGponOnuPortLinkStatisticsUpdated, fkGponProfileVoIPOmciMGCTerminationChanged, fkGponProfileVoIPServiceMgcMessageChanged, fkGponOnuLoopDetectUnblockChanged, 
                                fkGponProfile2OnuLoopDetectChanged, fkGponProfile2ExtVlanTagFilterOuterChanged, fkGponOnuPMStatsCurrentDetailChanged, fkGponIgmpGroupChanged, fkGponProfile2TcontAdded, 
                                fkGponProfile2TcontDeleted, fkGponProfile2TcontDbaChanged, fkGponOnuAniOpticModuleInfoUpdated, fkGponProfile2BridgeUniMcastRateLimitChanged, fkGponOltFixedTcontCountChanged, 
                                fkGponOltDynamicTcontCountChanged, fkGponOltPortCountChanged, fkGponOltDeactiveMonitorStatusChanged, fkGponOltDeactiveMonitorRaisePercentChanged, fkGponOltDeactiveMonitorClearPercentChanged, 
                                fkGponOltDeactiveMonitorPeriodChanged, fkGponOltDeactiveMonitorAlarmCleared, fkGponOnuMcastAclCreated, fkGponOnuMcastAclCleared, fkGponOnuMcastAclOnuCleared, 
                                fkGponOnuMcastAclOltCleared, fkGponOnuUserMacCntUpdated, fkGponOnuUserMacOltMacAllChanged, fkGponOnuUserMacOltMacUpdated, fkGponFlowMappingMethodChanged, 
                                fkGponFlowMappingMethodCleared, fkGponFlowMappingMethodOltCleared, fkGponProfile2OnuTr069UrlCleared, fkGponProfile2OnuTr069StatusChanged, fkGponProfile2OnuTr069AccessChanged, 
                                fkGponProfile2OnuTr069AccessCleared, fkGponProfile2OnuTr069TagChanged, fkGponProfile2OnuTr069TagCleared, fkGponProfile2TcontQueueWeight, fkGponBaseOnuRxPowerUpdateTimeChanged, 
                                fkGponOnuFWAutoUpgradeMTimeRebootTimeChanged, fkGponBaseOltMulticastGemChanged, fkGponBaseOltInterworkIgmpSnoopingChanged, fkGponStaticMacCreated, fkGponStaticMacDeleted, 
                                fkGponOnuVideoAniupdateVideoAniStatusUpdated, fkGponOnuVideoAniControlVideoAniArcChanged, fkGponOltRegisterd, fkGponBaseOnuRFPseudowireDstMacChanged, fkGponOnuAccountUpdated, 
                                fkGponOnuAccountChanged, fkGponOnuMacUpdated, fkGponOnuIgmpPmStatisticsPmDataChanged, fkGponOnuIgmpPmStatisticsPmDataCleared, fkGponOnuMacFilterChanged, 
                                fkGponOnuMacFilterDeleted, fkGponProfile2BridgeAniMacFilterPreassignChanged, fkGponProfile2BridgeUniMacFilterPreassignChanged, fkGponBaseOnuActiveModeChanged, fkGponOltUsFlowMappingChanged, 
                                fkGponProfile2OnuTr069UrlChanged, fkGponBaseOnuRFPseudowireEthTypeChanged, fkGponBaseOnuRFPseudowireVlanIdChanged, fkGponProfile2MapperActiveEthCreated, fkGponProfile2MapperActiveEthDeleted, 
                                fkGponProfile2GemNctpServiceAdded, fkGponProfile2GemNctpServiceDeleted, fkGponProfile2GemNctpServiceChanged, fkGponProfile2VideoReturnPathSvcAdded, fkGponProfile2VideoReturnPathSvcDeleted, 
                                fkGponProfile2VideoReturnPathSvcModeChanged, fkGponProfile2VideoReturnPathSvcFrequencyChanged, fkGponProfile2VideoReturnPathSvcPhysicalChanged, fkGponOnuPortMgmtChanged, fkGponProfile2PortMgmtSetted, 
                                fkGponProfile2PortMgmtUnsetted, fkGponProfileVoIPDetailSpecialLineServiceChanged, fkGponProfileVoIPDetailThreeWaySSWMixingChanged, fkGponProfileVoIPDetailSIPDNSCacheChanged, fkGponProfileVoIPDetailSIPTimerChanged, 
                                fkGponProfileVoIPDetailSIPSessionTimerChanged, fkGponProfileVoIPDetailSIPEndOfDigitChanged, fkGponProfileVoIPDetailSIPEndSharpTokenChanged, fkGponProfile2OnuSwitchControlChanged, fkGponProfile2McastAccessListAdded, 
                                fkGponProfile2McastAccessListDeleted, fkGponProfile2McastAccessListDynamicAdded, fkGponProfile2McastAccessListDynamicDeleted, fkGponProfile2McastAccessListStaticControlAdded, fkGponProfile2McastAccessListStaticControlDeleted, 
                                fkGponOnuMcastAccessListAdded, fkGponOnuMcastAccessListDeleted, fkGponOnuMcastAccessListOnuDeleted, fkGponOnuMcastAccessListOltDeleted, fkGponOltDsQosMappingChanged, 
                                fkGponOltDsQosMappingCleared, fkGponOltDsQosMappingModeChanged, fkGponProfile2OnuAniVoltageHighThrChanged, fkGponProfile2OnuAniVoltageLowThrChanged, fkGponProfile2OnuAniTemperatureHighThrChanged, 
                                fkGponProfile2OnuAniTemperatureLowThrChanged, fkGponProfile2OnuAniTxBiasHighThrChanged, fkGponProfile2OnuAniTxBiasLowThrChanged, fkGponProfile2OnuAniTxpowerHighThrChanged, fkGponProfile2OnuAniTxpowerLowThrChanged, 
                                fkGponProfile2OnuIgmpMaxGroupsChanged, fkGponProfile2OnuIgmpUpRateLimitChanged, fkGponProfile2OnuIgmpHostTrackingChanged, fkGponOnuPmStatsUniAvgUpdated, fkGponProfile2BridgeUniRateLimitProfileChanged, 
                                fkGponProfile2MapperGemRateLimitProfileChanged, fkGponProfile2RateLimitProfileCreated, fkGponProfile2RateLimitProfileDeleted, fkGponProfile2RateLimitProfileChanged, fkGponProfile2BridgePortBridgeChanged, 
                                fkGponProfile2OnuMacFullPolicyChanged, fkGponProfile2OnuCpuPacketLimitBroadcastChanged, fkGponProfile2OnuCpuPacketLimitMulticastChanged, fkGponProfile2OnuCpuPacketLimitDlfChanged, fkGponOnuOmciPingTest, 
                                fkGponOltBerUsIntervalChanged, fkGponOltBerDsIntervalChanged, fkGponOltBerSfThresholdChanged, fkGponOltBerSdThresholdChanged, fkGponProfile2MapperGemRateLimitChanged, 
                                fkGponProfile2MapperGemRateLimitDeleted }
                        STATUS current
                        DESCRIPTION 
                                "Description."
                        ::= { fkGpon 54 }

                
        
        END

--
-- fk-gpon-mib.mib
--
