--
-- fk-network-mib.mib
-- MIB generated by MG-SOFT Visual MIB Builder Version 6.0  Build 88
-- Monday, January 21, 2013 at 17:17:29
--

        FK-NETWORK-MIB DEFINITIONS ::= BEGIN
 
                IMPORTS
                        fkMgmt                  
                                FROM FKOLTG1040-SMI                     
                        IANAtunnelType                  
                                FROM IANAifType-MIB                     
                        InterfaceIndex                  
                                FROM IF-MIB                     
                        InetAddressType, InetAddress                    
                                FROM INET-ADDRESS-MIB                   
                        FkControlStatusType, FkControlRequestResultType                 
                                FROM FK-TC-MIB                  
                        OBJECT-GROUP, NOTIFICATION-GROUP                        
                                FROM SNMPv2-CONF                        
                        TimeTicks, IpAddress, Integer32, Unsigned32, Gauge32, 
                        Counter64, OBJECT-TYPE, MODULE-IDENTITY, NOTIFICATION-TYPE                        
                                FROM SNMPv2-SMI                 
                        MacAddress                      
                                FROM SNMPv2-TC;
        
        
                -- 1.3.6.1.4.1.10428 9 1.101.11
                fkNetwork MODULE-IDENTITY 
                        LAST-UPDATED "200412291441Z"            -- December 29, 2004 at 14:41 GMT
                        ORGANIZATION 
                                "Furukawa Industrial S.A."
                        CONTACT-INFO 
                                "Furukawa Industrial S.A. Produtos Eletricos
        Rua Hasdrubal Bellegard, 820 - CIC
        CEP 81460-120 - Curitiba - Parana - Brasil
        CSC 0800-41-2100
        E-mail: fisa@furukawa.com.br"
                        DESCRIPTION 
                                "The MIB module for Furukawa GPON OLT FK-OLT-G1040."
                        ::= { fkMgmt 11 }

                
        
        
        
--
-- Node definitions
--
        
                -- 1.3.6.1.4.1.10428 9 1.101.11.1
                fkNetInterface OBJECT IDENTIFIER ::= { fkNetwork 1 }

                
                -- 1.3.6.1.4.1.10428 9 1.101.11.1.1
                fkNetIfTable OBJECT-TYPE
                        SYNTAX SEQUENCE OF FkNetIfEntry
                        MAX-ACCESS not-accessible
                        STATUS current
                        DESCRIPTION
                                "Description."
                        ::= { fkNetInterface 1 }

                
                -- 1.3.6.1.4.1.10428 9 1.101.11.1.1.1
                fkNetIfEntry OBJECT-TYPE
                        SYNTAX FkNetIfEntry
                        MAX-ACCESS not-accessible
                        STATUS current
                        DESCRIPTION
                                "Description."
                        INDEX { fkNetIfIndex }
                        ::= { fkNetIfTable 1 }

                
                FkNetIfEntry ::=
                        SEQUENCE { 
                                fkNetIfIndex
                                        Integer32,
                                fkNetIfName
                                        OCTET STRING,
                                fkNetIfDescription
                                        OCTET STRING,
                                fkNetIfTableIndex
                                        InterfaceIndex,
                                fkNetIfRegState
                                        INTEGER,
                                fkNetIfAdminState
                                        INTEGER,
                                fkNetIfOperState
                                        INTEGER,
                                fkNetIfMulticast
                                        INTEGER,
                                fkNetIfMtu
                                        INTEGER,
                                fkNetIfIpSetMode
                                        INTEGER,
                                fkNetIfIpMartianFilter
                                        INTEGER,
                                fkNetIfUpCnt
                                        Integer32,
                                fkNetIfDownCnt
                                        Integer32,
                                fkNetIfLinkUpTime
                                        Counter64,
                                fkNetIfElapsedTimeAfterClearStats
                                        Counter64,
                                fkNetIfBindingVRFName
                                        OCTET STRING,
                                fkNetIfOnFailUseVRF
                                        INTEGER,
                                fkNetIfIpUnreachability
                                        INTEGER,
                                fkNetIfipRedirects
                                        INTEGER,
                                fkNetIfIpForwarding
                                        INTEGER
                         }

                -- 1.3.6.1.4.1.10428 9 1.101.11.1.1.1.1
                fkNetIfIndex OBJECT-TYPE
                        SYNTAX Integer32 (0..11023)
                        MAX-ACCESS read-only
                        STATUS current
                        DESCRIPTION
                                "Network interface index
                                0           : any(all)
                                1..4094     : VLAN
                                4095        : management
                                4096        : loopback
                                4097        : NULL device
                                10000..11023: Tunnel interface index
                                "
                        ::= { fkNetIfEntry 1 }

                
                -- 1.3.6.1.4.1.10428 9 1.101.11.1.1.1.2
                fkNetIfName OBJECT-TYPE
                        SYNTAX OCTET STRING (SIZE (0..8))
                        MAX-ACCESS read-only
                        STATUS current
                        DESCRIPTION
                                "Device Name of this Interface."
                        ::= { fkNetIfEntry 2 }

                
                -- 1.3.6.1.4.1.10428 9 1.101.11.1.1.1.3
                fkNetIfDescription OBJECT-TYPE
                        SYNTAX OCTET STRING (SIZE (0..64))
                        MAX-ACCESS read-only
                        STATUS current
                        DESCRIPTION
                                "Description of this interface."
                        ::= { fkNetIfEntry 3 }

                
                -- 1.3.6.1.4.1.10428 9 1.101.11.1.1.1.4
                fkNetIfTableIndex OBJECT-TYPE
                        SYNTAX InterfaceIndex
                        MAX-ACCESS read-only
                        STATUS current
                        DESCRIPTION
                                "Same as ifIndex (for appropriated ifTable entries)."
                        ::= { fkNetIfEntry 4 }

                
                -- 1.3.6.1.4.1.10428 9 1.101.11.1.1.1.5
                fkNetIfRegState OBJECT-TYPE
                        SYNTAX INTEGER
                                {
                                unregistered(0),
                                registered(1)
                                }
                        MAX-ACCESS read-only
                        STATUS current
                        DESCRIPTION
                                "Registered state of Network device."
                        ::= { fkNetIfEntry 5 }

                
                -- 1.3.6.1.4.1.10428 9 1.101.11.1.1.1.6
                fkNetIfAdminState OBJECT-TYPE
                        SYNTAX INTEGER
                                {
                                down(0),
                                up(1)
                                }
                        MAX-ACCESS read-only
                        STATUS current
                        DESCRIPTION
                                "Administrative state.
                                down - shutdown
                                up - noshutdown"
                        ::= { fkNetIfEntry 6 }

                
                -- 1.3.6.1.4.1.10428 9 1.101.11.1.1.1.7
                fkNetIfOperState OBJECT-TYPE
                        SYNTAX INTEGER
                                {
                                down(0),
                                up(1)
                                }
                        MAX-ACCESS read-only
                        STATUS current
                        DESCRIPTION
                                "Operational state.
                                down - shutdown or not running
                                up - running"
                        ::= { fkNetIfEntry 7 }

                
                -- 1.3.6.1.4.1.10428 9 1.101.11.1.1.1.8
                fkNetIfMulticast OBJECT-TYPE
                        SYNTAX INTEGER
                                {
                                disable(0),
                                enable(1)
                                }
                        MAX-ACCESS read-only
                        STATUS current
                        DESCRIPTION
                                "Multicast enable/disable state."
                        ::= { fkNetIfEntry 8 }

                
                -- 1.3.6.1.4.1.10428 9 1.101.11.1.1.1.9
                fkNetIfMtu OBJECT-TYPE
                        SYNTAX INTEGER (64..17940)
                        MAX-ACCESS read-only
                        STATUS current
                        DESCRIPTION
                                "Maximum Transmission Unit."
                        ::= { fkNetIfEntry 9 }

                
                -- 1.3.6.1.4.1.10428 9 1.101.11.1.1.1.10
                fkNetIfIpSetMode OBJECT-TYPE
                        SYNTAX INTEGER
                                {
                                static(0),
                                dynamic(1)
                                }
                        MAX-ACCESS read-only
                        STATUS current
                        DESCRIPTION
                                "IP address setting mode.
                                0 : static
                                1 : dynamic (by DHCP client)
                                "
                        ::= { fkNetIfEntry 10 }

                
                -- 1.3.6.1.4.1.10428 9 1.101.11.1.1.1.11
                fkNetIfIpMartianFilter OBJECT-TYPE
                        SYNTAX INTEGER
                                {
                                disable(0),
                                enable(1)
                                }
                        MAX-ACCESS read-only
                        STATUS current
                        DESCRIPTION
                                "Description."
                        ::= { fkNetIfEntry 11 }

                
                -- 1.3.6.1.4.1.10428 9 1.101.11.1.1.1.12
                fkNetIfUpCnt OBJECT-TYPE
                        SYNTAX Integer32
                        MAX-ACCESS read-only
                        STATUS current
                        DESCRIPTION
                                "The times of link-up event."
                        ::= { fkNetIfEntry 12 }

                
                -- 1.3.6.1.4.1.10428 9 1.101.11.1.1.1.13
                fkNetIfDownCnt OBJECT-TYPE
                        SYNTAX Integer32
                        MAX-ACCESS read-only
                        STATUS current
                        DESCRIPTION
                                "The times of link-down event."
                        ::= { fkNetIfEntry 13 }

                
                -- 1.3.6.1.4.1.10428 9 1.101.11.1.1.1.14
                fkNetIfLinkUpTime OBJECT-TYPE
                        SYNTAX Counter64
                        UNITS "1 sec"
                        MAX-ACCESS read-only
                        STATUS current
                        DESCRIPTION
                                "The elapsed time after link is up."
                        ::= { fkNetIfEntry 14 }

                
                -- 1.3.6.1.4.1.10428 9 1.101.11.1.1.1.15
                fkNetIfElapsedTimeAfterClearStats OBJECT-TYPE
                        SYNTAX Counter64
                        UNITS "1 sec"
                        MAX-ACCESS read-only
                        STATUS current
                        DESCRIPTION
                                "The elapsed time after clearing status."
                        ::= { fkNetIfEntry 15 }

                
                -- 1.3.6.1.4.1.10428 9 1.101.11.1.1.1.16
                fkNetIfBindingVRFName OBJECT-TYPE
                        SYNTAX OCTET STRING (SIZE (0..63))
                        MAX-ACCESS read-only
                        STATUS current
                        DESCRIPTION
                                "VRF name that this tunnel interface is binding."
                        ::= { fkNetIfEntry 16 }

                
                -- 1.3.6.1.4.1.10428 9 1.101.11.1.1.1.17
                fkNetIfOnFailUseVRF OBJECT-TYPE
                        SYNTAX INTEGER
                                {
                                enable(1),
                                disable(2)
                                }
                        MAX-ACCESS read-only
                        STATUS current
                        DESCRIPTION
                                "Lookup into a global routing table when the VRF routing table lookup was failed."
                        ::= { fkNetIfEntry 17 }

                
                -- 1.3.6.1.4.1.10428 9 1.101.11.1.1.1.18
                fkNetIfIpUnreachability OBJECT-TYPE
                        SYNTAX INTEGER
                                {
                                enable(1),
                                disable(2)
                                }
                        MAX-ACCESS read-only
                        STATUS current
                        DESCRIPTION
                                "IP unreachability ON/OFF
                                "
                        DEFVAL { enable }
                        ::= { fkNetIfEntry 18 }

                
                -- 1.3.6.1.4.1.10428 9 1.101.11.1.1.1.19
                fkNetIfipRedirects OBJECT-TYPE
                        SYNTAX INTEGER
                                {
                                enable(1),
                                disable(2)
                                }
                        MAX-ACCESS read-only
                        STATUS current
                        DESCRIPTION
                                "Description."
                        ::= { fkNetIfEntry 19 }

                
                -- 1.3.6.1.4.1.10428 9 1.101.11.1.1.1.20
                fkNetIfIpForwarding OBJECT-TYPE
                        SYNTAX INTEGER
                                {
                                disable(0),
                                enable(1)
                                }
                        MAX-ACCESS read-only
                        STATUS current
                        DESCRIPTION
                                "The IP forwarding status"
                        ::= { fkNetIfEntry 20 }

                
                -- 1.3.6.1.4.1.10428 9 1.101.11.1.2
                fkNetIfControl OBJECT IDENTIFIER ::= { fkNetInterface 2 }

                
                -- 1.3.6.1.4.1.10428 9 1.101.11.1.2.1
                fkNetIfControlRequest OBJECT-TYPE
                        SYNTAX INTEGER
                                {
                                setNetIfRegState(1),
                                setNetIfProfile(2),
                                setNetIfIpMartianFilter(3),
                                setNetIfBindingVRF(4),
                                unsetNetIfBindingVRF(5),
                                setNetIfOnFailUseVRF(6),
                                setNetIfIpUnreachability(7),
                                setNetIfIpRedirects(8),
                                setNetIfIpForwarding(9)
                                }
                        MAX-ACCESS read-write
                        STATUS current
                        DESCRIPTION
                                "The request of a user command."
                        DEFVAL { setNetIfProfile }
                        ::= { fkNetIfControl 1 }

                
                -- 1.3.6.1.4.1.10428 9 1.101.11.1.2.2
                fkNetIfControlStatus OBJECT-TYPE
                        SYNTAX FkControlStatusType
                        MAX-ACCESS read-only
                        STATUS current
                        DESCRIPTION
                                "The status of a user command."
                        ::= { fkNetIfControl 2 }

                
                -- 1.3.6.1.4.1.10428 9 1.101.11.1.2.3
                fkNetIfControlTimer OBJECT-TYPE
                        SYNTAX Gauge32
                        MAX-ACCESS read-write
                        STATUS current
                        DESCRIPTION
                                "The maximum wait time for the manager for a long running user command."
                        DEFVAL { 0 }
                        ::= { fkNetIfControl 3 }

                
                -- 1.3.6.1.4.1.10428 9 1.101.11.1.2.4
                fkNetIfControlTimeStamp OBJECT-TYPE
                        SYNTAX FkControlRequestResultType
                        MAX-ACCESS read-only
                        STATUS current
                        DESCRIPTION
                                "The time stamp of the last command (end of command)."
                        ::= { fkNetIfControl 4 }

                
                -- 1.3.6.1.4.1.10428 9 1.101.11.1.2.5
                fkNetIfControlReqResult OBJECT-TYPE
                        SYNTAX TimeTicks
                        MAX-ACCESS read-only
                        STATUS current
                        DESCRIPTION
                                "The result of the last user command."
                        ::= { fkNetIfControl 5 }

                
                -- 1.3.6.1.4.1.10428 9 1.101.11.1.2.6
                fkNetIfControlIndex OBJECT-TYPE
                        SYNTAX Integer32 (0..11023)
                        MAX-ACCESS read-write
                        STATUS current
                        DESCRIPTION
                                "Network interface index
                                0           : any(all)
                                1..4094     : VLAN
                                4095        : management
                                4096        : loopback
                                4097        : NULL device
                                10000..11023: Tunnel interface index"
                        ::= { fkNetIfControl 6 }

                
                -- 1.3.6.1.4.1.10428 9 1.101.11.1.2.7
                fkNetIfControlDescription OBJECT-TYPE
                        SYNTAX OCTET STRING (SIZE (0..64))
                        MAX-ACCESS read-write
                        STATUS current
                        DESCRIPTION
                                "Description of this interface."
                        DEFVAL { "" }
                        ::= { fkNetIfControl 7 }

                
                -- 1.3.6.1.4.1.10428 9 1.101.11.1.2.8
                fkNetIfControlRegState OBJECT-TYPE
                        SYNTAX INTEGER
                                {
                                unregister(0),
                                register(1)
                                }
                        MAX-ACCESS read-write
                        STATUS current
                        DESCRIPTION
                                "Description."
                        ::= { fkNetIfControl 8 }

                
                -- 1.3.6.1.4.1.10428 9 1.101.11.1.2.9
                fkNetIfControlAdminState OBJECT-TYPE
                        SYNTAX INTEGER
                                {
                                down(0),
                                up(1)
                                }
                        MAX-ACCESS read-write
                        STATUS current
                        DESCRIPTION
                                "Administrative state."
                        DEFVAL { up }
                        ::= { fkNetIfControl 9 }

                
                -- 1.3.6.1.4.1.10428 9 1.101.11.1.2.10
                fkNetIfControlMulticast OBJECT-TYPE
                        SYNTAX INTEGER
                                {
                                disable(0),
                                enable(1)
                                }
                        MAX-ACCESS read-write
                        STATUS current
                        DESCRIPTION
                                "Multicast enable/disable state."
                        DEFVAL { enable }
                        ::= { fkNetIfControl 10 }

                
                -- 1.3.6.1.4.1.10428 9 1.101.11.1.2.11
                fkNetIfControlMtu OBJECT-TYPE
                        SYNTAX INTEGER (64..17940)
                        MAX-ACCESS read-write
                        STATUS current
                        DESCRIPTION
                                "Maximum Transmission Unit."
                        DEFVAL { 1500 }
                        ::= { fkNetIfControl 11 }

                
                -- 1.3.6.1.4.1.10428 9 1.101.11.1.2.12
                fkNetIfControlIpMartianFilter OBJECT-TYPE
                        SYNTAX INTEGER
                                {
                                disable(0),
                                enable(1)
                                }
                        MAX-ACCESS read-write
                        STATUS current
                        DESCRIPTION
                                "Description."
                        ::= { fkNetIfControl 12 }

                
                -- 1.3.6.1.4.1.10428 9 1.101.11.1.2.13
                fkNetIfControlBindingVRFName OBJECT-TYPE
                        SYNTAX OCTET STRING (SIZE (0..63))
                        MAX-ACCESS read-write
                        STATUS current
                        DESCRIPTION
                                "VRF name that this tunnel interface is binding."
                        ::= { fkNetIfControl 13 }

                
                -- 1.3.6.1.4.1.10428 9 1.101.11.1.2.14
                fkNetIfControlOnFailUseVRF OBJECT-TYPE
                        SYNTAX INTEGER
                                {
                                enable(1),
                                disable(2)
                                }
                        MAX-ACCESS read-write
                        STATUS current
                        DESCRIPTION
                                "Lookup into a global routing table when the VRF routing table lookup was failed."
                        ::= { fkNetIfControl 14 }

                
                -- 1.3.6.1.4.1.10428 9 1.101.11.1.2.15
                fkNetIfControlIpUnreachability OBJECT-TYPE
                        SYNTAX INTEGER
                                {
                                enable(1),
                                disable(2)
                                }
                        MAX-ACCESS read-write
                        STATUS current
                        DESCRIPTION
                                "IP unreachability ON/OFF"
                        DEFVAL { enable }
                        ::= { fkNetIfControl 15 }

                
                -- 1.3.6.1.4.1.10428 9 1.101.11.1.2.16
                fkNetIfControlIpRedirects OBJECT-TYPE
                        SYNTAX INTEGER
                                {
                                enable(1),
                                disable(2)
                                }
                        MAX-ACCESS read-write
                        STATUS current
                        DESCRIPTION
                                "Description."
                        ::= { fkNetIfControl 16 }

                
                -- 1.3.6.1.4.1.10428 9 1.101.11.1.2.17
                fkNetIfControlIpForwarding OBJECT-TYPE
                        SYNTAX INTEGER
                                {
                                disable(0),
                                enable(1)
                                }
                        MAX-ACCESS read-write
                        STATUS current
                        DESCRIPTION
                                "The IP forwarding status"
                        ::= { fkNetIfControl 17 }

                
                -- 1.3.6.1.4.1.10428 9 1.101.11.1.3
                fkNetIfNotification OBJECT IDENTIFIER ::= { fkNetInterface 3 }

                
                -- 1.3.6.1.4.1.10428 9 1.101.11.1.3.1
                fkNetIfRegStateChanged NOTIFICATION-TYPE
                        OBJECTS { fkNetIfControlRequest, fkNetIfControlTimeStamp, fkNetIfControlReqResult, fkNetIfRegState }
                        STATUS current
                        DESCRIPTION 
                                "Description."
                        ::= { fkNetIfNotification 1 }

                
                -- 1.3.6.1.4.1.10428 9 1.101.11.1.3.2
                fkNetIfProfileChanged NOTIFICATION-TYPE
                        OBJECTS { fkNetIfControlRequest, fkNetIfControlTimeStamp, fkNetIfControlReqResult, fkNetIfDescription, fkNetIfAdminState, 
                                fkNetIfMulticast, fkNetIfMtu }
                        STATUS current
                        DESCRIPTION 
                                "setNetIfProfile."
                        ::= { fkNetIfNotification 2 }

                
                -- 1.3.6.1.4.1.10428 9 1.101.11.1.3.3
                fkNetIfIpMartianFilterChanged NOTIFICATION-TYPE
                        OBJECTS { fkNetIfControlRequest, fkNetIfControlIndex, fkNetIfControlTimeStamp, fkNetIfControlReqResult, fkNetIfControlIpMartianFilter
                                 }
                        STATUS current
                        DESCRIPTION 
                                "Description."
                        ::= { fkNetIfNotification 3 }

                
                -- 1.3.6.1.4.1.10428 9 1.101.11.1.3.4
                fkNetIfBindingVRFSet NOTIFICATION-TYPE
                        OBJECTS { fkNetIfControlRequest, fkNetIfControlTimeStamp, fkNetIfControlReqResult, fkNetIfControlIndex, fkNetIfControlBindingVRFName
                                 }
                        STATUS current
                        DESCRIPTION 
                                "Description."
                        ::= { fkNetIfNotification 4 }

                
                -- 1.3.6.1.4.1.10428 9 1.101.11.1.3.5
                fkNetIfBindingVRFUnset NOTIFICATION-TYPE
                        OBJECTS { fkNetIfControlRequest, fkNetIfControlTimeStamp, fkNetIfControlReqResult, fkNetIfControlIndex, fkNetIfControlBindingVRFName
                                 }
                        STATUS current
                        DESCRIPTION 
                                "Description."
                        ::= { fkNetIfNotification 5 }

                
                -- 1.3.6.1.4.1.10428 9 1.101.11.1.3.6
                fkNetIfIpOnFailUseVRFChanged NOTIFICATION-TYPE
                        OBJECTS { fkNetIfControlRequest, fkNetIfControlTimeStamp, fkNetIfControlReqResult, fkNetIfControlIndex, fkNetIfControlOnFailUseVRF
                                 }
                        STATUS current
                        DESCRIPTION 
                                "Description."
                        ::= { fkNetIfNotification 6 }

                
                -- 1.3.6.1.4.1.10428 9 1.101.11.1.3.7
                fkNetIfIpUnreachabilityChanged NOTIFICATION-TYPE
                        OBJECTS { fkNetIfControlRequest, fkNetIfControlTimeStamp, fkNetIfControlReqResult, fkNetIfControlIndex, fkNetIfControlIpUnreachability
                                 }
                        STATUS current
                        DESCRIPTION 
                                "Description."
                        ::= { fkNetIfNotification 7 }

                
                -- 1.3.6.1.4.1.10428 9 1.101.11.1.3.8
                fkNetIfIpRedirectsChanged NOTIFICATION-TYPE
                        OBJECTS { fkNetIfControlRequest, fkNetIfControlTimeStamp, fkNetIfControlReqResult, fkNetIfControlIpRedirects }
                        STATUS current
                        DESCRIPTION 
                                "Description."
                        ::= { fkNetIfNotification 8 }

                
                -- 1.3.6.1.4.1.10428 9 1.101.11.1.3.9
                fkNetIfIpForwardingChanged NOTIFICATION-TYPE
                        OBJECTS { fkNetIfControlRequest, fkNetIfControlTimeStamp, fkNetIfControlReqResult, fkNetIfControlIndex, fkNetIfControlIpForwarding
                                 }
                        STATUS current
                        DESCRIPTION 
                                "setNetIfIpForwarding"
                        ::= { fkNetIfNotification 9 }

                
                -- 1.3.6.1.4.1.10428 9 1.101.11.2
                fkIpAddress OBJECT IDENTIFIER ::= { fkNetwork 2 }

                
                -- 1.3.6.1.4.1.10428 9 1.101.11.2.1
                fkIpAddrTable OBJECT-TYPE
                        SYNTAX SEQUENCE OF FkIpAddrEntry
                        MAX-ACCESS not-accessible
                        STATUS current
                        DESCRIPTION
                                "Description."
                        ::= { fkIpAddress 1 }

                
                -- 1.3.6.1.4.1.10428 9 1.101.11.2.1.1
                fkIpAddrEntry OBJECT-TYPE
                        SYNTAX FkIpAddrEntry
                        MAX-ACCESS not-accessible
                        STATUS current
                        DESCRIPTION
                                "Description."
                        INDEX { fkNetIfIndex, fkIpAddrValue }
                        ::= { fkIpAddrTable 1 }

                
                FkIpAddrEntry ::=
                        SEQUENCE { 
                                fkIpAddrValue
                                        IpAddress,
                                fkIpAddrMask
                                        Integer32,
                                fkIpAddrBcast
                                        IpAddress,
                                fkIpAddrFlag
                                        BITS,
                                fkIpAddrScope
                                        INTEGER,
                                fkIpAddrIpIndex
                                        INTEGER,
                                fkIpAddrUnnumUsedIp
                                        INTEGER
                         }

                -- 1.3.6.1.4.1.10428 9 1.101.11.2.1.1.1
                fkIpAddrValue OBJECT-TYPE
                        SYNTAX IpAddress
                        MAX-ACCESS read-only
                        STATUS current
                        DESCRIPTION
                                "The IP address to which this entry's addressing information pertains."
                        ::= { fkIpAddrEntry 1 }

                
                -- 1.3.6.1.4.1.10428 9 1.101.11.2.1.1.2
                fkIpAddrMask OBJECT-TYPE
                        SYNTAX Integer32 (1..32)
                        MAX-ACCESS read-only
                        STATUS current
                        DESCRIPTION
                                "The subnet mask associated with the IP address of this entry.  
                                The value of the mask is an IP address with all the network 
                                bits set to 1 and all the hosts bits set to 0."
                        ::= { fkIpAddrEntry 2 }

                
                -- 1.3.6.1.4.1.10428 9 1.101.11.2.1.1.3
                fkIpAddrBcast OBJECT-TYPE
                        SYNTAX IpAddress
                        MAX-ACCESS read-only
                        STATUS current
                        DESCRIPTION
                                "The value of the least-significant bit in the IP broadcast 
                                address used for sending datagrams on the (logical) 
                                interface associated with the IP address of this entry.
                                For example, when the Internet standard all-ones broadcast 
                                address is used, the value will be 1.  This value applies 
                                to both the subnet and network broadcasts addresses used 
                                by the entity on this (logical) interface."
                        ::= { fkIpAddrEntry 3 }

                
                -- 1.3.6.1.4.1.10428 9 1.101.11.2.1.1.4
                fkIpAddrFlag OBJECT-TYPE
                        SYNTAX BITS
                                {
                                permanent(0),
                                tentative(1),
                                deprecated(2),
                                reserved3(3),
                                reserved4(4),
                                reserved5(5),
                                reserved6(6),
                                secondary(7)
                                }
                        MAX-ACCESS read-only
                        STATUS current
                        DESCRIPTION
                                "Description."
                        ::= { fkIpAddrEntry 4 }

                
                -- 1.3.6.1.4.1.10428 9 1.101.11.2.1.1.5
                fkIpAddrScope OBJECT-TYPE
                        SYNTAX INTEGER
                                {
                                global(0),
                                site(200),
                                link(253),
                                host(254),
                                nowhere(255)
                                }
                        MAX-ACCESS read-only
                        STATUS current
                        DESCRIPTION
                                "Description."
                        ::= { fkIpAddrEntry 5 }

                
                -- 1.3.6.1.4.1.10428 9 1.101.11.2.1.1.6
                fkIpAddrIpIndex OBJECT-TYPE
                        SYNTAX INTEGER (0..1024)
                        MAX-ACCESS read-only
                        STATUS current
                        DESCRIPTION
                                "The Ip index for Interface Unnumbered feature enhanced.
                                If Interface Unnumbered enhanced feature is enabled on a point-to-point interface. It will get a ip address of a specific interface.
                                Interface unnumbered default setting - it get primary ip address.
                                Interface unnumbered enhanced setting - it get secondary ip address with ip-index.
                                (cf. primary ip address's ip-index : 1. no setting: 0. other setting: 2-1024)"
                        ::= { fkIpAddrEntry 6 }

                
                -- 1.3.6.1.4.1.10428 9 1.101.11.2.1.1.7
                fkIpAddrUnnumUsedIp OBJECT-TYPE
                        SYNTAX INTEGER
                                {
                                none(0),
                                used(1)
                                }
                        MAX-ACCESS read-only
                        STATUS current
                        DESCRIPTION
                                "The Check a specific IP address for using interface unnumbered feature."
                        ::= { fkIpAddrEntry 7 }

                
                -- 1.3.6.1.4.1.10428 9 1.101.11.2.2
                fkIpAddrControl OBJECT IDENTIFIER ::= { fkIpAddress 2 }

                
                -- 1.3.6.1.4.1.10428 9 1.101.11.2.2.1
                fkIpAddrControlRequest OBJECT-TYPE
                        SYNTAX INTEGER
                                {
                                createIpAddress(1),
                                destroyIpAddress(2),
                                addIpIndex(3),
                                delIpIndex(4)
                                }
                        MAX-ACCESS read-write
                        STATUS current
                        DESCRIPTION
                                "The request of a user command."
                        ::= { fkIpAddrControl 1 }

                
                -- 1.3.6.1.4.1.10428 9 1.101.11.2.2.2
                fkIpAddrControlStatus OBJECT-TYPE
                        SYNTAX FkControlStatusType
                        MAX-ACCESS read-only
                        STATUS current
                        DESCRIPTION
                                "The status of a user command."
                        ::= { fkIpAddrControl 2 }

                
                -- 1.3.6.1.4.1.10428 9 1.101.11.2.2.3
                fkIpAddrControlTimer OBJECT-TYPE
                        SYNTAX Gauge32
                        MAX-ACCESS read-write
                        STATUS current
                        DESCRIPTION
                                "The maximum wait time for the manager for a long running user command."
                        DEFVAL { 0 }
                        ::= { fkIpAddrControl 3 }

                
                -- 1.3.6.1.4.1.10428 9 1.101.11.2.2.4
                fkIpAddrControlTimeStamp OBJECT-TYPE
                        SYNTAX FkControlRequestResultType
                        MAX-ACCESS read-only
                        STATUS current
                        DESCRIPTION
                                "The time stamp of the last command (end of command)."
                        ::= { fkIpAddrControl 4 }

                
                -- 1.3.6.1.4.1.10428 9 1.101.11.2.2.5
                fkIpAddrControlReqResult OBJECT-TYPE
                        SYNTAX TimeTicks
                        MAX-ACCESS read-only
                        STATUS current
                        DESCRIPTION
                                "The result of the last user command."
                        ::= { fkIpAddrControl 5 }

                
                -- 1.3.6.1.4.1.10428 9 1.101.11.2.2.6
                fkIpAddrControlNetIfIndex OBJECT-TYPE
                        SYNTAX Integer32 (1..4094 | 10000..11023)
                        MAX-ACCESS read-write
                        STATUS current
                        DESCRIPTION
                                "Network interface index
                                1..4094     : VLAN
                                10000..11023: Tunnel interface index
                                "
                        DEFVAL { 1 }
                        ::= { fkIpAddrControl 6 }

                
                -- 1.3.6.1.4.1.10428 9 1.101.11.2.2.7
                fkIpAddrControlValue OBJECT-TYPE
                        SYNTAX IpAddress
                        MAX-ACCESS read-write
                        STATUS current
                        DESCRIPTION
                                "The IP address to which this entry's addressing information pertains."
                        DEFVAL { 'ac106464'h }
                        ::= { fkIpAddrControl 7 }

                
                -- 1.3.6.1.4.1.10428 9 1.101.11.2.2.8
                fkIpAddrControlMask OBJECT-TYPE
                        SYNTAX Integer32 (1..32)
                        MAX-ACCESS read-write
                        STATUS current
                        DESCRIPTION
                                "The subnet mask associated with the IP address of this entry.  "
                        DEFVAL { 24 }
                        ::= { fkIpAddrControl 8 }

                
                -- 1.3.6.1.4.1.10428 9 1.101.11.2.2.9
                fkIpAddrControlFlag OBJECT-TYPE
                        SYNTAX INTEGER
                                {
                                primary(0),
                                secondary(1)
                                }
                        MAX-ACCESS read-write
                        STATUS current
                        DESCRIPTION
                                "Description."
                        DEFVAL { primary }
                        ::= { fkIpAddrControl 9 }

                
                -- 1.3.6.1.4.1.10428 9 1.101.11.2.2.10
                fkIpAddrControlScope OBJECT-TYPE
                        SYNTAX INTEGER
                                {
                                global(0),
                                link(253),
                                host(254)
                                }
                        MAX-ACCESS read-write
                        STATUS current
                        DESCRIPTION
                                "Description."
                        DEFVAL { global }
                        ::= { fkIpAddrControl 10 }

                
                -- 1.3.6.1.4.1.10428 9 1.101.11.2.2.11
                fkIpAddrControlIpIndex OBJECT-TYPE
                        SYNTAX INTEGER (1..1024)
                        MAX-ACCESS read-write
                        STATUS current
                        DESCRIPTION
                                "The Ip index for Interface Unnumbered feature enhanced.
                                If Interface Unnumbered enhanced feature is enabled on a point-to-point interface. It will get a ip address of a specific interface.
                                Interface unnumbered default setting - it get primary ip address.
                                Interface unnumbered enhanced setting - it get secondary ip address with ip-index.
                                (cf. primary ip address's ip-index : 1. no setting: 0. other setting: 2-1024)"
                        ::= { fkIpAddrControl 11 }

                
                -- 1.3.6.1.4.1.10428 9 1.101.11.2.3
                fkIpAddrNotification OBJECT IDENTIFIER ::= { fkIpAddress 3 }

                
                -- 1.3.6.1.4.1.10428 9 1.101.11.2.3.1
                fkIpAddressCreated NOTIFICATION-TYPE
                        OBJECTS { fkIpAddrControlRequest, fkIpAddrControlTimeStamp, fkIpAddrControlReqResult, fkIpAddrMask, fkIpAddrFlag, 
                                fkIpAddrScope }
                        STATUS current
                        DESCRIPTION 
                                "createIpAddress."
                        ::= { fkIpAddrNotification 1 }

                
                -- 1.3.6.1.4.1.10428 9 1.101.11.2.3.2
                fkIpAddressDestroyed NOTIFICATION-TYPE
                        OBJECTS { fkIpAddrControlRequest, fkIpAddrControlTimeStamp, fkIpAddrControlReqResult, fkIpAddrMask }
                        STATUS current
                        DESCRIPTION 
                                "destroyIpAddress."
                        ::= { fkIpAddrNotification 2 }

                
                -- 1.3.6.1.4.1.10428 9 1.101.11.2.3.3
                fkIpAddressIpIndexAdded NOTIFICATION-TYPE
                        OBJECTS { fkIpAddrControlRequest, fkIpAddrControlTimeStamp, fkIpAddrControlReqResult, fkIpAddrControlNetIfIndex, fkIpAddrControlValue, 
                                fkIpAddrControlMask, fkIpAddrControlIpIndex }
                        STATUS current
                        DESCRIPTION 
                                "addIpIndex"
                        ::= { fkIpAddrNotification 3 }

                
                -- 1.3.6.1.4.1.10428 9 1.101.11.2.3.4
                fkIpAddressIpIndexDeleted NOTIFICATION-TYPE
                        OBJECTS { fkIpAddrControlRequest, fkIpAddrControlTimeStamp, fkIpAddrControlReqResult, fkIpAddrControlNetIfIndex, fkIpAddrControlIpIndex
                                 }
                        STATUS current
                        DESCRIPTION 
                                "delIpIndex"
                        ::= { fkIpAddrNotification 4 }

                
                -- 1.3.6.1.4.1.10428 9 1.101.11.3
                fkArp OBJECT IDENTIFIER ::= { fkNetwork 3 }

                
                -- 1.3.6.1.4.1.10428 9 1.101.11.3.1
                fkArpTable OBJECT-TYPE
                        SYNTAX SEQUENCE OF FkArpEntry
                        MAX-ACCESS not-accessible
                        STATUS current
                        DESCRIPTION
                                "Description."
                        ::= { fkArp 1 }

                
                -- 1.3.6.1.4.1.10428 9 1.101.11.3.1.1
                fkArpEntry OBJECT-TYPE
                        SYNTAX FkArpEntry
                        MAX-ACCESS not-accessible
                        STATUS current
                        DESCRIPTION
                                "Description."
                        INDEX { fkNetIfIndex, fkArpIpAddress }
                        ::= { fkArpTable 1 }

                
                FkArpEntry ::=
                        SEQUENCE { 
                                fkArpIpAddress
                                        IpAddress,
                                fkArpPhyAddress
                                        MacAddress,
                                fkArpPortIndex
                                        Integer32,
                                fkArpState
                                        INTEGER,
                                fkArpHwType
                                        INTEGER,
                                fkArpHwUsed
                                        INTEGER,
                                fkArpUsedTime
                                        INTEGER
                         }

                -- 1.3.6.1.4.1.10428 9 1.101.11.3.1.1.1
                fkArpIpAddress OBJECT-TYPE
                        SYNTAX IpAddress
                        MAX-ACCESS read-only
                        STATUS current
                        DESCRIPTION
                                "The NetworkAddress (e.g., the IP address) corresponding 
                                to the media-dependent `physical' address."
                        ::= { fkArpEntry 1 }

                
                -- 1.3.6.1.4.1.10428 9 1.101.11.3.1.1.2
                fkArpPhyAddress OBJECT-TYPE
                        SYNTAX MacAddress
                        MAX-ACCESS read-only
                        STATUS current
                        DESCRIPTION
                                "The media-dependent `physical' address."
                        ::= { fkArpEntry 2 }

                
                -- 1.3.6.1.4.1.10428 9 1.101.11.3.1.1.3
                fkArpPortIndex OBJECT-TYPE
                        SYNTAX Integer32 (0..255)
                        MAX-ACCESS read-only
                        STATUS current
                        DESCRIPTION
                                "The interface on which this entry's equivalence is effective.
                                0: for any ports."
                        ::= { fkArpEntry 3 }

                
                -- 1.3.6.1.4.1.10428 9 1.101.11.3.1.1.4
                fkArpState OBJECT-TYPE
                        SYNTAX INTEGER
                                {
                                static(0),
                                dynamic(1)
                                }
                        MAX-ACCESS read-only
                        STATUS current
                        DESCRIPTION
                                "Arp entry's currently status."
                        ::= { fkArpEntry 4 }

                
                -- 1.3.6.1.4.1.10428 9 1.101.11.3.1.1.5
                fkArpHwType OBJECT-TYPE
                        SYNTAX INTEGER { ethernet(1) }
                        MAX-ACCESS read-only
                        STATUS current
                        DESCRIPTION
                                "Hardware Type of media."
                        ::= { fkArpEntry 5 }

                
                -- 1.3.6.1.4.1.10428 9 1.101.11.3.1.1.6
                fkArpHwUsed OBJECT-TYPE
                        SYNTAX INTEGER
                                {
                                nonused(0),
                                used(1)
                                }
                        MAX-ACCESS read-only
                        STATUS current
                        DESCRIPTION
                                "Arp entry's currently chip usage state."
                        ::= { fkArpEntry 6 }

                
                -- 1.3.6.1.4.1.10428 9 1.101.11.3.1.1.7
                fkArpUsedTime OBJECT-TYPE
                        SYNTAX INTEGER (1..10000000)
                        MAX-ACCESS read-only
                        STATUS current
                        DESCRIPTION
                                "Arp entry's chip used time.(if fkArpState is 0, always 0 and if fkArpHwUsed is 0, always 0.)"
                        ::= { fkArpEntry 7 }

                
                -- 1.3.6.1.4.1.10428 9 1.101.11.3.2
                fkArpControl OBJECT IDENTIFIER ::= { fkArp 2 }

                
                -- 1.3.6.1.4.1.10428 9 1.101.11.3.2.1
                fkArpControlRequest OBJECT-TYPE
                        SYNTAX INTEGER
                                {
                                createArpEntry(1),
                                destroyArpEntry(2),
                                clearArpTable(3),
                                clearArpTableByAddr(4)
                                }
                        MAX-ACCESS read-write
                        STATUS current
                        DESCRIPTION
                                "The request of a user command."
                        ::= { fkArpControl 1 }

                
                -- 1.3.6.1.4.1.10428 9 1.101.11.3.2.2
                fkArpControlStatus OBJECT-TYPE
                        SYNTAX FkControlStatusType
                        MAX-ACCESS read-only
                        STATUS current
                        DESCRIPTION
                                "The status of a user command."
                        ::= { fkArpControl 2 }

                
                -- 1.3.6.1.4.1.10428 9 1.101.11.3.2.3
                fkArpControlTimer OBJECT-TYPE
                        SYNTAX Gauge32
                        MAX-ACCESS read-write
                        STATUS current
                        DESCRIPTION
                                "The maximum wait time for the manager for a long running user command."
                        ::= { fkArpControl 3 }

                
                -- 1.3.6.1.4.1.10428 9 1.101.11.3.2.4
                fkArpControlTimeStamp OBJECT-TYPE
                        SYNTAX FkControlRequestResultType
                        MAX-ACCESS read-only
                        STATUS current
                        DESCRIPTION
                                "The time stamp of the last command (end of command)."
                        ::= { fkArpControl 4 }

                
                -- 1.3.6.1.4.1.10428 9 1.101.11.3.2.5
                fkArpControlReqResult OBJECT-TYPE
                        SYNTAX TimeTicks
                        MAX-ACCESS read-only
                        STATUS current
                        DESCRIPTION
                                "The result of the last user command."
                        ::= { fkArpControl 5 }

                
                -- 1.3.6.1.4.1.10428 9 1.101.11.3.2.6
                fkArpControlNetIfIndex OBJECT-TYPE
                        SYNTAX Integer32 (0..4096)
                        MAX-ACCESS read-write
                        STATUS current
                        DESCRIPTION
                                "Network interface index."
                        ::= { fkArpControl 6 }

                
                -- 1.3.6.1.4.1.10428 9 1.101.11.3.2.7
                fkArpControlIpAddress OBJECT-TYPE
                        SYNTAX IpAddress
                        MAX-ACCESS read-write
                        STATUS current
                        DESCRIPTION
                                "The NetworkAddress (e.g., the IP address) corresponding 
                                to the media-dependent `physical' address."
                        ::= { fkArpControl 7 }

                
                -- 1.3.6.1.4.1.10428 9 1.101.11.3.2.8
                fkArpControlPhyAddress OBJECT-TYPE
                        SYNTAX MacAddress
                        MAX-ACCESS read-write
                        STATUS current
                        DESCRIPTION
                                "The media-dependent `physical' address."
                        ::= { fkArpControl 8 }

                
                -- 1.3.6.1.4.1.10428 9 1.101.11.3.2.9
                fkArpControlState OBJECT-TYPE
                        SYNTAX INTEGER
                                {
                                static(0),
                                dynamic(1)
                                }
                        MAX-ACCESS read-write
                        STATUS current
                        DESCRIPTION
                                "Arp entry's currently status."
                        ::= { fkArpControl 9 }

                
                -- 1.3.6.1.4.1.10428 9 1.101.11.3.2.10
                fkArpControlMask OBJECT-TYPE
                        SYNTAX INTEGER (0..32)
                        MAX-ACCESS read-write
                        STATUS current
                        DESCRIPTION
                                "Description."
                        ::= { fkArpControl 10 }

                
                -- 1.3.6.1.4.1.10428 9 1.101.11.3.3
                fkArpNotification OBJECT IDENTIFIER ::= { fkArp 3 }

                
                -- 1.3.6.1.4.1.10428 9 1.101.11.3.3.1
                fkArpEntryCreated NOTIFICATION-TYPE
                        OBJECTS { fkArpControlRequest, fkArpControlTimeStamp, fkArpControlReqResult, fkArpPhyAddress }
                        STATUS current
                        DESCRIPTION 
                                "createArpEntry."
                        ::= { fkArpNotification 1 }

                
                -- 1.3.6.1.4.1.10428 9 1.101.11.3.3.2
                fkArpEntryDestroyed NOTIFICATION-TYPE
                        OBJECTS { fkArpControlRequest, fkArpControlTimeStamp, fkArpControlReqResult, fkArpPhyAddress }
                        STATUS current
                        DESCRIPTION 
                                "destroyArpEntry."
                        ::= { fkArpNotification 2 }

                
                -- 1.3.6.1.4.1.10428 9 1.101.11.3.3.3
                fkArpTableCleared NOTIFICATION-TYPE
                        OBJECTS { fkArpControlRequest, fkArpControlTimeStamp, fkArpControlReqResult, fkArpState }
                        STATUS current
                        DESCRIPTION 
                                "clearArpTable.
                                 In this notification PDU, key of fkArpState 
                                 is ifindex.0.0.0.0."
                        ::= { fkArpNotification 3 }

                
                -- 1.3.6.1.4.1.10428 9 1.101.11.3.3.4
                fkArpTableClearedByAddr NOTIFICATION-TYPE
                        OBJECTS { fkArpControlRequest, fkArpControlTimeStamp, fkArpControlReqResult, fkArpControlIpAddress, fkArpControlMask, 
                                fkArpControlState }
                        STATUS current
                        DESCRIPTION 
                                "clearArpTableByAddr"
                        ::= { fkArpNotification 4 }

                
                -- 1.3.6.1.4.1.10428 9 1.101.11.4
                fkRoute OBJECT IDENTIFIER ::= { fkNetwork 4 }

                
                -- 1.3.6.1.4.1.10428 9 1.101.11.4.1
                fkRouteTable OBJECT-TYPE
                        SYNTAX SEQUENCE OF FkRouteEntry
                        MAX-ACCESS not-accessible
                        STATUS current
                        DESCRIPTION
                                "Description."
                        ::= { fkRoute 1 }

                
                -- 1.3.6.1.4.1.10428 9 1.101.11.4.1.1
                fkRouteEntry OBJECT-TYPE
                        SYNTAX FkRouteEntry
                        MAX-ACCESS not-accessible
                        STATUS current
                        DESCRIPTION
                                "Description."
                        INDEX { fkRouteDstAddress, fkRouteDstMask, fkRouteGateway, fkRouteInterface, fkRouteVRFIndex
                                 }
                        ::= { fkRouteTable 1 }

                
                FkRouteEntry ::=
                        SEQUENCE { 
                                fkRouteDstAddress
                                        IpAddress,
                                fkRouteDstMask
                                        INTEGER,
                                fkRouteGateway
                                        IpAddress,
                                fkRouteInterface
                                        INTEGER,
                                fkRouteType
                                        INTEGER,
                                fkRouteProto
                                        INTEGER,
                                fkRouteMetric
                                        INTEGER,
                                fkRouteActive
                                        INTEGER,
                                fkRouteBindingSrcAddr
                                        IpAddress,
                                fkRouteDistance
                                        INTEGER,
                                fkRouteSubtype
                                        INTEGER,
                                fkRouteNexthopStatus
                                        BITS,
                                fkRouteRibStatus
                                        BITS,
                                fkRouteVRFIndex
                                        Integer32
                         }

                -- 1.3.6.1.4.1.10428 9 1.101.11.4.1.1.1
                fkRouteDstAddress OBJECT-TYPE
                        SYNTAX IpAddress
                        MAX-ACCESS read-only
                        STATUS current
                        DESCRIPTION
                                "The destination IP address of this route. 
                                An entry with a value of 0.0.0.0 is considered a default route. 
                                Multiple routes to a single destination can appear in the table, 
                                but access to such multiple entries is dependent on the table-access mechanisms defined by the network management protocol in use."
                        ::= { fkRouteEntry 1 }

                
                -- 1.3.6.1.4.1.10428 9 1.101.11.4.1.1.2
                fkRouteDstMask OBJECT-TYPE
                        SYNTAX INTEGER (0..32)
                        MAX-ACCESS read-only
                        STATUS current
                        DESCRIPTION
                                "Indicate the mask to be logical-ANDed with the destination address 
                                before being compared to the value in the fkRouteDstAddress field. 
                                For those systems that do not support arbitrary subnet masks, 
                                an agent constructs the value of the fkRouteDstMask 
                                by determining whether the value of the correspondent fkRouteDstAddress field 
                                belong to a class-A, B, or C network. 
                                If the value of the fkRouteDstAddress is 0.0.0.0 (a default route), 
                                then the mask value is also 0.0.0.0. It should be noted that all IP routing subsystems implicitly use this mechanism."
                        ::= { fkRouteEntry 2 }

                
                -- 1.3.6.1.4.1.10428 9 1.101.11.4.1.1.3
                fkRouteGateway OBJECT-TYPE
                        SYNTAX IpAddress
                        MAX-ACCESS read-only
                        STATUS current
                        DESCRIPTION
                                "The Gateway IP Address.
                                0.0.0.0/0 : indicate default gateway or invalid"
                        ::= { fkRouteEntry 3 }

                
                -- 1.3.6.1.4.1.10428 9 1.101.11.4.1.1.4
                fkRouteInterface OBJECT-TYPE
                        SYNTAX INTEGER (0..11023)
                        MAX-ACCESS read-only
                        STATUS current
                        DESCRIPTION
                                "The index value which uniquely identifies 
                                the local interface through 
                                which the next hop of this route 
                                should be reached. 
                                The interface identified by a particular 
                                value of this index is the same interface 
                                as identified by the same value of 
                                fkNetIfIndex.
                                
                                Network interface index
                                0: invalid
                                1..4094: VLAN
                                4095: management
                                4096: loopback
                                4097: NULL device
                                10000..11023: Tunnel interface index"
                        ::= { fkRouteEntry 4 }

                
                -- 1.3.6.1.4.1.10428 9 1.101.11.4.1.1.5
                fkRouteType OBJECT-TYPE
                        SYNTAX INTEGER
                                {
                                other(1),
                                invalid(2),
                                direct(3),
                                indirect(4)
                                }
                        MAX-ACCESS read-write
                        STATUS current
                        DESCRIPTION
                                "The type of route. 
                                Note that the values direct and indirect refer to the notion of direct 
                                and indirect routing in the IP architecture.
                                Setting this object to the value invalid has the effect of invalidating the corresponding entry 
                                in the fkRouteTable object. 
                                That is, it effectively dissasociates the destination identified 
                                with said entry from the route identified with said entry. 
                                It is an implementation-specific matter as to whether the agent removes an invalidated entry 
                                from the table. Accordingly, 
                                management stations must be prepared to receive tabular information 
                                from agents that corresponds to entries not currently in use. 
                                Proper interpretation of such entries requires examination of the relevant fkRouteType object."
                        ::= { fkRouteEntry 5 }

                
                -- 1.3.6.1.4.1.10428 9 1.101.11.4.1.1.6
                fkRouteProto OBJECT-TYPE
                        SYNTAX INTEGER
                                {
                                other(1),
                                localDirect(2),
                                netmgmtStatic(3),
                                icmp(4),
                                egp(5),
                                ggp(6),
                                hello(7),
                                rip(8),
                                isIs(9),
                                esIs(10),
                                ciscoIgrp(11),
                                bbnSpfIgp(12),
                                ospf(13),
                                bgp(14),
                                idpr(15),
                                ciscoEigrp(16),
                                dhcp(17)
                                }
                        MAX-ACCESS read-only
                        STATUS current
                        DESCRIPTION
                                "The routing mechanism via which this route was learned. 
                                Inclusion of values for gateway routing protocols is not intended to imply 
                                that hosts should support those protocols."
                        ::= { fkRouteEntry 6 }

                
                -- 1.3.6.1.4.1.10428 9 1.101.11.4.1.1.7
                fkRouteMetric OBJECT-TYPE
                        SYNTAX INTEGER (-1..255)
                        MAX-ACCESS read-write
                        STATUS current
                        DESCRIPTION
                                "The primary routing metric for this route.
                                The semantics of this metric are determined 
                                by the routing-protocol specified 
                                in the route's fkRouteProto value. 
                                If this metric is not used, 
                                its value should be set to -1."
                        ::= { fkRouteEntry 7 }

                
                -- 1.3.6.1.4.1.10428 9 1.101.11.4.1.1.8
                fkRouteActive OBJECT-TYPE
                        SYNTAX INTEGER
                                {
                                inactive(0),
                                active(1)
                                }
                        MAX-ACCESS read-write
                        STATUS current
                        DESCRIPTION
                                "The active status for this routing entry."
                        ::= { fkRouteEntry 8 }

                
                -- 1.3.6.1.4.1.10428 9 1.101.11.4.1.1.9
                fkRouteBindingSrcAddr OBJECT-TYPE
                        SYNTAX IpAddress
                        MAX-ACCESS read-only
                        STATUS current
                        DESCRIPTION
                                "The binding source IP Address for this route."
                        ::= { fkRouteEntry 9 }

                
                -- 1.3.6.1.4.1.10428 9 1.101.11.4.1.1.10
                fkRouteDistance OBJECT-TYPE
                        SYNTAX INTEGER (1..255)
                        MAX-ACCESS read-write
                        STATUS current
                        DESCRIPTION
                                "The Distance value for this route."
                        ::= { fkRouteEntry 10 }

                
                -- 1.3.6.1.4.1.10428 9 1.101.11.4.1.1.11
                fkRouteSubtype OBJECT-TYPE
                        SYNTAX INTEGER
                                {
                                unknown(0),
                                ospfIa(1),
                                ospfNssa1(2),
                                ospfNssa2(3),
                                ospfExternal1(4),
                                ospfExternal2(5),
                                isisL1(8),
                                isisL2(9),
                                isisIa(10),
                                bgpMpls(11)
                                }
                        MAX-ACCESS read-only
                        STATUS current
                        DESCRIPTION
                                "The subtype of this route."
                        ::= { fkRouteEntry 11 }

                
                -- 1.3.6.1.4.1.10428 9 1.101.11.4.1.1.12
                fkRouteNexthopStatus OBJECT-TYPE
                        SYNTAX BITS
                                {
                                active(0),
                                fib(1),
                                recursive(2)
                                }
                        MAX-ACCESS read-only
                        STATUS current
                        DESCRIPTION
                                "The nexthop status of this route."
                        ::= { fkRouteEntry 12 }

                
                -- 1.3.6.1.4.1.10428 9 1.101.11.4.1.1.13
                fkRouteRibStatus OBJECT-TYPE
                        SYNTAX BITS
                                {
                                internal(0),
                                selfroute(1),
                                blackhole(2),
                                nonfib(3),
                                selected(4),
                                changed(5),
                                static(6),
                                stale(7)
                                }
                        MAX-ACCESS read-only
                        STATUS current
                        DESCRIPTION
                                "The rib status for this route."
                        ::= { fkRouteEntry 13 }

                
                -- 1.3.6.1.4.1.10428 9 1.101.11.4.1.1.14
                fkRouteVRFIndex OBJECT-TYPE
                        SYNTAX Integer32 (0..2147483647)
                        MAX-ACCESS read-only
                        STATUS current
                        DESCRIPTION
                                "VRF index in fkIpVRFTable."
                        ::= { fkRouteEntry 14 }

                
                -- 1.3.6.1.4.1.10428 9 1.101.11.4.2
                fkRouteControl OBJECT IDENTIFIER ::= { fkRoute 2 }

                
                -- 1.3.6.1.4.1.10428 9 1.101.11.4.2.1
                fkRouteControlRequest OBJECT-TYPE
                        SYNTAX INTEGER
                                {
                                createStaticRoute(1),
                                destroyStaticRoute(2),
                                setStaticRouteProfile(3)
                                }
                        MAX-ACCESS read-write
                        STATUS current
                        DESCRIPTION
                                "The request of a user command."
                        ::= { fkRouteControl 1 }

                
                -- 1.3.6.1.4.1.10428 9 1.101.11.4.2.2
                fkRouteControlStatus OBJECT-TYPE
                        SYNTAX FkControlStatusType
                        MAX-ACCESS read-only
                        STATUS current
                        DESCRIPTION
                                "The status of a user command."
                        ::= { fkRouteControl 2 }

                
                -- 1.3.6.1.4.1.10428 9 1.101.11.4.2.3
                fkRouteControlTimer OBJECT-TYPE
                        SYNTAX Gauge32
                        MAX-ACCESS read-write
                        STATUS current
                        DESCRIPTION
                                "The maximum wait time for the manager for a long running user command."
                        ::= { fkRouteControl 3 }

                
                -- 1.3.6.1.4.1.10428 9 1.101.11.4.2.4
                fkRouteControlTimeStamp OBJECT-TYPE
                        SYNTAX FkControlRequestResultType
                        MAX-ACCESS read-only
                        STATUS current
                        DESCRIPTION
                                "The result of the last user command."
                        ::= { fkRouteControl 4 }

                
                -- 1.3.6.1.4.1.10428 9 1.101.11.4.2.5
                fkRouteControlReqResult OBJECT-TYPE
                        SYNTAX TimeTicks
                        MAX-ACCESS read-only
                        STATUS current
                        DESCRIPTION
                                "The time stamp of the last command (end of command)."
                        ::= { fkRouteControl 5 }

                
                -- 1.3.6.1.4.1.10428 9 1.101.11.4.2.6
                fkRouteControlDstAddress OBJECT-TYPE
                        SYNTAX IpAddress
                        MAX-ACCESS read-write
                        STATUS current
                        DESCRIPTION
                                "The destination IP address of this route. 
                                An entry with a value of 0.0.0.0 is considered a default route. 
                                Multiple routes to a single destination can appear in the table, 
                                but access to such multiple entries is dependent on the table-access mechanisms defined by the network management protocol in use."
                        ::= { fkRouteControl 6 }

                
                -- 1.3.6.1.4.1.10428 9 1.101.11.4.2.7
                fkRouteControlDstMask OBJECT-TYPE
                        SYNTAX INTEGER (0..32)
                        MAX-ACCESS read-write
                        STATUS current
                        DESCRIPTION
                                "Indicate the mask to be logical-ANDed with the destination address 
                                before being compared to the value in the fkRouteDstAddress field. 
                                For those systems that do not support arbitrary subnet masks, 
                                an agent constructs the value of the fkRouteDstMask 
                                by determining whether the value of the correspondent fkRouteDstAddress field 
                                belong to a class-A, B, or C network. 
                                If the value of the fkRouteDstAddress is 0.0.0.0 (a default route), 
                                then the mask value is also 0.0.0.0. It should be noted that all IP routing subsystems implicitly use this mechanism."
                        ::= { fkRouteControl 7 }

                
                -- 1.3.6.1.4.1.10428 9 1.101.11.4.2.8
                fkRouteControlGateway OBJECT-TYPE
                        SYNTAX IpAddress
                        MAX-ACCESS read-write
                        STATUS current
                        DESCRIPTION
                                "The Gateway IP Address.
                                0.0.0.0/0 : indicate default gateway or invalid"
                        ::= { fkRouteControl 8 }

                
                -- 1.3.6.1.4.1.10428 9 1.101.11.4.2.9
                fkRouteControlInterface OBJECT-TYPE
                        SYNTAX INTEGER (0..11023)
                        MAX-ACCESS read-write
                        STATUS current
                        DESCRIPTION
                                "Network interface index
                                0: invalid
                                1..4094: VLAN
                                4095: management
                                4096: loopback
                                4097: NULL device
                                10000..11023: Tunnel interface index
                                To config interface, fkRouteControlGateway have to be removed."
                        ::= { fkRouteControl 9 }

                
                -- 1.3.6.1.4.1.10428 9 1.101.11.4.2.10
                fkRouteControlBindingSrcAddr OBJECT-TYPE
                        SYNTAX IpAddress
                        MAX-ACCESS read-write
                        STATUS current
                        DESCRIPTION
                                "The binding source IP Address for this route."
                        ::= { fkRouteControl 10 }

                
                -- 1.3.6.1.4.1.10428 9 1.101.11.4.2.11
                fkRouteControlDistance OBJECT-TYPE
                        SYNTAX INTEGER (1..255)
                        MAX-ACCESS read-write
                        STATUS current
                        DESCRIPTION
                                "The Distance value for this route."
                        DEFVAL { 1 }
                        ::= { fkRouteControl 11 }

                
                -- 1.3.6.1.4.1.10428 9 1.101.11.4.2.12
                fkRouteControlVRFIndex OBJECT-TYPE
                        SYNTAX Integer32 (0..2147483647)
                        MAX-ACCESS read-write
                        STATUS current
                        DESCRIPTION
                                "VRF index in fkIpVRFTable."
                        ::= { fkRouteControl 12 }

                
                -- 1.3.6.1.4.1.10428 9 1.101.11.4.3
                fkRouteNotification OBJECT IDENTIFIER ::= { fkRoute 3 }

                
                -- 1.3.6.1.4.1.10428 9 1.101.11.4.3.1
                fkRouteStaticCreated NOTIFICATION-TYPE
                        OBJECTS { fkRouteControlRequest, fkRouteControlTimeStamp, fkRouteControlReqResult, fkRouteControlDstAddress, fkRouteControlDstMask, 
                                fkRouteControlGateway, fkRouteControlInterface, fkRouteControlBindingSrcAddr, fkRouteControlDistance, fkRouteControlVRFIndex
                                 }
                        STATUS current
                        DESCRIPTION 
                                "createStaticRoute"
                        ::= { fkRouteNotification 1 }

                
                -- 1.3.6.1.4.1.10428 9 1.101.11.4.3.2
                fkRouteStaticDestroyed NOTIFICATION-TYPE
                        OBJECTS { fkRouteControlRequest, fkRouteControlTimeStamp, fkRouteControlReqResult, fkRouteControlDstAddress, fkRouteControlDstMask, 
                                fkRouteControlGateway, fkRouteControlInterface, fkRouteControlVRFIndex }
                        STATUS current
                        DESCRIPTION 
                                "destroyStaticRoute"
                        ::= { fkRouteNotification 2 }

                
                -- 1.3.6.1.4.1.10428 9 1.101.11.4.3.3
                fkRouteStaticProfileChanged NOTIFICATION-TYPE
                        OBJECTS { fkRouteControlRequest, fkRouteControlTimeStamp, fkRouteControlReqResult, fkRouteControlDstAddress, fkRouteControlDstMask, 
                                fkRouteControlGateway, fkRouteControlInterface, fkRouteControlBindingSrcAddr, fkRouteControlDistance, fkRouteControlVRFIndex
                                 }
                        STATUS current
                        DESCRIPTION 
                                "setStaticRouteProfile"
                        ::= { fkRouteNotification 3 }

                
                -- 1.3.6.1.4.1.10428 9 1.101.11.5
                fkDhcpClient OBJECT IDENTIFIER ::= { fkNetwork 5 }

                
                -- 1.3.6.1.4.1.10428 9 1.101.11.5.1
                fkDhcpClTable OBJECT-TYPE
                        SYNTAX SEQUENCE OF FkDhcpClEntry
                        MAX-ACCESS not-accessible
                        STATUS current
                        DESCRIPTION
                                "Description."
                        ::= { fkDhcpClient 1 }

                
                -- 1.3.6.1.4.1.10428 9 1.101.11.5.1.1
                fkDhcpClEntry OBJECT-TYPE
                        SYNTAX FkDhcpClEntry
                        MAX-ACCESS not-accessible
                        STATUS current
                        DESCRIPTION
                                "Description."
                        INDEX { fkNetIfIndex }
                        ::= { fkDhcpClTable 1 }

                
                FkDhcpClEntry ::=
                        SEQUENCE { 
                                fkDhcpClMode
                                        INTEGER,
                                fkDhcpClIpAddr
                                        IpAddress,
                                fkDhcpClNetmask
                                        IpAddress,
                                fkDhcpClGateway
                                        IpAddress,
                                fkDhcpClDnsServer
                                        IpAddress,
                                fkDhcpClServer
                                        IpAddress,
                                fkDhcpClClientId
                                        OCTET STRING,
                                fkDhcpClClientIdStyle
                                        INTEGER,
                                fkDhcpClClassId
                                        OCTET STRING,
                                fkDhcpClClassIdStyle
                                        INTEGER,
                                fkDhcpClLeasetime
                                        Integer32,
                                fkDhcpClState
                                        INTEGER
                         }

                -- 1.3.6.1.4.1.10428 9 1.101.11.5.1.1.1
                fkDhcpClMode OBJECT-TYPE
                        SYNTAX INTEGER
                                {
                                disable(0),
                                enable(1)
                                }
                        MAX-ACCESS read-only
                        STATUS current
                        DESCRIPTION
                                "DHCP Client activity state in this interface."
                        DEFVAL { disable }
                        ::= { fkDhcpClEntry 1 }

                
                -- 1.3.6.1.4.1.10428 9 1.101.11.5.1.1.2
                fkDhcpClIpAddr OBJECT-TYPE
                        SYNTAX IpAddress
                        MAX-ACCESS read-only
                        STATUS current
                        DESCRIPTION
                                "The IP address acquired by DHCP Client active in this interface."
                        ::= { fkDhcpClEntry 2 }

                
                -- 1.3.6.1.4.1.10428 9 1.101.11.5.1.1.3
                fkDhcpClNetmask OBJECT-TYPE
                        SYNTAX IpAddress
                        MAX-ACCESS read-only
                        STATUS current
                        DESCRIPTION
                                "The subnet mask associated with the IP address acquired by DHCP Client.  
                                The value of the mask is an IP address with all the network 
                                bits set to 1 and all the hosts bits set to 0."
                        ::= { fkDhcpClEntry 3 }

                
                -- 1.3.6.1.4.1.10428 9 1.101.11.5.1.1.4
                fkDhcpClGateway OBJECT-TYPE
                        SYNTAX IpAddress
                        MAX-ACCESS read-only
                        STATUS current
                        DESCRIPTION
                                "The Gateway's IP address acquired by DHCP Client active in this interface."
                        ::= { fkDhcpClEntry 4 }

                
                -- 1.3.6.1.4.1.10428 9 1.101.11.5.1.1.5
                fkDhcpClDnsServer OBJECT-TYPE
                        SYNTAX IpAddress
                        MAX-ACCESS read-only
                        STATUS current
                        DESCRIPTION
                                "The DNS server's IP address acquired by DHCP Client active in this interface."
                        ::= { fkDhcpClEntry 5 }

                
                -- 1.3.6.1.4.1.10428 9 1.101.11.5.1.1.6
                fkDhcpClServer OBJECT-TYPE
                        SYNTAX IpAddress
                        MAX-ACCESS read-only
                        STATUS current
                        DESCRIPTION
                                "DHCP Server's IP address."
                        ::= { fkDhcpClEntry 6 }

                
                -- 1.3.6.1.4.1.10428 9 1.101.11.5.1.1.7
                fkDhcpClClientId OBJECT-TYPE
                        SYNTAX OCTET STRING (SIZE (0..255))
                        MAX-ACCESS read-only
                        STATUS current
                        DESCRIPTION
                                "DHCP Client-identifier value.
                                This is used by DHCP clients to specify their unique identifier.
                                DHCP servers use this value to index their database of address bindings.
                                This value is expected to be unique for all clients in an administrative domain."
                        ::= { fkDhcpClEntry 7 }

                
                -- 1.3.6.1.4.1.10428 9 1.101.11.5.1.1.8
                fkDhcpClClientIdStyle OBJECT-TYPE
                        SYNTAX INTEGER
                                {
                                ascii(0),
                                hex(1)
                                }
                        MAX-ACCESS read-only
                        STATUS current
                        DESCRIPTION
                                "DHCP Client-identifier input style.
                                0 : ascii string format
                                1 : hexadecimal format"
                        DEFVAL { ascii }
                        ::= { fkDhcpClEntry 8 }

                
                -- 1.3.6.1.4.1.10428 9 1.101.11.5.1.1.9
                fkDhcpClClassId OBJECT-TYPE
                        SYNTAX OCTET STRING (SIZE (0..256))
                        MAX-ACCESS read-only
                        STATUS current
                        DESCRIPTION
                                "DHCP Class identifier value.
                                This is used by DHCP clients to optionally identify the vendor 
                                type and configuration of a DHCP client.
                                The information is a string of n octets, interpreted by servers.
                                Vendors may choose to define specific vendor class identifiers 
                                to convey particular configuration or other identification 
                                information about a client.
                                For example, the identifier may encode the client's hardware configuration."
                        ::= { fkDhcpClEntry 9 }

                
                -- 1.3.6.1.4.1.10428 9 1.101.11.5.1.1.10
                fkDhcpClClassIdStyle OBJECT-TYPE
                        SYNTAX INTEGER
                                {
                                ascii(0),
                                hex(1)
                                }
                        MAX-ACCESS read-only
                        STATUS current
                        DESCRIPTION
                                "DHCP Class identifier input style.
                                0 : ascii string format
                                1 : hexadecimal format"
                        DEFVAL { ascii }
                        ::= { fkDhcpClEntry 10 }

                
                -- 1.3.6.1.4.1.10428 9 1.101.11.5.1.1.11
                fkDhcpClLeasetime OBJECT-TYPE
                        SYNTAX Integer32 (120..2147483637)
                        MAX-ACCESS read-only
                        STATUS current
                        DESCRIPTION
                                "The leased time for IP address acquired by DHCP Client.
                                 Default lease-time: 3600s"
                        DEFVAL { 3600 }
                        ::= { fkDhcpClEntry 11 }

                
                -- 1.3.6.1.4.1.10428 9 1.101.11.5.1.1.12
                fkDhcpClState OBJECT-TYPE
                        SYNTAX INTEGER
                                {
                                halt(0),
                                init(1),
                                request(3),
                                bound(4),
                                renew(5),
                                rebind(6),
                                nonactive(255)
                                }
                        MAX-ACCESS read-only
                        STATUS current
                        DESCRIPTION
                                "The operating status of DHCP Client."
                        DEFVAL { non-active }
                        ::= { fkDhcpClEntry 12 }

                
                -- 1.3.6.1.4.1.10428 9 1.101.11.5.2
                fkDhcpClControl OBJECT IDENTIFIER ::= { fkDhcpClient 2 }

                
                -- 1.3.6.1.4.1.10428 9 1.101.11.5.2.1
                fkDhcpClControlRequest OBJECT-TYPE
                        SYNTAX INTEGER
                                {
                                setDhcpClMode(1),
                                setDhcpClProfile(2),
                                changeDhcpClState(3)
                                }
                        MAX-ACCESS read-write
                        STATUS current
                        DESCRIPTION
                                "The request of a user command."
                        ::= { fkDhcpClControl 1 }

                
                -- 1.3.6.1.4.1.10428 9 1.101.11.5.2.2
                fkDhcpClControlStatus OBJECT-TYPE
                        SYNTAX FkControlStatusType
                        MAX-ACCESS read-only
                        STATUS current
                        DESCRIPTION
                                "The status of a user command."
                        ::= { fkDhcpClControl 2 }

                
                -- 1.3.6.1.4.1.10428 9 1.101.11.5.2.3
                fkDhcpClControlTimer OBJECT-TYPE
                        SYNTAX Gauge32
                        MAX-ACCESS read-write
                        STATUS current
                        DESCRIPTION
                                "The maximum wait time for the manager for a long running user command."
                        ::= { fkDhcpClControl 3 }

                
                -- 1.3.6.1.4.1.10428 9 1.101.11.5.2.4
                fkDhcpClControlTimeStamp OBJECT-TYPE
                        SYNTAX FkControlRequestResultType
                        MAX-ACCESS read-only
                        STATUS current
                        DESCRIPTION
                                "The time stamp of the last command (end of command)."
                        ::= { fkDhcpClControl 4 }

                
                -- 1.3.6.1.4.1.10428 9 1.101.11.5.2.5
                fkDhcpClControlReqResult OBJECT-TYPE
                        SYNTAX TimeTicks
                        MAX-ACCESS read-only
                        STATUS current
                        DESCRIPTION
                                "The result of the last user command."
                        ::= { fkDhcpClControl 5 }

                
                -- 1.3.6.1.4.1.10428 9 1.101.11.5.2.6
                fkDhcpClControlNetIfIndex OBJECT-TYPE
                        SYNTAX Integer32 (1..4094)
                        MAX-ACCESS read-write
                        STATUS current
                        DESCRIPTION
                                "Network Interface Index."
                        DEFVAL { 1 }
                        ::= { fkDhcpClControl 6 }

                
                -- 1.3.6.1.4.1.10428 9 1.101.11.5.2.7
                fkDhcpClControlMode OBJECT-TYPE
                        SYNTAX INTEGER
                                {
                                disable(0),
                                enable(1)
                                }
                        MAX-ACCESS read-write
                        STATUS current
                        DESCRIPTION
                                "DHCP Client activity state in this interface."
                        DEFVAL { disable }
                        ::= { fkDhcpClControl 7 }

                
                -- 1.3.6.1.4.1.10428 9 1.101.11.5.2.8
                fkDhcpClControlClientId OBJECT-TYPE
                        SYNTAX OCTET STRING (SIZE (0..255))
                        MAX-ACCESS read-write
                        STATUS current
                        DESCRIPTION
                                "DHCP Client-identifier value.
                                This is used by DHCP clients to specify their unique identifier.
                                DHCP servers use this value to index their database of address bindings.
                                This value is expected to be unique for all clients in an administrative domain."
                        ::= { fkDhcpClControl 8 }

                
                -- 1.3.6.1.4.1.10428 9 1.101.11.5.2.9
                fkDhcpClControlClientIdStyle OBJECT-TYPE
                        SYNTAX INTEGER
                                {
                                ascii(0),
                                hex(1)
                                }
                        MAX-ACCESS read-write
                        STATUS current
                        DESCRIPTION
                                "DHCP Client-identifier input style.
                                0 : ascii string format
                                1 : hexadecimal format"
                        DEFVAL { ascii }
                        ::= { fkDhcpClControl 9 }

                
                -- 1.3.6.1.4.1.10428 9 1.101.11.5.2.10
                fkDhcpClControlClassId OBJECT-TYPE
                        SYNTAX OCTET STRING (SIZE (0..255))
                        MAX-ACCESS read-write
                        STATUS current
                        DESCRIPTION
                                "DHCP Class identifier value.
                                This is used by DHCP clients to optionally identify the vendor 
                                type and configuration of a DHCP client.
                                The information is a string of n octets, interpreted by servers.
                                Vendors may choose to define specific vendor class identifiers 
                                to convey particular configuration or other identification 
                                information about a client.
                                For example, the identifier may encode the client's hardware configuration."
                        ::= { fkDhcpClControl 10 }

                
                -- 1.3.6.1.4.1.10428 9 1.101.11.5.2.11
                fkDhcpClControlClassIdStyle OBJECT-TYPE
                        SYNTAX INTEGER
                                {
                                ascii(0),
                                hex(1)
                                }
                        MAX-ACCESS read-write
                        STATUS current
                        DESCRIPTION
                                "DHCP Class identifier input style.
                                0 : ascii string format
                                1 : hexadecimal format"
                        DEFVAL { ascii }
                        ::= { fkDhcpClControl 11 }

                
                -- 1.3.6.1.4.1.10428 9 1.101.11.5.2.12
                fkDhcpClControlLeasetime OBJECT-TYPE
                        SYNTAX Integer32 (120..2147483637)
                        MAX-ACCESS read-write
                        STATUS current
                        DESCRIPTION
                                "The leased time for IP address acquired by DHCP Client.
                                 Default lease-time: 3600s"
                        DEFVAL { 3600 }
                        ::= { fkDhcpClControl 12 }

                
                -- 1.3.6.1.4.1.10428 9 1.101.11.5.2.13
                fkDhcpClControlUpdateIP OBJECT-TYPE
                        SYNTAX INTEGER
                                {
                                remain(0),
                                renew(1),
                                release(2)
                                }
                        MAX-ACCESS read-write
                        STATUS current
                        DESCRIPTION
                                "Update DHCP client operating status.
                                0 : default
                                1 : renew
                                2 : release
                                "
                        DEFVAL { remain }
                        ::= { fkDhcpClControl 13 }

                
                -- 1.3.6.1.4.1.10428 9 1.101.11.5.3
                fkDhcpClNotification OBJECT IDENTIFIER ::= { fkDhcpClient 3 }

                
                -- 1.3.6.1.4.1.10428 9 1.101.11.5.3.1
                fkDhcpClModeChanged NOTIFICATION-TYPE
                        OBJECTS { fkDhcpClControlRequest, fkDhcpClControlTimeStamp, fkDhcpClControlReqResult, fkDhcpClMode }
                        STATUS current
                        DESCRIPTION 
                                "setDhcpClMode."
                        ::= { fkDhcpClNotification 1 }

                
                -- 1.3.6.1.4.1.10428 9 1.101.11.5.3.2
                fkDhcpClProfileChanged NOTIFICATION-TYPE
                        OBJECTS { fkDhcpClControlRequest, fkDhcpClControlTimeStamp, fkDhcpClControlReqResult, fkDhcpClClientId, fkDhcpClClientIdStyle, 
                                fkDhcpClClassId, fkDhcpClClassIdStyle, fkDhcpClLeasetime }
                        STATUS current
                        DESCRIPTION 
                                "setDhcpClProfile."
                        ::= { fkDhcpClNotification 2 }

                
                -- 1.3.6.1.4.1.10428 9 1.101.11.5.3.3
                fkDhcpClStateChanged NOTIFICATION-TYPE
                        OBJECTS { fkDhcpClControlRequest, fkDhcpClControlTimeStamp, fkDhcpClControlReqResult, fkDhcpClState }
                        STATUS current
                        DESCRIPTION 
                                "ChangeDhcpClState."
                        ::= { fkDhcpClNotification 3 }

                
                -- 1.3.6.1.4.1.10428 9 1.101.11.6
                fkV2DhcpClient OBJECT IDENTIFIER ::= { fkNetwork 6 }

                
                -- 1.3.6.1.4.1.10428 9 1.101.11.7
                fkNetworkBase OBJECT IDENTIFIER ::= { fkNetwork 7 }

                
                -- 1.3.6.1.4.1.10428 9 1.101.11.7.1
                fkNetworkBaseInfo OBJECT IDENTIFIER ::= { fkNetworkBase 1 }

                
                -- 1.3.6.1.4.1.10428 9 1.101.11.7.1.1
                fkNetworkArpAgingTime OBJECT-TYPE
                        SYNTAX INTEGER (10..2147483637)
                        MAX-ACCESS read-only
                        STATUS current
                        DESCRIPTION
                                "System Arp Aging Time"
                        ::= { fkNetworkBaseInfo 1 }

                
                -- 1.3.6.1.4.1.10428 9 1.101.11.7.2
                fkNetworkBaseControl OBJECT IDENTIFIER ::= { fkNetworkBase 2 }

                
                -- 1.3.6.1.4.1.10428 9 1.101.11.7.2.1
                fkNetworkControlRequest OBJECT-TYPE
                        SYNTAX INTEGER { setArpProfile(1) }
                        MAX-ACCESS read-write
                        STATUS current
                        DESCRIPTION
                                "Description."
                        ::= { fkNetworkBaseControl 1 }

                
                -- 1.3.6.1.4.1.10428 9 1.101.11.7.2.2
                fkNetworkControlStatus OBJECT-TYPE
                        SYNTAX FkControlStatusType
                        MAX-ACCESS read-only
                        STATUS current
                        DESCRIPTION
                                "Description."
                        ::= { fkNetworkBaseControl 2 }

                
                -- 1.3.6.1.4.1.10428 9 1.101.11.7.2.3
                fkNetworkControlTimer OBJECT-TYPE
                        SYNTAX Gauge32
                        MAX-ACCESS read-write
                        STATUS current
                        DESCRIPTION
                                "Description."
                        ::= { fkNetworkBaseControl 3 }

                
                -- 1.3.6.1.4.1.10428 9 1.101.11.7.2.4
                fkNetworkControlTimeStamp OBJECT-TYPE
                        SYNTAX TimeTicks
                        MAX-ACCESS read-only
                        STATUS current
                        DESCRIPTION
                                "Description."
                        ::= { fkNetworkBaseControl 4 }

                
                -- 1.3.6.1.4.1.10428 9 1.101.11.7.2.5
                fkNetworkControlReqResult OBJECT-TYPE
                        SYNTAX FkControlRequestResultType
                        MAX-ACCESS read-only
                        STATUS current
                        DESCRIPTION
                                "Description."
                        ::= { fkNetworkBaseControl 5 }

                
                -- 1.3.6.1.4.1.10428 9 1.101.11.7.2.6
                fkNetworkControlArpAgingTime OBJECT-TYPE
                        SYNTAX INTEGER (10..2147483637)
                        MAX-ACCESS read-write
                        STATUS current
                        DESCRIPTION
                                "Description."
                        ::= { fkNetworkBaseControl 6 }

                
                -- 1.3.6.1.4.1.10428 9 1.101.11.7.3
                fkNetworkBaseNotification OBJECT IDENTIFIER ::= { fkNetworkBase 3 }

                
                -- 1.3.6.1.4.1.10428 9 1.101.11.7.3.1
                fkNetworkArpProfileChanged NOTIFICATION-TYPE
                        OBJECTS { fkNetworkControlRequest, fkNetworkControlReqResult, fkNetworkControlTimeStamp, fkNetworkArpAgingTime }
                        STATUS current
                        DESCRIPTION 
                                "Description."
                        ::= { fkNetworkBaseNotification 1 }

                
                -- 1.3.6.1.4.1.10428 9 1.101.11.8
                fkTunnel OBJECT IDENTIFIER ::= { fkNetwork 8 }

                
                -- 1.3.6.1.4.1.10428 9 1.101.11.8.1
                fkTunnelIfTable OBJECT-TYPE
                        SYNTAX SEQUENCE OF FkTunnelIfEntry
                        MAX-ACCESS not-accessible
                        STATUS current
                        DESCRIPTION
                                "Description."
                        ::= { fkTunnel 1 }

                
                -- 1.3.6.1.4.1.10428 9 1.101.11.8.1.1
                fkTunnelIfEntry OBJECT-TYPE
                        SYNTAX FkTunnelIfEntry
                        MAX-ACCESS not-accessible
                        STATUS current
                        DESCRIPTION
                                "Description."
                        INDEX { fkTunnelIfIndex }
                        ::= { fkTunnelIfTable 1 }

                
                FkTunnelIfEntry ::=
                        SEQUENCE { 
                                fkTunnelIfIndex
                                        Integer32,
                                fkTunnelIfLocalAddress
                                        IpAddress,
                                fkTunnelIfRemoteAddress
                                        IpAddress,
                                fkTunnelIfMode
                                        IANAtunnelType,
                                fkTunnelIfTTL
                                        Integer32,
                                fkTunnelIfDscpMode
                                        INTEGER,
                                fkTunnelIfDscp
                                        Integer32,
                                fkTunnelIfKeepaliveInterval
                                        Integer32,
                                fkTunnelIfKeepaliveRetry
                                        Integer32,
                                fkTunnelIfPathMtuDiscovery
                                        INTEGER,
                                fkTunnelIfVRFName
                                        OCTET STRING,
                                fkTunnelIfBindingPorts
                                        OCTET STRING
                         }

                -- 1.3.6.1.4.1.10428 9 1.101.11.8.1.1.1
                fkTunnelIfIndex OBJECT-TYPE
                        SYNTAX Integer32 (10000..11023)
                        MAX-ACCESS read-only
                        STATUS current
                        DESCRIPTION
                                "Tunnel interface index"
                        ::= { fkTunnelIfEntry 1 }

                
                -- 1.3.6.1.4.1.10428 9 1.101.11.8.1.1.2
                fkTunnelIfLocalAddress OBJECT-TYPE
                        SYNTAX IpAddress
                        MAX-ACCESS read-only
                        STATUS current
                        DESCRIPTION
                                "The address of the local endpoint of the tunnel (i.e., the source address used in the outer IP header), or 0.0.0.0 if unknown."
                        ::= { fkTunnelIfEntry 2 }

                
                -- 1.3.6.1.4.1.10428 9 1.101.11.8.1.1.3
                fkTunnelIfRemoteAddress OBJECT-TYPE
                        SYNTAX IpAddress
                        MAX-ACCESS read-only
                        STATUS current
                        DESCRIPTION
                                "The address of the remote endpoint of the tunnel (i.e., the destination address used in the outer IP header), or 0.0.0.0 if unknown."
                        ::= { fkTunnelIfEntry 3 }

                
                -- 1.3.6.1.4.1.10428 9 1.101.11.8.1.1.4
                fkTunnelIfMode OBJECT-TYPE
                        SYNTAX IANAtunnelType
                        MAX-ACCESS read-only
                        STATUS current
                        DESCRIPTION
                                "The encapsulation method used by the tunnel.
                                
                                other(1) - none of the following
                                direct(2) - intermediate header
                                gre(3) - GRE encapsulation
                                minimal(4) - Minimal encapsulation
                                l2tp(5) - L2TP encapsulation
                                pptp(6)  - PPTP encapsulation
                                l2f(7) - L2F encapsulation
                                udp(8) - UDP encapsulation
                                atmp(9) - ATMP encapsulation
                                msdp(10) - MSDP encapsulation
                                sixToFour(11) - 6to4 encapsulation
                                sixOverFour(12) - 6over4 encapsulation
                                isatap(13) - ISATAP encapsulation
                                teredo(14)  - Teredo encapsulation
                                "
                        ::= { fkTunnelIfEntry 4 }

                
                -- 1.3.6.1.4.1.10428 9 1.101.11.8.1.1.5
                fkTunnelIfTTL OBJECT-TYPE
                        SYNTAX Integer32 (1..255)
                        MAX-ACCESS read-only
                        STATUS current
                        DESCRIPTION
                                "The TTL to use in the outer IP header."
                        ::= { fkTunnelIfEntry 5 }

                
                -- 1.3.6.1.4.1.10428 9 1.101.11.8.1.1.6
                fkTunnelIfDscpMode OBJECT-TYPE
                        SYNTAX INTEGER
                                {
                                dscpAssign(1),
                                dscpCopyFromPacket(2),
                                dscpMapFromPacket(3)
                                }
                        MAX-ACCESS read-only
                        STATUS current
                        DESCRIPTION
                                "The DiffServ field mode to use in the outer IP header.
                                A value of dscpCopyFromPacket indicates that the bits are copied from the payload's header. A value of dscpMapFromPacket indicates that the bit field is mapping dscp field of incoming packet.  A value of dscpAssign indicates that the bit field is static DiffServ field value.
                                "
                        ::= { fkTunnelIfEntry 6 }

                
                -- 1.3.6.1.4.1.10428 9 1.101.11.8.1.1.7
                fkTunnelIfDscp OBJECT-TYPE
                        SYNTAX Integer32 (0..63)
                        MAX-ACCESS read-only
                        STATUS current
                        DESCRIPTION
                                "The static DiffServ field value to use in the outer IP header."
                        ::= { fkTunnelIfEntry 7 }

                
                -- 1.3.6.1.4.1.10428 9 1.101.11.8.1.1.8
                fkTunnelIfKeepaliveInterval OBJECT-TYPE
                        SYNTAX Integer32 (0..32767)
                        MAX-ACCESS read-only
                        STATUS current
                        DESCRIPTION
                                "Specifies the time interval, in seconds, at which keepalive packets are sent. (This object is available for a gre tunnel only.)"
                        ::= { fkTunnelIfEntry 8 }

                
                -- 1.3.6.1.4.1.10428 9 1.101.11.8.1.1.9
                fkTunnelIfKeepaliveRetry OBJECT-TYPE
                        SYNTAX Integer32 (1..255)
                        MAX-ACCESS read-only
                        STATUS current
                        DESCRIPTION
                                "Specifies the number times that the device will continue to send keepalive packets without response before bringing the tunnel interface protocol down. (This object is available for a gre tunnel only.)"
                        ::= { fkTunnelIfEntry 9 }

                
                -- 1.3.6.1.4.1.10428 9 1.101.11.8.1.1.10
                fkTunnelIfPathMtuDiscovery OBJECT-TYPE
                        SYNTAX INTEGER
                                {
                                enable(1),
                                disable(2)
                                }
                        MAX-ACCESS read-only
                        STATUS current
                        DESCRIPTION
                                "Path mtu discovery on tunnel."
                        ::= { fkTunnelIfEntry 10 }

                
                -- 1.3.6.1.4.1.10428 9 1.101.11.8.1.1.11
                fkTunnelIfVRFName OBJECT-TYPE
                        SYNTAX OCTET STRING (SIZE (0..63))
                        MAX-ACCESS read-only
                        STATUS current
                        DESCRIPTION
                                "VPN Routing/Forwarding instance name."
                        ::= { fkTunnelIfEntry 11 }

                
                -- 1.3.6.1.4.1.10428 9 1.101.11.8.1.1.12
                fkTunnelIfBindingPorts OBJECT-TYPE
                        SYNTAX OCTET STRING
                        MAX-ACCESS read-only
                        STATUS current
                        DESCRIPTION
                                "Tunnel binding ports map."
                        ::= { fkTunnelIfEntry 12 }

                
                -- 1.3.6.1.4.1.10428 9 1.101.11.8.2
                fkTunnelIfControl OBJECT IDENTIFIER ::= { fkTunnel 2 }

                
                -- 1.3.6.1.4.1.10428 9 1.101.11.8.2.1
                fkTunnelIfControlRequest OBJECT-TYPE
                        SYNTAX INTEGER
                                {
                                createTunnelInterface(1),
                                deleteTunnelInterface(2),
                                setTunnelIfLocalAddress(3),
                                setTunnelIfRemoteAddress(4),
                                setTunnelIfMode(5),
                                setTunnelIfTTL(6),
                                setTunnelIfDscp(7),
                                setTunnelIfKeepalive(8),
                                setTunnelIfPathMtuDiscovery(9),
                                setTunnelIfVRFName(10),
                                unsetTunnelIfVRFName(11)
                                }
                        MAX-ACCESS read-write
                        STATUS current
                        DESCRIPTION
                                "The request of a user command."
                        ::= { fkTunnelIfControl 1 }

                
                -- 1.3.6.1.4.1.10428 9 1.101.11.8.2.2
                fkTunnelIfControlStatus OBJECT-TYPE
                        SYNTAX FkControlStatusType
                        MAX-ACCESS read-only
                        STATUS current
                        DESCRIPTION
                                "The status of a user command."
                        ::= { fkTunnelIfControl 2 }

                
                -- 1.3.6.1.4.1.10428 9 1.101.11.8.2.3
                fkTunnelIfControlTimer OBJECT-TYPE
                        SYNTAX Gauge32
                        MAX-ACCESS read-write
                        STATUS current
                        DESCRIPTION
                                "The maximum wait time for the manager for a long running user command."
                        ::= { fkTunnelIfControl 3 }

                
                -- 1.3.6.1.4.1.10428 9 1.101.11.8.2.4
                fkTunnelIfControlTimeStamp OBJECT-TYPE
                        SYNTAX FkControlRequestResultType
                        MAX-ACCESS read-only
                        STATUS current
                        DESCRIPTION
                                "The result of the last user command."
                        ::= { fkTunnelIfControl 4 }

                
                -- 1.3.6.1.4.1.10428 9 1.101.11.8.2.5
                fkTunnelIfControlReqResult OBJECT-TYPE
                        SYNTAX TimeTicks
                        MAX-ACCESS read-only
                        STATUS current
                        DESCRIPTION
                                "The time stamp of the last command (end of command)."
                        ::= { fkTunnelIfControl 5 }

                
                -- 1.3.6.1.4.1.10428 9 1.101.11.8.2.6
                fkTunnelIfControlIndex OBJECT-TYPE
                        SYNTAX Integer32 (10000..11023)
                        MAX-ACCESS read-write
                        STATUS current
                        DESCRIPTION
                                "Tunnel interface index"
                        ::= { fkTunnelIfControl 6 }

                
                -- 1.3.6.1.4.1.10428 9 1.101.11.8.2.7
                fkTunnelIfControlLocalAddress OBJECT-TYPE
                        SYNTAX IpAddress
                        MAX-ACCESS read-write
                        STATUS current
                        DESCRIPTION
                                "The address of the local endpoint of the tunnel (i.e., the source address used in the outer IP header), or 0.0.0.0 if unknown."
                        ::= { fkTunnelIfControl 7 }

                
                -- 1.3.6.1.4.1.10428 9 1.101.11.8.2.8
                fkTunnelIfControlRemoteAddress OBJECT-TYPE
                        SYNTAX IpAddress
                        MAX-ACCESS read-write
                        STATUS current
                        DESCRIPTION
                                "The address of the remote endpoint of the tunnel (i.e., the destination address used in the outer IP header), or 0.0.0.0 if unknown."
                        ::= { fkTunnelIfControl 8 }

                
                -- 1.3.6.1.4.1.10428 9 1.101.11.8.2.9
                fkTunnelIfControlMode OBJECT-TYPE
                        SYNTAX IANAtunnelType
                        MAX-ACCESS read-write
                        STATUS current
                        DESCRIPTION
                                "The encapsulation method used by the tunnel.
                                
                                other(1) - none of the following
                                direct(2) - intermediate header
                                gre(3) - GRE encapsulation
                                minimal(4) - Minimal encapsulation
                                l2tp(5) - L2TP encapsulation
                                pptp(6)  - PPTP encapsulation
                                l2f(7) - L2F encapsulation
                                udp(8) - UDP encapsulation
                                atmp(9) - ATMP encapsulation
                                msdp(10) - MSDP encapsulation
                                sixToFour(11) - 6to4 encapsulation
                                sixOverFour(12) - 6over4 encapsulation
                                isatap(13) - ISATAP encapsulation
                                teredo(14)  - Teredo encapsulation
                                "
                        ::= { fkTunnelIfControl 9 }

                
                -- 1.3.6.1.4.1.10428 9 1.101.11.8.2.10
                fkTunnelIfControlTTL OBJECT-TYPE
                        SYNTAX Integer32 (1..255)
                        MAX-ACCESS read-write
                        STATUS current
                        DESCRIPTION
                                "The TTL to use in the outer IP header."
                        ::= { fkTunnelIfControl 10 }

                
                -- 1.3.6.1.4.1.10428 9 1.101.11.8.2.11
                fkTunneIflControlDscpMode OBJECT-TYPE
                        SYNTAX INTEGER
                                {
                                dscpAssign(1),
                                dscpCopyFromPacket(2),
                                dscpMapFromPacket(3)
                                }
                        MAX-ACCESS read-write
                        STATUS current
                        DESCRIPTION
                                "The DiffServ field mode to use in the outer IP header.
                                A value of dscpCopyFromPacket indicates that the bits are copied from the payload's header. A value of dscpMapFromPacket indicates that the bit field is mapping dscp field of incoming packet.  A value of dscpAssign indicates that the bit field is static DiffServ field value.
                                "
                        DEFVAL { dscpCopyFromPacket }
                        ::= { fkTunnelIfControl 11 }

                
                -- 1.3.6.1.4.1.10428 9 1.101.11.8.2.12
                fkTunneIflControlDscp OBJECT-TYPE
                        SYNTAX Integer32 (0..63)
                        MAX-ACCESS read-write
                        STATUS current
                        DESCRIPTION
                                "The static DiffServ field value to use in the outer IP header."
                        ::= { fkTunnelIfControl 12 }

                
                -- 1.3.6.1.4.1.10428 9 1.101.11.8.2.13
                fkTunnelIfControlKeepaliveInterval OBJECT-TYPE
                        SYNTAX Integer32 (1..32767)
                        MAX-ACCESS read-write
                        STATUS current
                        DESCRIPTION
                                "Specifies the time interval, in seconds, at which keepalive packets are sent. (This object is available for a gre tunnel only.)"
                        DEFVAL { 100 }
                        ::= { fkTunnelIfControl 13 }

                
                -- 1.3.6.1.4.1.10428 9 1.101.11.8.2.14
                fkTunneIflControlKeepaliveRetry OBJECT-TYPE
                        SYNTAX Integer32 (1..255)
                        MAX-ACCESS read-write
                        STATUS current
                        DESCRIPTION
                                "Specifies the number times that the device will continue to send keepalive packets without response before bringing the tunnel interface protocol down. (This object is available for a gre tunnel only.)"
                        DEFVAL { 3 }
                        ::= { fkTunnelIfControl 14 }

                
                -- 1.3.6.1.4.1.10428 9 1.101.11.8.2.15
                fkTunnelIfControlPathMtuDiscovery OBJECT-TYPE
                        SYNTAX INTEGER
                                {
                                enable(1),
                                disable(2)
                                }
                        MAX-ACCESS read-write
                        STATUS current
                        DESCRIPTION
                                " Path mtu discovery on tunnel."
                        ::= { fkTunnelIfControl 15 }

                
                -- 1.3.6.1.4.1.10428 9 1.101.11.8.2.16
                fkTunnelIfControlVRFName OBJECT-TYPE
                        SYNTAX OCTET STRING (SIZE (0..63))
                        MAX-ACCESS read-write
                        STATUS current
                        DESCRIPTION
                                "VPN Routing/Forwarding instance name."
                        ::= { fkTunnelIfControl 16 }

                
                -- 1.3.6.1.4.1.10428 9 1.101.11.8.3
                fkTunnelIfNotification OBJECT IDENTIFIER ::= { fkTunnel 3 }

                
                -- 1.3.6.1.4.1.10428 9 1.101.11.8.3.1
                fkTunnelIfCreated NOTIFICATION-TYPE
                        OBJECTS { fkTunnelIfControlRequest, fkTunnelIfControlTimeStamp, fkTunnelIfControlReqResult, fkTunnelIfControlIndex }
                        STATUS current
                        DESCRIPTION 
                                "Description."
                        ::= { fkTunnelIfNotification 1 }

                
                -- 1.3.6.1.4.1.10428 9 1.101.11.8.3.2
                fkTunnelIfDeleted NOTIFICATION-TYPE
                        OBJECTS { fkTunnelIfControlRequest, fkTunnelIfControlTimeStamp, fkTunnelIfControlReqResult, fkTunnelIfControlIndex }
                        STATUS current
                        DESCRIPTION 
                                "Description."
                        ::= { fkTunnelIfNotification 2 }

                
                -- 1.3.6.1.4.1.10428 9 1.101.11.8.3.3
                fkTunnelIfLocalAddressChanged NOTIFICATION-TYPE
                        OBJECTS { fkTunnelIfControlRequest, fkTunnelIfControlTimeStamp, fkTunnelIfControlReqResult, fkTunnelIfControlIndex, fkTunnelIfControlLocalAddress
                                 }
                        STATUS current
                        DESCRIPTION 
                                "Description."
                        ::= { fkTunnelIfNotification 3 }

                
                -- 1.3.6.1.4.1.10428 9 1.101.11.8.3.4
                fkTunnelIfRemoteAddressChanged NOTIFICATION-TYPE
                        OBJECTS { fkTunnelIfControlRequest, fkTunnelIfControlTimeStamp, fkTunnelIfControlReqResult, fkTunnelIfControlIndex, fkTunnelIfControlRemoteAddress
                                 }
                        STATUS current
                        DESCRIPTION 
                                "Description."
                        ::= { fkTunnelIfNotification 4 }

                
                -- 1.3.6.1.4.1.10428 9 1.101.11.8.3.5
                fkTunnelIfModeChanged NOTIFICATION-TYPE
                        OBJECTS { fkTunnelIfControlRequest, fkTunnelIfControlTimeStamp, fkTunnelIfControlReqResult, fkTunnelIfControlIndex, fkTunnelIfControlMode
                                 }
                        STATUS current
                        DESCRIPTION 
                                "Description."
                        ::= { fkTunnelIfNotification 5 }

                
                -- 1.3.6.1.4.1.10428 9 1.101.11.8.3.6
                fkTunnelIfTTLChanged NOTIFICATION-TYPE
                        OBJECTS { fkTunnelIfControlRequest, fkTunnelIfControlTimeStamp, fkTunnelIfControlReqResult, fkTunnelIfControlIndex, fkTunnelIfControlTTL
                                 }
                        STATUS current
                        DESCRIPTION 
                                "Description."
                        ::= { fkTunnelIfNotification 6 }

                
                -- 1.3.6.1.4.1.10428 9 1.101.11.8.3.7
                fkTunnelIfDscpChanged NOTIFICATION-TYPE
                        OBJECTS { fkTunnelIfControlRequest, fkTunnelIfControlTimeStamp, fkTunnelIfControlReqResult, fkTunnelIfControlIndex, fkTunneIflControlDscpMode, 
                                fkTunneIflControlDscp }
                        STATUS current
                        DESCRIPTION 
                                "Description."
                        ::= { fkTunnelIfNotification 7 }

                
                -- 1.3.6.1.4.1.10428 9 1.101.11.8.3.8
                fkTunnelIfKeepaliveChanged NOTIFICATION-TYPE
                        OBJECTS { fkTunnelIfControlRequest, fkTunnelIfControlTimeStamp, fkTunnelIfControlReqResult, fkTunnelIfControlIndex, fkTunnelIfControlKeepaliveInterval, 
                                fkTunneIflControlKeepaliveRetry }
                        STATUS current
                        DESCRIPTION 
                                "Description."
                        ::= { fkTunnelIfNotification 8 }

                
                -- 1.3.6.1.4.1.10428 9 1.101.11.8.3.9
                fkTunnelIfPathMtuDiscoveryChanged NOTIFICATION-TYPE
                        OBJECTS { fkTunnelIfControlRequest, fkTunnelIfControlTimeStamp, fkTunnelIfControlReqResult, fkTunnelIfControlIndex, fkTunnelIfControlPathMtuDiscovery
                                 }
                        STATUS current
                        DESCRIPTION 
                                "Description."
                        ::= { fkTunnelIfNotification 9 }

                
                -- 1.3.6.1.4.1.10428 9 1.101.11.8.3.10
                fkTunnelIfVRFNameSet NOTIFICATION-TYPE
                        OBJECTS { fkTunnelIfControlRequest, fkTunnelIfControlTimeStamp, fkTunnelIfControlReqResult, fkTunnelIfControlIndex, fkTunnelIfControlVRFName
                                 }
                        STATUS current
                        DESCRIPTION 
                                "Description."
                        ::= { fkTunnelIfNotification 10 }

                
                -- 1.3.6.1.4.1.10428 9 1.101.11.8.3.11
                fkTunnelIfVRFNameUnset NOTIFICATION-TYPE
                        OBJECTS { fkTunnelIfControlRequest, fkTunnelIfControlTimeStamp, fkTunnelIfControlReqResult, fkTunnelIfControlIndex }
                        STATUS current
                        DESCRIPTION 
                                "Description."
                        ::= { fkTunnelIfNotification 11 }

                
                -- 1.3.6.1.4.1.10428 9 1.101.11.8.4
                fkTunnelAddressTable OBJECT-TYPE
                        SYNTAX SEQUENCE OF FkTunnelAddressEntry
                        MAX-ACCESS not-accessible
                        STATUS current
                        DESCRIPTION
                                "Description."
                        ::= { fkTunnel 4 }

                
                -- 1.3.6.1.4.1.10428 9 1.101.11.8.4.1
                fkTunnelAddressEntry OBJECT-TYPE
                        SYNTAX FkTunnelAddressEntry
                        MAX-ACCESS not-accessible
                        STATUS current
                        DESCRIPTION
                                "Description."
                        INDEX { fkTunnelIfIndex, fkTunnelAddressValue }
                        ::= { fkTunnelAddressTable 1 }

                
                FkTunnelAddressEntry ::=
                        SEQUENCE { 
                                fkTunnelAddressValue
                                        IpAddress,
                                fkTunnelAddressMask
                                        Integer32,
                                fkTunnelIpAddrBcast
                                        IpAddress,
                                fkTunnelAddressFlag
                                        BITS,
                                fkTunnelAddressScope
                                        Integer32,
                                fkTunnelAddressUnnumIfIndex
                                        INTEGER,
                                fkTunnelAddressUnnumIpIndex
                                        INTEGER
                         }

                -- 1.3.6.1.4.1.10428 9 1.101.11.8.4.1.1
                fkTunnelAddressValue OBJECT-TYPE
                        SYNTAX IpAddress
                        MAX-ACCESS read-only
                        STATUS current
                        DESCRIPTION
                                "The IP address to which this entry's addressing information pertains."
                        ::= { fkTunnelAddressEntry 1 }

                
                -- 1.3.6.1.4.1.10428 9 1.101.11.8.4.1.2
                fkTunnelAddressMask OBJECT-TYPE
                        SYNTAX Integer32 (1..128)
                        MAX-ACCESS read-only
                        STATUS current
                        DESCRIPTION
                                "The subnet mask associated with the IP address of this entry. The value of the mask is an IP address with all the network bits set to 1 and all the hosts bits set to 0."
                        ::= { fkTunnelAddressEntry 2 }

                
                -- 1.3.6.1.4.1.10428 9 1.101.11.8.4.1.3
                fkTunnelIpAddrBcast OBJECT-TYPE
                        SYNTAX IpAddress
                        MAX-ACCESS read-only
                        STATUS current
                        DESCRIPTION
                                "Description."
                        ::= { fkTunnelAddressEntry 3 }
-- The value of the least-significant bit in the IP broadcast address used for sending datagrams on the (logical) interface associated with the IP address of this entry. For example, when the Internet standard all-ones broadcast address is used, the value will be 1. This value applies to both the subnet and network broadcasts addresses used by the entity on this (logical) interface.
                
                -- 1.3.6.1.4.1.10428 9 1.101.11.8.4.1.4
                fkTunnelAddressFlag OBJECT-TYPE
                        SYNTAX BITS
                                {
                                permanent(0),
                                tentative(1),
                                deprecated(2),
                                anycast(3),
                                reserved1(4),
                                reserved2(5),
                                reserved3(6),
                                secondary(7)
                                }
                        MAX-ACCESS read-only
                        STATUS current
                        DESCRIPTION
                                "dynamic: ~ permanent
                                primary : ~ secondary
                                anycast: this bit is available for ipv6 only.
                                The others are available for ipv4 only.
                                "
                        ::= { fkTunnelAddressEntry 4 }

                
                -- 1.3.6.1.4.1.10428 9 1.101.11.8.4.1.5
                fkTunnelAddressScope OBJECT-TYPE
                        SYNTAX Integer32 (0..255)
                        MAX-ACCESS read-only
                        STATUS current
                        DESCRIPTION
                                "default : global
                                In linux, 200 - site
                                0 - global
                                1..252 - scopeNUM
                                253 - link
                                254 - host
                                255 - nowhere
                                "
                        ::= { fkTunnelAddressEntry 5 }

                
                -- 1.3.6.1.4.1.10428 9 1.101.11.8.4.1.6
                fkTunnelAddressUnnumIfIndex OBJECT-TYPE
                        SYNTAX INTEGER (1..4094)
                        MAX-ACCESS read-only
                        STATUS current
                        DESCRIPTION
                                "The unnumbered-source interface index (Before ip unnumbered feature is set, a tunnel interface must be created.)
                                (ex. br100 -> 100, br200 -> 200)"
                        ::= { fkTunnelAddressEntry 6 }

                
                -- 1.3.6.1.4.1.10428 9 1.101.11.8.4.1.7
                fkTunnelAddressUnnumIpIndex OBJECT-TYPE
                        SYNTAX INTEGER (0 | 2..1024)
                        MAX-ACCESS read-only
                        STATUS current
                        DESCRIPTION
                                "The Ip index for Interface Unnumbered feature enhanced.
                                If Interface Unnumbered enhanced feature is enabled on a point-to-point interface. It will get a ip address of a specific interface.
                                Interface unnumbered default setting - it get primary ip address.
                                Interface unnumbered enhanced setting - it get secondary ip address with ip-index.
                                (cf. primary ip address's ip-index : 1. no setting: 0. other setting: 2-1024)"
                        ::= { fkTunnelAddressEntry 7 }

                
                -- 1.3.6.1.4.1.10428 9 1.101.11.8.5
                fkTunnelAddressControl OBJECT IDENTIFIER ::= { fkTunnel 5 }

                
                -- 1.3.6.1.4.1.10428 9 1.101.11.8.5.1
                fkTunnelAddressControlRequest OBJECT-TYPE
                        SYNTAX INTEGER
                                {
                                createTunnelIpAddress(1),
                                destroyTunnelIpAddress(2),
                                setIfUnnumbered(3),
                                delIfUnnumbered(4)
                                }
                        MAX-ACCESS read-write
                        STATUS current
                        DESCRIPTION
                                "The request of a user command."
                        ::= { fkTunnelAddressControl 1 }

                
                -- 1.3.6.1.4.1.10428 9 1.101.11.8.5.2
                fkTunnelAddressControlStatus OBJECT-TYPE
                        SYNTAX FkControlStatusType
                        MAX-ACCESS read-only
                        STATUS current
                        DESCRIPTION
                                "The status of a user command."
                        ::= { fkTunnelAddressControl 2 }

                
                -- 1.3.6.1.4.1.10428 9 1.101.11.8.5.3
                fkTunnelAddressControlTimer OBJECT-TYPE
                        SYNTAX Gauge32
                        MAX-ACCESS read-write
                        STATUS current
                        DESCRIPTION
                                "The maximum wait time for the manager for a long running user command."
                        ::= { fkTunnelAddressControl 3 }

                
                -- 1.3.6.1.4.1.10428 9 1.101.11.8.5.4
                fkTunnelAddressControlTimeStamp OBJECT-TYPE
                        SYNTAX FkControlRequestResultType
                        MAX-ACCESS read-only
                        STATUS current
                        DESCRIPTION
                                "The result of the last user command."
                        ::= { fkTunnelAddressControl 4 }

                
                -- 1.3.6.1.4.1.10428 9 1.101.11.8.5.5
                fkTunnelAddressControlReqResult OBJECT-TYPE
                        SYNTAX TimeTicks
                        MAX-ACCESS read-only
                        STATUS current
                        DESCRIPTION
                                "The time stamp of the last command (end of command)."
                        ::= { fkTunnelAddressControl 5 }

                
                -- 1.3.6.1.4.1.10428 9 1.101.11.8.5.6
                fkTunnelAddressControlTunnelIfIndex OBJECT-TYPE
                        SYNTAX Integer32 (10000..11023)
                        MAX-ACCESS read-write
                        STATUS current
                        DESCRIPTION
                                "Tunnel interface index"
                        ::= { fkTunnelAddressControl 6 }

                
                -- 1.3.6.1.4.1.10428 9 1.101.11.8.5.7
                fkTunnelAddressControlValue OBJECT-TYPE
                        SYNTAX IpAddress
                        MAX-ACCESS read-write
                        STATUS current
                        DESCRIPTION
                                "The IP address to which this entry's addressing information pertains."
                        ::= { fkTunnelAddressControl 7 }

                
                -- 1.3.6.1.4.1.10428 9 1.101.11.8.5.8
                fkTunnelAddressControlMask OBJECT-TYPE
                        SYNTAX Integer32 (1..128)
                        MAX-ACCESS read-write
                        STATUS current
                        DESCRIPTION
                                "The subnet mask associated with the IP address of this entry. The value of the mask is an IP address with all the network bits set to 1 and all the hosts bits set to 0."
                        ::= { fkTunnelAddressControl 8 }

                
                -- 1.3.6.1.4.1.10428 9 1.101.11.8.5.9
                fkTunnelAddressControlFlag OBJECT-TYPE
                        SYNTAX INTEGER
                                {
                                primary(1),
                                secondary(2),
                                anycast(3),
                                unicast(4)
                                }
                        MAX-ACCESS read-write
                        STATUS current
                        DESCRIPTION
                                "default : primary"
                        DEFVAL { primary }
                        ::= { fkTunnelAddressControl 9 }

                
                -- 1.3.6.1.4.1.10428 9 1.101.11.8.5.10
                fkTunnelAddressControlScope OBJECT-TYPE
                        SYNTAX INTEGER
                                {
                                global(0),
                                link(253),
                                host(254)
                                }
                        MAX-ACCESS read-write
                        STATUS current
                        DESCRIPTION
                                "default : global
                                not applicable : nowhere"
                        DEFVAL { global }
                        ::= { fkTunnelAddressControl 10 }

                
                -- 1.3.6.1.4.1.10428 9 1.101.11.8.5.11
                fkTunnelAddressControlUnnumIfIndex OBJECT-TYPE
                        SYNTAX INTEGER (1..4094)
                        MAX-ACCESS read-write
                        STATUS current
                        DESCRIPTION
                                "The unnumbered-source interface index (Before ip unnumbered feature is set, a tunnel interface must be created.)
                                (ex. br100 -> 100, br200 -> 200)"
                        ::= { fkTunnelAddressControl 11 }

                
                -- 1.3.6.1.4.1.10428 9 1.101.11.8.5.12
                fkTunnelAddressControlUnnumIpIndex OBJECT-TYPE
                        SYNTAX INTEGER (0 | 2..1024)
                        MAX-ACCESS read-write
                        STATUS current
                        DESCRIPTION
                                "The Ip index for Interface Unnumbered feature enhanced.
                                If Interface Unnumbered enhanced feature is enabled on a point-to-point interface. It will get a ip address of a specific interface.
                                Interface unnumbered default setting - it get primary ip address.
                                Interface unnumbered enhanced setting - it get secondary ip address with ip-index.
                                (cf. primary ip address's ip-index : 1. no setting: 0. other setting: 2-1024)"
                        ::= { fkTunnelAddressControl 12 }

                
                -- 1.3.6.1.4.1.10428 9 1.101.11.8.6
                fkTunnelAddressNotification OBJECT IDENTIFIER ::= { fkTunnel 6 }

                
                -- 1.3.6.1.4.1.10428 9 1.101.11.8.6.1
                fkTunnelAddressCreated NOTIFICATION-TYPE
                        OBJECTS { fkTunnelAddressControlRequest, fkTunnelAddressControlTimeStamp, fkTunnelAddressControlReqResult, fkTunnelAddressControlTunnelIfIndex, fkTunnelAddressControlValue, 
                                fkTunnelAddressControlMask, fkTunnelAddressControlFlag, fkTunnelAddressControlScope }
                        STATUS current
                        DESCRIPTION 
                                "Description."
                        ::= { fkTunnelAddressNotification 1 }

                
                -- 1.3.6.1.4.1.10428 9 1.101.11.8.6.2
                fkTunnelAddressDeleted NOTIFICATION-TYPE
                        OBJECTS { fkTunnelAddressControlRequest, fkTunnelAddressControlTimeStamp, fkTunnelAddressControlReqResult, fkTunnelAddressControlTunnelIfIndex, fkTunnelAddressControlValue, 
                                fkTunnelAddressControlMask, fkTunnelAddressControlFlag }
                        STATUS current
                        DESCRIPTION 
                                "Description."
                        ::= { fkTunnelAddressNotification 2 }

                
                -- 1.3.6.1.4.1.10428 9 1.101.11.8.6.3
                fkTunnelAddressUnnumChanged NOTIFICATION-TYPE
                        OBJECTS { fkTunnelAddressControlRequest, fkTunnelAddressControlTimeStamp, fkTunnelAddressControlReqResult, fkTunnelAddressControlUnnumIfIndex, fkTunnelAddressControlUnnumIpIndex
                                 }
                        STATUS current
                        DESCRIPTION 
                                "setIfUnnumbered"
                        ::= { fkTunnelAddressNotification 3 }

                
                -- 1.3.6.1.4.1.10428 9 1.101.11.8.6.4
                fkTunnelAddressUnnumDeleted NOTIFICATION-TYPE
                        OBJECTS { fkTunnelAddressControlRequest, fkTunnelAddressControlTimeStamp, fkTunnelAddressControlReqResult, fkTunnelAddressControlTunnelIfIndex }
                        STATUS current
                        DESCRIPTION 
                                "delIfUnnumbered"
                        ::= { fkTunnelAddressNotification 4 }

                
                -- 1.3.6.1.4.1.10428 9 1.101.11.9
                fkIpVRF OBJECT IDENTIFIER ::= { fkNetwork 9 }

                
                -- 1.3.6.1.4.1.10428 9 1.101.11.9.1
                fkIpVRFTable OBJECT-TYPE
                        SYNTAX SEQUENCE OF FkIpVRFEntry
                        MAX-ACCESS not-accessible
                        STATUS current
                        DESCRIPTION
                                "Description."
                        ::= { fkIpVRF 1 }

                
                -- 1.3.6.1.4.1.10428 9 1.101.11.9.1.1
                fkIpVRFEntry OBJECT-TYPE
                        SYNTAX FkIpVRFEntry
                        MAX-ACCESS not-accessible
                        STATUS current
                        DESCRIPTION
                                "Description."
                        INDEX { fkIpVRFIndex }
                        ::= { fkIpVRFTable 1 }

                
                FkIpVRFEntry ::=
                        SEQUENCE { 
                                fkIpVRFIndex
                                        Integer32,
                                fkIpVRFName
                                        OCTET STRING,
                                fkIpVRFDesignatedPorts
                                        OCTET STRING,
                                fkIpVRFRouterId
                                        IpAddress,
                                fkIpVRFDescription
                                        OCTET STRING
                         }

                -- 1.3.6.1.4.1.10428 9 1.101.11.9.1.1.1
                fkIpVRFIndex OBJECT-TYPE
                        SYNTAX Integer32 (0..2147483647)
                        MAX-ACCESS read-only
                        STATUS current
                        DESCRIPTION
                                "VRF index."
                        ::= { fkIpVRFEntry 1 }

                
                -- 1.3.6.1.4.1.10428 9 1.101.11.9.1.1.2
                fkIpVRFName OBJECT-TYPE
                        SYNTAX OCTET STRING (SIZE (0..63))
                        MAX-ACCESS read-only
                        STATUS current
                        DESCRIPTION
                                "VRF name."
                        ::= { fkIpVRFEntry 2 }

                
                -- 1.3.6.1.4.1.10428 9 1.101.11.9.1.1.3
                fkIpVRFDesignatedPorts OBJECT-TYPE
                        SYNTAX OCTET STRING
                        MAX-ACCESS read-only
                        STATUS current
                        DESCRIPTION
                                "The port map of  VRF designated-port."
                        ::= { fkIpVRFEntry 3 }

                
                -- 1.3.6.1.4.1.10428 9 1.101.11.9.1.1.4
                fkIpVRFRouterId OBJECT-TYPE
                        SYNTAX IpAddress
                        MAX-ACCESS read-only
                        STATUS current
                        DESCRIPTION
                                "Router-Identifier 
                                "
                        ::= { fkIpVRFEntry 4 }

                
                -- 1.3.6.1.4.1.10428 9 1.101.11.9.1.1.5
                fkIpVRFDescription OBJECT-TYPE
                        SYNTAX OCTET STRING (SIZE (0..128))
                        MAX-ACCESS read-only
                        STATUS current
                        DESCRIPTION
                                "The description of VRF.
                                "
                        ::= { fkIpVRFEntry 5 }

                
                -- 1.3.6.1.4.1.10428 9 1.101.11.9.2
                fkIpVRFControl OBJECT IDENTIFIER ::= { fkIpVRF 2 }

                
                -- 1.3.6.1.4.1.10428 9 1.101.11.9.2.1
                fkIpVRFControlRequest OBJECT-TYPE
                        SYNTAX INTEGER
                                {
                                createIpVRF(1),
                                deleteIpVRF(2),
                                setIpVRFDesignatedPorts(3),
                                unsetIpVRFDesignatedPorts(4),
                                setVRFRouterId(5),
                                setVRFDescription(6)
                                }
                        MAX-ACCESS read-write
                        STATUS current
                        DESCRIPTION
                                "The request of a user command."
                        ::= { fkIpVRFControl 1 }

                
                -- 1.3.6.1.4.1.10428 9 1.101.11.9.2.2
                fkIpVRFControlStatus OBJECT-TYPE
                        SYNTAX FkControlStatusType
                        MAX-ACCESS read-only
                        STATUS current
                        DESCRIPTION
                                "The status of a user command."
                        ::= { fkIpVRFControl 2 }

                
                -- 1.3.6.1.4.1.10428 9 1.101.11.9.2.3
                fkIpVRFControlTimer OBJECT-TYPE
                        SYNTAX Gauge32
                        MAX-ACCESS read-write
                        STATUS current
                        DESCRIPTION
                                "The maximum wait time for the manager for a long running user command."
                        ::= { fkIpVRFControl 3 }

                
                -- 1.3.6.1.4.1.10428 9 1.101.11.9.2.4
                fkIpVRFControlTimeStamp OBJECT-TYPE
                        SYNTAX FkControlRequestResultType
                        MAX-ACCESS read-only
                        STATUS current
                        DESCRIPTION
                                "The result of the last user command."
                        ::= { fkIpVRFControl 4 }

                
                -- 1.3.6.1.4.1.10428 9 1.101.11.9.2.5
                fkIpVRFControlReqResult OBJECT-TYPE
                        SYNTAX TimeTicks
                        MAX-ACCESS read-only
                        STATUS current
                        DESCRIPTION
                                "The time stamp of the last command (end of command)."
                        ::= { fkIpVRFControl 5 }

                
                -- 1.3.6.1.4.1.10428 9 1.101.11.9.2.6
                fkIpVRFControlName OBJECT-TYPE
                        SYNTAX OCTET STRING (SIZE (0..63))
                        MAX-ACCESS read-write
                        STATUS current
                        DESCRIPTION
                                "VRF name"
                        ::= { fkIpVRFControl 6 }

                
                -- 1.3.6.1.4.1.10428 9 1.101.11.9.2.7
                fkIpVRFControlDesignatedPorts OBJECT-TYPE
                        SYNTAX OCTET STRING
                        MAX-ACCESS read-write
                        STATUS current
                        DESCRIPTION
                                "The port map of  VRF designated-port."
                        ::= { fkIpVRFControl 7 }

                
                -- 1.3.6.1.4.1.10428 9 1.101.11.9.2.8
                fkIpVRFControlRouterId OBJECT-TYPE
                        SYNTAX IpAddress
                        MAX-ACCESS read-write
                        STATUS current
                        DESCRIPTION
                                "Router-Identifier 
                                "
                        ::= { fkIpVRFControl 8 }

                
                -- 1.3.6.1.4.1.10428 9 1.101.11.9.2.9
                fkIpVRFControlDescription OBJECT-TYPE
                        SYNTAX OCTET STRING (SIZE (0..128))
                        MAX-ACCESS read-write
                        STATUS current
                        DESCRIPTION
                                "The description of VRF."
                        ::= { fkIpVRFControl 9 }

                
                -- 1.3.6.1.4.1.10428 9 1.101.11.9.3
                fkIpVRFNotification OBJECT IDENTIFIER ::= { fkIpVRF 3 }

                
                -- 1.3.6.1.4.1.10428 9 1.101.11.9.3.1
                fkIpVRFCreated NOTIFICATION-TYPE
                        OBJECTS { fkIpVRFControlRequest, fkIpVRFControlTimeStamp, fkIpVRFControlName, fkIpVRFControlReqResult }
                        STATUS current
                        DESCRIPTION 
                                "Description."
                        ::= { fkIpVRFNotification 1 }

                
                -- 1.3.6.1.4.1.10428 9 1.101.11.9.3.2
                fkIpVRFDeleted NOTIFICATION-TYPE
                        OBJECTS { fkIpVRFControlRequest, fkIpVRFControlTimeStamp, fkIpVRFControlReqResult, fkIpVRFControlName }
                        STATUS current
                        DESCRIPTION 
                                "Description."
                        ::= { fkIpVRFNotification 2 }

                
                -- 1.3.6.1.4.1.10428 9 1.101.11.9.3.3
                fkIpVRFDesignatedPortsSet NOTIFICATION-TYPE
                        OBJECTS { fkIpVRFControlRequest, fkIpVRFControlTimeStamp, fkIpVRFControlReqResult, fkIpVRFControlName, fkIpVRFControlDesignatedPorts
                                 }
                        STATUS current
                        DESCRIPTION 
                                "Description."
                        ::= { fkIpVRFNotification 3 }

                
                -- 1.3.6.1.4.1.10428 9 1.101.11.9.3.4
                fkIpVRFDesignatedPortsUnset NOTIFICATION-TYPE
                        OBJECTS { fkIpVRFControlRequest, fkIpVRFControlTimeStamp, fkIpVRFControlReqResult, fkIpVRFControlName, fkIpVRFControlDesignatedPorts
                                 }
                        STATUS current
                        DESCRIPTION 
                                "Description."
                        ::= { fkIpVRFNotification 4 }

                
                -- 1.3.6.1.4.1.10428 9 1.101.11.9.3.5
                fkIpVRFRouterIdChanged NOTIFICATION-TYPE
                        OBJECTS { fkIpVRFControlRequest, fkIpVRFControlTimeStamp, fkIpVRFControlReqResult, fkIpVRFControlName, fkIpVRFControlRouterId
                                 }
                        STATUS current
                        DESCRIPTION 
                                "Description."
                        ::= { fkIpVRFNotification 5 }

                
                -- 1.3.6.1.4.1.10428 9 1.101.11.9.3.6
                fkIpVRFDescriptionChanged NOTIFICATION-TYPE
                        OBJECTS { fkIpVRFControlRequest, fkIpVRFControlTimeStamp, fkIpVRFControlReqResult, fkIpVRFControlName, fkIpVRFControlDescription
                                 }
                        STATUS current
                        DESCRIPTION 
                                "Description."
                        ::= { fkIpVRFNotification 6 }

                
                -- 1.3.6.1.4.1.10428 9 1.101.11.9.4
                fkIpVRFSelectionSourceTable OBJECT-TYPE
                        SYNTAX SEQUENCE OF FkIpVRFSelectionSourceEntry
                        MAX-ACCESS not-accessible
                        STATUS current
                        DESCRIPTION
                                "Description."
                        ::= { fkIpVRF 4 }

                
                -- 1.3.6.1.4.1.10428 9 1.101.11.9.4.1
                fkIpVRFSelectionSourceEntry OBJECT-TYPE
                        SYNTAX FkIpVRFSelectionSourceEntry
                        MAX-ACCESS not-accessible
                        STATUS current
                        DESCRIPTION
                                "Description."
                        INDEX { fkIpVRFSelectionSrcIndex }
                        ::= { fkIpVRFSelectionSourceTable 1 }

                
                FkIpVRFSelectionSourceEntry ::=
                        SEQUENCE { 
                                fkIpVRFSelectionSrcIndex
                                        INTEGER,
                                fkIpVRFSelectionSrcAddr
                                        IpAddress,
                                fkIpVRFSelectionSrcMask
                                        Integer32,
                                fkIpVRFSelectionSrcVRFName
                                        OCTET STRING
                         }

                -- 1.3.6.1.4.1.10428 9 1.101.11.9.4.1.1
                fkIpVRFSelectionSrcIndex OBJECT-TYPE
                        SYNTAX INTEGER (1..1024)
                        MAX-ACCESS read-only
                        STATUS current
                        DESCRIPTION
                                "VRF selection source index."
                        ::= { fkIpVRFSelectionSourceEntry 1 }

                
                -- 1.3.6.1.4.1.10428 9 1.101.11.9.4.1.2
                fkIpVRFSelectionSrcAddr OBJECT-TYPE
                        SYNTAX IpAddress
                        MAX-ACCESS read-only
                        STATUS current
                        DESCRIPTION
                                "VRF selection by source IP address."
                        ::= { fkIpVRFSelectionSourceEntry 2 }

                
                -- 1.3.6.1.4.1.10428 9 1.101.11.9.4.1.3
                fkIpVRFSelectionSrcMask OBJECT-TYPE
                        SYNTAX Integer32 (1..32)
                        MAX-ACCESS read-only
                        STATUS current
                        DESCRIPTION
                                "The subnet mask associated with the IP address of this entry. The value of the mask is an IP address with all the network bits set to 1 and all the hosts bits set to 0."
                        ::= { fkIpVRFSelectionSourceEntry 3 }

                
                -- 1.3.6.1.4.1.10428 9 1.101.11.9.4.1.4
                fkIpVRFSelectionSrcVRFName OBJECT-TYPE
                        SYNTAX OCTET STRING (SIZE (0..63))
                        MAX-ACCESS read-only
                        STATUS current
                        DESCRIPTION
                                "VPN Routing/Forwarding instance name."
                        ::= { fkIpVRFSelectionSourceEntry 4 }

                
                -- 1.3.6.1.4.1.10428 9 1.101.11.9.5
                fkIpVRFSelectionSourceControl OBJECT IDENTIFIER ::= { fkIpVRF 5 }

                
                -- 1.3.6.1.4.1.10428 9 1.101.11.9.5.1
                fkIpVRFSelectionSrcControlRequest OBJECT-TYPE
                        SYNTAX INTEGER
                                {
                                setVRFSelectionSource(1),
                                unsetVRFSelectionSource(2)
                                }
                        MAX-ACCESS read-write
                        STATUS current
                        DESCRIPTION
                                "The request of a user command."
                        ::= { fkIpVRFSelectionSourceControl 1 }

                
                -- 1.3.6.1.4.1.10428 9 1.101.11.9.5.2
                fkIpVRFSelectionSrcControlStatus OBJECT-TYPE
                        SYNTAX FkControlStatusType
                        MAX-ACCESS read-only
                        STATUS current
                        DESCRIPTION
                                "The status of a user command."
                        ::= { fkIpVRFSelectionSourceControl 2 }

                
                -- 1.3.6.1.4.1.10428 9 1.101.11.9.5.3
                fkIpVRFSelectionSrcControlTimer OBJECT-TYPE
                        SYNTAX Gauge32
                        MAX-ACCESS read-write
                        STATUS current
                        DESCRIPTION
                                "The maximum wait time for the manager for a long running user command."
                        ::= { fkIpVRFSelectionSourceControl 3 }

                
                -- 1.3.6.1.4.1.10428 9 1.101.11.9.5.4
                fkIpVRFSelectionSrcControlTimeStamp OBJECT-TYPE
                        SYNTAX FkControlRequestResultType
                        MAX-ACCESS read-only
                        STATUS current
                        DESCRIPTION
                                "The result of the last user command."
                        ::= { fkIpVRFSelectionSourceControl 4 }

                
                -- 1.3.6.1.4.1.10428 9 1.101.11.9.5.5
                fkIpVRFSelectionSrcControlReqResult OBJECT-TYPE
                        SYNTAX TimeTicks
                        MAX-ACCESS read-only
                        STATUS current
                        DESCRIPTION
                                "The time stamp of the last command (end of command)."
                        ::= { fkIpVRFSelectionSourceControl 5 }

                
                -- 1.3.6.1.4.1.10428 9 1.101.11.9.5.6
                fkIpVRFSelectionSrcControlAddr OBJECT-TYPE
                        SYNTAX IpAddress
                        MAX-ACCESS read-write
                        STATUS current
                        DESCRIPTION
                                "VRF selection by source IP address."
                        ::= { fkIpVRFSelectionSourceControl 6 }

                
                -- 1.3.6.1.4.1.10428 9 1.101.11.9.5.7
                fkIpVRFSelectionSrcControlMask OBJECT-TYPE
                        SYNTAX Integer32 (1..32)
                        MAX-ACCESS read-write
                        STATUS current
                        DESCRIPTION
                                "The subnet mask associated with the IP address of this entry. The value of the mask is an IP address with all the network bits set to 1 and all the hosts bits set to 0."
                        ::= { fkIpVRFSelectionSourceControl 7 }

                
                -- 1.3.6.1.4.1.10428 9 1.101.11.9.5.8
                fkIpVRFSelectionSrcControlVRFName OBJECT-TYPE
                        SYNTAX OCTET STRING (SIZE (0..63))
                        MAX-ACCESS read-write
                        STATUS current
                        DESCRIPTION
                                "VPN Routing/Forwarding instance name."
                        ::= { fkIpVRFSelectionSourceControl 8 }

                
                -- 1.3.6.1.4.1.10428 9 1.101.11.9.6
                fkIpVRFSelectionSourceNotification OBJECT IDENTIFIER ::= { fkIpVRF 6 }

                
                -- 1.3.6.1.4.1.10428 9 1.101.11.9.6.1
                fkIpVRFSelectionSrcSet NOTIFICATION-TYPE
                        OBJECTS { fkIpVRFSelectionSrcControlRequest, fkIpVRFSelectionSrcControlTimeStamp, fkIpVRFSelectionSrcControlReqResult, fkIpVRFSelectionSrcControlAddr, fkIpVRFSelectionSrcControlMask, 
                                fkIpVRFSelectionSrcControlVRFName }
                        STATUS current
                        DESCRIPTION 
                                "Description."
                        ::= { fkIpVRFSelectionSourceNotification 1 }

                
                -- 1.3.6.1.4.1.10428 9 1.101.11.9.6.2
                fkIpVRFSelectionSrcUnset NOTIFICATION-TYPE
                        OBJECTS { fkIpVRFSelectionSrcControlRequest, fkIpVRFSelectionSrcControlTimeStamp, fkIpVRFSelectionSrcControlReqResult, fkIpVRFSelectionSrcControlAddr, fkIpVRFSelectionSrcControlMask, 
                                fkIpVRFSelectionSrcControlVRFName }
                        STATUS current
                        DESCRIPTION 
                                "Description."
                        ::= { fkIpVRFSelectionSourceNotification 2 }

                
                -- 1.3.6.1.4.1.10428 9 1.101.11.10
                fkBFD OBJECT IDENTIFIER ::= { fkNetwork 10 }

                
                -- 1.3.6.1.4.1.10428 9 1.101.11.10.1
                fkBFDBase OBJECT IDENTIFIER ::= { fkBFD 1 }

                
                -- 1.3.6.1.4.1.10428 9 1.101.11.10.1.1
                fkBFDBaseInfo OBJECT IDENTIFIER ::= { fkBFDBase 1 }

                
                -- 1.3.6.1.4.1.10428 9 1.101.11.10.1.1.1
                fkBFDEnable OBJECT-TYPE
                        SYNTAX INTEGER
                                {
                                disable(0),
                                enable(1)
                                }
                        MAX-ACCESS read-only
                        STATUS current
                        DESCRIPTION
                                "BFD fast-detect is enabled or disabled."
                        ::= { fkBFDBaseInfo 1 }

                
                -- 1.3.6.1.4.1.10428 9 1.101.11.10.1.1.2
                fkBFDEchoEnable OBJECT-TYPE
                        SYNTAX INTEGER
                                {
                                disable(0),
                                enable(1)
                                }
                        MAX-ACCESS read-only
                        STATUS current
                        DESCRIPTION
                                "BFD Echo function is enabled or disabled."
                        ::= { fkBFDBaseInfo 2 }

                
                -- 1.3.6.1.4.1.10428 9 1.101.11.10.1.1.3
                fkBFDSlowTimer OBJECT-TYPE
                        SYNTAX INTEGER (1000..30000)
                        MAX-ACCESS read-only
                        STATUS current
                        DESCRIPTION
                                "BFD Slow Timer in unit of milliseconds
                                default: 1000(ms)"
                        ::= { fkBFDBaseInfo 3 }

                
                -- 1.3.6.1.4.1.10428 9 1.101.11.10.1.2
                fkBFDBaseControl OBJECT IDENTIFIER ::= { fkBFDBase 2 }

                
                -- 1.3.6.1.4.1.10428 9 1.101.11.10.1.2.1
                fkBFDControlRequest OBJECT-TYPE
                        SYNTAX INTEGER { setBFDBaseProfile(1) }
                        MAX-ACCESS read-write
                        STATUS current
                        DESCRIPTION
                                "The request of a user command"
                        ::= { fkBFDBaseControl 1 }

                
                -- 1.3.6.1.4.1.10428 9 1.101.11.10.1.2.2
                fkBFDControlStatus OBJECT-TYPE
                        SYNTAX FkControlStatusType
                        MAX-ACCESS read-only
                        STATUS current
                        DESCRIPTION
                                "The status of user command."
                        ::= { fkBFDBaseControl 2 }

                
                -- 1.3.6.1.4.1.10428 9 1.101.11.10.1.2.3
                fkBFDControlTimer OBJECT-TYPE
                        SYNTAX Gauge32
                        MAX-ACCESS read-write
                        STATUS current
                        DESCRIPTION
                                "The maximum time for the manager for a long running user command."
                        ::= { fkBFDBaseControl 3 }

                
                -- 1.3.6.1.4.1.10428 9 1.101.11.10.1.2.4
                fkBFDControlTimeStamp OBJECT-TYPE
                        SYNTAX TimeTicks
                        MAX-ACCESS read-only
                        STATUS current
                        DESCRIPTION
                                "The time stamp of the last command(end of command)."
                        ::= { fkBFDBaseControl 4 }

                
                -- 1.3.6.1.4.1.10428 9 1.101.11.10.1.2.5
                fkBFDControlReqResult OBJECT-TYPE
                        SYNTAX FkControlRequestResultType
                        MAX-ACCESS read-only
                        STATUS current
                        DESCRIPTION
                                "The result of the last user command."
                        ::= { fkBFDBaseControl 5 }

                
                -- 1.3.6.1.4.1.10428 9 1.101.11.10.1.2.6
                fkBFDControlEnable OBJECT-TYPE
                        SYNTAX INTEGER
                                {
                                disable(0),
                                enable(1)
                                }
                        MAX-ACCESS read-write
                        STATUS current
                        DESCRIPTION
                                "BFD fast-detect is enabled or disabled."
                        ::= { fkBFDBaseControl 6 }

                
                -- 1.3.6.1.4.1.10428 9 1.101.11.10.1.2.7
                fkBFDControlEchoEnable OBJECT-TYPE
                        SYNTAX INTEGER
                                {
                                disable(0),
                                enable(1)
                                }
                        MAX-ACCESS read-write
                        STATUS current
                        DESCRIPTION
                                "BFD Echo function is enabled or disabled."
                        ::= { fkBFDBaseControl 7 }

                
                -- 1.3.6.1.4.1.10428 9 1.101.11.10.1.2.8
                fkBFDControlSlowTimer OBJECT-TYPE
                        SYNTAX INTEGER (1000..30000)
                        MAX-ACCESS read-write
                        STATUS current
                        DESCRIPTION
                                "BFD Slow Timer in unit of milliseconds
                                default: 1000(ms)"
                        ::= { fkBFDBaseControl 8 }

                
                -- 1.3.6.1.4.1.10428 9 1.101.11.10.1.3
                fkBFDBaseNotification OBJECT IDENTIFIER ::= { fkBFDBase 3 }

                
                -- 1.3.6.1.4.1.10428 9 1.101.11.10.1.3.1
                fkBFDBaseProfileChanged NOTIFICATION-TYPE
                        OBJECTS { fkBFDControlRequest, fkBFDControlReqResult, fkBFDControlTimeStamp, fkBFDEnable, fkBFDEchoEnable, 
                                fkBFDSlowTimer }
                        STATUS current
                        DESCRIPTION 
                                "Description."
                        ::= { fkBFDBaseNotification 1 }

                
                -- 1.3.6.1.4.1.10428 9 1.101.11.10.2
                fkBFDInterface OBJECT IDENTIFIER ::= { fkBFD 2 }

                
                -- 1.3.6.1.4.1.10428 9 1.101.11.10.2.1
                fkBFDInterfaceTable OBJECT-TYPE
                        SYNTAX SEQUENCE OF FkBFDInterfaceEntry
                        MAX-ACCESS not-accessible
                        STATUS current
                        DESCRIPTION
                                "Description."
                        ::= { fkBFDInterface 1 }

                
                -- 1.3.6.1.4.1.10428 9 1.101.11.10.2.1.1
                fkBFDInterfaceEntry OBJECT-TYPE
                        SYNTAX FkBFDInterfaceEntry
                        MAX-ACCESS not-accessible
                        STATUS current
                        DESCRIPTION
                                "Description."
                        INDEX { fkNetIfIndex }
                        ::= { fkBFDInterfaceTable 1 }

                
                FkBFDInterfaceEntry ::=
                        SEQUENCE { 
                                fkBFDIfRxInterval
                                        INTEGER,
                                fkBFDIfTxInterval
                                        INTEGER,
                                fkBFDIfDetectMulti
                                        INTEGER
                         }

                -- 1.3.6.1.4.1.10428 9 1.101.11.10.2.1.1.1
                fkBFDIfRxInterval OBJECT-TYPE
                        SYNTAX INTEGER (50..10000)
                        MAX-ACCESS read-only
                        STATUS current
                        DESCRIPTION
                                "Required Min Rx Interval of BFD control packet in this interface.
                                default: 50(ms)"
                        ::= { fkBFDInterfaceEntry 1 }

                
                -- 1.3.6.1.4.1.10428 9 1.101.11.10.2.1.1.2
                fkBFDIfTxInterval OBJECT-TYPE
                        SYNTAX INTEGER (50..10000)
                        MAX-ACCESS read-only
                        STATUS current
                        DESCRIPTION
                                "Required Min Tx Interval of BFD control packet in this interface.
                                default: 50(ms)"
                        ::= { fkBFDInterfaceEntry 2 }

                
                -- 1.3.6.1.4.1.10428 9 1.101.11.10.2.1.1.3
                fkBFDIfDetectMulti OBJECT-TYPE
                        SYNTAX INTEGER (3..255)
                        MAX-ACCESS read-only
                        STATUS current
                        DESCRIPTION
                                "Detect Multi value of BFD control packet in this interface.
                                default: 3"
                        ::= { fkBFDInterfaceEntry 3 }

                
                -- 1.3.6.1.4.1.10428 9 1.101.11.10.2.2
                fkBFDInterfaceControl OBJECT IDENTIFIER ::= { fkBFDInterface 2 }

                
                -- 1.3.6.1.4.1.10428 9 1.101.11.10.2.2.1
                fkBFDIfControlRequest OBJECT-TYPE
                        SYNTAX INTEGER { setBFDIfProfile(1) }
                        MAX-ACCESS read-write
                        STATUS current
                        DESCRIPTION
                                "The request of a user command"
                        ::= { fkBFDInterfaceControl 1 }

                
                -- 1.3.6.1.4.1.10428 9 1.101.11.10.2.2.2
                fkBFDIfControlStatus OBJECT-TYPE
                        SYNTAX FkControlStatusType
                        MAX-ACCESS read-only
                        STATUS current
                        DESCRIPTION
                                "The status of user command."
                        ::= { fkBFDInterfaceControl 2 }

                
                -- 1.3.6.1.4.1.10428 9 1.101.11.10.2.2.3
                fkBFDIfControlTimer OBJECT-TYPE
                        SYNTAX Gauge32
                        MAX-ACCESS read-write
                        STATUS current
                        DESCRIPTION
                                "The maximum time for the manager for a long running user command."
                        ::= { fkBFDInterfaceControl 3 }

                
                -- 1.3.6.1.4.1.10428 9 1.101.11.10.2.2.4
                fkBFDIfControlTimeStamp OBJECT-TYPE
                        SYNTAX TimeTicks
                        MAX-ACCESS read-only
                        STATUS current
                        DESCRIPTION
                                "The time stamp of the last command(end of command)."
                        ::= { fkBFDInterfaceControl 4 }

                
                -- 1.3.6.1.4.1.10428 9 1.101.11.10.2.2.5
                fkBFDIfControlReqResult OBJECT-TYPE
                        SYNTAX FkControlRequestResultType
                        MAX-ACCESS read-only
                        STATUS current
                        DESCRIPTION
                                "The result of the last user command."
                        ::= { fkBFDInterfaceControl 5 }

                
                -- 1.3.6.1.4.1.10428 9 1.101.11.10.2.2.6
                fkBFDIfControlNetIfIndex OBJECT-TYPE
                        SYNTAX Integer32 (0..4097)
                        MAX-ACCESS read-write
                        STATUS current
                        DESCRIPTION
                                "BFD Interface Index."
                        ::= { fkBFDInterfaceControl 6 }

                
                -- 1.3.6.1.4.1.10428 9 1.101.11.10.2.2.7
                fkBFDIfControlRxInterval OBJECT-TYPE
                        SYNTAX INTEGER (50..10000)
                        MAX-ACCESS read-write
                        STATUS current
                        DESCRIPTION
                                "Required Min Rx Interval of BFD control packet in this interface.
                                default: 50(ms)"
                        ::= { fkBFDInterfaceControl 7 }

                
                -- 1.3.6.1.4.1.10428 9 1.101.11.10.2.2.8
                fkBFDIfControlTxInterval OBJECT-TYPE
                        SYNTAX INTEGER (50..10000)
                        MAX-ACCESS read-write
                        STATUS current
                        DESCRIPTION
                                "Required Min Tx Interval of BFD control packet in this interface.
                                default: 50(ms)"
                        ::= { fkBFDInterfaceControl 8 }

                
                -- 1.3.6.1.4.1.10428 9 1.101.11.10.2.2.9
                fkBFDIfControlDetectMulti OBJECT-TYPE
                        SYNTAX INTEGER (3..255)
                        MAX-ACCESS read-write
                        STATUS current
                        DESCRIPTION
                                "Detect Multi value of BFD control packet in this interface.
                                default: 3"
                        ::= { fkBFDInterfaceControl 9 }

                
                -- 1.3.6.1.4.1.10428 9 1.101.11.10.2.3
                fkBFDInterfaceNotification OBJECT IDENTIFIER ::= { fkBFDInterface 3 }

                
                -- 1.3.6.1.4.1.10428 9 1.101.11.10.2.3.1
                fkBFDIfProfileChanged NOTIFICATION-TYPE
                        OBJECTS { fkBFDIfControlRequest, fkBFDIfControlTimeStamp, fkBFDIfControlReqResult, fkBFDIfRxInterval, fkBFDIfTxInterval, 
                                fkBFDIfDetectMulti }
                        STATUS current
                        DESCRIPTION 
                                "Description."
                        ::= { fkBFDInterfaceNotification 1 }

                
                -- 1.3.6.1.4.1.10428 9 1.101.11.10.3
                fkBFDSession OBJECT IDENTIFIER ::= { fkBFD 3 }

                
                -- 1.3.6.1.4.1.10428 9 1.101.11.10.3.1
                fkBFDSessionInfo OBJECT IDENTIFIER ::= { fkBFDSession 1 }

                
                -- 1.3.6.1.4.1.10428 9 1.101.11.10.3.1.1
                fkBFDSessionInfoTable OBJECT-TYPE
                        SYNTAX SEQUENCE OF FkBFDSessionInfoEntry
                        MAX-ACCESS not-accessible
                        STATUS current
                        DESCRIPTION
                                "Description."
                        ::= { fkBFDSessionInfo 1 }

                
                -- 1.3.6.1.4.1.10428 9 1.101.11.10.3.1.1.1
                fkBFDSessionInfoEntry OBJECT-TYPE
                        SYNTAX FkBFDSessionInfoEntry
                        MAX-ACCESS not-accessible
                        STATUS current
                        DESCRIPTION
                                "Description."
                        INDEX { fkNetIfIndex, fkBFDSessionNeighAddrType, fkBFDSessionNeighAddrValue }
                        ::= { fkBFDSessionInfoTable 1 }

                
                FkBFDSessionInfoEntry ::=
                        SEQUENCE { 
                                fkBFDSessionNeighAddrType
                                        InetAddressType,
                                fkBFDSessionNeighAddrValue
                                        InetAddress,
                                fkBFDSessionRegProtocols
                                        BITS,
                                fkBFDSessionLocalDiscr
                                        Unsigned32,
                                fkBFDSessionRemoteDiscr
                                        Unsigned32,
                                fkBFDSessionDetecMultiplier
                                        INTEGER,
                                fkBFDSessionStatus
                                        INTEGER,
                                fkBFDSessionEchoUsage
                                        INTEGER,
                                fkBFDSessionUptime
                                        TimeTicks
                         }

                -- 1.3.6.1.4.1.10428 9 1.101.11.10.3.1.1.1.1
                fkBFDSessionNeighAddrType OBJECT-TYPE
                        SYNTAX InetAddressType
                        MAX-ACCESS read-only
                        STATUS current
                        DESCRIPTION
                                "Type of Neighbor Address referred to this session"
                        ::= { fkBFDSessionInfoEntry 1 }

                
                -- 1.3.6.1.4.1.10428 9 1.101.11.10.3.1.1.1.2
                fkBFDSessionNeighAddrValue OBJECT-TYPE
                        SYNTAX InetAddress
                        MAX-ACCESS read-only
                        STATUS current
                        DESCRIPTION
                                "Value of Neighbor Address referred to this session."
                        ::= { fkBFDSessionInfoEntry 2 }

                
                -- 1.3.6.1.4.1.10428 9 1.101.11.10.3.1.1.1.3
                fkBFDSessionRegProtocols OBJECT-TYPE
                        SYNTAX BITS
                                {
                                ospfv2(0),
                                ospfv3(1),
                                vrrp4(2),
                                vrrp6(3)
                                }
                        MAX-ACCESS read-only
                        STATUS current
                        DESCRIPTION
                                "Value of Neighbor Address referred to this session."
                        ::= { fkBFDSessionInfoEntry 3 }

                
                -- 1.3.6.1.4.1.10428 9 1.101.11.10.3.1.1.1.4
                fkBFDSessionLocalDiscr OBJECT-TYPE
                        SYNTAX Unsigned32
                        MAX-ACCESS read-only
                        STATUS current
                        DESCRIPTION
                                "Discriminator of this session."
                        ::= { fkBFDSessionInfoEntry 4 }

                
                -- 1.3.6.1.4.1.10428 9 1.101.11.10.3.1.1.1.5
                fkBFDSessionRemoteDiscr OBJECT-TYPE
                        SYNTAX Unsigned32
                        MAX-ACCESS read-only
                        STATUS current
                        DESCRIPTION
                                "Discriminator of remote session neighboring this session."
                        ::= { fkBFDSessionInfoEntry 5 }

                
                -- 1.3.6.1.4.1.10428 9 1.101.11.10.3.1.1.1.6
                fkBFDSessionDetecMultiplier OBJECT-TYPE
                        SYNTAX INTEGER (1..63)
                        MAX-ACCESS read-only
                        STATUS current
                        DESCRIPTION
                                "Detect Multiplier value which this session used.
                                default: 3"
                        ::= { fkBFDSessionInfoEntry 6 }

                
                -- 1.3.6.1.4.1.10428 9 1.101.11.10.3.1.1.1.7
                fkBFDSessionStatus OBJECT-TYPE
                        SYNTAX INTEGER
                                {
                                adminDown(0),
                                down(1),
                                init(2),
                                up(3),
                                disabled(4)
                                }
                        MAX-ACCESS read-only
                        STATUS current
                        DESCRIPTION
                                "Status of this session.
                                AdminDown(0) is same as disabled(4)."
                        ::= { fkBFDSessionInfoEntry 7 }

                
                -- 1.3.6.1.4.1.10428 9 1.101.11.10.3.1.1.1.8
                fkBFDSessionEchoUsage OBJECT-TYPE
                        SYNTAX INTEGER
                                {
                                notUsing(0),
                                using(1)
                                }
                        MAX-ACCESS read-only
                        STATUS current
                        DESCRIPTION
                                "Determine whether this session use or not echo function."
                        ::= { fkBFDSessionInfoEntry 8 }

                
                -- 1.3.6.1.4.1.10428 9 1.101.11.10.3.1.1.1.9
                fkBFDSessionUptime OBJECT-TYPE
                        SYNTAX TimeTicks
                        MAX-ACCESS read-only
                        STATUS current
                        DESCRIPTION
                                "The time since this session’s status changed into ‘Up’."
                        ::= { fkBFDSessionInfoEntry 9 }

                
                -- 1.3.6.1.4.1.10428 9 1.101.11.10.3.2
                fkBFDSessionStats OBJECT IDENTIFIER ::= { fkBFDSession 2 }

                
                -- 1.3.6.1.4.1.10428 9 1.101.11.10.3.2.1
                fkBFDSessionStatsTable OBJECT-TYPE
                        SYNTAX SEQUENCE OF FkBFDSessionStatsEntry
                        MAX-ACCESS not-accessible
                        STATUS current
                        DESCRIPTION
                                "Description."
                        ::= { fkBFDSessionStats 1 }

                
                -- 1.3.6.1.4.1.10428 9 1.101.11.10.3.2.1.1
                fkBFDSessionStatsEntry OBJECT-TYPE
                        SYNTAX FkBFDSessionStatsEntry
                        MAX-ACCESS not-accessible
                        STATUS current
                        DESCRIPTION
                                "Description."
                        INDEX { fkNetIfIndex, fkBFDSessionNeighAddrType, fkBFDSessionNeighAddrValue }
                        ::= { fkBFDSessionStatsTable 1 }

                
                FkBFDSessionStatsEntry ::=
                        SEQUENCE { 
                                fkBFDSessionStatsHolddownTime
                                        Unsigned32,
                                fkBFDSessionStatsHolddownExpires
                                        Unsigned32,
                                fkBFDSessionStatsHolddownHitCount
                                        Unsigned32,
                                fkBFDSessionStatsHelloTime
                                        Unsigned32,
                                fkBFDSessionStatsHelloHitCount
                                        Unsigned32,
                                fkBFDSessionStatsRxCount
                                        Unsigned32,
                                fkBFDSessionStatsRxAvgInterval
                                        Unsigned32,
                                fkBFDSessionStatsRxMinInterval
                                        Unsigned32,
                                fkBFDSessionStatsRxMaxInterval
                                        Unsigned32,
                                fkBFDSessionStatsTxCount
                                        Unsigned32,
                                fkBFDSessionStatsTxAvgInterval
                                        Unsigned32,
                                fkBFDSessionStatsTxMinInterval
                                        Unsigned32,
                                fkBFDSessionStatsTxMaxInterval
                                        Unsigned32,
                                fkBFDSessionStatsEchoRxCount
                                        Unsigned32,
                                fkBFDSessionStatsEchoRxAvgInterval
                                        Unsigned32,
                                fkBFDSessionStatsEchoRxMinInterval
                                        Unsigned32,
                                fkBFDSessionStatsEchoRxMaxInterval
                                        Unsigned32,
                                fkBFDSessionStatsEchoTxCount
                                        Unsigned32,
                                fkBFDSessionStatsEchoTxAvgInterval
                                        Unsigned32,
                                fkBFDSessionStatsEchoTxMinInterva
                                        Unsigned32,
                                fkBFDSessionStatsEchoTxMaxInterval
                                        Unsigned32
                         }

                -- 1.3.6.1.4.1.10428 9 1.101.11.10.3.2.1.1.1
                fkBFDSessionStatsHolddownTime OBJECT-TYPE
                        SYNTAX Unsigned32
                        MAX-ACCESS read-only
                        STATUS current
                        DESCRIPTION
                                "Type of Neighbor Address referred to this session."
                        ::= { fkBFDSessionStatsEntry 1 }

                
                -- 1.3.6.1.4.1.10428 9 1.101.11.10.3.2.1.1.2
                fkBFDSessionStatsHolddownExpires OBJECT-TYPE
                        SYNTAX Unsigned32
                        MAX-ACCESS read-only
                        STATUS current
                        DESCRIPTION
                                "The time remaining before this entry change into down status without receiving hello in unit of milliseconds."
                        ::= { fkBFDSessionStatsEntry 2 }

                
                -- 1.3.6.1.4.1.10428 9 1.101.11.10.3.2.1.1.3
                fkBFDSessionStatsHolddownHitCount OBJECT-TYPE
                        SYNTAX Unsigned32
                        MAX-ACCESS read-only
                        STATUS current
                        DESCRIPTION
                                "Hit Count whose this session status chang into down."
                        ::= { fkBFDSessionStatsEntry 3 }

                
                -- 1.3.6.1.4.1.10428 9 1.101.11.10.3.2.1.1.4
                fkBFDSessionStatsHelloTime OBJECT-TYPE
                        SYNTAX Unsigned32
                        MAX-ACCESS read-only
                        STATUS current
                        DESCRIPTION
                                "The time is when it expects next hello, after receiving that in unit of milliseconds."
                        ::= { fkBFDSessionStatsEntry 4 }

                
                -- 1.3.6.1.4.1.10428 9 1.101.11.10.3.2.1.1.5
                fkBFDSessionStatsHelloHitCount OBJECT-TYPE
                        SYNTAX Unsigned32
                        MAX-ACCESS read-only
                        STATUS current
                        DESCRIPTION
                                "Hit Count whose this session received."
                        ::= { fkBFDSessionStatsEntry 5 }

                
                -- 1.3.6.1.4.1.10428 9 1.101.11.10.3.2.1.1.6
                fkBFDSessionStatsRxCount OBJECT-TYPE
                        SYNTAX Unsigned32
                        MAX-ACCESS read-only
                        STATUS current
                        DESCRIPTION
                                "Hit Count whose this session received control packet."
                        ::= { fkBFDSessionStatsEntry 6 }

                
                -- 1.3.6.1.4.1.10428 9 1.101.11.10.3.2.1.1.7
                fkBFDSessionStatsRxAvgInterval OBJECT-TYPE
                        SYNTAX Unsigned32
                        MAX-ACCESS read-only
                        STATUS current
                        DESCRIPTION
                                "Average interval whose this session received control packet."
                        ::= { fkBFDSessionStatsEntry 7 }

                
                -- 1.3.6.1.4.1.10428 9 1.101.11.10.3.2.1.1.8
                fkBFDSessionStatsRxMinInterval OBJECT-TYPE
                        SYNTAX Unsigned32
                        MAX-ACCESS read-only
                        STATUS current
                        DESCRIPTION
                                "Minimum interval whose this session received control packet."
                        ::= { fkBFDSessionStatsEntry 8 }

                
                -- 1.3.6.1.4.1.10428 9 1.101.11.10.3.2.1.1.9
                fkBFDSessionStatsRxMaxInterval OBJECT-TYPE
                        SYNTAX Unsigned32
                        MAX-ACCESS read-only
                        STATUS current
                        DESCRIPTION
                                "Maximum interval whose this session received control packet."
                        ::= { fkBFDSessionStatsEntry 9 }

                
                -- 1.3.6.1.4.1.10428 9 1.101.11.10.3.2.1.1.10
                fkBFDSessionStatsTxCount OBJECT-TYPE
                        SYNTAX Unsigned32
                        MAX-ACCESS read-only
                        STATUS current
                        DESCRIPTION
                                "Hit Count whose this session send control packet."
                        ::= { fkBFDSessionStatsEntry 10 }

                
                -- 1.3.6.1.4.1.10428 9 1.101.11.10.3.2.1.1.11
                fkBFDSessionStatsTxAvgInterval OBJECT-TYPE
                        SYNTAX Unsigned32
                        MAX-ACCESS read-only
                        STATUS current
                        DESCRIPTION
                                "Average interval whose this session sent control packet."
                        ::= { fkBFDSessionStatsEntry 11 }

                
                -- 1.3.6.1.4.1.10428 9 1.101.11.10.3.2.1.1.12
                fkBFDSessionStatsTxMinInterval OBJECT-TYPE
                        SYNTAX Unsigned32
                        MAX-ACCESS read-only
                        STATUS current
                        DESCRIPTION
                                "Minimum interval whose this session sent control packet."
                        ::= { fkBFDSessionStatsEntry 12 }

                
                -- 1.3.6.1.4.1.10428 9 1.101.11.10.3.2.1.1.13
                fkBFDSessionStatsTxMaxInterval OBJECT-TYPE
                        SYNTAX Unsigned32
                        MAX-ACCESS read-only
                        STATUS current
                        DESCRIPTION
                                "Maximum interval whose this session received control packet."
                        ::= { fkBFDSessionStatsEntry 13 }

                
                -- 1.3.6.1.4.1.10428 9 1.101.11.10.3.2.1.1.14
                fkBFDSessionStatsEchoRxCount OBJECT-TYPE
                        SYNTAX Unsigned32
                        MAX-ACCESS read-only
                        STATUS current
                        DESCRIPTION
                                "Hit Count whose this session received echo packet"
                        ::= { fkBFDSessionStatsEntry 14 }

                
                -- 1.3.6.1.4.1.10428 9 1.101.11.10.3.2.1.1.15
                fkBFDSessionStatsEchoRxAvgInterval OBJECT-TYPE
                        SYNTAX Unsigned32
                        MAX-ACCESS read-only
                        STATUS current
                        DESCRIPTION
                                "Average interval whose this session received echo packet"
                        ::= { fkBFDSessionStatsEntry 15 }

                
                -- 1.3.6.1.4.1.10428 9 1.101.11.10.3.2.1.1.16
                fkBFDSessionStatsEchoRxMinInterval OBJECT-TYPE
                        SYNTAX Unsigned32
                        MAX-ACCESS read-only
                        STATUS current
                        DESCRIPTION
                                "Minimum interval whose this session received echo packet"
                        ::= { fkBFDSessionStatsEntry 16 }

                
                -- 1.3.6.1.4.1.10428 9 1.101.11.10.3.2.1.1.17
                fkBFDSessionStatsEchoRxMaxInterval OBJECT-TYPE
                        SYNTAX Unsigned32
                        MAX-ACCESS read-only
                        STATUS current
                        DESCRIPTION
                                "Maximum interval whose this session received echo packet"
                        ::= { fkBFDSessionStatsEntry 17 }

                
                -- 1.3.6.1.4.1.10428 9 1.101.11.10.3.2.1.1.18
                fkBFDSessionStatsEchoTxCount OBJECT-TYPE
                        SYNTAX Unsigned32
                        MAX-ACCESS read-only
                        STATUS current
                        DESCRIPTION
                                "Hit Count whose this session send echo packet
                                "
                        ::= { fkBFDSessionStatsEntry 18 }

                
                -- 1.3.6.1.4.1.10428 9 1.101.11.10.3.2.1.1.19
                fkBFDSessionStatsEchoTxAvgInterval OBJECT-TYPE
                        SYNTAX Unsigned32
                        MAX-ACCESS read-only
                        STATUS current
                        DESCRIPTION
                                "Average interval whose this session sent echo packet."
                        ::= { fkBFDSessionStatsEntry 19 }

                
                -- 1.3.6.1.4.1.10428 9 1.101.11.10.3.2.1.1.20
                fkBFDSessionStatsEchoTxMinInterva OBJECT-TYPE
                        SYNTAX Unsigned32
                        MAX-ACCESS read-only
                        STATUS current
                        DESCRIPTION
                                "Minimum interval whose this session sent echo packet."
                        ::= { fkBFDSessionStatsEntry 20 }

                
                -- 1.3.6.1.4.1.10428 9 1.101.11.10.3.2.1.1.21
                fkBFDSessionStatsEchoTxMaxInterval OBJECT-TYPE
                        SYNTAX Unsigned32
                        MAX-ACCESS read-only
                        STATUS current
                        DESCRIPTION
                                "Maximum interval whose this session received echo packet."
                        ::= { fkBFDSessionStatsEntry 21 }

                
                -- 1.3.6.1.4.1.10428 9 1.101.11.10.3.3
                fkBFDSessionLocal OBJECT IDENTIFIER ::= { fkBFDSession 3 }

                
                -- 1.3.6.1.4.1.10428 9 1.101.11.10.3.3.1
                fkBFDSessionLocalTable OBJECT-TYPE
                        SYNTAX SEQUENCE OF FkBFDSessionLocalEntry
                        MAX-ACCESS not-accessible
                        STATUS current
                        DESCRIPTION
                                "Description."
                        ::= { fkBFDSessionLocal 1 }

                
                -- 1.3.6.1.4.1.10428 9 1.101.11.10.3.3.1.1
                fkBFDSessionLocalEntry OBJECT-TYPE
                        SYNTAX FkBFDSessionLocalEntry
                        MAX-ACCESS not-accessible
                        STATUS current
                        DESCRIPTION
                                "Description."
                        INDEX { fkNetIfIndex, fkBFDSessionNeighAddrType, fkBFDSessionNeighAddrValue }
                        ::= { fkBFDSessionLocalTable 1 }

                
                FkBFDSessionLocalEntry ::=
                        SEQUENCE { 
                                fkBFDSessionLocalDiag
                                        INTEGER,
                                fkBFDSessionLocalState
                                        INTEGER,
                                fkBFDSessionLocalFlags
                                        BITS,
                                fkBFDSessionLocalMultiplier
                                        INTEGER,
                                fkBFDSessionLocalMinTxInterval
                                        Unsigned32,
                                fkBFDSessionLocalMinRxInterval
                                        Unsigned32,
                                fkBFDSessionLocalMinEchoInterval
                                        Unsigned32
                         }

                -- 1.3.6.1.4.1.10428 9 1.101.11.10.3.3.1.1.1
                fkBFDSessionLocalDiag OBJECT-TYPE
                        SYNTAX INTEGER
                                {
                                noDiag(0),
                                detectExpired(1),
                                echoFailed(2),
                                neighDownAlarm(3),
                                fwdPlaneReset(4),
                                pathDown(5),
                                concatPathDown(6),
                                adminDown(7),
                                reverseConcatDown(8),
                                reserved(9)
                                }
                        MAX-ACCESS read-only
                        STATUS current
                        DESCRIPTION
                                "Value of State field of this session’s control packet."
                        ::= { fkBFDSessionLocalEntry 1 }

                
                -- 1.3.6.1.4.1.10428 9 1.101.11.10.3.3.1.1.2
                fkBFDSessionLocalState OBJECT-TYPE
                        SYNTAX INTEGER
                                {
                                adminDown(0),
                                donw(1),
                                init(2),
                                up(3)
                                }
                        MAX-ACCESS read-only
                        STATUS current
                        DESCRIPTION
                                "Value of Diag field of this session’s control packet"
                        ::= { fkBFDSessionLocalEntry 2 }

                
                -- 1.3.6.1.4.1.10428 9 1.101.11.10.3.3.1.1.3
                fkBFDSessionLocalFlags OBJECT-TYPE
                        SYNTAX BITS
                                {
                                poll(0),
                                final(1),
                                controlIndependent(2),
                                authPresent(3),
                                demand(4),
                                multipoint(5)
                                }
                        MAX-ACCESS read-only
                        STATUS current
                        DESCRIPTION
                                "Value of Flags field of this session’s control packet."
                        ::= { fkBFDSessionLocalEntry 3 }

                
                -- 1.3.6.1.4.1.10428 9 1.101.11.10.3.3.1.1.4
                fkBFDSessionLocalMultiplier OBJECT-TYPE
                        SYNTAX INTEGER (1..63)
                        MAX-ACCESS read-only
                        STATUS current
                        DESCRIPTION
                                "Value of MinTxInterval field of this session’s control packet in unit of microseconds."
                        ::= { fkBFDSessionLocalEntry 4 }

                
                -- 1.3.6.1.4.1.10428 9 1.101.11.10.3.3.1.1.5
                fkBFDSessionLocalMinTxInterval OBJECT-TYPE
                        SYNTAX Unsigned32
                        MAX-ACCESS read-only
                        STATUS current
                        DESCRIPTION
                                "Value of MinTxInterval field of this session’s control packet in unit of microseconds."
                        ::= { fkBFDSessionLocalEntry 5 }

                
                -- 1.3.6.1.4.1.10428 9 1.101.11.10.3.3.1.1.6
                fkBFDSessionLocalMinRxInterval OBJECT-TYPE
                        SYNTAX Unsigned32
                        MAX-ACCESS read-only
                        STATUS current
                        DESCRIPTION
                                "Value of MinRxInterval field of this session’s control packet in unit of microseconds."
                        ::= { fkBFDSessionLocalEntry 6 }

                
                -- 1.3.6.1.4.1.10428 9 1.101.11.10.3.3.1.1.7
                fkBFDSessionLocalMinEchoInterval OBJECT-TYPE
                        SYNTAX Unsigned32
                        MAX-ACCESS read-only
                        STATUS current
                        DESCRIPTION
                                "Value of MinEchoInterval field of this session’s control packet in unit of microseconds."
                        ::= { fkBFDSessionLocalEntry 7 }

                
                -- 1.3.6.1.4.1.10428 9 1.101.11.10.3.4
                fkBFDSessionRemote OBJECT IDENTIFIER ::= { fkBFDSession 4 }

                
                -- 1.3.6.1.4.1.10428 9 1.101.11.10.3.4.1
                fkBFDSessionRemoteTable OBJECT-TYPE
                        SYNTAX SEQUENCE OF FkBFDSessionRemoteEntry
                        MAX-ACCESS not-accessible
                        STATUS current
                        DESCRIPTION
                                "Description."
                        ::= { fkBFDSessionRemote 1 }

                
                -- 1.3.6.1.4.1.10428 9 1.101.11.10.3.4.1.1
                fkBFDSessionRemoteEntry OBJECT-TYPE
                        SYNTAX FkBFDSessionRemoteEntry
                        MAX-ACCESS not-accessible
                        STATUS current
                        DESCRIPTION
                                "Description."
                        INDEX { fkNetIfIndex, fkBFDSessionNeighAddrType, fkBFDSessionNeighAddrValue }
                        ::= { fkBFDSessionRemoteTable 1 }

                
                FkBFDSessionRemoteEntry ::=
                        SEQUENCE { 
                                fkBFDSessionRemoteDiag
                                        INTEGER,
                                fkBFDSessionRemoteState
                                        INTEGER,
                                fkBFDSessionremoteFlags
                                        BITS,
                                fkBFDSessionRemoteMultiplier
                                        INTEGER,
                                fkBFDSessionRemoteMinTxInterval
                                        Unsigned32,
                                fkBFDSessionRemoteMinRxInterval
                                        Unsigned32,
                                fkBFDSessionRemoteMinEchoInterval
                                        Unsigned32
                         }

                -- 1.3.6.1.4.1.10428 9 1.101.11.10.3.4.1.1.1
                fkBFDSessionRemoteDiag OBJECT-TYPE
                        SYNTAX INTEGER
                                {
                                noDiag(0),
                                detectExpired(1),
                                echoFailed(2),
                                neighDownAlarm(3),
                                fwdPlaneReset(4),
                                pathDown(5),
                                concatPathDown(6),
                                adminDown(7),
                                reverseConcatDown(8),
                                reserved(9)
                                }
                        MAX-ACCESS read-only
                        STATUS current
                        DESCRIPTION
                                "Value of State field of remote session’s control packet."
                        ::= { fkBFDSessionRemoteEntry 1 }

                
                -- 1.3.6.1.4.1.10428 9 1.101.11.10.3.4.1.1.2
                fkBFDSessionRemoteState OBJECT-TYPE
                        SYNTAX INTEGER
                                {
                                adminDown(0),
                                donw(1),
                                init(2),
                                up(3)
                                }
                        MAX-ACCESS read-only
                        STATUS current
                        DESCRIPTION
                                "Value of Diag field of remote session’s control packet"
                        ::= { fkBFDSessionRemoteEntry 2 }

                
                -- 1.3.6.1.4.1.10428 9 1.101.11.10.3.4.1.1.3
                fkBFDSessionremoteFlags OBJECT-TYPE
                        SYNTAX BITS
                                {
                                poll(0),
                                final(1),
                                controlIndependent(2),
                                authPresent(3),
                                demand(4),
                                multipoint(5)
                                }
                        MAX-ACCESS read-only
                        STATUS current
                        DESCRIPTION
                                "Value of Flags field of remote session’s control packet."
                        ::= { fkBFDSessionRemoteEntry 3 }

                
                -- 1.3.6.1.4.1.10428 9 1.101.11.10.3.4.1.1.4
                fkBFDSessionRemoteMultiplier OBJECT-TYPE
                        SYNTAX INTEGER (1..63)
                        MAX-ACCESS read-only
                        STATUS current
                        DESCRIPTION
                                "Value of MinTxInterval field of this session’s control packet in unit of microseconds."
                        ::= { fkBFDSessionRemoteEntry 4 }

                
                -- 1.3.6.1.4.1.10428 9 1.101.11.10.3.4.1.1.5
                fkBFDSessionRemoteMinTxInterval OBJECT-TYPE
                        SYNTAX Unsigned32
                        MAX-ACCESS read-only
                        STATUS current
                        DESCRIPTION
                                "Value of MinTxInterval field of remote session’s control packet in unit of microseconds."
                        ::= { fkBFDSessionRemoteEntry 5 }

                
                -- 1.3.6.1.4.1.10428 9 1.101.11.10.3.4.1.1.6
                fkBFDSessionRemoteMinRxInterval OBJECT-TYPE
                        SYNTAX Unsigned32
                        MAX-ACCESS read-only
                        STATUS current
                        DESCRIPTION
                                "Value of MinRxInterval field of remote session’s control packet in unit of microseconds."
                        ::= { fkBFDSessionRemoteEntry 6 }

                
                -- 1.3.6.1.4.1.10428 9 1.101.11.10.3.4.1.1.7
                fkBFDSessionRemoteMinEchoInterval OBJECT-TYPE
                        SYNTAX Unsigned32
                        MAX-ACCESS read-only
                        STATUS current
                        DESCRIPTION
                                "Value of MinEchoInterval field of remote session’s control packet in unit of microseconds."
                        ::= { fkBFDSessionRemoteEntry 7 }

                
                -- 1.3.6.1.4.1.10428 9 1.101.11.10.4
                fkBFDStaticGw OBJECT IDENTIFIER ::= { fkBFD 4 }

                
                -- 1.3.6.1.4.1.10428 9 1.101.11.10.4.1
                fkBFDStaticGwTable OBJECT-TYPE
                        SYNTAX SEQUENCE OF FkBFDStaticGwEntry
                        MAX-ACCESS not-accessible
                        STATUS current
                        DESCRIPTION
                                "Description."
                        ::= { fkBFDStaticGw 1 }

                
                -- 1.3.6.1.4.1.10428 9 1.101.11.10.4.1.1
                fkBFDStaticGwEntry OBJECT-TYPE
                        SYNTAX FkBFDStaticGwEntry
                        MAX-ACCESS not-accessible
                        STATUS current
                        DESCRIPTION
                                "Description."
                        INDEX { fkNetIfIndex, fkBFDStaticGwAddrType, fkBFDStaticGwAddr }
                        ::= { fkBFDStaticGwTable 1 }

                
                FkBFDStaticGwEntry ::=
                        SEQUENCE { 
                                fkBFDStaticGwAddrType
                                        InetAddressType,
                                fkBFDStaticGwAddr
                                        InetAddress
                         }

                -- 1.3.6.1.4.1.10428 9 1.101.11.10.4.1.1.1
                fkBFDStaticGwAddrType OBJECT-TYPE
                        SYNTAX InetAddressType
                        MAX-ACCESS read-write
                        STATUS current
                        DESCRIPTION
                                "The BFD static Gateway address type.  Only ipv4(1)."
                        ::= { fkBFDStaticGwEntry 1 }

                
                -- 1.3.6.1.4.1.10428 9 1.101.11.10.4.1.1.2
                fkBFDStaticGwAddr OBJECT-TYPE
                        SYNTAX InetAddress
                        MAX-ACCESS read-write
                        STATUS current
                        DESCRIPTION
                                "The BFD static Gateway address. 4bytes"
                        ::= { fkBFDStaticGwEntry 2 }

                
                -- 1.3.6.1.4.1.10428 9 1.101.11.10.4.2
                fkBFDStaticGwControl OBJECT IDENTIFIER ::= { fkBFDStaticGw 2 }

                
                -- 1.3.6.1.4.1.10428 9 1.101.11.10.4.2.1
                fkBFDStaticGwControlRequest OBJECT-TYPE
                        SYNTAX INTEGER
                                {
                                addBfdStaticGw(1),
                                delBfdStaticGw(2)
                                }
                        MAX-ACCESS read-write
                        STATUS current
                        DESCRIPTION
                                "Description."
                        ::= { fkBFDStaticGwControl 1 }

                
                -- 1.3.6.1.4.1.10428 9 1.101.11.10.4.2.2
                fkBFDStaticGwControlStatus OBJECT-TYPE
                        SYNTAX FkControlStatusType
                        MAX-ACCESS read-only
                        STATUS current
                        DESCRIPTION
                                "Description."
                        ::= { fkBFDStaticGwControl 2 }

                
                -- 1.3.6.1.4.1.10428 9 1.101.11.10.4.2.3
                fkBFDStaticGwControlTimer OBJECT-TYPE
                        SYNTAX Gauge32
                        MAX-ACCESS read-write
                        STATUS current
                        DESCRIPTION
                                "Description."
                        ::= { fkBFDStaticGwControl 3 }

                
                -- 1.3.6.1.4.1.10428 9 1.101.11.10.4.2.4
                fkBFDStaticGwControlTimeStamp OBJECT-TYPE
                        SYNTAX TimeTicks
                        MAX-ACCESS read-only
                        STATUS current
                        DESCRIPTION
                                "Description."
                        ::= { fkBFDStaticGwControl 4 }

                
                -- 1.3.6.1.4.1.10428 9 1.101.11.10.4.2.5
                fkBFDStaticGwControlReqResult OBJECT-TYPE
                        SYNTAX FkControlRequestResultType
                        MAX-ACCESS read-only
                        STATUS current
                        DESCRIPTION
                                "Description."
                        ::= { fkBFDStaticGwControl 5 }

                
-- The index of fkNetIfTable.
                -- 1.3.6.1.4.1.10428 9 1.101.11.10.4.2.6
                fkBFDStaticGwControlNetIfIndex OBJECT-TYPE
                        SYNTAX Integer32
                        MAX-ACCESS read-write
                        STATUS current
                        DESCRIPTION
                                "Description."
                        ::= { fkBFDStaticGwControl 6 }

                
-- The BFD static Gateway address type.  Only ipv4(1).
                -- 1.3.6.1.4.1.10428 9 1.101.11.10.4.2.7
                fkBFDStaticGwControlGwAddrType OBJECT-TYPE
                        SYNTAX InetAddressType
                        MAX-ACCESS read-write
                        STATUS current
                        DESCRIPTION
                                "Description."
                        ::= { fkBFDStaticGwControl 7 }

                
-- The BFD static Gateway address. 4bytes
                -- 1.3.6.1.4.1.10428 9 1.101.11.10.4.2.8
                fkBFDStaticGwControlGwAddr OBJECT-TYPE
                        SYNTAX InetAddress
                        MAX-ACCESS read-write
                        STATUS current
                        DESCRIPTION
                                "Description."
                        ::= { fkBFDStaticGwControl 8 }

                
                -- 1.3.6.1.4.1.10428 9 1.101.11.10.4.3
                fkBFDStaticGwNotification OBJECT IDENTIFIER ::= { fkBFDStaticGw 3 }

                
-- fkBFDStaticGwControlNetIfIndex
-- fkBFDStaticGwControlGwAddrType
-- fkBFDStaticGwControlGwAddr
                -- 1.3.6.1.4.1.10428 9 1.101.11.10.4.3.1
                fkBFDStaticGwAdded NOTIFICATION-TYPE
                        OBJECTS { fkBFDStaticGwControlRequest, fkBFDStaticGwControlTimer, fkBFDStaticGwControlReqResult, fkBFDStaticGwControlNetIfIndex, fkBFDStaticGwControlGwAddr, 
                                fkBFDStaticGwControlGwAddrType }
                        STATUS current
                        DESCRIPTION 
                                "Description."
                        ::= { fkBFDStaticGwNotification 1 }

                
-- fkBFDStaticGwControlNetIfIndex
-- fkBFDStaticGwControlGwAddrType
-- fkBFDStaticGwControlGwAddr
                -- 1.3.6.1.4.1.10428 9 1.101.11.10.4.3.2
                fkBFDStaticGwDeleted NOTIFICATION-TYPE
                        OBJECTS { fkBFDStaticGwControlRequest, fkBFDStaticGwControlTimeStamp, fkBFDStaticGwControlReqResult, fkBFDStaticGwControlNetIfIndex, fkBFDStaticGwControlGwAddr, 
                                fkBFDStaticGwControlGwAddrType }
                        STATUS current
                        DESCRIPTION 
                                "Description."
                        ::= { fkBFDStaticGwNotification 2 }

                
                -- 1.3.6.1.4.1.10428 9 1.101.11.11
                fkNetworkGroup OBJECT-GROUP
                        OBJECTS { fkNetIfIndex, fkNetIfName, fkNetIfDescription, fkNetIfTableIndex, fkNetIfAdminState, 
                                fkNetIfOperState, fkNetIfMulticast, fkNetIfControlRequest, fkNetIfControlStatus, fkNetIfControlTimer, 
                                fkNetIfControlTimeStamp, fkNetIfControlReqResult, fkNetIfControlIndex, fkNetIfControlDescription, fkNetIfControlAdminState, 
                                fkNetIfControlMulticast, fkIpAddrValue, fkIpAddrMask, fkIpAddrBcast, fkIpAddrControlRequest, 
                                fkIpAddrControlStatus, fkIpAddrControlTimer, fkIpAddrControlTimeStamp, fkIpAddrControlReqResult, fkIpAddrControlNetIfIndex, 
                                fkIpAddrControlValue, fkIpAddrControlMask, fkArpIpAddress, fkArpPhyAddress, fkArpPortIndex, 
                                fkArpHwType, fkArpControlRequest, fkArpControlStatus, fkArpControlTimer, fkArpControlTimeStamp, 
                                fkArpControlReqResult, fkArpControlIpAddress, fkArpControlPhyAddress, fkRouteDstAddress, fkRouteDstMask, 
                                fkRouteGateway, fkRouteInterface, fkRouteType, fkRouteProto, fkRouteMetric, 
                                fkRouteActive, fkRouteBindingSrcAddr, fkRouteDistance, fkRouteControlRequest, fkRouteControlStatus, 
                                fkRouteControlTimer, fkRouteControlTimeStamp, fkRouteControlReqResult, fkRouteControlDstAddress, fkRouteControlDstMask, 
                                fkRouteControlGateway, fkRouteControlInterface, fkRouteControlBindingSrcAddr, fkRouteControlDistance, fkDhcpClIpAddr, 
                                fkDhcpClState, fkDhcpClControlRequest, fkDhcpClControlStatus, fkDhcpClControlTimer, fkDhcpClControlTimeStamp, 
                                fkDhcpClControlReqResult, fkDhcpClControlUpdateIP, fkNetIfRegState, fkNetIfMtu, fkNetIfIpSetMode, 
                                fkNetIfIpMartianFilter, fkNetIfControlRegState, fkNetIfControlMtu, fkNetIfControlIpMartianFilter, fkIpAddrFlag, 
                                fkIpAddrScope, fkIpAddrControlFlag, fkIpAddrControlScope, fkArpState, fkArpHwUsed, 
                                fkArpUsedTime, fkArpControlNetIfIndex, fkArpControlState, fkArpControlMask, fkRouteSubtype, 
                                fkRouteNexthopStatus, fkRouteRibStatus, fkNetworkArpAgingTime, fkNetworkControlRequest, fkNetworkControlStatus, 
                                fkNetworkControlTimer, fkNetworkControlReqResult, fkNetworkControlTimeStamp, fkNetworkControlArpAgingTime, fkNetIfUpCnt, 
                                fkNetIfDownCnt, fkNetIfLinkUpTime, fkNetIfElapsedTimeAfterClearStats, fkNetIfBindingVRFName, fkNetIfControlBindingVRFName, 
                                fkRouteVRFIndex, fkRouteControlVRFIndex, fkTunnelIfIndex, fkTunnelIfLocalAddress, fkTunnelIfRemoteAddress, 
                                fkTunnelIfMode, fkTunnelIfTTL, fkTunnelIfDscpMode, fkTunnelIfDscp, fkTunnelIfKeepaliveInterval, 
                                fkTunnelIfKeepaliveRetry, fkTunnelIfControlRequest, fkTunnelIfControlStatus, fkTunnelIfControlTimer, fkTunnelIfControlTimeStamp, 
                                fkTunnelIfControlReqResult, fkTunnelIfControlIndex, fkTunnelIfControlLocalAddress, fkTunnelIfControlRemoteAddress, fkTunnelIfControlMode, 
                                fkTunnelIfControlTTL, fkTunneIflControlDscpMode, fkTunneIflControlDscp, fkTunnelIfControlKeepaliveInterval, fkTunneIflControlKeepaliveRetry, 
                                fkTunnelAddressValue, fkTunnelAddressMask, fkTunnelIpAddrBcast, fkTunnelAddressFlag, fkTunnelAddressScope, 
                                fkTunnelAddressControlRequest, fkTunnelAddressControlStatus, fkTunnelAddressControlTimer, fkTunnelAddressControlTimeStamp, fkTunnelAddressControlReqResult, 
                                fkTunnelAddressControlTunnelIfIndex, fkTunnelAddressControlValue, fkTunnelAddressControlMask, fkTunnelAddressControlFlag, fkTunnelAddressControlScope, 
                                fkIpVRFIndex, fkIpVRFName, fkIpVRFControlRequest, fkIpVRFControlStatus, fkIpVRFControlTimer, 
                                fkIpVRFControlTimeStamp, fkIpVRFControlReqResult, fkIpVRFControlName, fkNetIfOnFailUseVRF, fkNetIfControlOnFailUseVRF, 
                                fkTunnelIfPathMtuDiscovery, fkTunnelIfVRFName, fkTunnelIfBindingPorts, fkTunnelIfControlPathMtuDiscovery, fkTunnelIfControlVRFName, 
                                fkIpVRFDesignatedPorts, fkIpVRFControlDesignatedPorts, fkIpVRFSelectionSrcIndex, fkIpVRFSelectionSrcAddr, fkIpVRFSelectionSrcMask, 
                                fkIpVRFSelectionSrcVRFName, fkIpVRFSelectionSrcControlRequest, fkIpVRFSelectionSrcControlStatus, fkIpVRFSelectionSrcControlTimer, fkIpVRFSelectionSrcControlTimeStamp, 
                                fkIpVRFSelectionSrcControlReqResult, fkIpVRFSelectionSrcControlAddr, fkIpVRFSelectionSrcControlMask, fkIpVRFSelectionSrcControlVRFName, fkNetIfIpUnreachability, 
                                fkNetIfControlIpUnreachability, fkIpVRFRouterId, fkIpVRFDescription, fkIpVRFControlRouterId, fkIpVRFControlDescription, 
                                fkBFDEnable, fkBFDEchoEnable, fkBFDSlowTimer, fkBFDControlRequest, fkBFDControlStatus, 
                                fkBFDControlTimer, fkBFDControlTimeStamp, fkBFDControlReqResult, fkBFDControlEnable, fkBFDControlEchoEnable, 
                                fkBFDControlSlowTimer, fkBFDIfRxInterval, fkBFDIfTxInterval, fkBFDIfDetectMulti, fkBFDIfControlRequest, 
                                fkBFDIfControlStatus, fkBFDIfControlTimer, fkBFDIfControlTimeStamp, fkBFDIfControlReqResult, fkBFDIfControlNetIfIndex, 
                                fkBFDIfControlRxInterval, fkBFDIfControlTxInterval, fkBFDIfControlDetectMulti, fkBFDSessionNeighAddrType, fkBFDSessionNeighAddrValue, 
                                fkBFDSessionRegProtocols, fkBFDSessionLocalDiscr, fkBFDSessionRemoteDiscr, fkBFDSessionDetecMultiplier, fkBFDSessionStatus, 
                                fkBFDSessionEchoUsage, fkBFDSessionUptime, fkBFDSessionStatsHolddownTime, fkBFDSessionStatsHolddownExpires, fkBFDSessionStatsHolddownHitCount, 
                                fkBFDSessionStatsHelloTime, fkBFDSessionStatsHelloHitCount, fkBFDSessionStatsRxCount, fkBFDSessionStatsRxAvgInterval, fkBFDSessionStatsRxMinInterval, 
                                fkBFDSessionStatsRxMaxInterval, fkBFDSessionStatsTxCount, fkBFDSessionStatsTxAvgInterval, fkBFDSessionStatsTxMinInterval, fkBFDSessionStatsTxMaxInterval, 
                                fkBFDSessionLocalDiag, fkBFDSessionLocalState, fkBFDSessionLocalFlags, fkBFDSessionLocalMultiplier, fkBFDSessionLocalMinTxInterval, 
                                fkBFDSessionLocalMinRxInterval, fkBFDSessionLocalMinEchoInterval, fkBFDSessionRemoteDiag, fkBFDSessionRemoteState, fkBFDSessionremoteFlags, 
                                fkBFDSessionRemoteMultiplier, fkBFDSessionRemoteMinTxInterval, fkBFDSessionRemoteMinRxInterval, fkBFDSessionRemoteMinEchoInterval, fkBFDStaticGwAddrType, 
                                fkBFDStaticGwAddr, fkBFDStaticGwControlRequest, fkBFDStaticGwControlStatus, fkBFDStaticGwControlTimer, fkBFDStaticGwControlTimeStamp, 
                                fkBFDStaticGwControlReqResult, fkBFDStaticGwControlNetIfIndex, fkBFDStaticGwControlGwAddrType, fkBFDStaticGwControlGwAddr, fkBFDSessionStatsEchoRxCount, 
                                fkBFDSessionStatsEchoRxAvgInterval, fkBFDSessionStatsEchoRxMinInterval, fkBFDSessionStatsEchoRxMaxInterval, fkBFDSessionStatsEchoTxCount, fkBFDSessionStatsEchoTxAvgInterval, 
                                fkBFDSessionStatsEchoTxMinInterva, fkBFDSessionStatsEchoTxMaxInterval, fkNetIfipRedirects, fkNetIfControlIpRedirects, fkIpAddrIpIndex, 
                                fkIpAddrUnnumUsedIp, fkIpAddrControlIpIndex, fkTunnelAddressUnnumIpIndex, fkTunnelAddressControlUnnumIpIndex, fkNetIfIpForwarding, 
                                fkNetIfControlIpForwarding, fkDhcpClControlNetIfIndex, fkDhcpClMode, fkDhcpClNetmask, fkDhcpClGateway, 
                                fkDhcpClDnsServer, fkDhcpClServer, fkDhcpClClientId, fkDhcpClClientIdStyle, fkDhcpClClassId, 
                                fkDhcpClClassIdStyle, fkDhcpClLeasetime, fkDhcpClControlMode, fkDhcpClControlClientId, fkDhcpClControlClientIdStyle, 
                                fkDhcpClControlClassId, fkDhcpClControlClassIdStyle, fkDhcpClControlLeasetime, fkTunnelAddressUnnumIfIndex, fkTunnelAddressControlUnnumIfIndex
                                 }
                        STATUS current
                        DESCRIPTION 
                                "Description."
                        ::= { fkNetwork 11 }

                
                -- 1.3.6.1.4.1.10428 9 1.101.11.12
                fkNetworkNotificationGroup NOTIFICATION-GROUP
                        NOTIFICATIONS { fkNetIfProfileChanged, fkIpAddressCreated, fkIpAddressDestroyed, fkArpEntryCreated, fkArpEntryDestroyed, 
                                fkArpTableCleared, fkRouteStaticCreated, fkRouteStaticDestroyed, fkRouteStaticProfileChanged, fkDhcpClModeChanged, 
                                fkDhcpClProfileChanged, fkTunnelIfCreated, fkTunnelIfDeleted, fkTunnelIfLocalAddressChanged, fkTunnelIfRemoteAddressChanged, 
                                fkTunnelIfModeChanged, fkTunnelIfTTLChanged, fkTunnelIfDscpChanged, fkTunnelIfKeepaliveChanged, fkTunnelAddressCreated, 
                                fkTunnelAddressDeleted, fkIpVRFCreated, fkIpVRFDeleted, fkDhcpClStateChanged, fkNetIfRegStateChanged, 
                                fkNetIfIpMartianFilterChanged, fkArpTableClearedByAddr, fkNetworkArpProfileChanged, fkNetIfBindingVRFSet, fkNetIfBindingVRFUnset, 
                                fkNetIfIpOnFailUseVRFChanged, fkTunnelIfPathMtuDiscoveryChanged, fkIpVRFDesignatedPortsSet, fkIpVRFDesignatedPortsUnset, fkIpVRFSelectionSrcSet, 
                                fkNetIfIpUnreachabilityChanged, fkIpVRFRouterIdChanged, fkIpVRFDescriptionChanged, fkBFDBaseProfileChanged, fkBFDIfProfileChanged, 
                                fkBFDStaticGwAdded, fkBFDStaticGwDeleted, fkNetIfIpRedirectsChanged, fkIpAddressIpIndexAdded, fkIpAddressIpIndexDeleted, 
                                fkTunnelAddressUnnumChanged, fkTunnelAddressUnnumDeleted, fkNetIfIpForwardingChanged, fkIpVRFSelectionSrcUnset, fkTunnelIfVRFNameSet, 
                                fkTunnelIfVRFNameUnset }
                        STATUS current
                        DESCRIPTION 
                                "Description."
                        ::= { fkNetwork 12 }

                
        
        END

--
-- fk-network-mib.mib
--
