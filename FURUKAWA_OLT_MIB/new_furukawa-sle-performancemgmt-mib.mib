--
-- fk-performancemgmt-mib.mib
-- MIB generated by MG-SOFT Visual MIB Builder Version 6.0  Build 88
-- Tuesday, September 11, 2012 at 17:10:45
--

	FK-PERFORMANCEMGMT-MIB DEFINITIONS ::= BEGIN
 
		IMPORTS
			fkMgmt			
				FROM FKOLTG1040-SMI			
			InterfaceIndex			
				FROM IF-MIB			
			OBJECT-GROUP, NOTIFICATION-GROUP			
				FROM SNMPv2-CONF			
			TimeTicks, Integer32, Unsigned32, Gauge32, Counter64, OBJECT-TYPE, MODULE-IDENTITY, NOTIFICATION-TYPE			
				FROM SNMPv2-SMI;
	
	
		-- 1.3.6.1.4.1.10428 9 1.101.5
		fkPerformanceMgmt MODULE-IDENTITY 
			LAST-UPDATED "200412291118Z"		-- December 29, 2004 at 11:18 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 5 }

		
	
--
-- Type definitions
--
	
		FkControlStatusType ::= INTEGER
			{
			idle(1),
			busy(2),
			passed(3),
			failed(4)
			}

		FkControlRequestResultType ::= INTEGER
			{
			noRequest(1),
			comExecStarted(5),
			paramFaulty(11),
			requestBusy(12),
			setDataFailed(13),
			aswTimeout(14),
			commandFailed(15),
			commandSuccessed(16)
			}

		FkStatisticsClearTableIndexType ::= INTEGER
			{
			counter(1),
			portStatisticsTable(2),
			dot1xPortStatisticsTable(3),
			lldpStatisticsTable(4)
			}

	
	
--
-- Node definitions
--
	
		-- 1.3.6.1.4.1.10428 9 1.101.5.1
		fkPortThreshold OBJECT IDENTIFIER ::= { fkPerformanceMgmt 1 }

		
--   1.3.6.1.4.1.10428 9 1.101.5.1.1
-- 1.3.6.1.4.1.10428 9 1.101.5.1.1
		-- 1.3.6.1.4.1.10428 9 1.101.5.1.1
		fkPortThresholdTable OBJECT-TYPE
			SYNTAX SEQUENCE OF FkPortThresholdEntry
			MAX-ACCESS not-accessible
			STATUS current
			DESCRIPTION
				"Description."
			::= { fkPortThreshold 1 }

		
--   1.3.6.1.4.1.10428 9 1.101.5.1.1.1
-- 1.3.6.1.4.1.10428 9 1.101.5.1.1.1
		-- 1.3.6.1.4.1.10428 9 1.101.5.1.1.1
		fkPortThresholdEntry OBJECT-TYPE
			SYNTAX FkPortThresholdEntry
			MAX-ACCESS not-accessible
			STATUS current
			DESCRIPTION
				"Description."
			INDEX { fkThresholdIndex }
			::= { fkPortThresholdTable 1 }

		
		FkPortThresholdEntry ::=
			SEQUENCE { 
				fkThresholdIndex
					INTEGER,
				fkPortThresholdUpLimit
					Integer32,
				fkPortThresholdUpSamplingInterval
					INTEGER,
				fkPortThresholdDownLimit
					Integer32,
				fkPortThresholdDownSamplingInterval
					INTEGER,
				fkPortThresholdBlockTimer
					INTEGER,
				fkPortThresholdPpsCurrLimit
					Integer32,
				fkPortThresholdPpsBlocked
					Integer32,
				fkPortThresholdPpsLimit
					Integer32,
				fkPortThresholdPpsInterval
					INTEGER,
				fkPortThresholdPpsBlockTimer
					INTEGER,
				fkPortThresholdWarnTxLimit
					Integer32,
				fkPortThresholdWarnTxInterval
					INTEGER,
				fkPortThresholdWarnTxDuration
					INTEGER,
				fkPortThresholdWarnRxLimit
					Integer32,
				fkPortThresholdWarnRxInterval
					INTEGER,
				fkPortThresholdWarnRxDuration
					INTEGER,
				fkPortThresholdAlarmTxLimit
					Integer32,
				fkPortThresholdAlarmTxInterval
					INTEGER,
				fkPortThresholdAlarmTxDuration
					INTEGER,
				fkPortThresholdAlarmRxLimit
					Integer32,
				fkPortThresholdAlarmRxInterval
					INTEGER,
				fkPortThresholdAlarmRxDuration
					INTEGER
			 }

--  1.3.6.1.4.1.10428 9 1.101.5.1.1.1.1
		-- 1.3.6.1.4.1.10428 9 1.101.5.1.1.1.1
		fkThresholdIndex OBJECT-TYPE
			SYNTAX INTEGER (1..255)
			MAX-ACCESS read-only
			STATUS current
			DESCRIPTION
				"port index."
			::= { fkPortThresholdEntry 1 }

		
--  1.3.6.1.4.1.10428 9 1.101.5.1.1.1.2
		-- 1.3.6.1.4.1.10428 9 1.101.5.1.1.1.2
		fkPortThresholdUpLimit OBJECT-TYPE
			SYNTAX Integer32
			MAX-ACCESS read-only
			STATUS current
			DESCRIPTION
				"The threshold of port bandwidth. Unit: Kbps Validvalues: 1~"
			::= { fkPortThresholdEntry 2 }

		
--  1.3.6.1.4.1.10428 9 1.101.5.1.1.1.3
		-- 1.3.6.1.4.1.10428 9 1.101.5.1.1.1.3
		fkPortThresholdUpSamplingInterval OBJECT-TYPE
			SYNTAX INTEGER
				{
				clear(0),
				second5(5),
				second60(60),
				second600(600)
				}
			MAX-ACCESS read-write
			STATUS current
			DESCRIPTION
				"The sampling interval value in second. "
			::= { fkPortThresholdEntry 3 }

		
--  1.3.6.1.4.1.10428 9 1.101.5.1.1.1.4
		-- 1.3.6.1.4.1.10428 9 1.101.5.1.1.1.4
		fkPortThresholdDownLimit OBJECT-TYPE
			SYNTAX Integer32
			MAX-ACCESS read-only
			STATUS current
			DESCRIPTION
				"The threshold of port bandwidth. Unit: Kbps Validvalues: 1~"
			::= { fkPortThresholdEntry 4 }

		
--  1.3.6.1.4.1.10428 9 1.101.5.1.1.1.5
		-- 1.3.6.1.4.1.10428 9 1.101.5.1.1.1.5
		fkPortThresholdDownSamplingInterval OBJECT-TYPE
			SYNTAX INTEGER
				{
				clear(0),
				second5(5),
				second60(60),
				second600(600)
				}
			MAX-ACCESS read-only
			STATUS current
			DESCRIPTION
				"Description."
			::= { fkPortThresholdEntry 5 }

		
--  1.3.6.1.4.1.10428 9 1.101.5.1.1.1.6
		-- 1.3.6.1.4.1.10428 9 1.101.5.1.1.1.6
		fkPortThresholdBlockTimer OBJECT-TYPE
			SYNTAX INTEGER (-1 | 10..3600)
			MAX-ACCESS read-only
			STATUS current
			DESCRIPTION
				"Description."
			::= { fkPortThresholdEntry 6 }

		
--  1.3.6.1.4.1.10428 9 1.101.5.1.1.1.7
		-- 1.3.6.1.4.1.10428 9 1.101.5.1.1.1.7
		fkPortThresholdPpsCurrLimit OBJECT-TYPE
			SYNTAX Integer32
			MAX-ACCESS read-only
			STATUS current
			DESCRIPTION
				"Description."
			::= { fkPortThresholdEntry 7 }

		
--  1.3.6.1.4.1.10428 9 1.101.5.1.1.1.8
		-- 1.3.6.1.4.1.10428 9 1.101.5.1.1.1.8
		fkPortThresholdPpsBlocked OBJECT-TYPE
			SYNTAX Integer32
			MAX-ACCESS read-only
			STATUS current
			DESCRIPTION
				"Description."
			::= { fkPortThresholdEntry 8 }

		
--  1.3.6.1.4.1.10428 9 1.101.5.1.1.1.9
		-- 1.3.6.1.4.1.10428 9 1.101.5.1.1.1.9
		fkPortThresholdPpsLimit OBJECT-TYPE
			SYNTAX Integer32
			MAX-ACCESS read-only
			STATUS current
			DESCRIPTION
				"Description."
			::= { fkPortThresholdEntry 9 }

		
--  1.3.6.1.4.1.10428 9 1.101.5.1.1.1.10
		-- 1.3.6.1.4.1.10428 9 1.101.5.1.1.1.10
		fkPortThresholdPpsInterval OBJECT-TYPE
			SYNTAX INTEGER (0 | 5 | 60 | 600)
			MAX-ACCESS read-only
			STATUS current
			DESCRIPTION
				"Description."
			::= { fkPortThresholdEntry 10 }

		
--  1.3.6.1.4.1.10428 9 1.101.5.1.1.1.11
		-- 1.3.6.1.4.1.10428 9 1.101.5.1.1.1.11
		fkPortThresholdPpsBlockTimer OBJECT-TYPE
			SYNTAX INTEGER (-1 | 10..3600)
			MAX-ACCESS read-only
			STATUS current
			DESCRIPTION
				"Description."
			::= { fkPortThresholdEntry 11 }

		
--  1.3.6.1.4.1.10428 9 1.101.5.1.1.1.12
		-- 1.3.6.1.4.1.10428 9 1.101.5.1.1.1.12
		fkPortThresholdWarnTxLimit OBJECT-TYPE
			SYNTAX Integer32
			MAX-ACCESS read-only
			STATUS current
			DESCRIPTION
				"The threshold of port bandwidth. Unit: Kbps Validvalues: 1~"
			::= { fkPortThresholdEntry 12 }

		
--  1.3.6.1.4.1.10428 9 1.101.5.1.1.1.13
		-- 1.3.6.1.4.1.10428 9 1.101.5.1.1.1.13
		fkPortThresholdWarnTxInterval OBJECT-TYPE
			SYNTAX INTEGER
				{
				clear(0),
				second5(5),
				second60(60),
				second600(600)
				}
			MAX-ACCESS read-only
			STATUS current
			DESCRIPTION
				"The sampling interval value in second. "
			::= { fkPortThresholdEntry 13 }

		
--  1.3.6.1.4.1.10428 9 1.101.5.1.1.1.14
		-- 1.3.6.1.4.1.10428 9 1.101.5.1.1.1.14
		fkPortThresholdWarnTxDuration OBJECT-TYPE
			SYNTAX INTEGER (1..65535)
			MAX-ACCESS read-only
			STATUS current
			DESCRIPTION
				"The sampling duration value in second. 
				Duration-time units by the 5 sec"
			::= { fkPortThresholdEntry 14 }

		
--  1.3.6.1.4.1.10428 9 1.101.5.1.1.1.15
		-- 1.3.6.1.4.1.10428 9 1.101.5.1.1.1.15
		fkPortThresholdWarnRxLimit OBJECT-TYPE
			SYNTAX Integer32
			MAX-ACCESS read-only
			STATUS current
			DESCRIPTION
				"The threshold of port bandwidth. Unit: Kbps Validvalues: 1~"
			::= { fkPortThresholdEntry 15 }

		
--  1.3.6.1.4.1.10428 9 1.101.5.1.1.1.16
		-- 1.3.6.1.4.1.10428 9 1.101.5.1.1.1.16
		fkPortThresholdWarnRxInterval OBJECT-TYPE
			SYNTAX INTEGER
				{
				clear(0),
				second5(5),
				second60(60),
				second600(600)
				}
			MAX-ACCESS read-only
			STATUS current
			DESCRIPTION
				"The sampling interval value in second. "
			::= { fkPortThresholdEntry 16 }

		
--  1.3.6.1.4.1.10428 9 1.101.5.1.1.1.17
		-- 1.3.6.1.4.1.10428 9 1.101.5.1.1.1.17
		fkPortThresholdWarnRxDuration OBJECT-TYPE
			SYNTAX INTEGER (1..65535)
			MAX-ACCESS read-only
			STATUS current
			DESCRIPTION
				"The sampling duration value in second. 
				Duration-time units by the 5 sec"
			::= { fkPortThresholdEntry 17 }

		
--  1.3.6.1.4.1.10428 9 1.101.5.1.1.1.18
		-- 1.3.6.1.4.1.10428 9 1.101.5.1.1.1.18
		fkPortThresholdAlarmTxLimit OBJECT-TYPE
			SYNTAX Integer32
			MAX-ACCESS read-only
			STATUS current
			DESCRIPTION
				"The threshold of port bandwidth. Unit: Kbps Validvalues: 1~"
			::= { fkPortThresholdEntry 18 }

		
--  1.3.6.1.4.1.10428 9 1.101.5.1.1.1.19
		-- 1.3.6.1.4.1.10428 9 1.101.5.1.1.1.19
		fkPortThresholdAlarmTxInterval OBJECT-TYPE
			SYNTAX INTEGER
				{
				clear(0),
				second5(5),
				second60(60),
				second600(600)
				}
			MAX-ACCESS read-only
			STATUS current
			DESCRIPTION
				"The sampling interval value in second. "
			::= { fkPortThresholdEntry 19 }

		
--  1.3.6.1.4.1.10428 9 1.101.5.1.1.1.20
		-- 1.3.6.1.4.1.10428 9 1.101.5.1.1.1.20
		fkPortThresholdAlarmTxDuration OBJECT-TYPE
			SYNTAX INTEGER (1..65535)
			MAX-ACCESS read-only
			STATUS current
			DESCRIPTION
				"The sampling duration value in second. 
				Duration-time units by the 5 sec"
			::= { fkPortThresholdEntry 20 }

		
--  1.3.6.1.4.1.10428 9 1.101.5.1.1.1.21
		-- 1.3.6.1.4.1.10428 9 1.101.5.1.1.1.21
		fkPortThresholdAlarmRxLimit OBJECT-TYPE
			SYNTAX Integer32
			MAX-ACCESS read-only
			STATUS current
			DESCRIPTION
				"The threshold of port bandwidth. Unit: Kbps Validvalues: 1~"
			::= { fkPortThresholdEntry 21 }

		
--  1.3.6.1.4.1.10428 9 1.101.5.1.1.1.22
		-- 1.3.6.1.4.1.10428 9 1.101.5.1.1.1.22
		fkPortThresholdAlarmRxInterval OBJECT-TYPE
			SYNTAX INTEGER
				{
				clear(0),
				second5(5),
				second60(60),
				second600(600)
				}
			MAX-ACCESS read-only
			STATUS current
			DESCRIPTION
				"The sampling interval value in second. "
			::= { fkPortThresholdEntry 22 }

		
--  1.3.6.1.4.1.10428 9 1.101.5.1.1.1.23
		-- 1.3.6.1.4.1.10428 9 1.101.5.1.1.1.23
		fkPortThresholdAlarmRxDuration OBJECT-TYPE
			SYNTAX INTEGER (1..65535)
			MAX-ACCESS read-only
			STATUS current
			DESCRIPTION
				"The sampling duration value in second. 
				Duration-time units by the 5 sec"
			::= { fkPortThresholdEntry 23 }

		
--   1.3.6.1.4.1.10428 9 1.101.5.1.2
-- 1.3.6.1.4.1.10428 9 1.101.5.1.2
		-- 1.3.6.1.4.1.10428 9 1.101.5.1.2
		fkPortThresholdControl OBJECT IDENTIFIER ::= { fkPortThreshold 2 }

		
--   1.3.6.1.4.1.10428 9 1.101.5.1.2.1
-- 1.3.6.1.4.1.10428 9 1.101.5.1.2.1
		-- 1.3.6.1.4.1.10428 9 1.101.5.1.2.1
		fkPortThresholdControlRequest OBJECT-TYPE
			SYNTAX INTEGER
				{
				setPortThresholdProfile(1),
				setPortThresholdBlockProfile(2),
				setPortThresholdPPSProfile(3),
				setPortThresholdPPSBlockProfile(4),
				setPortThresholdWarnTxProfile(5),
				setPortThresholdWarnRxProfile(6),
				setPortThresholdAlarmTxProfile(7),
				setPortThresholdAlarmRxProfile(8)
				}
			MAX-ACCESS read-write
			STATUS current
			DESCRIPTION
				"Description."
			::= { fkPortThresholdControl 1 }

		
--   1.3.6.1.4.1.10428 9 1.101.5.1.2.2
-- 1.3.6.1.4.1.10428 9 1.101.5.1.2.2
		-- 1.3.6.1.4.1.10428 9 1.101.5.1.2.2
		fkPortThresholdControlStatus OBJECT-TYPE
			SYNTAX FkControlStatusType
			MAX-ACCESS read-only
			STATUS current
			DESCRIPTION
				"Description."
			::= { fkPortThresholdControl 2 }

		
--   1.3.6.1.4.1.10428 9 1.101.5.1.2.3
-- 1.3.6.1.4.1.10428 9 1.101.5.1.2.3
		-- 1.3.6.1.4.1.10428 9 1.101.5.1.2.3
		fkPortThresholdControlTimer OBJECT-TYPE
			SYNTAX Gauge32
			MAX-ACCESS read-write
			STATUS current
			DESCRIPTION
				"Description."
			::= { fkPortThresholdControl 3 }

		
--   1.3.6.1.4.1.10428 9 1.101.5.1.2.4
-- 1.3.6.1.4.1.10428 9 1.101.5.1.2.4
		-- 1.3.6.1.4.1.10428 9 1.101.5.1.2.4
		fkPortThresholdControlTimeStamp OBJECT-TYPE
			SYNTAX TimeTicks
			MAX-ACCESS read-only
			STATUS current
			DESCRIPTION
				"Description."
			::= { fkPortThresholdControl 4 }

		
--   1.3.6.1.4.1.10428 9 1.101.5.1.2.5
-- 1.3.6.1.4.1.10428 9 1.101.5.1.2.5
		-- 1.3.6.1.4.1.10428 9 1.101.5.1.2.5
		fkPortThresholdControlReqResult OBJECT-TYPE
			SYNTAX FkControlRequestResultType
			MAX-ACCESS read-only
			STATUS current
			DESCRIPTION
				"Description."
			::= { fkPortThresholdControl 5 }

		
--   1.3.6.1.4.1.10428 9 1.101.5.1.2.6
-- 1.3.6.1.4.1.10428 9 1.101.5.1.2.6
		-- 1.3.6.1.4.1.10428 9 1.101.5.1.2.6
		fkPortThresholdControlIndex OBJECT-TYPE
			SYNTAX INTEGER (1..255)
			MAX-ACCESS read-write
			STATUS current
			DESCRIPTION
				"Description."
			::= { fkPortThresholdControl 6 }

		
--   1.3.6.1.4.1.10428 9 1.101.5.1.2.7
-- 1.3.6.1.4.1.10428 9 1.101.5.1.2.7
		-- 1.3.6.1.4.1.10428 9 1.101.5.1.2.7
		fkPortThresholdControlThresholdUpLimit OBJECT-TYPE
			SYNTAX Integer32
			MAX-ACCESS read-write
			STATUS current
			DESCRIPTION
				"The threshold of port bandwidth. Unit: Kbps Validvalues: 1~"
			::= { fkPortThresholdControl 7 }

		
--   1.3.6.1.4.1.10428 9 1.101.5.1.2.8
-- 1.3.6.1.4.1.10428 9 1.101.5.1.2.8
		-- 1.3.6.1.4.1.10428 9 1.101.5.1.2.8
		fkPortThresholdControlUpSamplingInterval OBJECT-TYPE
			SYNTAX INTEGER
				{
				clear(0),
				second5(5),
				second60(60),
				second600(600)
				}
			MAX-ACCESS read-write
			STATUS current
			DESCRIPTION
				"The sampling interval value in second. "
			::= { fkPortThresholdControl 8 }

		
--   1.3.6.1.4.1.10428 9 1.101.5.1.2.9
-- 1.3.6.1.4.1.10428 9 1.101.5.1.2.9
		-- 1.3.6.1.4.1.10428 9 1.101.5.1.2.9
		fkPortThresholdControlThresholdDownLimit OBJECT-TYPE
			SYNTAX Integer32
			MAX-ACCESS read-write
			STATUS current
			DESCRIPTION
				"The threshold of port bandwidth. Unit: Kbps Validvalues: 1~"
			::= { fkPortThresholdControl 9 }

		
--   1.3.6.1.4.1.10428 9 1.101.5.1.2.10
-- 1.3.6.1.4.1.10428 9 1.101.5.1.2.10
		-- 1.3.6.1.4.1.10428 9 1.101.5.1.2.10
		fkPortThresholdControlDownSamplingInterval OBJECT-TYPE
			SYNTAX INTEGER
				{
				clear(0),
				second5(5),
				second60(60),
				second600(600)
				}
			MAX-ACCESS read-write
			STATUS current
			DESCRIPTION
				"Description."
			::= { fkPortThresholdControl 10 }

		
--   1.3.6.1.4.1.10428 9 1.101.5.1.2.11
-- 1.3.6.1.4.1.10428 9 1.101.5.1.2.11
		-- 1.3.6.1.4.1.10428 9 1.101.5.1.2.11
		fkPortThresholdControlBlockTimer OBJECT-TYPE
			SYNTAX INTEGER (-1 | 10..3600)
			MAX-ACCESS read-write
			STATUS current
			DESCRIPTION
				"Description."
			::= { fkPortThresholdControl 11 }

		
--   1.3.6.1.4.1.10428 9 1.101.5.1.2.12
-- 1.3.6.1.4.1.10428 9 1.101.5.1.2.12
		-- 1.3.6.1.4.1.10428 9 1.101.5.1.2.12
		fkPortThresholdControlPpsLimit OBJECT-TYPE
			SYNTAX Integer32
			MAX-ACCESS read-write
			STATUS current
			DESCRIPTION
				"Description."
			::= { fkPortThresholdControl 12 }

		
--   1.3.6.1.4.1.10428 9 1.101.5.1.2.13
-- 1.3.6.1.4.1.10428 9 1.101.5.1.2.13
		-- 1.3.6.1.4.1.10428 9 1.101.5.1.2.13
		fkPortThresholdControlPpsInterval OBJECT-TYPE
			SYNTAX INTEGER (0 | 5 | 60 | 600)
			MAX-ACCESS read-write
			STATUS current
			DESCRIPTION
				"Description."
			::= { fkPortThresholdControl 13 }

		
--   1.3.6.1.4.1.10428 9 1.101.5.1.2.14
-- 1.3.6.1.4.1.10428 9 1.101.5.1.2.14
		-- 1.3.6.1.4.1.10428 9 1.101.5.1.2.14
		fkPortThresholdControlPpsBlockTimer OBJECT-TYPE
			SYNTAX INTEGER (-1 | 10..3600)
			MAX-ACCESS read-write
			STATUS current
			DESCRIPTION
				"Description."
			::= { fkPortThresholdControl 14 }

		
--  1.3.6.1.4.1.10428 9 1.101.5.1.2.15
		-- 1.3.6.1.4.1.10428 9 1.101.5.1.2.15
		fkPortThresholdControlThresholdLimit OBJECT-TYPE
			SYNTAX Integer32
			MAX-ACCESS read-write
			STATUS current
			DESCRIPTION
				"The threshold of port bandwidth. Unit: Kbps Validvalues: 1~
				( -1 : delete threshold profile. )"
			::= { fkPortThresholdControl 15 }

		
--  1.3.6.1.4.1.10428 9 1.101.5.1.2.16
		-- 1.3.6.1.4.1.10428 9 1.101.5.1.2.16
		fkPortThresholdControlSamplingInterval OBJECT-TYPE
			SYNTAX INTEGER
				{
				clear(0),
				second5(5),
				second60(60),
				second600(600)
				}
			MAX-ACCESS read-write
			STATUS current
			DESCRIPTION
				"The sampling interval value in second. "
			::= { fkPortThresholdControl 16 }

		
--  1.3.6.1.4.1.10428 9 1.101.5.1.2.17
		-- 1.3.6.1.4.1.10428 9 1.101.5.1.2.17
		fkPortThresholdControlSamplingDuration OBJECT-TYPE
			SYNTAX INTEGER (5..300)
			MAX-ACCESS read-write
			STATUS current
			DESCRIPTION
				"The sampling interval value in second. 
				Duration-time units by the 5 sec"
			::= { fkPortThresholdControl 17 }

		
--   1.3.6.1.4.1.10428 9 1.101.5.1.3
-- 1.3.6.1.4.1.10428 9 1.101.5.1.3
		-- 1.3.6.1.4.1.10428 9 1.101.5.1.3
		fkPortThresholdNotification OBJECT IDENTIFIER ::= { fkPortThreshold 3 }

		
--   1.3.6.1.4.1.10428 9 1.101.5.1.3.1
-- 1.3.6.1.4.1.10428 9 1.101.5.1.3.1
		-- 1.3.6.1.4.1.10428 9 1.101.5.1.3.1
		fkPortThresholdChanged NOTIFICATION-TYPE
			OBJECTS { fkPortThresholdUpLimit, fkPortThresholdUpSamplingInterval, fkPortThresholdDownLimit, fkPortThresholdDownSamplingInterval, fkPortThresholdWarnTxLimit, 
				fkPortThresholdWarnTxInterval, fkPortThresholdWarnTxDuration, fkPortThresholdWarnRxLimit, fkPortThresholdWarnRxInterval, fkPortThresholdWarnRxDuration, 
				fkPortThresholdAlarmTxLimit, fkPortThresholdAlarmTxInterval, fkPortThresholdAlarmTxDuration, fkPortThresholdAlarmRxLimit, fkPortThresholdAlarmRxInterval, 
				fkPortThresholdAlarmRxDuration, fkPortThresholdControlRequest, fkPortThresholdControlTimeStamp, fkPortThresholdControlReqResult }
			STATUS current
			DESCRIPTION 
				"Description."
			::= { fkPortThresholdNotification 1 }

		
--   1.3.6.1.4.1.10428 9 1.101.5.1.3.2
-- 1.3.6.1.4.1.10428 9 1.101.5.1.3.2
		-- 1.3.6.1.4.1.10428 9 1.101.5.1.3.2
		fkPortThresholdBlockProfileChanged NOTIFICATION-TYPE
			OBJECTS { fkPortThresholdControlRequest, fkPortThresholdControlTimeStamp, fkPortThresholdControlReqResult, fkPortThresholdBlockTimer }
			STATUS current
			DESCRIPTION 
				"Description."
			::= { fkPortThresholdNotification 2 }

		
--   1.3.6.1.4.1.10428 9 1.101.5.1.3.3
-- 1.3.6.1.4.1.10428 9 1.101.5.1.3.3
		-- 1.3.6.1.4.1.10428 9 1.101.5.1.3.3
		fkPortThresholdPPSProfileChanged NOTIFICATION-TYPE
			OBJECTS { fkPortThresholdControlRequest, fkPortThresholdControlTimeStamp, fkPortThresholdControlReqResult, fkPortThresholdUpLimit, fkPortThresholdUpSamplingInterval
				 }
			STATUS current
			DESCRIPTION 
				"Description."
			::= { fkPortThresholdNotification 3 }

		
--   1.3.6.1.4.1.10428 9 1.101.5.1.3.4
-- 1.3.6.1.4.1.10428 9 1.101.5.1.3.4
		-- 1.3.6.1.4.1.10428 9 1.101.5.1.3.4
		fkPortThresholdPPSBlockProfileChanged NOTIFICATION-TYPE
			OBJECTS { fkPortThresholdControlRequest, fkPortThresholdControlTimeStamp, fkPortThresholdControlReqResult, fkPortThresholdPpsBlockTimer }
			STATUS current
			DESCRIPTION 
				"Description."
			::= { fkPortThresholdNotification 4 }

		
		-- 1.3.6.1.4.1.10428 9 1.101.5.2
		fkPortRate OBJECT IDENTIFIER ::= { fkPerformanceMgmt 2 }

		
		-- 1.3.6.1.4.1.10428 9 1.101.5.2.1
		fkPortRateTable OBJECT-TYPE
			SYNTAX SEQUENCE OF FkPortRateEntry
			MAX-ACCESS not-accessible
			STATUS current
			DESCRIPTION
				"Description."
			::= { fkPortRate 1 }

		
		-- 1.3.6.1.4.1.10428 9 1.101.5.2.1.1
		fkPortRateEntry OBJECT-TYPE
			SYNTAX FkPortRateEntry
			MAX-ACCESS not-accessible
			STATUS current
			DESCRIPTION
				"Description."
			INDEX { fkPortRateInterfaceIndex }
			::= { fkPortRateTable 1 }

		
		FkPortRateEntry ::=
			SEQUENCE { 
				fkPortRateInterfaceIndex
					INTEGER,
				fkPortRateIngressRate
					Integer32,
				fkPortRateEgressRate
					Integer32,
				fkPortRateEnhanced
					INTEGER
			 }

		-- 1.3.6.1.4.1.10428 9 1.101.5.2.1.1.1
		fkPortRateInterfaceIndex OBJECT-TYPE
			SYNTAX INTEGER (1..255)
			MAX-ACCESS read-only
			STATUS current
			DESCRIPTION
				"Interface Index"
			::= { fkPortRateEntry 1 }

		
		-- 1.3.6.1.4.1.10428 9 1.101.5.2.1.1.2
		fkPortRateIngressRate OBJECT-TYPE
			SYNTAX Integer32
			MAX-ACCESS read-only
			STATUS current
			DESCRIPTION
				"Ingress rate for port. 
				The value is in units fo 64 kbps.
				For 100MB ports, the valid range is from 0 to 100000.
				For 1000MB ports, the valid range is from 0 to 1000000."
			::= { fkPortRateEntry 2 }

		
		-- 1.3.6.1.4.1.10428 9 1.101.5.2.1.1.3
		fkPortRateEgressRate OBJECT-TYPE
			SYNTAX Integer32
			MAX-ACCESS read-only
			STATUS current
			DESCRIPTION
				"Egress rate for port, 
				The value is in units fo 64 kbps.
				For 100MB ports, the valid range is from 0 to 100000.
				For 1000MB ports, the valid range is from 0 to 1000000."
			::= { fkPortRateEntry 3 }

		
		-- 1.3.6.1.4.1.10428 9 1.101.5.2.1.1.4
		fkPortRateEnhanced OBJECT-TYPE
			SYNTAX INTEGER
				{
				disable(0),
				enable(1)
				}
			MAX-ACCESS read-only
			STATUS current
			DESCRIPTION
				"Description."
			::= { fkPortRateEntry 4 }

		
		-- 1.3.6.1.4.1.10428 9 1.101.5.2.2
		fkPortRateControl OBJECT IDENTIFIER ::= { fkPortRate 2 }

		
		-- 1.3.6.1.4.1.10428 9 1.101.5.2.2.1
		fkPortRateControlRequest OBJECT-TYPE
			SYNTAX INTEGER
				{
				setPortRateProfile(1),
				setPortRateEnhanced(2)
				}
			MAX-ACCESS read-write
			STATUS current
			DESCRIPTION
				"Description."
			::= { fkPortRateControl 1 }

		
		-- 1.3.6.1.4.1.10428 9 1.101.5.2.2.2
		fkPortRateControlStatus OBJECT-TYPE
			SYNTAX FkControlStatusType
			MAX-ACCESS read-only
			STATUS current
			DESCRIPTION
				"Description."
			::= { fkPortRateControl 2 }

		
		-- 1.3.6.1.4.1.10428 9 1.101.5.2.2.3
		fkPortRateControlTimer OBJECT-TYPE
			SYNTAX Gauge32
			MAX-ACCESS read-write
			STATUS current
			DESCRIPTION
				"Description."
			::= { fkPortRateControl 3 }

		
		-- 1.3.6.1.4.1.10428 9 1.101.5.2.2.4
		fkPortRateControlTimeStamp OBJECT-TYPE
			SYNTAX TimeTicks
			MAX-ACCESS read-only
			STATUS current
			DESCRIPTION
				"Description."
			::= { fkPortRateControl 4 }

		
		-- 1.3.6.1.4.1.10428 9 1.101.5.2.2.5
		fkPortRateControlReqResult OBJECT-TYPE
			SYNTAX FkControlRequestResultType
			MAX-ACCESS read-only
			STATUS current
			DESCRIPTION
				"Description."
			::= { fkPortRateControl 5 }

		
		-- 1.3.6.1.4.1.10428 9 1.101.5.2.2.6
		fkPortRateControlInterfaceIndex OBJECT-TYPE
			SYNTAX INTEGER (1..255)
			MAX-ACCESS read-write
			STATUS current
			DESCRIPTION
				"
				"
			::= { fkPortRateControl 6 }

		
		-- 1.3.6.1.4.1.10428 9 1.101.5.2.2.7
		fkPortRateControlIngressRate OBJECT-TYPE
			SYNTAX Integer32
			MAX-ACCESS read-write
			STATUS current
			DESCRIPTION
				"Ingress rate for port. 
				The value is in units fo 64 kbps.
				For 100MB ports, the valid range is from 0 to 100000.
				For 1000MB ports, the valid range is from 0 to 1000000."
			::= { fkPortRateControl 7 }

		
		-- 1.3.6.1.4.1.10428 9 1.101.5.2.2.8
		fkPortRateControlEgressRate OBJECT-TYPE
			SYNTAX Integer32
			MAX-ACCESS read-write
			STATUS current
			DESCRIPTION
				"Egress rate for port, 
				The value is in units fo 64 kbps.
				For 100MB ports, the valid range is from 0 to 100000.
				For 1000MB ports, the valid range is from 0 to 1000000."
			::= { fkPortRateControl 8 }

		
		-- 1.3.6.1.4.1.10428 9 1.101.5.2.2.9
		fkPortRateControlEnhanced OBJECT-TYPE
			SYNTAX INTEGER
				{
				disable(0),
				enable(1)
				}
			MAX-ACCESS read-write
			STATUS current
			DESCRIPTION
				"Description."
			::= { fkPortRateControl 9 }

		
		-- 1.3.6.1.4.1.10428 9 1.101.5.2.3
		fkPortRateNotification OBJECT IDENTIFIER ::= { fkPortRate 3 }

		
		-- 1.3.6.1.4.1.10428 9 1.101.5.2.3.1
		fkPortRateProfileChanged NOTIFICATION-TYPE
			OBJECTS { fkPortRateIngressRate, fkPortRateEgressRate, fkPortRateControlRequest, fkPortRateControlTimeStamp, fkPortRateControlReqResult
				 }
			STATUS current
			DESCRIPTION 
				"Description."
			::= { fkPortRateNotification 1 }

		
		-- 1.3.6.1.4.1.10428 9 1.101.5.2.3.2
		fkPortRateEnhancedChanged NOTIFICATION-TYPE
			OBJECTS { fkPortRateControlRequest, fkPortRateControlTimeStamp, fkPortRateControlReqResult, fkPortRateEnhanced }
			STATUS current
			DESCRIPTION 
				"Description."
			::= { fkPortRateNotification 2 }

		
		-- 1.3.6.1.4.1.10428 9 1.101.5.3
		fkPortStatistics OBJECT IDENTIFIER ::= { fkPerformanceMgmt 3 }

		
		-- 1.3.6.1.4.1.10428 9 1.101.5.3.1
		fkPortStatisticsTable OBJECT-TYPE
			SYNTAX SEQUENCE OF FkPortStatisticsEntry
			MAX-ACCESS not-accessible
			STATUS current
			DESCRIPTION
				"Description."
			::= { fkPortStatistics 1 }

		
		-- 1.3.6.1.4.1.10428 9 1.101.5.3.1.1
		fkPortStatisticsEntry OBJECT-TYPE
			SYNTAX FkPortStatisticsEntry
			MAX-ACCESS not-accessible
			STATUS current
			DESCRIPTION
				"Description."
			INDEX { fkPortStatsIndex, fkPortStatsInterval, fkPortStatsOrder }
			::= { fkPortStatisticsTable 1 }

		
		FkPortStatisticsEntry ::=
			SEQUENCE { 
				fkPortStatsIndex
					INTEGER,
				fkPortStatsInterval
					INTEGER,
				fkPortStatsOrder
					INTEGER,
				fkPortStatsUpPackets
					Counter64,
				fkPortStatsUpBytes
					Counter64,
				fkPortStatsDownPackets
					Counter64,
				fkPortStatsDownBytes
					Counter64
			 }

		-- 1.3.6.1.4.1.10428 9 1.101.5.3.1.1.1
		fkPortStatsIndex OBJECT-TYPE
			SYNTAX INTEGER (1..255)
			MAX-ACCESS read-only
			STATUS current
			DESCRIPTION
				"Port index of EthernetPort, only valid for physical ports."
			::= { fkPortStatisticsEntry 1 }

		
		-- 1.3.6.1.4.1.10428 9 1.101.5.3.1.1.2
		fkPortStatsInterval OBJECT-TYPE
			SYNTAX INTEGER
				{
				fiveSeconds(5),
				oneMinute(60),
				fifteenMinutes(900),
				oneDay(86400)
				}
			MAX-ACCESS read-only
			STATUS current
			DESCRIPTION
				"Interval time of counters (unit: seconds)"
			::= { fkPortStatisticsEntry 2 }

		
		-- 1.3.6.1.4.1.10428 9 1.101.5.3.1.1.3
		fkPortStatsOrder OBJECT-TYPE
			SYNTAX INTEGER (0..95)
			MAX-ACCESS read-only
			STATUS current
			DESCRIPTION
				"History sequence of counters (0: current)"
			::= { fkPortStatisticsEntry 3 }

		
		-- 1.3.6.1.4.1.10428 9 1.101.5.3.1.1.4
		fkPortStatsUpPackets OBJECT-TYPE
			SYNTAX Counter64
			MAX-ACCESS read-only
			STATUS current
			DESCRIPTION
				"Upstream traffic utilization during fkPortStatsInterval seconds.
				Unit: Accumulated packets per fkPortStatsInterval"
			::= { fkPortStatisticsEntry 4 }

		
		-- 1.3.6.1.4.1.10428 9 1.101.5.3.1.1.5
		fkPortStatsUpBytes OBJECT-TYPE
			SYNTAX Counter64
			MAX-ACCESS read-only
			STATUS current
			DESCRIPTION
				"Upstream traffic utilization during fkPortStatsInterval seconds.
				Unit: Accumulated bytes per fkPortStatsInterval"
			::= { fkPortStatisticsEntry 5 }

		
		-- 1.3.6.1.4.1.10428 9 1.101.5.3.1.1.6
		fkPortStatsDownPackets OBJECT-TYPE
			SYNTAX Counter64
			MAX-ACCESS read-only
			STATUS current
			DESCRIPTION
				"Downstream traffic utilization during fkPortStatsInterval seconds.
				Unit: Accumulated packets per fkPortStatsInterval"
			::= { fkPortStatisticsEntry 6 }

		
		-- 1.3.6.1.4.1.10428 9 1.101.5.3.1.1.7
		fkPortStatsDownBytes OBJECT-TYPE
			SYNTAX Counter64
			MAX-ACCESS read-only
			STATUS current
			DESCRIPTION
				"Downstream traffic utilization during fkPortStatsInterval seconds.
				Unit: Accumulated bytes per fkPortStatsInterval"
			::= { fkPortStatisticsEntry 7 }

		
		-- 1.3.6.1.4.1.10428 9 1.101.5.3.2
		fkPortStatisticsControl OBJECT IDENTIFIER ::= { fkPortStatistics 2 }

		
		-- 1.3.6.1.4.1.10428 9 1.101.5.3.2.1
		fkPortStatsControlRequest OBJECT-TYPE
			SYNTAX INTEGER
				{
				clearPortStatistics(1),
				clearPortStatisticsAll(2)
				}
			MAX-ACCESS read-write
			STATUS current
			DESCRIPTION
				"Description."
			::= { fkPortStatisticsControl 1 }

		
		-- 1.3.6.1.4.1.10428 9 1.101.5.3.2.2
		fkPortStatsControlStatus OBJECT-TYPE
			SYNTAX FkControlStatusType
			MAX-ACCESS read-only
			STATUS current
			DESCRIPTION
				"Description."
			::= { fkPortStatisticsControl 2 }

		
		-- 1.3.6.1.4.1.10428 9 1.101.5.3.2.3
		fkPortStatsControlTimer OBJECT-TYPE
			SYNTAX Gauge32
			MAX-ACCESS read-write
			STATUS current
			DESCRIPTION
				"Description."
			::= { fkPortStatisticsControl 3 }

		
		-- 1.3.6.1.4.1.10428 9 1.101.5.3.2.4
		fkPortStatsControlTimeStamp OBJECT-TYPE
			SYNTAX TimeTicks
			MAX-ACCESS read-only
			STATUS current
			DESCRIPTION
				"Description."
			::= { fkPortStatisticsControl 4 }

		
		-- 1.3.6.1.4.1.10428 9 1.101.5.3.2.5
		fkPortStatsControlReqResult OBJECT-TYPE
			SYNTAX FkControlRequestResultType
			MAX-ACCESS read-only
			STATUS current
			DESCRIPTION
				"Description."
			::= { fkPortStatisticsControl 5 }

		
		-- 1.3.6.1.4.1.10428 9 1.101.5.3.2.6
		fkPortStatsControlIndex OBJECT-TYPE
			SYNTAX Unsigned32 (1..255)
			MAX-ACCESS read-write
			STATUS current
			DESCRIPTION
				"Description."
			::= { fkPortStatisticsControl 6 }

		
		-- 1.3.6.1.4.1.10428 9 1.101.5.3.3
		fkPortStatisticsNotification OBJECT IDENTIFIER ::= { fkPortStatistics 3 }

		
		-- 1.3.6.1.4.1.10428 9 1.101.5.3.3.1
		fkPortStatisticsCleared NOTIFICATION-TYPE
			OBJECTS { fkPortStatsControlRequest, fkPortStatsControlTimeStamp, fkPortStatsControlReqResult, fkPortStatsIndex }
			STATUS current
			DESCRIPTION 
				"Description."
			::= { fkPortStatisticsNotification 1 }

		
		-- 1.3.6.1.4.1.10428 9 1.101.5.3.3.2
		fkPortStatisticsAllCleared NOTIFICATION-TYPE
			OBJECTS { fkPortStatsControlRequest, fkPortStatsControlTimeStamp, fkPortStatsControlReqResult }
			STATUS current
			DESCRIPTION 
				"Description."
			::= { fkPortStatisticsNotification 2 }

		
		-- 1.3.6.1.4.1.10428 9 1.101.5.3.4
		fkPortStatisticsAverageTable OBJECT-TYPE
			SYNTAX SEQUENCE OF FkPortStatisticsAverageEntry
			MAX-ACCESS not-accessible
			STATUS current
			DESCRIPTION
				"Description."
			::= { fkPortStatistics 4 }

		
		-- 1.3.6.1.4.1.10428 9 1.101.5.3.4.1
		fkPortStatisticsAverageEntry OBJECT-TYPE
			SYNTAX FkPortStatisticsAverageEntry
			MAX-ACCESS not-accessible
			STATUS current
			DESCRIPTION
				"Description."
			INDEX { fkPortStatsIndex, fkPortStatsAvgInterval }
			::= { fkPortStatisticsAverageTable 1 }

		
		FkPortStatisticsAverageEntry ::=
			SEQUENCE { 
				fkPortStatsAvgInterval
					INTEGER,
				fkPortStatsAvgTxPackets
					Counter64,
				fkPortStatsAvgTxBytes
					Counter64,
				fkPortStatsAvgTxUcastPackets
					Counter64,
				fkPortStatsAvgTxMcastPackets
					Counter64,
				fkPortStatsAvgTxBcastPackets
					Counter64,
				fkPortStatsAvgRxPackets
					Counter64,
				fkPortStatsAvgRxBytes
					Counter64,
				fkPortStatsAvgRxUcastPackets
					Counter64,
				fkPortStatsAvgRxMcastPackets
					Counter64,
				fkPortStatsAvgRxBcastPackets
					Counter64
			 }

		-- 1.3.6.1.4.1.10428 9 1.101.5.3.4.1.1
		fkPortStatsAvgInterval OBJECT-TYPE
			SYNTAX INTEGER
				{
				fiveSeconds(5),
				oneMinute(60),
				tenMinutes(600)
				}
			MAX-ACCESS read-only
			STATUS current
			DESCRIPTION
				"Interval time of counters (unit: seconds)"
			::= { fkPortStatisticsAverageEntry 1 }

		
		-- 1.3.6.1.4.1.10428 9 1.101.5.3.4.1.2
		fkPortStatsAvgTxPackets OBJECT-TYPE
			SYNTAX Counter64
			MAX-ACCESS read-only
			STATUS current
			DESCRIPTION
				"Average statistics of upstream traffic calculated during fkPortStatsAvgInterval seconds. 
				Unit: packets per second
				"
			::= { fkPortStatisticsAverageEntry 2 }

		
		-- 1.3.6.1.4.1.10428 9 1.101.5.3.4.1.3
		fkPortStatsAvgTxBytes OBJECT-TYPE
			SYNTAX Counter64
			MAX-ACCESS read-only
			STATUS current
			DESCRIPTION
				"Average statistics of upstream traffic calculated during fkPortStatsAvgInterval seconds. 
				Unit: bytes per second
				"
			::= { fkPortStatisticsAverageEntry 3 }

		
		-- 1.3.6.1.4.1.10428 9 1.101.5.3.4.1.4
		fkPortStatsAvgTxUcastPackets OBJECT-TYPE
			SYNTAX Counter64
			MAX-ACCESS read-only
			STATUS current
			DESCRIPTION
				"Average statistics of upstream unicast traffic calculated during fkPortStatsAvgInterval seconds. 
				Unit: packets per second
				"
			::= { fkPortStatisticsAverageEntry 4 }

		
		-- 1.3.6.1.4.1.10428 9 1.101.5.3.4.1.5
		fkPortStatsAvgTxMcastPackets OBJECT-TYPE
			SYNTAX Counter64
			MAX-ACCESS read-only
			STATUS current
			DESCRIPTION
				"Average statistics of upstream multicast traffic calculated during fkPortStatsAvgInterval seconds. 
				Unit: packets per second
				"
			::= { fkPortStatisticsAverageEntry 5 }

		
		-- 1.3.6.1.4.1.10428 9 1.101.5.3.4.1.6
		fkPortStatsAvgTxBcastPackets OBJECT-TYPE
			SYNTAX Counter64
			MAX-ACCESS read-only
			STATUS current
			DESCRIPTION
				"Average statistics of upstream broadcast traffic calculated during fkPortStatsAvgInterval seconds. 
				Unit: packets per second
				"
			::= { fkPortStatisticsAverageEntry 6 }

		
		-- 1.3.6.1.4.1.10428 9 1.101.5.3.4.1.7
		fkPortStatsAvgRxPackets OBJECT-TYPE
			SYNTAX Counter64
			MAX-ACCESS read-only
			STATUS current
			DESCRIPTION
				"Average statistics of downstream traffic calculated during fkPortStatsAvgInterval seconds. 
				Unit: packets per second
				"
			::= { fkPortStatisticsAverageEntry 7 }

		
		-- 1.3.6.1.4.1.10428 9 1.101.5.3.4.1.8
		fkPortStatsAvgRxBytes OBJECT-TYPE
			SYNTAX Counter64
			MAX-ACCESS read-only
			STATUS current
			DESCRIPTION
				"Average statistics of downstream traffic calculated during fkPortStatsAvgInterval seconds. 
				Unit: bytes per second
				"
			::= { fkPortStatisticsAverageEntry 8 }

		
		-- 1.3.6.1.4.1.10428 9 1.101.5.3.4.1.9
		fkPortStatsAvgRxUcastPackets OBJECT-TYPE
			SYNTAX Counter64
			MAX-ACCESS read-only
			STATUS current
			DESCRIPTION
				"Average statistics of downstream unicast traffic calculated during fkPortStatsAvgInterval seconds. 
				Unit: packets per second
				"
			::= { fkPortStatisticsAverageEntry 9 }

		
		-- 1.3.6.1.4.1.10428 9 1.101.5.3.4.1.10
		fkPortStatsAvgRxMcastPackets OBJECT-TYPE
			SYNTAX Counter64
			MAX-ACCESS read-only
			STATUS current
			DESCRIPTION
				"Average statistics of downstream multicast traffic calculated during fkPortStatsAvgInterval seconds. 
				Unit: packets per second
				"
			::= { fkPortStatisticsAverageEntry 10 }

		
		-- 1.3.6.1.4.1.10428 9 1.101.5.3.4.1.11
		fkPortStatsAvgRxBcastPackets OBJECT-TYPE
			SYNTAX Counter64
			MAX-ACCESS read-only
			STATUS current
			DESCRIPTION
				"Average statistics of downstream broadcast traffic calculated during fkPortStatsAvgInterval seconds. 
				Unit: packets per second
				"
			::= { fkPortStatisticsAverageEntry 11 }

		
		-- 1.3.6.1.4.1.10428 9 1.101.5.3.5
		fkPortStatisticsAccTable OBJECT-TYPE
			SYNTAX SEQUENCE OF FkPortStatisticsAccEntry
			MAX-ACCESS not-accessible
			STATUS current
			DESCRIPTION
				"Description."
			::= { fkPortStatistics 5 }

		
		-- 1.3.6.1.4.1.10428 9 1.101.5.3.5.1
		fkPortStatisticsAccEntry OBJECT-TYPE
			SYNTAX FkPortStatisticsAccEntry
			MAX-ACCESS not-accessible
			STATUS current
			DESCRIPTION
				"Description."
			INDEX { fkPortStatisticsAccHCIndex }
			::= { fkPortStatisticsAccTable 1 }

		
		FkPortStatisticsAccEntry ::=
			SEQUENCE { 
				fkPortStatisticsAccHCIndex
					InterfaceIndex,
				fkPortStatisticsAccHCInUnicastPkts
					Counter64,
				fkPortStatisticsAccHCInMulticastPkts
					Counter64,
				fkPortStatisticsAccHCInBroadcastPkts
					Counter64,
				fkPortStatisticsAccHCOutUnicastPkts
					Counter64,
				fkPortStatisticsAccHCOutMulticastPkts
					Counter64,
				fkPortStatisticsAccHCOutBroadcastPkts
					Counter64,
				fkPortStatisticsAccHCInOctets
					Counter64,
				fkPortStatisticsAccHCOutOctets
					Counter64,
				fkPortStatisticsAccHCOutVlanTagPkts
					Counter64
			 }

		-- 1.3.6.1.4.1.10428 9 1.101.5.3.5.1.1
		fkPortStatisticsAccHCIndex OBJECT-TYPE
			SYNTAX InterfaceIndex
			MAX-ACCESS read-only
			STATUS current
			DESCRIPTION
				"ifIndx"
			::= { fkPortStatisticsAccEntry 1 }

		
		-- 1.3.6.1.4.1.10428 9 1.101.5.3.5.1.2
		fkPortStatisticsAccHCInUnicastPkts OBJECT-TYPE
			SYNTAX Counter64
			MAX-ACCESS read-only
			STATUS current
			DESCRIPTION
				"Rx unicast packet counter"
			::= { fkPortStatisticsAccEntry 2 }

		
		-- 1.3.6.1.4.1.10428 9 1.101.5.3.5.1.3
		fkPortStatisticsAccHCInMulticastPkts OBJECT-TYPE
			SYNTAX Counter64
			MAX-ACCESS read-only
			STATUS current
			DESCRIPTION
				"Rx multicast packet counter"
			::= { fkPortStatisticsAccEntry 3 }

		
		-- 1.3.6.1.4.1.10428 9 1.101.5.3.5.1.4
		fkPortStatisticsAccHCInBroadcastPkts OBJECT-TYPE
			SYNTAX Counter64
			MAX-ACCESS read-only
			STATUS current
			DESCRIPTION
				"Rx broadcast packet counter"
			::= { fkPortStatisticsAccEntry 4 }

		
		-- 1.3.6.1.4.1.10428 9 1.101.5.3.5.1.5
		fkPortStatisticsAccHCOutUnicastPkts OBJECT-TYPE
			SYNTAX Counter64
			MAX-ACCESS read-only
			STATUS current
			DESCRIPTION
				"Tx unicast packet counter"
			::= { fkPortStatisticsAccEntry 5 }

		
		-- 1.3.6.1.4.1.10428 9 1.101.5.3.5.1.6
		fkPortStatisticsAccHCOutMulticastPkts OBJECT-TYPE
			SYNTAX Counter64
			MAX-ACCESS read-only
			STATUS current
			DESCRIPTION
				"Tx multicast packet counter"
			::= { fkPortStatisticsAccEntry 6 }

		
		-- 1.3.6.1.4.1.10428 9 1.101.5.3.5.1.7
		fkPortStatisticsAccHCOutBroadcastPkts OBJECT-TYPE
			SYNTAX Counter64
			MAX-ACCESS read-only
			STATUS current
			DESCRIPTION
				"Tx broadcast packet counter"
			::= { fkPortStatisticsAccEntry 7 }

		
		-- 1.3.6.1.4.1.10428 9 1.101.5.3.5.1.8
		fkPortStatisticsAccHCInOctets OBJECT-TYPE
			SYNTAX Counter64
			MAX-ACCESS read-only
			STATUS current
			DESCRIPTION
				"Rx bytes"
			::= { fkPortStatisticsAccEntry 8 }

		
		-- 1.3.6.1.4.1.10428 9 1.101.5.3.5.1.9
		fkPortStatisticsAccHCOutOctets OBJECT-TYPE
			SYNTAX Counter64
			MAX-ACCESS read-only
			STATUS current
			DESCRIPTION
				"Tx bytes"
			::= { fkPortStatisticsAccEntry 9 }

		
		-- 1.3.6.1.4.1.10428 9 1.101.5.3.5.1.10
		fkPortStatisticsAccHCOutVlanTagPkts OBJECT-TYPE
			SYNTAX Counter64
			MAX-ACCESS read-only
			STATUS current
			DESCRIPTION
				"Tx VLAN tag counter"
			::= { fkPortStatisticsAccEntry 10 }

		
		-- 1.3.6.1.4.1.10428 9 1.101.5.3.6
		fkPortStatisticsPacketPerQueueTable OBJECT-TYPE
			SYNTAX SEQUENCE OF FkPortStatisticsPacketPerQueueEntry
			MAX-ACCESS not-accessible
			STATUS current
			DESCRIPTION
				"fkPortStatisticsPacketPerQueueTable"
			::= { fkPortStatistics 6 }

		
		-- 1.3.6.1.4.1.10428 9 1.101.5.3.6.1
		fkPortStatisticsPacketPerQueueEntry OBJECT-TYPE
			SYNTAX FkPortStatisticsPacketPerQueueEntry
			MAX-ACCESS not-accessible
			STATUS current
			DESCRIPTION
				"key: fkPortStatisticsPPQPortNum, fkPortStatisticsPPQQueueNumber"
			INDEX { fkPortStatisticsPPQPortNum, fkPortStatisticsPPQQueueNumber }
			::= { fkPortStatisticsPacketPerQueueTable 1 }

		
		FkPortStatisticsPacketPerQueueEntry ::=
			SEQUENCE { 
				fkPortStatisticsPPQPortNum
					INTEGER,
				fkPortStatisticsPPQQueueNumber
					INTEGER,
				fkPortStatisticsPPQPacketPassedCount
					Counter64,
				fkPortStatisticsPPQOctetPassedCount
					Counter64,
				fkPortStatisticsPPQPacketDiscards
					Counter64,
				fkPortStatisticsPPQOctetDiscard
					Counter64
			 }

		-- 1.3.6.1.4.1.10428 9 1.101.5.3.6.1.1
		fkPortStatisticsPPQPortNum OBJECT-TYPE
			SYNTAX INTEGER (1..128)
			MAX-ACCESS read-only
			STATUS current
			DESCRIPTION
				"The Physical port index."
			::= { fkPortStatisticsPacketPerQueueEntry 1 }

		
		-- 1.3.6.1.4.1.10428 9 1.101.5.3.6.1.2
		fkPortStatisticsPPQQueueNumber OBJECT-TYPE
			SYNTAX INTEGER (0..7)
			MAX-ACCESS read-only
			STATUS current
			DESCRIPTION
				"The Queue number (0~7)"
			::= { fkPortStatisticsPacketPerQueueEntry 2 }

		
		-- 1.3.6.1.4.1.10428 9 1.101.5.3.6.1.3
		fkPortStatisticsPPQPacketPassedCount OBJECT-TYPE
			SYNTAX Counter64
			MAX-ACCESS read-only
			STATUS current
			DESCRIPTION
				"The Packet Passed count."
			::= { fkPortStatisticsPacketPerQueueEntry 3 }

		
		-- 1.3.6.1.4.1.10428 9 1.101.5.3.6.1.4
		fkPortStatisticsPPQOctetPassedCount OBJECT-TYPE
			SYNTAX Counter64
			MAX-ACCESS read-only
			STATUS current
			DESCRIPTION
				"The Packet Passed count expressed by bytes."
			::= { fkPortStatisticsPacketPerQueueEntry 4 }

		
		-- 1.3.6.1.4.1.10428 9 1.101.5.3.6.1.5
		fkPortStatisticsPPQPacketDiscards OBJECT-TYPE
			SYNTAX Counter64
			MAX-ACCESS read-only
			STATUS current
			DESCRIPTION
				"The Packet discards count."
			::= { fkPortStatisticsPacketPerQueueEntry 5 }

		
		-- 1.3.6.1.4.1.10428 9 1.101.5.3.6.1.6
		fkPortStatisticsPPQOctetDiscard OBJECT-TYPE
			SYNTAX Counter64
			MAX-ACCESS read-only
			STATUS current
			DESCRIPTION
				"The Packet discards expressed by bytes."
			::= { fkPortStatisticsPacketPerQueueEntry 6 }

		
		-- 1.3.6.1.4.1.10428 9 1.101.5.4
		fkCpuStatistics OBJECT IDENTIFIER ::= { fkPerformanceMgmt 4 }

		
		-- 1.3.6.1.4.1.10428 9 1.101.5.4.1
		fkCpuIntervalStatisticsTable OBJECT-TYPE
			SYNTAX SEQUENCE OF FkCpuIntervalStatisticsEntry
			MAX-ACCESS not-accessible
			STATUS current
			DESCRIPTION
				"Description."
			::= { fkCpuStatistics 1 }

		
		-- 1.3.6.1.4.1.10428 9 1.101.5.4.1.1
		fkCpuIntervalStatisticsEntry OBJECT-TYPE
			SYNTAX FkCpuIntervalStatisticsEntry
			MAX-ACCESS not-accessible
			STATUS current
			DESCRIPTION
				"Description."
			INDEX { fkCpuIntvlStatsPortIndex, fkCpuIntvlStatsInterval, fkCpuIntvlStatsOrder }
			::= { fkCpuIntervalStatisticsTable 1 }

		
		FkCpuIntervalStatisticsEntry ::=
			SEQUENCE { 
				fkCpuIntvlStatsPortIndex
					InterfaceIndex,
				fkCpuIntvlStatsInterval
					INTEGER,
				fkCpuIntvlStatsOrder
					INTEGER,
				fkCpuIntvlStatsTxUcastPkts
					Counter64,
				fkCpuIntvlStatsTxMcastPkts
					Counter64,
				fkCpuIntvlStatsTxBcastPkts
					Counter64,
				fkCpuIntvlStatsTxUcastBytes
					Counter64,
				fkCpuIntvlStatsTxMcastBytes
					Counter64,
				fkCpuIntvlStatsTxBcastBytes
					Counter64,
				fkCpuIntvlStatsRxUcastPkts
					Counter64,
				fkCpuIntvlStatsRxMcastPkts
					Counter64,
				fkCpuIntvlStatsRxBcastPkts
					Counter64,
				fkCpuIntvlStatsRxUcastBytes
					Counter64,
				fkCpuIntvlStatsRxMcastBytes
					Counter64,
				fkCpuIntvlStatsRxBcastBytes
					Counter64
			 }

		-- 1.3.6.1.4.1.10428 9 1.101.5.4.1.1.1
		fkCpuIntvlStatsPortIndex OBJECT-TYPE
			SYNTAX InterfaceIndex
			MAX-ACCESS read-only
			STATUS current
			DESCRIPTION
				"Port index of EthernetPort, only valid for physical ports."
			::= { fkCpuIntervalStatisticsEntry 1 }

		
		-- 1.3.6.1.4.1.10428 9 1.101.5.4.1.1.2
		fkCpuIntvlStatsInterval OBJECT-TYPE
			SYNTAX INTEGER
				{
				fiveSeconds(1),
				oneMinute(2),
				tenMinute(3)
				}
			MAX-ACCESS read-only
			STATUS current
			DESCRIPTION
				"Interval time of counters (unit: seconds)"
			::= { fkCpuIntervalStatisticsEntry 2 }

		
		-- 1.3.6.1.4.1.10428 9 1.101.5.4.1.1.3
		fkCpuIntvlStatsOrder OBJECT-TYPE
			SYNTAX INTEGER (0..95)
			MAX-ACCESS read-only
			STATUS current
			DESCRIPTION
				"History sequence of counters (0: current) 
				(support only 0)
				"
			::= { fkCpuIntervalStatisticsEntry 3 }

		
		-- 1.3.6.1.4.1.10428 9 1.101.5.4.1.1.4
		fkCpuIntvlStatsTxUcastPkts OBJECT-TYPE
			SYNTAX Counter64
			MAX-ACCESS read-only
			STATUS current
			DESCRIPTION
				"The Average value of the txUnicast that have been transmitted to CPU during fkCpuIntvlStatsInterval
				Unit: Packets/ fkCpuIntvlStatsInterval
				"
			::= { fkCpuIntervalStatisticsEntry 4 }

		
		-- 1.3.6.1.4.1.10428 9 1.101.5.4.1.1.5
		fkCpuIntvlStatsTxMcastPkts OBJECT-TYPE
			SYNTAX Counter64
			MAX-ACCESS read-only
			STATUS current
			DESCRIPTION
				"The Average value of the txMulticast that have been transmitted to CPU during fkCpuIntvlStatsInterval"
			::= { fkCpuIntervalStatisticsEntry 5 }

		
		-- 1.3.6.1.4.1.10428 9 1.101.5.4.1.1.6
		fkCpuIntvlStatsTxBcastPkts OBJECT-TYPE
			SYNTAX Counter64
			MAX-ACCESS read-only
			STATUS current
			DESCRIPTION
				"The Average value of the txBroadcast that have been transmitted to CPU during fkCpuIntvlStatsInterval
				Unit: Packets/ fkCpuIntvlStatsInterval
				"
			::= { fkCpuIntervalStatisticsEntry 6 }

		
		-- 1.3.6.1.4.1.10428 9 1.101.5.4.1.1.7
		fkCpuIntvlStatsTxUcastBytes OBJECT-TYPE
			SYNTAX Counter64
			MAX-ACCESS read-only
			STATUS current
			DESCRIPTION
				"The Average value of the txUnicast that have been transmitted to CPU during fkCpuIntvlStatsInterval
				Unit: Bytes/ fkCpuIntvlStatsInterval
				"
			::= { fkCpuIntervalStatisticsEntry 7 }

		
		-- 1.3.6.1.4.1.10428 9 1.101.5.4.1.1.8
		fkCpuIntvlStatsTxMcastBytes OBJECT-TYPE
			SYNTAX Counter64
			MAX-ACCESS read-only
			STATUS current
			DESCRIPTION
				"The Average value of the txMulticast that have been transmitted to CPU during fkCpuIntvlStatsInterval
				Unit: Bytes/ fkCpuIntvlStatsInterval
				"
			::= { fkCpuIntervalStatisticsEntry 8 }

		
		-- 1.3.6.1.4.1.10428 9 1.101.5.4.1.1.9
		fkCpuIntvlStatsTxBcastBytes OBJECT-TYPE
			SYNTAX Counter64
			MAX-ACCESS read-only
			STATUS current
			DESCRIPTION
				"The Average value of the txBroadcast that have been transmitted to CPU during fkCpuIntvlStatsInterval
				Unit: Bytes/ fkCpuIntvlStatsInterval
				"
			::= { fkCpuIntervalStatisticsEntry 9 }

		
		-- 1.3.6.1.4.1.10428 9 1.101.5.4.1.1.10
		fkCpuIntvlStatsRxUcastPkts OBJECT-TYPE
			SYNTAX Counter64
			MAX-ACCESS read-only
			STATUS current
			DESCRIPTION
				"The Average value of the rxUnicast that have been transmitted to CPU during fkCpuIntvlStatsInterval
				Unit: Packets/ fkCpuIntvlStatsInterval
				"
			::= { fkCpuIntervalStatisticsEntry 10 }

		
		-- 1.3.6.1.4.1.10428 9 1.101.5.4.1.1.11
		fkCpuIntvlStatsRxMcastPkts OBJECT-TYPE
			SYNTAX Counter64
			MAX-ACCESS read-only
			STATUS current
			DESCRIPTION
				"The Average value of the rxMulticast that have been transmitted to CPU during fkCpuIntvlStatsInterval
				Unit: Packets/ fkCpuIntvlStatsInterval
				"
			::= { fkCpuIntervalStatisticsEntry 11 }

		
		-- 1.3.6.1.4.1.10428 9 1.101.5.4.1.1.12
		fkCpuIntvlStatsRxBcastPkts OBJECT-TYPE
			SYNTAX Counter64
			MAX-ACCESS read-only
			STATUS current
			DESCRIPTION
				"The Average value of the rxBroadcast that have been transmitted to CPU during fkCpuIntvlStatsInterval
				Unit: Packets/ fkCpuIntvlStatsInterval
				"
			::= { fkCpuIntervalStatisticsEntry 12 }

		
		-- 1.3.6.1.4.1.10428 9 1.101.5.4.1.1.13
		fkCpuIntvlStatsRxUcastBytes OBJECT-TYPE
			SYNTAX Counter64
			MAX-ACCESS read-only
			STATUS current
			DESCRIPTION
				"The Average value of the rxUnicast that have been transmitted to CPU during fkCpuIntvlStatsInterval
				Unit: Bytes/ fkCpuIntvlStatsInterval
				"
			::= { fkCpuIntervalStatisticsEntry 13 }

		
		-- 1.3.6.1.4.1.10428 9 1.101.5.4.1.1.14
		fkCpuIntvlStatsRxMcastBytes OBJECT-TYPE
			SYNTAX Counter64
			MAX-ACCESS read-only
			STATUS current
			DESCRIPTION
				"The Average value of the rxMulticast that have been transmitted to CPU during fkCpuIntvlStatsInterval
				Unit: Bytes/ fkCpuIntvlStatsInterval
				"
			::= { fkCpuIntervalStatisticsEntry 14 }

		
		-- 1.3.6.1.4.1.10428 9 1.101.5.4.1.1.15
		fkCpuIntvlStatsRxBcastBytes OBJECT-TYPE
			SYNTAX Counter64
			MAX-ACCESS read-only
			STATUS current
			DESCRIPTION
				"The Average value of the rxBroadcast that have been transmitted to CPU during fkCpuIntvlStatsInterval
				Unit: Bytes/ fkCpuIntvlStatsInterval
				"
			::= { fkCpuIntervalStatisticsEntry 15 }

		
		-- 1.3.6.1.4.1.10428 9 1.101.5.4.2
		fkCpuStatisticsTable OBJECT-TYPE
			SYNTAX SEQUENCE OF FkCpuStatisticsEntry
			MAX-ACCESS not-accessible
			STATUS current
			DESCRIPTION
				"Description."
			::= { fkCpuStatistics 2 }

		
		-- 1.3.6.1.4.1.10428 9 1.101.5.4.2.1
		fkCpuStatisticsEntry OBJECT-TYPE
			SYNTAX FkCpuStatisticsEntry
			MAX-ACCESS not-accessible
			STATUS current
			DESCRIPTION
				"Description."
			INDEX { fkCpuStatsPortIndex }
			::= { fkCpuStatisticsTable 1 }

		
		FkCpuStatisticsEntry ::=
			SEQUENCE { 
				fkCpuStatsPortIndex
					InterfaceIndex,
				fkCpuStatsTxUcastPkts
					Counter64,
				fkCpuStatsTxMcastPkts
					Counter64,
				fkCpuStatsTxBcastPkts
					Counter64,
				fkCpuStatsTxUcastBytes
					Counter64,
				fkCpuStatsTxMcastBytes
					Counter64,
				fkCpuStatsTxBcastBytes
					Counter64,
				fkCpuStatsRxUcastPkts
					Counter64,
				fkCpuStatsRxMcastPkts
					Counter64,
				fkCpuStatsRxBcastPkts
					Counter64,
				fkCpuStatsRxUcastBytes
					Counter64,
				fkCpuStatsRxMcastBytes
					Counter64,
				fkCpuStatsRxBcastBytes
					Counter64
			 }

		-- 1.3.6.1.4.1.10428 9 1.101.5.4.2.1.1
		fkCpuStatsPortIndex OBJECT-TYPE
			SYNTAX InterfaceIndex
			MAX-ACCESS read-only
			STATUS current
			DESCRIPTION
				"Port index of EthernetPort, only valid for physical ports."
			::= { fkCpuStatisticsEntry 1 }

		
		-- 1.3.6.1.4.1.10428 9 1.101.5.4.2.1.2
		fkCpuStatsTxUcastPkts OBJECT-TYPE
			SYNTAX Counter64
			UNITS "Bytes"
			MAX-ACCESS read-only
			STATUS current
			DESCRIPTION
				"The Total value of the txUnicast that have been transmitted to CPU 
				Unit : Packets
				"
			::= { fkCpuStatisticsEntry 2 }

		
		-- 1.3.6.1.4.1.10428 9 1.101.5.4.2.1.3
		fkCpuStatsTxMcastPkts OBJECT-TYPE
			SYNTAX Counter64
			UNITS "Bytes"
			MAX-ACCESS read-only
			STATUS current
			DESCRIPTION
				"The Total value of the txMulticast that have been transmitted to CPU 
				Unit : Packets
				"
			::= { fkCpuStatisticsEntry 3 }

		
		-- 1.3.6.1.4.1.10428 9 1.101.5.4.2.1.4
		fkCpuStatsTxBcastPkts OBJECT-TYPE
			SYNTAX Counter64
			UNITS "Bytes"
			MAX-ACCESS read-only
			STATUS current
			DESCRIPTION
				"The Total value of the txBroadcast that have been transmitted to CPU 
				Unit : Packets
				"
			::= { fkCpuStatisticsEntry 4 }

		
		-- 1.3.6.1.4.1.10428 9 1.101.5.4.2.1.5
		fkCpuStatsTxUcastBytes OBJECT-TYPE
			SYNTAX Counter64
			UNITS "Bytes"
			MAX-ACCESS read-only
			STATUS current
			DESCRIPTION
				"The Total value of the txUnicast that have been transmitted to CPU 
				Unit : Bytes
				"
			::= { fkCpuStatisticsEntry 5 }

		
		-- 1.3.6.1.4.1.10428 9 1.101.5.4.2.1.6
		fkCpuStatsTxMcastBytes OBJECT-TYPE
			SYNTAX Counter64
			UNITS "Bytes"
			MAX-ACCESS read-only
			STATUS current
			DESCRIPTION
				"The Total value of the txMulticast that have been transmitted to CPU 
				Unit : Bytes
				"
			::= { fkCpuStatisticsEntry 6 }

		
		-- 1.3.6.1.4.1.10428 9 1.101.5.4.2.1.7
		fkCpuStatsTxBcastBytes OBJECT-TYPE
			SYNTAX Counter64
			UNITS "Bytes"
			MAX-ACCESS read-only
			STATUS current
			DESCRIPTION
				"The Total value of the txBroadcast that have been transmitted to CPU 
				Unit : Bytes
				"
			::= { fkCpuStatisticsEntry 7 }

		
		-- 1.3.6.1.4.1.10428 9 1.101.5.4.2.1.8
		fkCpuStatsRxUcastPkts OBJECT-TYPE
			SYNTAX Counter64
			UNITS "Bytes"
			MAX-ACCESS read-only
			STATUS current
			DESCRIPTION
				"The Total value of the rxUnicast that have been transmitted to CPU 
				Unit : Packets
				"
			::= { fkCpuStatisticsEntry 8 }

		
		-- 1.3.6.1.4.1.10428 9 1.101.5.4.2.1.9
		fkCpuStatsRxMcastPkts OBJECT-TYPE
			SYNTAX Counter64
			UNITS "Bytes"
			MAX-ACCESS read-only
			STATUS current
			DESCRIPTION
				"The Total value of the rxMulticast that have been transmitted to CPU 
				Unit : Packets
				"
			::= { fkCpuStatisticsEntry 9 }

		
		-- 1.3.6.1.4.1.10428 9 1.101.5.4.2.1.10
		fkCpuStatsRxBcastPkts OBJECT-TYPE
			SYNTAX Counter64
			UNITS "Bytes"
			MAX-ACCESS read-only
			STATUS current
			DESCRIPTION
				"The Total value of the rxBroadcast that have been transmitted to CPU 
				Unit : Packets
				"
			::= { fkCpuStatisticsEntry 10 }

		
		-- 1.3.6.1.4.1.10428 9 1.101.5.4.2.1.11
		fkCpuStatsRxUcastBytes OBJECT-TYPE
			SYNTAX Counter64
			UNITS "Bytes"
			MAX-ACCESS read-only
			STATUS current
			DESCRIPTION
				"The Total value of the rxUnicast that have been transmitted to CPU 
				Unit : Bytes
				"
			::= { fkCpuStatisticsEntry 11 }

		
		-- 1.3.6.1.4.1.10428 9 1.101.5.4.2.1.12
		fkCpuStatsRxMcastBytes OBJECT-TYPE
			SYNTAX Counter64
			UNITS "Bytes"
			MAX-ACCESS read-only
			STATUS current
			DESCRIPTION
				"The Total value of the rxMulticast that have been transmitted to CPU 
				Unit : Bytes
				"
			::= { fkCpuStatisticsEntry 12 }

		
		-- 1.3.6.1.4.1.10428 9 1.101.5.4.2.1.13
		fkCpuStatsRxBcastBytes OBJECT-TYPE
			SYNTAX Counter64
			UNITS "Bytes"
			MAX-ACCESS read-only
			STATUS current
			DESCRIPTION
				"The Total value of the trMulticast that have been transmitted to CPU 
				Unit : Bytes
				"
			::= { fkCpuStatisticsEntry 13 }

		
		-- 1.3.6.1.4.1.10428 9 1.101.5.4.3
		fkCpuStatisticsControl OBJECT IDENTIFIER ::= { fkCpuStatistics 3 }

		
		-- 1.3.6.1.4.1.10428 9 1.101.5.4.3.1
		fkCpuStatsControlRequest OBJECT-TYPE
			SYNTAX INTEGER { clearCpuStatistics(1) }
			MAX-ACCESS read-write
			STATUS current
			DESCRIPTION
				"Description."
			::= { fkCpuStatisticsControl 1 }

		
		-- 1.3.6.1.4.1.10428 9 1.101.5.4.3.2
		fkCpuStatsControlStatus OBJECT-TYPE
			SYNTAX FkControlStatusType
			MAX-ACCESS read-only
			STATUS current
			DESCRIPTION
				"Description."
			::= { fkCpuStatisticsControl 2 }

		
		-- 1.3.6.1.4.1.10428 9 1.101.5.4.3.3
		fkCpuStatsControlTimer OBJECT-TYPE
			SYNTAX Gauge32
			MAX-ACCESS read-write
			STATUS current
			DESCRIPTION
				"Description."
			::= { fkCpuStatisticsControl 3 }

		
		-- 1.3.6.1.4.1.10428 9 1.101.5.4.3.4
		fkCpuStatsControlTimeStamp OBJECT-TYPE
			SYNTAX TimeTicks
			MAX-ACCESS read-only
			STATUS current
			DESCRIPTION
				"Description."
			::= { fkCpuStatisticsControl 4 }

		
		-- 1.3.6.1.4.1.10428 9 1.101.5.4.3.5
		fkCpuStatsControlReqResult OBJECT-TYPE
			SYNTAX FkControlRequestResultType
			MAX-ACCESS read-only
			STATUS current
			DESCRIPTION
				"Description."
			::= { fkCpuStatisticsControl 5 }

		
		-- 1.3.6.1.4.1.10428 9 1.101.5.4.3.6
		fkCpuStatsControlIndex OBJECT-TYPE
			SYNTAX InterfaceIndex
			MAX-ACCESS read-write
			STATUS current
			DESCRIPTION
				"Description."
			::= { fkCpuStatisticsControl 6 }

		
		-- 1.3.6.1.4.1.10428 9 1.101.5.4.4
		fkCpuStatisticsNotification OBJECT IDENTIFIER ::= { fkCpuStatistics 4 }

		
		-- 1.3.6.1.4.1.10428 9 1.101.5.4.4.1
		fkCpuStatisticsCleared NOTIFICATION-TYPE
			OBJECTS { fkCpuStatsControlRequest, fkCpuStatsControlTimeStamp, fkCpuStatsControlReqResult, fkCpuStatsPortIndex }
			STATUS current
			DESCRIPTION 
				"Description."
			::= { fkCpuStatisticsNotification 1 }

		
		-- 1.3.6.1.4.1.10428 9 1.101.5.5
		fkPerformanceBase OBJECT IDENTIFIER ::= { fkPerformanceMgmt 5 }

		
		-- 1.3.6.1.4.1.10428 9 1.101.5.5.1
		fkPerformanceBaseInfo OBJECT IDENTIFIER ::= { fkPerformanceBase 1 }

		
		-- 1.3.6.1.4.1.10428 9 1.101.5.5.1.1
		fkPerformanceBaseProtoStatsEnable OBJECT-TYPE
			SYNTAX BITS
				{
				arp(0),
				ip(1),
				icmp(2),
				tcp(3),
				udp(4)
				}
			MAX-ACCESS read-only
			STATUS current
			DESCRIPTION
				"The admin status of gathering each protocol statistics
				"
			::= { fkPerformanceBaseInfo 1 }

		
		-- 1.3.6.1.4.1.10428 9 1.101.5.5.1.2
		fkPerformanceBaseCpuPpsStatus OBJECT-TYPE
			SYNTAX INTEGER
				{
				enable(1),
				disable(2)
				}
			MAX-ACCESS read-only
			STATUS current
			DESCRIPTION
				"The Cpu PPS status."
			::= { fkPerformanceBaseInfo 2 }

		
		-- 1.3.6.1.4.1.10428 9 1.101.5.5.1.3
		fkPerformanceBaseCpuPpsThreshold OBJECT-TYPE
			SYNTAX Unsigned32
			MAX-ACCESS read-only
			STATUS current
			DESCRIPTION
				"The CPU PPS threshold."
			::= { fkPerformanceBaseInfo 3 }

		
		-- 1.3.6.1.4.1.10428 9 1.101.5.5.1.4
		fkPerformanceBaseCpuPpsAvg OBJECT-TYPE
			SYNTAX Unsigned32
			MAX-ACCESS read-only
			STATUS current
			DESCRIPTION
				"The CPU PPS average."
			::= { fkPerformanceBaseInfo 4 }

		
		-- 1.3.6.1.4.1.10428 9 1.101.5.5.2
		fkPerformanceBaseControl OBJECT IDENTIFIER ::= { fkPerformanceBase 2 }

		
		-- 1.3.6.1.4.1.10428 9 1.101.5.5.2.1
		fkPerformanceBaseControlRequest OBJECT-TYPE
			SYNTAX INTEGER
				{
				setProtocolStatsEnable(1),
				setPsetCpuPpsProfile(2)
				}
			MAX-ACCESS read-write
			STATUS current
			DESCRIPTION
				"Description."
			::= { fkPerformanceBaseControl 1 }

		
		-- 1.3.6.1.4.1.10428 9 1.101.5.5.2.2
		fkPerformanceBaseControlStatus OBJECT-TYPE
			SYNTAX FkControlStatusType
			MAX-ACCESS read-only
			STATUS current
			DESCRIPTION
				"Description."
			::= { fkPerformanceBaseControl 2 }

		
		-- 1.3.6.1.4.1.10428 9 1.101.5.5.2.3
		fkPerformanceBaseControlTimer OBJECT-TYPE
			SYNTAX Gauge32
			MAX-ACCESS read-write
			STATUS current
			DESCRIPTION
				"Description."
			::= { fkPerformanceBaseControl 3 }

		
		-- 1.3.6.1.4.1.10428 9 1.101.5.5.2.4
		fkPerformanceBaseControlTimeStamp OBJECT-TYPE
			SYNTAX TimeTicks
			MAX-ACCESS read-only
			STATUS current
			DESCRIPTION
				"Description."
			::= { fkPerformanceBaseControl 4 }

		
		-- 1.3.6.1.4.1.10428 9 1.101.5.5.2.5
		fkPerformanceBaseControlReqResult OBJECT-TYPE
			SYNTAX FkControlRequestResultType
			MAX-ACCESS read-only
			STATUS current
			DESCRIPTION
				"Description."
			::= { fkPerformanceBaseControl 5 }

		
		-- 1.3.6.1.4.1.10428 9 1.101.5.5.2.6
		fkPerformanceBaseControlProtoStatsEnable OBJECT-TYPE
			SYNTAX BITS
				{
				arp(0),
				ip(1),
				icmp(2),
				tcp(3),
				udp(4)
				}
			MAX-ACCESS read-write
			STATUS current
			DESCRIPTION
				"The admin status of gathering 
				each protocol statistics"
			::= { fkPerformanceBaseControl 6 }

		
		-- 1.3.6.1.4.1.10428 9 1.101.5.5.2.7
		fkPerformanceBaseControlCpuPpsStatus OBJECT-TYPE
			SYNTAX INTEGER
				{
				enable(1),
				disable(2)
				}
			MAX-ACCESS read-write
			STATUS current
			DESCRIPTION
				"The Cpu PPS status."
			::= { fkPerformanceBaseControl 7 }

		
		-- 1.3.6.1.4.1.10428 9 1.101.5.5.2.8
		fkPerformanceBaseControlCpuPpsThreshold OBJECT-TYPE
			SYNTAX Unsigned32
			MAX-ACCESS read-write
			STATUS current
			DESCRIPTION
				"The CPU PPS threshold."
			::= { fkPerformanceBaseControl 8 }

		
		-- 1.3.6.1.4.1.10428 9 1.101.5.5.3
		fkPerformanceBaseNotification OBJECT IDENTIFIER ::= { fkPerformanceBase 3 }

		
		-- 1.3.6.1.4.1.10428 9 1.101.5.5.3.1
		fkPerformanceBaseProtoStatsChanged NOTIFICATION-TYPE
			OBJECTS { fkPerformanceBaseControlRequest, fkPerformanceBaseControlTimeStamp, fkPerformanceBaseControlReqResult, fkPerformanceBaseControlProtoStatsEnable }
			STATUS current
			DESCRIPTION 
				"Description."
			::= { fkPerformanceBaseNotification 1 }

		
		-- 1.3.6.1.4.1.10428 9 1.101.5.5.3.2
		fkPerformanceBaseCpuPpsProfileChanged NOTIFICATION-TYPE
			OBJECTS { fkPerformanceBaseControlRequest, fkPerformanceBaseControlTimeStamp, fkPerformanceBaseControlReqResult, fkPerformanceBaseControlCpuPpsStatus, fkPerformanceBaseControlCpuPpsThreshold
				 }
			STATUS current
			DESCRIPTION 
				"setPsetCpuPpsProfile"
			::= { fkPerformanceBaseNotification 2 }

		
--   Node definitions
-- 
-- 1.3.6.1.4.1.10428 9 1.101.5.6
		-- 1.3.6.1.4.1.10428 9 1.101.5.6
		fkSfpmonThreshold OBJECT IDENTIFIER ::= { fkPerformanceMgmt 6 }

		
--  1.3.6.1.4.1.10428 9 1.101.5.6.1
		-- 1.3.6.1.4.1.10428 9 1.101.5.6.1
		fkSfpmonThresholdTable OBJECT-TYPE
			SYNTAX SEQUENCE OF FkSfpmonThresholdEntry
			MAX-ACCESS not-accessible
			STATUS current
			DESCRIPTION
				"Description."
			::= { fkSfpmonThreshold 1 }

		
--  1.3.6.1.4.1.10428 9 1.101.5.6.1.1
		-- 1.3.6.1.4.1.10428 9 1.101.5.6.1.1
		fkSfpmonThresholdEntry OBJECT-TYPE
			SYNTAX FkSfpmonThresholdEntry
			MAX-ACCESS not-accessible
			STATUS current
			DESCRIPTION
				"Description."
			INDEX { fkSfpmonThresholdIndex }
			::= { fkSfpmonThresholdTable 1 }

		
		FkSfpmonThresholdEntry ::=
			SEQUENCE { 
				fkSfpmonThresholdIndex
					INTEGER,
				fkSfpmonWarnTxPowerLow
					Integer32,
				fkSfpmonWarnTxPowerHigh
					Integer32,
				fkSfpmonWarnTxPowerDuration
					INTEGER,
				fkSfpmonWarnRxPowerLow
					Integer32,
				fkSfpmonWarnRxPowerHigh
					Integer32,
				fkSfpmonWarnRxPowerDuration
					INTEGER,
				fkSfpmonAlarmTxPowerLow
					Integer32,
				fkSfpmonAlarmTxPowerHigh
					Integer32,
				fkSfpmonAlarmTxPowerDuration
					INTEGER,
				fkSfpmonAlarmRxPowerLow
					Integer32,
				fkSfpmonAlarmRxPowerHigh
					Integer32,
				fkSfpmonAlarmRxPowerDuration
					INTEGER,
				fkSfpmonWarnTxbiasLow
					Integer32,
				fkSfpmonWarnTxbiasHigh
					Integer32,
				fkSfpmonAlarmTxbiasLow
					Integer32,
				fkSfpmonAlarmTxbiasHigh
					Integer32,
				fkSfpmonWarnTemperLow
					Integer32,
				fkSfpmonWarnTemperHigh
					Integer32,
				fkSfpmonAlarmTemperLow
					Integer32,
				fkSfpmonAlarmTemperHigh
					Integer32,
				fkSfpmonWarnVoltageLow
					Integer32,
				fkSfpmonWarnVoltageHigh
					Integer32,
				fkSfpmonAlarmVoltageLow
					Integer32,
				fkSfpmonAlarmVoltageHigh
					Integer32
			 }

--  1.3.6.1.4.1.10428 9 1.101.5.6.1.1.1
		-- 1.3.6.1.4.1.10428 9 1.101.5.6.1.1.1
		fkSfpmonThresholdIndex OBJECT-TYPE
			SYNTAX INTEGER (1..255)
			MAX-ACCESS read-only
			STATUS current
			DESCRIPTION
				"port index."
			::= { fkSfpmonThresholdEntry 1 }

		
--  1.3.6.1.4.1.10428 9 1.101.5.6.1.1.2
		-- 1.3.6.1.4.1.10428 9 1.101.5.6.1.1.2
		fkSfpmonWarnTxPowerLow OBJECT-TYPE
			SYNTAX Integer32
			MAX-ACCESS read-only
			STATUS current
			DESCRIPTION
				"The Power threshold -40~8,1647 (dBm)
				It must be devided by 10000.
				"
			::= { fkSfpmonThresholdEntry 2 }

		
--  1.3.6.1.4.1.10428 9 1.101.5.6.1.1.3
		-- 1.3.6.1.4.1.10428 9 1.101.5.6.1.1.3
		fkSfpmonWarnTxPowerHigh OBJECT-TYPE
			SYNTAX Integer32
			MAX-ACCESS read-only
			STATUS current
			DESCRIPTION
				"The Power threshold -40~8,1647 (dBm)
				It must be devided by 10000."
			::= { fkSfpmonThresholdEntry 3 }

		
--  1.3.6.1.4.1.10428 9 1.101.5.6.1.1.4
		-- 1.3.6.1.4.1.10428 9 1.101.5.6.1.1.4
		fkSfpmonWarnTxPowerDuration OBJECT-TYPE
			SYNTAX INTEGER (1..65535)
			MAX-ACCESS read-only
			STATUS current
			DESCRIPTION
				"Duration-time units by the 10 sec"
			::= { fkSfpmonThresholdEntry 4 }

		
--  1.3.6.1.4.1.10428 9 1.101.5.6.1.1.5
		-- 1.3.6.1.4.1.10428 9 1.101.5.6.1.1.5
		fkSfpmonWarnRxPowerLow OBJECT-TYPE
			SYNTAX Integer32
			MAX-ACCESS read-only
			STATUS current
			DESCRIPTION
				"The Power threshold -40~8,1647 (dBm)
				It must be devided by 10000.
				"
			::= { fkSfpmonThresholdEntry 5 }

		
--  1.3.6.1.4.1.10428 9 1.101.5.6.1.1.6
		-- 1.3.6.1.4.1.10428 9 1.101.5.6.1.1.6
		fkSfpmonWarnRxPowerHigh OBJECT-TYPE
			SYNTAX Integer32
			MAX-ACCESS read-only
			STATUS current
			DESCRIPTION
				"The Power threshold -40~8,1647 (dBm)
				It must be devided by 10000.
				"
			::= { fkSfpmonThresholdEntry 6 }

		
--  1.3.6.1.4.1.10428 9 1.101.5.6.1.1.7
		-- 1.3.6.1.4.1.10428 9 1.101.5.6.1.1.7
		fkSfpmonWarnRxPowerDuration OBJECT-TYPE
			SYNTAX INTEGER (1..65535)
			MAX-ACCESS read-only
			STATUS current
			DESCRIPTION
				"Duration-time units by the 10 sec"
			::= { fkSfpmonThresholdEntry 7 }

		
--  1.3.6.1.4.1.10428 9 1.101.5.6.1.1.8
		-- 1.3.6.1.4.1.10428 9 1.101.5.6.1.1.8
		fkSfpmonAlarmTxPowerLow OBJECT-TYPE
			SYNTAX Integer32
			MAX-ACCESS read-only
			STATUS current
			DESCRIPTION
				"The Power threshold -40~8,1647 (dBm)
				It must be devided by 10000.
				"
			::= { fkSfpmonThresholdEntry 8 }

		
--  1.3.6.1.4.1.10428 9 1.101.5.6.1.1.9
		-- 1.3.6.1.4.1.10428 9 1.101.5.6.1.1.9
		fkSfpmonAlarmTxPowerHigh OBJECT-TYPE
			SYNTAX Integer32
			MAX-ACCESS read-only
			STATUS current
			DESCRIPTION
				"The Power threshold -40~8,1647 (dBm)
				It must be devided by 10000.
				"
			::= { fkSfpmonThresholdEntry 9 }

		
--  1.3.6.1.4.1.10428 9 1.101.5.6.1.1.10
		-- 1.3.6.1.4.1.10428 9 1.101.5.6.1.1.10
		fkSfpmonAlarmTxPowerDuration OBJECT-TYPE
			SYNTAX INTEGER (1..65535)
			MAX-ACCESS read-only
			STATUS current
			DESCRIPTION
				"Duration-time units by the 10 sec"
			::= { fkSfpmonThresholdEntry 10 }

		
--  1.3.6.1.4.1.10428 9 1.101.5.6.1.1.11
		-- 1.3.6.1.4.1.10428 9 1.101.5.6.1.1.11
		fkSfpmonAlarmRxPowerLow OBJECT-TYPE
			SYNTAX Integer32
			MAX-ACCESS read-only
			STATUS current
			DESCRIPTION
				"The Power threshold -40~8,1647 (dBm)
				It must be devided by 10000.
				"
			::= { fkSfpmonThresholdEntry 11 }

		
--  1.3.6.1.4.1.10428 9 1.101.5.6.1.1.12
		-- 1.3.6.1.4.1.10428 9 1.101.5.6.1.1.12
		fkSfpmonAlarmRxPowerHigh OBJECT-TYPE
			SYNTAX Integer32
			MAX-ACCESS read-only
			STATUS current
			DESCRIPTION
				"The Power threshold -40~8,1647 (dBm)
				It must be devided by 10000.
				"
			::= { fkSfpmonThresholdEntry 12 }

		
--  1.3.6.1.4.1.10428 9 1.101.5.6.1.1.13
		-- 1.3.6.1.4.1.10428 9 1.101.5.6.1.1.13
		fkSfpmonAlarmRxPowerDuration OBJECT-TYPE
			SYNTAX INTEGER (1..65535)
			MAX-ACCESS read-only
			STATUS current
			DESCRIPTION
				"Duration-time units by the 10 sec"
			::= { fkSfpmonThresholdEntry 13 }

		
--  1.3.6.1.4.1.10428 9 1.101.5.6.1.1.13
		-- 1.3.6.1.4.1.10428 9 1.101.5.6.1.1.14
		fkSfpmonWarnTxbiasLow OBJECT-TYPE
			SYNTAX Integer32 (0..131)
			MAX-ACCESS read-only
			STATUS current
			DESCRIPTION
				"The Txbias Threshold 0~131(mA)
				It must be devided by 10000.
				"
			::= { fkSfpmonThresholdEntry 14 }

		
--  1.3.6.1.4.1.10428 9 1.101.5.6.1.1.13
		-- 1.3.6.1.4.1.10428 9 1.101.5.6.1.1.15
		fkSfpmonWarnTxbiasHigh OBJECT-TYPE
			SYNTAX Integer32 (0..131)
			MAX-ACCESS read-only
			STATUS current
			DESCRIPTION
				"The Txbias Threshold 0~131(mA)
				It must be devided by 10000."
			::= { fkSfpmonThresholdEntry 15 }

		
--  1.3.6.1.4.1.10428 9 1.101.5.6.1.1.13
		-- 1.3.6.1.4.1.10428 9 1.101.5.6.1.1.16
		fkSfpmonAlarmTxbiasLow OBJECT-TYPE
			SYNTAX Integer32 (0..131)
			MAX-ACCESS read-only
			STATUS current
			DESCRIPTION
				"The Txbias Threshold 0~131(mA)
				It must be devided by 10000.
				"
			::= { fkSfpmonThresholdEntry 16 }

		
--  1.3.6.1.4.1.10428 9 1.101.5.6.1.1.13
		-- 1.3.6.1.4.1.10428 9 1.101.5.6.1.1.17
		fkSfpmonAlarmTxbiasHigh OBJECT-TYPE
			SYNTAX Integer32 (0..131)
			MAX-ACCESS read-only
			STATUS current
			DESCRIPTION
				"The Txbias Threshold 0~131(mA)
				It must be devided by 10000.
				"
			::= { fkSfpmonThresholdEntry 17 }

		
		-- 1.3.6.1.4.1.10428 9 1.101.5.6.1.1.18
		fkSfpmonWarnTemperLow OBJECT-TYPE
			SYNTAX Integer32
			MAX-ACCESS read-only
			STATUS current
			DESCRIPTION
				"The Temperature threshold -128~127.99(C)
				It must be devided by 10000."
			::= { fkSfpmonThresholdEntry 18 }

		
		-- 1.3.6.1.4.1.10428 9 1.101.5.6.1.1.19
		fkSfpmonWarnTemperHigh OBJECT-TYPE
			SYNTAX Integer32
			MAX-ACCESS read-only
			STATUS current
			DESCRIPTION
				"The Temperature threshold -128~127.99(C)
				It must be devided by 10000."
			::= { fkSfpmonThresholdEntry 19 }

		
		-- 1.3.6.1.4.1.10428 9 1.101.5.6.1.1.20
		fkSfpmonAlarmTemperLow OBJECT-TYPE
			SYNTAX Integer32
			MAX-ACCESS read-only
			STATUS current
			DESCRIPTION
				"The Temperature threshold -128~127.99(C)
				It must be devided by 10000."
			::= { fkSfpmonThresholdEntry 20 }

		
		-- 1.3.6.1.4.1.10428 9 1.101.5.6.1.1.21
		fkSfpmonAlarmTemperHigh OBJECT-TYPE
			SYNTAX Integer32
			MAX-ACCESS read-only
			STATUS current
			DESCRIPTION
				"The Temperature threshold -128~127.99(C)
				It must be devided by 10000."
			::= { fkSfpmonThresholdEntry 21 }

		
		-- 1.3.6.1.4.1.10428 9 1.101.5.6.1.1.22
		fkSfpmonWarnVoltageLow OBJECT-TYPE
			SYNTAX Integer32
			MAX-ACCESS read-only
			STATUS current
			DESCRIPTION
				"The Voltage threshold 0~6.5535(V)
				It must be devided by 10000"
			::= { fkSfpmonThresholdEntry 22 }

		
		-- 1.3.6.1.4.1.10428 9 1.101.5.6.1.1.23
		fkSfpmonWarnVoltageHigh OBJECT-TYPE
			SYNTAX Integer32
			MAX-ACCESS read-only
			STATUS current
			DESCRIPTION
				"The Voltage threshold 0~6.5535(V)
				It must be devided by 10000"
			::= { fkSfpmonThresholdEntry 23 }

		
		-- 1.3.6.1.4.1.10428 9 1.101.5.6.1.1.24
		fkSfpmonAlarmVoltageLow OBJECT-TYPE
			SYNTAX Integer32
			MAX-ACCESS read-only
			STATUS current
			DESCRIPTION
				"The Voltage threshold 0~6.5535(V)
				It must be devided by 10000"
			::= { fkSfpmonThresholdEntry 24 }

		
		-- 1.3.6.1.4.1.10428 9 1.101.5.6.1.1.25
		fkSfpmonAlarmVoltageHigh OBJECT-TYPE
			SYNTAX Integer32
			MAX-ACCESS read-only
			STATUS current
			DESCRIPTION
				"The Voltage threshold 0~6.5535(V)
				It must be devided by 10000"
			::= { fkSfpmonThresholdEntry 25 }

		
--  1.3.6.1.4.1.10428 9 1.101.5.6.2
		-- 1.3.6.1.4.1.10428 9 1.101.5.6.2
		fkSfpmonThresholdControl OBJECT IDENTIFIER ::= { fkSfpmonThreshold 2 }

		
--  1.3.6.1.4.1.10428 9 1.101.5.6.2.1
		-- 1.3.6.1.4.1.10428 9 1.101.5.6.2.1
		fkSfpmonThresholdControlRequest OBJECT-TYPE
			SYNTAX INTEGER
				{
				setSfpmonThresholdWarnTxPower(1),
				setSfpmonThresholdWarnRxPower(2),
				setSfpmonThresholdAlarmTxPower(3),
				setSfpmonThresholdAlarmRxPower(4),
				clearSfpmonThresholdWarnTxPower(5),
				clearSfpmonThresholdWarnRxPower(6),
				clearSfpmonThresholdAlarmTxPower(7),
				clearSfpmonThresholdAlarmRxPower(8),
				setSfpmonThresholdWarnTxbias(9),
				setSfpmonThresholdAlarmTxbias(10),
				clearSfpmonThresholdWarnTxbias(11),
				clearSfpmonThresholdAlarmTxbias(12),
				setSfpmonThresholdWarnTemper(13),
				setSfpmonThresholdAlarmTemper(14),
				clearSfpmonThresholdWarnTemper(15),
				clearSfpmonThresholdAlarmTemper(16),
				setSfpmonThresholdWarnVoltage(17),
				setSfpmonThresholdAlarmVoltage(18),
				clearSfpmonThresholdWarnVoltage(19),
				clearSfpmonThresholdAlarmVoltage(20)
				}
			MAX-ACCESS read-write
			STATUS current
			DESCRIPTION
				"Description."
			::= { fkSfpmonThresholdControl 1 }

		
--  1.3.6.1.4.1.10428 9 1.101.5.6.2.2
		-- 1.3.6.1.4.1.10428 9 1.101.5.6.2.2
		fkSfpmonThresholdControlStatus OBJECT-TYPE
			SYNTAX FkControlStatusType
			MAX-ACCESS read-only
			STATUS current
			DESCRIPTION
				"Description."
			::= { fkSfpmonThresholdControl 2 }

		
--  1.3.6.1.4.1.10428 9 1.101.5.6.2.3
		-- 1.3.6.1.4.1.10428 9 1.101.5.6.2.3
		fkSfpmonThresholdControlTimer OBJECT-TYPE
			SYNTAX Gauge32
			MAX-ACCESS read-write
			STATUS current
			DESCRIPTION
				"Description."
			::= { fkSfpmonThresholdControl 3 }

		
--  1.3.6.1.4.1.10428 9 1.101.5.6.2.4
		-- 1.3.6.1.4.1.10428 9 1.101.5.6.2.4
		fkSfpmonThresholdControlTimeStamp OBJECT-TYPE
			SYNTAX TimeTicks
			MAX-ACCESS read-only
			STATUS current
			DESCRIPTION
				"Description."
			::= { fkSfpmonThresholdControl 4 }

		
--  1.3.6.1.4.1.10428 9 1.101.5.6.2.5
		-- 1.3.6.1.4.1.10428 9 1.101.5.6.2.5
		fkSfpmonThresholdControlReqResult OBJECT-TYPE
			SYNTAX FkControlRequestResultType
			MAX-ACCESS read-only
			STATUS current
			DESCRIPTION
				"Description."
			::= { fkSfpmonThresholdControl 5 }

		
--  1.3.6.1.4.1.10428 9 1.101.5.6.2.6
		-- 1.3.6.1.4.1.10428 9 1.101.5.6.2.6
		fkSfpmonThresholdControlIndex OBJECT-TYPE
			SYNTAX INTEGER (1..255)
			MAX-ACCESS read-write
			STATUS current
			DESCRIPTION
				"Description."
			::= { fkSfpmonThresholdControl 6 }

		
--  1.3.6.1.4.1.10428 9 1.101.5.6.2.7
		-- 1.3.6.1.4.1.10428 9 1.101.5.6.2.7
		fkSfpmonThresholdControlPowerLow OBJECT-TYPE
			SYNTAX Integer32
			MAX-ACCESS read-write
			STATUS current
			DESCRIPTION
				"Power threshold in dBm -40 ~ 8.1647 (dBm)
				It must be multiplied by 10000."
			::= { fkSfpmonThresholdControl 7 }

		
--  1.3.6.1.4.1.10428 9 1.101.5.6.2.8
		-- 1.3.6.1.4.1.10428 9 1.101.5.6.2.8
		fkSfpmonThresholdControlPowerHigh OBJECT-TYPE
			SYNTAX Integer32
			MAX-ACCESS read-write
			STATUS current
			DESCRIPTION
				"Power threshold in dBm -40 ~ 8.1647 (dBm)
				It must be multiplied by 10000."
			::= { fkSfpmonThresholdControl 8 }

		
--  1.3.6.1.4.1.10428 9 1.101.5.6.2.9
		-- 1.3.6.1.4.1.10428 9 1.101.5.6.2.9
		fkSfpmonThresholdControlPowerDuration OBJECT-TYPE
			SYNTAX INTEGER (5..300)
			MAX-ACCESS read-write
			STATUS current
			DESCRIPTION
				"Duration-time units by the 10 sec"
			::= { fkSfpmonThresholdControl 9 }

		
--  1.3.6.1.4.1.10428 9 1.101.5.6.2.7
		-- 1.3.6.1.4.1.10428 9 1.101.5.6.2.10
		fkSfpmonThresholdControlTxbiasLow OBJECT-TYPE
			SYNTAX Integer32
			MAX-ACCESS read-write
			STATUS current
			DESCRIPTION
				"The Txbias 0~131 (mA)
				It must be multiplied by 10000."
			::= { fkSfpmonThresholdControl 10 }

		
--  1.3.6.1.4.1.10428 9 1.101.5.6.2.7
		-- 1.3.6.1.4.1.10428 9 1.101.5.6.2.11
		fkSfpmonThresholdControlTxbiasHigh OBJECT-TYPE
			SYNTAX Integer32
			MAX-ACCESS read-write
			STATUS current
			DESCRIPTION
				"The Txbias 0~131 (mA)
				It must be multiplied by 10000."
			::= { fkSfpmonThresholdControl 11 }

		
		-- 1.3.6.1.4.1.10428 9 1.101.5.6.2.12
		fkSfpmonThresholdControlTemperLow OBJECT-TYPE
			SYNTAX Integer32
			MAX-ACCESS read-write
			STATUS current
			DESCRIPTION
				"The Temperature threshold 0~131 (mA)
				It must be multiplied by 10000."
			::= { fkSfpmonThresholdControl 12 }

		
		-- 1.3.6.1.4.1.10428 9 1.101.5.6.2.13
		fkSfpmonThresholdControlTemperHigh OBJECT-TYPE
			SYNTAX Integer32
			MAX-ACCESS read-write
			STATUS current
			DESCRIPTION
				"The Temperature threshold 0~131 (mA)
				It must be multiplied by 10000."
			::= { fkSfpmonThresholdControl 13 }

		
		-- 1.3.6.1.4.1.10428 9 1.101.5.6.2.14
		fkSfpmonThresholdControlVoltageLow OBJECT-TYPE
			SYNTAX Integer32
			MAX-ACCESS read-write
			STATUS current
			DESCRIPTION
				"The voltage threshold 0~6.5535 (V)
				It must be multiplied by 10000."
			::= { fkSfpmonThresholdControl 14 }

		
		-- 1.3.6.1.4.1.10428 9 1.101.5.6.2.15
		fkSfpmonThresholdControlVoltageHigh OBJECT-TYPE
			SYNTAX Integer32
			MAX-ACCESS read-write
			STATUS current
			DESCRIPTION
				"The voltage threshold 0~6.5535 (V)
				It must be multiplied by 10000."
			::= { fkSfpmonThresholdControl 15 }

		
--  1.3.6.1.4.1.10428 9 1.101.5.6.3
		-- 1.3.6.1.4.1.10428 9 1.101.5.6.3
		fkSfpmonThresholdNotification OBJECT IDENTIFIER ::= { fkSfpmonThreshold 3 }

		
--  1.3.6.1.4.1.10428 9 1.101.5.6.3.1
		-- 1.3.6.1.4.1.10428 9 1.101.5.6.3.1
		fkSfpmonThresholdPowerChanged NOTIFICATION-TYPE
			OBJECTS { fkSfpmonThresholdIndex, fkSfpmonWarnTxPowerLow, fkSfpmonWarnTxPowerHigh, fkSfpmonWarnTxPowerDuration, fkSfpmonWarnRxPowerLow, 
				fkSfpmonWarnRxPowerHigh, fkSfpmonWarnRxPowerDuration, fkSfpmonAlarmTxPowerLow, fkSfpmonAlarmTxPowerHigh, fkSfpmonAlarmTxPowerDuration, 
				fkSfpmonAlarmRxPowerLow, fkSfpmonAlarmRxPowerHigh, fkSfpmonAlarmRxPowerDuration, fkSfpmonThresholdControlRequest, fkSfpmonThresholdControlTimeStamp, 
				fkSfpmonThresholdControlReqResult }
			STATUS current
			DESCRIPTION 
				"setSfpmonThresholdWarnTxPower
				setSfpmonThresholdWarnRxPower
				setSfpmonThresholdAlarmTxPower
				setSfpmonThresholdAlarmRxPower
				clearSfpmonThresholdWarnTxPower
				clearSfpmonThresholdWarnRxPower
				clearSfpmonThresholdAlarmTxPower
				clearSfpmonThresholdAlarmRxPower"
			::= { fkSfpmonThresholdNotification 1 }

		
		-- 1.3.6.1.4.1.10428 9 1.101.5.6.3.2
		fkSfpmonThresholdTxbiasChanged NOTIFICATION-TYPE
			OBJECTS { fkSfpmonThresholdControlRequest, fkSfpmonThresholdControlTimeStamp, fkSfpmonThresholdControlReqResult, fkSfpmonThresholdIndex, fkSfpmonWarnTxbiasLow, 
				fkSfpmonWarnTxbiasHigh, fkSfpmonAlarmTxbiasLow, fkSfpmonAlarmTxbiasHigh }
			STATUS current
			DESCRIPTION 
				"setSfpmonThresholdWarnTxbias
				setSfpmonThresholdAlarmTxbias
				clearSfpmonThresholdWarnTxbias
				clearSfpmonThresholdAlarmTxbias"
			::= { fkSfpmonThresholdNotification 2 }

		
		-- 1.3.6.1.4.1.10428 9 1.101.5.6.3.3
		fkSfpmonThresholdTemperChanged NOTIFICATION-TYPE
			OBJECTS { fkSfpmonThresholdControlRequest, fkSfpmonThresholdControlTimeStamp, fkSfpmonThresholdControlReqResult, fkSfpmonThresholdIndex, fkSfpmonWarnTemperLow, 
				fkSfpmonWarnTemperHigh, fkSfpmonAlarmTemperLow, fkSfpmonAlarmTemperHigh }
			STATUS current
			DESCRIPTION 
				"setSfpmonThresholdWarnTemper
				setSfpmonThresholdAlarmTemper
				clearSfpmonThresholdWarnTemper
				clearSfpmonThresholdAlarmTemper"
			::= { fkSfpmonThresholdNotification 3 }

		
		-- 1.3.6.1.4.1.10428 9 1.101.5.6.3.4
		fkSfpmonThresholdVoltageChanged NOTIFICATION-TYPE
			OBJECTS { fkSfpmonThresholdControlRequest, fkSfpmonThresholdControlTimeStamp, fkSfpmonThresholdControlReqResult, fkSfpmonThresholdIndex, fkSfpmonThresholdControlVoltageLow, 
				fkSfpmonThresholdControlVoltageHigh }
			STATUS current
			DESCRIPTION 
				"setSfpmonThresholdWarnVoltage
				setSfpmonThresholdAlarmVoltage
				clearSfpmonThresholdWarnVoltage
				clearSfpmonThresholdAlarmVoltage"
			::= { fkSfpmonThresholdNotification 4 }

		
		-- 1.3.6.1.4.1.10428 9 1.101.5.7
		fkVlanStatistics OBJECT IDENTIFIER ::= { fkPerformanceMgmt 7 }

		
		-- 1.3.6.1.4.1.10428 9 1.101.5.7.1
		fkVlanStatisticsTable OBJECT-TYPE
			SYNTAX SEQUENCE OF FkVlanStatisticsEntry
			MAX-ACCESS not-accessible
			STATUS current
			DESCRIPTION
				"Description."
			::= { fkVlanStatistics 1 }

		
		-- 1.3.6.1.4.1.10428 9 1.101.5.7.1.1
		fkVlanStatisticsEntry OBJECT-TYPE
			SYNTAX FkVlanStatisticsEntry
			MAX-ACCESS not-accessible
			STATUS current
			DESCRIPTION
				"Description."
			INDEX { fkVlanStatisticsIndex }
			::= { fkVlanStatisticsTable 1 }

		
		FkVlanStatisticsEntry ::=
			SEQUENCE { 
				fkVlanStatisticsIndex
					Integer32,
				fkVlanStatisticsIngressBytes
					Counter64,
				fkVlanStatisticsEgressBytes
					Counter64,
				fkVlanStatisticsIngressPackets
					Counter64,
				fkVlanStatisticsEgressPackets
					Counter64
			 }

		-- 1.3.6.1.4.1.10428 9 1.101.5.7.1.1.1
		fkVlanStatisticsIndex OBJECT-TYPE
			SYNTAX Integer32 (1..4094)
			MAX-ACCESS read-only
			STATUS current
			DESCRIPTION
				"The VLAN index."
			::= { fkVlanStatisticsEntry 1 }

		
		-- 1.3.6.1.4.1.10428 9 1.101.5.7.1.1.2
		fkVlanStatisticsIngressBytes OBJECT-TYPE
			SYNTAX Counter64
			MAX-ACCESS read-only
			STATUS current
			DESCRIPTION
				"Bytes that ingress on the VLAN"
			::= { fkVlanStatisticsEntry 2 }

		
		-- 1.3.6.1.4.1.10428 9 1.101.5.7.1.1.3
		fkVlanStatisticsEgressBytes OBJECT-TYPE
			SYNTAX Counter64
			MAX-ACCESS read-only
			STATUS current
			DESCRIPTION
				"Bytes that egress on the VLAN."
			::= { fkVlanStatisticsEntry 3 }

		
		-- 1.3.6.1.4.1.10428 9 1.101.5.7.1.1.4
		fkVlanStatisticsIngressPackets OBJECT-TYPE
			SYNTAX Counter64
			MAX-ACCESS read-only
			STATUS current
			DESCRIPTION
				"Packets that ingress on the VLAN."
			::= { fkVlanStatisticsEntry 4 }

		
		-- 1.3.6.1.4.1.10428 9 1.101.5.7.1.1.5
		fkVlanStatisticsEgressPackets OBJECT-TYPE
			SYNTAX Counter64
			MAX-ACCESS read-only
			STATUS current
			DESCRIPTION
				"Packets that egress on the VLAN."
			::= { fkVlanStatisticsEntry 5 }

		
--  1.3.6.1.4.1.10428 9 1.101.5.6.2
		-- 1.3.6.1.4.1.10428 9 1.101.5.7.2
		fkVlanStatisticsControl OBJECT IDENTIFIER ::= { fkVlanStatistics 2 }

		
--  1.3.6.1.4.1.10428 9 1.101.5.6.2.1
		-- 1.3.6.1.4.1.10428 9 1.101.5.7.2.1
		fkVlanStatisticsControlRequest OBJECT-TYPE
			SYNTAX INTEGER
				{
				clearVlanStatistics(1),
				clearVlanStatisticsAll(2)
				}
			MAX-ACCESS read-write
			STATUS current
			DESCRIPTION
				"Description."
			::= { fkVlanStatisticsControl 1 }

		
--  1.3.6.1.4.1.10428 9 1.101.5.6.2.2
		-- 1.3.6.1.4.1.10428 9 1.101.5.7.2.2
		fkVlanStatisticsControlStatus OBJECT-TYPE
			SYNTAX FkControlStatusType
			MAX-ACCESS read-only
			STATUS current
			DESCRIPTION
				"Description."
			::= { fkVlanStatisticsControl 2 }

		
--  1.3.6.1.4.1.10428 9 1.101.5.6.2.3
		-- 1.3.6.1.4.1.10428 9 1.101.5.7.2.3
		fkVlanStatisticsControlTimer OBJECT-TYPE
			SYNTAX Gauge32
			MAX-ACCESS read-write
			STATUS current
			DESCRIPTION
				"Description."
			::= { fkVlanStatisticsControl 3 }

		
--  1.3.6.1.4.1.10428 9 1.101.5.6.2.4
		-- 1.3.6.1.4.1.10428 9 1.101.5.7.2.4
		fkVlanStatisticsControlTimeStamp OBJECT-TYPE
			SYNTAX TimeTicks
			MAX-ACCESS read-only
			STATUS current
			DESCRIPTION
				"Description."
			::= { fkVlanStatisticsControl 4 }

		
--  1.3.6.1.4.1.10428 9 1.101.5.6.2.5
		-- 1.3.6.1.4.1.10428 9 1.101.5.7.2.5
		fkVlanStatisticsControlReqResult OBJECT-TYPE
			SYNTAX FkControlRequestResultType
			MAX-ACCESS read-only
			STATUS current
			DESCRIPTION
				"Description."
			::= { fkVlanStatisticsControl 5 }

		
--  1.3.6.1.4.1.10428 9 1.101.5.6.2.6
		-- 1.3.6.1.4.1.10428 9 1.101.5.7.2.6
		fkVlanStatisticsControlIndex OBJECT-TYPE
			SYNTAX Integer32 (1..4094)
			MAX-ACCESS read-write
			STATUS current
			DESCRIPTION
				"Description."
			::= { fkVlanStatisticsControl 6 }

		
		-- 1.3.6.1.4.1.10428 9 1.101.5.7.3
		fkVlanStatisticsNotification OBJECT IDENTIFIER ::= { fkVlanStatistics 3 }

		
		-- 1.3.6.1.4.1.10428 9 1.101.5.7.3.1
		fkVlanStatisticsCleared NOTIFICATION-TYPE
			OBJECTS { fkVlanStatisticsControlRequest, fkVlanStatisticsControlTimeStamp, fkVlanStatisticsControlReqResult, fkVlanStatisticsControlIndex }
			STATUS current
			DESCRIPTION 
				"Clear VLAN statistics"
			::= { fkVlanStatisticsNotification 1 }

		
		-- 1.3.6.1.4.1.10428 9 1.101.5.7.3.2
		fkVlanStatisticsAllCleared NOTIFICATION-TYPE
			OBJECTS { fkVlanStatisticsControlRequest, fkVlanStatisticsControlTimeStamp, fkVlanStatisticsControlReqResult }
			STATUS current
			DESCRIPTION 
				"Clear all VLANs statistics"
			::= { fkVlanStatisticsNotification 2 }

		
		-- 1.3.6.1.4.1.10428 9 1.101.5.8
		fkPerformanceMgmtGroup OBJECT-GROUP
			OBJECTS { fkThresholdIndex, fkPortThresholdUpLimit, fkPortThresholdUpSamplingInterval, fkPortThresholdDownLimit, fkPortThresholdDownSamplingInterval, 
				fkPortThresholdBlockTimer, fkPortThresholdPpsCurrLimit, fkPortThresholdPpsBlocked, fkPortThresholdPpsLimit, fkPortThresholdPpsInterval, 
				fkPortThresholdPpsBlockTimer, fkPortThresholdControlRequest, fkPortThresholdControlStatus, fkPortThresholdControlTimer, fkPortThresholdControlTimeStamp, 
				fkPortThresholdControlReqResult, fkPortThresholdControlIndex, fkPortThresholdControlThresholdUpLimit, fkPortThresholdControlUpSamplingInterval, fkPortThresholdControlThresholdDownLimit, 
				fkPortThresholdControlDownSamplingInterval, fkPortThresholdControlBlockTimer, fkPortThresholdControlPpsLimit, fkPortThresholdControlPpsInterval, fkPortThresholdControlPpsBlockTimer, 
				fkPortRateInterfaceIndex, fkPortRateIngressRate, fkPortRateEgressRate, fkPortRateControlRequest, fkPortRateControlStatus, 
				fkPortRateControlTimer, fkPortRateControlTimeStamp, fkPortRateControlReqResult, fkPortRateControlInterfaceIndex, fkPortRateControlIngressRate, 
				fkPortRateControlEgressRate, fkPortStatsIndex, fkPortStatsInterval, fkPortStatsOrder, fkPortStatsUpPackets, 
				fkPortStatsUpBytes, fkPortStatsDownPackets, fkPortStatsDownBytes, fkPortStatsControlRequest, fkPortStatsControlStatus, 
				fkPortStatsControlTimer, fkPortStatsControlTimeStamp, fkPortStatsControlReqResult, fkPortStatsControlIndex, fkCpuIntvlStatsPortIndex, 
				fkCpuIntvlStatsInterval, fkCpuIntvlStatsOrder, fkCpuIntvlStatsTxUcastPkts, fkCpuIntvlStatsTxMcastPkts, fkCpuIntvlStatsTxBcastPkts, 
				fkCpuIntvlStatsTxUcastBytes, fkCpuIntvlStatsTxMcastBytes, fkCpuIntvlStatsTxBcastBytes, fkCpuIntvlStatsRxUcastPkts, fkCpuIntvlStatsRxMcastPkts, 
				fkCpuIntvlStatsRxBcastPkts, fkCpuIntvlStatsRxUcastBytes, fkCpuIntvlStatsRxMcastBytes, fkCpuIntvlStatsRxBcastBytes, fkCpuStatsPortIndex, 
				fkCpuStatsTxUcastPkts, fkCpuStatsTxMcastPkts, fkCpuStatsTxBcastPkts, fkCpuStatsTxUcastBytes, fkCpuStatsTxMcastBytes, 
				fkCpuStatsTxBcastBytes, fkCpuStatsRxUcastPkts, fkCpuStatsRxMcastPkts, fkCpuStatsRxBcastPkts, fkCpuStatsRxUcastBytes, 
				fkCpuStatsRxMcastBytes, fkCpuStatsRxBcastBytes, fkCpuStatsControlRequest, fkCpuStatsControlStatus, fkCpuStatsControlTimer, 
				fkCpuStatsControlTimeStamp, fkCpuStatsControlReqResult, fkPortStatsAvgRxPackets, fkPortStatsAvgRxBytes, fkPortStatsAvgRxUcastPackets, 
				fkPortStatsAvgRxMcastPackets, fkPortStatsAvgRxBcastPackets, fkPortStatsAvgTxPackets, fkPortStatsAvgTxBytes, fkPortStatsAvgTxUcastPackets, 
				fkPortStatsAvgTxMcastPackets, fkPortStatsAvgTxBcastPackets, fkPortStatisticsAccHCInUnicastPkts, fkPortStatisticsAccHCInMulticastPkts, fkPortStatisticsAccHCOutUnicastPkts, 
				fkPortStatisticsAccHCOutMulticastPkts, fkPortStatisticsAccHCOutBroadcastPkts, fkPortStatisticsAccHCInOctets, fkPortStatisticsAccHCOutOctets, fkPortStatisticsAccHCOutVlanTagPkts, 
				fkPortStatisticsPPQPortNum, fkPortStatisticsPPQQueueNumber, fkPortStatisticsPPQPacketPassedCount, fkPortStatisticsPPQOctetPassedCount, fkPortStatisticsPPQPacketDiscards, 
				fkPortStatisticsPPQOctetDiscard, fkPortThresholdWarnTxLimit, fkPortThresholdWarnTxInterval, fkPortThresholdWarnTxDuration, fkPortThresholdWarnRxLimit, 
				fkPortThresholdWarnRxInterval, fkPortThresholdWarnRxDuration, fkPortThresholdAlarmTxLimit, fkPortThresholdAlarmTxInterval, fkPortThresholdAlarmTxDuration, 
				fkPortThresholdAlarmRxLimit, fkPortThresholdAlarmRxInterval, fkPortThresholdAlarmRxDuration, fkPortThresholdControlThresholdLimit, fkPortThresholdControlSamplingInterval, 
				fkPortThresholdControlSamplingDuration, fkSfpmonThresholdIndex, fkSfpmonWarnTxPowerLow, fkSfpmonWarnTxPowerHigh, fkSfpmonWarnTxPowerDuration, 
				fkSfpmonWarnRxPowerLow, fkSfpmonWarnRxPowerHigh, fkSfpmonWarnRxPowerDuration, fkSfpmonAlarmTxPowerLow, fkSfpmonAlarmTxPowerHigh, 
				fkSfpmonAlarmTxPowerDuration, fkSfpmonAlarmRxPowerLow, fkSfpmonAlarmRxPowerHigh, fkSfpmonAlarmRxPowerDuration, fkSfpmonThresholdControlRequest, 
				fkSfpmonThresholdControlStatus, fkSfpmonThresholdControlTimer, fkSfpmonThresholdControlTimeStamp, fkSfpmonThresholdControlReqResult, fkSfpmonThresholdControlIndex, 
				fkSfpmonThresholdControlPowerLow, fkSfpmonThresholdControlPowerHigh, fkSfpmonThresholdControlPowerDuration, fkSfpmonWarnTxbiasLow, fkSfpmonWarnTxbiasHigh, 
				fkSfpmonAlarmTxbiasLow, fkSfpmonAlarmTxbiasHigh, fkSfpmonWarnTemperLow, fkSfpmonWarnTemperHigh, fkSfpmonAlarmTemperLow, 
				fkSfpmonAlarmTemperHigh, fkSfpmonThresholdControlTxbiasLow, fkSfpmonThresholdControlTxbiasHigh, fkSfpmonThresholdControlTemperLow, fkSfpmonThresholdControlTemperHigh, 
				fkSfpmonThresholdControlVoltageLow, fkSfpmonThresholdControlVoltageHigh, fkPerformanceBaseCpuPpsStatus, fkPerformanceBaseCpuPpsThreshold, fkPerformanceBaseCpuPpsAvg, 
				fkPerformanceBaseControlCpuPpsStatus, fkPerformanceBaseControlCpuPpsThreshold, fkVlanStatisticsIndex, fkVlanStatisticsIngressBytes, fkVlanStatisticsEgressBytes, 
				fkVlanStatisticsIngressPackets, fkVlanStatisticsEgressPackets, fkVlanStatisticsControlRequest, fkVlanStatisticsControlStatus, fkVlanStatisticsControlTimer, 
				fkVlanStatisticsControlTimeStamp, fkVlanStatisticsControlReqResult, fkVlanStatisticsControlIndex, fkCpuStatsControlIndex, fkPortRateEnhanced, 
				fkPortRateControlEnhanced, fkPortStatsAvgInterval, fkPortStatisticsAccHCIndex, fkPortStatisticsAccHCInBroadcastPkts, fkPerformanceBaseProtoStatsEnable, 
				fkPerformanceBaseControlRequest, fkPerformanceBaseControlStatus, fkPerformanceBaseControlTimer, fkPerformanceBaseControlTimeStamp, fkPerformanceBaseControlReqResult, 
				fkPerformanceBaseControlProtoStatsEnable, fkSfpmonWarnVoltageLow, fkSfpmonWarnVoltageHigh, fkSfpmonAlarmVoltageLow, fkSfpmonAlarmVoltageHigh
				 }
			STATUS current
			DESCRIPTION 
				"Description."
			::= { fkPerformanceMgmt 8 }

		
		-- 1.3.6.1.4.1.10428 9 1.101.5.9
		fkPerformancdMgmtNotificationGroup NOTIFICATION-GROUP
			NOTIFICATIONS { fkPortThresholdChanged, fkPortThresholdBlockProfileChanged, fkPortThresholdPPSProfileChanged, fkPortThresholdPPSBlockProfileChanged, fkPortStatisticsCleared, 
				fkPerformanceBaseProtoStatsChanged, fkPortStatisticsAllCleared, fkCpuStatisticsCleared, fkSfpmonThresholdTxbiasChanged, fkSfpmonThresholdTemperChanged, 
				fkSfpmonThresholdVoltageChanged, fkPerformanceBaseCpuPpsProfileChanged, fkVlanStatisticsCleared, fkVlanStatisticsAllCleared, fkPortRateEnhancedChanged, 
				fkPortRateProfileChanged, fkSfpmonThresholdPowerChanged }
			STATUS current
			DESCRIPTION 
				"Description."
			::= { fkPerformanceMgmt 9 }

		
	
	END

--
-- fk-performancemgmt-mib.mib
--
