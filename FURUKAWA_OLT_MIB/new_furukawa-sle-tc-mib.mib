--
-- FK-TC-MIB.my
-- MIB generated by MG-SOFT Visual MIB Builder Version 4.0 Build 349
-- Thursday, October 07, 2004 at 16:34:15
--

FK-TC-MIB DEFINITIONS ::= BEGIN
 
                IMPORTS
                        fkMgmt                  
                                FROM FKOLTG1040-SMI                     
                        MODULE-IDENTITY                 
                                FROM SNMPv2-SMI                 
                        TEXTUAL-CONVENTION                       
                                FROM SNMPv2-TC;
        
                fkTcMib MODULE-IDENTITY 
                        LAST-UPDATED "200410071042Z"            -- October 07, 2004 at 10:42 GMT
                        ORGANIZATION 
                                "Furukawa Industrial S.A."
                        CONTACT-INFO 
                                "Furukawa Industrial S.A. Produtos Eletricos
        Rua Hasdrubal Bellegard, 820 - CIC
        CEP 81460-120 - Curitiba - Parana - Brasil
        CSC 0800-41-2100
        E-mail: fisa@furukawa.com.br"
                        DESCRIPTION 
                                "The MIB module for Furukawa GPON OLT FK-OLT-G1040."
                        ::= { fkMgmt 100 }

                
        
--
-- Textual conventions
--
        
                FkControlStatusType ::= TEXTUAL-CONVENTION
                        STATUS current
                        DESCRIPTION 
                                "The control status of an entity."
                        SYNTAX INTEGER
                                {
                                requestIdle(1),
                                requestBusy(2),
                                requestPassed(3),
                                requestFailed(4)
                                }

                FkControlRequestResultType ::= TEXTUAL-CONVENTION
                        STATUS current
                        DESCRIPTION 
                                "The request result."
                        SYNTAX INTEGER

                FkPermissionType ::= TEXTUAL-CONVENTION
                        STATUS current
                        DESCRIPTION 
                                "Description."
                        SYNTAX INTEGER
                                {
                                deny(0),
                                permit(1)
                                }

                FkTrafficType ::= TEXTUAL-CONVENTION
                        STATUS current
                        DESCRIPTION 
                                "Description."
                        SYNTAX INTEGER
                                {
                                broadcast(1),
                                multicast(2),
                                dlf(3)
                                }

                FkScopeType ::= TEXTUAL-CONVENTION
                        STATUS current
                        DESCRIPTION 
                                "Description."
                        SYNTAX INTEGER
                                {
                                port(1),
                                vlan(2)
                                }

                FkOperStateType ::= TEXTUAL-CONVENTION
                        STATUS current
                        DESCRIPTION 
                                "Description."
                        SYNTAX INTEGER
                                {
                                enabled(1),
                                disabled(2)
                                }

                FkAdminStateType ::= TEXTUAL-CONVENTION
                        STATUS current
                        DESCRIPTION 
                                "Description."
                        SYNTAX INTEGER
                                {
                                unlocked(1),
                                locked(2)
                                }

                FkCardType ::= TEXTUAL-CONVENTION
                        STATUS current
                        DESCRIPTION 
                                "Type for card type."
                        SYNTAX  OCTET STRING (SIZE (0..20))
                        
        
        FkSystemFileIndexType ::= TEXTUAL-CONVENTION
                        STATUS current
                        DESCRIPTION 
                                " Sytem file index type."
                        SYNTAX  INTEGER (1..8)

END
