--
-- fkv2-dhcp-mib.mib
-- MIB generated by MG-SOFT Visual MIB Builder Version 6.0  Build 88
-- Monday, April 08, 2013 at 19:49:45
--

	FKV2-DHCP-MIB DEFINITIONS ::= BEGIN
 
		IMPORTS
			fkV2Mgmt			
				FROM FKOLTG1040-SMI			
			InterfaceIndex			
				FROM IF-MIB			
			FkControlStatusType, FkControlRequestResultType			
				FROM FK-TC-MIB			
			OBJECT-GROUP, NOTIFICATION-GROUP			
				FROM SNMPv2-CONF			
			TimeTicks, IpAddress, Integer32, Unsigned32, Gauge32, 
			Counter32, BITS, OBJECT-TYPE, MODULE-IDENTITY, NOTIFICATION-TYPE			
				FROM SNMPv2-SMI			
			MacAddress			
				FROM SNMPv2-TC;
	
	
		-- 1.3.6.1.4.1.10428 9 1.102.6
		fkV2Dhcp MODULE-IDENTITY 
			LAST-UPDATED "200510241120Z"		-- October 24, 2005 at 11:20 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkV2Mgmt 6 }

		
	
--
-- Type definitions
--
	
		Boolean ::= INTEGER
			{
			disable(0),
			enable(1)
			}

	
	
--
-- Node definitions
--
	
		-- 1.3.6.1.4.1.10428 9 1.102.6.1
		fkV2DhcpBase OBJECT IDENTIFIER ::= { fkV2Dhcp 1 }

		
		-- 1.3.6.1.4.1.10428 9 1.102.6.2
		fkV2Dhcp4 OBJECT IDENTIFIER ::= { fkV2Dhcp 2 }

		
		-- 1.3.6.1.4.1.10428 9 1.102.6.2.1
		fkV2Dhcp4Base OBJECT IDENTIFIER ::= { fkV2Dhcp4 1 }

		
		-- 1.3.6.1.4.1.10428 9 1.102.6.2.1.1
		fkV2Dhcp4Info OBJECT IDENTIFIER ::= { fkV2Dhcp4Base 1 }

		
		-- 1.3.6.1.4.1.10428 9 1.102.6.2.1.1.1
		fkV2Dhcp4ServiceActivity OBJECT-TYPE
			SYNTAX INTEGER
				{
				disable(0),
				enable(1)
				}
			MAX-ACCESS read-only
			STATUS current
			DESCRIPTION
				"This object indicates whether DHCP servie is disable or enable.
				"
			::= { fkV2Dhcp4Info 1 }

		
		-- 1.3.6.1.4.1.10428 9 1.102.6.2.1.1.2
		fkV2Dhcp4DatabaseURL OBJECT-TYPE
			SYNTAX IpAddress
			MAX-ACCESS read-only
			STATUS current
			DESCRIPTION
				"The IP address of back up server.
				"
			::= { fkV2Dhcp4Info 2 }

		
		-- 1.3.6.1.4.1.10428 9 1.102.6.2.1.1.3
		fkV2Dhcp4DatabaseInterval OBJECT-TYPE
			SYNTAX INTEGER (0 | 1..2147483637)
			MAX-ACCESS read-only
			STATUS current
			DESCRIPTION
				"The backup interval to backup server.
				"
			::= { fkV2Dhcp4Info 3 }

		
		-- 1.3.6.1.4.1.10428 9 1.102.6.2.1.1.4
		fkV2Dhcp4ArpPingFlag OBJECT-TYPE
			SYNTAX INTEGER
				{
				ping(0),
				arp(1)
				}
			MAX-ACCESS read-only
			STATUS current
			DESCRIPTION
				"This object indicates whether it's ping or arp that is for validation using ip before DHCP server assign IP address."
			DEFVAL { ping }
			::= { fkV2Dhcp4Info 4 }

		
		-- 1.3.6.1.4.1.10428 9 1.102.6.2.1.1.5
		fkV2Dhcp4ArpRetransmits OBJECT-TYPE
			SYNTAX INTEGER (0..20)
			MAX-ACCESS read-only
			STATUS current
			DESCRIPTION
				"The number of retransmission for Arp"
			::= { fkV2Dhcp4Info 5 }

		
		-- 1.3.6.1.4.1.10428 9 1.102.6.2.1.1.6
		fkV2Dhcp4ArpTimeout OBJECT-TYPE
			SYNTAX INTEGER (100..5000)
			MAX-ACCESS read-only
			STATUS current
			DESCRIPTION
				"The timeout of the Arp"
			::= { fkV2Dhcp4Info 6 }

		
		-- 1.3.6.1.4.1.10428 9 1.102.6.2.1.1.7
		fkV2Dhcp4PingRetransmits OBJECT-TYPE
			SYNTAX INTEGER (0..20)
			MAX-ACCESS read-only
			STATUS current
			DESCRIPTION
				"The number of retransmission for Ping"
			::= { fkV2Dhcp4Info 7 }

		
		-- 1.3.6.1.4.1.10428 9 1.102.6.2.1.1.8
		fkV2Dhcp4PingTimeout OBJECT-TYPE
			SYNTAX INTEGER (100..5000)
			MAX-ACCESS read-only
			STATUS current
			DESCRIPTION
				"The timeout of the ping"
			::= { fkV2Dhcp4Info 8 }

		
		-- 1.3.6.1.4.1.10428 9 1.102.6.2.1.1.9
		fkV2Dhcp4ClassUsage OBJECT-TYPE
			SYNTAX INTEGER
				{
				disable(0),
				enable(1)
				}
			MAX-ACCESS read-only
			STATUS current
			DESCRIPTION
				"This object indicates whether the class function of DHCP is disable or enable."
			::= { fkV2Dhcp4Info 9 }

		
		-- 1.3.6.1.4.1.10428 9 1.102.6.2.1.1.10
		fkV2Dhcp4SmartRelayUsage OBJECT-TYPE
			SYNTAX INTEGER
				{
				disable(0),
				enable(1)
				}
			MAX-ACCESS read-only
			STATUS current
			DESCRIPTION
				"This object indicates whether the smart relay function of DHCP is disable or enable.
				"
			::= { fkV2Dhcp4Info 10 }

		
		-- 1.3.6.1.4.1.10428 9 1.102.6.2.1.1.11
		fkV2Dhcp4Option82Usage OBJECT-TYPE
			SYNTAX INTEGER
				{
				disable(0),
				enable(1)
				}
			MAX-ACCESS read-only
			STATUS current
			DESCRIPTION
				"This object indicates whether the option82 function in the DHCP is disable or enable.
				"
			::= { fkV2Dhcp4Info 11 }

		
		-- 1.3.6.1.4.1.10428 9 1.102.6.2.1.1.12
		fkV2Dhcp4Option82Drop OBJECT-TYPE
			SYNTAX INTEGER
				{
				none(0),
				normal(1),
				option82(2)
				}
			MAX-ACCESS read-only
			STATUS current
			DESCRIPTION
				"The drop policy of the request packet.
				"
			::= { fkV2Dhcp4Info 12 }

		
		-- 1.3.6.1.4.1.10428 9 1.102.6.2.1.1.13
		fkV2Dhcp4Option82Policy OBJECT-TYPE
			SYNTAX INTEGER
				{
				keep(0),
				replace(1)
				}
			MAX-ACCESS read-only
			STATUS current
			DESCRIPTION
				"The policy of the relay agent information option.
				"
			::= { fkV2Dhcp4Info 13 }

		
		-- 1.3.6.1.4.1.10428 9 1.102.6.2.1.1.14
		fkV2Dhcp4Option82TrustDefault OBJECT-TYPE
			SYNTAX INTEGER
				{
				deny(0),
				permit(1)
				}
			MAX-ACCESS read-only
			STATUS current
			DESCRIPTION
				"The Dhcp operation mode."
			::= { fkV2Dhcp4Info 14 }

		
		-- 1.3.6.1.4.1.10428 9 1.102.6.2.1.1.15
		fkV2Dhcp4Option82SystemRemoteType OBJECT-TYPE
			SYNTAX INTEGER
				{
				ipaddress(1),
				hex(2),
				text(3),
				host(4),
				index(5),
				option(6),
				undef(255)
				}
			MAX-ACCESS read-only
			STATUS current
			DESCRIPTION
				"The type of remote ID for the option82 systme of DHCP 
				Ipaddress, Hex, Text, Index"
			::= { fkV2Dhcp4Info 15 }

		
		-- 1.3.6.1.4.1.10428 9 1.102.6.2.1.1.16
		fkV2Dhcp4Option82SystemRemoteId OBJECT-TYPE
			SYNTAX OCTET STRING (SIZE (0 | 1..64))
			MAX-ACCESS read-only
			STATUS current
			DESCRIPTION
				"The remote identifier for the option82 system of DHCP.
				"
			::= { fkV2Dhcp4Info 16 }

		
		-- 1.3.6.1.4.1.10428 9 1.102.6.2.1.1.17
		fkV2Dhcp4DatabaseKey OBJECT-TYPE
			SYNTAX INTEGER
				{
				clientid(0),
				hwaddress(1)
				}
			MAX-ACCESS read-only
			STATUS current
			DESCRIPTION
				"The Database-key Setting for dhcp daemon.
				"
			::= { fkV2Dhcp4Info 17 }

		
		-- 1.3.6.1.4.1.10428 9 1.102.6.2.1.1.18
		fkV2Dhcp4DebugStatus OBJECT-TYPE
			SYNTAX BITS
				{
				debugFilter(0),
				debugLease(1),
				debugPacket(2),
				debugServices(3)
				}
			MAX-ACCESS read-write
			STATUS current
			DESCRIPTION
				"The  debug option setting of dhcp daemon.
				debugNo(0)
				debugFilter(1)
				debugLease(2)
				debugPacket(4)
				debugService(8)
				The above value is denotes by 'or'.
				debugAll(16)
				
				"
			::= { fkV2Dhcp4Info 18 }

		
		-- 1.3.6.1.4.1.10428 9 1.102.6.2.1.1.19
		fkV2Dhcp4AuthArpTime OBJECT-TYPE
			SYNTAX INTEGER (0 | 120..2147483637)
			UNITS "second"
			MAX-ACCESS read-only
			STATUS current
			DESCRIPTION
				"The set of starting Time for secure ARP function."
			::= { fkV2Dhcp4Info 19 }

		
		-- 1.3.6.1.4.1.10428 9 1.102.6.2.1.1.20
		fkV2Dhcp4AuthArpLeft OBJECT-TYPE
			SYNTAX Unsigned32
			UNITS "second"
			MAX-ACCESS read-only
			STATUS current
			DESCRIPTION
				"The left Time until authorized-arp function will be start.
				It denotes such as '01:20:31'"
			::= { fkV2Dhcp4Info 20 }

		
		-- 1.3.6.1.4.1.10428 9 1.102.6.2.1.1.21
		fkV2Dhcp4ClientHardwareAddress OBJECT-TYPE
			SYNTAX Boolean
			MAX-ACCESS read-only
			STATUS current
			DESCRIPTION
				"Prevent a client from getting multiple IP address"
			::= { fkV2Dhcp4Info 21 }

		
		-- 1.3.6.1.4.1.10428 9 1.102.6.2.1.1.22
		fkV2Dhcp4PEStatus OBJECT-TYPE
			SYNTAX INTEGER
				{
				disable(0),
				enable(1)
				}
			MAX-ACCESS read-only
			STATUS current
			DESCRIPTION
				"The debug option setting of DHCP daemon.
				"
			::= { fkV2Dhcp4Info 22 }

		
		-- 1.3.6.1.4.1.10428 9 1.102.6.2.1.1.23
		fkV2Dhcp4AuthArpReadyTime OBJECT-TYPE
			SYNTAX INTEGER (0 | 120..2147483637)
			MAX-ACCESS read-only
			STATUS current
			DESCRIPTION
				"Authorzed Arp starting time.
				"
			::= { fkV2Dhcp4Info 23 }

		
		-- 1.3.6.1.4.1.10428 9 1.102.6.2.1.1.24
		fkV2Dhcp4AuthArpRemainTime OBJECT-TYPE
			SYNTAX INTEGER (0..2147483637)
			MAX-ACCESS read-write
			STATUS current
			DESCRIPTION
				"Authorzed Arp remain time.
				"
			::= { fkV2Dhcp4Info 24 }

		
		-- 1.3.6.1.4.1.10428 9 1.102.6.2.1.1.25
		fkV2Dhcp4Option82SystemRemoteOption OBJECT-TYPE
			SYNTAX OCTET STRING (SIZE (0..16))
			MAX-ACCESS read-only
			STATUS current
			DESCRIPTION
				"Option82 system remote option.
				"
			::= { fkV2Dhcp4Info 25 }

		
		-- 1.3.6.1.4.1.10428 9 1.102.6.2.1.1.26
		fkV2Dhcp4Option82SystemCircuitPortType OBJECT-TYPE
			SYNTAX INTEGER
				{
				physical(1),
				logical(2)
				}
			MAX-ACCESS read-only
			STATUS current
			DESCRIPTION
				"The system-circuit-id port-type of option82.
				physical/logical"
			::= { fkV2Dhcp4Info 26 }

		
		-- 1.3.6.1.4.1.10428 9 1.102.6.2.1.2
		fkV2Dhcp4Control OBJECT IDENTIFIER ::= { fkV2Dhcp4Base 2 }

		
		-- 1.3.6.1.4.1.10428 9 1.102.6.2.1.2.1
		fkV2Dhcp4ControlRequest OBJECT-TYPE
			SYNTAX INTEGER
				{
				setDhcpServiceActivity(1),
				setDhcpDatabaseProfile(2),
				setDhcpArpPingProfile(3),
				setDhcpClassState(4),
				setDhcpSmartRelayState(5),
				setDhcpOption82State(6),
				setDhcpOption82Policy(7),
				setDhcpOption82TrustDefault(8),
				setDhcpOption82SystemRemoteId(9),
				setDhcpDatabaseKey(10),
				setDhcpDebugStatus(11),
				setDhcpAuthArpTime(12),
				setDhcpClientHardwareAddress(13),
				setDhcpPEStatus(14),
				setDhcpOption82SystemRemoteOption(15),
				setDhcpOption82SystemCircuitIdPortType(16)
				}
			MAX-ACCESS read-write
			STATUS current
			DESCRIPTION
				"The request of a user command."
			::= { fkV2Dhcp4Control 1 }

		
		-- 1.3.6.1.4.1.10428 9 1.102.6.2.1.2.2
		fkV2Dhcp4ControlStatus OBJECT-TYPE
			SYNTAX FkControlStatusType
			MAX-ACCESS read-only
			STATUS current
			DESCRIPTION
				"The status of a user command."
			::= { fkV2Dhcp4Control 2 }

		
		-- 1.3.6.1.4.1.10428 9 1.102.6.2.1.2.3
		fkV2Dhcp4ControlTimer OBJECT-TYPE
			SYNTAX Gauge32
			MAX-ACCESS read-write
			STATUS current
			DESCRIPTION
				"The maximum wait Time for the manager for a long running user command."
			::= { fkV2Dhcp4Control 3 }

		
		-- 1.3.6.1.4.1.10428 9 1.102.6.2.1.2.4
		fkV2Dhcp4ControlTimeStamp OBJECT-TYPE
			SYNTAX TimeTicks
			MAX-ACCESS read-only
			STATUS current
			DESCRIPTION
				"The Time stamp of the last command (end of command)."
			::= { fkV2Dhcp4Control 4 }

		
		-- 1.3.6.1.4.1.10428 9 1.102.6.2.1.2.5
		fkV2Dhcp4ControlReqResult OBJECT-TYPE
			SYNTAX FkControlRequestResultType
			MAX-ACCESS read-only
			STATUS current
			DESCRIPTION
				"The result of the last user command."
			::= { fkV2Dhcp4Control 5 }

		
		-- 1.3.6.1.4.1.10428 9 1.102.6.2.1.2.6
		fkV2Dhcp4ControlServiceActivity OBJECT-TYPE
			SYNTAX INTEGER
				{
				disable(0),
				enable(1)
				}
			MAX-ACCESS read-write
			STATUS current
			DESCRIPTION
				"This object indicates whether DHCP servie is disable or enable.
				"
			::= { fkV2Dhcp4Control 6 }

		
		-- 1.3.6.1.4.1.10428 9 1.102.6.2.1.2.7
		fkV2Dhcp4ControlDatabaseURL OBJECT-TYPE
			SYNTAX IpAddress
			MAX-ACCESS read-write
			STATUS current
			DESCRIPTION
				"The IP address of back up server.
				"
			::= { fkV2Dhcp4Control 7 }

		
		-- 1.3.6.1.4.1.10428 9 1.102.6.2.1.2.8
		fkV2Dhcp4ControlDatabaseInterval OBJECT-TYPE
			SYNTAX INTEGER (0 | 1..2147483637)
			MAX-ACCESS read-write
			STATUS current
			DESCRIPTION
				"The backup interval to backup server.
				"
			::= { fkV2Dhcp4Control 8 }

		
		-- 1.3.6.1.4.1.10428 9 1.102.6.2.1.2.9
		fkV2Dhcp4ControlArpPingFlag OBJECT-TYPE
			SYNTAX INTEGER
				{
				ping(0),
				arp(1)
				}
			MAX-ACCESS read-write
			STATUS current
			DESCRIPTION
				"This object indicates whether it's ping or arp that is for validation using ip before DHCP server assign IP address."
			DEFVAL { ping }
			::= { fkV2Dhcp4Control 9 }

		
		-- 1.3.6.1.4.1.10428 9 1.102.6.2.1.2.10
		fkV2Dhcp4ControlArpRetransmits OBJECT-TYPE
			SYNTAX INTEGER (0..20)
			MAX-ACCESS read-write
			STATUS current
			DESCRIPTION
				"The number of retransmission for Arp"
			::= { fkV2Dhcp4Control 10 }

		
		-- 1.3.6.1.4.1.10428 9 1.102.6.2.1.2.11
		fkV2Dhcp4ControlArpTimeout OBJECT-TYPE
			SYNTAX INTEGER (100..5000)
			MAX-ACCESS read-write
			STATUS current
			DESCRIPTION
				"The timeout of the Arp"
			::= { fkV2Dhcp4Control 11 }

		
		-- 1.3.6.1.4.1.10428 9 1.102.6.2.1.2.12
		fkV2Dhcp4ControlPingRetransmits OBJECT-TYPE
			SYNTAX INTEGER (0..20)
			MAX-ACCESS read-write
			STATUS current
			DESCRIPTION
				"The number of retransmission for Ping.
				"
			::= { fkV2Dhcp4Control 12 }

		
		-- 1.3.6.1.4.1.10428 9 1.102.6.2.1.2.13
		fkV2Dhcp4ControlPingTimeout OBJECT-TYPE
			SYNTAX INTEGER (100..5000)
			MAX-ACCESS read-write
			STATUS current
			DESCRIPTION
				"The timeout of the ping.
				"
			::= { fkV2Dhcp4Control 13 }

		
		-- 1.3.6.1.4.1.10428 9 1.102.6.2.1.2.14
		fkV2Dhcp4ControlClassUsage OBJECT-TYPE
			SYNTAX INTEGER
				{
				disable(0),
				enable(1)
				}
			MAX-ACCESS read-write
			STATUS current
			DESCRIPTION
				"This object indicates whether the class function of DHCP is disable or enable.
				"
			::= { fkV2Dhcp4Control 14 }

		
		-- 1.3.6.1.4.1.10428 9 1.102.6.2.1.2.15
		fkV2Dhcp4ControlSmartRelayUsage OBJECT-TYPE
			SYNTAX INTEGER
				{
				disable(0),
				enable(1)
				}
			MAX-ACCESS read-write
			STATUS current
			DESCRIPTION
				"This object indicates whether the smart relay function of DHCP is disable or enable.
				"
			::= { fkV2Dhcp4Control 15 }

		
		-- 1.3.6.1.4.1.10428 9 1.102.6.2.1.2.16
		fkV2Dhcp4ControlOption82Usage OBJECT-TYPE
			SYNTAX INTEGER
				{
				disable(0),
				enable(1)
				}
			MAX-ACCESS read-write
			STATUS current
			DESCRIPTION
				"This object indicates whether the option82 function in the DHCP is disable or enable.
				"
			::= { fkV2Dhcp4Control 16 }

		
		-- 1.3.6.1.4.1.10428 9 1.102.6.2.1.2.17
		fkV2Dhcp4ControlOption82Drop OBJECT-TYPE
			SYNTAX INTEGER
				{
				none(0),
				normal(1),
				option82(2)
				}
			MAX-ACCESS read-write
			STATUS current
			DESCRIPTION
				"The drop policy of the request packet.
				"
			::= { fkV2Dhcp4Control 17 }

		
		-- 1.3.6.1.4.1.10428 9 1.102.6.2.1.2.18
		fkV2Dhcp4ControlOption82Policy OBJECT-TYPE
			SYNTAX INTEGER
				{
				keep(0),
				replace(1)
				}
			MAX-ACCESS read-write
			STATUS current
			DESCRIPTION
				"The policy of the relay agent information option.
				"
			::= { fkV2Dhcp4Control 18 }

		
		-- 1.3.6.1.4.1.10428 9 1.102.6.2.1.2.19
		fkV2Dhcp4ControlOption82TrustDefault OBJECT-TYPE
			SYNTAX INTEGER
				{
				deny(0),
				permit(1)
				}
			MAX-ACCESS read-write
			STATUS current
			DESCRIPTION
				"The default policy of the trust for the relay agent information option.
				"
			::= { fkV2Dhcp4Control 19 }

		
		-- 1.3.6.1.4.1.10428 9 1.102.6.2.1.2.20
		fkV2Dhcp4ControlOption82SystemRemoteType OBJECT-TYPE
			SYNTAX INTEGER
				{
				ipaddress(1),
				hex(2),
				text(3),
				host(4),
				index(5),
				option(6),
				undef(255)
				}
			MAX-ACCESS read-write
			STATUS current
			DESCRIPTION
				"The type of remote ID for the option82 systme of DHCP 
				Ipaddress, Hex, Text, Index"
			::= { fkV2Dhcp4Control 20 }

		
		-- 1.3.6.1.4.1.10428 9 1.102.6.2.1.2.21
		fkV2Dhcp4ControlOption82SystemRemoteId OBJECT-TYPE
			SYNTAX OCTET STRING (SIZE (0 | 1..64))
			MAX-ACCESS read-write
			STATUS current
			DESCRIPTION
				"The remote identifier for the option82 system of DHCP.
				"
			::= { fkV2Dhcp4Control 21 }

		
		-- 1.3.6.1.4.1.10428 9 1.102.6.2.1.2.22
		fkV2Dhcp4ControlDatabaseKey OBJECT-TYPE
			SYNTAX INTEGER
				{
				clientid(0),
				hwaddress(1)
				}
			MAX-ACCESS read-write
			STATUS current
			DESCRIPTION
				"The database key on the relay.
				"
			::= { fkV2Dhcp4Control 22 }

		
		-- 1.3.6.1.4.1.10428 9 1.102.6.2.1.2.23
		fkV2Dhcp4ControlDebugStatus OBJECT-TYPE
			SYNTAX BITS
				{
				debugFilter(0),
				debugLease(1),
				debugPacket(2),
				debugServices(3)
				}
			MAX-ACCESS read-write
			STATUS current
			DESCRIPTION
				"The  debug option setting of dhcp daemon.
				The  debug option setting of dhcp daemon.
				debugNo(0)
				debugFilter(1)
				debugLease(2)
				debugPacket(4)
				debugService(8)
				The above value is denotes by 'or'.
				debugAll(16)
				
				"
			::= { fkV2Dhcp4Control 23 }

		
		-- 1.3.6.1.4.1.10428 9 1.102.6.2.1.2.24
		fkV2Dhcp4ControlAuthArpTime OBJECT-TYPE
			SYNTAX INTEGER (0 | 120..2147483637)
			UNITS "second"
			MAX-ACCESS read-write
			STATUS current
			DESCRIPTION
				"Authorized Arp timeout.
				"
			::= { fkV2Dhcp4Control 24 }

		
		-- 1.3.6.1.4.1.10428 9 1.102.6.2.1.2.25
		fkV2Dhcp4ControlClientHardwareAddress OBJECT-TYPE
			SYNTAX Boolean
			MAX-ACCESS read-write
			STATUS current
			DESCRIPTION
				"The left time until authorized arp time out.
				"
			::= { fkV2Dhcp4Control 25 }

		
		-- 1.3.6.1.4.1.10428 9 1.102.6.2.1.2.26
		fkV2Dhcp4ControlPEStatus OBJECT-TYPE
			SYNTAX INTEGER
				{
				disable(0),
				enable(1)
				}
			MAX-ACCESS read-write
			STATUS current
			DESCRIPTION
				"The debug option setting of DHCP daemon.
				"
			::= { fkV2Dhcp4Control 26 }

		
		-- 1.3.6.1.4.1.10428 9 1.102.6.2.1.2.27
		fkV2Dhcp4ControlAuthArpReadyTime OBJECT-TYPE
			SYNTAX INTEGER (0 | 120..2147483637)
			MAX-ACCESS read-write
			STATUS current
			DESCRIPTION
				"Authorzed Arp Staring time.
				"
			::= { fkV2Dhcp4Control 27 }

		
		-- 1.3.6.1.4.1.10428 9 1.102.6.2.1.2.28
		fkV2Dhcp4ControlOption82SystemRemoteOption OBJECT-TYPE
			SYNTAX OCTET STRING (SIZE (0..16))
			MAX-ACCESS read-write
			STATUS current
			DESCRIPTION
				"Option82 system remote option.
				"
			::= { fkV2Dhcp4Control 28 }

		
		-- 1.3.6.1.4.1.10428 9 1.102.6.2.1.2.29
		fkV2Dhcp4ControlOption82SystemCircuitPortType OBJECT-TYPE
			SYNTAX INTEGER
				{
				physical(1),
				logical(2)
				}
			MAX-ACCESS read-write
			STATUS current
			DESCRIPTION
				"The system-circuit-id port-type of option82.
				physical/logical"
			::= { fkV2Dhcp4Control 29 }

		
		-- 1.3.6.1.4.1.10428 9 1.102.6.2.1.3
		fkV2Dhcp4Notification OBJECT IDENTIFIER ::= { fkV2Dhcp4Base 3 }

		
		-- 1.3.6.1.4.1.10428 9 1.102.6.2.1.3.1
		fkV2Dhcp4ServiceActivityChanged NOTIFICATION-TYPE
			OBJECTS { fkV2Dhcp4ControlRequest, fkV2Dhcp4ControlTimeStamp, fkV2Dhcp4ControlReqResult, fkV2Dhcp4ServiceActivity }
			STATUS current
			DESCRIPTION 
				"Description."
			::= { fkV2Dhcp4Notification 1 }

		
		-- 1.3.6.1.4.1.10428 9 1.102.6.2.1.3.2
		fkV2Dhcp4DatabaseProfileChanged NOTIFICATION-TYPE
			OBJECTS { fkV2Dhcp4ControlRequest, fkV2Dhcp4ControlTimeStamp, fkV2Dhcp4ControlReqResult, fkV2Dhcp4DatabaseURL, fkV2Dhcp4DatabaseInterval
				 }
			STATUS current
			DESCRIPTION 
				"Description."
			::= { fkV2Dhcp4Notification 2 }

		
		-- 1.3.6.1.4.1.10428 9 1.102.6.2.1.3.3
		fkV2Dhcp4ArpPingProfileChanged NOTIFICATION-TYPE
			OBJECTS { fkV2Dhcp4ControlRequest, fkV2Dhcp4ControlTimeStamp, fkV2Dhcp4ControlReqResult, fkV2Dhcp4ArpPingFlag, fkV2Dhcp4ArpRetransmits, 
				fkV2Dhcp4ArpTimeout, fkV2Dhcp4PingRetransmits, fkV2Dhcp4PingTimeout }
			STATUS current
			DESCRIPTION 
				"Description."
			::= { fkV2Dhcp4Notification 3 }

		
		-- 1.3.6.1.4.1.10428 9 1.102.6.2.1.3.4
		fkV2Dhcp4ClassUsageChanged NOTIFICATION-TYPE
			OBJECTS { fkV2Dhcp4ControlRequest, fkV2Dhcp4ControlTimeStamp, fkV2Dhcp4ControlReqResult, fkV2Dhcp4ClassUsage }
			STATUS current
			DESCRIPTION 
				"Description."
			::= { fkV2Dhcp4Notification 4 }

		
		-- 1.3.6.1.4.1.10428 9 1.102.6.2.1.3.5
		fkV2Dhcp4SmartRelayUsageChanged NOTIFICATION-TYPE
			OBJECTS { fkV2Dhcp4ControlRequest, fkV2Dhcp4ControlTimeStamp, fkV2Dhcp4ControlReqResult, fkV2Dhcp4SmartRelayUsage }
			STATUS current
			DESCRIPTION 
				"Description."
			::= { fkV2Dhcp4Notification 5 }

		
		-- 1.3.6.1.4.1.10428 9 1.102.6.2.1.3.6
		fkV2Dhcp4Option82UsageChanged NOTIFICATION-TYPE
			OBJECTS { fkV2Dhcp4ControlRequest, fkV2Dhcp4ControlTimeStamp, fkV2Dhcp4ControlReqResult, fkV2Dhcp4Option82Usage }
			STATUS current
			DESCRIPTION 
				"Description."
			::= { fkV2Dhcp4Notification 6 }

		
		-- 1.3.6.1.4.1.10428 9 1.102.6.2.1.3.7
		fkV2Dhcp4Option82PolicyChanged NOTIFICATION-TYPE
			OBJECTS { fkV2Dhcp4ControlRequest, fkV2Dhcp4ControlTimeStamp, fkV2Dhcp4ControlReqResult, fkV2Dhcp4Option82Drop, fkV2Dhcp4Option82Policy
				 }
			STATUS current
			DESCRIPTION 
				"Description."
			::= { fkV2Dhcp4Notification 7 }

		
		-- 1.3.6.1.4.1.10428 9 1.102.6.2.1.3.8
		fkV2Dhcp4Option82TrustDefaultChanged NOTIFICATION-TYPE
			OBJECTS { fkV2Dhcp4ControlRequest, fkV2Dhcp4ControlTimeStamp, fkV2Dhcp4ControlReqResult, fkV2Dhcp4Option82TrustDefault }
			STATUS current
			DESCRIPTION 
				"Description."
			::= { fkV2Dhcp4Notification 8 }

		
		-- 1.3.6.1.4.1.10428 9 1.102.6.2.1.3.9
		fkV2Dhcp4Option82SystemRemoteIdChanged NOTIFICATION-TYPE
			OBJECTS { fkV2Dhcp4ControlRequest, fkV2Dhcp4ControlTimeStamp, fkV2Dhcp4ControlReqResult, fkV2Dhcp4Option82SystemRemoteId, fkV2Dhcp4Option82SystemRemoteType
				 }
			STATUS current
			DESCRIPTION 
				"Description."
			::= { fkV2Dhcp4Notification 9 }

		
		-- 1.3.6.1.4.1.10428 9 1.102.6.2.1.3.10
		fkV2Dhcp4DatabaseKeyChanged NOTIFICATION-TYPE
			OBJECTS { fkV2Dhcp4ControlRequest, fkV2Dhcp4ControlTimeStamp, fkV2Dhcp4ControlReqResult, fkV2Dhcp4DatabaseKey }
			STATUS current
			DESCRIPTION 
				"Description."
			::= { fkV2Dhcp4Notification 10 }

		
		-- 1.3.6.1.4.1.10428 9 1.102.6.2.1.3.11
		fkV2Dhcp4DebugStatusChanged NOTIFICATION-TYPE
			OBJECTS { fkV2Dhcp4ControlRequest, fkV2Dhcp4ControlTimeStamp, fkV2Dhcp4ControlReqResult, fkV2Dhcp4DebugStatus }
			STATUS current
			DESCRIPTION 
				"Description."
			::= { fkV2Dhcp4Notification 11 }

		
		-- 1.3.6.1.4.1.10428 9 1.102.6.2.1.3.12
		fkV2Dhcp4AuthoArpTimeChanged NOTIFICATION-TYPE
			OBJECTS { fkV2Dhcp4ControlRequest, fkV2Dhcp4ControlTimeStamp, fkV2Dhcp4ControlReqResult, fkV2Dhcp4AuthArpTime, fkV2Dhcp4AuthArpReadyTime
				 }
			STATUS current
			DESCRIPTION 
				"Description."
			::= { fkV2Dhcp4Notification 12 }

		
		-- 1.3.6.1.4.1.10428 9 1.102.6.2.1.3.13
		fkV2Dhcp4ClientHardwareAddressChanged NOTIFICATION-TYPE
			OBJECTS { fkV2Dhcp4ControlRequest, fkV2Dhcp4ControlTimeStamp, fkV2Dhcp4ControlReqResult, fkV2Dhcp4ControlClientHardwareAddress }
			STATUS current
			DESCRIPTION 
				"Description."
			::= { fkV2Dhcp4Notification 13 }

		
		-- 1.3.6.1.4.1.10428 9 1.102.6.2.1.3.14
		fkV2Dhcp4PEStatusChanged NOTIFICATION-TYPE
			OBJECTS { fkV2Dhcp4ControlRequest, fkV2Dhcp4ControlTimeStamp, fkV2Dhcp4ControlReqResult, fkV2Dhcp4ControlPEStatus }
			STATUS current
			DESCRIPTION 
				"Description."
			::= { fkV2Dhcp4Notification 14 }

		
		-- 1.3.6.1.4.1.10428 9 1.102.6.2.1.3.15
		fkV2Dhcp4Option82SystemRemoteOptionChanged NOTIFICATION-TYPE
			OBJECTS { fkV2Dhcp4ControlRequest, fkV2Dhcp4ControlTimeStamp, fkV2Dhcp4ControlReqResult, fkV2Dhcp4ControlOption82SystemRemoteOption }
			STATUS current
			DESCRIPTION 
				"Description."
			::= { fkV2Dhcp4Notification 15 }

		
		-- 1.3.6.1.4.1.10428 9 1.102.6.2.1.3.16
		fkV2DhcpOption82SystemCirucitIdPortTypeChanged NOTIFICATION-TYPE
			OBJECTS { fkV2Dhcp4ControlRequest, fkV2Dhcp4ControlTimeStamp, fkV2Dhcp4ControlReqResult, fkV2Dhcp4ControlOption82SystemCircuitPortType }
			STATUS current
			DESCRIPTION 
				"setDhcpOption82SystemCircuitIdPortType"
			::= { fkV2Dhcp4Notification 16 }

		
		-- 1.3.6.1.4.1.10428 9 1.102.6.2.2
		fkV2Dhcp4Pool OBJECT IDENTIFIER ::= { fkV2Dhcp4 2 }

		
		-- 1.3.6.1.4.1.10428 9 1.102.6.2.2.1
		fkV2Dhcp4PoolBase OBJECT IDENTIFIER ::= { fkV2Dhcp4Pool 1 }

		
		-- 1.3.6.1.4.1.10428 9 1.102.6.2.2.1.1
		fkV2Dhcp4PoolTable OBJECT-TYPE
			SYNTAX SEQUENCE OF FkV2Dhcp4PoolEntry
			MAX-ACCESS not-accessible
			STATUS current
			DESCRIPTION
				"Description."
			::= { fkV2Dhcp4PoolBase 1 }

		
		-- 1.3.6.1.4.1.10428 9 1.102.6.2.2.1.1.1
		fkV2Dhcp4PoolEntry OBJECT-TYPE
			SYNTAX FkV2Dhcp4PoolEntry
			MAX-ACCESS not-accessible
			STATUS current
			DESCRIPTION
				"Description."
			INDEX { fkV2Dhcp4PoolIndex }
			::= { fkV2Dhcp4PoolTable 1 }

		
		FkV2Dhcp4PoolEntry ::=
			SEQUENCE { 
				fkV2Dhcp4PoolIndex
					INTEGER,
				fkV2Dhcp4PoolName
					OCTET STRING,
				fkV2Dhcp4PoolDefaultLeaseTime
					INTEGER,
				fkV2Dhcp4PoolMaxLeaseTime
					INTEGER,
				fkV2Dhcp4PoolDomainName
					OCTET STRING,
				fkV2Dhcp4PoolSummaryTotal
					Unsigned32,
				fkV2Dhcp4PoolSummaryAllocated
					Unsigned32,
				fkV2Dhcp4PoolSummaryBound
					Unsigned32,
				fkV2Dhcp4PoolSummaryOffered
					Unsigned32,
				fkV2Dhcp4PoolSummaryFixed
					Unsigned32,
				fkV2Dhcp4PoolSummaryAbandon
					Unsigned32,
				fkV2Dhcp4PoolSummaryAvailable
					Unsigned32,
				fkV2Dhcp4PoolMeritDumpPath
					OCTET STRING,
				fkV2Dhcp4PoolRootPath
					OCTET STRING,
				fkV2Dhcp4PoolSummaryNetwork
					Unsigned32
			 }

		-- 1.3.6.1.4.1.10428 9 1.102.6.2.2.1.1.1.1
		fkV2Dhcp4PoolIndex OBJECT-TYPE
			SYNTAX INTEGER (1..255)
			MAX-ACCESS read-only
			STATUS current
			DESCRIPTION
				"The Pool index"
			::= { fkV2Dhcp4PoolEntry 1 }

		
		-- 1.3.6.1.4.1.10428 9 1.102.6.2.2.1.1.1.2
		fkV2Dhcp4PoolName OBJECT-TYPE
			SYNTAX OCTET STRING (SIZE (1..32))
			MAX-ACCESS read-only
			STATUS current
			DESCRIPTION
				"The Pool name."
			::= { fkV2Dhcp4PoolEntry 2 }

		
		-- 1.3.6.1.4.1.10428 9 1.102.6.2.2.1.1.1.3
		fkV2Dhcp4PoolDefaultLeaseTime OBJECT-TYPE
			SYNTAX INTEGER (0 | 120..2147483637)
			UNITS "second"
			MAX-ACCESS read-only
			STATUS current
			DESCRIPTION
				"The default Time assigned to Lease in Pool.
				The value of 0 denotes that the default Time was not set."
			::= { fkV2Dhcp4PoolEntry 3 }

		
		-- 1.3.6.1.4.1.10428 9 1.102.6.2.2.1.1.1.4
		fkV2Dhcp4PoolMaxLeaseTime OBJECT-TYPE
			SYNTAX INTEGER (0 | 120..2147483637)
			UNITS "second"
			MAX-ACCESS read-only
			STATUS current
			DESCRIPTION
				"The max Time assigned to Lease in Pool.
				The value of 0 denotes that the max Time was not set"
			::= { fkV2Dhcp4PoolEntry 4 }

		
		-- 1.3.6.1.4.1.10428 9 1.102.6.2.2.1.1.1.5
		fkV2Dhcp4PoolDomainName OBJECT-TYPE
			SYNTAX OCTET STRING (SIZE (0 | 1..64))
			MAX-ACCESS read-only
			STATUS current
			DESCRIPTION
				"The Pool Domain Name."
			::= { fkV2Dhcp4PoolEntry 5 }

		
		-- 1.3.6.1.4.1.10428 9 1.102.6.2.2.1.1.1.6
		fkV2Dhcp4PoolSummaryTotal OBJECT-TYPE
			SYNTAX Unsigned32
			MAX-ACCESS read-only
			STATUS current
			DESCRIPTION
				"The number of Total Leases in Pool."
			::= { fkV2Dhcp4PoolEntry 6 }

		
		-- 1.3.6.1.4.1.10428 9 1.102.6.2.2.1.1.1.7
		fkV2Dhcp4PoolSummaryAllocated OBJECT-TYPE
			SYNTAX Unsigned32
			MAX-ACCESS read-only
			STATUS current
			DESCRIPTION
				"The number of Allocated Leases in Pool."
			::= { fkV2Dhcp4PoolEntry 7 }

		
		-- 1.3.6.1.4.1.10428 9 1.102.6.2.2.1.1.1.8
		fkV2Dhcp4PoolSummaryBound OBJECT-TYPE
			SYNTAX Unsigned32
			MAX-ACCESS read-only
			STATUS current
			DESCRIPTION
				"The number of Bound Leases in Pool."
			::= { fkV2Dhcp4PoolEntry 8 }

		
		-- 1.3.6.1.4.1.10428 9 1.102.6.2.2.1.1.1.9
		fkV2Dhcp4PoolSummaryOffered OBJECT-TYPE
			SYNTAX Unsigned32
			MAX-ACCESS read-only
			STATUS current
			DESCRIPTION
				"The number of Offered Leases in Pool."
			::= { fkV2Dhcp4PoolEntry 9 }

		
		-- 1.3.6.1.4.1.10428 9 1.102.6.2.2.1.1.1.10
		fkV2Dhcp4PoolSummaryFixed OBJECT-TYPE
			SYNTAX Unsigned32
			MAX-ACCESS read-only
			STATUS current
			DESCRIPTION
				"The number of Fixed Leases in Pool."
			::= { fkV2Dhcp4PoolEntry 10 }

		
		-- 1.3.6.1.4.1.10428 9 1.102.6.2.2.1.1.1.11
		fkV2Dhcp4PoolSummaryAbandon OBJECT-TYPE
			SYNTAX Unsigned32
			MAX-ACCESS read-only
			STATUS current
			DESCRIPTION
				"The number of Abandon Leases in Pool."
			::= { fkV2Dhcp4PoolEntry 11 }

		
		-- 1.3.6.1.4.1.10428 9 1.102.6.2.2.1.1.1.12
		fkV2Dhcp4PoolSummaryAvailable OBJECT-TYPE
			SYNTAX Unsigned32
			MAX-ACCESS read-only
			STATUS current
			DESCRIPTION
				"The number of Available Leases in Pool."
			::= { fkV2Dhcp4PoolEntry 12 }

		
		-- 1.3.6.1.4.1.10428 9 1.102.6.2.2.1.1.1.13
		fkV2Dhcp4PoolMeritDumpPath OBJECT-TYPE
			SYNTAX OCTET STRING (SIZE (1..255))
			MAX-ACCESS read-only
			STATUS current
			DESCRIPTION
				"This value specifies the path name of a file which the client's core image should be dumped in the event the client crashes."
			::= { fkV2Dhcp4PoolEntry 13 }

		
		-- 1.3.6.1.4.1.10428 9 1.102.6.2.2.1.1.1.14
		fkV2Dhcp4PoolRootPath OBJECT-TYPE
			SYNTAX OCTET STRING (SIZE (1..255))
			MAX-ACCESS read-only
			STATUS current
			DESCRIPTION
				"Description."
			::= { fkV2Dhcp4PoolEntry 14 }

		
		-- 1.3.6.1.4.1.10428 9 1.102.6.2.2.1.1.1.15
		fkV2Dhcp4PoolSummaryNetwork OBJECT-TYPE
			SYNTAX Unsigned32
			MAX-ACCESS read-only
			STATUS current
			DESCRIPTION
				"Description."
			::= { fkV2Dhcp4PoolEntry 15 }

		
		-- 1.3.6.1.4.1.10428 9 1.102.6.2.2.1.2
		fkV2Dhcp4PoolControl OBJECT IDENTIFIER ::= { fkV2Dhcp4PoolBase 2 }

		
		-- 1.3.6.1.4.1.10428 9 1.102.6.2.2.1.2.1
		fkV2Dhcp4PoolControlRequest OBJECT-TYPE
			SYNTAX INTEGER
				{
				createDhcpPool(1),
				destroyDhcpPool(2),
				setPoolDhcpLeaseTimeProfile(3),
				setPoolDhcpDomainName(4),
				setPoolDhcpOriginProfile(5),
				setPoolDhcpMeritDumpPath(6),
				setPoolDhcpRootPath(7)
				}
			MAX-ACCESS read-write
			STATUS current
			DESCRIPTION
				"The request of a user command."
			::= { fkV2Dhcp4PoolControl 1 }

		
		-- 1.3.6.1.4.1.10428 9 1.102.6.2.2.1.2.2
		fkV2Dhcp4PoolControlStatus OBJECT-TYPE
			SYNTAX FkControlStatusType
			MAX-ACCESS read-only
			STATUS current
			DESCRIPTION
				"The status of a user command."
			::= { fkV2Dhcp4PoolControl 2 }

		
		-- 1.3.6.1.4.1.10428 9 1.102.6.2.2.1.2.3
		fkV2Dhcp4PoolControlTimer OBJECT-TYPE
			SYNTAX Gauge32
			MAX-ACCESS read-write
			STATUS current
			DESCRIPTION
				"The maximum wait Time for the manager for a long running user command."
			::= { fkV2Dhcp4PoolControl 3 }

		
		-- 1.3.6.1.4.1.10428 9 1.102.6.2.2.1.2.4
		fkV2Dhcp4PoolControlTimeStamp OBJECT-TYPE
			SYNTAX TimeTicks
			MAX-ACCESS read-only
			STATUS current
			DESCRIPTION
				"The Time stamp of the last command (end of command)."
			::= { fkV2Dhcp4PoolControl 4 }

		
		-- 1.3.6.1.4.1.10428 9 1.102.6.2.2.1.2.5
		fkV2Dhcp4PoolControlReqResult OBJECT-TYPE
			SYNTAX FkControlRequestResultType
			MAX-ACCESS read-only
			STATUS current
			DESCRIPTION
				"The result of the last user command."
			::= { fkV2Dhcp4PoolControl 5 }

		
		-- 1.3.6.1.4.1.10428 9 1.102.6.2.2.1.2.6
		fkV2Dhcp4PoolControlIndex OBJECT-TYPE
			SYNTAX INTEGER (1..255)
			MAX-ACCESS read-write
			STATUS current
			DESCRIPTION
				"Description."
			::= { fkV2Dhcp4PoolControl 6 }

		
		-- 1.3.6.1.4.1.10428 9 1.102.6.2.2.1.2.7
		fkV2Dhcp4PoolControlName OBJECT-TYPE
			SYNTAX OCTET STRING (SIZE (1..32))
			MAX-ACCESS read-write
			STATUS current
			DESCRIPTION
				"The Pool name."
			::= { fkV2Dhcp4PoolControl 7 }

		
		-- 1.3.6.1.4.1.10428 9 1.102.6.2.2.1.2.8
		fkV2Dhcp4PoolControlDefaultLeaseTime OBJECT-TYPE
			SYNTAX INTEGER (0 | 120..2147483637)
			UNITS "second"
			MAX-ACCESS read-write
			STATUS current
			DESCRIPTION
				"The default Time assigned to Lease in Pool.
				If 0, the default Time is clear"
			DEFVAL { 3600 }
			::= { fkV2Dhcp4PoolControl 8 }

		
		-- 1.3.6.1.4.1.10428 9 1.102.6.2.2.1.2.9
		fkV2Dhcp4PoolControlMaxLeaseTime OBJECT-TYPE
			SYNTAX INTEGER (0 | 120..2147483637)
			UNITS "second"
			MAX-ACCESS read-write
			STATUS current
			DESCRIPTION
				"The max Time assigned to Lease in Pool.
				If 0, the max Time is clear."
			DEFVAL { 3600 }
			::= { fkV2Dhcp4PoolControl 9 }

		
		-- 1.3.6.1.4.1.10428 9 1.102.6.2.2.1.2.10
		fkV2Dhcp4PoolControlDomainName OBJECT-TYPE
			SYNTAX OCTET STRING (SIZE (0 | 1..64))
			MAX-ACCESS read-write
			STATUS current
			DESCRIPTION
				"."
			::= { fkV2Dhcp4PoolControl 10 }

		
		-- 1.3.6.1.4.1.10428 9 1.102.6.2.2.1.2.11
		fkV2Dhcp4PoolControlOriginURL OBJECT-TYPE
			SYNTAX IpAddress
			MAX-ACCESS read-write
			STATUS current
			DESCRIPTION
				"."
			::= { fkV2Dhcp4PoolControl 11 }

		
		-- 1.3.6.1.4.1.10428 9 1.102.6.2.2.1.2.12
		fkV2Dhcp4PoolControlOriginFileName OBJECT-TYPE
			SYNTAX OCTET STRING (SIZE (0 | 1..64))
			MAX-ACCESS read-write
			STATUS current
			DESCRIPTION
				"."
			::= { fkV2Dhcp4PoolControl 12 }

		
		-- 1.3.6.1.4.1.10428 9 1.102.6.2.2.1.2.13
		fkV2Dhcp4PoolControlMeritDumpPath OBJECT-TYPE
			SYNTAX OCTET STRING (SIZE (1..255))
			MAX-ACCESS read-write
			STATUS current
			DESCRIPTION
				"Description."
			::= { fkV2Dhcp4PoolControl 13 }

		
		-- 1.3.6.1.4.1.10428 9 1.102.6.2.2.1.2.14
		fkV2Dhcp4PoolControlRootPath OBJECT-TYPE
			SYNTAX OCTET STRING (SIZE (1..255))
			MAX-ACCESS read-write
			STATUS current
			DESCRIPTION
				"Description."
			::= { fkV2Dhcp4PoolControl 14 }

		
		-- 1.3.6.1.4.1.10428 9 1.102.6.2.2.1.3
		fkV2Dhcp4PoolNotification OBJECT IDENTIFIER ::= { fkV2Dhcp4PoolBase 3 }

		
		-- 1.3.6.1.4.1.10428 9 1.102.6.2.2.1.3.1
		fkV2Dhcp4PoolCreated NOTIFICATION-TYPE
			OBJECTS { fkV2Dhcp4PoolName, fkV2Dhcp4PoolDefaultLeaseTime, fkV2Dhcp4PoolMaxLeaseTime, fkV2Dhcp4PoolDomainName, fkV2Dhcp4PoolControlRequest, 
				fkV2Dhcp4PoolControlTimeStamp, fkV2Dhcp4PoolControlReqResult, fkV2Dhcp4PoolMeritDumpPath, fkV2Dhcp4PoolRootPath }
			STATUS current
			DESCRIPTION 
				"Description."
			::= { fkV2Dhcp4PoolNotification 1 }

		
		-- 1.3.6.1.4.1.10428 9 1.102.6.2.2.1.3.2
		fkV2Dhcp4PoolDestroyed NOTIFICATION-TYPE
			OBJECTS { fkV2Dhcp4PoolControlRequest, fkV2Dhcp4PoolControlTimeStamp, fkV2Dhcp4PoolControlReqResult, fkV2Dhcp4PoolControlIndex }
			STATUS current
			DESCRIPTION 
				"Description."
			::= { fkV2Dhcp4PoolNotification 2 }

		
		-- 1.3.6.1.4.1.10428 9 1.102.6.2.2.1.3.3
		fkV2Dhcp4PoolLeaseTimeProfileChanged NOTIFICATION-TYPE
			OBJECTS { fkV2Dhcp4PoolDefaultLeaseTime, fkV2Dhcp4PoolMaxLeaseTime, fkV2Dhcp4PoolControlRequest, fkV2Dhcp4PoolControlTimeStamp, fkV2Dhcp4PoolControlReqResult
				 }
			STATUS current
			DESCRIPTION 
				"Description."
			::= { fkV2Dhcp4PoolNotification 3 }

		
		-- 1.3.6.1.4.1.10428 9 1.102.6.2.2.1.3.4
		fkV2Dhcp4PoolDomainNameChanged NOTIFICATION-TYPE
			OBJECTS { fkV2Dhcp4PoolControlRequest, fkV2Dhcp4PoolControlTimeStamp, fkV2Dhcp4PoolControlReqResult, fkV2Dhcp4PoolDomainName }
			STATUS current
			DESCRIPTION 
				"Description."
			::= { fkV2Dhcp4PoolNotification 4 }

		
		-- 1.3.6.1.4.1.10428 9 1.102.6.2.2.1.3.5
		fkV2Dhcp4PoolOriginProfileChanged NOTIFICATION-TYPE
			OBJECTS { fkV2Dhcp4PoolControlRequest, fkV2Dhcp4PoolControlTimeStamp, fkV2Dhcp4PoolControlReqResult, fkV2Dhcp4PoolControlOriginURL, fkV2Dhcp4PoolControlOriginFileName
				 }
			STATUS current
			DESCRIPTION 
				"Description."
			::= { fkV2Dhcp4PoolNotification 5 }

		
		-- 1.3.6.1.4.1.10428 9 1.102.6.2.2.1.3.6
		fkV2Dhcp4PoolMeritDumpPathChanged NOTIFICATION-TYPE
			OBJECTS { fkV2Dhcp4PoolControlRequest, fkV2Dhcp4PoolControlTimeStamp, fkV2Dhcp4PoolControlReqResult, fkV2Dhcp4PoolMeritDumpPath }
			STATUS current
			DESCRIPTION 
				"Description."
			::= { fkV2Dhcp4PoolNotification 6 }

		
		-- 1.3.6.1.4.1.10428 9 1.102.6.2.2.1.3.7
		fkV2Dhcp4PoolRootPathChanged NOTIFICATION-TYPE
			OBJECTS { fkV2Dhcp4PoolControlRequest, fkV2Dhcp4PoolControlTimeStamp, fkV2Dhcp4PoolControlReqResult, fkV2Dhcp4PoolRootPath }
			STATUS current
			DESCRIPTION 
				"Description."
			::= { fkV2Dhcp4PoolNotification 7 }

		
		-- 1.3.6.1.4.1.10428 9 1.102.6.2.2.2
		fkV2Dhcp4Network OBJECT IDENTIFIER ::= { fkV2Dhcp4Pool 2 }

		
		-- 1.3.6.1.4.1.10428 9 1.102.6.2.2.2.1
		fkV2Dhcp4NetworkTable OBJECT-TYPE
			SYNTAX SEQUENCE OF FkV2Dhcp4NetworkEntry
			MAX-ACCESS not-accessible
			STATUS current
			DESCRIPTION
				"Description."
			::= { fkV2Dhcp4Network 1 }

		
		-- 1.3.6.1.4.1.10428 9 1.102.6.2.2.2.1.1
		fkV2Dhcp4NetworkEntry OBJECT-TYPE
			SYNTAX FkV2Dhcp4NetworkEntry
			MAX-ACCESS not-accessible
			STATUS current
			DESCRIPTION
				"Description."
			INDEX { fkV2Dhcp4PoolIndex, fkV2Dhcp4NetworkAddress, fkV2Dhcp4NetworkMask }
			::= { fkV2Dhcp4NetworkTable 1 }

		
		FkV2Dhcp4NetworkEntry ::=
			SEQUENCE { 
				fkV2Dhcp4NetworkAddress
					IpAddress,
				fkV2Dhcp4NetworkMask
					INTEGER
			 }

		-- 1.3.6.1.4.1.10428 9 1.102.6.2.2.2.1.1.1
		fkV2Dhcp4NetworkAddress OBJECT-TYPE
			SYNTAX IpAddress
			MAX-ACCESS read-only
			STATUS current
			DESCRIPTION
				"The Subnet IP Address."
			::= { fkV2Dhcp4NetworkEntry 1 }

		
		-- 1.3.6.1.4.1.10428 9 1.102.6.2.2.2.1.1.2
		fkV2Dhcp4NetworkMask OBJECT-TYPE
			SYNTAX INTEGER (1..32)
			MAX-ACCESS read-only
			STATUS current
			DESCRIPTION
				"The Subnet Mask prefix length."
			::= { fkV2Dhcp4NetworkEntry 2 }

		
		-- 1.3.6.1.4.1.10428 9 1.102.6.2.2.2.2
		fkV2Dhcp4NetworkControl OBJECT IDENTIFIER ::= { fkV2Dhcp4Network 2 }

		
		-- 1.3.6.1.4.1.10428 9 1.102.6.2.2.2.2.1
		fkV2Dhcp4NetworkControlRequest OBJECT-TYPE
			SYNTAX INTEGER
				{
				createDhcpNetwork(1),
				destroyDhcpNetwork(2)
				}
			MAX-ACCESS read-write
			STATUS current
			DESCRIPTION
				"The request of a user command."
			::= { fkV2Dhcp4NetworkControl 1 }

		
		-- 1.3.6.1.4.1.10428 9 1.102.6.2.2.2.2.2
		fkV2Dhcp4NetworkControlStatus OBJECT-TYPE
			SYNTAX FkControlStatusType
			MAX-ACCESS read-only
			STATUS current
			DESCRIPTION
				"The status of a user command."
			::= { fkV2Dhcp4NetworkControl 2 }

		
		-- 1.3.6.1.4.1.10428 9 1.102.6.2.2.2.2.3
		fkV2Dhcp4NetworkControlTimer OBJECT-TYPE
			SYNTAX Gauge32
			MAX-ACCESS read-write
			STATUS current
			DESCRIPTION
				"The maximum wait Time for the manager for a long running user command."
			::= { fkV2Dhcp4NetworkControl 3 }

		
		-- 1.3.6.1.4.1.10428 9 1.102.6.2.2.2.2.4
		fkV2Dhcp4NetworkControlTimeStamp OBJECT-TYPE
			SYNTAX TimeTicks
			MAX-ACCESS read-only
			STATUS current
			DESCRIPTION
				"The Time stamp of the last command (end of command)."
			::= { fkV2Dhcp4NetworkControl 4 }

		
		-- 1.3.6.1.4.1.10428 9 1.102.6.2.2.2.2.5
		fkV2Dhcp4NetworkControlReqResult OBJECT-TYPE
			SYNTAX FkControlRequestResultType
			MAX-ACCESS read-only
			STATUS current
			DESCRIPTION
				"The result of the last user command."
			::= { fkV2Dhcp4NetworkControl 5 }

		
		-- 1.3.6.1.4.1.10428 9 1.102.6.2.2.2.2.6
		fkV2Dhcp4NetworkControlPoolIndex OBJECT-TYPE
			SYNTAX INTEGER (1..255)
			MAX-ACCESS read-write
			STATUS current
			DESCRIPTION
				"Description."
			::= { fkV2Dhcp4NetworkControl 6 }

		
		-- 1.3.6.1.4.1.10428 9 1.102.6.2.2.2.2.7
		fkV2Dhcp4NetworkControlAddress OBJECT-TYPE
			SYNTAX IpAddress
			MAX-ACCESS read-only
			STATUS current
			DESCRIPTION
				"The result of the last user command."
			::= { fkV2Dhcp4NetworkControl 7 }

		
		-- 1.3.6.1.4.1.10428 9 1.102.6.2.2.2.2.8
		fkV2Dhcp4NetworkControlMask OBJECT-TYPE
			SYNTAX INTEGER (1..32)
			MAX-ACCESS read-only
			STATUS current
			DESCRIPTION
				"The result of the last user command."
			::= { fkV2Dhcp4NetworkControl 8 }

		
		-- 1.3.6.1.4.1.10428 9 1.102.6.2.2.2.3
		fkV2Dhcp4NetworkNotification OBJECT IDENTIFIER ::= { fkV2Dhcp4Network 3 }

		
		-- 1.3.6.1.4.1.10428 9 1.102.6.2.2.2.3.1
		fkV2Dhcp4NetworkCreated NOTIFICATION-TYPE
			OBJECTS { fkV2Dhcp4NetworkControlRequest, fkV2Dhcp4NetworkControlTimeStamp, fkV2Dhcp4NetworkControlReqResult, fkV2Dhcp4NetworkControlPoolIndex, fkV2Dhcp4NetworkControlAddress, 
				fkV2Dhcp4NetworkControlMask }
			STATUS current
			DESCRIPTION 
				"Description."
			::= { fkV2Dhcp4NetworkNotification 1 }

		
		-- 1.3.6.1.4.1.10428 9 1.102.6.2.2.2.3.2
		fkV2Dhcp4NetworkDestroyed NOTIFICATION-TYPE
			OBJECTS { fkV2Dhcp4NetworkControlRequest, fkV2Dhcp4NetworkControlTimeStamp, fkV2Dhcp4NetworkControlReqResult, fkV2Dhcp4NetworkControlPoolIndex, fkV2Dhcp4NetworkControlAddress, 
				fkV2Dhcp4NetworkControlMask }
			STATUS current
			DESCRIPTION 
				"Description."
			::= { fkV2Dhcp4NetworkNotification 2 }

		
		-- 1.3.6.1.4.1.10428 9 1.102.6.2.2.3
		fkV2Dhcp4Range OBJECT IDENTIFIER ::= { fkV2Dhcp4Pool 3 }

		
		-- 1.3.6.1.4.1.10428 9 1.102.6.2.2.3.1
		fkV2Dhcp4RangeTable OBJECT-TYPE
			SYNTAX SEQUENCE OF FkV2Dhcp4RangeEntry
			MAX-ACCESS not-accessible
			STATUS current
			DESCRIPTION
				"Description."
			::= { fkV2Dhcp4Range 1 }

		
		-- 1.3.6.1.4.1.10428 9 1.102.6.2.2.3.1.1
		fkV2Dhcp4RangeEntry OBJECT-TYPE
			SYNTAX FkV2Dhcp4RangeEntry
			MAX-ACCESS not-accessible
			STATUS current
			DESCRIPTION
				"Description."
			INDEX { fkV2Dhcp4PoolIndex, fkV2Dhcp4RangeStart, fkV2Dhcp4RangeEnd }
			::= { fkV2Dhcp4RangeTable 1 }

		
		FkV2Dhcp4RangeEntry ::=
			SEQUENCE { 
				fkV2Dhcp4RangeStart
					IpAddress,
				fkV2Dhcp4RangeEnd
					IpAddress
			 }

		-- 1.3.6.1.4.1.10428 9 1.102.6.2.2.3.1.1.1
		fkV2Dhcp4RangeStart OBJECT-TYPE
			SYNTAX IpAddress
			MAX-ACCESS read-only
			STATUS current
			DESCRIPTION
				"The start IP of subnet's range."
			::= { fkV2Dhcp4RangeEntry 1 }

		
		-- 1.3.6.1.4.1.10428 9 1.102.6.2.2.3.1.1.2
		fkV2Dhcp4RangeEnd OBJECT-TYPE
			SYNTAX IpAddress
			MAX-ACCESS read-only
			STATUS current
			DESCRIPTION
				"The end IP of subnet's range."
			::= { fkV2Dhcp4RangeEntry 2 }

		
		-- 1.3.6.1.4.1.10428 9 1.102.6.2.2.3.2
		fkV2Dhcp4RangeControl OBJECT IDENTIFIER ::= { fkV2Dhcp4Range 2 }

		
		-- 1.3.6.1.4.1.10428 9 1.102.6.2.2.3.2.1
		fkV2Dhcp4RangeControlRequest OBJECT-TYPE
			SYNTAX INTEGER
				{
				createDhcpRange(1),
				destroyDhcpRange(2)
				}
			MAX-ACCESS read-write
			STATUS current
			DESCRIPTION
				"The request of a user command."
			::= { fkV2Dhcp4RangeControl 1 }

		
		-- 1.3.6.1.4.1.10428 9 1.102.6.2.2.3.2.2
		fkV2Dhcp4RangeControlStatus OBJECT-TYPE
			SYNTAX FkControlStatusType
			MAX-ACCESS read-only
			STATUS current
			DESCRIPTION
				"The status of a user command."
			::= { fkV2Dhcp4RangeControl 2 }

		
		-- 1.3.6.1.4.1.10428 9 1.102.6.2.2.3.2.3
		fkV2Dhcp4RangeControlTimer OBJECT-TYPE
			SYNTAX Gauge32
			MAX-ACCESS read-write
			STATUS current
			DESCRIPTION
				"The maximum wait Time for the manager for a long running user command."
			::= { fkV2Dhcp4RangeControl 3 }

		
		-- 1.3.6.1.4.1.10428 9 1.102.6.2.2.3.2.4
		fkV2Dhcp4RangeControlTimeStamp OBJECT-TYPE
			SYNTAX TimeTicks
			MAX-ACCESS read-only
			STATUS current
			DESCRIPTION
				"The Time stamp of the last command (end of command)."
			::= { fkV2Dhcp4RangeControl 4 }

		
		-- 1.3.6.1.4.1.10428 9 1.102.6.2.2.3.2.5
		fkV2Dhcp4RangeControlReqResult OBJECT-TYPE
			SYNTAX FkControlRequestResultType
			MAX-ACCESS read-only
			STATUS current
			DESCRIPTION
				"The result of the last user command."
			::= { fkV2Dhcp4RangeControl 5 }

		
		-- 1.3.6.1.4.1.10428 9 1.102.6.2.2.3.2.6
		fkV2Dhcp4RangeControlPoolIndex OBJECT-TYPE
			SYNTAX INTEGER (1..255)
			MAX-ACCESS read-write
			STATUS current
			DESCRIPTION
				"Description."
			::= { fkV2Dhcp4RangeControl 6 }

		
		-- 1.3.6.1.4.1.10428 9 1.102.6.2.2.3.2.7
		fkV2Dhcp4RangeControlStart OBJECT-TYPE
			SYNTAX IpAddress
			MAX-ACCESS read-write
			STATUS current
			DESCRIPTION
				"Description."
			::= { fkV2Dhcp4RangeControl 7 }

		
		-- 1.3.6.1.4.1.10428 9 1.102.6.2.2.3.2.8
		fkV2Dhcp4RangeControlEnd OBJECT-TYPE
			SYNTAX IpAddress
			MAX-ACCESS read-write
			STATUS current
			DESCRIPTION
				"Description."
			::= { fkV2Dhcp4RangeControl 8 }

		
		-- 1.3.6.1.4.1.10428 9 1.102.6.2.2.3.3
		fkV2Dhcp4RangeNotification OBJECT IDENTIFIER ::= { fkV2Dhcp4Range 3 }

		
		-- 1.3.6.1.4.1.10428 9 1.102.6.2.2.3.3.1
		fkV2Dhcp4RangeCreated NOTIFICATION-TYPE
			OBJECTS { fkV2Dhcp4RangeControlRequest, fkV2Dhcp4RangeControlTimeStamp, fkV2Dhcp4RangeControlReqResult, fkV2Dhcp4RangeControlPoolIndex, fkV2Dhcp4RangeControlStart, 
				fkV2Dhcp4RangeControlEnd }
			STATUS current
			DESCRIPTION 
				"Description."
			::= { fkV2Dhcp4RangeNotification 1 }

		
		-- 1.3.6.1.4.1.10428 9 1.102.6.2.2.3.3.2
		fkV2Dhcp4RangeDestroyed NOTIFICATION-TYPE
			OBJECTS { fkV2Dhcp4RangeControlRequest, fkV2Dhcp4RangeControlTimeStamp, fkV2Dhcp4RangeControlReqResult, fkV2Dhcp4RangeControlPoolIndex, fkV2Dhcp4RangeControlStart, 
				fkV2Dhcp4RangeControlEnd }
			STATUS current
			DESCRIPTION 
				"Description."
			::= { fkV2Dhcp4RangeNotification 2 }

		
		-- 1.3.6.1.4.1.10428 9 1.102.6.2.2.4
		fkV2Dhcp4Fixed OBJECT IDENTIFIER ::= { fkV2Dhcp4Pool 4 }

		
		-- 1.3.6.1.4.1.10428 9 1.102.6.2.2.4.1
		fkV2Dhcp4FixedTable OBJECT-TYPE
			SYNTAX SEQUENCE OF FkV2Dhcp4FixedEntry
			MAX-ACCESS not-accessible
			STATUS current
			DESCRIPTION
				"Description."
			::= { fkV2Dhcp4Fixed 1 }

		
		-- 1.3.6.1.4.1.10428 9 1.102.6.2.2.4.1.1
		fkV2Dhcp4FixedEntry OBJECT-TYPE
			SYNTAX FkV2Dhcp4FixedEntry
			MAX-ACCESS not-accessible
			STATUS current
			DESCRIPTION
				"Description."
			INDEX { fkV2Dhcp4PoolIndex, fkV2Dhcp4FixedMac, fkV2Dhcp4FixedAddress }
			::= { fkV2Dhcp4FixedTable 1 }

		
		FkV2Dhcp4FixedEntry ::=
			SEQUENCE { 
				fkV2Dhcp4FixedMac
					MacAddress,
				fkV2Dhcp4FixedAddress
					IpAddress
			 }

		-- 1.3.6.1.4.1.10428 9 1.102.6.2.2.4.1.1.1
		fkV2Dhcp4FixedMac OBJECT-TYPE
			SYNTAX MacAddress
			MAX-ACCESS read-only
			STATUS current
			DESCRIPTION
				"The MAC address for the fixed Lease."
			::= { fkV2Dhcp4FixedEntry 1 }

		
		-- 1.3.6.1.4.1.10428 9 1.102.6.2.2.4.1.1.2
		fkV2Dhcp4FixedAddress OBJECT-TYPE
			SYNTAX IpAddress
			MAX-ACCESS read-only
			STATUS current
			DESCRIPTION
				"The IP address for the fixed Lease."
			::= { fkV2Dhcp4FixedEntry 2 }

		
		-- 1.3.6.1.4.1.10428 9 1.102.6.2.2.4.2
		fkV2Dhcp4FixedControl OBJECT IDENTIFIER ::= { fkV2Dhcp4Fixed 2 }

		
		-- 1.3.6.1.4.1.10428 9 1.102.6.2.2.4.2.1
		fkV2Dhcp4FixedControlRequest OBJECT-TYPE
			SYNTAX INTEGER
				{
				createDhcpFixed(1),
				destroyDhcpFixed(2)
				}
			MAX-ACCESS read-write
			STATUS current
			DESCRIPTION
				"The request of a user command."
			::= { fkV2Dhcp4FixedControl 1 }

		
		-- 1.3.6.1.4.1.10428 9 1.102.6.2.2.4.2.2
		fkV2Dhcp4FixedControlStatus OBJECT-TYPE
			SYNTAX FkControlStatusType
			MAX-ACCESS read-only
			STATUS current
			DESCRIPTION
				"The status of a user command."
			::= { fkV2Dhcp4FixedControl 2 }

		
		-- 1.3.6.1.4.1.10428 9 1.102.6.2.2.4.2.3
		fkV2Dhcp4FixedControlTimer OBJECT-TYPE
			SYNTAX Gauge32
			MAX-ACCESS read-write
			STATUS current
			DESCRIPTION
				"The maximum wait Time for the manager for a long running user command."
			::= { fkV2Dhcp4FixedControl 3 }

		
		-- 1.3.6.1.4.1.10428 9 1.102.6.2.2.4.2.4
		fkV2Dhcp4FixedControlTimeStamp OBJECT-TYPE
			SYNTAX TimeTicks
			MAX-ACCESS read-only
			STATUS current
			DESCRIPTION
				"The Time stamp of the last command (end of command)."
			::= { fkV2Dhcp4FixedControl 4 }

		
		-- 1.3.6.1.4.1.10428 9 1.102.6.2.2.4.2.5
		fkV2Dhcp4FixedControlReqResult OBJECT-TYPE
			SYNTAX FkControlRequestResultType
			MAX-ACCESS read-only
			STATUS current
			DESCRIPTION
				"The result of the last user command."
			::= { fkV2Dhcp4FixedControl 5 }

		
		-- 1.3.6.1.4.1.10428 9 1.102.6.2.2.4.2.6
		fkV2Dhcp4FixedControlPoolIndex OBJECT-TYPE
			SYNTAX INTEGER (1..255)
			MAX-ACCESS read-write
			STATUS current
			DESCRIPTION
				"Description."
			::= { fkV2Dhcp4FixedControl 6 }

		
		-- 1.3.6.1.4.1.10428 9 1.102.6.2.2.4.2.7
		fkV2Dhcp4FixedControlAddress OBJECT-TYPE
			SYNTAX IpAddress
			MAX-ACCESS read-write
			STATUS current
			DESCRIPTION
				"Description."
			::= { fkV2Dhcp4FixedControl 7 }

		
		-- 1.3.6.1.4.1.10428 9 1.102.6.2.2.4.2.8
		fkV2Dhcp4FixedControlMac OBJECT-TYPE
			SYNTAX MacAddress
			MAX-ACCESS read-write
			STATUS current
			DESCRIPTION
				"Description."
			::= { fkV2Dhcp4FixedControl 8 }

		
		-- 1.3.6.1.4.1.10428 9 1.102.6.2.2.4.3
		fkV2Dhcp4FixedNotification OBJECT IDENTIFIER ::= { fkV2Dhcp4Fixed 3 }

		
		-- 1.3.6.1.4.1.10428 9 1.102.6.2.2.4.3.1
		fkV2Dhcp4FixedCreated NOTIFICATION-TYPE
			OBJECTS { fkV2Dhcp4FixedControlRequest, fkV2Dhcp4FixedControlTimeStamp, fkV2Dhcp4FixedControlReqResult, fkV2Dhcp4FixedControlPoolIndex, fkV2Dhcp4FixedControlAddress, 
				fkV2Dhcp4FixedControlMac }
			STATUS current
			DESCRIPTION 
				"Description."
			::= { fkV2Dhcp4FixedNotification 1 }

		
		-- 1.3.6.1.4.1.10428 9 1.102.6.2.2.4.3.2
		fkV2Dhcp4FixedDestroyed NOTIFICATION-TYPE
			OBJECTS { fkV2Dhcp4FixedControlRequest, fkV2Dhcp4FixedControlTimeStamp, fkV2Dhcp4FixedControlReqResult, fkV2Dhcp4FixedControlPoolIndex, fkV2Dhcp4FixedControlAddress, 
				fkV2Dhcp4FixedControlMac }
			STATUS current
			DESCRIPTION 
				"Description."
			::= { fkV2Dhcp4FixedNotification 2 }

		
		-- 1.3.6.1.4.1.10428 9 1.102.6.2.2.5
		fkV2Dhcp4Dns OBJECT IDENTIFIER ::= { fkV2Dhcp4Pool 5 }

		
		-- 1.3.6.1.4.1.10428 9 1.102.6.2.2.5.1
		fkV2Dhcp4DnsTable OBJECT-TYPE
			SYNTAX SEQUENCE OF FkV2Dhcp4DnsEntry
			MAX-ACCESS not-accessible
			STATUS current
			DESCRIPTION
				"Description."
			::= { fkV2Dhcp4Dns 1 }

		
		-- 1.3.6.1.4.1.10428 9 1.102.6.2.2.5.1.1
		fkV2Dhcp4DnsEntry OBJECT-TYPE
			SYNTAX FkV2Dhcp4DnsEntry
			MAX-ACCESS not-accessible
			STATUS current
			DESCRIPTION
				"Description."
			INDEX { fkV2Dhcp4PoolIndex, fkV2Dhcp4DnsIndex }
			::= { fkV2Dhcp4DnsTable 1 }

		
		FkV2Dhcp4DnsEntry ::=
			SEQUENCE { 
				fkV2Dhcp4DnsIndex
					INTEGER,
				fkV2Dhcp4DnsAddress
					IpAddress
			 }

		-- 1.3.6.1.4.1.10428 9 1.102.6.2.2.5.1.1.1
		fkV2Dhcp4DnsIndex OBJECT-TYPE
			SYNTAX INTEGER (1..8)
			MAX-ACCESS read-only
			STATUS current
			DESCRIPTION
				"Description."
			::= { fkV2Dhcp4DnsEntry 1 }

		
		-- 1.3.6.1.4.1.10428 9 1.102.6.2.2.5.1.1.2
		fkV2Dhcp4DnsAddress OBJECT-TYPE
			SYNTAX IpAddress
			MAX-ACCESS read-only
			STATUS current
			DESCRIPTION
				"The Ip address of Dns setting in Dhcp server daemon.
				"
			::= { fkV2Dhcp4DnsEntry 2 }

		
		-- 1.3.6.1.4.1.10428 9 1.102.6.2.2.5.2
		fkV2Dhcp4DnsControl OBJECT IDENTIFIER ::= { fkV2Dhcp4Dns 2 }

		
		-- 1.3.6.1.4.1.10428 9 1.102.6.2.2.5.2.1
		fkV2Dhcp4DnsControlRequest OBJECT-TYPE
			SYNTAX INTEGER
				{
				createDhcpDns(1),
				destroyDhcpDns(2)
				}
			MAX-ACCESS read-write
			STATUS current
			DESCRIPTION
				"The request of a user command.
				create될때는 항상 insert방식이면 개수가 넘쳐나면
				실패한다.
				destroy할때는 그 번호만을 삭제한다. 없으면 실패.삭제된 후에
				뒤의 index들은 앞으로 당겨진다.
				
				이러한 동작은 gateway나 option에서도 마찬가지이다."
			::= { fkV2Dhcp4DnsControl 1 }

		
		-- 1.3.6.1.4.1.10428 9 1.102.6.2.2.5.2.2
		fkV2Dhcp4DnsControlStatus OBJECT-TYPE
			SYNTAX FkControlStatusType
			MAX-ACCESS read-only
			STATUS current
			DESCRIPTION
				"The status of a user command."
			::= { fkV2Dhcp4DnsControl 2 }

		
		-- 1.3.6.1.4.1.10428 9 1.102.6.2.2.5.2.3
		fkV2Dhcp4DnsControlTimer OBJECT-TYPE
			SYNTAX Gauge32
			MAX-ACCESS read-write
			STATUS current
			DESCRIPTION
				"The maximum wait Time for the manager for a long running user command."
			::= { fkV2Dhcp4DnsControl 3 }

		
		-- 1.3.6.1.4.1.10428 9 1.102.6.2.2.5.2.4
		fkV2Dhcp4DnsControlTimeStamp OBJECT-TYPE
			SYNTAX TimeTicks
			MAX-ACCESS read-only
			STATUS current
			DESCRIPTION
				"The Time stamp of the last command (end of command)."
			::= { fkV2Dhcp4DnsControl 4 }

		
		-- 1.3.6.1.4.1.10428 9 1.102.6.2.2.5.2.5
		fkV2Dhcp4DnsControlReqResult OBJECT-TYPE
			SYNTAX FkControlRequestResultType
			MAX-ACCESS read-write
			STATUS current
			DESCRIPTION
				"The result of the last user command."
			::= { fkV2Dhcp4DnsControl 5 }

		
		-- 1.3.6.1.4.1.10428 9 1.102.6.2.2.5.2.6
		fkV2Dhcp4DnsControlPoolIndex OBJECT-TYPE
			SYNTAX INTEGER (1..255)
			MAX-ACCESS read-write
			STATUS current
			DESCRIPTION
				"Description."
			::= { fkV2Dhcp4DnsControl 6 }

		
		-- 1.3.6.1.4.1.10428 9 1.102.6.2.2.5.2.7
		fkV2Dhcp4DnsControlIndex OBJECT-TYPE
			SYNTAX INTEGER (0 | 1..8)
			MAX-ACCESS read-write
			STATUS current
			DESCRIPTION
				"Description."
			::= { fkV2Dhcp4DnsControl 7 }

		
		-- 1.3.6.1.4.1.10428 9 1.102.6.2.2.5.2.8
		fkV2Dhcp4DnsControlAddress OBJECT-TYPE
			SYNTAX IpAddress
			MAX-ACCESS read-write
			STATUS current
			DESCRIPTION
				"Description."
			::= { fkV2Dhcp4DnsControl 8 }

		
		-- 1.3.6.1.4.1.10428 9 1.102.6.2.2.5.3
		fkV2Dhcp4DnsNotification OBJECT IDENTIFIER ::= { fkV2Dhcp4Dns 3 }

		
		-- 1.3.6.1.4.1.10428 9 1.102.6.2.2.5.3.1
		fkV2Dhcp4DnsCreated NOTIFICATION-TYPE
			OBJECTS { fkV2Dhcp4DnsControlRequest, fkV2Dhcp4DnsControlTimeStamp, fkV2Dhcp4DnsControlReqResult, fkV2Dhcp4DnsAddress }
			STATUS current
			DESCRIPTION 
				"Description."
			::= { fkV2Dhcp4DnsNotification 1 }

		
		-- 1.3.6.1.4.1.10428 9 1.102.6.2.2.5.3.2
		fkV2Dhcp4DnsDestroyed NOTIFICATION-TYPE
			OBJECTS { fkV2Dhcp4DnsControlRequest, fkV2Dhcp4DnsControlTimeStamp, fkV2Dhcp4DnsControlReqResult, fkV2Dhcp4DnsControlPoolIndex, fkV2Dhcp4DnsControlIndex
				 }
			STATUS current
			DESCRIPTION 
				"The fkDnsIp is 0.0.0.0 for CLI 
				'no ip dhcp default-config dns-server'"
			::= { fkV2Dhcp4DnsNotification 2 }

		
		-- 1.3.6.1.4.1.10428 9 1.102.6.2.2.6
		fkV2Dhcp4DefaultGateway OBJECT IDENTIFIER ::= { fkV2Dhcp4Pool 6 }

		
		-- 1.3.6.1.4.1.10428 9 1.102.6.2.2.6.1
		fkV2Dhcp4DefaultGatewayTable OBJECT-TYPE
			SYNTAX SEQUENCE OF FkV2Dhcp4DefaultGatewayEntry
			MAX-ACCESS not-accessible
			STATUS current
			DESCRIPTION
				"Description."
			::= { fkV2Dhcp4DefaultGateway 1 }

		
		-- 1.3.6.1.4.1.10428 9 1.102.6.2.2.6.1.1
		fkV2Dhcp4DefaultGatewayEntry OBJECT-TYPE
			SYNTAX FkV2Dhcp4DefaultGatewayEntry
			MAX-ACCESS not-accessible
			STATUS current
			DESCRIPTION
				"Description."
			INDEX { fkV2Dhcp4PoolIndex, fkV2Dhcp4DefaultGatewayIndex }
			::= { fkV2Dhcp4DefaultGatewayTable 1 }

		
		FkV2Dhcp4DefaultGatewayEntry ::=
			SEQUENCE { 
				fkV2Dhcp4DefaultGatewayIndex
					INTEGER,
				fkV2Dhcp4DefaultGatewayAddress
					IpAddress
			 }

		-- 1.3.6.1.4.1.10428 9 1.102.6.2.2.6.1.1.1
		fkV2Dhcp4DefaultGatewayIndex OBJECT-TYPE
			SYNTAX INTEGER (1..8)
			MAX-ACCESS read-only
			STATUS current
			DESCRIPTION
				"Description."
			::= { fkV2Dhcp4DefaultGatewayEntry 1 }

		
		-- 1.3.6.1.4.1.10428 9 1.102.6.2.2.6.1.1.2
		fkV2Dhcp4DefaultGatewayAddress OBJECT-TYPE
			SYNTAX IpAddress
			MAX-ACCESS read-only
			STATUS current
			DESCRIPTION
				"The Gateway IP assigned to leases of the Subnet."
			::= { fkV2Dhcp4DefaultGatewayEntry 2 }

		
		-- 1.3.6.1.4.1.10428 9 1.102.6.2.2.6.2
		fkV2Dhcp4DefaultGatewayControl OBJECT IDENTIFIER ::= { fkV2Dhcp4DefaultGateway 2 }

		
		-- 1.3.6.1.4.1.10428 9 1.102.6.2.2.6.2.1
		fkV2Dhcp4DefaultGatewayControlRequest OBJECT-TYPE
			SYNTAX INTEGER
				{
				createDhcpDefaultGateway(1),
				destroyDhcpDefaultGateway(2)
				}
			MAX-ACCESS read-write
			STATUS current
			DESCRIPTION
				"The request of a user command."
			::= { fkV2Dhcp4DefaultGatewayControl 1 }

		
		-- 1.3.6.1.4.1.10428 9 1.102.6.2.2.6.2.2
		fkV2Dhcp4DefaultGatewayControlStatus OBJECT-TYPE
			SYNTAX FkControlStatusType
			MAX-ACCESS read-only
			STATUS current
			DESCRIPTION
				"The status of a user command."
			::= { fkV2Dhcp4DefaultGatewayControl 2 }

		
		-- 1.3.6.1.4.1.10428 9 1.102.6.2.2.6.2.3
		fkV2Dhcp4DefaultGatewayControlTimer OBJECT-TYPE
			SYNTAX Gauge32
			MAX-ACCESS read-write
			STATUS current
			DESCRIPTION
				"The maximum wait Time for the manager for a long running user command."
			::= { fkV2Dhcp4DefaultGatewayControl 3 }

		
		-- 1.3.6.1.4.1.10428 9 1.102.6.2.2.6.2.4
		fkV2Dhcp4DefaultGatewayControlTimeStamp OBJECT-TYPE
			SYNTAX TimeTicks
			MAX-ACCESS read-only
			STATUS current
			DESCRIPTION
				"The Time stamp of the last command (end of command)."
			::= { fkV2Dhcp4DefaultGatewayControl 4 }

		
		-- 1.3.6.1.4.1.10428 9 1.102.6.2.2.6.2.5
		fkV2Dhcp4DefaultGatewayControlReqResult OBJECT-TYPE
			SYNTAX FkControlRequestResultType
			MAX-ACCESS read-only
			STATUS current
			DESCRIPTION
				"The result of the last user command."
			::= { fkV2Dhcp4DefaultGatewayControl 5 }

		
		-- 1.3.6.1.4.1.10428 9 1.102.6.2.2.6.2.6
		fkV2Dhcp4DefaultGatewayControlPoolIndex OBJECT-TYPE
			SYNTAX INTEGER (1..255)
			MAX-ACCESS read-write
			STATUS current
			DESCRIPTION
				"The Pool name."
			::= { fkV2Dhcp4DefaultGatewayControl 6 }

		
		-- 1.3.6.1.4.1.10428 9 1.102.6.2.2.6.2.7
		fkV2Dhcp4DefaultGatewayControlIndex OBJECT-TYPE
			SYNTAX INTEGER (0 | 1..8)
			MAX-ACCESS read-write
			STATUS current
			DESCRIPTION
				"Description."
			::= { fkV2Dhcp4DefaultGatewayControl 7 }

		
		-- 1.3.6.1.4.1.10428 9 1.102.6.2.2.6.2.8
		fkV2Dhcp4DefaultGatewayControlAddress OBJECT-TYPE
			SYNTAX IpAddress
			MAX-ACCESS read-write
			STATUS current
			DESCRIPTION
				"The Gateway IP assigned to Subnet."
			::= { fkV2Dhcp4DefaultGatewayControl 8 }

		
		-- 1.3.6.1.4.1.10428 9 1.102.6.2.2.6.3
		fkV2Dhcp4DefaultGatewayNotification OBJECT IDENTIFIER ::= { fkV2Dhcp4DefaultGateway 3 }

		
		-- 1.3.6.1.4.1.10428 9 1.102.6.2.2.6.3.1
		fkV2Dhcp4DefaultGatewayCreated NOTIFICATION-TYPE
			OBJECTS { fkV2Dhcp4DefaultGatewayControlRequest, fkV2Dhcp4DefaultGatewayControlTimeStamp, fkV2Dhcp4DefaultGatewayControlReqResult, fkV2Dhcp4DefaultGatewayAddress }
			STATUS current
			DESCRIPTION 
				"Description."
			::= { fkV2Dhcp4DefaultGatewayNotification 1 }

		
		-- 1.3.6.1.4.1.10428 9 1.102.6.2.2.6.3.2
		fkV2Dhcp4DefaultGatewayDestroyed NOTIFICATION-TYPE
			OBJECTS { fkV2Dhcp4DefaultGatewayControlRequest, fkV2Dhcp4DefaultGatewayControlReqResult, fkV2Dhcp4DefaultGatewayControlTimeStamp, fkV2Dhcp4DefaultGatewayControlPoolIndex, fkV2Dhcp4DefaultGatewayControlIndex
				 }
			STATUS current
			DESCRIPTION 
				"The fkDefaultGatewayIp is 0.0.0.0 for CLI 
				'no default-gateway all'"
			::= { fkV2Dhcp4DefaultGatewayNotification 2 }

		
		-- 1.3.6.1.4.1.10428 9 1.102.6.2.2.7
		fkV2Dhcp4Option OBJECT IDENTIFIER ::= { fkV2Dhcp4Pool 7 }

		
		-- 1.3.6.1.4.1.10428 9 1.102.6.2.2.7.1
		fkV2Dhcp4OptionTable OBJECT-TYPE
			SYNTAX SEQUENCE OF FkV2Dhcp4OptionEntry
			MAX-ACCESS not-accessible
			STATUS current
			DESCRIPTION
				"Description."
			::= { fkV2Dhcp4Option 1 }

		
		-- 1.3.6.1.4.1.10428 9 1.102.6.2.2.7.1.1
		fkV2Dhcp4OptionEntry OBJECT-TYPE
			SYNTAX FkV2Dhcp4OptionEntry
			MAX-ACCESS not-accessible
			STATUS current
			DESCRIPTION
				"Description."
			INDEX { fkV2Dhcp4PoolIndex, fkV2Dhcp4OptionCode, fkV2Dhcp4OptionInstance }
			::= { fkV2Dhcp4OptionTable 1 }

		
		FkV2Dhcp4OptionEntry ::=
			SEQUENCE { 
				fkV2Dhcp4OptionCode
					INTEGER,
				fkV2Dhcp4OptionInstance
					INTEGER,
				fkV2Dhcp4OptionType
					INTEGER,
				fkV2Dhcp4OptionValue
					OCTET STRING
			 }

		-- 1.3.6.1.4.1.10428 9 1.102.6.2.2.7.1.1.1
		fkV2Dhcp4OptionCode OBJECT-TYPE
			SYNTAX INTEGER
				{
				subnetMask(1),
				timeOffset(2),
				router(3),
				timeServer(4),
				nameServer(5),
				domainNameServer(6),
				logServer(7),
				cookieServer(8),
				lprServer(9),
				impressServer(10),
				resourceLocationServer(11),
				hostName(12),
				bootFileSize(13),
				meritFile(14),
				domainName(15),
				swapServer(16),
				rootPath(17),
				extensionsPath(18),
				ipForwardState(19),
				nonLocalSourceRoutingState(20),
				policyFilter(21),
				maximumDatagramReassemblySize(22),
				defaultIpTimeToLive(23),
				pathMtuAgingTimeout(24),
				pathMtuPlateauTable(25),
				interfaceMtu(26),
				allSubnetsAreLocal(27),
				broadcastAddress(28),
				performMaskDiscovery(29),
				maskSupplier(30),
				performRouterDiscovery(31),
				routerSolicitationAddress(32),
				staticRoute(33),
				trailerEncapsulation(34),
				arpCacheTimeout(35),
				ethernetEncapsulationOption(36),
				tcpDefaultTtl(37),
				tcpKeepaliveInterval(38),
				tcpKeepaliveGarbage(39),
				nisDomain(40),
				nisServers(41),
				networkTimeProtocolServers(42),
				vendorSpecificInformation(43),
				netbiosOverTcpIpNameServer(44),
				netbiosOverTcpIpDatagramDistributionServer(45),
				netbiosOverTcpIpNodeType(46),
				netbiosOverTcpIpScope(47),
				xWindowSystemFontServer(48),
				xWindowSystemDisplayManager(49),
				requestedIpAddress(50),
				ipAddressLeaseTime(51),
				optionOverload(52),
				dhcpMessageType(53),
				serverIdentifier(54),
				parameterRequestList(55),
				message(56),
				maximumDhcpMessageSize(57),
				renewalTimeValue(58),
				rebindingTimeValue(59),
				vendorClassIdentifier(60),
				clientIdentifier(61),
				nisPlusDomain(64),
				nisPlusServers(65),
				tftpServerName(66),
				bootFileName(67),
				mobileIpHomeAgent(68),
				smtpServer(69),
				pop3Server(70),
				nntpServer(71),
				wwwServer(72),
				defaultFingerServer(73),
				ircServer(74),
				streetTalkServer(75),
				stdaServer(76)
				}
			MAX-ACCESS read-only
			STATUS current
			DESCRIPTION
				"3: default Gateway
				4: DNS Server"
			::= { fkV2Dhcp4OptionEntry 1 }

		
		-- 1.3.6.1.4.1.10428 9 1.102.6.2.2.7.1.1.2
		fkV2Dhcp4OptionInstance OBJECT-TYPE
			SYNTAX INTEGER (1..8)
			MAX-ACCESS read-only
			STATUS current
			DESCRIPTION
				"Description."
			::= { fkV2Dhcp4OptionEntry 2 }

		
		-- 1.3.6.1.4.1.10428 9 1.102.6.2.2.7.1.1.3
		fkV2Dhcp4OptionType OBJECT-TYPE
			SYNTAX INTEGER
				{
				ipaddress(1),
				hex(2),
				text(3)
				}
			MAX-ACCESS read-only
			STATUS current
			DESCRIPTION
				"Description."
			::= { fkV2Dhcp4OptionEntry 3 }

		
		-- 1.3.6.1.4.1.10428 9 1.102.6.2.2.7.1.1.4
		fkV2Dhcp4OptionValue OBJECT-TYPE
			SYNTAX OCTET STRING (SIZE (1..64))
			MAX-ACCESS read-only
			STATUS current
			DESCRIPTION
				"Description."
			::= { fkV2Dhcp4OptionEntry 4 }

		
		-- 1.3.6.1.4.1.10428 9 1.102.6.2.2.7.2
		fkV2Dhcp4OptionControl OBJECT IDENTIFIER ::= { fkV2Dhcp4Option 2 }

		
		-- 1.3.6.1.4.1.10428 9 1.102.6.2.2.7.2.1
		fkV2Dhcp4OptionControlRequest OBJECT-TYPE
			SYNTAX INTEGER
				{
				createDhcpOption(1),
				destoryDhcpOption(2)
				}
			MAX-ACCESS read-write
			STATUS current
			DESCRIPTION
				"The request of a user command."
			::= { fkV2Dhcp4OptionControl 1 }

		
		-- 1.3.6.1.4.1.10428 9 1.102.6.2.2.7.2.2
		fkV2Dhcp4OptionControlStatus OBJECT-TYPE
			SYNTAX FkControlStatusType
			MAX-ACCESS read-only
			STATUS current
			DESCRIPTION
				"The status of a user command."
			::= { fkV2Dhcp4OptionControl 2 }

		
		-- 1.3.6.1.4.1.10428 9 1.102.6.2.2.7.2.3
		fkV2Dhcp4OptionControlTimer OBJECT-TYPE
			SYNTAX Gauge32
			MAX-ACCESS read-write
			STATUS current
			DESCRIPTION
				"The maximum wait Time for the manager for a long running user command."
			::= { fkV2Dhcp4OptionControl 3 }

		
		-- 1.3.6.1.4.1.10428 9 1.102.6.2.2.7.2.4
		fkV2Dhcp4OptionControlTimeStamp OBJECT-TYPE
			SYNTAX TimeTicks
			MAX-ACCESS read-only
			STATUS current
			DESCRIPTION
				"The Time stamp of the last command (end of command)."
			::= { fkV2Dhcp4OptionControl 4 }

		
		-- 1.3.6.1.4.1.10428 9 1.102.6.2.2.7.2.5
		fkV2Dhcp4OptionControlReqResult OBJECT-TYPE
			SYNTAX FkControlRequestResultType
			MAX-ACCESS read-only
			STATUS current
			DESCRIPTION
				"The result of the last user command."
			::= { fkV2Dhcp4OptionControl 5 }

		
		-- 1.3.6.1.4.1.10428 9 1.102.6.2.2.7.2.6
		fkV2Dhcp4OptionControlPoolIndex OBJECT-TYPE
			SYNTAX INTEGER (1..255)
			MAX-ACCESS read-write
			STATUS current
			DESCRIPTION
				"Description."
			::= { fkV2Dhcp4OptionControl 6 }

		
		-- 1.3.6.1.4.1.10428 9 1.102.6.2.2.7.2.7
		fkV2Dhcp4OptionControlCode OBJECT-TYPE
			SYNTAX INTEGER
				{
				timeOffset(2),
				timeServer(4),
				nameServer(5),
				logServer(7),
				cookieServer(8),
				lprServer(9),
				impressServer(10),
				resourceLocationServer(11),
				swapServer(16),
				rootPath(17),
				ipForwardState(19),
				nonLocalSourceRoutingState(20),
				policyFilter(21),
				maximumDatagramReassemblySize(22),
				defaultIpTimeToLive(23),
				pathMtuAgingTimeout(24),
				interfaceMtu(26),
				allSubnetsAreLocal(27),
				broadcastAddress(28),
				performMaskDiscovery(29),
				maskSupplier(30),
				performRouterDiscovery(31),
				routerSolicitationAddress(32),
				staticRoute(33),
				trailerEncapsulation(34),
				arpCacheTimeout(35),
				ethernetEncapsulationOption(36),
				tcpDefaultTtl(37),
				tcpKeepaliveInterval(38),
				tcpKeepaliveGarbage(39),
				nisDomain(40),
				nisServers(41),
				networkTimeProtocolServers(42),
				xWindowSystemFontServer(48),
				xWindowSystemDisplayManager(49),
				nisPlusDomain(64),
				nisPlusServers(65),
				tftpServerName(66),
				mobileIpHomeAgent(68),
				smtpServer(69),
				pop3Server(70),
				nntpServer(71),
				wwwServer(72),
				defaultFingerServer(73),
				ircServer(74),
				streetTalkServer(75),
				stdaServer(76)
				}
			MAX-ACCESS read-write
			STATUS current
			DESCRIPTION
				"Description."
			::= { fkV2Dhcp4OptionControl 7 }

		
		-- 1.3.6.1.4.1.10428 9 1.102.6.2.2.7.2.8
		fkV2Dhcp4OptionControlInstance OBJECT-TYPE
			SYNTAX INTEGER (0 | 1..8)
			MAX-ACCESS read-write
			STATUS current
			DESCRIPTION
				"Description."
			::= { fkV2Dhcp4OptionControl 8 }

		
		-- 1.3.6.1.4.1.10428 9 1.102.6.2.2.7.2.9
		fkV2Dhcp4OptionControlType OBJECT-TYPE
			SYNTAX INTEGER
				{
				ipaddress(1),
				hex(2),
				text(3)
				}
			MAX-ACCESS read-write
			STATUS current
			DESCRIPTION
				"Description."
			::= { fkV2Dhcp4OptionControl 9 }

		
		-- 1.3.6.1.4.1.10428 9 1.102.6.2.2.7.2.10
		fkV2Dhcp4OptionControlValue OBJECT-TYPE
			SYNTAX OCTET STRING (SIZE (1..64))
			MAX-ACCESS read-write
			STATUS current
			DESCRIPTION
				"Description."
			::= { fkV2Dhcp4OptionControl 10 }

		
		-- 1.3.6.1.4.1.10428 9 1.102.6.2.2.7.3
		fkV2Dhcp4OptionNotification OBJECT IDENTIFIER ::= { fkV2Dhcp4Option 3 }

		
		-- 1.3.6.1.4.1.10428 9 1.102.6.2.2.7.3.1
		fkV2Dhcp4OptionCreated NOTIFICATION-TYPE
			OBJECTS { fkV2Dhcp4OptionControlRequest, fkV2Dhcp4OptionControlReqResult, fkV2Dhcp4OptionControlTimeStamp, fkV2Dhcp4OptionType, fkV2Dhcp4OptionValue
				 }
			STATUS current
			DESCRIPTION 
				"Description."
			::= { fkV2Dhcp4OptionNotification 1 }

		
		-- 1.3.6.1.4.1.10428 9 1.102.6.2.2.7.3.2
		fkV2Dhcp4OptionDestroyed NOTIFICATION-TYPE
			OBJECTS { fkV2Dhcp4OptionControlRequest, fkV2Dhcp4OptionControlTimeStamp, fkV2Dhcp4OptionControlReqResult, fkV2Dhcp4OptionControlPoolIndex, fkV2Dhcp4OptionControlCode, 
				fkV2Dhcp4OptionControlInstance }
			STATUS current
			DESCRIPTION 
				"Description."
			::= { fkV2Dhcp4OptionNotification 2 }

		
		-- 1.3.6.1.4.1.10428 9 1.102.6.2.2.8
		fkV2Dhcp4Logs OBJECT IDENTIFIER ::= { fkV2Dhcp4Pool 8 }

		
		-- 1.3.6.1.4.1.10428 9 1.102.6.2.2.8.1
		fkV2Dhcp4LogsTable OBJECT-TYPE
			SYNTAX SEQUENCE OF FkV2Dhcp4LogsEntry
			MAX-ACCESS not-accessible
			STATUS current
			DESCRIPTION
				"Description."
			::= { fkV2Dhcp4Logs 1 }

		
		-- 1.3.6.1.4.1.10428 9 1.102.6.2.2.8.1.1
		fkV2Dhcp4LogsEntry OBJECT-TYPE
			SYNTAX FkV2Dhcp4LogsEntry
			MAX-ACCESS not-accessible
			STATUS current
			DESCRIPTION
				"Description."
			INDEX { fkV2Dhcp4PoolIndex, fkV2Dhcp4LogsIndex }
			::= { fkV2Dhcp4LogsTable 1 }

		
		FkV2Dhcp4LogsEntry ::=
			SEQUENCE { 
				fkV2Dhcp4LogsIndex
					INTEGER,
				fkV2Dhcp4LogsAddress
					IpAddress
			 }

		-- 1.3.6.1.4.1.10428 9 1.102.6.2.2.8.1.1.1
		fkV2Dhcp4LogsIndex OBJECT-TYPE
			SYNTAX INTEGER (1..3)
			MAX-ACCESS read-only
			STATUS current
			DESCRIPTION
				"The index of Log server setting in DHCP server daemon"
			::= { fkV2Dhcp4LogsEntry 1 }

		
		-- 1.3.6.1.4.1.10428 9 1.102.6.2.2.8.1.1.2
		fkV2Dhcp4LogsAddress OBJECT-TYPE
			SYNTAX IpAddress
			MAX-ACCESS read-only
			STATUS current
			DESCRIPTION
				"The IP address of Log server setting in DHCP server daemon"
			::= { fkV2Dhcp4LogsEntry 2 }

		
		-- 1.3.6.1.4.1.10428 9 1.102.6.2.2.8.2
		fkV2Dhcp4LogsControl OBJECT IDENTIFIER ::= { fkV2Dhcp4Logs 2 }

		
		-- 1.3.6.1.4.1.10428 9 1.102.6.2.2.8.2.1
		fkV2Dhcp4LogsControlRequest OBJECT-TYPE
			SYNTAX INTEGER
				{
				createDhcpLogs(1),
				destroyDhcpLogs(2)
				}
			MAX-ACCESS read-write
			STATUS current
			DESCRIPTION
				"Description."
			::= { fkV2Dhcp4LogsControl 1 }

		
		-- 1.3.6.1.4.1.10428 9 1.102.6.2.2.8.2.2
		fkV2Dhcp4LogsControlStatus OBJECT-TYPE
			SYNTAX FkControlStatusType
			MAX-ACCESS read-only
			STATUS current
			DESCRIPTION
				"Description."
			::= { fkV2Dhcp4LogsControl 2 }

		
		-- 1.3.6.1.4.1.10428 9 1.102.6.2.2.8.2.3
		fkV2Dhcp4LogsControlTimer OBJECT-TYPE
			SYNTAX Gauge32
			MAX-ACCESS read-write
			STATUS current
			DESCRIPTION
				"Description."
			::= { fkV2Dhcp4LogsControl 3 }

		
		-- 1.3.6.1.4.1.10428 9 1.102.6.2.2.8.2.4
		fkV2Dhcp4LogsControlTimeStamp OBJECT-TYPE
			SYNTAX TimeTicks
			MAX-ACCESS read-only
			STATUS current
			DESCRIPTION
				"Description."
			::= { fkV2Dhcp4LogsControl 4 }

		
		-- 1.3.6.1.4.1.10428 9 1.102.6.2.2.8.2.5
		fkV2Dhcp4LogsControlReqResult OBJECT-TYPE
			SYNTAX FkControlRequestResultType
			MAX-ACCESS read-only
			STATUS current
			DESCRIPTION
				"Description."
			::= { fkV2Dhcp4LogsControl 5 }

		
		-- 1.3.6.1.4.1.10428 9 1.102.6.2.2.8.2.6
		fkV2Dhcp4LogsControlPoolIndex OBJECT-TYPE
			SYNTAX INTEGER (1..255)
			MAX-ACCESS read-write
			STATUS current
			DESCRIPTION
				"The index of DCHP pool"
			::= { fkV2Dhcp4LogsControl 6 }

		
		-- 1.3.6.1.4.1.10428 9 1.102.6.2.2.8.2.7
		fkV2Dhcp4LogsControlIndex OBJECT-TYPE
			SYNTAX INTEGER (0 | 1..3)
			MAX-ACCESS read-write
			STATUS current
			DESCRIPTION
				"The index of Log server setting in DHCP server daemon"
			::= { fkV2Dhcp4LogsControl 7 }

		
		-- 1.3.6.1.4.1.10428 9 1.102.6.2.2.8.2.8
		fkV2Dhcp4LogsControlAddress OBJECT-TYPE
			SYNTAX IpAddress
			MAX-ACCESS read-write
			STATUS current
			DESCRIPTION
				"The IP address of Log server setting in DHCP server daemon"
			::= { fkV2Dhcp4LogsControl 8 }

		
		-- 1.3.6.1.4.1.10428 9 1.102.6.2.2.8.3
		fkV2Dhcp4LogsNotification OBJECT IDENTIFIER ::= { fkV2Dhcp4Logs 3 }

		
		-- 1.3.6.1.4.1.10428 9 1.102.6.2.2.8.3.1
		fkV2Dhcp4LogsCreated NOTIFICATION-TYPE
			OBJECTS { fkV2Dhcp4LogsControlRequest, fkV2Dhcp4LogsControlTimeStamp, fkV2Dhcp4LogsControlReqResult, fkV2Dhcp4LogsAddress }
			STATUS current
			DESCRIPTION 
				"Description."
			::= { fkV2Dhcp4LogsNotification 1 }

		
		-- 1.3.6.1.4.1.10428 9 1.102.6.2.2.8.3.2
		fkV2Dhcp4LogsDestroyed NOTIFICATION-TYPE
			OBJECTS { fkV2Dhcp4LogsControlRequest, fkV2Dhcp4LogsControlTimeStamp, fkV2Dhcp4LogsControlReqResult, fkV2Dhcp4LogsControlIndex }
			STATUS current
			DESCRIPTION 
				"Description."
			::= { fkV2Dhcp4LogsNotification 2 }

		
		-- 1.3.6.1.4.1.10428 9 1.102.6.2.2.9
		fkV2Dhcp4Ntp OBJECT IDENTIFIER ::= { fkV2Dhcp4Pool 9 }

		
		-- 1.3.6.1.4.1.10428 9 1.102.6.2.2.9.1
		fkV2Dhcp4NtpTable OBJECT-TYPE
			SYNTAX SEQUENCE OF FkV2Dhcp4NtpEntry
			MAX-ACCESS not-accessible
			STATUS current
			DESCRIPTION
				"Description."
			::= { fkV2Dhcp4Ntp 1 }

		
		-- 1.3.6.1.4.1.10428 9 1.102.6.2.2.9.1.1
		fkV2Dhcp4NtpEntry OBJECT-TYPE
			SYNTAX FkV2Dhcp4NtpEntry
			MAX-ACCESS not-accessible
			STATUS current
			DESCRIPTION
				"Description."
			INDEX { fkV2Dhcp4PoolIndex, fkV2Dhcp4NtpIndex }
			::= { fkV2Dhcp4NtpTable 1 }

		
		FkV2Dhcp4NtpEntry ::=
			SEQUENCE { 
				fkV2Dhcp4NtpIndex
					INTEGER,
				fkV2Dhcp4NtpAddress
					IpAddress
			 }

		-- 1.3.6.1.4.1.10428 9 1.102.6.2.2.9.1.1.1
		fkV2Dhcp4NtpIndex OBJECT-TYPE
			SYNTAX INTEGER (1..3)
			MAX-ACCESS read-only
			STATUS current
			DESCRIPTION
				"The index of Ntp server setting in DHCP server daemon"
			::= { fkV2Dhcp4NtpEntry 1 }

		
		-- 1.3.6.1.4.1.10428 9 1.102.6.2.2.9.1.1.2
		fkV2Dhcp4NtpAddress OBJECT-TYPE
			SYNTAX IpAddress
			MAX-ACCESS read-only
			STATUS current
			DESCRIPTION
				"The IP address of Ntp server setting in DHCP server daemon"
			::= { fkV2Dhcp4NtpEntry 2 }

		
		-- 1.3.6.1.4.1.10428 9 1.102.6.2.2.9.2
		fkV2Dhcp4NtpControl OBJECT IDENTIFIER ::= { fkV2Dhcp4Ntp 2 }

		
		-- 1.3.6.1.4.1.10428 9 1.102.6.2.2.9.2.1
		fkV2Dhcp4NtpControlRequest OBJECT-TYPE
			SYNTAX INTEGER
				{
				createDhcpNtp(1),
				destroyDhcpNtp(2)
				}
			MAX-ACCESS read-write
			STATUS current
			DESCRIPTION
				"Description."
			::= { fkV2Dhcp4NtpControl 1 }

		
		-- 1.3.6.1.4.1.10428 9 1.102.6.2.2.9.2.2
		fkV2Dhcp4NtpControlStatus OBJECT-TYPE
			SYNTAX FkControlStatusType
			MAX-ACCESS read-only
			STATUS current
			DESCRIPTION
				"Description."
			::= { fkV2Dhcp4NtpControl 2 }

		
		-- 1.3.6.1.4.1.10428 9 1.102.6.2.2.9.2.3
		fkV2Dhcp4NtpControlTimer OBJECT-TYPE
			SYNTAX Gauge32
			MAX-ACCESS read-write
			STATUS current
			DESCRIPTION
				"Description."
			::= { fkV2Dhcp4NtpControl 3 }

		
		-- 1.3.6.1.4.1.10428 9 1.102.6.2.2.9.2.4
		fkV2Dhcp4NtpControlTimeStamp OBJECT-TYPE
			SYNTAX TimeTicks
			MAX-ACCESS read-only
			STATUS current
			DESCRIPTION
				"Description."
			::= { fkV2Dhcp4NtpControl 4 }

		
		-- 1.3.6.1.4.1.10428 9 1.102.6.2.2.9.2.5
		fkV2Dhcp4NtpControlReqResult OBJECT-TYPE
			SYNTAX FkControlRequestResultType
			MAX-ACCESS read-only
			STATUS current
			DESCRIPTION
				"Description."
			::= { fkV2Dhcp4NtpControl 5 }

		
		-- 1.3.6.1.4.1.10428 9 1.102.6.2.2.9.2.6
		fkV2Dhcp4NtpControlPoolIndex OBJECT-TYPE
			SYNTAX INTEGER (1..255)
			MAX-ACCESS read-write
			STATUS current
			DESCRIPTION
				"The index of DCHP pool"
			::= { fkV2Dhcp4NtpControl 6 }

		
		-- 1.3.6.1.4.1.10428 9 1.102.6.2.2.9.2.7
		fkV2Dhcp4NtpControlIndex OBJECT-TYPE
			SYNTAX INTEGER (0 | 1..3)
			MAX-ACCESS read-write
			STATUS current
			DESCRIPTION
				"The index of Ntp server setting in DHCP server daemon"
			::= { fkV2Dhcp4NtpControl 7 }

		
		-- 1.3.6.1.4.1.10428 9 1.102.6.2.2.9.2.8
		fkV2Dhcp4NtpControlAddress OBJECT-TYPE
			SYNTAX IpAddress
			MAX-ACCESS read-write
			STATUS current
			DESCRIPTION
				"The IP address of Ntp server setting in DHCP server daemon"
			::= { fkV2Dhcp4NtpControl 8 }

		
		-- 1.3.6.1.4.1.10428 9 1.102.6.2.2.9.3
		fkV2Dhcp4NtpNotification OBJECT IDENTIFIER ::= { fkV2Dhcp4Ntp 3 }

		
		-- 1.3.6.1.4.1.10428 9 1.102.6.2.2.9.3.1
		fkV2Dhcp4NtpCreated NOTIFICATION-TYPE
			OBJECTS { fkV2Dhcp4NtpControlRequest, fkV2Dhcp4NtpControlTimeStamp, fkV2Dhcp4NtpControlReqResult, fkV2Dhcp4NtpAddress }
			STATUS current
			DESCRIPTION 
				"Description."
			::= { fkV2Dhcp4NtpNotification 1 }

		
		-- 1.3.6.1.4.1.10428 9 1.102.6.2.2.9.3.2
		fkV2Dhcp4NtpDestroyed NOTIFICATION-TYPE
			OBJECTS { fkV2Dhcp4NtpControlRequest, fkV2Dhcp4NtpControlTimeStamp, fkV2Dhcp4NtpControlReqResult, fkV2Dhcp4NtpControlPoolIndex, fkV2Dhcp4NtpControlIndex
				 }
			STATUS current
			DESCRIPTION 
				"Description."
			::= { fkV2Dhcp4NtpNotification 2 }

		
		-- 1.3.6.1.4.1.10428 9 1.102.6.2.2.10
		fkV2Dhcp4PE OBJECT IDENTIFIER ::= { fkV2Dhcp4Pool 10 }

		
		-- 1.3.6.1.4.1.10428 9 1.102.6.2.2.10.1
		fkV2Dhcp4PEVendor OBJECT IDENTIFIER ::= { fkV2Dhcp4PE 1 }

		
		-- 1.3.6.1.4.1.10428 9 1.102.6.2.2.10.1.1
		fkV2Dhcp4PEVendorTable OBJECT-TYPE
			SYNTAX SEQUENCE OF FkV2Dhcp4PEVendorEntry
			MAX-ACCESS not-accessible
			STATUS current
			DESCRIPTION
				"Description."
			::= { fkV2Dhcp4PEVendor 1 }

		
		-- 1.3.6.1.4.1.10428 9 1.102.6.2.2.10.1.1.1
		fkV2Dhcp4PEVendorEntry OBJECT-TYPE
			SYNTAX FkV2Dhcp4PEVendorEntry
			MAX-ACCESS not-accessible
			STATUS current
			DESCRIPTION
				"Description."
			INDEX { fkV2Dhcp4PEVendorPoolIndex, fkV2Dhcp4PEVendorIfIndex, fkV2Dhcp4PEVendorID, fkV2Dhcp4PEVendorStart }
			::= { fkV2Dhcp4PEVendorTable 1 }

		
		FkV2Dhcp4PEVendorEntry ::=
			SEQUENCE { 
				fkV2Dhcp4PEVendorPoolIndex
					INTEGER,
				fkV2Dhcp4PEVendorIfIndex
					INTEGER,
				fkV2Dhcp4PEVendorID
					OCTET STRING,
				fkV2Dhcp4PEVendorStart
					IpAddress,
				fkV2Dhcp4PEVendorEnd
					IpAddress
			 }

		-- 1.3.6.1.4.1.10428 9 1.102.6.2.2.10.1.1.1.1
		fkV2Dhcp4PEVendorPoolIndex OBJECT-TYPE
			SYNTAX INTEGER (1..255)
			MAX-ACCESS read-only
			STATUS current
			DESCRIPTION
				"The Pool index"
			::= { fkV2Dhcp4PEVendorEntry 1 }

		
		-- 1.3.6.1.4.1.10428 9 1.102.6.2.2.10.1.1.1.2
		fkV2Dhcp4PEVendorIfIndex OBJECT-TYPE
			SYNTAX INTEGER (1..512)
			MAX-ACCESS read-only
			STATUS current
			DESCRIPTION
				"Description."
			::= { fkV2Dhcp4PEVendorEntry 2 }

		
		-- 1.3.6.1.4.1.10428 9 1.102.6.2.2.10.1.1.1.3
		fkV2Dhcp4PEVendorID OBJECT-TYPE
			SYNTAX OCTET STRING (SIZE (0..32))
			MAX-ACCESS read-only
			STATUS current
			DESCRIPTION
				"Description."
			::= { fkV2Dhcp4PEVendorEntry 3 }

		
		-- 1.3.6.1.4.1.10428 9 1.102.6.2.2.10.1.1.1.4
		fkV2Dhcp4PEVendorStart OBJECT-TYPE
			SYNTAX IpAddress
			MAX-ACCESS read-only
			STATUS current
			DESCRIPTION
				"Description."
			::= { fkV2Dhcp4PEVendorEntry 4 }

		
		-- 1.3.6.1.4.1.10428 9 1.102.6.2.2.10.1.1.1.5
		fkV2Dhcp4PEVendorEnd OBJECT-TYPE
			SYNTAX IpAddress
			MAX-ACCESS read-only
			STATUS current
			DESCRIPTION
				"Description."
			::= { fkV2Dhcp4PEVendorEntry 5 }

		
		-- 1.3.6.1.4.1.10428 9 1.102.6.2.2.10.1.2
		fkV2Dhcp4PEVendorControl OBJECT IDENTIFIER ::= { fkV2Dhcp4PEVendor 2 }

		
		-- 1.3.6.1.4.1.10428 9 1.102.6.2.2.10.1.2.1
		fkV2Dhcp4PEVendorControlRequest OBJECT-TYPE
			SYNTAX INTEGER
				{
				createPEVendorEntry(1),
				destroyPEVendorEntry(2),
				destroyPEVendorEntryAll(3)
				}
			MAX-ACCESS read-write
			STATUS current
			DESCRIPTION
				"Description."
			::= { fkV2Dhcp4PEVendorControl 1 }

		
		-- 1.3.6.1.4.1.10428 9 1.102.6.2.2.10.1.2.2
		fkV2Dhcp4PEVendorControlStatus OBJECT-TYPE
			SYNTAX FkControlStatusType
			MAX-ACCESS read-only
			STATUS current
			DESCRIPTION
				"Description."
			::= { fkV2Dhcp4PEVendorControl 2 }

		
		-- 1.3.6.1.4.1.10428 9 1.102.6.2.2.10.1.2.3
		fkV2Dhcp4PEVendorControlTimer OBJECT-TYPE
			SYNTAX Gauge32
			MAX-ACCESS read-write
			STATUS current
			DESCRIPTION
				"Description."
			::= { fkV2Dhcp4PEVendorControl 3 }

		
		-- 1.3.6.1.4.1.10428 9 1.102.6.2.2.10.1.2.4
		fkV2Dhcp4PEVendorControlTimeStamp OBJECT-TYPE
			SYNTAX TimeTicks
			MAX-ACCESS read-only
			STATUS current
			DESCRIPTION
				"Description."
			::= { fkV2Dhcp4PEVendorControl 4 }

		
		-- 1.3.6.1.4.1.10428 9 1.102.6.2.2.10.1.2.5
		fkV2Dhcp4PEVendorControlReqResult OBJECT-TYPE
			SYNTAX FkControlRequestResultType
			MAX-ACCESS read-only
			STATUS current
			DESCRIPTION
				"Description."
			::= { fkV2Dhcp4PEVendorControl 5 }

		
		-- 1.3.6.1.4.1.10428 9 1.102.6.2.2.10.1.2.6
		fkV2Dhcp4PEVendorControlPoolIndex OBJECT-TYPE
			SYNTAX INTEGER (1..255)
			MAX-ACCESS read-write
			STATUS current
			DESCRIPTION
				"The Pool index"
			::= { fkV2Dhcp4PEVendorControl 6 }

		
		-- 1.3.6.1.4.1.10428 9 1.102.6.2.2.10.1.2.7
		fkV2Dhcp4PEVendorControlIfIndex OBJECT-TYPE
			SYNTAX INTEGER (1..512)
			MAX-ACCESS read-write
			STATUS current
			DESCRIPTION
				"Description."
			::= { fkV2Dhcp4PEVendorControl 7 }

		
		-- 1.3.6.1.4.1.10428 9 1.102.6.2.2.10.1.2.8
		fkV2Dhcp4PEVendorControlVendorID OBJECT-TYPE
			SYNTAX OCTET STRING (SIZE (0..32))
			MAX-ACCESS read-write
			STATUS current
			DESCRIPTION
				"Description."
			::= { fkV2Dhcp4PEVendorControl 8 }

		
		-- 1.3.6.1.4.1.10428 9 1.102.6.2.2.10.1.2.9
		fkV2Dhcp4PEVendorControlStart OBJECT-TYPE
			SYNTAX IpAddress
			MAX-ACCESS read-write
			STATUS current
			DESCRIPTION
				"Description."
			::= { fkV2Dhcp4PEVendorControl 9 }

		
		-- 1.3.6.1.4.1.10428 9 1.102.6.2.2.10.1.2.10
		fkV2Dhcp4PEVendorControlEnd OBJECT-TYPE
			SYNTAX IpAddress
			MAX-ACCESS read-write
			STATUS current
			DESCRIPTION
				"Description."
			::= { fkV2Dhcp4PEVendorControl 10 }

		
		-- 1.3.6.1.4.1.10428 9 1.102.6.2.2.10.1.3
		fkV2Dhcp4PEVendorNotification OBJECT IDENTIFIER ::= { fkV2Dhcp4PEVendor 3 }

		
		-- 1.3.6.1.4.1.10428 9 1.102.6.2.2.10.1.3.1
		fkV2Dhcp4PEVendorCreated NOTIFICATION-TYPE
			OBJECTS { fkV2Dhcp4PEVendorControlRequest, fkV2Dhcp4PEVendorControlTimeStamp, fkV2Dhcp4PEVendorControlReqResult, fkV2Dhcp4PEVendorControlPoolIndex, fkV2Dhcp4PEVendorControlIfIndex, 
				fkV2Dhcp4PEVendorControlVendorID, fkV2Dhcp4PEVendorControlStart, fkV2Dhcp4PEVendorControlEnd }
			STATUS current
			DESCRIPTION 
				"Description."
			::= { fkV2Dhcp4PEVendorNotification 1 }

		
		-- 1.3.6.1.4.1.10428 9 1.102.6.2.2.10.1.3.2
		fkV2Dhcp4PEVendorDestroyed NOTIFICATION-TYPE
			OBJECTS { fkV2Dhcp4PEVendorControlRequest, fkV2Dhcp4PEVendorControlTimeStamp, fkV2Dhcp4PEVendorControlReqResult, fkV2Dhcp4PEVendorControlPoolIndex, fkV2Dhcp4PEVendorControlIfIndex, 
				fkV2Dhcp4PEVendorControlVendorID, fkV2Dhcp4PEVendorControlStart, fkV2Dhcp4PEVendorControlEnd }
			STATUS current
			DESCRIPTION 
				"Description."
			::= { fkV2Dhcp4PEVendorNotification 2 }

		
		-- 1.3.6.1.4.1.10428 9 1.102.6.2.2.10.1.3.3
		fkV2Dhcp4PEVendorAllDestroyed NOTIFICATION-TYPE
			OBJECTS { fkV2Dhcp4PEVendorControlRequest, fkV2Dhcp4PEVendorControlTimeStamp, fkV2Dhcp4PEVendorControlReqResult, fkV2Dhcp4PEVendorControlPoolIndex, fkV2Dhcp4PEVendorControlIfIndex
				 }
			STATUS current
			DESCRIPTION 
				"Description."
			::= { fkV2Dhcp4PEVendorNotification 3 }

		
		-- 1.3.6.1.4.1.10428 9 1.102.6.2.2.10.2
		fkV2Dhcp4PEAddress OBJECT IDENTIFIER ::= { fkV2Dhcp4PE 2 }

		
		-- 1.3.6.1.4.1.10428 9 1.102.6.2.2.10.2.1
		fkV2Dhcp4PEAddressTable OBJECT-TYPE
			SYNTAX SEQUENCE OF FkV2Dhcp4PEAddressEntry
			MAX-ACCESS not-accessible
			STATUS current
			DESCRIPTION
				"Description."
			::= { fkV2Dhcp4PEAddress 1 }

		
		-- 1.3.6.1.4.1.10428 9 1.102.6.2.2.10.2.1.1
		fkV2Dhcp4PEAddressEntry OBJECT-TYPE
			SYNTAX FkV2Dhcp4PEAddressEntry
			MAX-ACCESS not-accessible
			STATUS current
			DESCRIPTION
				"Description."
			INDEX { fkV2Dhcp4PEAddressPoolIndex, fkV2Dhcp4PEAddressIfIndex, fkV2Dhcp4PEAddressStart }
			::= { fkV2Dhcp4PEAddressTable 1 }

		
		FkV2Dhcp4PEAddressEntry ::=
			SEQUENCE { 
				fkV2Dhcp4PEAddressPoolIndex
					INTEGER,
				fkV2Dhcp4PEAddressIfIndex
					INTEGER,
				fkV2Dhcp4PEAddressStart
					IpAddress,
				fkV2Dhcp4PEAddressEnd
					IpAddress
			 }

		-- 1.3.6.1.4.1.10428 9 1.102.6.2.2.10.2.1.1.1
		fkV2Dhcp4PEAddressPoolIndex OBJECT-TYPE
			SYNTAX INTEGER (1..255)
			MAX-ACCESS read-only
			STATUS current
			DESCRIPTION
				"The Pool index"
			::= { fkV2Dhcp4PEAddressEntry 1 }

		
		-- 1.3.6.1.4.1.10428 9 1.102.6.2.2.10.2.1.1.2
		fkV2Dhcp4PEAddressIfIndex OBJECT-TYPE
			SYNTAX INTEGER (1..512)
			MAX-ACCESS read-only
			STATUS current
			DESCRIPTION
				"Description."
			::= { fkV2Dhcp4PEAddressEntry 2 }

		
		-- 1.3.6.1.4.1.10428 9 1.102.6.2.2.10.2.1.1.3
		fkV2Dhcp4PEAddressStart OBJECT-TYPE
			SYNTAX IpAddress
			MAX-ACCESS read-only
			STATUS current
			DESCRIPTION
				"Description."
			::= { fkV2Dhcp4PEAddressEntry 3 }

		
		-- 1.3.6.1.4.1.10428 9 1.102.6.2.2.10.2.1.1.4
		fkV2Dhcp4PEAddressEnd OBJECT-TYPE
			SYNTAX IpAddress
			MAX-ACCESS read-only
			STATUS current
			DESCRIPTION
				"Description."
			::= { fkV2Dhcp4PEAddressEntry 4 }

		
		-- 1.3.6.1.4.1.10428 9 1.102.6.2.2.10.2.2
		fkV2Dhcp4PEAddressControl OBJECT IDENTIFIER ::= { fkV2Dhcp4PEAddress 2 }

		
		-- 1.3.6.1.4.1.10428 9 1.102.6.2.2.10.2.2.1
		fkV2Dhcp4PEAddressControlRequest OBJECT-TYPE
			SYNTAX INTEGER
				{
				createPEAddressEntry(1),
				destroyPEAddressEntry(2),
				destroyPEAddressEntryAll(3)
				}
			MAX-ACCESS read-write
			STATUS current
			DESCRIPTION
				"Description."
			::= { fkV2Dhcp4PEAddressControl 1 }

		
		-- 1.3.6.1.4.1.10428 9 1.102.6.2.2.10.2.2.2
		fkV2Dhcp4PEAddressControlStatus OBJECT-TYPE
			SYNTAX FkControlStatusType
			MAX-ACCESS read-only
			STATUS current
			DESCRIPTION
				"Description."
			::= { fkV2Dhcp4PEAddressControl 2 }

		
		-- 1.3.6.1.4.1.10428 9 1.102.6.2.2.10.2.2.3
		fkV2Dhcp4PEAddressControlTimer OBJECT-TYPE
			SYNTAX Gauge32
			MAX-ACCESS read-write
			STATUS current
			DESCRIPTION
				"Description."
			::= { fkV2Dhcp4PEAddressControl 3 }

		
		-- 1.3.6.1.4.1.10428 9 1.102.6.2.2.10.2.2.4
		fkV2Dhcp4PEAddressControlTimeStamp OBJECT-TYPE
			SYNTAX TimeTicks
			MAX-ACCESS read-only
			STATUS current
			DESCRIPTION
				"Description."
			::= { fkV2Dhcp4PEAddressControl 4 }

		
		-- 1.3.6.1.4.1.10428 9 1.102.6.2.2.10.2.2.5
		fkV2Dhcp4PEAddressControlReqResult OBJECT-TYPE
			SYNTAX FkControlRequestResultType
			MAX-ACCESS read-only
			STATUS current
			DESCRIPTION
				"Description."
			::= { fkV2Dhcp4PEAddressControl 5 }

		
		-- 1.3.6.1.4.1.10428 9 1.102.6.2.2.10.2.2.6
		fkV2Dhcp4PEAddressControlPoolIndex OBJECT-TYPE
			SYNTAX INTEGER (1..255)
			MAX-ACCESS read-write
			STATUS current
			DESCRIPTION
				"The Pool index"
			::= { fkV2Dhcp4PEAddressControl 6 }

		
		-- 1.3.6.1.4.1.10428 9 1.102.6.2.2.10.2.2.7
		fkV2Dhcp4PEAddressControlIfIndex OBJECT-TYPE
			SYNTAX INTEGER (1..512)
			MAX-ACCESS read-write
			STATUS current
			DESCRIPTION
				"Description"
			::= { fkV2Dhcp4PEAddressControl 7 }

		
		-- 1.3.6.1.4.1.10428 9 1.102.6.2.2.10.2.2.8
		fkV2Dhcp4PEAddressControlStart OBJECT-TYPE
			SYNTAX IpAddress
			MAX-ACCESS read-write
			STATUS current
			DESCRIPTION
				"Description."
			::= { fkV2Dhcp4PEAddressControl 8 }

		
		-- 1.3.6.1.4.1.10428 9 1.102.6.2.2.10.2.2.9
		fkV2Dhcp4PEAddressControlEnd OBJECT-TYPE
			SYNTAX IpAddress
			MAX-ACCESS read-write
			STATUS current
			DESCRIPTION
				"Description."
			::= { fkV2Dhcp4PEAddressControl 9 }

		
		-- 1.3.6.1.4.1.10428 9 1.102.6.2.2.10.2.3
		fkV2Dhcp4PEAddressNotification OBJECT IDENTIFIER ::= { fkV2Dhcp4PEAddress 3 }

		
		-- 1.3.6.1.4.1.10428 9 1.102.6.2.2.10.2.3.1
		fkV2Dhcp4PEAddressCreated NOTIFICATION-TYPE
			OBJECTS { fkV2Dhcp4PEAddressControlRequest, fkV2Dhcp4PEAddressControlTimeStamp, fkV2Dhcp4PEAddressControlReqResult, fkV2Dhcp4PEAddressControlPoolIndex, fkV2Dhcp4PEAddressControlIfIndex, 
				fkV2Dhcp4PEAddressControlStart, fkV2Dhcp4PEAddressControlEnd }
			STATUS current
			DESCRIPTION 
				"Description."
			::= { fkV2Dhcp4PEAddressNotification 1 }

		
		-- 1.3.6.1.4.1.10428 9 1.102.6.2.2.10.2.3.2
		fkV2Dhcp4PEAddressDestroyed NOTIFICATION-TYPE
			OBJECTS { fkV2Dhcp4PEAddressControlRequest, fkV2Dhcp4PEAddressControlTimeStamp, fkV2Dhcp4PEAddressControlReqResult, fkV2Dhcp4PEAddressControlPoolIndex, fkV2Dhcp4PEAddressControlIfIndex, 
				fkV2Dhcp4PEAddressControlStart, fkV2Dhcp4PEAddressControlEnd }
			STATUS current
			DESCRIPTION 
				"Description."
			::= { fkV2Dhcp4PEAddressNotification 2 }

		
		-- 1.3.6.1.4.1.10428 9 1.102.6.2.2.10.2.3.3
		fkV2Dhcp4PEAddressAllDestroyed NOTIFICATION-TYPE
			OBJECTS { fkV2Dhcp4PEAddressControlRequest, fkV2Dhcp4PEAddressControlTimeStamp, fkV2Dhcp4PEAddressControlReqResult, fkV2Dhcp4PEAddressControlPoolIndex, fkV2Dhcp4PEAddressControlIfIndex
				 }
			STATUS current
			DESCRIPTION 
				"Description."
			::= { fkV2Dhcp4PEAddressNotification 3 }

		
		-- 1.3.6.1.4.1.10428 9 1.102.6.2.2.10.3
		fkV2Dhcp4PENonPE OBJECT IDENTIFIER ::= { fkV2Dhcp4PE 3 }

		
		-- 1.3.6.1.4.1.10428 9 1.102.6.2.2.10.3.1
		fkV2Dhcp4PENonPETable OBJECT-TYPE
			SYNTAX SEQUENCE OF FkV2Dhcp4PENonPEEntry
			MAX-ACCESS not-accessible
			STATUS current
			DESCRIPTION
				"Description."
			::= { fkV2Dhcp4PENonPE 1 }

		
		-- 1.3.6.1.4.1.10428 9 1.102.6.2.2.10.3.1.1
		fkV2Dhcp4PENonPEEntry OBJECT-TYPE
			SYNTAX FkV2Dhcp4PENonPEEntry
			MAX-ACCESS not-accessible
			STATUS current
			DESCRIPTION
				"Description."
			INDEX { fkV2Dhcp4PENonPEPoolIndex }
			::= { fkV2Dhcp4PENonPETable 1 }

		
		FkV2Dhcp4PENonPEEntry ::=
			SEQUENCE { 
				fkV2Dhcp4PENonPEPoolIndex
					INTEGER,
				fkV2Dhcp4PENonPEStart
					IpAddress,
				fkV2Dhcp4PENonPEEnd
					IpAddress
			 }

		-- 1.3.6.1.4.1.10428 9 1.102.6.2.2.10.3.1.1.1
		fkV2Dhcp4PENonPEPoolIndex OBJECT-TYPE
			SYNTAX INTEGER (1..255)
			MAX-ACCESS read-only
			STATUS current
			DESCRIPTION
				"The Pool index"
			::= { fkV2Dhcp4PENonPEEntry 1 }

		
		-- 1.3.6.1.4.1.10428 9 1.102.6.2.2.10.3.1.1.2
		fkV2Dhcp4PENonPEStart OBJECT-TYPE
			SYNTAX IpAddress
			MAX-ACCESS read-only
			STATUS current
			DESCRIPTION
				"Description."
			::= { fkV2Dhcp4PENonPEEntry 2 }

		
		-- 1.3.6.1.4.1.10428 9 1.102.6.2.2.10.3.1.1.3
		fkV2Dhcp4PENonPEEnd OBJECT-TYPE
			SYNTAX IpAddress
			MAX-ACCESS read-only
			STATUS current
			DESCRIPTION
				"Description."
			::= { fkV2Dhcp4PENonPEEntry 3 }

		
		-- 1.3.6.1.4.1.10428 9 1.102.6.2.2.10.3.2
		fkV2Dhcp4PENonPEControl OBJECT IDENTIFIER ::= { fkV2Dhcp4PENonPE 2 }

		
		-- 1.3.6.1.4.1.10428 9 1.102.6.2.2.10.3.2.1
		fkV2Dhcp4PENonPEControlRequest OBJECT-TYPE
			SYNTAX INTEGER
				{
				createPENonPEEntry(1),
				destroyPENonPEEntry(2)
				}
			MAX-ACCESS read-write
			STATUS current
			DESCRIPTION
				"Description."
			::= { fkV2Dhcp4PENonPEControl 1 }

		
		-- 1.3.6.1.4.1.10428 9 1.102.6.2.2.10.3.2.2
		fkV2Dhcp4PENonPEControlStatus OBJECT-TYPE
			SYNTAX FkControlStatusType
			MAX-ACCESS read-only
			STATUS current
			DESCRIPTION
				"Description."
			::= { fkV2Dhcp4PENonPEControl 2 }

		
		-- 1.3.6.1.4.1.10428 9 1.102.6.2.2.10.3.2.3
		fkV2Dhcp4PENonPEControlTimer OBJECT-TYPE
			SYNTAX Gauge32
			MAX-ACCESS read-write
			STATUS current
			DESCRIPTION
				"Description."
			::= { fkV2Dhcp4PENonPEControl 3 }

		
		-- 1.3.6.1.4.1.10428 9 1.102.6.2.2.10.3.2.4
		fkV2Dhcp4PENonPEControlTimeStamp OBJECT-TYPE
			SYNTAX TimeTicks
			MAX-ACCESS read-only
			STATUS current
			DESCRIPTION
				"Description."
			::= { fkV2Dhcp4PENonPEControl 4 }

		
		-- 1.3.6.1.4.1.10428 9 1.102.6.2.2.10.3.2.5
		fkV2Dhcp4PENonPEControlReqResult OBJECT-TYPE
			SYNTAX FkControlRequestResultType
			MAX-ACCESS read-only
			STATUS current
			DESCRIPTION
				"Description."
			::= { fkV2Dhcp4PENonPEControl 5 }

		
		-- 1.3.6.1.4.1.10428 9 1.102.6.2.2.10.3.2.6
		fkV2Dhcp4PENonPEControlPoolIndex OBJECT-TYPE
			SYNTAX INTEGER (1..255)
			MAX-ACCESS read-write
			STATUS current
			DESCRIPTION
				"The Pool index"
			::= { fkV2Dhcp4PENonPEControl 6 }

		
		-- 1.3.6.1.4.1.10428 9 1.102.6.2.2.10.3.2.7
		fkV2Dhcp4PENonPEControlStart OBJECT-TYPE
			SYNTAX IpAddress
			MAX-ACCESS read-write
			STATUS current
			DESCRIPTION
				"Description."
			::= { fkV2Dhcp4PENonPEControl 7 }

		
		-- 1.3.6.1.4.1.10428 9 1.102.6.2.2.10.3.2.8
		fkV2Dhcp4PENonPEControlEnd OBJECT-TYPE
			SYNTAX IpAddress
			MAX-ACCESS read-write
			STATUS current
			DESCRIPTION
				"Description."
			::= { fkV2Dhcp4PENonPEControl 8 }

		
		-- 1.3.6.1.4.1.10428 9 1.102.6.2.2.10.3.3
		fkV2Dhcp4PENonPENotification OBJECT IDENTIFIER ::= { fkV2Dhcp4PENonPE 3 }

		
		-- 1.3.6.1.4.1.10428 9 1.102.6.2.2.10.3.3.1
		fkV2Dhcp4PENonPECreated NOTIFICATION-TYPE
			OBJECTS { fkV2Dhcp4PENonPEControlRequest, fkV2Dhcp4PENonPEControlTimeStamp, fkV2Dhcp4PENonPEControlReqResult, fkV2Dhcp4PENonPEControlPoolIndex, fkV2Dhcp4PENonPEControlStart, 
				fkV2Dhcp4PENonPEControlEnd }
			STATUS current
			DESCRIPTION 
				"Description."
			::= { fkV2Dhcp4PENonPENotification 1 }

		
		-- 1.3.6.1.4.1.10428 9 1.102.6.2.2.10.3.3.2
		fkV2Dhcp4PENonPEDestroyed NOTIFICATION-TYPE
			OBJECTS { fkV2Dhcp4PENonPEControlRequest, fkV2Dhcp4PENonPEControlTimeStamp, fkV2Dhcp4PENonPEControlReqResult, fkV2Dhcp4PENonPEControlPoolIndex, fkV2Dhcp4PENonPEControlStart, 
				fkV2Dhcp4PENonPEControlEnd }
			STATUS current
			DESCRIPTION 
				"Description."
			::= { fkV2Dhcp4PENonPENotification 2 }

		
		-- 1.3.6.1.4.1.10428 9 1.102.6.2.3
		fkV2Dhcp4Option82 OBJECT IDENTIFIER ::= { fkV2Dhcp4 3 }

		
		-- 1.3.6.1.4.1.10428 9 1.102.6.2.3.1
		fkV2Dhcp4Option82Port OBJECT IDENTIFIER ::= { fkV2Dhcp4Option82 1 }

		
		-- 1.3.6.1.4.1.10428 9 1.102.6.2.3.1.1
		fkV2Dhcp4Option82PortTable OBJECT-TYPE
			SYNTAX SEQUENCE OF FkV2Dhcp4Option82PortEntry
			MAX-ACCESS not-accessible
			STATUS current
			DESCRIPTION
				"Description."
			::= { fkV2Dhcp4Option82Port 1 }

		
		-- 1.3.6.1.4.1.10428 9 1.102.6.2.3.1.1.1
		fkV2Dhcp4Option82PortEntry OBJECT-TYPE
			SYNTAX FkV2Dhcp4Option82PortEntry
			MAX-ACCESS not-accessible
			STATUS current
			DESCRIPTION
				"Description."
			INDEX { fkV2Dhcp4Option82PortIndex }
			::= { fkV2Dhcp4Option82PortTable 1 }

		
		FkV2Dhcp4Option82PortEntry ::=
			SEQUENCE { 
				fkV2Dhcp4Option82PortIndex
					INTEGER,
				fkV2Dhcp4Option82PortCircuitType
					INTEGER,
				fkV2Dhcp4Option82PortCircuitId
					OCTET STRING,
				fkV2Dhcp4Option82PortTrustState
					INTEGER,
				fkV2Dhcp4Option82PortPolicy
					INTEGER,
				fkV2Dhcp4Option82PortPolicyDrop
					INTEGER
			 }

		-- 1.3.6.1.4.1.10428 9 1.102.6.2.3.1.1.1.1
		fkV2Dhcp4Option82PortIndex OBJECT-TYPE
			SYNTAX INTEGER (1..255)
			MAX-ACCESS read-only
			STATUS current
			DESCRIPTION
				"Description."
			::= { fkV2Dhcp4Option82PortEntry 1 }

		
		-- 1.3.6.1.4.1.10428 9 1.102.6.2.3.1.1.1.2
		fkV2Dhcp4Option82PortCircuitType OBJECT-TYPE
			SYNTAX INTEGER
				{
				undefined(0),
				index(1),
				hex(2),
				text(3),
				option(4)
				}
			MAX-ACCESS read-only
			STATUS current
			DESCRIPTION
				"Description."
			::= { fkV2Dhcp4Option82PortEntry 2 }

		
		-- 1.3.6.1.4.1.10428 9 1.102.6.2.3.1.1.1.3
		fkV2Dhcp4Option82PortCircuitId OBJECT-TYPE
			SYNTAX OCTET STRING (SIZE (0 | 1..32))
			MAX-ACCESS read-only
			STATUS current
			DESCRIPTION
				"Description."
			::= { fkV2Dhcp4Option82PortEntry 3 }

		
		-- 1.3.6.1.4.1.10428 9 1.102.6.2.3.1.1.1.4
		fkV2Dhcp4Option82PortTrustState OBJECT-TYPE
			SYNTAX INTEGER
				{
				none(0),
				normal(1),
				option82(2),
				all(3)
				}
			MAX-ACCESS read-only
			STATUS current
			DESCRIPTION
				"."
			DEFVAL { disable }
			::= { fkV2Dhcp4Option82PortEntry 4 }

		
		-- 1.3.6.1.4.1.10428 9 1.102.6.2.3.1.1.1.5
		fkV2Dhcp4Option82PortPolicy OBJECT-TYPE
			SYNTAX INTEGER
				{
				none(0),
				keep(1),
				replace(2)
				}
			MAX-ACCESS read-only
			STATUS current
			DESCRIPTION
				"The option82 port policy."
			::= { fkV2Dhcp4Option82PortEntry 5 }

		
		-- 1.3.6.1.4.1.10428 9 1.102.6.2.3.1.1.1.6
		fkV2Dhcp4Option82PortPolicyDrop OBJECT-TYPE
			SYNTAX INTEGER
				{
				none(0),
				normal(1),
				option82(2)
				}
			MAX-ACCESS read-only
			STATUS current
			DESCRIPTION
				"The option82 port drop policy."
			::= { fkV2Dhcp4Option82PortEntry 6 }

		
		-- 1.3.6.1.4.1.10428 9 1.102.6.2.3.1.2
		fkV2Dhcp4Option82PortControl OBJECT IDENTIFIER ::= { fkV2Dhcp4Option82Port 2 }

		
		-- 1.3.6.1.4.1.10428 9 1.102.6.2.3.1.2.1
		fkV2Dhcp4Option82PortControlRequest OBJECT-TYPE
			SYNTAX INTEGER
				{
				setDhcpOption82PortCircuitId(1),
				setDhcpOption82PortTrustState(2),
				clearDhcpOption82PortCircuitId(3),
				setDhcpOption82PortPolicy(4)
				}
			MAX-ACCESS read-write
			STATUS current
			DESCRIPTION
				"The request of a user command."
			::= { fkV2Dhcp4Option82PortControl 1 }

		
		-- 1.3.6.1.4.1.10428 9 1.102.6.2.3.1.2.2
		fkV2Dhcp4Option82PortControlStatus OBJECT-TYPE
			SYNTAX FkControlStatusType
			MAX-ACCESS read-only
			STATUS current
			DESCRIPTION
				"The status of a user command."
			::= { fkV2Dhcp4Option82PortControl 2 }

		
		-- 1.3.6.1.4.1.10428 9 1.102.6.2.3.1.2.3
		fkV2Dhcp4Option82PortControlTimer OBJECT-TYPE
			SYNTAX Gauge32
			MAX-ACCESS read-write
			STATUS current
			DESCRIPTION
				"The maximum wait Time for the manager for a long running user command."
			::= { fkV2Dhcp4Option82PortControl 3 }

		
		-- 1.3.6.1.4.1.10428 9 1.102.6.2.3.1.2.4
		fkV2Dhcp4Option82PortControlTimeStamp OBJECT-TYPE
			SYNTAX TimeTicks
			MAX-ACCESS read-write
			STATUS current
			DESCRIPTION
				"The Time stamp of the last command (end of command)."
			::= { fkV2Dhcp4Option82PortControl 4 }

		
		-- 1.3.6.1.4.1.10428 9 1.102.6.2.3.1.2.5
		fkV2Dhcp4Option82PortControlReqResult OBJECT-TYPE
			SYNTAX FkControlRequestResultType
			MAX-ACCESS read-write
			STATUS current
			DESCRIPTION
				"The result of the last user command."
			::= { fkV2Dhcp4Option82PortControl 5 }

		
		-- 1.3.6.1.4.1.10428 9 1.102.6.2.3.1.2.6
		fkV2Dhcp4Option82PortControlIndex OBJECT-TYPE
			SYNTAX INTEGER (1..255)
			MAX-ACCESS read-write
			STATUS current
			DESCRIPTION
				"Description."
			::= { fkV2Dhcp4Option82PortControl 6 }

		
		-- 1.3.6.1.4.1.10428 9 1.102.6.2.3.1.2.7
		fkV2Dhcp4Option82PortControlCircuitType OBJECT-TYPE
			SYNTAX INTEGER
				{
				undefined(0),
				index(1),
				hex(2),
				text(3),
				option(4)
				}
			MAX-ACCESS read-write
			STATUS current
			DESCRIPTION
				"Description."
			::= { fkV2Dhcp4Option82PortControl 7 }

		
		-- 1.3.6.1.4.1.10428 9 1.102.6.2.3.1.2.8
		fkV2Dhcp4Option82PortControlCircuitId OBJECT-TYPE
			SYNTAX OCTET STRING (SIZE (0 | 1..32))
			MAX-ACCESS read-write
			STATUS current
			DESCRIPTION
				"Description."
			::= { fkV2Dhcp4Option82PortControl 8 }

		
		-- 1.3.6.1.4.1.10428 9 1.102.6.2.3.1.2.9
		fkV2Dhcp4Option82PortControlTrustState OBJECT-TYPE
			SYNTAX INTEGER
				{
				none(0),
				normal(1),
				option82(2),
				all(3)
				}
			MAX-ACCESS read-write
			STATUS current
			DESCRIPTION
				"The result of the last user command."
			::= { fkV2Dhcp4Option82PortControl 9 }

		
		-- 1.3.6.1.4.1.10428 9 1.102.6.2.3.1.2.10
		fkV2Dhcp4Option82PortControlPolicy OBJECT-TYPE
			SYNTAX INTEGER
				{
				none(0),
				keep(1),
				replace(2)
				}
			MAX-ACCESS read-write
			STATUS current
			DESCRIPTION
				"The option82 port policy."
			::= { fkV2Dhcp4Option82PortControl 10 }

		
		-- 1.3.6.1.4.1.10428 9 1.102.6.2.3.1.2.11
		fkV2Dhcp4Option82PortControlPolicyDrop OBJECT-TYPE
			SYNTAX INTEGER
				{
				none(0),
				normal(1),
				option82(2)
				}
			MAX-ACCESS read-write
			STATUS current
			DESCRIPTION
				"Description."
			::= { fkV2Dhcp4Option82PortControl 11 }

		
		-- 1.3.6.1.4.1.10428 9 1.102.6.2.3.1.3
		fkV2Dhcp4Option82PortNotification OBJECT IDENTIFIER ::= { fkV2Dhcp4Option82Port 3 }

		
		-- 1.3.6.1.4.1.10428 9 1.102.6.2.3.1.3.1
		fkV2Dhcp4Option82PortCircuitIdChanged NOTIFICATION-TYPE
			OBJECTS { fkV2Dhcp4Option82PortControlRequest, fkV2Dhcp4Option82PortControlTimeStamp, fkV2Dhcp4Option82PortIndex, fkV2Dhcp4Option82PortControlReqResult, fkV2Dhcp4Option82PortCircuitType, 
				fkV2Dhcp4Option82PortCircuitId }
			STATUS current
			DESCRIPTION 
				"Description."
			::= { fkV2Dhcp4Option82PortNotification 1 }

		
		-- 1.3.6.1.4.1.10428 9 1.102.6.2.3.1.3.2
		fkV2Dhcp4Option82PortTrustStateChanged NOTIFICATION-TYPE
			OBJECTS { fkV2Dhcp4Option82PortControlRequest, fkV2Dhcp4Option82PortControlTimeStamp, fkV2Dhcp4Option82PortControlReqResult, fkV2Dhcp4Option82PortTrustState }
			STATUS current
			DESCRIPTION 
				"Description."
			::= { fkV2Dhcp4Option82PortNotification 2 }

		
		-- 1.3.6.1.4.1.10428 9 1.102.6.2.3.1.3.3
		fkV2Dhcp4Option82PortCircuitIdCleared NOTIFICATION-TYPE
			OBJECTS { fkV2Dhcp4Option82PortControlRequest, fkV2Dhcp4Option82PortControlTimeStamp, fkV2Dhcp4Option82PortControlReqResult, fkV2Dhcp4Option82PortIndex, fkV2Dhcp4Option82PortCircuitType
				 }
			STATUS current
			DESCRIPTION 
				"Description."
			::= { fkV2Dhcp4Option82PortNotification 3 }

		
		-- 1.3.6.1.4.1.10428 9 1.102.6.2.3.1.3.4
		fkV2Dhcp4Option82PortPolicyChanged NOTIFICATION-TYPE
			OBJECTS { fkV2Dhcp4Option82PortControlRequest, fkV2Dhcp4Option82PortControlTimeStamp, fkV2Dhcp4Option82PortControlReqResult, fkV2Dhcp4Option82PortIndex, fkV2Dhcp4Option82PortPolicy, 
				fkV2Dhcp4Option82PortPolicyDrop }
			STATUS current
			DESCRIPTION 
				"Description."
			::= { fkV2Dhcp4Option82PortNotification 4 }

		
		-- 1.3.6.1.4.1.10428 9 1.102.6.2.3.2
		fkV2Dhcp4RelayInfo OBJECT IDENTIFIER ::= { fkV2Dhcp4Option82 2 }

		
		-- 1.3.6.1.4.1.10428 9 1.102.6.2.3.2.1
		fkV2Dhcp4Remote OBJECT IDENTIFIER ::= { fkV2Dhcp4RelayInfo 1 }

		
		-- 1.3.6.1.4.1.10428 9 1.102.6.2.3.2.1.1
		fkV2Dhcp4RemoteTable OBJECT-TYPE
			SYNTAX SEQUENCE OF FkV2Dhcp4RemoteEntry
			MAX-ACCESS not-accessible
			STATUS current
			DESCRIPTION
				"Description."
			::= { fkV2Dhcp4Remote 1 }

		
		-- 1.3.6.1.4.1.10428 9 1.102.6.2.3.2.1.1.1
		fkV2Dhcp4RemoteEntry OBJECT-TYPE
			SYNTAX FkV2Dhcp4RemoteEntry
			MAX-ACCESS not-accessible
			STATUS current
			DESCRIPTION
				"Description."
			INDEX { fkV2Dhcp4RemoteId }
			::= { fkV2Dhcp4RemoteTable 1 }

		
		FkV2Dhcp4RemoteEntry ::=
			SEQUENCE { 
				fkV2Dhcp4RemoteId
					OCTET STRING,
				fkV2Dhcp4RemoteType
					INTEGER,
				fkV2Dhcp4RemoteClass
					OCTET STRING,
				fkV2Dhcp4RemoteTrust
					Boolean,
				fkV2Dhcp4RemoteLeaseLimit
					INTEGER,
				fkV2Dhcp4RemoteLeaseCnt
					INTEGER
			 }

		-- 1.3.6.1.4.1.10428 9 1.102.6.2.3.2.1.1.1.1
		fkV2Dhcp4RemoteId OBJECT-TYPE
			SYNTAX OCTET STRING (SIZE (1..64))
			MAX-ACCESS read-only
			STATUS current
			DESCRIPTION
				"Description."
			::= { fkV2Dhcp4RemoteEntry 1 }

		
		-- 1.3.6.1.4.1.10428 9 1.102.6.2.3.2.1.1.1.2
		fkV2Dhcp4RemoteType OBJECT-TYPE
			SYNTAX INTEGER
				{
				ipaddress(1),
				hex(2),
				text(3),
				index(5)
				}
			MAX-ACCESS read-only
			STATUS current
			DESCRIPTION
				"Description."
			::= { fkV2Dhcp4RemoteEntry 2 }

		
		-- 1.3.6.1.4.1.10428 9 1.102.6.2.3.2.1.1.1.3
		fkV2Dhcp4RemoteClass OBJECT-TYPE
			SYNTAX OCTET STRING (SIZE (0 | 1..32))
			MAX-ACCESS read-only
			STATUS current
			DESCRIPTION
				"Description."
			::= { fkV2Dhcp4RemoteEntry 3 }

		
		-- 1.3.6.1.4.1.10428 9 1.102.6.2.3.2.1.1.1.4
		fkV2Dhcp4RemoteTrust OBJECT-TYPE
			SYNTAX Boolean
			MAX-ACCESS read-only
			STATUS current
			DESCRIPTION
				"The Information that is whether this remote is trusted or not."
			::= { fkV2Dhcp4RemoteEntry 4 }

		
		-- 1.3.6.1.4.1.10428 9 1.102.6.2.3.2.1.1.1.5
		fkV2Dhcp4RemoteLeaseLimit OBJECT-TYPE
			SYNTAX INTEGER (1..2147483637)
			MAX-ACCESS read-only
			STATUS current
			DESCRIPTION
				"Description."
			::= { fkV2Dhcp4RemoteEntry 5 }

		
		-- 1.3.6.1.4.1.10428 9 1.102.6.2.3.2.1.1.1.6
		fkV2Dhcp4RemoteLeaseCnt OBJECT-TYPE
			SYNTAX INTEGER (1..2147483637)
			MAX-ACCESS read-only
			STATUS current
			DESCRIPTION
				"Description."
			::= { fkV2Dhcp4RemoteEntry 6 }

		
		-- 1.3.6.1.4.1.10428 9 1.102.6.2.3.2.1.2
		fkV2Dhcp4RemoteControl OBJECT IDENTIFIER ::= { fkV2Dhcp4Remote 2 }

		
		-- 1.3.6.1.4.1.10428 9 1.102.6.2.3.2.1.2.1
		fkV2Dhcp4RemoteControlRequest OBJECT-TYPE
			SYNTAX INTEGER
				{
				createDhcpRemote(1),
				destroyDhcpRemote(2),
				setDhcpRemote(3),
				clearDhcpRemotes(4)
				}
			MAX-ACCESS read-write
			STATUS current
			DESCRIPTION
				"The request of a user command."
			::= { fkV2Dhcp4RemoteControl 1 }

		
		-- 1.3.6.1.4.1.10428 9 1.102.6.2.3.2.1.2.2
		fkV2Dhcp4RemoteControlStatus OBJECT-TYPE
			SYNTAX FkControlStatusType
			MAX-ACCESS read-only
			STATUS current
			DESCRIPTION
				"The status of a user command."
			::= { fkV2Dhcp4RemoteControl 2 }

		
		-- 1.3.6.1.4.1.10428 9 1.102.6.2.3.2.1.2.3
		fkV2Dhcp4RemoteControlTimer OBJECT-TYPE
			SYNTAX Gauge32
			MAX-ACCESS read-write
			STATUS current
			DESCRIPTION
				"The maximum wait Time for the manager for a long running user command."
			::= { fkV2Dhcp4RemoteControl 3 }

		
		-- 1.3.6.1.4.1.10428 9 1.102.6.2.3.2.1.2.4
		fkV2Dhcp4RemoteControlTimeStamp OBJECT-TYPE
			SYNTAX TimeTicks
			MAX-ACCESS read-only
			STATUS current
			DESCRIPTION
				"The Time stamp of the last command (end of command)."
			::= { fkV2Dhcp4RemoteControl 4 }

		
		-- 1.3.6.1.4.1.10428 9 1.102.6.2.3.2.1.2.5
		fkV2Dhcp4RemoteControlReqResult OBJECT-TYPE
			SYNTAX FkControlRequestResultType
			MAX-ACCESS read-only
			STATUS current
			DESCRIPTION
				"The result of the last user command."
			::= { fkV2Dhcp4RemoteControl 5 }

		
		-- 1.3.6.1.4.1.10428 9 1.102.6.2.3.2.1.2.6
		fkV2Dhcp4RemoteControlId OBJECT-TYPE
			SYNTAX OCTET STRING (SIZE (1..64))
			MAX-ACCESS read-write
			STATUS current
			DESCRIPTION
				"Description."
			::= { fkV2Dhcp4RemoteControl 6 }

		
		-- 1.3.6.1.4.1.10428 9 1.102.6.2.3.2.1.2.7
		fkV2Dhcp4RemoteControlType OBJECT-TYPE
			SYNTAX INTEGER
				{
				ipaddress(1),
				hex(2),
				text(3),
				index(5)
				}
			MAX-ACCESS read-write
			STATUS current
			DESCRIPTION
				"Description."
			::= { fkV2Dhcp4RemoteControl 7 }

		
		-- 1.3.6.1.4.1.10428 9 1.102.6.2.3.2.1.2.8
		fkV2Dhcp4RemoteControlClass OBJECT-TYPE
			SYNTAX OCTET STRING (SIZE (0 | 1..32))
			MAX-ACCESS read-write
			STATUS current
			DESCRIPTION
				"Description."
			::= { fkV2Dhcp4RemoteControl 8 }

		
		-- 1.3.6.1.4.1.10428 9 1.102.6.2.3.2.1.2.9
		fkV2Dhcp4RemoteControlTrust OBJECT-TYPE
			SYNTAX Boolean
			MAX-ACCESS read-write
			STATUS current
			DESCRIPTION
				"Description."
			::= { fkV2Dhcp4RemoteControl 9 }

		
		-- 1.3.6.1.4.1.10428 9 1.102.6.2.3.2.1.2.10
		fkV4Dhcp4RemoteControlLeaseLimit OBJECT-TYPE
			SYNTAX INTEGER (1..2147483637)
			MAX-ACCESS read-write
			STATUS current
			DESCRIPTION
				"Description."
			::= { fkV2Dhcp4RemoteControl 10 }

		
		-- 1.3.6.1.4.1.10428 9 1.102.6.2.3.2.1.3
		fkV2Dhcp4RemoteNotification OBJECT IDENTIFIER ::= { fkV2Dhcp4Remote 3 }

		
		-- 1.3.6.1.4.1.10428 9 1.102.6.2.3.2.1.3.1
		fkV2Dhcp4RemoteCreated NOTIFICATION-TYPE
			OBJECTS { fkV2Dhcp4RemoteControlRequest, fkV2Dhcp4RemoteControlTimeStamp, fkV4Dhcp4RemoteControlLeaseLimit, fkV2Dhcp4RemoteControlReqResult, fkV2Dhcp4RemoteType, 
				fkV2Dhcp4RemoteClass, fkV2Dhcp4RemoteTrust }
			STATUS current
			DESCRIPTION 
				"Description."
			::= { fkV2Dhcp4RemoteNotification 1 }

		
		-- 1.3.6.1.4.1.10428 9 1.102.6.2.3.2.1.3.2
		fkV2Dhcp4RemoteDestroyed NOTIFICATION-TYPE
			OBJECTS { fkV2Dhcp4RemoteControlRequest, fkV2Dhcp4RemoteControlTimeStamp, fkV2Dhcp4RemoteControlReqResult, fkV2Dhcp4RemoteControlId }
			STATUS current
			DESCRIPTION 
				"Description."
			::= { fkV2Dhcp4RemoteNotification 2 }

		
		-- 1.3.6.1.4.1.10428 9 1.102.6.2.3.2.1.3.3
		fkV2Dhcp4RemoteChanged NOTIFICATION-TYPE
			OBJECTS { fkV2Dhcp4RemoteControlRequest, fkV2Dhcp4RemoteControlTimeStamp, fkV4Dhcp4RemoteControlLeaseLimit, fkV2Dhcp4RemoteControlReqResult, fkV2Dhcp4RemoteClass, 
				fkV2Dhcp4RemoteTrust }
			STATUS current
			DESCRIPTION 
				"Description."
			::= { fkV2Dhcp4RemoteNotification 3 }

		
		-- 1.3.6.1.4.1.10428 9 1.102.6.2.3.2.1.3.4
		fkV2Dhcp4RemoteCleared NOTIFICATION-TYPE
			OBJECTS { fkV2Dhcp4RemoteControlRequest, fkV2Dhcp4RemoteControlTimeStamp, fkV2Dhcp4RemoteControlReqResult }
			STATUS current
			DESCRIPTION 
				"Description."
			::= { fkV2Dhcp4RemoteNotification 4 }

		
		-- 1.3.6.1.4.1.10428 9 1.102.6.2.3.2.2
		fkV2Dhcp4RCircuit OBJECT IDENTIFIER ::= { fkV2Dhcp4RelayInfo 2 }

		
		-- 1.3.6.1.4.1.10428 9 1.102.6.2.3.2.2.1
		fkV2Dhcp4RCircuitTable OBJECT-TYPE
			SYNTAX SEQUENCE OF FkV2Dhcp4RCircuitEntry
			MAX-ACCESS not-accessible
			STATUS current
			DESCRIPTION
				"Description."
			::= { fkV2Dhcp4RCircuit 1 }

		
		-- 1.3.6.1.4.1.10428 9 1.102.6.2.3.2.2.1.1
		fkV2Dhcp4RCircuitEntry OBJECT-TYPE
			SYNTAX FkV2Dhcp4RCircuitEntry
			MAX-ACCESS not-accessible
			STATUS current
			DESCRIPTION
				"Description."
			INDEX { fkV2Dhcp4RemoteId, fkV2Dhcp4RCircuitId }
			::= { fkV2Dhcp4RCircuitTable 1 }

		
		FkV2Dhcp4RCircuitEntry ::=
			SEQUENCE { 
				fkV2Dhcp4RCircuitId
					OCTET STRING,
				fkV2Dhcp4RCircuitType
					INTEGER,
				fkV2Dhcp4RCircuitClass
					OCTET STRING,
				fkV2Dhcp4RCircuitLeaseLimit
					INTEGER,
				fkV2Dhcp4RCircuitLeaseCnt
					INTEGER
			 }

		-- 1.3.6.1.4.1.10428 9 1.102.6.2.3.2.2.1.1.1
		fkV2Dhcp4RCircuitId OBJECT-TYPE
			SYNTAX OCTET STRING (SIZE (1..32))
			MAX-ACCESS read-only
			STATUS current
			DESCRIPTION
				"Description."
			::= { fkV2Dhcp4RCircuitEntry 1 }

		
		-- 1.3.6.1.4.1.10428 9 1.102.6.2.3.2.2.1.1.2
		fkV2Dhcp4RCircuitType OBJECT-TYPE
			SYNTAX INTEGER
				{
				index(1),
				hex(2),
				text(3)
				}
			MAX-ACCESS read-only
			STATUS current
			DESCRIPTION
				"Description."
			::= { fkV2Dhcp4RCircuitEntry 2 }

		
		-- 1.3.6.1.4.1.10428 9 1.102.6.2.3.2.2.1.1.3
		fkV2Dhcp4RCircuitClass OBJECT-TYPE
			SYNTAX OCTET STRING (SIZE (1..32))
			MAX-ACCESS read-only
			STATUS current
			DESCRIPTION
				"Description."
			::= { fkV2Dhcp4RCircuitEntry 3 }

		
		-- 1.3.6.1.4.1.10428 9 1.102.6.2.3.2.2.1.1.4
		fkV2Dhcp4RCircuitLeaseLimit OBJECT-TYPE
			SYNTAX INTEGER (1..2147483637)
			MAX-ACCESS read-only
			STATUS current
			DESCRIPTION
				"Description."
			::= { fkV2Dhcp4RCircuitEntry 4 }

		
		-- 1.3.6.1.4.1.10428 9 1.102.6.2.3.2.2.1.1.5
		fkV2Dhcp4RCircuitLeaseCnt OBJECT-TYPE
			SYNTAX INTEGER (1..2147483637)
			MAX-ACCESS read-only
			STATUS current
			DESCRIPTION
				"Description."
			::= { fkV2Dhcp4RCircuitEntry 5 }

		
		-- 1.3.6.1.4.1.10428 9 1.102.6.2.3.2.2.2
		fkV2Dhcp4RCircuitControl OBJECT IDENTIFIER ::= { fkV2Dhcp4RCircuit 2 }

		
		-- 1.3.6.1.4.1.10428 9 1.102.6.2.3.2.2.2.1
		fkV2Dhcp4RCircuitControlRequest OBJECT-TYPE
			SYNTAX INTEGER
				{
				createDhcpRemoteCircuit(1),
				destroyDhcpRemoteCircuit(2),
				clearDhcpRemoteCircuits(3),
				setDhcpRemoteCircuit(4)
				}
			MAX-ACCESS read-write
			STATUS current
			DESCRIPTION
				"The request of a user command."
			::= { fkV2Dhcp4RCircuitControl 1 }

		
		-- 1.3.6.1.4.1.10428 9 1.102.6.2.3.2.2.2.2
		fkV2Dhcp4RCircuitControlStatus OBJECT-TYPE
			SYNTAX FkControlStatusType
			MAX-ACCESS read-only
			STATUS current
			DESCRIPTION
				"The status of a user command."
			::= { fkV2Dhcp4RCircuitControl 2 }

		
		-- 1.3.6.1.4.1.10428 9 1.102.6.2.3.2.2.2.3
		fkV2Dhcp4RCircuitControlTimer OBJECT-TYPE
			SYNTAX Gauge32
			MAX-ACCESS read-write
			STATUS current
			DESCRIPTION
				"The maximum wait Time for the manager for a long running user command."
			::= { fkV2Dhcp4RCircuitControl 3 }

		
		-- 1.3.6.1.4.1.10428 9 1.102.6.2.3.2.2.2.4
		fkV2Dhcp4RCircuitControlTimeStamp OBJECT-TYPE
			SYNTAX TimeTicks
			MAX-ACCESS read-only
			STATUS current
			DESCRIPTION
				"The Time stamp of the last command (end of command)."
			::= { fkV2Dhcp4RCircuitControl 4 }

		
		-- 1.3.6.1.4.1.10428 9 1.102.6.2.3.2.2.2.5
		fkV2Dhcp4RCircuitControlReqResult OBJECT-TYPE
			SYNTAX FkControlRequestResultType
			MAX-ACCESS read-only
			STATUS current
			DESCRIPTION
				"The result of the last user command."
			::= { fkV2Dhcp4RCircuitControl 5 }

		
		-- 1.3.6.1.4.1.10428 9 1.102.6.2.3.2.2.2.6
		fkV2Dhcp4RCircuitControlRemote OBJECT-TYPE
			SYNTAX OCTET STRING (SIZE (1..32))
			MAX-ACCESS read-write
			STATUS current
			DESCRIPTION
				"Description."
			::= { fkV2Dhcp4RCircuitControl 6 }

		
		-- 1.3.6.1.4.1.10428 9 1.102.6.2.3.2.2.2.7
		fkV2Dhcp4RCircuitControlId OBJECT-TYPE
			SYNTAX OCTET STRING (SIZE (1..32))
			MAX-ACCESS read-write
			STATUS current
			DESCRIPTION
				"Description."
			::= { fkV2Dhcp4RCircuitControl 7 }

		
		-- 1.3.6.1.4.1.10428 9 1.102.6.2.3.2.2.2.8
		fkV2Dhcp4RCircuitControlType OBJECT-TYPE
			SYNTAX INTEGER
				{
				index(1),
				hex(2),
				text(3)
				}
			MAX-ACCESS read-write
			STATUS current
			DESCRIPTION
				"Description."
			::= { fkV2Dhcp4RCircuitControl 8 }

		
		-- 1.3.6.1.4.1.10428 9 1.102.6.2.3.2.2.2.9
		fkV2Dhcp4RCircuitControlClass OBJECT-TYPE
			SYNTAX OCTET STRING (SIZE (1..32))
			MAX-ACCESS read-write
			STATUS current
			DESCRIPTION
				"Description."
			::= { fkV2Dhcp4RCircuitControl 9 }

		
		-- 1.3.6.1.4.1.10428 9 1.102.6.2.3.2.2.2.10
		fkV2Dhcp4RCircuitControlLeaseLimit OBJECT-TYPE
			SYNTAX INTEGER (1..2147483637)
			MAX-ACCESS read-write
			STATUS current
			DESCRIPTION
				"Description."
			::= { fkV2Dhcp4RCircuitControl 10 }

		
		-- 1.3.6.1.4.1.10428 9 1.102.6.2.3.2.2.3
		fkV2Dhcp4RCircuitNotification OBJECT IDENTIFIER ::= { fkV2Dhcp4RCircuit 3 }

		
		-- 1.3.6.1.4.1.10428 9 1.102.6.2.3.2.2.3.1
		fkV2Dhcp4RCircuitCreated NOTIFICATION-TYPE
			OBJECTS { fkV2Dhcp4RCircuitControlRequest, fkV2Dhcp4RCircuitControlTimeStamp, fkV2Dhcp4RCircuitLeaseLimit, fkV2Dhcp4RCircuitControlReqResult, fkV2Dhcp4RCircuitType, 
				fkV2Dhcp4RCircuitClass }
			STATUS current
			DESCRIPTION 
				"Description."
			::= { fkV2Dhcp4RCircuitNotification 1 }

		
		-- 1.3.6.1.4.1.10428 9 1.102.6.2.3.2.2.3.2
		fkV2Dhcp4RCircuitDestroyed NOTIFICATION-TYPE
			OBJECTS { fkV2Dhcp4RCircuitControlRequest, fkV2Dhcp4RCircuitControlTimeStamp, fkV2Dhcp4RCircuitControlReqResult, fkV2Dhcp4RCircuitControlRemote, fkV2Dhcp4RCircuitControlId
				 }
			STATUS current
			DESCRIPTION 
				"Description."
			::= { fkV2Dhcp4RCircuitNotification 2 }

		
		-- 1.3.6.1.4.1.10428 9 1.102.6.2.3.2.2.3.3
		fkV2Dhcp4RCircuitCleared NOTIFICATION-TYPE
			OBJECTS { fkV2Dhcp4RCircuitControlRequest, fkV2Dhcp4RCircuitControlTimeStamp, fkV2Dhcp4RCircuitControlReqResult, fkV2Dhcp4RCircuitControlRemote }
			STATUS current
			DESCRIPTION 
				"Description."
			::= { fkV2Dhcp4RCircuitNotification 3 }

		
		-- 1.3.6.1.4.1.10428 9 1.102.6.2.3.2.2.3.4
		fkV2Dhcp4RCircuitChanged NOTIFICATION-TYPE
			OBJECTS { fkV2Dhcp4RCircuitControlRequest, fkV2Dhcp4RCircuitControlTimeStamp, fkV2Dhcp4RCircuitControlReqResult, fkV2Dhcp4RCircuitControlRemote, fkV2Dhcp4RCircuitLeaseLimit
				 }
			STATUS current
			DESCRIPTION 
				"Description."
			::= { fkV2Dhcp4RCircuitNotification 4 }

		
		-- 1.3.6.1.4.1.10428 9 1.102.6.2.3.3
		fkV2Dhcp4Class OBJECT IDENTIFIER ::= { fkV2Dhcp4Option82 3 }

		
		-- 1.3.6.1.4.1.10428 9 1.102.6.2.3.3.1
		fkV2Dhcp4ClassBase OBJECT IDENTIFIER ::= { fkV2Dhcp4Class 1 }

		
		-- 1.3.6.1.4.1.10428 9 1.102.6.2.3.3.1.1
		fkV2Dhcp4ClassTable OBJECT-TYPE
			SYNTAX SEQUENCE OF FkV2Dhcp4ClassEntry
			MAX-ACCESS not-accessible
			STATUS current
			DESCRIPTION
				"Description."
			::= { fkV2Dhcp4ClassBase 1 }

		
		-- 1.3.6.1.4.1.10428 9 1.102.6.2.3.3.1.1.1
		fkV2Dhcp4ClassEntry OBJECT-TYPE
			SYNTAX FkV2Dhcp4ClassEntry
			MAX-ACCESS not-accessible
			STATUS current
			DESCRIPTION
				"Description."
			INDEX { fkV2Dhcp4ClassName }
			::= { fkV2Dhcp4ClassTable 1 }

		
		FkV2Dhcp4ClassEntry ::=
			SEQUENCE { 
				fkV2Dhcp4ClassName
					OCTET STRING
			 }

		-- 1.3.6.1.4.1.10428 9 1.102.6.2.3.3.1.1.1.1
		fkV2Dhcp4ClassName OBJECT-TYPE
			SYNTAX OCTET STRING (SIZE (1..32))
			MAX-ACCESS read-only
			STATUS current
			DESCRIPTION
				"Description."
			::= { fkV2Dhcp4ClassEntry 1 }

		
		-- 1.3.6.1.4.1.10428 9 1.102.6.2.3.3.1.2
		fkV2Dhcp4ClassControl OBJECT IDENTIFIER ::= { fkV2Dhcp4ClassBase 2 }

		
		-- 1.3.6.1.4.1.10428 9 1.102.6.2.3.3.1.2.1
		fkV2Dhcp4ClassControlRequest OBJECT-TYPE
			SYNTAX INTEGER
				{
				createDhcpClass(1),
				destroyDhcpClass(2)
				}
			MAX-ACCESS read-write
			STATUS current
			DESCRIPTION
				"Description."
			::= { fkV2Dhcp4ClassControl 1 }

		
		-- 1.3.6.1.4.1.10428 9 1.102.6.2.3.3.1.2.2
		fkV2Dhcp4ClassControlStatus OBJECT-TYPE
			SYNTAX FkControlStatusType
			MAX-ACCESS read-only
			STATUS current
			DESCRIPTION
				"Description."
			::= { fkV2Dhcp4ClassControl 2 }

		
		-- 1.3.6.1.4.1.10428 9 1.102.6.2.3.3.1.2.3
		fkV2Dhcp4ClassControlTimer OBJECT-TYPE
			SYNTAX Gauge32
			MAX-ACCESS read-write
			STATUS current
			DESCRIPTION
				"Description."
			::= { fkV2Dhcp4ClassControl 3 }

		
		-- 1.3.6.1.4.1.10428 9 1.102.6.2.3.3.1.2.4
		fkV2Dhcp4ClassControlTimeStamp OBJECT-TYPE
			SYNTAX TimeTicks
			MAX-ACCESS read-only
			STATUS current
			DESCRIPTION
				"Description."
			::= { fkV2Dhcp4ClassControl 4 }

		
		-- 1.3.6.1.4.1.10428 9 1.102.6.2.3.3.1.2.5
		fkV2Dhcp4ClassControlReqResult OBJECT-TYPE
			SYNTAX FkControlRequestResultType
			MAX-ACCESS read-only
			STATUS current
			DESCRIPTION
				"Description."
			::= { fkV2Dhcp4ClassControl 5 }

		
		-- 1.3.6.1.4.1.10428 9 1.102.6.2.3.3.1.2.6
		fkV2Dhcp4ClassControlName OBJECT-TYPE
			SYNTAX OCTET STRING (SIZE (1..32))
			MAX-ACCESS read-write
			STATUS current
			DESCRIPTION
				"Description."
			::= { fkV2Dhcp4ClassControl 6 }

		
		-- 1.3.6.1.4.1.10428 9 1.102.6.2.3.3.1.3
		fkV2Dhcp4ClassNotification OBJECT IDENTIFIER ::= { fkV2Dhcp4ClassBase 3 }

		
		-- 1.3.6.1.4.1.10428 9 1.102.6.2.3.3.1.3.1
		fkV2Dhcp4ClassCreated NOTIFICATION-TYPE
			OBJECTS { fkV2Dhcp4ClassControlRequest, fkV2Dhcp4ClassControlTimeStamp, fkV2Dhcp4ClassControlReqResult, fkV2Dhcp4ClassControlName }
			STATUS current
			DESCRIPTION 
				"Description."
			::= { fkV2Dhcp4ClassNotification 1 }

		
		-- 1.3.6.1.4.1.10428 9 1.102.6.2.3.3.1.3.2
		fkV2Dhcp4ClassDestroyed NOTIFICATION-TYPE
			OBJECTS { fkV2Dhcp4ClassControlRequest, fkV2Dhcp4ClassControlTimeStamp, fkV2Dhcp4ClassControlReqResult, fkV2Dhcp4ClassControlName }
			STATUS current
			DESCRIPTION 
				"Description."
			::= { fkV2Dhcp4ClassNotification 2 }

		
		-- 1.3.6.1.4.1.10428 9 1.102.6.2.3.3.2
		fkV2Dhcp4CRCMap OBJECT IDENTIFIER ::= { fkV2Dhcp4Class 2 }

		
		-- 1.3.6.1.4.1.10428 9 1.102.6.2.3.3.2.1
		fkV2Dhcp4CRCMapTable OBJECT-TYPE
			SYNTAX SEQUENCE OF FkV2Dhcp4CRCMapEntry
			MAX-ACCESS not-accessible
			STATUS current
			DESCRIPTION
				"Description."
			::= { fkV2Dhcp4CRCMap 1 }

		
		-- 1.3.6.1.4.1.10428 9 1.102.6.2.3.3.2.1.1
		fkV2Dhcp4CRCMapEntry OBJECT-TYPE
			SYNTAX FkV2Dhcp4CRCMapEntry
			MAX-ACCESS not-accessible
			STATUS current
			DESCRIPTION
				"Description."
			INDEX { fkV2Dhcp4CRCMapClass, fkV2Dhcp4CRCMapRemote, fkV2Dhcp4CRCMapCircuit }
			::= { fkV2Dhcp4CRCMapTable 1 }

		
		FkV2Dhcp4CRCMapEntry ::=
			SEQUENCE { 
				fkV2Dhcp4CRCMapClass
					OCTET STRING,
				fkV2Dhcp4CRCMapRemote
					OCTET STRING,
				fkV2Dhcp4CRCMapCircuit
					OCTET STRING
			 }

		-- 1.3.6.1.4.1.10428 9 1.102.6.2.3.3.2.1.1.1
		fkV2Dhcp4CRCMapClass OBJECT-TYPE
			SYNTAX OCTET STRING (SIZE (1..32))
			MAX-ACCESS read-only
			STATUS current
			DESCRIPTION
				"Description."
			::= { fkV2Dhcp4CRCMapEntry 1 }

		
		-- 1.3.6.1.4.1.10428 9 1.102.6.2.3.3.2.1.1.2
		fkV2Dhcp4CRCMapRemote OBJECT-TYPE
			SYNTAX OCTET STRING (SIZE (1..64))
			MAX-ACCESS read-only
			STATUS current
			DESCRIPTION
				"Description."
			::= { fkV2Dhcp4CRCMapEntry 2 }

		
		-- 1.3.6.1.4.1.10428 9 1.102.6.2.3.3.2.1.1.3
		fkV2Dhcp4CRCMapCircuit OBJECT-TYPE
			SYNTAX OCTET STRING (SIZE (0 | 1..32))
			MAX-ACCESS read-only
			STATUS current
			DESCRIPTION
				"Description."
			::= { fkV2Dhcp4CRCMapEntry 3 }

		
		-- 1.3.6.1.4.1.10428 9 1.102.6.2.3.3.2.2
		fkV2Dhcp4CRCMapControl OBJECT IDENTIFIER ::= { fkV2Dhcp4CRCMap 2 }

		
		-- 1.3.6.1.4.1.10428 9 1.102.6.2.3.3.2.2.1
		fkV2Dhcp4CRCMapControlRequest OBJECT-TYPE
			SYNTAX INTEGER
				{
				clearDhcpClassMapCircuits(1),
				clearDhcpClassMapRemotes(2)
				}
			MAX-ACCESS read-write
			STATUS current
			DESCRIPTION
				"The request of a user command."
			::= { fkV2Dhcp4CRCMapControl 1 }

		
		-- 1.3.6.1.4.1.10428 9 1.102.6.2.3.3.2.2.2
		fkV2Dhcp4CRCMapControlStatus OBJECT-TYPE
			SYNTAX FkControlStatusType
			MAX-ACCESS read-only
			STATUS current
			DESCRIPTION
				"The status of a user command."
			::= { fkV2Dhcp4CRCMapControl 2 }

		
		-- 1.3.6.1.4.1.10428 9 1.102.6.2.3.3.2.2.3
		fkV2Dhcp4CRCMapControlTimer OBJECT-TYPE
			SYNTAX Gauge32
			MAX-ACCESS read-write
			STATUS current
			DESCRIPTION
				"The maximum wait Time for the manager for a long running user command."
			::= { fkV2Dhcp4CRCMapControl 3 }

		
		-- 1.3.6.1.4.1.10428 9 1.102.6.2.3.3.2.2.4
		fkV2Dhcp4CRCMapControlTimeStamp OBJECT-TYPE
			SYNTAX TimeTicks
			MAX-ACCESS read-only
			STATUS current
			DESCRIPTION
				"The Time stamp of the last command (end of command)."
			::= { fkV2Dhcp4CRCMapControl 4 }

		
		-- 1.3.6.1.4.1.10428 9 1.102.6.2.3.3.2.2.5
		fkV2Dhcp4CRCMapControlReqResult OBJECT-TYPE
			SYNTAX FkControlRequestResultType
			MAX-ACCESS read-only
			STATUS current
			DESCRIPTION
				"The result of the last user command."
			::= { fkV2Dhcp4CRCMapControl 5 }

		
		-- 1.3.6.1.4.1.10428 9 1.102.6.2.3.3.2.2.6
		fkV2Dhcp4CRCMapControlClass OBJECT-TYPE
			SYNTAX OCTET STRING (SIZE (1..32))
			MAX-ACCESS read-write
			STATUS current
			DESCRIPTION
				"Description."
			::= { fkV2Dhcp4CRCMapControl 6 }

		
		-- 1.3.6.1.4.1.10428 9 1.102.6.2.3.3.2.2.7
		fkV2Dhcp4CRCMapControlRemote OBJECT-TYPE
			SYNTAX OCTET STRING (SIZE (1..32))
			MAX-ACCESS read-write
			STATUS current
			DESCRIPTION
				"Description."
			::= { fkV2Dhcp4CRCMapControl 7 }

		
		-- 1.3.6.1.4.1.10428 9 1.102.6.2.3.3.2.3
		fkV2Dhcp4CRCMapNotification OBJECT IDENTIFIER ::= { fkV2Dhcp4CRCMap 3 }

		
		-- 1.3.6.1.4.1.10428 9 1.102.6.2.3.3.2.3.1
		fkV2Dhcp4CRCMapCircuitCleared NOTIFICATION-TYPE
			OBJECTS { fkV2Dhcp4CRCMapControlRequest, fkV2Dhcp4CRCMapControlTimeStamp, fkV2Dhcp4CRCMapControlReqResult, fkV2Dhcp4CRCMapControlClass, fkV2Dhcp4CRCMapControlRemote
				 }
			STATUS current
			DESCRIPTION 
				"Description."
			::= { fkV2Dhcp4CRCMapNotification 1 }

		
		-- 1.3.6.1.4.1.10428 9 1.102.6.2.3.3.2.3.2
		fkV2Dhcp4CRCMapRemoteCleared NOTIFICATION-TYPE
			OBJECTS { fkV2Dhcp4CRCMapControlRequest, fkV2Dhcp4CRCMapControlTimeStamp, fkV2Dhcp4CRCMapControlReqResult, fkV2Dhcp4CRCMapControlClass }
			STATUS current
			DESCRIPTION 
				"Description."
			::= { fkV2Dhcp4CRCMapNotification 2 }

		
		-- 1.3.6.1.4.1.10428 9 1.102.6.2.3.3.3
		fkV2Dhcp4ClassRange OBJECT IDENTIFIER ::= { fkV2Dhcp4Class 3 }

		
		-- 1.3.6.1.4.1.10428 9 1.102.6.2.3.3.3.1
		fkV2Dhcp4ClassRangeTable OBJECT-TYPE
			SYNTAX SEQUENCE OF FkV2Dhcp4ClassRangeEntry
			MAX-ACCESS not-accessible
			STATUS current
			DESCRIPTION
				"Description."
			::= { fkV2Dhcp4ClassRange 1 }

		
		-- 1.3.6.1.4.1.10428 9 1.102.6.2.3.3.3.1.1
		fkV2Dhcp4ClassRangeEntry OBJECT-TYPE
			SYNTAX FkV2Dhcp4ClassRangeEntry
			MAX-ACCESS not-accessible
			STATUS current
			DESCRIPTION
				"Description."
			INDEX { fkV2Dhcp4PoolIndex, fkV2Dhcp4ClassName, fkV2Dhcp4ClassRangeStart, fkV2Dhcp4ClassRangeEnd }
			::= { fkV2Dhcp4ClassRangeTable 1 }

		
		FkV2Dhcp4ClassRangeEntry ::=
			SEQUENCE { 
				fkV2Dhcp4ClassRangeStart
					IpAddress,
				fkV2Dhcp4ClassRangeEnd
					IpAddress
			 }

		-- 1.3.6.1.4.1.10428 9 1.102.6.2.3.3.3.1.1.1
		fkV2Dhcp4ClassRangeStart OBJECT-TYPE
			SYNTAX IpAddress
			MAX-ACCESS read-only
			STATUS current
			DESCRIPTION
				"Description."
			::= { fkV2Dhcp4ClassRangeEntry 1 }

		
		-- 1.3.6.1.4.1.10428 9 1.102.6.2.3.3.3.1.1.2
		fkV2Dhcp4ClassRangeEnd OBJECT-TYPE
			SYNTAX IpAddress
			MAX-ACCESS read-only
			STATUS current
			DESCRIPTION
				"Description."
			::= { fkV2Dhcp4ClassRangeEntry 2 }

		
		-- 1.3.6.1.4.1.10428 9 1.102.6.2.3.3.3.2
		fkV2Dhcp4ClassRangeControl OBJECT IDENTIFIER ::= { fkV2Dhcp4ClassRange 2 }

		
		-- 1.3.6.1.4.1.10428 9 1.102.6.2.3.3.3.2.1
		fkV2Dhcp4ClassRangeControlRequest OBJECT-TYPE
			SYNTAX INTEGER
				{
				createDhcpClassRange(1),
				destoryDhcpClassRange(2)
				}
			MAX-ACCESS read-write
			STATUS current
			DESCRIPTION
				"The request of a user command."
			::= { fkV2Dhcp4ClassRangeControl 1 }

		
		-- 1.3.6.1.4.1.10428 9 1.102.6.2.3.3.3.2.2
		fkV2Dhcp4ClassRangeControlStatus OBJECT-TYPE
			SYNTAX FkControlStatusType
			MAX-ACCESS read-only
			STATUS current
			DESCRIPTION
				"The status of a user command."
			::= { fkV2Dhcp4ClassRangeControl 2 }

		
		-- 1.3.6.1.4.1.10428 9 1.102.6.2.3.3.3.2.3
		fkV2Dhcp4ClassRangeControlTimer OBJECT-TYPE
			SYNTAX Gauge32
			MAX-ACCESS read-write
			STATUS current
			DESCRIPTION
				"The maximum wait Time for the manager for a long running user command."
			::= { fkV2Dhcp4ClassRangeControl 3 }

		
		-- 1.3.6.1.4.1.10428 9 1.102.6.2.3.3.3.2.4
		fkV2Dhcp4ClassRangeControlTimeStamp OBJECT-TYPE
			SYNTAX TimeTicks
			MAX-ACCESS read-only
			STATUS current
			DESCRIPTION
				"The Time stamp of the last command (end of command)."
			::= { fkV2Dhcp4ClassRangeControl 4 }

		
		-- 1.3.6.1.4.1.10428 9 1.102.6.2.3.3.3.2.5
		fkV2Dhcp4ClassRangeControlReqResult OBJECT-TYPE
			SYNTAX FkControlRequestResultType
			MAX-ACCESS read-only
			STATUS current
			DESCRIPTION
				"The result of the last user command."
			::= { fkV2Dhcp4ClassRangeControl 5 }

		
		-- 1.3.6.1.4.1.10428 9 1.102.6.2.3.3.3.2.6
		fkV2Dhcp4ClassRangeControlPoolIndex OBJECT-TYPE
			SYNTAX INTEGER (1..255)
			MAX-ACCESS read-write
			STATUS current
			DESCRIPTION
				"Description."
			::= { fkV2Dhcp4ClassRangeControl 6 }

		
		-- 1.3.6.1.4.1.10428 9 1.102.6.2.3.3.3.2.7
		fkV2Dhcp4ClassRangeControlName OBJECT-TYPE
			SYNTAX OCTET STRING (SIZE (1..32))
			MAX-ACCESS read-write
			STATUS current
			DESCRIPTION
				"Description."
			::= { fkV2Dhcp4ClassRangeControl 7 }

		
		-- 1.3.6.1.4.1.10428 9 1.102.6.2.3.3.3.2.8
		fkV2Dhcp4ClassRangeControlStart OBJECT-TYPE
			SYNTAX IpAddress
			MAX-ACCESS read-write
			STATUS current
			DESCRIPTION
				"Description."
			::= { fkV2Dhcp4ClassRangeControl 8 }

		
		-- 1.3.6.1.4.1.10428 9 1.102.6.2.3.3.3.2.9
		fkV2Dhcp4ClassRangeControlEnd OBJECT-TYPE
			SYNTAX IpAddress
			MAX-ACCESS read-write
			STATUS current
			DESCRIPTION
				"Description."
			::= { fkV2Dhcp4ClassRangeControl 9 }

		
		-- 1.3.6.1.4.1.10428 9 1.102.6.2.3.3.3.3
		fkV2Dhcp4ClassRangeNotification OBJECT IDENTIFIER ::= { fkV2Dhcp4ClassRange 3 }

		
		-- 1.3.6.1.4.1.10428 9 1.102.6.2.3.3.3.3.1
		fkV2Dhcp4ClassRangeCreated NOTIFICATION-TYPE
			OBJECTS { fkV2Dhcp4ClassRangeControlRequest, fkV2Dhcp4ClassRangeControlTimeStamp, fkV2Dhcp4ClassRangeControlReqResult, fkV2Dhcp4ClassRangeControlPoolIndex, fkV2Dhcp4ClassRangeControlName, 
				fkV2Dhcp4ClassRangeControlStart, fkV2Dhcp4ClassRangeControlEnd }
			STATUS current
			DESCRIPTION 
				"Description."
			::= { fkV2Dhcp4ClassRangeNotification 1 }

		
		-- 1.3.6.1.4.1.10428 9 1.102.6.2.3.3.3.3.2
		fkV2Dhcp4ClassRangeDestroyed NOTIFICATION-TYPE
			OBJECTS { fkV2Dhcp4ClassRangeControlRequest, fkV2Dhcp4ClassRangeControlTimeStamp, fkV2Dhcp4ClassRangeControlReqResult, fkV2Dhcp4ClassRangeControlPoolIndex, fkV2Dhcp4ClassRangeControlName, 
				fkV2Dhcp4ClassRangeControlStart, fkV2Dhcp4ClassRangeControlEnd }
			STATUS current
			DESCRIPTION 
				"Description."
			::= { fkV2Dhcp4ClassRangeNotification 2 }

		
		-- 1.3.6.1.4.1.10428 9 1.102.6.2.3.4
		fkV2Dhcp4OptionFormat OBJECT IDENTIFIER ::= { fkV2Dhcp4Option82 4 }

		
		-- 1.3.6.1.4.1.10428 9 1.102.6.2.3.4.1
		fkV2Dhcp4OptionFormatBase OBJECT IDENTIFIER ::= { fkV2Dhcp4OptionFormat 1 }

		
		-- 1.3.6.1.4.1.10428 9 1.102.6.2.3.4.1.1
		fkV2Dhcp4OptionFormatTable OBJECT-TYPE
			SYNTAX SEQUENCE OF FkV2Dhcp4OptionFormatEntry
			MAX-ACCESS not-accessible
			STATUS current
			DESCRIPTION
				"Description."
			::= { fkV2Dhcp4OptionFormatBase 1 }

		
		-- 1.3.6.1.4.1.10428 9 1.102.6.2.3.4.1.1.1
		fkV2Dhcp4OptionFormatEntry OBJECT-TYPE
			SYNTAX FkV2Dhcp4OptionFormatEntry
			MAX-ACCESS not-accessible
			STATUS current
			DESCRIPTION
				"Description."
			INDEX { fkV2Dhcp4OptionFormatName }
			::= { fkV2Dhcp4OptionFormatTable 1 }

		
		FkV2Dhcp4OptionFormatEntry ::=
			SEQUENCE { 
				fkV2Dhcp4OptionFormatName
					OCTET STRING
			 }

		-- 1.3.6.1.4.1.10428 9 1.102.6.2.3.4.1.1.1.1
		fkV2Dhcp4OptionFormatName OBJECT-TYPE
			SYNTAX OCTET STRING (SIZE (1..16))
			MAX-ACCESS read-only
			STATUS current
			DESCRIPTION
				"The name of Option Format"
			::= { fkV2Dhcp4OptionFormatEntry 1 }

		
		-- 1.3.6.1.4.1.10428 9 1.102.6.2.3.4.1.2
		fkV2Dhcp4OptionFormatControl OBJECT IDENTIFIER ::= { fkV2Dhcp4OptionFormatBase 2 }

		
		-- 1.3.6.1.4.1.10428 9 1.102.6.2.3.4.1.2.1
		fkV2Dhcp4OptionFormatControlRequest OBJECT-TYPE
			SYNTAX INTEGER
				{
				createOptionFormat(1),
				destroyOptionFormat(2)
				}
			MAX-ACCESS read-write
			STATUS current
			DESCRIPTION
				"The request of a user command"
			::= { fkV2Dhcp4OptionFormatControl 1 }
-- The request of a user command
		
		-- 1.3.6.1.4.1.10428 9 1.102.6.2.3.4.1.2.2
		fkV2Dhcp4OptionFormatControlStatus OBJECT-TYPE
			SYNTAX FkControlStatusType
			MAX-ACCESS read-only
			STATUS current
			DESCRIPTION
				"The status of user command"
			::= { fkV2Dhcp4OptionFormatControl 2 }

		
		-- 1.3.6.1.4.1.10428 9 1.102.6.2.3.4.1.2.3
		fkV2Dhcp4OptionFormatControlTimer OBJECT-TYPE
			SYNTAX Gauge32
			MAX-ACCESS read-write
			STATUS current
			DESCRIPTION
				"The maximum time for the manager for a long running user command"
			::= { fkV2Dhcp4OptionFormatControl 3 }

		
		-- 1.3.6.1.4.1.10428 9 1.102.6.2.3.4.1.2.4
		fkV2Dhcp4OptionFormatControlTimeStamp OBJECT-TYPE
			SYNTAX TimeTicks
			MAX-ACCESS read-only
			STATUS current
			DESCRIPTION
				"The time stamp of the last command(end of command)"
			::= { fkV2Dhcp4OptionFormatControl 4 }

		
		-- 1.3.6.1.4.1.10428 9 1.102.6.2.3.4.1.2.5
		fkV2Dhcp4OptionFormatControlReqResult OBJECT-TYPE
			SYNTAX FkControlRequestResultType
			MAX-ACCESS read-only
			STATUS current
			DESCRIPTION
				"The result of the last user command"
			::= { fkV2Dhcp4OptionFormatControl 5 }

		
		-- 1.3.6.1.4.1.10428 9 1.102.6.2.3.4.1.2.6
		fkV2Dhcp4OptionFormatControlName OBJECT-TYPE
			SYNTAX OCTET STRING (SIZE (1..32))
			MAX-ACCESS read-write
			STATUS current
			DESCRIPTION
				"The name of Option Format"
			::= { fkV2Dhcp4OptionFormatControl 6 }

		
		-- 1.3.6.1.4.1.10428 9 1.102.6.2.3.4.1.3
		fkV2Dhcp4OptionFormatNotification OBJECT IDENTIFIER ::= { fkV2Dhcp4OptionFormatBase 3 }

		
		-- 1.3.6.1.4.1.10428 9 1.102.6.2.3.4.1.3.1
		fkV2Dhcp4OptionFormatCreated NOTIFICATION-TYPE
			OBJECTS { fkV2Dhcp4OptionFormatControlRequest, fkV2Dhcp4OptionFormatControlName, fkV2Dhcp4OptionFormatControlTimeStamp, fkV2Dhcp4OptionFormatControlReqResult }
			STATUS current
			DESCRIPTION 
				"Description."
			::= { fkV2Dhcp4OptionFormatNotification 1 }

		
		-- 1.3.6.1.4.1.10428 9 1.102.6.2.3.4.1.3.2
		fkV2Dhcp4OptionFormatDestroyed NOTIFICATION-TYPE
			OBJECTS { fkV2Dhcp4OptionFormatControlRequest, fkV2Dhcp4OptionFormatControlName, fkV2Dhcp4OptionFormatControlReqResult, fkV2Dhcp4OptionFormatControlTimeStamp }
			STATUS current
			DESCRIPTION 
				"Description."
			::= { fkV2Dhcp4OptionFormatNotification 2 }

		
		-- 1.3.6.1.4.1.10428 9 1.102.6.2.3.4.2
		fkV2Dhcp4OptionFormatAttribute OBJECT IDENTIFIER ::= { fkV2Dhcp4OptionFormat 2 }

		
		-- 1.3.6.1.4.1.10428 9 1.102.6.2.3.4.2.1
		fkV2Dhcp4OptionFormatAttrTable OBJECT-TYPE
			SYNTAX SEQUENCE OF FkV2Dhcp4OptionFormatAttrEntry
			MAX-ACCESS not-accessible
			STATUS current
			DESCRIPTION
				"Description."
			::= { fkV2Dhcp4OptionFormatAttribute 1 }

		
		-- 1.3.6.1.4.1.10428 9 1.102.6.2.3.4.2.1.1
		fkV2Dhcp4OptionFormatAttrEntry OBJECT-TYPE
			SYNTAX FkV2Dhcp4OptionFormatAttrEntry
			MAX-ACCESS not-accessible
			STATUS current
			DESCRIPTION
				"Description."
			INDEX { fkV2Dhcp4OptionFormatName, fkV2Dhcp4OptionFormatAttrID }
			::= { fkV2Dhcp4OptionFormatAttrTable 1 }

		
		FkV2Dhcp4OptionFormatAttrEntry ::=
			SEQUENCE { 
				fkV2Dhcp4OptionFormatAttrID
					INTEGER,
				fkV2Dhcp4OptionFormatAttrLength
					INTEGER,
				fkV2Dhcp4OptionFormatAttrHiddenLength
					INTEGER,
				fkV2Dhcp4OptionFormatAttrType
					INTEGER,
				fkV2Dhcp4OptionFormatAttrVarType
					INTEGER,
				fkV2Dhcp4OptionFormatAttrVarValue
					OCTET STRING
			 }

		-- 1.3.6.1.4.1.10428 9 1.102.6.2.3.4.2.1.1.1
		fkV2Dhcp4OptionFormatAttrID OBJECT-TYPE
			SYNTAX INTEGER (1..32)
			MAX-ACCESS read-only
			STATUS current
			DESCRIPTION
				"The ID of Option Format Attr"
			::= { fkV2Dhcp4OptionFormatAttrEntry 1 }

		
		-- 1.3.6.1.4.1.10428 9 1.102.6.2.3.4.2.1.1.2
		fkV2Dhcp4OptionFormatAttrLength OBJECT-TYPE
			SYNTAX INTEGER (-1..64)
			MAX-ACCESS read-write
			STATUS current
			DESCRIPTION
				"The Length Field of Option Format Attr.
				The -1 of value means this field is not defined.
				The Zero of value means this field is variable.
				"
			::= { fkV2Dhcp4OptionFormatAttrEntry 2 }

		
		-- 1.3.6.1.4.1.10428 9 1.102.6.2.3.4.2.1.1.3
		fkV2Dhcp4OptionFormatAttrHiddenLength OBJECT-TYPE
			SYNTAX INTEGER (-1..64)
			MAX-ACCESS read-write
			STATUS current
			DESCRIPTION
				"The Hidden Length Field of Option Format Attr.
				The -1 of value means this field is not defined.
				The Zero of value means this field is variable.
				
				"
			::= { fkV2Dhcp4OptionFormatAttrEntry 3 }

		
		-- 1.3.6.1.4.1.10428 9 1.102.6.2.3.4.2.1.1.4
		fkV2Dhcp4OptionFormatAttrType OBJECT-TYPE
			SYNTAX INTEGER (-1..255)
			MAX-ACCESS read-write
			STATUS current
			DESCRIPTION
				"The Hidden Length Field of Option Format Attr.
				The -1 of value means this field is not defined.
				"
			::= { fkV2Dhcp4OptionFormatAttrEntry 4 }

		
		-- 1.3.6.1.4.1.10428 9 1.102.6.2.3.4.2.1.1.5
		fkV2Dhcp4OptionFormatAttrVarType OBJECT-TYPE
			SYNTAX INTEGER
				{
				hex(1),
				ifIp(2),
				index(3),
				ip(4),
				string(5)
				}
			MAX-ACCESS read-only
			STATUS current
			DESCRIPTION
				"The Variable Type Field of Option Format Attr."
			::= { fkV2Dhcp4OptionFormatAttrEntry 5 }

		
		-- 1.3.6.1.4.1.10428 9 1.102.6.2.3.4.2.1.1.6
		fkV2Dhcp4OptionFormatAttrVarValue OBJECT-TYPE
			SYNTAX OCTET STRING (SIZE (1..255))
			MAX-ACCESS read-write
			STATUS current
			DESCRIPTION
				"The Variable Value Field of Option Format Attr.
				"
			::= { fkV2Dhcp4OptionFormatAttrEntry 6 }

		
		-- 1.3.6.1.4.1.10428 9 1.102.6.2.3.4.2.2
		fkV2Dhcp4OptionFormatAttrControl OBJECT IDENTIFIER ::= { fkV2Dhcp4OptionFormatAttribute 2 }

		
		-- 1.3.6.1.4.1.10428 9 1.102.6.2.3.4.2.2.1
		fkV2Dhcp4OptionFormatAttrControlRequest OBJECT-TYPE
			SYNTAX INTEGER
				{
				addOptionFormatAttr(1),
				deleteOptionFormatAttr(2),
				modifyOptionFormatAttr(3)
				}
			MAX-ACCESS read-write
			STATUS current
			DESCRIPTION
				"The request of a user command."
			::= { fkV2Dhcp4OptionFormatAttrControl 1 }

		
		-- 1.3.6.1.4.1.10428 9 1.102.6.2.3.4.2.2.2
		fkV2Dhcp4OptionFormatAttrControlStatus OBJECT-TYPE
			SYNTAX FkControlStatusType
			MAX-ACCESS read-only
			STATUS current
			DESCRIPTION
				"The status of user command."
			::= { fkV2Dhcp4OptionFormatAttrControl 2 }

		
		-- 1.3.6.1.4.1.10428 9 1.102.6.2.3.4.2.2.3
		fkV2Dhcp4OptionFormatAttrControlTimer OBJECT-TYPE
			SYNTAX Gauge32
			MAX-ACCESS read-write
			STATUS current
			DESCRIPTION
				"The maximum time for the manager for a long running user command."
			::= { fkV2Dhcp4OptionFormatAttrControl 3 }

		
		-- 1.3.6.1.4.1.10428 9 1.102.6.2.3.4.2.2.4
		fkV2Dhcp4OptionFormatAttrControlTimeStamp OBJECT-TYPE
			SYNTAX TimeTicks
			MAX-ACCESS read-only
			STATUS current
			DESCRIPTION
				"The time stamp of the last command(end of command)."
			::= { fkV2Dhcp4OptionFormatAttrControl 4 }

		
		-- 1.3.6.1.4.1.10428 9 1.102.6.2.3.4.2.2.5
		fkV2Dhcp4OptionFormatAttrControlReqResult OBJECT-TYPE
			SYNTAX FkControlRequestResultType
			MAX-ACCESS read-only
			STATUS current
			DESCRIPTION
				"The result of the last user command."
			::= { fkV2Dhcp4OptionFormatAttrControl 5 }

		
		-- 1.3.6.1.4.1.10428 9 1.102.6.2.3.4.2.2.6
		fkV2Dhcp4OptionFormatAttrControlName OBJECT-TYPE
			SYNTAX OCTET STRING (SIZE (1..16))
			MAX-ACCESS read-write
			STATUS current
			DESCRIPTION
				"The name of Option Format."
			::= { fkV2Dhcp4OptionFormatAttrControl 6 }

		
		-- 1.3.6.1.4.1.10428 9 1.102.6.2.3.4.2.2.7
		fkV2Dhcp4OptionFormatAttrControlID OBJECT-TYPE
			SYNTAX INTEGER (1..64)
			MAX-ACCESS read-write
			STATUS current
			DESCRIPTION
				"The ID of Option Format Attr."
			::= { fkV2Dhcp4OptionFormatAttrControl 7 }

		
		-- 1.3.6.1.4.1.10428 9 1.102.6.2.3.4.2.2.8
		fkV2Dhcp4OptionFormatAttrControlLength OBJECT-TYPE
			SYNTAX INTEGER (-1..64)
			MAX-ACCESS read-write
			STATUS current
			DESCRIPTION
				"The Length Field of Option Format Attr.
				The -1 of value means this field is not defined.
				The Zero of value means this field is variable
				"
			::= { fkV2Dhcp4OptionFormatAttrControl 8 }

		
		-- 1.3.6.1.4.1.10428 9 1.102.6.2.3.4.2.2.9
		fkV2Dhcp4OptionFormatAttrControlHiddenLength OBJECT-TYPE
			SYNTAX INTEGER (-1..64)
			MAX-ACCESS read-write
			STATUS current
			DESCRIPTION
				"The Hidden Length Field of Option Format Attr.
				The -1 of value means this field is not defined.
				The Zero of value means this field is variable"
			::= { fkV2Dhcp4OptionFormatAttrControl 9 }
-- 
-- 
		
		-- 1.3.6.1.4.1.10428 9 1.102.6.2.3.4.2.2.10
		fkV2Dhcp4OptionFormatAttrControlType OBJECT-TYPE
			SYNTAX INTEGER (-1..255)
			MAX-ACCESS read-write
			STATUS current
			DESCRIPTION
				"The Type Field of Option Format Attr.
				The -1 of value means this field not defined."
			::= { fkV2Dhcp4OptionFormatAttrControl 10 }
-- 
-- 
		
		-- 1.3.6.1.4.1.10428 9 1.102.6.2.3.4.2.2.11
		fkV2Dhcp4OptionFormatAttrControlVarType OBJECT-TYPE
			SYNTAX INTEGER
				{
				hex(1),
				ifIp(2),
				index(3),
				ip(4),
				string(5)
				}
			MAX-ACCESS read-only
			STATUS current
			DESCRIPTION
				"The Variable Type Field of Option Format Attr."
			::= { fkV2Dhcp4OptionFormatAttrControl 11 }

		
		-- 1.3.6.1.4.1.10428 9 1.102.6.2.3.4.2.2.12
		fkV2Dhcp4OptionFormatAttrControlVarValue OBJECT-TYPE
			SYNTAX OCTET STRING (SIZE (1..255))
			MAX-ACCESS read-write
			STATUS current
			DESCRIPTION
				"The Variable Value Field of Option Format Attr."
			::= { fkV2Dhcp4OptionFormatAttrControl 12 }

		
		-- 1.3.6.1.4.1.10428 9 1.102.6.2.3.4.2.3
		fkV2Dhcp4OptionFormatAttrNotification OBJECT IDENTIFIER ::= { fkV2Dhcp4OptionFormatAttribute 3 }

		
		-- 1.3.6.1.4.1.10428 9 1.102.6.2.3.4.2.3.1
		fkV2Dhcp4OptionFormatAttrAdded NOTIFICATION-TYPE
			OBJECTS { fkV2Dhcp4OptionFormatAttrControlRequest, fkV2Dhcp4OptionFormatAttrControlVarValue, fkV2Dhcp4OptionFormatAttrControlVarType, fkV2Dhcp4OptionFormatAttrControlType, fkV2Dhcp4OptionFormatAttrControlHiddenLength, 
				fkV2Dhcp4OptionFormatAttrControlLength, fkV2Dhcp4OptionFormatAttrControlReqResult, fkV2Dhcp4OptionFormatAttrControlTimeStamp, fkV2Dhcp4OptionFormatAttrControlName, fkV2Dhcp4OptionFormatAttrControlID
				 }
			STATUS current
			DESCRIPTION 
				"addOptionFormatAttr."
			::= { fkV2Dhcp4OptionFormatAttrNotification 1 }

		
		-- 1.3.6.1.4.1.10428 9 1.102.6.2.3.4.2.3.2
		fkV2Dhcp4OptionFormatAttrDeleted NOTIFICATION-TYPE
			OBJECTS { fkV2Dhcp4OptionFormatAttrControlRequest, fkV2Dhcp4OptionFormatAttrControlID, fkV2Dhcp4OptionFormatAttrControlName, fkV2Dhcp4OptionFormatControlTimeStamp, fkV2Dhcp4OptionFormatControlReqResult
				 }
			STATUS current
			DESCRIPTION 
				"deleteOptionFormatAttr."
			::= { fkV2Dhcp4OptionFormatAttrNotification 2 }

		
		-- 1.3.6.1.4.1.10428 9 1.102.6.2.3.4.2.3.3
		fkV2Dhcp4OptionFormatAttrModified NOTIFICATION-TYPE
			OBJECTS { fkV2Dhcp4OptionFormatAttrControlRequest, fkV2Dhcp4OptionFormatAttrControlReqResult, fkV2Dhcp4OptionFormatAttrControlTimeStamp, fkV2Dhcp4OptionFormatAttrControlName, fkV2Dhcp4OptionFormatAttrControlID, 
				fkV2Dhcp4OptionFormatAttrControlLength, fkV2Dhcp4OptionFormatAttrControlHiddenLength, fkV2Dhcp4OptionFormatAttrControlType, fkV2Dhcp4OptionFormatAttrControlVarType, fkV2Dhcp4OptionFormatAttrControlVarValue
				 }
			STATUS current
			DESCRIPTION 
				"modifyOptionFormatAttr."
			::= { fkV2Dhcp4OptionFormatAttrNotification 3 }

		
		-- 1.3.6.1.4.1.10428 9 1.102.6.2.4
		fkV2Dhcp4Filter OBJECT IDENTIFIER ::= { fkV2Dhcp4 4 }

		
		-- 1.3.6.1.4.1.10428 9 1.102.6.2.4.1
		fkV2Dhcp4FilterPort OBJECT IDENTIFIER ::= { fkV2Dhcp4Filter 1 }

		
		-- 1.3.6.1.4.1.10428 9 1.102.6.2.4.1.1
		fkV2Dhcp4FilterPortTable OBJECT-TYPE
			SYNTAX SEQUENCE OF FkV2Dhcp4FilterPortEntry
			MAX-ACCESS not-accessible
			STATUS current
			DESCRIPTION
				"Description."
			::= { fkV2Dhcp4FilterPort 1 }

		
		-- 1.3.6.1.4.1.10428 9 1.102.6.2.4.1.1.1
		fkV2Dhcp4FilterPortEntry OBJECT-TYPE
			SYNTAX FkV2Dhcp4FilterPortEntry
			MAX-ACCESS not-accessible
			STATUS current
			DESCRIPTION
				"Description."
			INDEX { fkV2Dhcp4FilterPortIndex }
			::= { fkV2Dhcp4FilterPortTable 1 }

		
		FkV2Dhcp4FilterPortEntry ::=
			SEQUENCE { 
				fkV2Dhcp4FilterPortIndex
					INTEGER,
				fkV2Dhcp4FilterPortState
					INTEGER
			 }

		-- 1.3.6.1.4.1.10428 9 1.102.6.2.4.1.1.1.1
		fkV2Dhcp4FilterPortIndex OBJECT-TYPE
			SYNTAX INTEGER (1..255)
			MAX-ACCESS read-only
			STATUS current
			DESCRIPTION
				"Description."
			::= { fkV2Dhcp4FilterPortEntry 1 }

		
		-- 1.3.6.1.4.1.10428 9 1.102.6.2.4.1.1.1.2
		fkV2Dhcp4FilterPortState OBJECT-TYPE
			SYNTAX INTEGER
				{
				disable(0),
				enable(1)
				}
			MAX-ACCESS read-only
			STATUS current
			DESCRIPTION
				"Description."
			::= { fkV2Dhcp4FilterPortEntry 2 }

		
		-- 1.3.6.1.4.1.10428 9 1.102.6.2.4.1.2
		fkV2Dhcp4FilterPortControl OBJECT IDENTIFIER ::= { fkV2Dhcp4FilterPort 2 }

		
		-- 1.3.6.1.4.1.10428 9 1.102.6.2.4.1.2.1
		fkV2Dhcp4FilterPortControlRequest OBJECT-TYPE
			SYNTAX INTEGER { setDhcpFilterPortMode(1) }
			MAX-ACCESS read-write
			STATUS current
			DESCRIPTION
				"The request of a user command."
			::= { fkV2Dhcp4FilterPortControl 1 }

		
		-- 1.3.6.1.4.1.10428 9 1.102.6.2.4.1.2.2
		fkV2Dhcp4FilterPortControlStatus OBJECT-TYPE
			SYNTAX FkControlStatusType
			MAX-ACCESS read-only
			STATUS current
			DESCRIPTION
				"The status of a user command."
			::= { fkV2Dhcp4FilterPortControl 2 }

		
		-- 1.3.6.1.4.1.10428 9 1.102.6.2.4.1.2.3
		fkV2Dhcp4FilterPortControlTimer OBJECT-TYPE
			SYNTAX Gauge32
			MAX-ACCESS read-write
			STATUS current
			DESCRIPTION
				"The maximum wait Time for the manager for a long running user command."
			::= { fkV2Dhcp4FilterPortControl 3 }

		
		-- 1.3.6.1.4.1.10428 9 1.102.6.2.4.1.2.4
		fkV2Dhcp4FilterPortControlTimeStamp OBJECT-TYPE
			SYNTAX TimeTicks
			MAX-ACCESS read-only
			STATUS current
			DESCRIPTION
				"The Time stamp of the last command (end of command)."
			::= { fkV2Dhcp4FilterPortControl 4 }

		
		-- 1.3.6.1.4.1.10428 9 1.102.6.2.4.1.2.5
		fkV2Dhcp4FilterPortControlReqResult OBJECT-TYPE
			SYNTAX FkControlRequestResultType
			MAX-ACCESS read-only
			STATUS current
			DESCRIPTION
				"The result of the last user command."
			::= { fkV2Dhcp4FilterPortControl 5 }

		
		-- 1.3.6.1.4.1.10428 9 1.102.6.2.4.1.2.6
		fkV2Dhcp4FilterPortControlIndex OBJECT-TYPE
			SYNTAX INTEGER (1..255)
			MAX-ACCESS read-write
			STATUS current
			DESCRIPTION
				"Description."
			::= { fkV2Dhcp4FilterPortControl 6 }

		
		-- 1.3.6.1.4.1.10428 9 1.102.6.2.4.1.2.7
		fkV2Dhcp4FilterPortControlState OBJECT-TYPE
			SYNTAX INTEGER
				{
				disable(0),
				enable(1)
				}
			MAX-ACCESS read-write
			STATUS current
			DESCRIPTION
				"Description."
			::= { fkV2Dhcp4FilterPortControl 7 }

		
		-- 1.3.6.1.4.1.10428 9 1.102.6.2.4.1.3
		fkV2Dhcp4FilterPortNotification OBJECT IDENTIFIER ::= { fkV2Dhcp4FilterPort 3 }

		
		-- 1.3.6.1.4.1.10428 9 1.102.6.2.4.1.3.1
		fkV2Dhcp4FilterPortStateChanged NOTIFICATION-TYPE
			OBJECTS { fkV2Dhcp4FilterPortControlRequest, fkV2Dhcp4FilterPortControlTimeStamp, fkV2Dhcp4FilterPortControlReqResult, fkV2Dhcp4FilterPortState }
			STATUS current
			DESCRIPTION 
				"Description."
			::= { fkV2Dhcp4FilterPortNotification 1 }

		
		-- 1.3.6.1.4.1.10428 9 1.102.6.2.4.2
		fkV2Dhcp4FilterAddress OBJECT IDENTIFIER ::= { fkV2Dhcp4Filter 2 }

		
		-- 1.3.6.1.4.1.10428 9 1.102.6.2.4.2.1
		fkV2Dhcp4FilterAddressTable OBJECT-TYPE
			SYNTAX SEQUENCE OF FkV2Dhcp4FilterAddressEntry
			MAX-ACCESS not-accessible
			STATUS current
			DESCRIPTION
				"Description."
			::= { fkV2Dhcp4FilterAddress 1 }

		
		-- 1.3.6.1.4.1.10428 9 1.102.6.2.4.2.1.1
		fkV2Dhcp4FilterAddressEntry OBJECT-TYPE
			SYNTAX FkV2Dhcp4FilterAddressEntry
			MAX-ACCESS not-accessible
			STATUS current
			DESCRIPTION
				"Description."
			INDEX { fkV2Dhcp4FilterAddressMac }
			::= { fkV2Dhcp4FilterAddressTable 1 }

		
		FkV2Dhcp4FilterAddressEntry ::=
			SEQUENCE { 
				fkV2Dhcp4FilterAddressMac
					MacAddress,
				fkV2Dhcp4FilterAddressType
					BITS
			 }

		-- 1.3.6.1.4.1.10428 9 1.102.6.2.4.2.1.1.1
		fkV2Dhcp4FilterAddressMac OBJECT-TYPE
			SYNTAX MacAddress
			MAX-ACCESS read-only
			STATUS current
			DESCRIPTION
				"The mac address for the filtering.
				MAC address which IP address is not assigned"
			::= { fkV2Dhcp4FilterAddressEntry 1 }

		
		-- 1.3.6.1.4.1.10428 9 1.102.6.2.4.2.1.1.2
		fkV2Dhcp4FilterAddressType OBJECT-TYPE
			SYNTAX BITS
				{
				discover(0),
				offer(1),
				request(2),
				decline(3),
				ack(4),
				nak(5),
				release(6),
				inform(7)
				}
			MAX-ACCESS read-only
			STATUS current
			DESCRIPTION
				"The type can be assigned as a DHCP PACKET
				  ack       packet type - DHCPACK
				  decline   packet type - DHCPDECLINE
				  discover  packet type - DHCPDISCOVER
				  inform    packet type - DHCPINFORM
				  nak       packet type - DHCPNAK
				  offer     packet type - DHCPOFFER
				  release   packet type - DHCPRELEASE
				  request   packet type - DHCPREQUEST"
			::= { fkV2Dhcp4FilterAddressEntry 2 }

		
		-- 1.3.6.1.4.1.10428 9 1.102.6.2.4.2.2
		fkV2Dhcp4FilterAddressControl OBJECT IDENTIFIER ::= { fkV2Dhcp4FilterAddress 2 }

		
		-- 1.3.6.1.4.1.10428 9 1.102.6.2.4.2.2.1
		fkV2Dhcp4FilterAddressControlRequest OBJECT-TYPE
			SYNTAX INTEGER
				{
				createDhcpFilterAddress(1),
				destroyDhcpFilterAddress(2)
				}
			MAX-ACCESS read-write
			STATUS current
			DESCRIPTION
				"The request of a user command."
			::= { fkV2Dhcp4FilterAddressControl 1 }

		
		-- 1.3.6.1.4.1.10428 9 1.102.6.2.4.2.2.2
		fkV2Dhcp4FilterAddressControlStatus OBJECT-TYPE
			SYNTAX FkControlStatusType
			MAX-ACCESS read-only
			STATUS current
			DESCRIPTION
				"The status of a user command."
			::= { fkV2Dhcp4FilterAddressControl 2 }

		
		-- 1.3.6.1.4.1.10428 9 1.102.6.2.4.2.2.3
		fkV2Dhcp4FilterAddressControlTimer OBJECT-TYPE
			SYNTAX Gauge32
			MAX-ACCESS read-write
			STATUS current
			DESCRIPTION
				"The maximum wait Time for the manager for a long running user command."
			::= { fkV2Dhcp4FilterAddressControl 3 }

		
		-- 1.3.6.1.4.1.10428 9 1.102.6.2.4.2.2.4
		fkV2Dhcp4FilterAddressControlTimeStamp OBJECT-TYPE
			SYNTAX TimeTicks
			MAX-ACCESS read-only
			STATUS current
			DESCRIPTION
				"The Time stamp of the last command (end of command)."
			::= { fkV2Dhcp4FilterAddressControl 4 }

		
		-- 1.3.6.1.4.1.10428 9 1.102.6.2.4.2.2.5
		fkV2Dhcp4FilterAddressControlReqResult OBJECT-TYPE
			SYNTAX FkControlRequestResultType
			MAX-ACCESS read-only
			STATUS current
			DESCRIPTION
				"The result of the last user command."
			::= { fkV2Dhcp4FilterAddressControl 5 }

		
		-- 1.3.6.1.4.1.10428 9 1.102.6.2.4.2.2.6
		fkV2Dhcp4FilterAddressControlMac OBJECT-TYPE
			SYNTAX MacAddress
			MAX-ACCESS read-write
			STATUS current
			DESCRIPTION
				"The mac address for the filtering.
				MAC address which IP address is not assigned"
			::= { fkV2Dhcp4FilterAddressControl 6 }

		
		-- 1.3.6.1.4.1.10428 9 1.102.6.2.4.2.2.7
		fkV2Dhcp4FilterAddressControlType OBJECT-TYPE
			SYNTAX BITS
				{
				discover(0),
				offer(1),
				request(2),
				decline(3),
				ack(4),
				nak(5),
				release(6),
				inform(7)
				}
			MAX-ACCESS read-write
			STATUS current
			DESCRIPTION
				"The type can be assigned as a DHCP PACKET
				  ack       packet type - DHCPACK
				  decline   packet type - DHCPDECLINE
				  discover  packet type - DHCPDISCOVER
				  inform    packet type - DHCPINFORM
				  nak       packet type - DHCPNAK
				  offer     packet type - DHCPOFFER
				  release   packet type - DHCPRELEASE
				  request   packet type - DHCPREQUEST"
			::= { fkV2Dhcp4FilterAddressControl 7 }

		
		-- 1.3.6.1.4.1.10428 9 1.102.6.2.4.2.3
		fkV2Dhcp4FilterAddressNotification OBJECT IDENTIFIER ::= { fkV2Dhcp4FilterAddress 3 }

		
		-- 1.3.6.1.4.1.10428 9 1.102.6.2.4.2.3.1
		fkV2Dhcp4FilterAddressCreated NOTIFICATION-TYPE
			OBJECTS { fkV2Dhcp4FilterAddressControlRequest, fkV2Dhcp4FilterAddressControlTimeStamp, fkV2Dhcp4FilterAddressControlReqResult, fkV2Dhcp4FilterAddressControlMac, fkV2Dhcp4FilterAddressControlType
				 }
			STATUS current
			DESCRIPTION 
				"Description."
			::= { fkV2Dhcp4FilterAddressNotification 1 }

		
		-- 1.3.6.1.4.1.10428 9 1.102.6.2.4.2.3.2
		fkV2Dhcp4FilterAddressDestroyed NOTIFICATION-TYPE
			OBJECTS { fkV2Dhcp4FilterAddressControlRequest, fkV2Dhcp4FilterAddressControlTimeStamp, fkV2Dhcp4FilterAddressControlReqResult, fkV2Dhcp4FilterAddressControlMac, fkV2Dhcp4FilterAddressControlType
				 }
			STATUS current
			DESCRIPTION 
				"Description."
			::= { fkV2Dhcp4FilterAddressNotification 2 }

		
		-- 1.3.6.1.4.1.10428 9 1.102.6.2.4.3
		fkV2Dhcp4Illegal OBJECT IDENTIFIER ::= { fkV2Dhcp4Filter 3 }

		
		-- 1.3.6.1.4.1.10428 9 1.102.6.2.4.3.1
		fkV2Dhcp4IllegalTable OBJECT-TYPE
			SYNTAX SEQUENCE OF FkV2Dhcp4IllegalEntry
			MAX-ACCESS not-accessible
			STATUS current
			DESCRIPTION
				"Description."
			::= { fkV2Dhcp4Illegal 1 }

		
		-- 1.3.6.1.4.1.10428 9 1.102.6.2.4.3.1.1
		fkV2Dhcp4IllegalEntry OBJECT-TYPE
			SYNTAX FkV2Dhcp4IllegalEntry
			MAX-ACCESS not-accessible
			STATUS current
			DESCRIPTION
				"Description."
			INDEX { fkV2Dhcp4IllegalAddress, fkV2Dhcp4IllegalMac }
			::= { fkV2Dhcp4IllegalTable 1 }

		
		FkV2Dhcp4IllegalEntry ::=
			SEQUENCE { 
				fkV2Dhcp4IllegalAddress
					IpAddress,
				fkV2Dhcp4IllegalMac
					MacAddress,
				fkV2Dhcp4IllegalTime
					Unsigned32
			 }

		-- 1.3.6.1.4.1.10428 9 1.102.6.2.4.3.1.1.1
		fkV2Dhcp4IllegalAddress OBJECT-TYPE
			SYNTAX IpAddress
			MAX-ACCESS read-only
			STATUS current
			DESCRIPTION
				"The illegal IP address."
			::= { fkV2Dhcp4IllegalEntry 1 }

		
		-- 1.3.6.1.4.1.10428 9 1.102.6.2.4.3.1.1.2
		fkV2Dhcp4IllegalMac OBJECT-TYPE
			SYNTAX MacAddress
			MAX-ACCESS read-only
			STATUS current
			DESCRIPTION
				"The MAC Address of this illegal address."
			::= { fkV2Dhcp4IllegalEntry 2 }

		
		-- 1.3.6.1.4.1.10428 9 1.102.6.2.4.3.1.1.3
		fkV2Dhcp4IllegalTime OBJECT-TYPE
			SYNTAX Unsigned32
			MAX-ACCESS read-only
			STATUS current
			DESCRIPTION
				"단위는 1970.1.1일 0시 0분 0초부터 계산한 초"
			::= { fkV2Dhcp4IllegalEntry 3 }

		
		-- 1.3.6.1.4.1.10428 9 1.102.6.2.4.3.2
		fkV2Dhcp4IllegalControl OBJECT IDENTIFIER ::= { fkV2Dhcp4Illegal 2 }

		
		-- 1.3.6.1.4.1.10428 9 1.102.6.2.4.3.2.1
		fkV2Dhcp4IllegalControlRequest OBJECT-TYPE
			SYNTAX INTEGER { clearIllegal(1) }
			MAX-ACCESS read-write
			STATUS current
			DESCRIPTION
				"The request of a user command."
			::= { fkV2Dhcp4IllegalControl 1 }

		
		-- 1.3.6.1.4.1.10428 9 1.102.6.2.4.3.2.2
		fkV2Dhcp4IllegalControlStatus OBJECT-TYPE
			SYNTAX FkControlStatusType
			MAX-ACCESS read-only
			STATUS current
			DESCRIPTION
				"The status of a user command."
			::= { fkV2Dhcp4IllegalControl 2 }

		
		-- 1.3.6.1.4.1.10428 9 1.102.6.2.4.3.2.3
		fkV2Dhcp4IllegalControlTimer OBJECT-TYPE
			SYNTAX Gauge32
			MAX-ACCESS read-write
			STATUS current
			DESCRIPTION
				"The maximum wait Time for the manager for a long running user command."
			::= { fkV2Dhcp4IllegalControl 3 }

		
		-- 1.3.6.1.4.1.10428 9 1.102.6.2.4.3.2.4
		fkV2Dhcp4IllegalControlTimeStamp OBJECT-TYPE
			SYNTAX TimeTicks
			MAX-ACCESS read-only
			STATUS current
			DESCRIPTION
				"The Time stamp of the last command (end of command)."
			::= { fkV2Dhcp4IllegalControl 4 }

		
		-- 1.3.6.1.4.1.10428 9 1.102.6.2.4.3.2.5
		fkV2Dhcp4IllegalControlReqResult OBJECT-TYPE
			SYNTAX FkControlRequestResultType
			MAX-ACCESS read-only
			STATUS current
			DESCRIPTION
				"The result of the last user command."
			::= { fkV2Dhcp4IllegalControl 5 }

		
		-- 1.3.6.1.4.1.10428 9 1.102.6.2.4.3.3
		fkV2Dhcp4IllegalNotification OBJECT IDENTIFIER ::= { fkV2Dhcp4Illegal 3 }

		
		-- 1.3.6.1.4.1.10428 9 1.102.6.2.4.3.3.1
		fkV2Dhcp4IllegalCleared NOTIFICATION-TYPE
			OBJECTS { fkV2Dhcp4IllegalControlRequest, fkV2Dhcp4IllegalControlTimeStamp, fkV2Dhcp4IllegalControlReqResult }
			STATUS current
			DESCRIPTION 
				"Description."
			::= { fkV2Dhcp4IllegalNotification 1 }

		
		-- 1.3.6.1.4.1.10428 9 1.102.6.2.5
		fkV2Dhcp4Stats OBJECT IDENTIFIER ::= { fkV2Dhcp4 5 }

		
		-- 1.3.6.1.4.1.10428 9 1.102.6.2.5.1
		fkV2Dhcp4PacketStats OBJECT IDENTIFIER ::= { fkV2Dhcp4Stats 1 }

		
		-- 1.3.6.1.4.1.10428 9 1.102.6.2.5.1.1
		fkV2Dhcp4PacketStatsInfo OBJECT IDENTIFIER ::= { fkV2Dhcp4PacketStats 1 }

		
		-- 1.3.6.1.4.1.10428 9 1.102.6.2.5.1.1.1
		fkV2Dhcp4PacketStatsReceived OBJECT-TYPE
			SYNTAX Unsigned32
			MAX-ACCESS read-only
			STATUS current
			DESCRIPTION
				"The number of received DHCP packets."
			::= { fkV2Dhcp4PacketStatsInfo 1 }

		
		-- 1.3.6.1.4.1.10428 9 1.102.6.2.5.1.1.2
		fkV2Dhcp4PacketStatsSent OBJECT-TYPE
			SYNTAX Unsigned32
			MAX-ACCESS read-only
			STATUS current
			DESCRIPTION
				"The number of sent DHCP packets."
			::= { fkV2Dhcp4PacketStatsInfo 2 }

		
		-- 1.3.6.1.4.1.10428 9 1.102.6.2.5.1.1.3
		fkV2Dhcp4PacketStatsReceivedErrors OBJECT-TYPE
			SYNTAX Unsigned32
			MAX-ACCESS read-only
			STATUS current
			DESCRIPTION
				"The number of received DHCP Error packets."
			::= { fkV2Dhcp4PacketStatsInfo 3 }

		
		-- 1.3.6.1.4.1.10428 9 1.102.6.2.5.1.1.4
		fkV2Dhcp4PacketStatsSentErrors OBJECT-TYPE
			SYNTAX Unsigned32
			MAX-ACCESS read-only
			STATUS current
			DESCRIPTION
				"The number of sent DHCP Error packets."
			::= { fkV2Dhcp4PacketStatsInfo 4 }

		
		-- 1.3.6.1.4.1.10428 9 1.102.6.2.5.1.1.5
		fkV2Dhcp4PacketStatsBootpReceivedRequests OBJECT-TYPE
			SYNTAX Unsigned32
			MAX-ACCESS read-only
			STATUS current
			DESCRIPTION
				"The number of received DHCP Bootp Request packets."
			::= { fkV2Dhcp4PacketStatsInfo 5 }

		
		-- 1.3.6.1.4.1.10428 9 1.102.6.2.5.1.1.6
		fkV2Dhcp4PacketStatsBootpReceivedReplies OBJECT-TYPE
			SYNTAX Unsigned32
			MAX-ACCESS read-only
			STATUS current
			DESCRIPTION
				"The number of received DHCP Bootp Reply packets."
			::= { fkV2Dhcp4PacketStatsInfo 6 }

		
		-- 1.3.6.1.4.1.10428 9 1.102.6.2.5.1.1.7
		fkV2Dhcp4PacketStatsBootpSentRequests OBJECT-TYPE
			SYNTAX Unsigned32
			MAX-ACCESS read-only
			STATUS current
			DESCRIPTION
				"The number of sent DHCP Bootp Request packets."
			::= { fkV2Dhcp4PacketStatsInfo 7 }

		
		-- 1.3.6.1.4.1.10428 9 1.102.6.2.5.1.1.8
		fkV2Dhcp4PacketStatsBootpSentReplies OBJECT-TYPE
			SYNTAX Unsigned32
			MAX-ACCESS read-only
			STATUS current
			DESCRIPTION
				"The number of sent DHCP Bootp Reply packets."
			::= { fkV2Dhcp4PacketStatsInfo 8 }

		
		-- 1.3.6.1.4.1.10428 9 1.102.6.2.5.1.1.9
		fkV2Dhcp4PacketStatsReceivedDiscover OBJECT-TYPE
			SYNTAX Unsigned32
			MAX-ACCESS read-only
			STATUS current
			DESCRIPTION
				"The number of received Discover packets."
			::= { fkV2Dhcp4PacketStatsInfo 9 }

		
		-- 1.3.6.1.4.1.10428 9 1.102.6.2.5.1.1.10
		fkV2Dhcp4PacketStatsReceivedRequest OBJECT-TYPE
			SYNTAX Unsigned32
			MAX-ACCESS read-only
			STATUS current
			DESCRIPTION
				"The number of received DHCP Request packets."
			::= { fkV2Dhcp4PacketStatsInfo 10 }

		
		-- 1.3.6.1.4.1.10428 9 1.102.6.2.5.1.1.11
		fkV2Dhcp4PacketStatsReceivedRelease OBJECT-TYPE
			SYNTAX Unsigned32
			MAX-ACCESS read-only
			STATUS current
			DESCRIPTION
				"The number of received DHCP Release packets."
			::= { fkV2Dhcp4PacketStatsInfo 11 }

		
		-- 1.3.6.1.4.1.10428 9 1.102.6.2.5.1.1.12
		fkV2Dhcp4PacketStatscReceivedInform OBJECT-TYPE
			SYNTAX Unsigned32
			MAX-ACCESS read-only
			STATUS current
			DESCRIPTION
				"The number of received DHCP Inform packets."
			::= { fkV2Dhcp4PacketStatsInfo 12 }

		
		-- 1.3.6.1.4.1.10428 9 1.102.6.2.5.1.1.13
		fkV2Dhcp4PacketStatsReceivedDecline OBJECT-TYPE
			SYNTAX Unsigned32
			MAX-ACCESS read-only
			STATUS current
			DESCRIPTION
				"The number of received DHCP Decline packets."
			::= { fkV2Dhcp4PacketStatsInfo 13 }

		
		-- 1.3.6.1.4.1.10428 9 1.102.6.2.5.1.1.14
		fkV2Dhcp4PacketStatsSentOffer OBJECT-TYPE
			SYNTAX Unsigned32
			MAX-ACCESS read-only
			STATUS current
			DESCRIPTION
				"The number of sent DHCP Offer packets."
			::= { fkV2Dhcp4PacketStatsInfo 14 }

		
		-- 1.3.6.1.4.1.10428 9 1.102.6.2.5.1.1.15
		fkV2Dhcp4PacketStatsSentAck OBJECT-TYPE
			SYNTAX Unsigned32
			MAX-ACCESS read-only
			STATUS current
			DESCRIPTION
				"The number of sent DHCP Ack packets."
			::= { fkV2Dhcp4PacketStatsInfo 15 }

		
		-- 1.3.6.1.4.1.10428 9 1.102.6.2.5.1.1.16
		fkV2Dhcp4PacketStatsSentNak OBJECT-TYPE
			SYNTAX Unsigned32
			MAX-ACCESS read-only
			STATUS current
			DESCRIPTION
				"The number of sent DHCP Nak packets."
			::= { fkV2Dhcp4PacketStatsInfo 16 }

		
		-- 1.3.6.1.4.1.10428 9 1.102.6.2.5.1.1.17
		fkV2Dhcp4SummaryPoolCnt OBJECT-TYPE
			SYNTAX Unsigned32
			MAX-ACCESS read-only
			STATUS current
			DESCRIPTION
				"The number of Pools.to be set."
			::= { fkV2Dhcp4PacketStatsInfo 17 }

		
		-- 1.3.6.1.4.1.10428 9 1.102.6.2.5.1.1.18
		fkV2Dhcp4SummaryTotal OBJECT-TYPE
			SYNTAX Unsigned32
			MAX-ACCESS read-only
			STATUS current
			DESCRIPTION
				"The number of Total leases to be set."
			::= { fkV2Dhcp4PacketStatsInfo 18 }

		
		-- 1.3.6.1.4.1.10428 9 1.102.6.2.5.1.1.19
		fkV2Dhcp4SummaryAvailable OBJECT-TYPE
			SYNTAX Unsigned32
			MAX-ACCESS read-only
			STATUS current
			DESCRIPTION
				"The number of Available leases to be set."
			::= { fkV2Dhcp4PacketStatsInfo 19 }

		
		-- 1.3.6.1.4.1.10428 9 1.102.6.2.5.1.1.20
		fkV2Dhcp4SummaryAbandon OBJECT-TYPE
			SYNTAX Unsigned32
			MAX-ACCESS read-only
			STATUS current
			DESCRIPTION
				"The number of Abandon leases to be set."
			::= { fkV2Dhcp4PacketStatsInfo 20 }

		
		-- 1.3.6.1.4.1.10428 9 1.102.6.2.5.1.1.21
		fkV2Dhcp4SummaryBound OBJECT-TYPE
			SYNTAX Unsigned32
			MAX-ACCESS read-only
			STATUS current
			DESCRIPTION
				"The number of Bound leases to be set."
			::= { fkV2Dhcp4PacketStatsInfo 21 }

		
		-- 1.3.6.1.4.1.10428 9 1.102.6.2.5.1.1.22
		fkV2Dhcp4SummaryOffered OBJECT-TYPE
			SYNTAX Unsigned32
			MAX-ACCESS read-only
			STATUS current
			DESCRIPTION
				"The number of Offered leases to be set."
			::= { fkV2Dhcp4PacketStatsInfo 22 }

		
		-- 1.3.6.1.4.1.10428 9 1.102.6.2.5.1.1.23
		fkV2Dhcp4SummaryFixed OBJECT-TYPE
			SYNTAX Unsigned32
			MAX-ACCESS read-only
			STATUS current
			DESCRIPTION
				"The number of Fixed leases to be set."
			::= { fkV2Dhcp4PacketStatsInfo 23 }

		
		-- 1.3.6.1.4.1.10428 9 1.102.6.2.5.1.1.24
		fkV2Dhcp4SummaryAllocated OBJECT-TYPE
			SYNTAX Unsigned32
			MAX-ACCESS read-only
			STATUS current
			DESCRIPTION
				"Description."
			::= { fkV2Dhcp4PacketStatsInfo 24 }

		
		-- 1.3.6.1.4.1.10428 9 1.102.6.2.5.1.2
		fkV2Dhcp4PacketStatsControl OBJECT IDENTIFIER ::= { fkV2Dhcp4PacketStats 2 }

		
		-- 1.3.6.1.4.1.10428 9 1.102.6.2.5.1.2.1
		fkV2Dhcp4PacketStatsControlRequest OBJECT-TYPE
			SYNTAX INTEGER { clearDhcpPacketStats(1) }
			MAX-ACCESS read-write
			STATUS current
			DESCRIPTION
				"The request of a user command."
			::= { fkV2Dhcp4PacketStatsControl 1 }

		
		-- 1.3.6.1.4.1.10428 9 1.102.6.2.5.1.2.2
		fkV2Dhcp4PacketStatsControlStatus OBJECT-TYPE
			SYNTAX FkControlStatusType
			MAX-ACCESS read-only
			STATUS current
			DESCRIPTION
				"The status of a user command."
			::= { fkV2Dhcp4PacketStatsControl 2 }

		
		-- 1.3.6.1.4.1.10428 9 1.102.6.2.5.1.2.3
		fkV2Dhcp4PacketStatsControlTimer OBJECT-TYPE
			SYNTAX Gauge32
			MAX-ACCESS read-write
			STATUS current
			DESCRIPTION
				"The maximum wait Time for the manager for a long running user command."
			::= { fkV2Dhcp4PacketStatsControl 3 }

		
		-- 1.3.6.1.4.1.10428 9 1.102.6.2.5.1.2.4
		fkV2Dhcp4PacketStatsControlTimeStamp OBJECT-TYPE
			SYNTAX TimeTicks
			MAX-ACCESS read-only
			STATUS current
			DESCRIPTION
				"The Time stamp of the last command (end of command)."
			::= { fkV2Dhcp4PacketStatsControl 4 }

		
		-- 1.3.6.1.4.1.10428 9 1.102.6.2.5.1.2.5
		fkV2Dhcp4PacketStatsControlReqResult OBJECT-TYPE
			SYNTAX FkControlRequestResultType
			MAX-ACCESS read-only
			STATUS current
			DESCRIPTION
				"The result of the last user command."
			::= { fkV2Dhcp4PacketStatsControl 5 }

		
		-- 1.3.6.1.4.1.10428 9 1.102.6.2.5.1.3
		fkV2Dhcp4PacketStatsNotification OBJECT IDENTIFIER ::= { fkV2Dhcp4PacketStats 3 }

		
		-- 1.3.6.1.4.1.10428 9 1.102.6.2.5.1.3.1
		fkV2Dhcp4PacketStatsCleared NOTIFICATION-TYPE
			OBJECTS { fkV2Dhcp4PacketStatsControlRequest, fkV2Dhcp4PacketStatsControlTimeStamp, fkV2Dhcp4PacketStatsControlReqResult }
			STATUS current
			DESCRIPTION 
				"Description."
			::= { fkV2Dhcp4PacketStatsNotification 1 }

		
		-- 1.3.6.1.4.1.10428 9 1.102.6.2.5.2
		fkV2Dhcp4Leased OBJECT IDENTIFIER ::= { fkV2Dhcp4Stats 2 }

		
		-- 1.3.6.1.4.1.10428 9 1.102.6.2.5.2.1
		fkV2Dhcp4LeasedTable OBJECT-TYPE
			SYNTAX SEQUENCE OF FkV2Dhcp4LeasedEntry
			MAX-ACCESS not-accessible
			STATUS current
			DESCRIPTION
				"Description."
			::= { fkV2Dhcp4Leased 1 }

		
		-- 1.3.6.1.4.1.10428 9 1.102.6.2.5.2.1.1
		fkV2Dhcp4LeasedEntry OBJECT-TYPE
			SYNTAX FkV2Dhcp4LeasedEntry
			MAX-ACCESS not-accessible
			STATUS current
			DESCRIPTION
				"Description."
			INDEX { fkV2Dhcp4LeasedAddress }
			::= { fkV2Dhcp4LeasedTable 1 }

		
		FkV2Dhcp4LeasedEntry ::=
			SEQUENCE { 
				fkV2Dhcp4LeasedAddress
					IpAddress,
				fkV2Dhcp4LeasedPoolIndex
					INTEGER,
				fkV2Dhcp4LeasedStatus
					INTEGER,
				fkV2Dhcp4LeasedMac
					MacAddress,
				fkV2Dhcp4LeasedHostName
					OCTET STRING,
				fkV2Dhcp4LeasedClientId
					OCTET STRING,
				fkV2Dhcp4LeasedRemoteId
					OCTET STRING,
				fkV2Dhcp4LeasedCircuitId
					OCTET STRING,
				fkV2Dhcp4LeasedStartTime
					Unsigned32,
				fkV2Dhcp4LeasedFinishTime
					Unsigned32
			 }

		-- 1.3.6.1.4.1.10428 9 1.102.6.2.5.2.1.1.1
		fkV2Dhcp4LeasedAddress OBJECT-TYPE
			SYNTAX IpAddress
			MAX-ACCESS read-only
			STATUS current
			DESCRIPTION
				"."
			::= { fkV2Dhcp4LeasedEntry 1 }

		
		-- 1.3.6.1.4.1.10428 9 1.102.6.2.5.2.1.1.2
		fkV2Dhcp4LeasedPoolIndex OBJECT-TYPE
			SYNTAX INTEGER (1..255)
			MAX-ACCESS read-only
			STATUS current
			DESCRIPTION
				"."
			::= { fkV2Dhcp4LeasedEntry 2 }

		
		-- 1.3.6.1.4.1.10428 9 1.102.6.2.5.2.1.1.3
		fkV2Dhcp4LeasedStatus OBJECT-TYPE
			SYNTAX INTEGER
				{
				fixed(1),
				offered(2),
				bound(3),
				abandon(4),
				free(5)
				}
			MAX-ACCESS read-only
			STATUS current
			DESCRIPTION
				"."
			::= { fkV2Dhcp4LeasedEntry 3 }

		
		-- 1.3.6.1.4.1.10428 9 1.102.6.2.5.2.1.1.4
		fkV2Dhcp4LeasedMac OBJECT-TYPE
			SYNTAX MacAddress
			MAX-ACCESS read-only
			STATUS current
			DESCRIPTION
				"."
			::= { fkV2Dhcp4LeasedEntry 4 }

		
		-- 1.3.6.1.4.1.10428 9 1.102.6.2.5.2.1.1.5
		fkV2Dhcp4LeasedHostName OBJECT-TYPE
			SYNTAX OCTET STRING (SIZE (0 | 1..64))
			MAX-ACCESS read-only
			STATUS current
			DESCRIPTION
				"."
			::= { fkV2Dhcp4LeasedEntry 5 }

		
		-- 1.3.6.1.4.1.10428 9 1.102.6.2.5.2.1.1.6
		fkV2Dhcp4LeasedClientId OBJECT-TYPE
			SYNTAX OCTET STRING (SIZE (0 | 1..64))
			MAX-ACCESS read-only
			STATUS current
			DESCRIPTION
				"."
			::= { fkV2Dhcp4LeasedEntry 6 }

		
		-- 1.3.6.1.4.1.10428 9 1.102.6.2.5.2.1.1.7
		fkV2Dhcp4LeasedRemoteId OBJECT-TYPE
			SYNTAX OCTET STRING (SIZE (0 | 1..32))
			MAX-ACCESS read-only
			STATUS current
			DESCRIPTION
				"."
			::= { fkV2Dhcp4LeasedEntry 7 }

		
		-- 1.3.6.1.4.1.10428 9 1.102.6.2.5.2.1.1.8
		fkV2Dhcp4LeasedCircuitId OBJECT-TYPE
			SYNTAX OCTET STRING (SIZE (0 | 1..32))
			MAX-ACCESS read-only
			STATUS current
			DESCRIPTION
				"."
			::= { fkV2Dhcp4LeasedEntry 8 }

		
		-- 1.3.6.1.4.1.10428 9 1.102.6.2.5.2.1.1.9
		fkV2Dhcp4LeasedStartTime OBJECT-TYPE
			SYNTAX Unsigned32
			UNITS "second"
			MAX-ACCESS read-only
			STATUS current
			DESCRIPTION
				"시작시간: 단위는 1970.1.1일 0시 0분 0초부터 계산한 초"
			::= { fkV2Dhcp4LeasedEntry 9 }

		
		-- 1.3.6.1.4.1.10428 9 1.102.6.2.5.2.1.1.10
		fkV2Dhcp4LeasedFinishTime OBJECT-TYPE
			SYNTAX Unsigned32
			UNITS "second"
			MAX-ACCESS read-only
			STATUS current
			DESCRIPTION
				"Description."
			::= { fkV2Dhcp4LeasedEntry 10 }

		
		-- 1.3.6.1.4.1.10428 9 1.102.6.2.5.2.2
		fkV2Dhcp4LeasedControl OBJECT IDENTIFIER ::= { fkV2Dhcp4Leased 2 }

		
		-- 1.3.6.1.4.1.10428 9 1.102.6.2.5.2.2.1
		fkV2Dhcp4LeasedControlRequest OBJECT-TYPE
			SYNTAX INTEGER
				{
				clearDhcpLeasedAddress(1),
				clearDhcpLeaseNetwork(2),
				clearDhcpLeasePool(3),
				clearDhcpLeaseAll(4)
				}
			MAX-ACCESS read-write
			STATUS current
			DESCRIPTION
				"The request of a user command."
			::= { fkV2Dhcp4LeasedControl 1 }

		
		-- 1.3.6.1.4.1.10428 9 1.102.6.2.5.2.2.2
		fkV2Dhcp4LeasedControlStatus OBJECT-TYPE
			SYNTAX FkControlStatusType
			MAX-ACCESS read-only
			STATUS current
			DESCRIPTION
				"The status of a user command."
			::= { fkV2Dhcp4LeasedControl 2 }

		
		-- 1.3.6.1.4.1.10428 9 1.102.6.2.5.2.2.3
		fkV2Dhcp4LeasedControlTimer OBJECT-TYPE
			SYNTAX Gauge32
			MAX-ACCESS read-write
			STATUS current
			DESCRIPTION
				"The maximum wait Time for the manager for a long running user command."
			::= { fkV2Dhcp4LeasedControl 3 }

		
		-- 1.3.6.1.4.1.10428 9 1.102.6.2.5.2.2.4
		fkV2Dhcp4LeasedControlTimeStamp OBJECT-TYPE
			SYNTAX TimeTicks
			MAX-ACCESS read-only
			STATUS current
			DESCRIPTION
				"The Time stamp of the last command (end of command)."
			::= { fkV2Dhcp4LeasedControl 4 }

		
		-- 1.3.6.1.4.1.10428 9 1.102.6.2.5.2.2.5
		fkV2Dhcp4LeasedControlReqResult OBJECT-TYPE
			SYNTAX FkControlRequestResultType
			MAX-ACCESS read-only
			STATUS current
			DESCRIPTION
				"The result of the last user command."
			::= { fkV2Dhcp4LeasedControl 5 }

		
		-- 1.3.6.1.4.1.10428 9 1.102.6.2.5.2.2.6
		fkV2Dhcp4LeasedControlAddress OBJECT-TYPE
			SYNTAX IpAddress
			MAX-ACCESS read-write
			STATUS current
			DESCRIPTION
				"."
			::= { fkV2Dhcp4LeasedControl 6 }

		
		-- 1.3.6.1.4.1.10428 9 1.102.6.2.5.2.2.7
		fkV2Dhcp4LeasedControlMask OBJECT-TYPE
			SYNTAX INTEGER (1..32)
			MAX-ACCESS read-only
			STATUS current
			DESCRIPTION
				"The result of the last user command."
			::= { fkV2Dhcp4LeasedControl 7 }

		
		-- 1.3.6.1.4.1.10428 9 1.102.6.2.5.2.2.8
		fkV2Dhcp4LeasedControlPoolIndex OBJECT-TYPE
			SYNTAX INTEGER (1..255)
			MAX-ACCESS read-write
			STATUS current
			DESCRIPTION
				"."
			::= { fkV2Dhcp4LeasedControl 8 }

		
		-- 1.3.6.1.4.1.10428 9 1.102.6.2.5.2.3
		fkV2Dhcp4LeasedNotification OBJECT IDENTIFIER ::= { fkV2Dhcp4Leased 3 }

		
		-- 1.3.6.1.4.1.10428 9 1.102.6.2.5.2.3.1
		fkV2Dhcp4LeasedAddressCleared NOTIFICATION-TYPE
			OBJECTS { fkV2Dhcp4LeasedControlRequest, fkV2Dhcp4LeasedControlTimeStamp, fkV2Dhcp4LeasedControlReqResult, fkV2Dhcp4LeasedControlAddress }
			STATUS current
			DESCRIPTION 
				"Description."
			::= { fkV2Dhcp4LeasedNotification 1 }

		
		-- 1.3.6.1.4.1.10428 9 1.102.6.2.5.2.3.2
		fkV2Dhcp4LeasedNetworkCleared NOTIFICATION-TYPE
			OBJECTS { fkV2Dhcp4LeasedControlRequest, fkV2Dhcp4LeasedControlTimeStamp, fkV2Dhcp4LeasedControlReqResult, fkV2Dhcp4LeasedControlAddress, fkV2Dhcp4LeasedControlMask
				 }
			STATUS current
			DESCRIPTION 
				"Description."
			::= { fkV2Dhcp4LeasedNotification 2 }

		
		-- 1.3.6.1.4.1.10428 9 1.102.6.2.5.2.3.3
		fkV2Dhcp4LeasedPoolCleared NOTIFICATION-TYPE
			OBJECTS { fkV2Dhcp4LeasedControlRequest, fkV2Dhcp4LeasedControlTimeStamp, fkV2Dhcp4LeasedControlReqResult, fkV2Dhcp4LeasedControlPoolIndex }
			STATUS current
			DESCRIPTION 
				"Description."
			::= { fkV2Dhcp4LeasedNotification 3 }

		
		-- 1.3.6.1.4.1.10428 9 1.102.6.2.5.2.3.4
		fkV2Dhcp4LeasedAllCleared NOTIFICATION-TYPE
			OBJECTS { fkV2Dhcp4LeasedControlRequest, fkV2Dhcp4LeasedControlTimeStamp, fkV2Dhcp4LeasedControlReqResult }
			STATUS current
			DESCRIPTION 
				"Description."
			::= { fkV2Dhcp4LeasedNotification 4 }

		
		-- 1.3.6.1.4.1.10428 9 1.102.6.2.5.3
		fkV2Dhcp4PacketStatsPort OBJECT IDENTIFIER ::= { fkV2Dhcp4Stats 3 }

		
		-- 1.3.6.1.4.1.10428 9 1.102.6.2.5.3.1
		fkV2Dhcp4PacketStatsPortTable OBJECT-TYPE
			SYNTAX SEQUENCE OF FkV2Dhcp4PacketStatsPortEntry
			MAX-ACCESS not-accessible
			STATUS current
			DESCRIPTION
				"Description."
			::= { fkV2Dhcp4PacketStatsPort 1 }

		
		-- 1.3.6.1.4.1.10428 9 1.102.6.2.5.3.1.1
		fkV2Dhcp4PacketStatsPortEntry OBJECT-TYPE
			SYNTAX FkV2Dhcp4PacketStatsPortEntry
			MAX-ACCESS not-accessible
			STATUS current
			DESCRIPTION
				"Description."
			INDEX { fkV2Dhcp4PacketStatsPortIndex }
			::= { fkV2Dhcp4PacketStatsPortTable 1 }

		
		FkV2Dhcp4PacketStatsPortEntry ::=
			SEQUENCE { 
				fkV2Dhcp4PacketStatsPortIndex
					InterfaceIndex,
				fkV2Dhcp4PacketStatsPortReceived
					Counter32,
				fkV2Dhcp4PacketStatsPortSent
					Counter32,
				fkV2Dhcp4PacketStatsPortReceivedError
					Counter32,
				fkV2Dhcp4PacketStatsPortSentError
					Counter32,
				fkV2Dhcp4PacketStatsPortReceivedDiscover
					Counter32,
				fkV2Dhcp4PacketStatsPortReceivedRequest
					Counter32,
				fkV2Dhcp4PacketStatsPortReceivedRelease
					Counter32,
				fkV2Dhcp4PacketStatsPortReceivedInform
					Counter32,
				fkV2Dhcp4PacketStatsPortReceivedDecline
					Counter32,
				fkV2Dhcp4PacketStatsPortSentOffer
					Counter32,
				fkV2Dhcp4PacketStatsPortSentAck
					Counter32,
				fkV2Dhcp4PacketStatsPortSentNak
					Counter32
			 }

		-- 1.3.6.1.4.1.10428 9 1.102.6.2.5.3.1.1.1
		fkV2Dhcp4PacketStatsPortIndex OBJECT-TYPE
			SYNTAX InterfaceIndex
			MAX-ACCESS read-only
			STATUS current
			DESCRIPTION
				"Description."
			::= { fkV2Dhcp4PacketStatsPortEntry 1 }

		
		-- 1.3.6.1.4.1.10428 9 1.102.6.2.5.3.1.1.2
		fkV2Dhcp4PacketStatsPortReceived OBJECT-TYPE
			SYNTAX Counter32
			MAX-ACCESS read-only
			STATUS current
			DESCRIPTION
				"Description."
			::= { fkV2Dhcp4PacketStatsPortEntry 2 }

		
		-- 1.3.6.1.4.1.10428 9 1.102.6.2.5.3.1.1.3
		fkV2Dhcp4PacketStatsPortSent OBJECT-TYPE
			SYNTAX Counter32
			MAX-ACCESS read-only
			STATUS current
			DESCRIPTION
				"Description."
			::= { fkV2Dhcp4PacketStatsPortEntry 3 }

		
		-- 1.3.6.1.4.1.10428 9 1.102.6.2.5.3.1.1.4
		fkV2Dhcp4PacketStatsPortReceivedError OBJECT-TYPE
			SYNTAX Counter32
			MAX-ACCESS read-only
			STATUS current
			DESCRIPTION
				"Description."
			::= { fkV2Dhcp4PacketStatsPortEntry 4 }

		
		-- 1.3.6.1.4.1.10428 9 1.102.6.2.5.3.1.1.5
		fkV2Dhcp4PacketStatsPortSentError OBJECT-TYPE
			SYNTAX Counter32
			MAX-ACCESS read-only
			STATUS current
			DESCRIPTION
				"Description."
			::= { fkV2Dhcp4PacketStatsPortEntry 5 }

		
		-- 1.3.6.1.4.1.10428 9 1.102.6.2.5.3.1.1.6
		fkV2Dhcp4PacketStatsPortReceivedDiscover OBJECT-TYPE
			SYNTAX Counter32
			MAX-ACCESS read-only
			STATUS current
			DESCRIPTION
				"Description."
			::= { fkV2Dhcp4PacketStatsPortEntry 6 }

		
		-- 1.3.6.1.4.1.10428 9 1.102.6.2.5.3.1.1.7
		fkV2Dhcp4PacketStatsPortReceivedRequest OBJECT-TYPE
			SYNTAX Counter32
			MAX-ACCESS read-only
			STATUS current
			DESCRIPTION
				"Description."
			::= { fkV2Dhcp4PacketStatsPortEntry 7 }

		
		-- 1.3.6.1.4.1.10428 9 1.102.6.2.5.3.1.1.8
		fkV2Dhcp4PacketStatsPortReceivedRelease OBJECT-TYPE
			SYNTAX Counter32
			MAX-ACCESS read-only
			STATUS current
			DESCRIPTION
				"Description."
			::= { fkV2Dhcp4PacketStatsPortEntry 8 }

		
		-- 1.3.6.1.4.1.10428 9 1.102.6.2.5.3.1.1.9
		fkV2Dhcp4PacketStatsPortReceivedInform OBJECT-TYPE
			SYNTAX Counter32
			MAX-ACCESS read-only
			STATUS current
			DESCRIPTION
				"Description."
			::= { fkV2Dhcp4PacketStatsPortEntry 9 }

		
		-- 1.3.6.1.4.1.10428 9 1.102.6.2.5.3.1.1.10
		fkV2Dhcp4PacketStatsPortReceivedDecline OBJECT-TYPE
			SYNTAX Counter32
			MAX-ACCESS read-only
			STATUS current
			DESCRIPTION
				"Description."
			::= { fkV2Dhcp4PacketStatsPortEntry 10 }

		
		-- 1.3.6.1.4.1.10428 9 1.102.6.2.5.3.1.1.11
		fkV2Dhcp4PacketStatsPortSentOffer OBJECT-TYPE
			SYNTAX Counter32
			MAX-ACCESS read-only
			STATUS current
			DESCRIPTION
				"Description."
			::= { fkV2Dhcp4PacketStatsPortEntry 11 }

		
		-- 1.3.6.1.4.1.10428 9 1.102.6.2.5.3.1.1.12
		fkV2Dhcp4PacketStatsPortSentAck OBJECT-TYPE
			SYNTAX Counter32
			MAX-ACCESS read-only
			STATUS current
			DESCRIPTION
				"Description."
			::= { fkV2Dhcp4PacketStatsPortEntry 12 }

		
		-- 1.3.6.1.4.1.10428 9 1.102.6.2.5.3.1.1.13
		fkV2Dhcp4PacketStatsPortSentNak OBJECT-TYPE
			SYNTAX Counter32
			MAX-ACCESS read-only
			STATUS current
			DESCRIPTION
				"Description."
			::= { fkV2Dhcp4PacketStatsPortEntry 13 }

		
		-- 1.3.6.1.4.1.10428 9 1.102.6.2.5.4
		fkV2Dhcp4State OBJECT IDENTIFIER ::= { fkV2Dhcp4Stats 4 }

		
		-- 1.3.6.1.4.1.10428 9 1.102.6.2.5.4.1
		fkV2Dhcp4StateTable OBJECT-TYPE
			SYNTAX SEQUENCE OF FkV2Dhcp4StateEntry
			MAX-ACCESS not-accessible
			STATUS current
			DESCRIPTION
				"Description."
			::= { fkV2Dhcp4State 1 }

		
		-- 1.3.6.1.4.1.10428 9 1.102.6.2.5.4.1.1
		fkV2Dhcp4StateEntry OBJECT-TYPE
			SYNTAX FkV2Dhcp4StateEntry
			MAX-ACCESS not-accessible
			STATUS current
			DESCRIPTION
				"Description."
			INDEX { fkV2Dhcp4StateIndex }
			::= { fkV2Dhcp4StateTable 1 }

		
		FkV2Dhcp4StateEntry ::=
			SEQUENCE { 
				fkV2Dhcp4StateIndex
					INTEGER,
				fkV2Dhcp4StateTotal
					Unsigned32,
				fkV2Dhcp4StateFixed
					Unsigned32,
				fkV2Dhcp4StateDynamic
					Unsigned32,
				fkV2Dhcp4StatePEntry
					Unsigned32
			 }

		-- 1.3.6.1.4.1.10428 9 1.102.6.2.5.4.1.1.1
		fkV2Dhcp4StateIndex OBJECT-TYPE
			SYNTAX INTEGER
				{
				bound(1),
				offer(2),
				abandon(3),
				free(4)
				}
			MAX-ACCESS read-only
			STATUS current
			DESCRIPTION
				"Description."
			::= { fkV2Dhcp4StateEntry 1 }

		
		-- 1.3.6.1.4.1.10428 9 1.102.6.2.5.4.1.1.2
		fkV2Dhcp4StateTotal OBJECT-TYPE
			SYNTAX Unsigned32
			MAX-ACCESS read-only
			STATUS current
			DESCRIPTION
				"Description."
			::= { fkV2Dhcp4StateEntry 2 }

		
		-- 1.3.6.1.4.1.10428 9 1.102.6.2.5.4.1.1.3
		fkV2Dhcp4StateFixed OBJECT-TYPE
			SYNTAX Unsigned32
			MAX-ACCESS read-only
			STATUS current
			DESCRIPTION
				"Description."
			::= { fkV2Dhcp4StateEntry 3 }

		
		-- 1.3.6.1.4.1.10428 9 1.102.6.2.5.4.1.1.4
		fkV2Dhcp4StateDynamic OBJECT-TYPE
			SYNTAX Unsigned32
			MAX-ACCESS read-only
			STATUS current
			DESCRIPTION
				"Description."
			::= { fkV2Dhcp4StateEntry 4 }

		
		-- 1.3.6.1.4.1.10428 9 1.102.6.2.5.4.1.1.5
		fkV2Dhcp4StatePEntry OBJECT-TYPE
			SYNTAX Unsigned32
			MAX-ACCESS read-only
			STATUS current
			DESCRIPTION
				"Description."
			::= { fkV2Dhcp4StateEntry 5 }

		
		-- 1.3.6.1.4.1.10428 9 1.102.6.2.5.4.2
		fkV2Dhcp4StatePoolTable OBJECT-TYPE
			SYNTAX SEQUENCE OF FkV2Dhcp4StatePoolEntry
			MAX-ACCESS not-accessible
			STATUS current
			DESCRIPTION
				"Description."
			::= { fkV2Dhcp4State 2 }

		
		-- 1.3.6.1.4.1.10428 9 1.102.6.2.5.4.2.1
		fkV2Dhcp4StatePoolEntry OBJECT-TYPE
			SYNTAX FkV2Dhcp4StatePoolEntry
			MAX-ACCESS not-accessible
			STATUS current
			DESCRIPTION
				"Description."
			INDEX { fkV2Dhcp4PoolIndex, fkV2Dhcp4StateIndex }
			::= { fkV2Dhcp4StatePoolTable 1 }

		
		FkV2Dhcp4StatePoolEntry ::=
			SEQUENCE { 
				fkV2Dhcp4StatePoolTotal
					Unsigned32,
				fkV2Dhcp4StatePoolFixed
					Unsigned32,
				fkV2Dhcp4StatePoolDynamic
					Unsigned32,
				fkV2Dhcp4StatePoolPEntry
					Unsigned32
			 }

		-- 1.3.6.1.4.1.10428 9 1.102.6.2.5.4.2.1.1
		fkV2Dhcp4StatePoolTotal OBJECT-TYPE
			SYNTAX Unsigned32
			MAX-ACCESS read-only
			STATUS current
			DESCRIPTION
				"Description."
			::= { fkV2Dhcp4StatePoolEntry 1 }

		
		-- 1.3.6.1.4.1.10428 9 1.102.6.2.5.4.2.1.2
		fkV2Dhcp4StatePoolFixed OBJECT-TYPE
			SYNTAX Unsigned32
			MAX-ACCESS read-only
			STATUS current
			DESCRIPTION
				"Description."
			::= { fkV2Dhcp4StatePoolEntry 2 }

		
		-- 1.3.6.1.4.1.10428 9 1.102.6.2.5.4.2.1.3
		fkV2Dhcp4StatePoolDynamic OBJECT-TYPE
			SYNTAX Unsigned32
			MAX-ACCESS read-only
			STATUS current
			DESCRIPTION
				"Description."
			::= { fkV2Dhcp4StatePoolEntry 3 }

		
		-- 1.3.6.1.4.1.10428 9 1.102.6.2.5.4.2.1.4
		fkV2Dhcp4StatePoolPEntry OBJECT-TYPE
			SYNTAX Unsigned32
			MAX-ACCESS read-only
			STATUS current
			DESCRIPTION
				"Description."
			::= { fkV2Dhcp4StatePoolEntry 4 }

		
		-- 1.3.6.1.4.1.10428 9 1.102.6.2.5.4.3
		fkV2Dhcp4StateBindTable OBJECT-TYPE
			SYNTAX SEQUENCE OF FkV2Dhcp4StateBindEntry
			MAX-ACCESS not-accessible
			STATUS current
			DESCRIPTION
				"Description."
			::= { fkV2Dhcp4State 3 }

		
		-- 1.3.6.1.4.1.10428 9 1.102.6.2.5.4.3.1
		fkV2Dhcp4StateBindEntry OBJECT-TYPE
			SYNTAX FkV2Dhcp4StateBindEntry
			MAX-ACCESS not-accessible
			STATUS current
			DESCRIPTION
				"Description."
			INDEX { fkV2Dhcp4StateBindIpAddress }
			::= { fkV2Dhcp4StateBindTable 1 }

		
		FkV2Dhcp4StateBindEntry ::=
			SEQUENCE { 
				fkV2Dhcp4StateBindIpAddress
					IpAddress,
				fkV2Dhcp4StateBindPoolIndex
					Integer32,
				fkV2Dhcp4StateBindMac
					MacAddress,
				fkV2Dhcp4StateBindState
					INTEGER,
				fkV2Dhcp4StateBindType
					INTEGER,
				fkV2Dhcp4StateBindExpiration
					OCTET STRING,
				fkV2Dhcp4StateBindPort
					Integer32
			 }

		-- 1.3.6.1.4.1.10428 9 1.102.6.2.5.4.3.1.1
		fkV2Dhcp4StateBindIpAddress OBJECT-TYPE
			SYNTAX IpAddress
			MAX-ACCESS read-only
			STATUS current
			DESCRIPTION
				"Description."
			::= { fkV2Dhcp4StateBindEntry 1 }

		
		-- 1.3.6.1.4.1.10428 9 1.102.6.2.5.4.3.1.2
		fkV2Dhcp4StateBindPoolIndex OBJECT-TYPE
			SYNTAX Integer32
			MAX-ACCESS read-write
			STATUS current
			DESCRIPTION
				"Description."
			::= { fkV2Dhcp4StateBindEntry 2 }

		
		-- 1.3.6.1.4.1.10428 9 1.102.6.2.5.4.3.1.3
		fkV2Dhcp4StateBindMac OBJECT-TYPE
			SYNTAX MacAddress
			MAX-ACCESS read-only
			STATUS current
			DESCRIPTION
				"Description."
			::= { fkV2Dhcp4StateBindEntry 3 }

		
		-- 1.3.6.1.4.1.10428 9 1.102.6.2.5.4.3.1.4
		fkV2Dhcp4StateBindState OBJECT-TYPE
			SYNTAX INTEGER
				{
				bound(1),
				offer(2),
				abandon(3),
				free(4)
				}
			MAX-ACCESS read-only
			STATUS current
			DESCRIPTION
				"Description."
			::= { fkV2Dhcp4StateBindEntry 4 }

		
		-- 1.3.6.1.4.1.10428 9 1.102.6.2.5.4.3.1.5
		fkV2Dhcp4StateBindType OBJECT-TYPE
			SYNTAX INTEGER
				{
				fixed(1),
				dynamic(2),
				portentry(3)
				}
			MAX-ACCESS read-only
			STATUS current
			DESCRIPTION
				"Description."
			::= { fkV2Dhcp4StateBindEntry 5 }

		
		-- 1.3.6.1.4.1.10428 9 1.102.6.2.5.4.3.1.6
		fkV2Dhcp4StateBindExpiration OBJECT-TYPE
			SYNTAX OCTET STRING
			MAX-ACCESS read-only
			STATUS current
			DESCRIPTION
				"Description."
			::= { fkV2Dhcp4StateBindEntry 6 }

		
		-- 1.3.6.1.4.1.10428 9 1.102.6.2.5.4.3.1.7
		fkV2Dhcp4StateBindPort OBJECT-TYPE
			SYNTAX Integer32
			MAX-ACCESS read-only
			STATUS current
			DESCRIPTION
				"Description."
			::= { fkV2Dhcp4StateBindEntry 7 }

		
		-- 1.3.6.1.4.1.10428 9 1.102.6.2.6
		fkV2Dhcp4Snooping OBJECT IDENTIFIER ::= { fkV2Dhcp4 6 }

		
		-- 1.3.6.1.4.1.10428 9 1.102.6.2.6.1
		fkV2Ds4Base OBJECT IDENTIFIER ::= { fkV2Dhcp4Snooping 1 }

		
		-- 1.3.6.1.4.1.10428 9 1.102.6.2.6.1.1
		fkV2Ds4Info OBJECT IDENTIFIER ::= { fkV2Ds4Base 1 }

		
		-- 1.3.6.1.4.1.10428 9 1.102.6.2.6.1.1.1
		fkV2Ds4Activity OBJECT-TYPE
			SYNTAX INTEGER
				{
				inactive(0),
				active(1)
				}
			MAX-ACCESS read-only
			STATUS current
			DESCRIPTION
				"This object indicates whether the DHCP Snooping feature is
				enabled at the device level."
			::= { fkV2Ds4Info 1 }

		
		-- 1.3.6.1.4.1.10428 9 1.102.6.2.6.1.1.2
		fkV2Ds4VerifyMacState OBJECT-TYPE
			SYNTAX INTEGER
				{
				disable(0),
				enable(1)
				}
			MAX-ACCESS read-only
			STATUS current
			DESCRIPTION
				"This object indicates whether the DHCP Snooping verify mac address of the untrusted port
				is enabled at the device level."
			::= { fkV2Ds4Info 2 }

		
		-- 1.3.6.1.4.1.10428 9 1.102.6.2.6.1.1.3
		fkV2Ds4DatabaseURL OBJECT-TYPE
			SYNTAX IpAddress
			MAX-ACCESS read-only
			STATUS current
			DESCRIPTION
				"This object indicates the address of server that snooping database 
				will be stored by TFTP."
			::= { fkV2Ds4Info 3 }

		
		-- 1.3.6.1.4.1.10428 9 1.102.6.2.6.1.1.4
		fkV2Ds4DatabaseInterval OBJECT-TYPE
			SYNTAX INTEGER (0 | 1..2147483637)
			MAX-ACCESS read-only
			STATUS current
			DESCRIPTION
				"This object indicates the interval time that snooping database 
				will be stored by TFTP."
			::= { fkV2Ds4Info 4 }

		
		-- 1.3.6.1.4.1.10428 9 1.102.6.2.6.1.1.5
		fkV2Ds4ArpInspectionTime OBJECT-TYPE
			SYNTAX Integer32 (0..2147483637)
			UNITS "sec"
			MAX-ACCESS read-only
			STATUS current
			DESCRIPTION
				"Description."
			DEFVAL { 1800 }
			::= { fkV2Ds4Info 5 }

		
		-- 1.3.6.1.4.1.10428 9 1.102.6.2.6.1.1.6
		fkV2Ds4LimitRateDiscover OBJECT-TYPE
			SYNTAX Integer32 (0 | 1..32767)
			MAX-ACCESS read-only
			STATUS current
			DESCRIPTION
				"The DHCP snooping limit rate discover."
			::= { fkV2Ds4Info 6 }

		
		-- 1.3.6.1.4.1.10428 9 1.102.6.2.6.1.1.7
		fkV2Ds4LimitRateRequest OBJECT-TYPE
			SYNTAX Integer32 (0 | 1..32767)
			MAX-ACCESS read-only
			STATUS current
			DESCRIPTION
				"The DHCP snooping limit rate request."
			::= { fkV2Ds4Info 7 }

		
		-- 1.3.6.1.4.1.10428 9 1.102.6.2.6.1.1.8
		fkV2Ds4InformationOption OBJECT-TYPE
			SYNTAX INTEGER
				{
				disable(0),
				enable(1)
				}
			MAX-ACCESS read-only
			STATUS current
			DESCRIPTION
				"The DCHP snooping information option."
			::= { fkV2Ds4Info 8 }

		
		-- 1.3.6.1.4.1.10428 9 1.102.6.2.6.1.2
		fkV2Ds4Control OBJECT IDENTIFIER ::= { fkV2Ds4Base 2 }

		
		-- 1.3.6.1.4.1.10428 9 1.102.6.2.6.1.2.1
		fkV2Ds4ControlRequest OBJECT-TYPE
			SYNTAX INTEGER
				{
				setDsActivity(1),
				setDsVerifyMacState(2),
				setDsDatabaseProfile(3),
				renewDsDatabase(4),
				setDsArpInspectionTime(5),
				setDsLimitRateDiscover(6),
				setDsLimitRateRequest(7),
				setDsInformationOption(8)
				}
			MAX-ACCESS read-write
			STATUS current
			DESCRIPTION
				"The request of a user command."
			::= { fkV2Ds4Control 1 }

		
		-- 1.3.6.1.4.1.10428 9 1.102.6.2.6.1.2.2
		fkV2Ds4ControlStatus OBJECT-TYPE
			SYNTAX FkControlStatusType
			MAX-ACCESS read-only
			STATUS current
			DESCRIPTION
				"The status of a user command."
			::= { fkV2Ds4Control 2 }

		
		-- 1.3.6.1.4.1.10428 9 1.102.6.2.6.1.2.3
		fkV2Ds4ControlTimer OBJECT-TYPE
			SYNTAX Gauge32
			MAX-ACCESS read-write
			STATUS current
			DESCRIPTION
				"The maximum wait time for the manager for a long running user command."
			::= { fkV2Ds4Control 3 }

		
		-- 1.3.6.1.4.1.10428 9 1.102.6.2.6.1.2.4
		fkV2Ds4ControlTimeStamp OBJECT-TYPE
			SYNTAX TimeTicks
			MAX-ACCESS read-only
			STATUS current
			DESCRIPTION
				"The time stamp of the last command (end of command)."
			::= { fkV2Ds4Control 4 }

		
		-- 1.3.6.1.4.1.10428 9 1.102.6.2.6.1.2.5
		fkV2Ds4ControlReqResult OBJECT-TYPE
			SYNTAX FkControlRequestResultType
			MAX-ACCESS read-only
			STATUS current
			DESCRIPTION
				"The result of the last user command."
			::= { fkV2Ds4Control 5 }

		
		-- 1.3.6.1.4.1.10428 9 1.102.6.2.6.1.2.6
		fkV2Ds4ControlActivity OBJECT-TYPE
			SYNTAX INTEGER
				{
				inactive(0),
				active(1)
				}
			MAX-ACCESS read-write
			STATUS current
			DESCRIPTION
				"Description."
			::= { fkV2Ds4Control 6 }

		
		-- 1.3.6.1.4.1.10428 9 1.102.6.2.6.1.2.7
		fkV2Ds4ControlVerifyMacState OBJECT-TYPE
			SYNTAX INTEGER
				{
				disable(0),
				enable(1)
				}
			MAX-ACCESS read-write
			STATUS current
			DESCRIPTION
				"Description."
			::= { fkV2Ds4Control 7 }

		
		-- 1.3.6.1.4.1.10428 9 1.102.6.2.6.1.2.8
		fkV2Ds4ControlDatabaseURL OBJECT-TYPE
			SYNTAX IpAddress
			MAX-ACCESS read-write
			STATUS current
			DESCRIPTION
				"Description."
			::= { fkV2Ds4Control 8 }

		
		-- 1.3.6.1.4.1.10428 9 1.102.6.2.6.1.2.9
		fkV2Ds4ControlDatabaseInterval OBJECT-TYPE
			SYNTAX INTEGER (0 | 1..2147483637)
			MAX-ACCESS read-write
			STATUS current
			DESCRIPTION
				"Description."
			::= { fkV2Ds4Control 9 }

		
		-- 1.3.6.1.4.1.10428 9 1.102.6.2.6.1.2.10
		fkV2Ds4ControlArpInspectionTime OBJECT-TYPE
			SYNTAX Integer32 (0..2147483637)
			UNITS "sec"
			MAX-ACCESS read-write
			STATUS current
			DESCRIPTION
				"Description."
			DEFVAL { 1800 }
			::= { fkV2Ds4Control 10 }

		
		-- 1.3.6.1.4.1.10428 9 1.102.6.2.6.1.2.11
		fkV2Ds4ControlLimitRateDiscover OBJECT-TYPE
			SYNTAX Integer32 (0 | 1..32767)
			MAX-ACCESS read-write
			STATUS current
			DESCRIPTION
				"The DHCP snooping limit rate discover. (0: delete)"
			::= { fkV2Ds4Control 11 }

		
		-- 1.3.6.1.4.1.10428 9 1.102.6.2.6.1.2.12
		fkV2Ds4ControlLimitRateRequest OBJECT-TYPE
			SYNTAX Integer32 (0 | 1..32767)
			MAX-ACCESS read-write
			STATUS current
			DESCRIPTION
				"The DHCP snooping limit rate request.  (0: delete)"
			::= { fkV2Ds4Control 12 }

		
		-- 1.3.6.1.4.1.10428 9 1.102.6.2.6.1.2.13
		fkV2Ds4ControlInformationOption OBJECT-TYPE
			SYNTAX INTEGER
				{
				disable(0),
				enable(1)
				}
			MAX-ACCESS read-write
			STATUS current
			DESCRIPTION
				"The DCHP snooping information option."
			::= { fkV2Ds4Control 13 }

		
		-- 1.3.6.1.4.1.10428 9 1.102.6.2.6.1.3
		fkV2Ds4Notification OBJECT IDENTIFIER ::= { fkV2Ds4Base 3 }

		
		-- 1.3.6.1.4.1.10428 9 1.102.6.2.6.1.3.1
		fkV2Ds4ActivityChanged NOTIFICATION-TYPE
			OBJECTS { fkV2Ds4ControlRequest, fkV2Ds4ControlTimeStamp, fkV2Ds4ControlReqResult, fkV2Ds4Activity }
			STATUS current
			DESCRIPTION 
				"Description."
			::= { fkV2Ds4Notification 1 }

		
		-- 1.3.6.1.4.1.10428 9 1.102.6.2.6.1.3.2
		fkV2Ds4VerifyMacStateChanged NOTIFICATION-TYPE
			OBJECTS { fkV2Ds4ControlRequest, fkV2Ds4ControlTimeStamp, fkV2Ds4ControlReqResult, fkV2Ds4VerifyMacState }
			STATUS current
			DESCRIPTION 
				"Description."
			::= { fkV2Ds4Notification 2 }

		
		-- 1.3.6.1.4.1.10428 9 1.102.6.2.6.1.3.3
		fkV2Ds4DatabaseProfileChanged NOTIFICATION-TYPE
			OBJECTS { fkV2Ds4ControlRequest, fkV2Ds4ControlTimeStamp, fkV2Ds4ControlReqResult, fkV2Ds4DatabaseURL, fkV2Ds4DatabaseInterval
				 }
			STATUS current
			DESCRIPTION 
				"Description."
			::= { fkV2Ds4Notification 3 }

		
		-- 1.3.6.1.4.1.10428 9 1.102.6.2.6.1.3.4
		fkV2Ds4DatabaseRenewed NOTIFICATION-TYPE
			OBJECTS { fkV2Ds4ControlRequest, fkV2Ds4ControlTimeStamp, fkV2Ds4ControlReqResult, fkV2Ds4ControlDatabaseURL }
			STATUS current
			DESCRIPTION 
				"Description."
			::= { fkV2Ds4Notification 4 }

		
		-- 1.3.6.1.4.1.10428 9 1.102.6.2.6.1.3.5
		fkV2Ds4ArpInspectionTimeChanged NOTIFICATION-TYPE
			OBJECTS { fkV2Ds4ControlRequest, fkV2Ds4ControlTimeStamp, fkV2Ds4ControlReqResult, fkV2Ds4ArpInspectionTime }
			STATUS current
			DESCRIPTION 
				"Description."
			::= { fkV2Ds4Notification 5 }

		
		-- 1.3.6.1.4.1.10428 9 1.102.6.2.6.1.3.6
		fkV2Ds4LimitRateDiscoverChanged NOTIFICATION-TYPE
			OBJECTS { fkV2Ds4ControlRequest, fkV2Ds4ControlTimeStamp, fkV2Ds4ControlReqResult, fkV2Ds4ControlLimitRateDiscover }
			STATUS current
			DESCRIPTION 
				"setDsLimitRateDiscover"
			::= { fkV2Ds4Notification 6 }

		
		-- 1.3.6.1.4.1.10428 9 1.102.6.2.6.1.3.7
		fkV2Ds4LimitRateRequestChanged NOTIFICATION-TYPE
			OBJECTS { fkV2Ds4ControlRequest, fkV2Ds4ControlTimeStamp, fkV2Ds4ControlReqResult, fkV2Ds4ControlLimitRateRequest }
			STATUS current
			DESCRIPTION 
				"setDsLimitRateRequest"
			::= { fkV2Ds4Notification 7 }

		
		-- 1.3.6.1.4.1.10428 9 1.102.6.2.6.1.3.8
		fkV2Ds4InformationOptionChanged NOTIFICATION-TYPE
			OBJECTS { fkV2Ds4ControlRequest, fkV2Ds4ControlTimeStamp, fkV2Ds4ControlReqResult, fkV2Ds4ControlInformationOption }
			STATUS current
			DESCRIPTION 
				"setDsInformationOption"
			::= { fkV2Ds4Notification 8 }

		
		-- 1.3.6.1.4.1.10428 9 1.102.6.2.6.2
		fkV2Ds4Vlan OBJECT IDENTIFIER ::= { fkV2Dhcp4Snooping 2 }

		
		-- 1.3.6.1.4.1.10428 9 1.102.6.2.6.2.1
		fkV2Ds4VlanTable OBJECT-TYPE
			SYNTAX SEQUENCE OF FkV2Ds4VlanEntry
			MAX-ACCESS not-accessible
			STATUS current
			DESCRIPTION
				"A table provides the mechanism to control DHCP Snooping 
				per VLAN. When a VLAN is created in a device supporting this
				table, a corresponding entry of this table will be added."
			::= { fkV2Ds4Vlan 1 }

		
		-- 1.3.6.1.4.1.10428 9 1.102.6.2.6.2.1.1
		fkV2Ds4VlanEntry OBJECT-TYPE
			SYNTAX FkV2Ds4VlanEntry
			MAX-ACCESS not-accessible
			STATUS current
			DESCRIPTION
				"A row instance contains the configuration to enable
				or disable DHCP Snooping at each existing VLAN."
			INDEX { fkV2Ds4VlanIndex }
			::= { fkV2Ds4VlanTable 1 }

		
		FkV2Ds4VlanEntry ::=
			SEQUENCE { 
				fkV2Ds4VlanIndex
					INTEGER,
				fkV2Ds4VlanState
					INTEGER
			 }

		-- 1.3.6.1.4.1.10428 9 1.102.6.2.6.2.1.1.1
		fkV2Ds4VlanIndex OBJECT-TYPE
			SYNTAX INTEGER (1..4094)
			MAX-ACCESS read-only
			STATUS current
			DESCRIPTION
				"This object indicates the VLAN number on which DHCP Snooping 
				feature is configured."
			::= { fkV2Ds4VlanEntry 1 }

		
		-- 1.3.6.1.4.1.10428 9 1.102.6.2.6.2.1.1.2
		fkV2Ds4VlanState OBJECT-TYPE
			SYNTAX INTEGER
				{
				disable(0),
				enable(1)
				}
			MAX-ACCESS read-only
			STATUS current
			DESCRIPTION
				"This object indicates whether DHCP Snooping is enabled in
				this VLAN. 
				
				If this object is set to 'true', DHCP Snooping is enabled. 
				
				If this object is set to 'false', DHCP Snooping is disabled."
			::= { fkV2Ds4VlanEntry 2 }

		
		-- 1.3.6.1.4.1.10428 9 1.102.6.2.6.2.2
		fkV2Ds4VlanControl OBJECT IDENTIFIER ::= { fkV2Ds4Vlan 2 }

		
		-- 1.3.6.1.4.1.10428 9 1.102.6.2.6.2.2.1
		fkV2Ds4VlanControlRequest OBJECT-TYPE
			SYNTAX INTEGER { setDsVlanState(1) }
			MAX-ACCESS read-write
			STATUS current
			DESCRIPTION
				"The request of a user command."
			::= { fkV2Ds4VlanControl 1 }

		
		-- 1.3.6.1.4.1.10428 9 1.102.6.2.6.2.2.2
		fkV2Ds4VlanControlStatus OBJECT-TYPE
			SYNTAX FkControlStatusType
			MAX-ACCESS read-only
			STATUS current
			DESCRIPTION
				"The status of a user command."
			::= { fkV2Ds4VlanControl 2 }

		
		-- 1.3.6.1.4.1.10428 9 1.102.6.2.6.2.2.3
		fkV2Ds4VlanControlTimer OBJECT-TYPE
			SYNTAX Gauge32
			MAX-ACCESS read-write
			STATUS current
			DESCRIPTION
				"The maximum wait time for the manager for a long running user command."
			::= { fkV2Ds4VlanControl 3 }

		
		-- 1.3.6.1.4.1.10428 9 1.102.6.2.6.2.2.4
		fkV2Ds4VlanControlTimeStamp OBJECT-TYPE
			SYNTAX TimeTicks
			MAX-ACCESS read-only
			STATUS current
			DESCRIPTION
				"The time stamp of the last command (end of command)."
			::= { fkV2Ds4VlanControl 4 }

		
		-- 1.3.6.1.4.1.10428 9 1.102.6.2.6.2.2.5
		fkV2Ds4VlanControlReqResult OBJECT-TYPE
			SYNTAX FkControlRequestResultType
			MAX-ACCESS read-only
			STATUS current
			DESCRIPTION
				"The result of the last user command."
			::= { fkV2Ds4VlanControl 5 }

		
		-- 1.3.6.1.4.1.10428 9 1.102.6.2.6.2.2.6
		fkV2Ds4VlanControlIndex OBJECT-TYPE
			SYNTAX INTEGER (1..4094)
			MAX-ACCESS read-write
			STATUS current
			DESCRIPTION
				"The vlan index of dhcp snooping."
			::= { fkV2Ds4VlanControl 6 }

		
		-- 1.3.6.1.4.1.10428 9 1.102.6.2.6.2.2.7
		fkV2Ds4VlanControlState OBJECT-TYPE
			SYNTAX INTEGER
				{
				disable(0),
				enable(1)
				}
			MAX-ACCESS read-write
			STATUS current
			DESCRIPTION
				"The Dhcp snooping status of Vlan."
			::= { fkV2Ds4VlanControl 7 }

		
		-- 1.3.6.1.4.1.10428 9 1.102.6.2.6.2.3
		fkV2Ds4VlanNotification OBJECT IDENTIFIER ::= { fkV2Ds4Vlan 3 }

		
		-- 1.3.6.1.4.1.10428 9 1.102.6.2.6.2.3.1
		fkV2Ds4VlanStateChanged NOTIFICATION-TYPE
			OBJECTS { fkV2Ds4VlanControlRequest, fkV2Ds4VlanControlTimeStamp, fkV2Ds4VlanControlReqResult, fkV2Ds4VlanState }
			STATUS current
			DESCRIPTION 
				"Description."
			::= { fkV2Ds4VlanNotification 1 }

		
		-- 1.3.6.1.4.1.10428 9 1.102.6.2.6.3
		fkV2Ds4Port OBJECT IDENTIFIER ::= { fkV2Dhcp4Snooping 3 }

		
		-- 1.3.6.1.4.1.10428 9 1.102.6.2.6.3.1
		fkV2Ds4PortTable OBJECT-TYPE
			SYNTAX SEQUENCE OF FkV2Ds4PortEntry
			MAX-ACCESS not-accessible
			STATUS current
			DESCRIPTION
				"Description."
			::= { fkV2Ds4Port 1 }

		
		-- 1.3.6.1.4.1.10428 9 1.102.6.2.6.3.1.1
		fkV2Ds4PortEntry OBJECT-TYPE
			SYNTAX FkV2Ds4PortEntry
			MAX-ACCESS not-accessible
			STATUS current
			DESCRIPTION
				"A row instance contains the configuration to enable
				or disable trust state for DHCP Snooping at each physical
				interface capable of this feature."
			INDEX { fkV2Ds4PortIndex }
			::= { fkV2Ds4PortTable 1 }

		
		FkV2Ds4PortEntry ::=
			SEQUENCE { 
				fkV2Ds4PortIndex
					INTEGER,
				fkV2Ds4PortTrustState
					INTEGER,
				fkV2Ds4PortLimitRate
					INTEGER,
				fkV2Ds4PortLimitLease
					INTEGER,
				fkV2Ds4PortSrcGuardState
					INTEGER,
				fkV2Ds4PortTimeout
					INTEGER,
				fkV2Ds4PortStatus
					INTEGER,
				fkV2Ds4PortFilterMode
					INTEGER,
				fkV2Ds4PortFilterDelayTimer
					INTEGER,
				fkV2Ds4PortFilterDelayCounter
					INTEGER
			 }

		-- 1.3.6.1.4.1.10428 9 1.102.6.2.6.3.1.1.1
		fkV2Ds4PortIndex OBJECT-TYPE
			SYNTAX INTEGER (1..255)
			MAX-ACCESS read-only
			STATUS current
			DESCRIPTION
				"Description."
			::= { fkV2Ds4PortEntry 1 }

		
		-- 1.3.6.1.4.1.10428 9 1.102.6.2.6.3.1.1.2
		fkV2Ds4PortTrustState OBJECT-TYPE
			SYNTAX INTEGER
				{
				disable(0),
				enable(1)
				}
			MAX-ACCESS read-only
			STATUS current
			DESCRIPTION
				"This object indicates whether the interface is trusted for
				DHCP Snooping purpose. 
				
				If this object is set to 'true', the interface is trusted.
				DHCP packets coming to this interface will be forwarded
				without checking.
				
				If this object is set to 'false', the interface is not
				trusted. DHCP packets coming to this interface will be
				subjected to DHCP checks."
			::= { fkV2Ds4PortEntry 2 }

		
		-- 1.3.6.1.4.1.10428 9 1.102.6.2.6.3.1.1.3
		fkV2Ds4PortLimitRate OBJECT-TYPE
			SYNTAX INTEGER (0 | 1..255)
			MAX-ACCESS read-only
			STATUS current
			DESCRIPTION
				"."
			::= { fkV2Ds4PortEntry 3 }

		
		-- 1.3.6.1.4.1.10428 9 1.102.6.2.6.3.1.1.4
		fkV2Ds4PortLimitLease OBJECT-TYPE
			SYNTAX INTEGER (0 | 1..2147483637)
			MAX-ACCESS read-only
			STATUS current
			DESCRIPTION
				"."
			::= { fkV2Ds4PortEntry 4 }

		
		-- 1.3.6.1.4.1.10428 9 1.102.6.2.6.3.1.1.5
		fkV2Ds4PortSrcGuardState OBJECT-TYPE
			SYNTAX INTEGER
				{
				disable(0),
				ipEnable(1),
				ipMacEnable(2)
				}
			MAX-ACCESS read-only
			STATUS current
			DESCRIPTION
				"."
			::= { fkV2Ds4PortEntry 5 }

		
		-- 1.3.6.1.4.1.10428 9 1.102.6.2.6.3.1.1.6
		fkV2Ds4PortTimeout OBJECT-TYPE
			SYNTAX INTEGER (0 | 120..2147483637)
			MAX-ACCESS read-only
			STATUS current
			DESCRIPTION
				"DHCP Snooping Timeout"
			::= { fkV2Ds4PortEntry 6 }

		
		-- 1.3.6.1.4.1.10428 9 1.102.6.2.6.3.1.1.7
		fkV2Ds4PortStatus OBJECT-TYPE
			SYNTAX INTEGER
				{
				enable(1),
				diable(2)
				}
			MAX-ACCESS read-only
			STATUS current
			DESCRIPTION
				"Description."
			::= { fkV2Ds4PortEntry 7 }

		
		-- 1.3.6.1.4.1.10428 9 1.102.6.2.6.3.1.1.8
		fkV2Ds4PortFilterMode OBJECT-TYPE
			SYNTAX INTEGER
				{
				disable(0),
				permit(1),
				bypass(2),
				filter(3)
				}
			MAX-ACCESS read-only
			STATUS current
			DESCRIPTION
				"Description."
			::= { fkV2Ds4PortEntry 8 }

		
		-- 1.3.6.1.4.1.10428 9 1.102.6.2.6.3.1.1.9
		fkV2Ds4PortFilterDelayTimer OBJECT-TYPE
			SYNTAX INTEGER (-1 | 1..2147483637)
			MAX-ACCESS read-only
			STATUS current
			DESCRIPTION
				"Description."
			::= { fkV2Ds4PortEntry 9 }

		
		-- 1.3.6.1.4.1.10428 9 1.102.6.2.6.3.1.1.10
		fkV2Ds4PortFilterDelayCounter OBJECT-TYPE
			SYNTAX INTEGER (-1 | 1..2147483637)
			MAX-ACCESS read-only
			STATUS current
			DESCRIPTION
				"Description."
			::= { fkV2Ds4PortEntry 10 }

		
		-- 1.3.6.1.4.1.10428 9 1.102.6.2.6.3.2
		fkV2Ds4PortControl OBJECT IDENTIFIER ::= { fkV2Ds4Port 2 }

		
		-- 1.3.6.1.4.1.10428 9 1.102.6.2.6.3.2.1
		fkV2Ds4PortControlRequest OBJECT-TYPE
			SYNTAX INTEGER
				{
				setDsPortTrustState(1),
				setDsPortLimitProfile(2),
				setDsPortSrcGuardState(3),
				setDsPortTimeout(4),
				setDsPortStatus(5),
				setDsPortFilterMode(6),
				setDsPortFilterDelay(7)
				}
			MAX-ACCESS read-write
			STATUS current
			DESCRIPTION
				"The request of a user command."
			::= { fkV2Ds4PortControl 1 }

		
		-- 1.3.6.1.4.1.10428 9 1.102.6.2.6.3.2.2
		fkV2Ds4PortControlStatus OBJECT-TYPE
			SYNTAX FkControlStatusType
			MAX-ACCESS read-only
			STATUS current
			DESCRIPTION
				"The status of a user command."
			::= { fkV2Ds4PortControl 2 }

		
		-- 1.3.6.1.4.1.10428 9 1.102.6.2.6.3.2.3
		fkV2Ds4PortControlTimer OBJECT-TYPE
			SYNTAX Gauge32
			MAX-ACCESS read-write
			STATUS current
			DESCRIPTION
				"The maximum wait time for the manager for a long running user command."
			::= { fkV2Ds4PortControl 3 }

		
		-- 1.3.6.1.4.1.10428 9 1.102.6.2.6.3.2.4
		fkV2Ds4PortControlTimeStamp OBJECT-TYPE
			SYNTAX TimeTicks
			MAX-ACCESS read-only
			STATUS current
			DESCRIPTION
				"The time stamp of the last command (end of command)."
			::= { fkV2Ds4PortControl 4 }

		
		-- 1.3.6.1.4.1.10428 9 1.102.6.2.6.3.2.5
		fkV2Ds4PortControlReqResult OBJECT-TYPE
			SYNTAX FkControlRequestResultType
			MAX-ACCESS read-only
			STATUS current
			DESCRIPTION
				"The result of the last user command."
			::= { fkV2Ds4PortControl 5 }

		
		-- 1.3.6.1.4.1.10428 9 1.102.6.2.6.3.2.6
		fkV2Ds4PortControlIndex OBJECT-TYPE
			SYNTAX INTEGER (1..255)
			MAX-ACCESS read-write
			STATUS current
			DESCRIPTION
				"."
			::= { fkV2Ds4PortControl 6 }

		
		-- 1.3.6.1.4.1.10428 9 1.102.6.2.6.3.2.7
		fkV2Ds4PortControlTrustState OBJECT-TYPE
			SYNTAX INTEGER
				{
				disable(0),
				enable(1)
				}
			MAX-ACCESS read-write
			STATUS current
			DESCRIPTION
				"."
			::= { fkV2Ds4PortControl 7 }

		
		-- 1.3.6.1.4.1.10428 9 1.102.6.2.6.3.2.8
		fkV2Ds4PortControlLimitRate OBJECT-TYPE
			SYNTAX INTEGER (0 | 1..255)
			MAX-ACCESS read-write
			STATUS current
			DESCRIPTION
				"."
			::= { fkV2Ds4PortControl 8 }

		
		-- 1.3.6.1.4.1.10428 9 1.102.6.2.6.3.2.9
		fkV2Ds4PortControlLimitLease OBJECT-TYPE
			SYNTAX INTEGER (0 | 1..2147483637)
			MAX-ACCESS read-write
			STATUS current
			DESCRIPTION
				"."
			::= { fkV2Ds4PortControl 9 }

		
		-- 1.3.6.1.4.1.10428 9 1.102.6.2.6.3.2.10
		fkV2Ds4PortControlSrcGuardState OBJECT-TYPE
			SYNTAX INTEGER
				{
				disable(0),
				ipEnable(1),
				ipMacEnable(2)
				}
			MAX-ACCESS read-write
			STATUS current
			DESCRIPTION
				"."
			::= { fkV2Ds4PortControl 10 }

		
		-- 1.3.6.1.4.1.10428 9 1.102.6.2.6.3.2.11
		fkV2Ds4PortControlTimeout OBJECT-TYPE
			SYNTAX INTEGER (0 | 120..2147483637)
			MAX-ACCESS read-write
			STATUS current
			DESCRIPTION
				"DHCP Snooping Timeout"
			::= { fkV2Ds4PortControl 11 }

		
		-- 1.3.6.1.4.1.10428 9 1.102.6.2.6.3.2.12
		fkV2Ds4PortControlPStatus OBJECT-TYPE
			SYNTAX INTEGER
				{
				enable(1),
				disable(2)
				}
			MAX-ACCESS read-write
			STATUS current
			DESCRIPTION
				"Description."
			::= { fkV2Ds4PortControl 12 }

		
		-- 1.3.6.1.4.1.10428 9 1.102.6.2.6.3.2.13
		fkV2Ds4PortControlFilterMode OBJECT-TYPE
			SYNTAX INTEGER
				{
				disable(0),
				permit(1),
				bypass(2),
				filter(3)
				}
			MAX-ACCESS read-write
			STATUS current
			DESCRIPTION
				"Description."
			::= { fkV2Ds4PortControl 13 }

		
		-- 1.3.6.1.4.1.10428 9 1.102.6.2.6.3.2.14
		fkV2Ds4PortControlFilterDelayTimer OBJECT-TYPE
			SYNTAX INTEGER (-1 | 1..2147483637)
			MAX-ACCESS read-write
			STATUS current
			DESCRIPTION
				"Description."
			::= { fkV2Ds4PortControl 14 }

		
		-- 1.3.6.1.4.1.10428 9 1.102.6.2.6.3.2.15
		fkV2Ds4PortControlFilterDelayCounter OBJECT-TYPE
			SYNTAX INTEGER (-1 | 1..2147483637)
			MAX-ACCESS read-write
			STATUS current
			DESCRIPTION
				"Description."
			::= { fkV2Ds4PortControl 15 }

		
		-- 1.3.6.1.4.1.10428 9 1.102.6.2.6.3.3
		fkV2Ds4PortNotification OBJECT IDENTIFIER ::= { fkV2Ds4Port 3 }

		
		-- 1.3.6.1.4.1.10428 9 1.102.6.2.6.3.3.1
		fkV2Ds4PortTrustStateChanged NOTIFICATION-TYPE
			OBJECTS { fkV2Ds4PortControlRequest, fkV2Ds4PortControlTimeStamp, fkV2Ds4PortControlReqResult, fkV2Ds4PortTrustState }
			STATUS current
			DESCRIPTION 
				"Description."
			::= { fkV2Ds4PortNotification 1 }

		
		-- 1.3.6.1.4.1.10428 9 1.102.6.2.6.3.3.2
		fkV2Ds4PortLimitProfileChagned NOTIFICATION-TYPE
			OBJECTS { fkV2Ds4PortControlRequest, fkV2Ds4PortControlTimeStamp, fkV2Ds4PortControlReqResult, fkV2Ds4PortLimitLease, fkV2Ds4PortLimitRate
				 }
			STATUS current
			DESCRIPTION 
				"Description."
			::= { fkV2Ds4PortNotification 2 }

		
		-- 1.3.6.1.4.1.10428 9 1.102.6.2.6.3.3.3
		fkV2Ds4PortSrcGuardStateChanged NOTIFICATION-TYPE
			OBJECTS { fkV2Ds4PortControlRequest, fkV2Ds4PortControlTimeStamp, fkV2Ds4PortControlReqResult, fkV2Ds4PortSrcGuardState }
			STATUS current
			DESCRIPTION 
				"Description."
			::= { fkV2Ds4PortNotification 3 }

		
		-- 1.3.6.1.4.1.10428 9 1.102.6.2.6.3.3.4
		fkV2Ds4PortTimeoutChanged NOTIFICATION-TYPE
			OBJECTS { fkV2Ds4PortControlRequest, fkV2Ds4PortControlTimeStamp, fkV2Ds4PortControlReqResult, fkV2Ds4PortTimeout }
			STATUS current
			DESCRIPTION 
				"Description."
			::= { fkV2Ds4PortNotification 4 }

		
		-- 1.3.6.1.4.1.10428 9 1.102.6.2.6.3.3.5
		fkV2Ds4PortStatusChanged NOTIFICATION-TYPE
			OBJECTS { fkV2Ds4PortControlRequest, fkV2Ds4PortControlTimeStamp, fkV2Ds4PortControlReqResult, fkV2Ds4PortControlPStatus }
			STATUS current
			DESCRIPTION 
				"Description."
			::= { fkV2Ds4PortNotification 5 }

		
		-- 1.3.6.1.4.1.10428 9 1.102.6.2.6.3.3.6
		fkV2Ds4PortFilterModeChanged NOTIFICATION-TYPE
			OBJECTS { fkV2Ds4PortControlRequest, fkV2Ds4PortControlTimeStamp, fkV2Ds4PortControlReqResult, fkV2Ds4PortFilterMode }
			STATUS current
			DESCRIPTION 
				"Description."
			::= { fkV2Ds4PortNotification 6 }

		
		-- 1.3.6.1.4.1.10428 9 1.102.6.2.6.3.3.7
		fkV2Ds4PortFilterDelayChanged NOTIFICATION-TYPE
			OBJECTS { fkV2Ds4PortControlRequest, fkV2Ds4PortControlTimeStamp, fkV2Ds4PortControlReqResult, fkV2Ds4PortFilterDelayTimer, fkV2Ds4PortFilterDelayCounter
				 }
			STATUS current
			DESCRIPTION 
				"Description."
			::= { fkV2Ds4PortNotification 7 }

		
		-- 1.3.6.1.4.1.10428 9 1.102.6.2.6.4
		fkV2Ds4Bindings OBJECT IDENTIFIER ::= { fkV2Dhcp4Snooping 4 }

		
		-- 1.3.6.1.4.1.10428 9 1.102.6.2.6.4.1
		fkV2Ds4BindingsTable OBJECT-TYPE
			SYNTAX SEQUENCE OF FkV2Ds4BindingsEntry
			MAX-ACCESS not-accessible
			STATUS current
			DESCRIPTION
				"A table provides the DHCP bindings information learnt by
				the device."
			::= { fkV2Ds4Bindings 1 }

		
		-- 1.3.6.1.4.1.10428 9 1.102.6.2.6.4.1.1
		fkV2Ds4BindingsEntry OBJECT-TYPE
			SYNTAX FkV2Ds4BindingsEntry
			MAX-ACCESS not-accessible
			STATUS current
			DESCRIPTION
				"A row instance contains the Mac address, IP address type,
				IP address, VLAN number, interface number, leased time and
				status of this instance."
			INDEX { fkV2Ds4BindingsPortIndex, fkV2Ds4BindingsAddress }
			::= { fkV2Ds4BindingsTable 1 }

		
		FkV2Ds4BindingsEntry ::=
			SEQUENCE { 
				fkV2Ds4BindingsVlanIndex
					INTEGER,
				fkV2Ds4BindingsPortIndex
					INTEGER,
				fkV2Ds4BindingsAddress
					IpAddress,
				fkV2Ds4BindingsMac
					MacAddress,
				fkV2Ds4BindingsType
					BITS,
				fkV2Ds4BindingsState
					INTEGER,
				fkV2Ds4BindingsLeasedTime
					INTEGER,
				fkV2Ds4BindingsMaskLen
					Integer32
			 }

		-- 1.3.6.1.4.1.10428 9 1.102.6.2.6.4.1.1.1
		fkV2Ds4BindingsVlanIndex OBJECT-TYPE
			SYNTAX INTEGER (1..4094)
			MAX-ACCESS read-only
			STATUS current
			DESCRIPTION
				"This object indicates the VLAN to which a DHCP client host
				belongs."
			::= { fkV2Ds4BindingsEntry 1 }

		
		-- 1.3.6.1.4.1.10428 9 1.102.6.2.6.4.1.1.2
		fkV2Ds4BindingsPortIndex OBJECT-TYPE
			SYNTAX INTEGER (1..255)
			MAX-ACCESS read-only
			STATUS current
			DESCRIPTION
				"This object indicates the interface where a DHCP client
				host connects to."
			::= { fkV2Ds4BindingsEntry 2 }

		
		-- 1.3.6.1.4.1.10428 9 1.102.6.2.6.4.1.1.3
		fkV2Ds4BindingsAddress OBJECT-TYPE
			SYNTAX IpAddress
			MAX-ACCESS read-only
			STATUS current
			DESCRIPTION
				"This object indicates the allocated IP address of
				a DHCP client host."
			::= { fkV2Ds4BindingsEntry 3 }

		
		-- 1.3.6.1.4.1.10428 9 1.102.6.2.6.4.1.1.4
		fkV2Ds4BindingsMac OBJECT-TYPE
			SYNTAX MacAddress
			MAX-ACCESS read-only
			STATUS current
			DESCRIPTION
				"This object indicates the MAC address of a DHCP client
				host."
			::= { fkV2Ds4BindingsEntry 4 }

		
		-- 1.3.6.1.4.1.10428 9 1.102.6.2.6.4.1.1.5
		fkV2Ds4BindingsType OBJECT-TYPE
			SYNTAX BITS
				{
				dhcpDynamic(0),
				srcGuardStatic(1)
				}
			MAX-ACCESS read-only
			STATUS current
			DESCRIPTION
				"."
			::= { fkV2Ds4BindingsEntry 5 }

		
		-- 1.3.6.1.4.1.10428 9 1.102.6.2.6.4.1.1.6
		fkV2Ds4BindingsState OBJECT-TYPE
			SYNTAX INTEGER
				{
				disable(0),
				enable(1)
				}
			MAX-ACCESS read-only
			STATUS current
			DESCRIPTION
				"Description."
			::= { fkV2Ds4BindingsEntry 6 }

		
		-- 1.3.6.1.4.1.10428 9 1.102.6.2.6.4.1.1.7
		fkV2Ds4BindingsLeasedTime OBJECT-TYPE
			SYNTAX INTEGER (-1 | 0 | 1..2147483637)
			UNITS "second"
			MAX-ACCESS read-only
			STATUS current
			DESCRIPTION
				"This object indicates the leased time of this DHCP
				binding entry.
				"
			::= { fkV2Ds4BindingsEntry 7 }

		
		-- 1.3.6.1.4.1.10428 9 1.102.6.2.6.4.1.1.8
		fkV2Ds4BindingsMaskLen OBJECT-TYPE
			SYNTAX Integer32
			MAX-ACCESS read-only
			STATUS current
			DESCRIPTION
				"The network mask of the address field of static binding table for snooping"
			::= { fkV2Ds4BindingsEntry 8 }

		
		-- 1.3.6.1.4.1.10428 9 1.102.6.2.6.4.2
		fkV2Ds4BindingsControl OBJECT IDENTIFIER ::= { fkV2Ds4Bindings 2 }

		
		-- 1.3.6.1.4.1.10428 9 1.102.6.2.6.4.2.1
		fkV2Ds4BindingsControlRequest OBJECT-TYPE
			SYNTAX INTEGER
				{
				createDsBinding(1),
				destroyDsBinding(2),
				clearDsBinding(3)
				}
			MAX-ACCESS read-write
			STATUS current
			DESCRIPTION
				"The request of a user command."
			::= { fkV2Ds4BindingsControl 1 }

		
		-- 1.3.6.1.4.1.10428 9 1.102.6.2.6.4.2.2
		fkV2Ds4BindingsControlStatus OBJECT-TYPE
			SYNTAX FkControlStatusType
			MAX-ACCESS read-only
			STATUS current
			DESCRIPTION
				"The status of a user command."
			::= { fkV2Ds4BindingsControl 2 }

		
		-- 1.3.6.1.4.1.10428 9 1.102.6.2.6.4.2.3
		fkV2Ds4BindingsControlTimer OBJECT-TYPE
			SYNTAX Gauge32
			MAX-ACCESS read-write
			STATUS current
			DESCRIPTION
				"The maximum wait time for the manager for a long running user command."
			::= { fkV2Ds4BindingsControl 3 }

		
		-- 1.3.6.1.4.1.10428 9 1.102.6.2.6.4.2.4
		fkV2Ds4BindingsControlTimeStamp OBJECT-TYPE
			SYNTAX TimeTicks
			MAX-ACCESS read-only
			STATUS current
			DESCRIPTION
				"The time stamp of the last command (end of command)."
			::= { fkV2Ds4BindingsControl 4 }

		
		-- 1.3.6.1.4.1.10428 9 1.102.6.2.6.4.2.5
		fkV2Ds4BindingsControlReqResult OBJECT-TYPE
			SYNTAX FkControlRequestResultType
			MAX-ACCESS read-only
			STATUS current
			DESCRIPTION
				"The result of the last user command."
			::= { fkV2Ds4BindingsControl 5 }

		
		-- 1.3.6.1.4.1.10428 9 1.102.6.2.6.4.2.6
		fkV2Ds4BindingsControlVlanIndex OBJECT-TYPE
			SYNTAX INTEGER (1..4094)
			MAX-ACCESS read-write
			STATUS current
			DESCRIPTION
				"."
			::= { fkV2Ds4BindingsControl 6 }

		
		-- 1.3.6.1.4.1.10428 9 1.102.6.2.6.4.2.7
		fkV2Ds4BindingsControlPortIndex OBJECT-TYPE
			SYNTAX INTEGER (1..255)
			MAX-ACCESS read-write
			STATUS current
			DESCRIPTION
				"."
			::= { fkV2Ds4BindingsControl 7 }

		
		-- 1.3.6.1.4.1.10428 9 1.102.6.2.6.4.2.8
		fkV2Ds4BindingsControlAddress OBJECT-TYPE
			SYNTAX IpAddress
			MAX-ACCESS read-only
			STATUS current
			DESCRIPTION
				"This object indicates the allocated IP address of
				a DHCP client host."
			::= { fkV2Ds4BindingsControl 8 }

		
		-- 1.3.6.1.4.1.10428 9 1.102.6.2.6.4.2.9
		fkV2Ds4BindingsControlMac OBJECT-TYPE
			SYNTAX MacAddress
			MAX-ACCESS read-write
			STATUS current
			DESCRIPTION
				"."
			::= { fkV2Ds4BindingsControl 9 }

		
		-- 1.3.6.1.4.1.10428 9 1.102.6.2.6.4.2.10
		fkV2Ds4BindingsControlType OBJECT-TYPE
			SYNTAX BITS
				{
				dhcpDynamic(0),
				srcGuardStatic(1)
				}
			MAX-ACCESS read-write
			STATUS current
			DESCRIPTION
				"Description."
			::= { fkV2Ds4BindingsControl 10 }

		
		-- 1.3.6.1.4.1.10428 9 1.102.6.2.6.4.2.11
		fkV2Ds4BindingsControlLeasedTime OBJECT-TYPE
			SYNTAX INTEGER (-1 | 0 | 1..2147483637)
			UNITS "second"
			MAX-ACCESS read-write
			STATUS current
			DESCRIPTION
				"."
			::= { fkV2Ds4BindingsControl 11 }

		
		-- 1.3.6.1.4.1.10428 9 1.102.6.2.6.4.2.12
		fkV2Ds4BindingsControlMaskLen OBJECT-TYPE
			SYNTAX Integer32
			MAX-ACCESS read-write
			STATUS current
			DESCRIPTION
				"The network mask of the address field of static binding table for snooping"
			::= { fkV2Ds4BindingsControl 12 }

		
		-- 1.3.6.1.4.1.10428 9 1.102.6.2.6.4.3
		fkV2Ds4BindingsNotification OBJECT IDENTIFIER ::= { fkV2Ds4Bindings 3 }

		
		-- 1.3.6.1.4.1.10428 9 1.102.6.2.6.4.3.1
		fkV2Ds4BindingsCreated NOTIFICATION-TYPE
			OBJECTS { fkV2Ds4BindingsControlRequest, fkV2Ds4BindingsControlTimeStamp, fkV2Ds4BindingsControlReqResult, fkV2Ds4BindingsVlanIndex, fkV2Ds4BindingsType, 
				fkV2Ds4BindingsMac, fkV2Ds4BindingsLeasedTime, fkV2Ds4BindingsMaskLen }
			STATUS current
			DESCRIPTION 
				"Description."
			::= { fkV2Ds4BindingsNotification 1 }

		
		-- 1.3.6.1.4.1.10428 9 1.102.6.2.6.4.3.2
		fkV2Ds4BindingsDestroyed NOTIFICATION-TYPE
			OBJECTS { fkV2Ds4BindingsControlRequest, fkV2Ds4BindingsControlTimeStamp, fkV2Ds4BindingsControlReqResult, fkV2Ds4BindingsControlPortIndex, fkV2Ds4BindingsControlAddress, 
				fkV2Ds4BindingsControlType, fkV2Ds4BindingsControlMaskLen }
			STATUS current
			DESCRIPTION 
				"Description."
			::= { fkV2Ds4BindingsNotification 2 }

		
		-- 1.3.6.1.4.1.10428 9 1.102.6.2.6.4.3.3
		fkV2Ds4BindingsCleared NOTIFICATION-TYPE
			OBJECTS { fkV2Ds4BindingsControlRequest, fkV2Ds4BindingsControlTimeStamp, fkV2Ds4BindingsControlReqResult, fkV2Ds4BindingsControlPortIndex, fkV2Ds4BindingsControlType
				 }
			STATUS current
			DESCRIPTION 
				"Description."
			::= { fkV2Ds4BindingsNotification 3 }

		
		-- 1.3.6.1.4.1.10428 9 1.102.6.2.6.5
		fkV2Ds4VlanInfoOpt OBJECT IDENTIFIER ::= { fkV2Dhcp4Snooping 5 }

		
		-- 1.3.6.1.4.1.10428 9 1.102.6.2.6.5.1
		fkV2Ds4VlanInfoOptTable OBJECT-TYPE
			SYNTAX SEQUENCE OF FkV2Ds4VlanInfoOptEntry
			MAX-ACCESS not-accessible
			STATUS current
			DESCRIPTION
				"Description."
			::= { fkV2Ds4VlanInfoOpt 1 }

		
		-- 1.3.6.1.4.1.10428 9 1.102.6.2.6.5.1.1
		fkV2Ds4VlanInfoOptEntry OBJECT-TYPE
			SYNTAX FkV2Ds4VlanInfoOptEntry
			MAX-ACCESS not-accessible
			STATUS current
			DESCRIPTION
				"Description."
			INDEX { fkV2Ds4VlanInfoOptIndex }
			::= { fkV2Ds4VlanInfoOptTable 1 }

		
		FkV2Ds4VlanInfoOptEntry ::=
			SEQUENCE { 
				fkV2Ds4VlanInfoOptIndex
					INTEGER,
				fkV2Ds4VlanInfoOptState
					INTEGER
			 }

		-- 1.3.6.1.4.1.10428 9 1.102.6.2.6.5.1.1.1
		fkV2Ds4VlanInfoOptIndex OBJECT-TYPE
			SYNTAX INTEGER (1..4094)
			MAX-ACCESS read-only
			STATUS current
			DESCRIPTION
				"Description."
			::= { fkV2Ds4VlanInfoOptEntry 1 }

		
		-- 1.3.6.1.4.1.10428 9 1.102.6.2.6.5.1.1.2
		fkV2Ds4VlanInfoOptState OBJECT-TYPE
			SYNTAX INTEGER
				{
				disable(0),
				enable(1)
				}
			MAX-ACCESS read-only
			STATUS current
			DESCRIPTION
				"Description."
			::= { fkV2Ds4VlanInfoOptEntry 2 }

		
		-- 1.3.6.1.4.1.10428 9 1.102.6.2.6.5.2
		fkV2Ds4VlanInforOptControl OBJECT IDENTIFIER ::= { fkV2Ds4VlanInfoOpt 2 }

		
		-- 1.3.6.1.4.1.10428 9 1.102.6.2.6.5.2.1
		fkV2Ds4VlanInfoOptControlRequest OBJECT-TYPE
			SYNTAX INTEGER { setDsVlanInfoOptState(1) }
			MAX-ACCESS read-write
			STATUS current
			DESCRIPTION
				"Description."
			::= { fkV2Ds4VlanInforOptControl 1 }

		
		-- 1.3.6.1.4.1.10428 9 1.102.6.2.6.5.2.2
		fkV2Ds4VlanInfoOptControlStatus OBJECT-TYPE
			SYNTAX FkControlStatusType
			MAX-ACCESS read-write
			STATUS current
			DESCRIPTION
				"Description."
			::= { fkV2Ds4VlanInforOptControl 2 }

		
		-- 1.3.6.1.4.1.10428 9 1.102.6.2.6.5.2.3
		fkV2Ds4VlanInfoOptControlTimer OBJECT-TYPE
			SYNTAX Gauge32
			MAX-ACCESS read-write
			STATUS current
			DESCRIPTION
				"Description."
			::= { fkV2Ds4VlanInforOptControl 3 }

		
		-- 1.3.6.1.4.1.10428 9 1.102.6.2.6.5.2.4
		fkV2Ds4VlanInfoOptControlTimeStamp OBJECT-TYPE
			SYNTAX TimeTicks
			MAX-ACCESS read-write
			STATUS current
			DESCRIPTION
				"Description."
			::= { fkV2Ds4VlanInforOptControl 4 }

		
		-- 1.3.6.1.4.1.10428 9 1.102.6.2.6.5.2.5
		fkV2Ds4VlanInfoOptControlReqResult OBJECT-TYPE
			SYNTAX FkControlRequestResultType
			MAX-ACCESS read-write
			STATUS current
			DESCRIPTION
				"Description."
			::= { fkV2Ds4VlanInforOptControl 5 }

		
		-- 1.3.6.1.4.1.10428 9 1.102.6.2.6.5.2.6
		fkV2Ds4VlanInfoOptControlIndex OBJECT-TYPE
			SYNTAX INTEGER (1..4094)
			MAX-ACCESS read-write
			STATUS current
			DESCRIPTION
				"Description."
			::= { fkV2Ds4VlanInforOptControl 6 }

		
		-- 1.3.6.1.4.1.10428 9 1.102.6.2.6.5.2.7
		fkV2Ds4VlanInfoOptControlState OBJECT-TYPE
			SYNTAX INTEGER
				{
				disable(0),
				enable(1)
				}
			MAX-ACCESS read-write
			STATUS current
			DESCRIPTION
				"Description."
			::= { fkV2Ds4VlanInforOptControl 7 }

		
		-- 1.3.6.1.4.1.10428 9 1.102.6.2.6.5.3
		fkV2Ds4VlanInfoOptNotification OBJECT IDENTIFIER ::= { fkV2Ds4VlanInfoOpt 3 }

		
		-- 1.3.6.1.4.1.10428 9 1.102.6.2.6.5.3.1
		fkV2Ds4VlanInfoOptStateChanged NOTIFICATION-TYPE
			OBJECTS { fkV2Ds4VlanInfoOptControlRequest, fkV2Ds4VlanInfoOptControlTimeStamp, fkV2Ds4VlanInfoOptControlReqResult, fkV2Ds4VlanInfoOptState }
			STATUS current
			DESCRIPTION 
				"Description."
			::= { fkV2Ds4VlanInfoOptNotification 1 }

		
		-- 1.3.6.1.4.1.10428 9 1.102.6.2.7
		fkV2Dhcp4Relay OBJECT IDENTIFIER ::= { fkV2Dhcp4 7 }

		
		-- 1.3.6.1.4.1.10428 9 1.102.6.2.7.1
		fkV2Dhcp4RelayInterface OBJECT IDENTIFIER ::= { fkV2Dhcp4Relay 1 }

		
		-- 1.3.6.1.4.1.10428 9 1.102.6.2.7.1.1
		fkV2Dhcp4RelayIfTable OBJECT-TYPE
			SYNTAX SEQUENCE OF FkV2Dhcp4RelayIfEntry
			MAX-ACCESS not-accessible
			STATUS current
			DESCRIPTION
				"Description."
			::= { fkV2Dhcp4RelayInterface 1 }

		
		-- 1.3.6.1.4.1.10428 9 1.102.6.2.7.1.1.1
		fkV2Dhcp4RelayIfEntry OBJECT-TYPE
			SYNTAX FkV2Dhcp4RelayIfEntry
			MAX-ACCESS not-accessible
			STATUS current
			DESCRIPTION
				"Description."
			INDEX { fkV2Dhcp4RelayIfIndex }
			::= { fkV2Dhcp4RelayIfTable 1 }

		
		FkV2Dhcp4RelayIfEntry ::=
			SEQUENCE { 
				fkV2Dhcp4RelayIfIndex
					INTEGER,
				fkV2Dhcp4RelayIfSimpleOpt82AdminState
					INTEGER,
				fkV2Dhcp4RelayIfSimpleOpt82OperState
					INTEGER,
				fkV2Dhcp4RelayIfMaxHops
					INTEGER
			 }

		-- 1.3.6.1.4.1.10428 9 1.102.6.2.7.1.1.1.1
		fkV2Dhcp4RelayIfIndex OBJECT-TYPE
			SYNTAX INTEGER (1..4094)
			MAX-ACCESS read-only
			STATUS current
			DESCRIPTION
				"Description."
			::= { fkV2Dhcp4RelayIfEntry 1 }

		
		-- 1.3.6.1.4.1.10428 9 1.102.6.2.7.1.1.1.2
		fkV2Dhcp4RelayIfSimpleOpt82AdminState OBJECT-TYPE
			SYNTAX INTEGER
				{
				disable(0),
				enable(1)
				}
			MAX-ACCESS read-only
			STATUS current
			DESCRIPTION
				"The status of Simplified option82 of interface."
			DEFVAL { disable }
			::= { fkV2Dhcp4RelayIfEntry 2 }

		
		-- 1.3.6.1.4.1.10428 9 1.102.6.2.7.1.1.1.3
		fkV2Dhcp4RelayIfSimpleOpt82OperState OBJECT-TYPE
			SYNTAX INTEGER
				{
				disabled(0),
				enabled(1)
				}
			MAX-ACCESS read-only
			STATUS current
			DESCRIPTION
				"Description."
			DEFVAL { disabled }
			::= { fkV2Dhcp4RelayIfEntry 3 }

		
		-- 1.3.6.1.4.1.10428 9 1.102.6.2.7.1.1.1.4
		fkV2Dhcp4RelayIfMaxHops OBJECT-TYPE
			SYNTAX INTEGER (1..15)
			MAX-ACCESS read-only
			STATUS current
			DESCRIPTION
				"Description."
			DEFVAL { 4 }
			::= { fkV2Dhcp4RelayIfEntry 4 }

		
		-- 1.3.6.1.4.1.10428 9 1.102.6.2.7.1.2
		fkV2Dhcp4RelayIfControl OBJECT IDENTIFIER ::= { fkV2Dhcp4RelayInterface 2 }

		
		-- 1.3.6.1.4.1.10428 9 1.102.6.2.7.1.2.1
		fkV2Dhcp4RelayIfControlRequest OBJECT-TYPE
			SYNTAX INTEGER
				{
				setDhcpSimplifiedOpt82State(1),
				setDhcpRelayMaxHops(2)
				}
			MAX-ACCESS read-write
			STATUS current
			DESCRIPTION
				"The request of a user command."
			::= { fkV2Dhcp4RelayIfControl 1 }

		
		-- 1.3.6.1.4.1.10428 9 1.102.6.2.7.1.2.2
		fkV2Dhcp4RelayIfControlStatus OBJECT-TYPE
			SYNTAX FkControlStatusType
			MAX-ACCESS read-only
			STATUS current
			DESCRIPTION
				"The status of a user command."
			::= { fkV2Dhcp4RelayIfControl 2 }

		
		-- 1.3.6.1.4.1.10428 9 1.102.6.2.7.1.2.3
		fkV2Dhcp4RelayIfControlTimer OBJECT-TYPE
			SYNTAX Gauge32
			MAX-ACCESS read-write
			STATUS current
			DESCRIPTION
				"The maximum wait time for the manager for a long running user command."
			::= { fkV2Dhcp4RelayIfControl 3 }

		
		-- 1.3.6.1.4.1.10428 9 1.102.6.2.7.1.2.4
		fkV2Dhcp4RelayIfControlTimeStamp OBJECT-TYPE
			SYNTAX TimeTicks
			MAX-ACCESS read-only
			STATUS current
			DESCRIPTION
				"The time stamp of the last command (end of command)."
			::= { fkV2Dhcp4RelayIfControl 4 }

		
		-- 1.3.6.1.4.1.10428 9 1.102.6.2.7.1.2.5
		fkV2Dhcp4RelayIfControllReqResult OBJECT-TYPE
			SYNTAX FkControlRequestResultType
			MAX-ACCESS read-only
			STATUS current
			DESCRIPTION
				"The result of the last user command."
			::= { fkV2Dhcp4RelayIfControl 5 }

		
		-- 1.3.6.1.4.1.10428 9 1.102.6.2.7.1.2.6
		fkV2Dhcp4RelayIfControlIndex OBJECT-TYPE
			SYNTAX INTEGER (1..4094)
			MAX-ACCESS read-write
			STATUS current
			DESCRIPTION
				"Network Interface Index."
			::= { fkV2Dhcp4RelayIfControl 6 }

		
		-- 1.3.6.1.4.1.10428 9 1.102.6.2.7.1.2.7
		fkV2Dhcp4RelayIfControlSimpleOpt82AdminState OBJECT-TYPE
			SYNTAX INTEGER
				{
				disable(0),
				enable(1)
				}
			MAX-ACCESS read-write
			STATUS current
			DESCRIPTION
				"The Simplified Option82 status of interface."
			DEFVAL { 0 }
			::= { fkV2Dhcp4RelayIfControl 7 }

		
		-- 1.3.6.1.4.1.10428 9 1.102.6.2.7.1.2.8
		fkV2Dhcp4RelayIfControlMaxHops OBJECT-TYPE
			SYNTAX INTEGER (1..15)
			MAX-ACCESS read-write
			STATUS current
			DESCRIPTION
				"Description."
			::= { fkV2Dhcp4RelayIfControl 8 }

		
		-- 1.3.6.1.4.1.10428 9 1.102.6.2.7.1.3
		fkV2Dhcp4RelayIfNotification OBJECT IDENTIFIER ::= { fkV2Dhcp4RelayInterface 3 }

		
		-- 1.3.6.1.4.1.10428 9 1.102.6.2.7.1.3.1
		fkV2Dhcp4RelayIfSimpleOpt82AdminStateChanged NOTIFICATION-TYPE
			OBJECTS { fkV2Dhcp4RelayIfControlRequest, fkV2Dhcp4RelayIfControlTimeStamp, fkV2Dhcp4RelayIfControllReqResult, fkV2Dhcp4RelayIfSimpleOpt82AdminState }
			STATUS current
			DESCRIPTION 
				"setDhcpSimplifiedOpt82status"
			::= { fkV2Dhcp4RelayIfNotification 1 }

		
		-- 1.3.6.1.4.1.10428 9 1.102.6.2.7.1.3.2
		fkV2Dhcp4RelayIfMaxHopsChanged NOTIFICATION-TYPE
			OBJECTS { fkV2Dhcp4RelayIfControlRequest, fkV2Dhcp4RelayIfControlTimeStamp, fkV2Dhcp4RelayIfMaxHops, fkV2Dhcp4RelayIfControllReqResult, fkV2Dhcp4RelayIfSimpleOpt82AdminState
				 }
			STATUS current
			DESCRIPTION 
				"setDhcpSimplifiedOpt82status"
			::= { fkV2Dhcp4RelayIfNotification 2 }

		
		-- 1.3.6.1.4.1.10428 9 1.102.6.2.7.2
		fkV2Dhcp4RelayHelper OBJECT IDENTIFIER ::= { fkV2Dhcp4Relay 2 }

		
		-- 1.3.6.1.4.1.10428 9 1.102.6.2.7.2.1
		fkV2Dhcp4RelayHelperTable OBJECT-TYPE
			SYNTAX SEQUENCE OF FkV2Dhcp4RelayHelperEntry
			MAX-ACCESS not-accessible
			STATUS current
			DESCRIPTION
				"Description."
			::= { fkV2Dhcp4RelayHelper 1 }

		
		-- 1.3.6.1.4.1.10428 9 1.102.6.2.7.2.1.1
		fkV2Dhcp4RelayHelperEntry OBJECT-TYPE
			SYNTAX FkV2Dhcp4RelayHelperEntry
			MAX-ACCESS not-accessible
			STATUS current
			DESCRIPTION
				"Description."
			INDEX { fkV2Dhcp4RelayIfIndex, fkV2Dhcp4RelayHelperOui, fkV2Dhcp4RelayHelperAddress }
			::= { fkV2Dhcp4RelayHelperTable 1 }

		
		FkV2Dhcp4RelayHelperEntry ::=
			SEQUENCE { 
				fkV2Dhcp4RelayHelperOui
					OCTET STRING,
				fkV2Dhcp4RelayHelperAddress
					IpAddress,
				fkV2Dhcp4RelayHelperType
					INTEGER
			 }

		-- 1.3.6.1.4.1.10428 9 1.102.6.2.7.2.1.1.1
		fkV2Dhcp4RelayHelperOui OBJECT-TYPE
			SYNTAX OCTET STRING (SIZE (3))
			MAX-ACCESS read-only
			STATUS current
			DESCRIPTION
				"00:00:00 - ff:ff:ff"
			::= { fkV2Dhcp4RelayHelperEntry 1 }

		
		-- 1.3.6.1.4.1.10428 9 1.102.6.2.7.2.1.1.2
		fkV2Dhcp4RelayHelperAddress OBJECT-TYPE
			SYNTAX IpAddress
			MAX-ACCESS read-only
			STATUS current
			DESCRIPTION
				"."
			::= { fkV2Dhcp4RelayHelperEntry 2 }

		
		-- 1.3.6.1.4.1.10428 9 1.102.6.2.7.2.1.1.3
		fkV2Dhcp4RelayHelperType OBJECT-TYPE
			SYNTAX INTEGER { unknown(0) }
			MAX-ACCESS read-only
			STATUS current
			DESCRIPTION
				"Description."
			::= { fkV2Dhcp4RelayHelperEntry 3 }

		
		-- 1.3.6.1.4.1.10428 9 1.102.6.2.7.2.2
		fkV2Dhcp4RelayHelperControl OBJECT IDENTIFIER ::= { fkV2Dhcp4RelayHelper 2 }

		
		-- 1.3.6.1.4.1.10428 9 1.102.6.2.7.2.2.1
		fkV2Dhcp4RelayHelperControlRequest OBJECT-TYPE
			SYNTAX INTEGER
				{
				createDhcpRelayHelperEntry(1),
				destroyDhcpRelayHelperEntry(2),
				clearDhcpRelayHelperEntry(3)
				}
			MAX-ACCESS read-write
			STATUS current
			DESCRIPTION
				"The request of a user command."
			::= { fkV2Dhcp4RelayHelperControl 1 }

		
		-- 1.3.6.1.4.1.10428 9 1.102.6.2.7.2.2.2
		fkV2Dhcp4RelayHelperControlStatus OBJECT-TYPE
			SYNTAX FkControlStatusType
			MAX-ACCESS read-only
			STATUS current
			DESCRIPTION
				"The status of a user command."
			::= { fkV2Dhcp4RelayHelperControl 2 }

		
		-- 1.3.6.1.4.1.10428 9 1.102.6.2.7.2.2.3
		fkV2Dhcp4RelayHelperControlTimer OBJECT-TYPE
			SYNTAX Gauge32
			MAX-ACCESS read-write
			STATUS current
			DESCRIPTION
				"The maximum wait time for the manager for a long running user command."
			::= { fkV2Dhcp4RelayHelperControl 3 }

		
		-- 1.3.6.1.4.1.10428 9 1.102.6.2.7.2.2.4
		fkV2Dhcp4RelayHelperControlTimeStamp OBJECT-TYPE
			SYNTAX TimeTicks
			MAX-ACCESS read-only
			STATUS current
			DESCRIPTION
				"The time stamp of the last command (end of command)."
			::= { fkV2Dhcp4RelayHelperControl 4 }

		
		-- 1.3.6.1.4.1.10428 9 1.102.6.2.7.2.2.5
		fkV2Dhcp4RelayHelperControlReqResult OBJECT-TYPE
			SYNTAX FkControlRequestResultType
			MAX-ACCESS read-only
			STATUS current
			DESCRIPTION
				"The result of the last user command."
			::= { fkV2Dhcp4RelayHelperControl 5 }

		
		-- 1.3.6.1.4.1.10428 9 1.102.6.2.7.2.2.6
		fkV2Dhcp4RelayHelperControlIfIndex OBJECT-TYPE
			SYNTAX INTEGER (1..4094)
			MAX-ACCESS read-write
			STATUS current
			DESCRIPTION
				"."
			::= { fkV2Dhcp4RelayHelperControl 6 }

		
		-- 1.3.6.1.4.1.10428 9 1.102.6.2.7.2.2.7
		fkV2Dhcp4RelayHelperControlOui OBJECT-TYPE
			SYNTAX OCTET STRING (SIZE (3))
			MAX-ACCESS read-write
			STATUS current
			DESCRIPTION
				"00:00:00 - ff:ff:ff"
			::= { fkV2Dhcp4RelayHelperControl 7 }

		
		-- 1.3.6.1.4.1.10428 9 1.102.6.2.7.2.2.8
		fkV2Dhcp4RelayHelperControlAddress OBJECT-TYPE
			SYNTAX IpAddress
			MAX-ACCESS read-write
			STATUS current
			DESCRIPTION
				"."
			::= { fkV2Dhcp4RelayHelperControl 8 }

		
		-- 1.3.6.1.4.1.10428 9 1.102.6.2.7.2.2.9
		fkV2Dhcp4RelayHelperControlType OBJECT-TYPE
			SYNTAX INTEGER { unknown(0) }
			MAX-ACCESS read-write
			STATUS current
			DESCRIPTION
				"Description."
			::= { fkV2Dhcp4RelayHelperControl 9 }

		
		-- 1.3.6.1.4.1.10428 9 1.102.6.2.7.2.3
		fkV2Dhcp4RelayHelperNotification OBJECT IDENTIFIER ::= { fkV2Dhcp4RelayHelper 3 }

		
		-- 1.3.6.1.4.1.10428 9 1.102.6.2.7.2.3.1
		fkV2Dhcp4RelayHelperCreated NOTIFICATION-TYPE
			OBJECTS { fkV2Dhcp4RelayHelperControlRequest, fkV2Dhcp4RelayHelperControlTimeStamp, fkV2Dhcp4RelayHelperControlReqResult, fkV2Dhcp4RelayHelperType }
			STATUS current
			DESCRIPTION 
				"."
			::= { fkV2Dhcp4RelayHelperNotification 1 }

		
		-- 1.3.6.1.4.1.10428 9 1.102.6.2.7.2.3.2
		fkV2Dhcp4RelayHelperDestroyed NOTIFICATION-TYPE
			OBJECTS { fkV2Dhcp4RelayHelperControlRequest, fkV2Dhcp4RelayHelperControlTimeStamp, fkV2Dhcp4RelayHelperControlReqResult, fkV2Dhcp4RelayHelperControlIfIndex, fkV2Dhcp4RelayHelperControlOui, 
				fkV2Dhcp4RelayHelperControlAddress }
			STATUS current
			DESCRIPTION 
				"."
			::= { fkV2Dhcp4RelayHelperNotification 2 }

		
		-- 1.3.6.1.4.1.10428 9 1.102.6.2.7.2.3.3
		fkV2Dhcp4RelayHelperCleared NOTIFICATION-TYPE
			OBJECTS { fkV2Dhcp4RelayHelperControlRequest, fkV2Dhcp4RelayHelperControlTimeStamp, fkV2Dhcp4RelayHelperControlReqResult, fkV2Dhcp4RelayHelperControlIfIndex, fkV2Dhcp4RelayHelperControlOui
				 }
			STATUS current
			DESCRIPTION 
				"."
			::= { fkV2Dhcp4RelayHelperNotification 3 }

		
		-- 1.3.6.1.4.1.10428 9 1.102.6.2.7.3
		fkV2Dhcp4RelayStats OBJECT IDENTIFIER ::= { fkV2Dhcp4Relay 3 }

		
		-- 1.3.6.1.4.1.10428 9 1.102.6.2.7.3.1
		fkV2Dhcp4RelayIntrStatsTable OBJECT-TYPE
			SYNTAX SEQUENCE OF FkV2Dhcp4RelayIntrStatsEntry
			MAX-ACCESS not-accessible
			STATUS current
			DESCRIPTION
				"Description."
			::= { fkV2Dhcp4RelayStats 1 }

		
		-- 1.3.6.1.4.1.10428 9 1.102.6.2.7.3.1.1
		fkV2Dhcp4RelayIntrStatsEntry OBJECT-TYPE
			SYNTAX FkV2Dhcp4RelayIntrStatsEntry
			MAX-ACCESS not-accessible
			STATUS current
			DESCRIPTION
				"Description."
			INDEX { fkV2Dhcp4RelayIntrIndex }
			::= { fkV2Dhcp4RelayIntrStatsTable 1 }

		
		FkV2Dhcp4RelayIntrStatsEntry ::=
			SEQUENCE { 
				fkV2Dhcp4RelayIntrIndex
					Integer32,
				fkV2Dhcp4RelayIntrRcvd
					Counter32,
				fkV2Dhcp4RelayIntrSent
					Gauge32,
				fkV2Dhcp4RelayIntrRcvdErrors
					Counter32,
				fkV2Dhcp4RelayIntrSentErrors
					Counter32,
				fkV2Dhcp4RelayIntrRcvdBootpRequest
					Counter32,
				fkV2Dhcp4RelayIntrRcvdBootpReply
					Counter32,
				fkV2Dhcp4RelayIntrSentBootpRequest
					Counter32,
				fkV2Dhcp4RelayIntrSentBootpReply
					Counter32,
				fkV2Dhcp4RelayIntrRcvdDiscover
					Counter32,
				fkV2Dhcp4RelayIntrRcvdRequest
					Counter32,
				fkV2Dhcp4RelayIntrRcvdRelease
					Counter32,
				fkV2Dhcp4RelayIntrRcvdInform
					Counter32,
				fkV2Dhcp4RelayIntrRcvdDecline
					Counter32,
				fkV2Dhcp4RelayIntrSentDiscover
					Counter32,
				fkV2Dhcp4RelayIntrSentRequest
					Counter32,
				fkV2Dhcp4RelayIntrSentRelease
					Counter32,
				fkV2Dhcp4RelayIntrSentInform
					Counter32,
				fkV2Dhcp4RelayIntrSentDecline
					Counter32,
				fkV2Dhcp4RelayIntrRcvdOffer
					Counter32,
				fkV2Dhcp4RelayIntrRcvdAck
					Counter32,
				fkV2Dhcp4RelayIntrRcvdNack
					Counter32,
				fkV2Dhcp4RelayIntrSentOffer
					Counter32,
				fkV2Dhcp4RelayIntrSentAck
					Counter32,
				fkV2Dhcp4RelayIntrSentNack
					Counter32
			 }

		-- 1.3.6.1.4.1.10428 9 1.102.6.2.7.3.1.1.1
		fkV2Dhcp4RelayIntrIndex OBJECT-TYPE
			SYNTAX Integer32 (1..65535)
			MAX-ACCESS read-only
			STATUS current
			DESCRIPTION
				"The relay interface index.  
				Same as  VLAN index related to the interface."
			::= { fkV2Dhcp4RelayIntrStatsEntry 1 }

		
		-- 1.3.6.1.4.1.10428 9 1.102.6.2.7.3.1.1.2
		fkV2Dhcp4RelayIntrRcvd OBJECT-TYPE
			SYNTAX Counter32
			MAX-ACCESS read-only
			STATUS current
			DESCRIPTION
				"The received-packets.
				"
			::= { fkV2Dhcp4RelayIntrStatsEntry 2 }

		
		-- 1.3.6.1.4.1.10428 9 1.102.6.2.7.3.1.1.3
		fkV2Dhcp4RelayIntrSent OBJECT-TYPE
			SYNTAX Gauge32
			MAX-ACCESS read-only
			STATUS current
			DESCRIPTION
				"The sent-packets.
				"
			::= { fkV2Dhcp4RelayIntrStatsEntry 3 }

		
		-- 1.3.6.1.4.1.10428 9 1.102.6.2.7.3.1.1.4
		fkV2Dhcp4RelayIntrRcvdErrors OBJECT-TYPE
			SYNTAX Counter32
			MAX-ACCESS read-only
			STATUS current
			DESCRIPTION
				"The received error packtes
				"
			::= { fkV2Dhcp4RelayIntrStatsEntry 4 }

		
		-- 1.3.6.1.4.1.10428 9 1.102.6.2.7.3.1.1.5
		fkV2Dhcp4RelayIntrSentErrors OBJECT-TYPE
			SYNTAX Counter32
			MAX-ACCESS read-only
			STATUS current
			DESCRIPTION
				"The sent error packtes.
				"
			::= { fkV2Dhcp4RelayIntrStatsEntry 5 }

		
		-- 1.3.6.1.4.1.10428 9 1.102.6.2.7.3.1.1.6
		fkV2Dhcp4RelayIntrRcvdBootpRequest OBJECT-TYPE
			SYNTAX Counter32
			MAX-ACCESS read-only
			STATUS current
			DESCRIPTION
				"The received bootp request.
				"
			::= { fkV2Dhcp4RelayIntrStatsEntry 6 }

		
		-- 1.3.6.1.4.1.10428 9 1.102.6.2.7.3.1.1.7
		fkV2Dhcp4RelayIntrRcvdBootpReply OBJECT-TYPE
			SYNTAX Counter32
			MAX-ACCESS read-only
			STATUS current
			DESCRIPTION
				"The received bootp reply.
				"
			::= { fkV2Dhcp4RelayIntrStatsEntry 7 }

		
		-- 1.3.6.1.4.1.10428 9 1.102.6.2.7.3.1.1.8
		fkV2Dhcp4RelayIntrSentBootpRequest OBJECT-TYPE
			SYNTAX Counter32
			MAX-ACCESS read-only
			STATUS current
			DESCRIPTION
				"The sent bootp request.
				"
			::= { fkV2Dhcp4RelayIntrStatsEntry 8 }

		
		-- 1.3.6.1.4.1.10428 9 1.102.6.2.7.3.1.1.9
		fkV2Dhcp4RelayIntrSentBootpReply OBJECT-TYPE
			SYNTAX Counter32
			MAX-ACCESS read-only
			STATUS current
			DESCRIPTION
				"The sent bootp reply
				"
			::= { fkV2Dhcp4RelayIntrStatsEntry 9 }

		
		-- 1.3.6.1.4.1.10428 9 1.102.6.2.7.3.1.1.10
		fkV2Dhcp4RelayIntrRcvdDiscover OBJECT-TYPE
			SYNTAX Counter32
			MAX-ACCESS read-only
			STATUS current
			DESCRIPTION
				"The received discover from client.
				"
			::= { fkV2Dhcp4RelayIntrStatsEntry 10 }

		
		-- 1.3.6.1.4.1.10428 9 1.102.6.2.7.3.1.1.11
		fkV2Dhcp4RelayIntrRcvdRequest OBJECT-TYPE
			SYNTAX Counter32
			MAX-ACCESS read-only
			STATUS current
			DESCRIPTION
				"The received request from client.
				"
			::= { fkV2Dhcp4RelayIntrStatsEntry 11 }

		
		-- 1.3.6.1.4.1.10428 9 1.102.6.2.7.3.1.1.12
		fkV2Dhcp4RelayIntrRcvdRelease OBJECT-TYPE
			SYNTAX Counter32
			MAX-ACCESS read-only
			STATUS current
			DESCRIPTION
				"The received release from client.
				"
			::= { fkV2Dhcp4RelayIntrStatsEntry 12 }

		
		-- 1.3.6.1.4.1.10428 9 1.102.6.2.7.3.1.1.13
		fkV2Dhcp4RelayIntrRcvdInform OBJECT-TYPE
			SYNTAX Counter32
			MAX-ACCESS read-only
			STATUS current
			DESCRIPTION
				"The received inform from client.
				"
			::= { fkV2Dhcp4RelayIntrStatsEntry 13 }

		
		-- 1.3.6.1.4.1.10428 9 1.102.6.2.7.3.1.1.14
		fkV2Dhcp4RelayIntrRcvdDecline OBJECT-TYPE
			SYNTAX Counter32
			MAX-ACCESS read-only
			STATUS current
			DESCRIPTION
				"The received decline from client.
				"
			::= { fkV2Dhcp4RelayIntrStatsEntry 14 }

		
		-- 1.3.6.1.4.1.10428 9 1.102.6.2.7.3.1.1.15
		fkV2Dhcp4RelayIntrSentDiscover OBJECT-TYPE
			SYNTAX Counter32
			MAX-ACCESS read-only
			STATUS current
			DESCRIPTION
				"The sent discover to server.
				"
			::= { fkV2Dhcp4RelayIntrStatsEntry 15 }

		
		-- 1.3.6.1.4.1.10428 9 1.102.6.2.7.3.1.1.16
		fkV2Dhcp4RelayIntrSentRequest OBJECT-TYPE
			SYNTAX Counter32
			MAX-ACCESS read-only
			STATUS current
			DESCRIPTION
				"The sent request to server.
				"
			::= { fkV2Dhcp4RelayIntrStatsEntry 16 }

		
		-- 1.3.6.1.4.1.10428 9 1.102.6.2.7.3.1.1.17
		fkV2Dhcp4RelayIntrSentRelease OBJECT-TYPE
			SYNTAX Counter32
			MAX-ACCESS read-only
			STATUS current
			DESCRIPTION
				"The sent release to server.
				"
			::= { fkV2Dhcp4RelayIntrStatsEntry 17 }

		
		-- 1.3.6.1.4.1.10428 9 1.102.6.2.7.3.1.1.18
		fkV2Dhcp4RelayIntrSentInform OBJECT-TYPE
			SYNTAX Counter32
			MAX-ACCESS read-only
			STATUS current
			DESCRIPTION
				"The sent inform to server.
				"
			::= { fkV2Dhcp4RelayIntrStatsEntry 18 }

		
		-- 1.3.6.1.4.1.10428 9 1.102.6.2.7.3.1.1.19
		fkV2Dhcp4RelayIntrSentDecline OBJECT-TYPE
			SYNTAX Counter32
			MAX-ACCESS read-only
			STATUS current
			DESCRIPTION
				"The sent decline to server.
				"
			::= { fkV2Dhcp4RelayIntrStatsEntry 19 }

		
		-- 1.3.6.1.4.1.10428 9 1.102.6.2.7.3.1.1.20
		fkV2Dhcp4RelayIntrRcvdOffer OBJECT-TYPE
			SYNTAX Counter32
			MAX-ACCESS read-only
			STATUS current
			DESCRIPTION
				"The received offer from server
				"
			::= { fkV2Dhcp4RelayIntrStatsEntry 20 }

		
		-- 1.3.6.1.4.1.10428 9 1.102.6.2.7.3.1.1.21
		fkV2Dhcp4RelayIntrRcvdAck OBJECT-TYPE
			SYNTAX Counter32
			MAX-ACCESS read-only
			STATUS current
			DESCRIPTION
				"The received ack from server
				"
			::= { fkV2Dhcp4RelayIntrStatsEntry 21 }

		
		-- 1.3.6.1.4.1.10428 9 1.102.6.2.7.3.1.1.22
		fkV2Dhcp4RelayIntrRcvdNack OBJECT-TYPE
			SYNTAX Counter32
			MAX-ACCESS read-only
			STATUS current
			DESCRIPTION
				"The received nak from server
				"
			::= { fkV2Dhcp4RelayIntrStatsEntry 22 }

		
		-- 1.3.6.1.4.1.10428 9 1.102.6.2.7.3.1.1.23
		fkV2Dhcp4RelayIntrSentOffer OBJECT-TYPE
			SYNTAX Counter32
			MAX-ACCESS read-only
			STATUS current
			DESCRIPTION
				"The sent offer to client
				"
			::= { fkV2Dhcp4RelayIntrStatsEntry 23 }

		
		-- 1.3.6.1.4.1.10428 9 1.102.6.2.7.3.1.1.24
		fkV2Dhcp4RelayIntrSentAck OBJECT-TYPE
			SYNTAX Counter32
			MAX-ACCESS read-only
			STATUS current
			DESCRIPTION
				"The sent ack to client
				"
			::= { fkV2Dhcp4RelayIntrStatsEntry 24 }

		
		-- 1.3.6.1.4.1.10428 9 1.102.6.2.7.3.1.1.25
		fkV2Dhcp4RelayIntrSentNack OBJECT-TYPE
			SYNTAX Counter32
			MAX-ACCESS read-only
			STATUS current
			DESCRIPTION
				"The sent nack to client
				"
			::= { fkV2Dhcp4RelayIntrStatsEntry 25 }

		
		-- 1.3.6.1.4.1.10428 9 1.102.6.2.7.3.2
		fkV2Dhcp4RelayIntrStatsControl OBJECT IDENTIFIER ::= { fkV2Dhcp4RelayStats 2 }

		
		-- 1.3.6.1.4.1.10428 9 1.102.6.2.7.3.2.1
		fkV2Dhcp4RelayIntrStatsControlRequest OBJECT-TYPE
			SYNTAX INTEGER { clearRelayStats(1) }
			MAX-ACCESS read-write
			STATUS current
			DESCRIPTION
				"Description."
			::= { fkV2Dhcp4RelayIntrStatsControl 1 }

		
		-- 1.3.6.1.4.1.10428 9 1.102.6.2.7.3.2.2
		fkV2Dhcp4RelayIntrStatsControlStatus OBJECT-TYPE
			SYNTAX FkControlStatusType
			MAX-ACCESS read-only
			STATUS current
			DESCRIPTION
				"Description."
			::= { fkV2Dhcp4RelayIntrStatsControl 2 }

		
		-- 1.3.6.1.4.1.10428 9 1.102.6.2.7.3.2.3
		fkV2Dhcp4RelayIntrStatsControlTimer OBJECT-TYPE
			SYNTAX Gauge32
			MAX-ACCESS read-write
			STATUS current
			DESCRIPTION
				"Description."
			::= { fkV2Dhcp4RelayIntrStatsControl 3 }

		
		-- 1.3.6.1.4.1.10428 9 1.102.6.2.7.3.2.4
		fkV2Dhcp4RelayIntrStatsControITimeStamp OBJECT-TYPE
			SYNTAX TimeTicks
			MAX-ACCESS read-only
			STATUS current
			DESCRIPTION
				"Description."
			::= { fkV2Dhcp4RelayIntrStatsControl 4 }

		
		-- 1.3.6.1.4.1.10428 9 1.102.6.2.7.3.2.5
		fkV2Dhcp4RelayIntrStatsControIResult OBJECT-TYPE
			SYNTAX FkControlRequestResultType
			MAX-ACCESS read-only
			STATUS current
			DESCRIPTION
				"Description."
			::= { fkV2Dhcp4RelayIntrStatsControl 5 }

		
		-- 1.3.6.1.4.1.10428 9 1.102.6.2.7.3.2.6
		fkV2Dhcp4RelayIntrStatsControIndex OBJECT-TYPE
			SYNTAX Integer32
			MAX-ACCESS read-write
			STATUS current
			DESCRIPTION
				"Description."
			::= { fkV2Dhcp4RelayIntrStatsControl 6 }

		
		-- 1.3.6.1.4.1.10428 9 1.102.6.2.7.3.3
		fkV2Dhcp4RelayIntrStatsNotification OBJECT IDENTIFIER ::= { fkV2Dhcp4RelayStats 3 }

		
		-- 1.3.6.1.4.1.10428 9 1.102.6.2.7.3.3.1
		fkV2Dhcp4RelayintrStatsCleared NOTIFICATION-TYPE
			OBJECTS { fkV2Dhcp4RelayIntrStatsControlRequest, fkV2Dhcp4RelayIntrStatsControITimeStamp, fkV2Dhcp4RelayIntrStatsControIResult, fkV2Dhcp4RelayIntrStatsControIndex }
			STATUS current
			DESCRIPTION 
				"Description."
			::= { fkV2Dhcp4RelayIntrStatsNotification 1 }

		
		-- 1.3.6.1.4.1.10428 9 1.102.6.2.8
		fkV2Dhcp4Client OBJECT IDENTIFIER ::= { fkV2Dhcp4 8 }

		
		-- 1.3.6.1.4.1.10428 9 1.102.6.2.8.1
		fkV2Dhcp4ClientInterface OBJECT IDENTIFIER ::= { fkV2Dhcp4Client 1 }

		
		-- 1.3.6.1.4.1.10428 9 1.102.6.2.8.1.1
		fkV2Dhcp4ClientIfTable OBJECT-TYPE
			SYNTAX SEQUENCE OF FkV2Dhcp4ClientIfEntry
			MAX-ACCESS not-accessible
			STATUS current
			DESCRIPTION
				"Description."
			::= { fkV2Dhcp4ClientInterface 1 }

		
		-- 1.3.6.1.4.1.10428 9 1.102.6.2.8.1.1.1
		fkV2Dhcp4ClientIfEntry OBJECT-TYPE
			SYNTAX FkV2Dhcp4ClientIfEntry
			MAX-ACCESS not-accessible
			STATUS current
			DESCRIPTION
				"Description."
			INDEX { fkV2Dhcp4ClientIfIndex }
			::= { fkV2Dhcp4ClientIfTable 1 }

		
		FkV2Dhcp4ClientIfEntry ::=
			SEQUENCE { 
				fkV2Dhcp4ClientIfIndex
					INTEGER,
				fkV2Dhcp4ClientIfActivity
					INTEGER,
				fkV2Dhcp4ClientIfAddress
					IpAddress,
				fkV2Dhcp4ClientIfMask
					IpAddress,
				fkV2Dhcp4ClientIfServer
					IpAddress,
				fkV2Dhcp4ClientIfHostName
					OCTET STRING,
				fkV2Dhcp4ClientIfRequestFlag
					BITS,
				fkV2Dhcp4ClientIfClientType
					INTEGER,
				fkV2Dhcp4ClientIfClientId
					OCTET STRING,
				fkV2Dhcp4ClientIfClassType
					INTEGER,
				fkV2Dhcp4ClientIfClassId
					OCTET STRING,
				fkV2Dhcp4ClientIfLeasetime
					INTEGER,
				fkV2Dhcp4ClientIfExpired
					Unsigned32,
				fkV2Dhcp4ClientIfState
					INTEGER,
				fkV2Dhcp4ClientIfLeasetimeOption
					INTEGER
			 }

		-- 1.3.6.1.4.1.10428 9 1.102.6.2.8.1.1.1.1
		fkV2Dhcp4ClientIfIndex OBJECT-TYPE
			SYNTAX INTEGER (1..4094)
			MAX-ACCESS read-only
			STATUS current
			DESCRIPTION
				"Description."
			::= { fkV2Dhcp4ClientIfEntry 1 }

		
		-- 1.3.6.1.4.1.10428 9 1.102.6.2.8.1.1.1.2
		fkV2Dhcp4ClientIfActivity OBJECT-TYPE
			SYNTAX INTEGER
				{
				disable(0),
				enable(1)
				}
			MAX-ACCESS read-only
			STATUS current
			DESCRIPTION
				"Description."
			DEFVAL { disable }
			::= { fkV2Dhcp4ClientIfEntry 2 }

		
		-- 1.3.6.1.4.1.10428 9 1.102.6.2.8.1.1.1.3
		fkV2Dhcp4ClientIfAddress OBJECT-TYPE
			SYNTAX IpAddress
			MAX-ACCESS read-only
			STATUS current
			DESCRIPTION
				"The IP address acquired by DHCP Client active in this interface."
			::= { fkV2Dhcp4ClientIfEntry 3 }

		
		-- 1.3.6.1.4.1.10428 9 1.102.6.2.8.1.1.1.4
		fkV2Dhcp4ClientIfMask OBJECT-TYPE
			SYNTAX IpAddress
			MAX-ACCESS read-only
			STATUS current
			DESCRIPTION
				"The subnet mask associated with the IP address acquired by DHCP Client.  
				The value of the mask is an IP address with all the network 
				bits set to 1 and all the hosts bits set to 0."
			::= { fkV2Dhcp4ClientIfEntry 4 }

		
		-- 1.3.6.1.4.1.10428 9 1.102.6.2.8.1.1.1.5
		fkV2Dhcp4ClientIfServer OBJECT-TYPE
			SYNTAX IpAddress
			MAX-ACCESS read-only
			STATUS current
			DESCRIPTION
				"DHCP Server's IP address."
			::= { fkV2Dhcp4ClientIfEntry 5 }

		
		-- 1.3.6.1.4.1.10428 9 1.102.6.2.8.1.1.1.6
		fkV2Dhcp4ClientIfHostName OBJECT-TYPE
			SYNTAX OCTET STRING (SIZE (0 | 1..64))
			MAX-ACCESS read-only
			STATUS current
			DESCRIPTION
				"Description."
			::= { fkV2Dhcp4ClientIfEntry 6 }

		
		-- 1.3.6.1.4.1.10428 9 1.102.6.2.8.1.1.1.7
		fkV2Dhcp4ClientIfRequestFlag OBJECT-TYPE
			SYNTAX BITS
				{
				unused0(0),
				subnetMask(1),
				timeOffset(2),
				router(3),
				timeServer(4),
				nameServer(5),
				domainNameServer(6),
				logServer(7),
				cookieServer(8),
				lprServer(9),
				impressServer(10),
				resourceLocationServer(11),
				hostName(12),
				bootFileSize(13),
				meritFile(14),
				domainName(15),
				swapServer(16),
				rootPath(17),
				extensionsPath(18),
				ipForwardState(19),
				nonLocalSourceRoutingState(20),
				policyFilter(21),
				maximumDatagramReassemblySize(22),
				defaultIpTimeToLive(23),
				pathMtuAgingTimeout(24),
				pathMtuPlateauTable(25),
				interfaceMtu(26),
				allSubnetsAreLocal(27),
				broadcastAddress(28),
				performMaskDiscovery(29),
				maskSupplier(30),
				performRouterDiscovery(31),
				routerSolicitationAddress(32),
				staticRoute(33),
				trailerEncapsulation(34),
				arpCacheTimeout(35),
				ethernetEncapsulationOption(36),
				tcpDefaultTtl(37),
				tcpKeepaliveInterval(38),
				tcpKeepaliveGarbage(39),
				nisDomain(40),
				nisServers(41),
				networkTimeProtocolServers(42),
				vendorSpecificInformation(43),
				netbiosOverTcpIpNameServer(44),
				netbiosOverTcpIpDatagramDistributionServer(45),
				netbiosOverTcpIpNodeType(46),
				netbiosOverTcpIpScope(47),
				xWindowSystemFontServer(48),
				xWindowSystemDisplayManager(49),
				requestedIpAddress(50),
				ipAddressLeaseTime(51),
				optionOverload(52),
				dhcpMessageType(53),
				serverIdentifier(54),
				unused55(55),
				message(56),
				maximumDhcpMessageSize(57),
				renewalTimeValue(58),
				rebindingTimeValue(59),
				vendorClassIdentifier(60),
				clientIdentifier(61),
				undefined62(62),
				undefined63(63),
				nisPlusDomain(64),
				nisPlusServers(65),
				tftpServerName(66),
				bootFileName(67),
				mobileIpHomeAgent(68),
				smtpServer(69),
				pop3Server(70),
				nntpServer(71),
				wwwServer(72),
				defaultFingerServer(73),
				ircServer(74),
				streetTalkServer(75),
				stdaServer(76)
				}
			MAX-ACCESS read-only
			STATUS current
			DESCRIPTION
				"Description."
			::= { fkV2Dhcp4ClientIfEntry 7 }

		
		-- 1.3.6.1.4.1.10428 9 1.102.6.2.8.1.1.1.8
		fkV2Dhcp4ClientIfClientType OBJECT-TYPE
			SYNTAX INTEGER
				{
				text(0),
				hex(1)
				}
			MAX-ACCESS read-only
			STATUS current
			DESCRIPTION
				"DHCP Client-identifier input style.
				0 : text(ascii) string format
				1 : hexadecimal format"
			DEFVAL { text }
			::= { fkV2Dhcp4ClientIfEntry 8 }

		
		-- 1.3.6.1.4.1.10428 9 1.102.6.2.8.1.1.1.9
		fkV2Dhcp4ClientIfClientId OBJECT-TYPE
			SYNTAX OCTET STRING (SIZE (0 | 1..64))
			MAX-ACCESS read-only
			STATUS current
			DESCRIPTION
				"DHCP Client-identifier value.
				This is used by DHCP clients to specify their unique identifier.
				DHCP servers use this value to index their database of address bindings.
				This value is expected to be unique for all clients in an administrative domain."
			::= { fkV2Dhcp4ClientIfEntry 9 }

		
		-- 1.3.6.1.4.1.10428 9 1.102.6.2.8.1.1.1.10
		fkV2Dhcp4ClientIfClassType OBJECT-TYPE
			SYNTAX INTEGER
				{
				text(0),
				hex(1)
				}
			MAX-ACCESS read-only
			STATUS current
			DESCRIPTION
				"DHCP Class identifier input style.
				0 : text(ascii) string format
				1 : hexadecimal format"
			DEFVAL { text }
			::= { fkV2Dhcp4ClientIfEntry 10 }

		
		-- 1.3.6.1.4.1.10428 9 1.102.6.2.8.1.1.1.11
		fkV2Dhcp4ClientIfClassId OBJECT-TYPE
			SYNTAX OCTET STRING (SIZE (0 | 1..64))
			MAX-ACCESS read-only
			STATUS current
			DESCRIPTION
				"DHCP Class identifier value.
				This is used by DHCP clients to optionally identify the vendor 
				type and configuration of a DHCP client.
				The information is a string of n octets, interpreted by servers.
				Vendors may choose to define specific vendor class identifiers 
				to convey particular configuration or other identification 
				information about a client.
				For example, the identifier may encode the client's hardware configuration."
			::= { fkV2Dhcp4ClientIfEntry 11 }

		
		-- 1.3.6.1.4.1.10428 9 1.102.6.2.8.1.1.1.12
		fkV2Dhcp4ClientIfLeasetime OBJECT-TYPE
			SYNTAX INTEGER (120..2147483637)
			UNITS "second"
			MAX-ACCESS read-only
			STATUS current
			DESCRIPTION
				"The leased time for IP address acquired by DHCP Client.
				Default lease-time: 3600s"
			DEFVAL { 3600 }
			::= { fkV2Dhcp4ClientIfEntry 12 }

		
		-- 1.3.6.1.4.1.10428 9 1.102.6.2.8.1.1.1.13
		fkV2Dhcp4ClientIfExpired OBJECT-TYPE
			SYNTAX Unsigned32
			UNITS "second"
			MAX-ACCESS read-only
			STATUS current
			DESCRIPTION
				"Description."
			::= { fkV2Dhcp4ClientIfEntry 13 }

		
		-- 1.3.6.1.4.1.10428 9 1.102.6.2.8.1.1.1.14
		fkV2Dhcp4ClientIfState OBJECT-TYPE
			SYNTAX INTEGER
				{
				halt(0),
				init(1),
				request(3),
				bound(4),
				renew(5),
				rebind(6),
				nonactive(255)
				}
			MAX-ACCESS read-only
			STATUS current
			DESCRIPTION
				"The operating status of DHCP Client."
			DEFVAL { non-active }
			::= { fkV2Dhcp4ClientIfEntry 14 }

		
		-- 1.3.6.1.4.1.10428 9 1.102.6.2.8.1.1.1.15
		fkV2Dhcp4ClientIfLeasetimeOption OBJECT-TYPE
			SYNTAX INTEGER
				{
				notUsed(0),
				used(1)
				}
			MAX-ACCESS read-only
			STATUS current
			DESCRIPTION
				"The operating status of DHCP Client."
			DEFVAL { notUsed }
			::= { fkV2Dhcp4ClientIfEntry 15 }

		
		-- 1.3.6.1.4.1.10428 9 1.102.6.2.8.1.2
		fkV2Dhcp4ClientIfControl OBJECT IDENTIFIER ::= { fkV2Dhcp4ClientInterface 2 }

		
		-- 1.3.6.1.4.1.10428 9 1.102.6.2.8.1.2.1
		fkV2Dhcp4ClientIfControlRequest OBJECT-TYPE
			SYNTAX INTEGER
				{
				setDhcpClientActivity(1),
				setDhcpClientProfile(2),
				renewDhcpClientAddress(3),
				releaseDhcpClientAddress(4),
				setDhcpClientLeasetimeOption(5)
				}
			MAX-ACCESS read-write
			STATUS current
			DESCRIPTION
				"The request of a user command."
			::= { fkV2Dhcp4ClientIfControl 1 }

		
		-- 1.3.6.1.4.1.10428 9 1.102.6.2.8.1.2.2
		fkV2Dhcp4ClientIfControlStatus OBJECT-TYPE
			SYNTAX FkControlStatusType
			MAX-ACCESS read-only
			STATUS current
			DESCRIPTION
				"The status of a user command."
			::= { fkV2Dhcp4ClientIfControl 2 }

		
		-- 1.3.6.1.4.1.10428 9 1.102.6.2.8.1.2.3
		fkV2Dhcp4ClientIfControlTimer OBJECT-TYPE
			SYNTAX Gauge32
			MAX-ACCESS read-write
			STATUS current
			DESCRIPTION
				"The maximum wait time for the manager for a long running user command."
			::= { fkV2Dhcp4ClientIfControl 3 }

		
		-- 1.3.6.1.4.1.10428 9 1.102.6.2.8.1.2.4
		fkV2Dhcp4ClientIfControlTimeStamp OBJECT-TYPE
			SYNTAX TimeTicks
			MAX-ACCESS read-only
			STATUS current
			DESCRIPTION
				"The time stamp of the last command (end of command)."
			::= { fkV2Dhcp4ClientIfControl 4 }

		
		-- 1.3.6.1.4.1.10428 9 1.102.6.2.8.1.2.5
		fkV2Dhcp4ClientIfControlReqResult OBJECT-TYPE
			SYNTAX FkControlRequestResultType
			MAX-ACCESS read-only
			STATUS current
			DESCRIPTION
				"The result of the last user command."
			::= { fkV2Dhcp4ClientIfControl 5 }

		
		-- 1.3.6.1.4.1.10428 9 1.102.6.2.8.1.2.6
		fkV2Dhcp4ClientIfControlIndex OBJECT-TYPE
			SYNTAX INTEGER (1..4094)
			MAX-ACCESS read-write
			STATUS current
			DESCRIPTION
				"Network Interface Index."
			::= { fkV2Dhcp4ClientIfControl 6 }

		
		-- 1.3.6.1.4.1.10428 9 1.102.6.2.8.1.2.7
		fkV2Dhcp4ClientIfControlActivity OBJECT-TYPE
			SYNTAX INTEGER
				{
				disable(0),
				enable(1)
				}
			MAX-ACCESS read-write
			STATUS current
			DESCRIPTION
				"Network Interface Index."
			::= { fkV2Dhcp4ClientIfControl 7 }

		
		-- 1.3.6.1.4.1.10428 9 1.102.6.2.8.1.2.8
		fkV2Dhcp4ClientIfControlHostName OBJECT-TYPE
			SYNTAX OCTET STRING (SIZE (0 | 1..64))
			MAX-ACCESS read-write
			STATUS current
			DESCRIPTION
				"Description."
			::= { fkV2Dhcp4ClientIfControl 8 }

		
		-- 1.3.6.1.4.1.10428 9 1.102.6.2.8.1.2.9
		fkV2Dhcp4ClientIfControlRequestFlag OBJECT-TYPE
			SYNTAX BITS
				{
				unused0(0),
				subnetMask(1),
				timeOffset(2),
				router(3),
				timeServer(4),
				nameServer(5),
				domainNameServer(6),
				logServer(7),
				cookieServer(8),
				lprServer(9),
				impressServer(10),
				resourceLocationServer(11),
				hostName(12),
				bootFileSize(13),
				meritFile(14),
				domainName(15),
				swapServer(16),
				rootPath(17),
				extensionsPath(18),
				ipForwardState(19),
				nonLocalSourceRoutingState(20),
				policyFilter(21),
				maximumDatagramReassemblySize(22),
				defaultIpTimeToLive(23),
				pathMtuAgingTimeout(24),
				pathMtuPlateauTable(25),
				interfaceMtu(26),
				allSubnetsAreLocal(27),
				broadcastAddress(28),
				performMaskDiscovery(29),
				maskSupplier(30),
				performRouterDiscovery(31),
				routerSolicitationAddress(32),
				staticRoute(33),
				trailerEncapsulation(34),
				arpCacheTimeout(35),
				ethernetEncapsulationOption(36),
				tcpDefaultTtl(37),
				tcpKeepaliveInterval(38),
				tcpKeepaliveGarbage(39),
				nisDomain(40),
				nisServers(41),
				networkTimeProtocolServers(42),
				vendorSpecificInformation(43),
				netbiosOverTcpIpNameServer(44),
				netbiosOverTcpIpDatagramDistributionServer(45),
				netbiosOverTcpIpNodeType(46),
				netbiosOverTcpIpScope(47),
				xWindowSystemFontServer(48),
				xWindowSystemDisplayManager(49),
				requestedIpAddress(50),
				ipAddressLeaseTime(51),
				optionOverload(52),
				dhcpMessageType(53),
				serverIdentifier(54),
				unused55(55),
				message(56),
				maximumDhcpMessageSize(57),
				renewalTimeValue(58),
				rebindingTimeValue(59),
				vendorClassIdentifier(60),
				clientIdentifier(61),
				undefined62(62),
				undefined63(63),
				nisPlusDomain(64),
				nisPlusServers(65),
				tftpServerName(66),
				bootFileName(67),
				mobileIpHomeAgent(68),
				smtpServer(69),
				pop3Server(70),
				nntpServer(71),
				wwwServer(72),
				defaultFingerServer(73),
				ircServer(74),
				streetTalkServer(75),
				stdaServer(76)
				}
			MAX-ACCESS read-write
			STATUS current
			DESCRIPTION
				"Description."
			::= { fkV2Dhcp4ClientIfControl 9 }

		
		-- 1.3.6.1.4.1.10428 9 1.102.6.2.8.1.2.10
		fkV2Dhcp4ClientIfControlClientType OBJECT-TYPE
			SYNTAX INTEGER
				{
				text(0),
				hex(1)
				}
			MAX-ACCESS read-write
			STATUS current
			DESCRIPTION
				"DHCP Client-identifier input style.
				0 : text(ascii) string format
				1 : hexadecimal format"
			DEFVAL { text }
			::= { fkV2Dhcp4ClientIfControl 10 }

		
		-- 1.3.6.1.4.1.10428 9 1.102.6.2.8.1.2.11
		fkV2Dhcp4ClientIfControlClientId OBJECT-TYPE
			SYNTAX OCTET STRING (SIZE (0 | 1..64))
			MAX-ACCESS read-write
			STATUS current
			DESCRIPTION
				"DHCP Client-identifier value.
				This is used by DHCP clients to specify their unique identifier.
				DHCP servers use this value to index their database of address bindings.
				This value is expected to be unique for all clients in an administrative domain."
			::= { fkV2Dhcp4ClientIfControl 11 }

		
		-- 1.3.6.1.4.1.10428 9 1.102.6.2.8.1.2.12
		fkV2Dhcp4ClientIfControlClassType OBJECT-TYPE
			SYNTAX INTEGER
				{
				text(0),
				hex(1)
				}
			MAX-ACCESS read-write
			STATUS current
			DESCRIPTION
				"DHCP Class identifier input style.
				0 : text(ascii) string format
				1 : hexadecimal format"
			DEFVAL { text }
			::= { fkV2Dhcp4ClientIfControl 12 }

		
		-- 1.3.6.1.4.1.10428 9 1.102.6.2.8.1.2.13
		fkV2Dhcp4ClientIfControlClassId OBJECT-TYPE
			SYNTAX OCTET STRING (SIZE (0 | 1..64))
			MAX-ACCESS read-write
			STATUS current
			DESCRIPTION
				"DHCP Class identifier value.
				This is used by DHCP clients to optionally identify the vendor 
				type and configuration of a DHCP client.
				The information is a string of n octets, interpreted by servers.
				Vendors may choose to define specific vendor class identifiers 
				to convey particular configuration or other identification 
				information about a client.
				For example, the identifier may encode the client's hardware configuration."
			::= { fkV2Dhcp4ClientIfControl 13 }

		
		-- 1.3.6.1.4.1.10428 9 1.102.6.2.8.1.2.14
		fkV2Dhcp4ClientIfControlLeasetime OBJECT-TYPE
			SYNTAX INTEGER (120..2147483637)
			MAX-ACCESS read-write
			STATUS current
			DESCRIPTION
				"The leased time for IP address acquired by DHCP Client.
				Default lease-time: 3600s"
			::= { fkV2Dhcp4ClientIfControl 14 }

		
		-- 1.3.6.1.4.1.10428 9 1.102.6.2.8.1.2.15
		fkV2Dhcp4ClientIfControlLeasetimeOption OBJECT-TYPE
			SYNTAX INTEGER
				{
				notUsed(0),
				used(1)
				}
			MAX-ACCESS read-write
			STATUS current
			DESCRIPTION
				"The leased time for IP address acquired by DHCP Client.
				Default lease-time: 3600s"
			::= { fkV2Dhcp4ClientIfControl 15 }

		
		-- 1.3.6.1.4.1.10428 9 1.102.6.2.8.1.3
		fkV2Dhcp4ClientIfNotification OBJECT IDENTIFIER ::= { fkV2Dhcp4ClientInterface 3 }

		
		-- 1.3.6.1.4.1.10428 9 1.102.6.2.8.1.3.1
		fkV2Dhcp4ClientIfActivityChanged NOTIFICATION-TYPE
			OBJECTS { fkV2Dhcp4ClientIfControlRequest, fkV2Dhcp4ClientIfControlTimeStamp, fkV2Dhcp4ClientIfControlReqResult, fkV2Dhcp4ClientIfActivity }
			STATUS current
			DESCRIPTION 
				"Description."
			::= { fkV2Dhcp4ClientIfNotification 1 }

		
		-- 1.3.6.1.4.1.10428 9 1.102.6.2.8.1.3.2
		fkV2Dhcp4ClientIfProfileChanged NOTIFICATION-TYPE
			OBJECTS { fkV2Dhcp4ClientIfControlRequest, fkV2Dhcp4ClientIfControlTimeStamp, fkV2Dhcp4ClientIfControlReqResult, fkV2Dhcp4ClientIfHostName, fkV2Dhcp4ClientIfRequestFlag, 
				fkV2Dhcp4ClientIfClientType, fkV2Dhcp4ClientIfClientId, fkV2Dhcp4ClientIfClassType, fkV2Dhcp4ClientIfClassId, fkV2Dhcp4ClientIfLeasetime
				 }
			STATUS current
			DESCRIPTION 
				"Description."
			::= { fkV2Dhcp4ClientIfNotification 2 }

		
		-- 1.3.6.1.4.1.10428 9 1.102.6.2.8.1.3.3
		fkV2Dhcp4ClientIfRenewed NOTIFICATION-TYPE
			OBJECTS { fkV2Dhcp4ClientIfControlRequest, fkV2Dhcp4ClientIfControlTimeStamp, fkV2Dhcp4ClientIfControlReqResult, fkV2Dhcp4ClientIfControlIndex }
			STATUS current
			DESCRIPTION 
				"Description."
			::= { fkV2Dhcp4ClientIfNotification 3 }

		
		-- 1.3.6.1.4.1.10428 9 1.102.6.2.8.1.3.4
		fkV2Dhcp4ClientIfReleased NOTIFICATION-TYPE
			OBJECTS { fkV2Dhcp4ClientIfControlRequest, fkV2Dhcp4ClientIfControlTimeStamp, fkV2Dhcp4ClientIfControlReqResult, fkV2Dhcp4ClientIfControlIndex }
			STATUS current
			DESCRIPTION 
				"Description."
			::= { fkV2Dhcp4ClientIfNotification 4 }

		
		-- 1.3.6.1.4.1.10428 9 1.102.6.2.8.1.3.5
		fkV2Dhcp4ClientIfLeasetimeOptionChanged NOTIFICATION-TYPE
			OBJECTS { fkV2Dhcp4ClientIfControlRequest, fkV2Dhcp4ClientIfControlTimeStamp, fkV2Dhcp4ClientIfControlReqResult, fkV2Dhcp4ClientIfControlIndex }
			STATUS current
			DESCRIPTION 
				"Description."
			::= { fkV2Dhcp4ClientIfNotification 5 }

		
		-- 1.3.6.1.4.1.10428 9 1.102.6.2.8.2
		fkV2Dhcp4ClientOption OBJECT IDENTIFIER ::= { fkV2Dhcp4Client 2 }

		
		-- 1.3.6.1.4.1.10428 9 1.102.6.2.8.2.1
		fkV2Dhcp4ClientOptionTable OBJECT-TYPE
			SYNTAX SEQUENCE OF FkV2Dhcp4ClientOptionEntry
			MAX-ACCESS not-accessible
			STATUS current
			DESCRIPTION
				"Description."
			::= { fkV2Dhcp4ClientOption 1 }

		
		-- 1.3.6.1.4.1.10428 9 1.102.6.2.8.2.1.1
		fkV2Dhcp4ClientOptionEntry OBJECT-TYPE
			SYNTAX FkV2Dhcp4ClientOptionEntry
			MAX-ACCESS not-accessible
			STATUS current
			DESCRIPTION
				"Description."
			INDEX { fkV2Dhcp4ClientIfIndex, fkV2Dhcp4OptionCode, fkV2Dhcp4OptionInstance }
			::= { fkV2Dhcp4ClientOptionTable 1 }

		
		FkV2Dhcp4ClientOptionEntry ::=
			SEQUENCE { 
				fkV2Dhcp4ClientOptionCode
					INTEGER,
				fkV2Dhcp4ClientOptionInstance
					INTEGER,
				fkV2Dhcp4ClientOptionType
					INTEGER,
				fkV2Dhcp4ClientOptionValue
					OCTET STRING
			 }

		-- 1.3.6.1.4.1.10428 9 1.102.6.2.8.2.1.1.1
		fkV2Dhcp4ClientOptionCode OBJECT-TYPE
			SYNTAX INTEGER
				{
				subnetMask(1),
				timeOffset(2),
				router(3),
				timeServer(4),
				nameServer(5),
				domainNameServer(6),
				logServer(7),
				cookieServer(8),
				lprServer(9),
				impressServer(10),
				resourceLocationServer(11),
				hostName(12),
				bootFileSize(13),
				meritFile(14),
				domainName(15),
				swapServer(16),
				rootPath(17),
				extensionsPath(18),
				ipForwardState(19),
				nonLocalSourceRoutingState(20),
				policyFilter(21),
				maximumDatagramReassemblySize(22),
				defaultIpTimeToLive(23),
				pathMtuAgingTimeout(24),
				pathMtuPlateauTable(25),
				interfaceMtu(26),
				allSubnetsAreLocal(27),
				broadcastAddress(28),
				performMaskDiscovery(29),
				maskSupplier(30),
				performRouterDiscovery(31),
				routerSolicitationAddress(32),
				staticRoute(33),
				trailerEncapsulation(34),
				arpCacheTimeout(35),
				ethernetEncapsulationOption(36),
				tcpDefaultTtl(37),
				tcpKeepaliveInterval(38),
				tcpKeepaliveGarbage(39),
				nisDomain(40),
				nisServers(41),
				networkTimeProtocolServers(42),
				vendorSpecificInformation(43),
				netbiosOverTcpIpNameServer(44),
				netbiosOverTcpIpDatagramDistributionServer(45),
				netbiosOverTcpIpNodeType(46),
				netbiosOverTcpIpScope(47),
				xWindowSystemFontServer(48),
				xWindowSystemDisplayManager(49),
				requestedIpAddress(50),
				ipAddressLeaseTime(51),
				optionOverload(52),
				dhcpMessageType(53),
				serverIdentifier(54),
				parameterRequestList(55),
				message(56),
				maximumDhcpMessageSize(57),
				renewalTimeValue(58),
				rebindingTimeValue(59),
				vendorClassIdentifier(60),
				clientIdentifier(61),
				nisPlusDomain(64),
				nisPlusServers(65),
				tftpServerName(66),
				bootFileName(67),
				mobileIpHomeAgent(68),
				smtpServer(69),
				pop3Server(70),
				nntpServer(71),
				wwwServer(72),
				defaultFingerServer(73),
				ircServer(74),
				streetTalkServer(75),
				stdaServer(76)
				}
			MAX-ACCESS read-only
			STATUS current
			DESCRIPTION
				"3: default Gateway
				4: DNS Server"
			::= { fkV2Dhcp4ClientOptionEntry 1 }

		
		-- 1.3.6.1.4.1.10428 9 1.102.6.2.8.2.1.1.2
		fkV2Dhcp4ClientOptionInstance OBJECT-TYPE
			SYNTAX INTEGER (1..8)
			MAX-ACCESS read-only
			STATUS current
			DESCRIPTION
				"The IP address acquired by DHCP Client active in this interface."
			::= { fkV2Dhcp4ClientOptionEntry 2 }

		
		-- 1.3.6.1.4.1.10428 9 1.102.6.2.8.2.1.1.3
		fkV2Dhcp4ClientOptionType OBJECT-TYPE
			SYNTAX INTEGER
				{
				ipaddress(1),
				hex(2),
				text(3)
				}
			MAX-ACCESS read-only
			STATUS current
			DESCRIPTION
				"The subnet mask associated with the IP address acquired by DHCP Client.  
				The value of the mask is an IP address with all the network 
				bits set to 1 and all the hosts bits set to 0."
			::= { fkV2Dhcp4ClientOptionEntry 3 }

		
		-- 1.3.6.1.4.1.10428 9 1.102.6.2.8.2.1.1.4
		fkV2Dhcp4ClientOptionValue OBJECT-TYPE
			SYNTAX OCTET STRING (SIZE (1..64))
			MAX-ACCESS read-only
			STATUS current
			DESCRIPTION
				"The Gateway's IP address acquired by DHCP Client active in this interface."
			::= { fkV2Dhcp4ClientOptionEntry 4 }

		
		-- 1.3.6.1.4.1.10428 9 1.102.6.2.9
		fkV2Dhcp4Port OBJECT IDENTIFIER ::= { fkV2Dhcp4 9 }

		
		-- 1.3.6.1.4.1.10428 9 1.102.6.2.9.1
		fkV2Dhcp4PortLease OBJECT IDENTIFIER ::= { fkV2Dhcp4Port 1 }

		
		-- 1.3.6.1.4.1.10428 9 1.102.6.2.9.1.1
		fkV2Dhcp4PortLeaseTable OBJECT-TYPE
			SYNTAX SEQUENCE OF FkV2Dhcp4PortLeaseEntry
			MAX-ACCESS not-accessible
			STATUS current
			DESCRIPTION
				"Description."
			::= { fkV2Dhcp4PortLease 1 }

		
		-- 1.3.6.1.4.1.10428 9 1.102.6.2.9.1.1.1
		fkV2Dhcp4PortLeaseEntry OBJECT-TYPE
			SYNTAX FkV2Dhcp4PortLeaseEntry
			MAX-ACCESS not-accessible
			STATUS current
			DESCRIPTION
				"Description."
			INDEX { fkV2Dhcp4PortLeaseIndex }
			::= { fkV2Dhcp4PortLeaseTable 1 }

		
		FkV2Dhcp4PortLeaseEntry ::=
			SEQUENCE { 
				fkV2Dhcp4PortLeaseIndex
					InterfaceIndex,
				fkV2Dhcp4PortLeaseLimit
					INTEGER,
				fkV2Dhcp4PortLeaseCount
					Integer32
			 }

		-- 1.3.6.1.4.1.10428 9 1.102.6.2.9.1.1.1.1
		fkV2Dhcp4PortLeaseIndex OBJECT-TYPE
			SYNTAX InterfaceIndex
			MAX-ACCESS read-only
			STATUS current
			DESCRIPTION
				"Description."
			::= { fkV2Dhcp4PortLeaseEntry 1 }

		
		-- 1.3.6.1.4.1.10428 9 1.102.6.2.9.1.1.1.2
		fkV2Dhcp4PortLeaseLimit OBJECT-TYPE
			SYNTAX INTEGER (-1 | 1..256)
			MAX-ACCESS read-only
			STATUS current
			DESCRIPTION
				"Description."
			::= { fkV2Dhcp4PortLeaseEntry 2 }

		
		-- 1.3.6.1.4.1.10428 9 1.102.6.2.9.1.1.1.3
		fkV2Dhcp4PortLeaseCount OBJECT-TYPE
			SYNTAX Integer32
			MAX-ACCESS read-only
			STATUS current
			DESCRIPTION
				"Description."
			::= { fkV2Dhcp4PortLeaseEntry 3 }

		
		-- 1.3.6.1.4.1.10428 9 1.102.6.2.9.1.2
		fkV2Dhcp4PortAddrLeaseTable OBJECT-TYPE
			SYNTAX SEQUENCE OF FkV2Dhcp4PortAddrLeaseEntry
			MAX-ACCESS not-accessible
			STATUS current
			DESCRIPTION
				"Description."
			::= { fkV2Dhcp4PortLease 2 }

		
		-- 1.3.6.1.4.1.10428 9 1.102.6.2.9.1.2.1
		fkV2Dhcp4PortAddrLeaseEntry OBJECT-TYPE
			SYNTAX FkV2Dhcp4PortAddrLeaseEntry
			MAX-ACCESS not-accessible
			STATUS current
			DESCRIPTION
				"Description."
			INDEX { fkV2Dhcp4PortAddrtLeaseIndex, fkV2Dhcp4PortAddrLeaseAddress }
			::= { fkV2Dhcp4PortAddrLeaseTable 1 }

		
		FkV2Dhcp4PortAddrLeaseEntry ::=
			SEQUENCE { 
				fkV2Dhcp4PortAddrtLeaseIndex
					InterfaceIndex,
				fkV2Dhcp4PortAddrLeaseAddress
					IpAddress,
				fkV2Dhcp4PortAddrLeasePoolIndex
					INTEGER,
				fkV2Dhcp4PortAddrLeaseStatus
					INTEGER,
				fkV2Dhcp4PortAddrLeaseMac
					MacAddress,
				fkV2Dhcp4PortAddrLeaseHostName
					OCTET STRING,
				fkV2Dhcp4PortAddrLeaseClientId
					OCTET STRING,
				fkV2Dhcp4PortAddrLeaseRemoteId
					OCTET STRING,
				fkV2Dhcp4PortAddrLeaseCircuitId
					OCTET STRING,
				fkV2Dhcp4PortAddrLeaseStartTime
					Unsigned32,
				fkV2Dhcp4PortAddrLeaseFinishTime
					Unsigned32
			 }

		-- 1.3.6.1.4.1.10428 9 1.102.6.2.9.1.2.1.1
		fkV2Dhcp4PortAddrtLeaseIndex OBJECT-TYPE
			SYNTAX InterfaceIndex
			MAX-ACCESS read-write
			STATUS current
			DESCRIPTION
				"Description."
			::= { fkV2Dhcp4PortAddrLeaseEntry 1 }

		
		-- 1.3.6.1.4.1.10428 9 1.102.6.2.9.1.2.1.2
		fkV2Dhcp4PortAddrLeaseAddress OBJECT-TYPE
			SYNTAX IpAddress
			MAX-ACCESS read-only
			STATUS current
			DESCRIPTION
				"Description."
			::= { fkV2Dhcp4PortAddrLeaseEntry 2 }

		
		-- 1.3.6.1.4.1.10428 9 1.102.6.2.9.1.2.1.3
		fkV2Dhcp4PortAddrLeasePoolIndex OBJECT-TYPE
			SYNTAX INTEGER (1..255)
			MAX-ACCESS read-only
			STATUS current
			DESCRIPTION
				"Description."
			::= { fkV2Dhcp4PortAddrLeaseEntry 3 }

		
		-- 1.3.6.1.4.1.10428 9 1.102.6.2.9.1.2.1.4
		fkV2Dhcp4PortAddrLeaseStatus OBJECT-TYPE
			SYNTAX INTEGER
				{
				fixed(1),
				offered(2),
				bound(3),
				abandon(4),
				free(5)
				}
			MAX-ACCESS read-only
			STATUS current
			DESCRIPTION
				"Description."
			::= { fkV2Dhcp4PortAddrLeaseEntry 4 }

		
		-- 1.3.6.1.4.1.10428 9 1.102.6.2.9.1.2.1.5
		fkV2Dhcp4PortAddrLeaseMac OBJECT-TYPE
			SYNTAX MacAddress
			MAX-ACCESS read-only
			STATUS current
			DESCRIPTION
				"Description."
			::= { fkV2Dhcp4PortAddrLeaseEntry 5 }

		
		-- 1.3.6.1.4.1.10428 9 1.102.6.2.9.1.2.1.6
		fkV2Dhcp4PortAddrLeaseHostName OBJECT-TYPE
			SYNTAX OCTET STRING (SIZE (0 | 1..64))
			MAX-ACCESS read-write
			STATUS current
			DESCRIPTION
				"Description."
			::= { fkV2Dhcp4PortAddrLeaseEntry 6 }

		
		-- 1.3.6.1.4.1.10428 9 1.102.6.2.9.1.2.1.7
		fkV2Dhcp4PortAddrLeaseClientId OBJECT-TYPE
			SYNTAX OCTET STRING (SIZE (0 | 1..64))
			MAX-ACCESS read-only
			STATUS current
			DESCRIPTION
				"Description."
			::= { fkV2Dhcp4PortAddrLeaseEntry 7 }

		
		-- 1.3.6.1.4.1.10428 9 1.102.6.2.9.1.2.1.8
		fkV2Dhcp4PortAddrLeaseRemoteId OBJECT-TYPE
			SYNTAX OCTET STRING (SIZE (0 | 1..32))
			MAX-ACCESS read-only
			STATUS current
			DESCRIPTION
				"Description."
			::= { fkV2Dhcp4PortAddrLeaseEntry 8 }

		
		-- 1.3.6.1.4.1.10428 9 1.102.6.2.9.1.2.1.9
		fkV2Dhcp4PortAddrLeaseCircuitId OBJECT-TYPE
			SYNTAX OCTET STRING (SIZE (0 | 1..32))
			MAX-ACCESS read-only
			STATUS current
			DESCRIPTION
				"Description."
			::= { fkV2Dhcp4PortAddrLeaseEntry 9 }

		
		-- 1.3.6.1.4.1.10428 9 1.102.6.2.9.1.2.1.10
		fkV2Dhcp4PortAddrLeaseStartTime OBJECT-TYPE
			SYNTAX Unsigned32
			MAX-ACCESS read-only
			STATUS current
			DESCRIPTION
				"Description."
			::= { fkV2Dhcp4PortAddrLeaseEntry 10 }

		
		-- 1.3.6.1.4.1.10428 9 1.102.6.2.9.1.2.1.11
		fkV2Dhcp4PortAddrLeaseFinishTime OBJECT-TYPE
			SYNTAX Unsigned32
			MAX-ACCESS read-only
			STATUS current
			DESCRIPTION
				"Description."
			::= { fkV2Dhcp4PortAddrLeaseEntry 11 }

		
		-- 1.3.6.1.4.1.10428 9 1.102.6.2.9.1.3
		fkV2Dhcp4PortLeaseControl OBJECT IDENTIFIER ::= { fkV2Dhcp4PortLease 3 }

		
		-- 1.3.6.1.4.1.10428 9 1.102.6.2.9.1.3.1
		fkV2Dhcp4PortLeaseControlRequest OBJECT-TYPE
			SYNTAX INTEGER { setDhcp4PortLeaseLimit(1) }
			MAX-ACCESS read-write
			STATUS current
			DESCRIPTION
				"Description."
			::= { fkV2Dhcp4PortLeaseControl 1 }

		
		-- 1.3.6.1.4.1.10428 9 1.102.6.2.9.1.3.2
		fkV2Dhcp4PortLeaseControlStatus OBJECT-TYPE
			SYNTAX FkControlStatusType
			MAX-ACCESS read-only
			STATUS current
			DESCRIPTION
				"Description."
			::= { fkV2Dhcp4PortLeaseControl 2 }

		
		-- 1.3.6.1.4.1.10428 9 1.102.6.2.9.1.3.3
		fkV2Dhcp4PortLeaseControlTimer OBJECT-TYPE
			SYNTAX Gauge32
			MAX-ACCESS read-write
			STATUS current
			DESCRIPTION
				"Description."
			::= { fkV2Dhcp4PortLeaseControl 3 }

		
		-- 1.3.6.1.4.1.10428 9 1.102.6.2.9.1.3.4
		fkV2Dhcp4PortLeaseControlTimeStamp OBJECT-TYPE
			SYNTAX TimeTicks
			MAX-ACCESS read-only
			STATUS current
			DESCRIPTION
				"Description."
			::= { fkV2Dhcp4PortLeaseControl 4 }

		
		-- 1.3.6.1.4.1.10428 9 1.102.6.2.9.1.3.5
		fkV2Dhcp4PortLeaseControlReqResult OBJECT-TYPE
			SYNTAX FkControlRequestResultType
			MAX-ACCESS read-only
			STATUS current
			DESCRIPTION
				"Description."
			::= { fkV2Dhcp4PortLeaseControl 5 }

		
		-- 1.3.6.1.4.1.10428 9 1.102.6.2.9.1.3.6
		fkV2Dhcp4PortLeaseControlIndex OBJECT-TYPE
			SYNTAX InterfaceIndex
			MAX-ACCESS read-write
			STATUS current
			DESCRIPTION
				"Description."
			::= { fkV2Dhcp4PortLeaseControl 6 }

		
		-- 1.3.6.1.4.1.10428 9 1.102.6.2.9.1.3.7
		fkV2Dhcp4PortLeaseControlLimit OBJECT-TYPE
			SYNTAX INTEGER (-1 | 1..256)
			MAX-ACCESS read-write
			STATUS current
			DESCRIPTION
				"Description."
			::= { fkV2Dhcp4PortLeaseControl 7 }

		
		-- 1.3.6.1.4.1.10428 9 1.102.6.2.9.1.4
		fkV2DhcpPortLeaseNotification OBJECT IDENTIFIER ::= { fkV2Dhcp4PortLease 4 }

		
		-- 1.3.6.1.4.1.10428 9 1.102.6.2.9.1.4.1
		fkV2Dhcp4PortLeaseLimitChanged NOTIFICATION-TYPE
			OBJECTS { fkV2Dhcp4PortLeaseControlRequest, fkV2Dhcp4PortLeaseControlTimeStamp, fkV2Dhcp4PortLeaseControlReqResult, fkV2Dhcp4PortLeaseLimit }
			STATUS current
			DESCRIPTION 
				"Description."
			::= { fkV2DhcpPortLeaseNotification 1 }

		
		-- 1.3.6.1.4.1.10428 9 1.102.6.3
		fkV2Dhcp6 OBJECT IDENTIFIER ::= { fkV2Dhcp 3 }

		
		-- 1.3.6.1.4.1.10428 9 1.102.6.4
		fkV2DhcpGroup OBJECT-GROUP
			OBJECTS { fkV2Dhcp4ClassRangeStart, fkV2Dhcp4ClassRangeEnd, fkV2Dhcp4ClassRangeControlRequest, fkV2Dhcp4ClassRangeControlStatus, fkV2Dhcp4ClassRangeControlTimer, 
				fkV2Dhcp4ClassRangeControlTimeStamp, fkV2Dhcp4ClassRangeControlReqResult, fkV2Dhcp4ClassRangeControlPoolIndex, fkV2Dhcp4ClassRangeControlStart, fkV2Dhcp4ClassRangeControlEnd, 
				fkV2Dhcp4RelayHelperAddress, fkV2Dhcp4RelayHelperControlRequest, fkV2Dhcp4RelayHelperControlStatus, fkV2Dhcp4RelayHelperControlTimer, fkV2Dhcp4RelayHelperControlTimeStamp, 
				fkV2Dhcp4RelayHelperControlReqResult, fkV2Dhcp4RelayHelperControlIfIndex, fkV2Dhcp4RelayHelperControlAddress, fkV2Dhcp4DatabaseURL, fkV2Dhcp4DatabaseInterval, 
				fkV2Dhcp4PingTimeout, fkV2Dhcp4Option82Policy, fkV2Dhcp4Option82SystemRemoteId, fkV2Dhcp4ControlDatabaseURL, fkV2Dhcp4ControlDatabaseInterval, 
				fkV2Dhcp4ControlPingTimeout, fkV2Dhcp4ControlOption82Policy, fkV2Dhcp4ControlOption82SystemRemoteId, fkV2Dhcp4PoolIndex, fkV2Dhcp4PoolName, 
				fkV2Dhcp4PoolDefaultLeaseTime, fkV2Dhcp4PoolMaxLeaseTime, fkV2Dhcp4PoolDomainName, fkV2Dhcp4PoolSummaryTotal, fkV2Dhcp4PoolSummaryAllocated, 
				fkV2Dhcp4PoolSummaryBound, fkV2Dhcp4PoolSummaryOffered, fkV2Dhcp4PoolSummaryFixed, fkV2Dhcp4PoolSummaryAbandon, fkV2Dhcp4PoolSummaryAvailable, 
				fkV2Dhcp4PoolControlRequest, fkV2Dhcp4PoolControlStatus, fkV2Dhcp4PoolControlTimer, fkV2Dhcp4PoolControlTimeStamp, fkV2Dhcp4PoolControlReqResult, 
				fkV2Dhcp4PoolControlIndex, fkV2Dhcp4PoolControlName, fkV2Dhcp4PoolControlDefaultLeaseTime, fkV2Dhcp4PoolControlMaxLeaseTime, fkV2Dhcp4PoolControlDomainName, 
				fkV2Dhcp4PoolControlOriginURL, fkV2Dhcp4PoolControlOriginFileName, fkV2Dhcp4NetworkAddress, fkV2Dhcp4NetworkMask, fkV2Dhcp4NetworkControlRequest, 
				fkV2Dhcp4NetworkControlStatus, fkV2Dhcp4NetworkControlTimer, fkV2Dhcp4NetworkControlTimeStamp, fkV2Dhcp4NetworkControlReqResult, fkV2Dhcp4NetworkControlAddress, 
				fkV2Dhcp4NetworkControlMask, fkV2Dhcp4RangeStart, fkV2Dhcp4RangeEnd, fkV2Dhcp4RangeControlRequest, fkV2Dhcp4RangeControlStatus, 
				fkV2Dhcp4RangeControlTimer, fkV2Dhcp4RangeControlTimeStamp, fkV2Dhcp4RangeControlReqResult, fkV2Dhcp4RangeControlPoolIndex, fkV2Dhcp4RangeControlStart, 
				fkV2Dhcp4RangeControlEnd, fkV2Dhcp4FixedMac, fkV2Dhcp4FixedControlRequest, fkV2Dhcp4FixedControlStatus, fkV2Dhcp4FixedControlTimer, 
				fkV2Dhcp4FixedControlTimeStamp, fkV2Dhcp4FixedControlReqResult, fkV2Dhcp4DnsIndex, fkV2Dhcp4DnsControlRequest, fkV2Dhcp4DnsControlStatus, 
				fkV2Dhcp4DnsControlTimer, fkV2Dhcp4DnsControlTimeStamp, fkV2Dhcp4DnsControlReqResult, fkV2Dhcp4DnsControlPoolIndex, fkV2Dhcp4DnsControlIndex, 
				fkV2Dhcp4DefaultGatewayIndex, fkV2Dhcp4DefaultGatewayControlRequest, fkV2Dhcp4DefaultGatewayControlStatus, fkV2Dhcp4DefaultGatewayControlTimer, fkV2Dhcp4DefaultGatewayControlTimeStamp, 
				fkV2Dhcp4DefaultGatewayControlReqResult, fkV2Dhcp4DefaultGatewayControlPoolIndex, fkV2Dhcp4DefaultGatewayControlIndex, fkV2Dhcp4OptionCode, fkV2Dhcp4OptionInstance, 
				fkV2Dhcp4OptionType, fkV2Dhcp4OptionValue, fkV2Dhcp4OptionControlRequest, fkV2Dhcp4OptionControlStatus, fkV2Dhcp4OptionControlTimer, 
				fkV2Dhcp4OptionControlTimeStamp, fkV2Dhcp4OptionControlReqResult, fkV2Dhcp4OptionControlCode, fkV2Dhcp4OptionControlInstance, fkV2Dhcp4OptionControlType, 
				fkV2Dhcp4OptionControlValue, fkV2Dhcp4ClassName, fkV2Dhcp4ClassControlRequest, fkV2Dhcp4ClassControlStatus, fkV2Dhcp4ClassControlTimer, 
				fkV2Dhcp4ClassControlReqResult, fkV2Dhcp4Option82TrustDefault, fkV2Dhcp4FilterPortControlRequest, fkV2Dhcp4FilterPortControlStatus, fkV2Dhcp4FilterPortControlTimer, 
				fkV2Dhcp4FilterPortControlTimeStamp, fkV2Dhcp4FilterPortControlReqResult, fkV2Dhcp4FilterPortControlIndex, fkV2Dhcp4FilterAddressMac, fkV2Dhcp4FilterAddressControlRequest, 
				fkV2Dhcp4FilterAddressControlStatus, fkV2Dhcp4FilterAddressControlTimer, fkV2Dhcp4FilterAddressControlTimeStamp, fkV2Dhcp4FilterAddressControlReqResult, fkV2Dhcp4FilterAddressControlMac, 
				fkV2Dhcp4PacketStatsReceived, fkV2Dhcp4PacketStatsSent, fkV2Dhcp4PacketStatsReceivedErrors, fkV2Dhcp4PacketStatsSentErrors, fkV2Dhcp4PacketStatsBootpReceivedRequests, 
				fkV2Dhcp4PacketStatsBootpReceivedReplies, fkV2Dhcp4PacketStatsBootpSentRequests, fkV2Dhcp4PacketStatsBootpSentReplies, fkV2Dhcp4PacketStatsReceivedDiscover, fkV2Dhcp4PacketStatsReceivedRequest, 
				fkV2Dhcp4PacketStatsReceivedRelease, fkV2Dhcp4PacketStatscReceivedInform, fkV2Dhcp4PacketStatsReceivedDecline, fkV2Dhcp4PacketStatsSentOffer, fkV2Dhcp4PacketStatsSentAck, 
				fkV2Dhcp4PacketStatsSentNak, fkV2Dhcp4DatabaseKey, fkV2Dhcp4DebugStatus, fkV2Dhcp4AuthArpTime, fkV2Dhcp4AuthArpLeft, 
				fkV2Dhcp4SummaryPoolCnt, fkV2Dhcp4SummaryTotal, fkV2Dhcp4SummaryAvailable, fkV2Dhcp4SummaryAbandon, fkV2Dhcp4SummaryBound, 
				fkV2Dhcp4SummaryOffered, fkV2Dhcp4SummaryFixed, fkV2Dhcp4ControlDatabaseKey, fkV2Dhcp4ControlDebugStatus, fkV2Dhcp4IllegalMac, 
				fkV2Dhcp4IllegalTime, fkV2Dhcp4IllegalControlRequest, fkV2Dhcp4IllegalControlStatus, fkV2Dhcp4IllegalControlTimer, fkV2Dhcp4IllegalControlTimeStamp, 
				fkV2Dhcp4IllegalControlReqResult, fkV2Dhcp4ClassControlName, fkV2Dhcp4ControlOption82TrustDefault, fkV2Dhcp4ClassControlTimeStamp, fkV2Dhcp4FixedControlPoolIndex, 
				fkV2Dhcp4FixedControlAddress, fkV2Dhcp4FixedControlMac, fkV2Dhcp4ServiceActivity, fkV2Dhcp4ClassUsage, fkV2Dhcp4SmartRelayUsage, 
				fkV2Dhcp4Option82Usage, fkV2Dhcp4ControlClassUsage, fkV2Dhcp4ControlSmartRelayUsage, fkV2Dhcp4ControlOption82Usage, fkV2Dhcp4NetworkControlPoolIndex, 
				fkV2Dhcp4FixedAddress, fkV2Dhcp4DnsAddress, fkV2Dhcp4DnsControlAddress, fkV2Dhcp4DefaultGatewayAddress, fkV2Dhcp4DefaultGatewayControlAddress, 
				fkV2Dhcp4OptionControlPoolIndex, fkV2Dhcp4FilterPortState, fkV2Dhcp4FilterPortControlState, fkV2Dhcp4ClientIfIndex, fkV2Dhcp4ClientIfActivity, 
				fkV2Dhcp4ClientIfAddress, fkV2Dhcp4ClientIfMask, fkV2Dhcp4ClientIfServer, fkV2Dhcp4ClientIfClientType, fkV2Dhcp4ClientIfClientId, 
				fkV2Dhcp4ClientIfClassType, fkV2Dhcp4ClientIfClassId, fkV2Dhcp4ClientIfLeasetime, fkV2Dhcp4ClientIfExpired, fkV2Dhcp4ClientIfState, 
				fkV2Dhcp4ClientIfControlRequest, fkV2Dhcp4ClientIfControlStatus, fkV2Dhcp4ClientIfControlTimer, fkV2Dhcp4ClientIfControlTimeStamp, fkV2Dhcp4ClientIfControlReqResult, 
				fkV2Dhcp4ClientIfControlIndex, fkV2Dhcp4ClientIfControlClientType, fkV2Dhcp4ClientIfControlClientId, fkV2Dhcp4ClientIfControlClassType, fkV2Dhcp4ClientIfControlClassId, 
				fkV2Dhcp4ClientIfControlLeasetime, fkV2Dhcp4ClientOptionCode, fkV2Dhcp4ClientOptionInstance, fkV2Dhcp4ClientOptionType, fkV2Dhcp4ClientOptionValue, 
				fkV2Dhcp4RelayIfIndex, fkV2Dhcp4Option82SystemRemoteType, fkV2Dhcp4ControlOption82SystemRemoteType, fkV2Ds4Activity, fkV2Ds4VerifyMacState, 
				fkV2Ds4DatabaseURL, fkV2Ds4DatabaseInterval, fkV2Ds4ControlRequest, fkV2Ds4ControlStatus, fkV2Ds4ControlTimer, 
				fkV2Ds4ControlTimeStamp, fkV2Ds4ControlReqResult, fkV2Ds4ControlActivity, fkV2Ds4ControlVerifyMacState, fkV2Ds4ControlDatabaseURL, 
				fkV2Ds4ControlDatabaseInterval, fkV2Ds4VlanIndex, fkV2Ds4VlanState, fkV2Ds4VlanControlRequest, fkV2Ds4VlanControlStatus, 
				fkV2Ds4VlanControlTimer, fkV2Ds4VlanControlTimeStamp, fkV2Ds4VlanControlReqResult, fkV2Ds4VlanControlState, fkV2Ds4PortIndex, 
				fkV2Ds4PortTrustState, fkV2Ds4PortLimitRate, fkV2Ds4PortLimitLease, fkV2Ds4PortSrcGuardState, fkV2Ds4PortControlRequest, 
				fkV2Ds4PortControlStatus, fkV2Ds4PortControlTimer, fkV2Ds4PortControlTimeStamp, fkV2Ds4PortControlReqResult, fkV2Ds4PortControlTrustState, 
				fkV2Ds4PortControlLimitRate, fkV2Ds4PortControlLimitLease, fkV2Ds4PortControlSrcGuardState, fkV2Ds4BindingsVlanIndex, fkV2Ds4BindingsPortIndex, 
				fkV2Ds4BindingsAddress, fkV2Ds4BindingsMac, fkV2Ds4BindingsType, fkV2Ds4BindingsLeasedTime, fkV2Ds4BindingsControlRequest, 
				fkV2Ds4BindingsControlStatus, fkV2Ds4BindingsControlTimer, fkV2Ds4BindingsControlTimeStamp, fkV2Ds4BindingsControlReqResult, fkV2Ds4BindingsControlVlanIndex, 
				fkV2Ds4BindingsControlPortIndex, fkV2Ds4BindingsControlAddress, fkV2Ds4BindingsControlMac, fkV2Dhcp4IllegalAddress, fkV2Dhcp4ControlServiceActivity, 
				fkV2Dhcp4ClientIfControlRequestFlag, fkV2Dhcp4ClientIfControlHostName, fkV2Dhcp4ClientIfRequestFlag, fkV2Dhcp4ClientIfHostName, fkV2Dhcp4ControlAuthArpTime, 
				fkV2Dhcp4ControlRequest, fkV2Dhcp4ControlStatus, fkV2Dhcp4ControlTimer, fkV2Dhcp4ControlTimeStamp, fkV2Dhcp4ControlReqResult, 
				fkV2Dhcp4ClientIfControlActivity, fkV2Ds4BindingsState, fkV2Dhcp4LeasedAddress, fkV2Dhcp4LeasedPoolIndex, fkV2Dhcp4LeasedStatus, 
				fkV2Dhcp4LeasedMac, fkV2Dhcp4LeasedHostName, fkV2Dhcp4LeasedClientId, fkV2Dhcp4LeasedRemoteId, fkV2Dhcp4LeasedCircuitId, 
				fkV2Dhcp4LeasedStartTime, fkV2Dhcp4LeasedFinishTime, fkV2Dhcp4LeasedControlRequest, fkV2Dhcp4LeasedControlStatus, fkV2Dhcp4LeasedControlTimer, 
				fkV2Dhcp4LeasedControlTimeStamp, fkV2Dhcp4LeasedControlReqResult, fkV2Dhcp4RelayHelperType, fkV2Dhcp4RelayHelperControlType, fkV2Dhcp4LeasedControlPoolIndex, 
				fkV2Dhcp4LeasedControlAddress, fkV2Dhcp4LeasedControlMask, fkV2Ds4VlanControlIndex, fkV2Ds4PortControlIndex, fkV2Dhcp4RelayIfControlRequest, 
				fkV2Dhcp4RelayIfControlStatus, fkV2Dhcp4RelayIfControlTimer, fkV2Dhcp4RelayIfControlTimeStamp, fkV2Dhcp4RelayIfControllReqResult, fkV2Dhcp4RelayIfControlIndex, 
				fkV2Ds4BindingsControlType, fkV2Dhcp4FilterPortIndex, fkV2Ds4BindingsControlLeasedTime, fkV2Dhcp4Option82PortIndex, fkV2Dhcp4Option82PortCircuitType, 
				fkV2Dhcp4Option82PortCircuitId, fkV2Dhcp4Option82PortTrustState, fkV2Dhcp4Option82PortControlRequest, fkV2Dhcp4Option82PortControlStatus, fkV2Dhcp4Option82PortControlTimer, 
				fkV2Dhcp4Option82PortControlTimeStamp, fkV2Dhcp4Option82PortControlReqResult, fkV2Dhcp4Option82PortControlIndex, fkV2Dhcp4Option82PortControlCircuitType, fkV2Dhcp4Option82PortControlCircuitId, 
				fkV2Dhcp4Option82PortControlTrustState, fkV2Dhcp4RelayIfSimpleOpt82AdminState, fkV2Dhcp4RelayIfSimpleOpt82OperState, fkV2Dhcp4RelayHelperOui, fkV2Dhcp4RelayHelperControlOui, 
				fkV2Dhcp4RelayIfControlSimpleOpt82AdminState, fkV2Dhcp4PacketStatsControlRequest, fkV2Dhcp4PacketStatsControlStatus, fkV2Dhcp4PacketStatsControlTimer, fkV2Dhcp4PacketStatsControlTimeStamp, 
				fkV2Dhcp4PacketStatsControlReqResult, fkV2Dhcp4CRCMapClass, fkV2Dhcp4CRCMapRemote, fkV2Dhcp4CRCMapCircuit, fkV2Dhcp4CRCMapControlRequest, 
				fkV2Dhcp4CRCMapControlStatus, fkV2Dhcp4CRCMapControlTimer, fkV2Dhcp4CRCMapControlTimeStamp, fkV2Dhcp4CRCMapControlReqResult, fkV2Dhcp4CRCMapControlClass, 
				fkV2Dhcp4CRCMapControlRemote, fkV2Dhcp4Option82Drop, fkV2Dhcp4ControlOption82Drop, fkV2Dhcp4ClassRangeControlName, fkV2Dhcp4RemoteId, 
				fkV2Dhcp4RemoteType, fkV2Dhcp4RemoteClass, fkV2Dhcp4RemoteTrust, fkV2Dhcp4RemoteControlRequest, fkV2Dhcp4RemoteControlStatus, 
				fkV2Dhcp4RemoteControlTimer, fkV2Dhcp4RemoteControlTimeStamp, fkV2Dhcp4RemoteControlReqResult, fkV2Dhcp4RemoteControlId, fkV2Dhcp4RemoteControlType, 
				fkV2Dhcp4RemoteControlClass, fkV2Dhcp4RemoteControlTrust, fkV2Dhcp4RCircuitId, fkV2Dhcp4RCircuitType, fkV2Dhcp4RCircuitClass, 
				fkV2Dhcp4RCircuitControlRequest, fkV2Dhcp4RCircuitControlStatus, fkV2Dhcp4RCircuitControlTimer, fkV2Dhcp4RCircuitControlTimeStamp, fkV2Dhcp4RCircuitControlReqResult, 
				fkV2Dhcp4RCircuitControlRemote, fkV2Dhcp4RCircuitControlId, fkV2Dhcp4RCircuitControlType, fkV2Dhcp4ClientHardwareAddress, fkV2Dhcp4ControlClientHardwareAddress, 
				fkV2Dhcp4PoolMeritDumpPath, fkV2Dhcp4PoolRootPath, fkV2Dhcp4PoolControlMeritDumpPath, fkV2Dhcp4PoolControlRootPath, fkV2Dhcp4LogsIndex, 
				fkV2Dhcp4LogsAddress, fkV2Dhcp4LogsControlRequest, fkV2Dhcp4LogsControlStatus, fkV2Dhcp4LogsControlTimer, fkV2Dhcp4LogsControlTimeStamp, 
				fkV2Dhcp4LogsControlReqResult, fkV2Dhcp4LogsControlPoolIndex, fkV2Dhcp4LogsControlIndex, fkV2Dhcp4LogsControlAddress, fkV2Dhcp4NtpIndex, 
				fkV2Dhcp4NtpAddress, fkV2Dhcp4NtpControlRequest, fkV2Dhcp4NtpControlStatus, fkV2Dhcp4NtpControlTimer, fkV2Dhcp4NtpControlTimeStamp, 
				fkV2Dhcp4NtpControlReqResult, fkV2Dhcp4NtpControlPoolIndex, fkV2Dhcp4NtpControlIndex, fkV2Dhcp4NtpControlAddress, fkV2Ds4PortTimeout, 
				fkV2Ds4PortStatus, fkV2Ds4PortControlTimeout, fkV2Ds4PortControlPStatus, fkV2Ds4BindingsMaskLen, fkV2Ds4BindingsControlMaskLen, 
				fkV2Ds4PortFilterMode, fkV2Ds4PortFilterDelayTimer, fkV2Ds4PortFilterDelayCounter, fkV2Ds4PortControlFilterMode, fkV2Ds4PortControlFilterDelayTimer, 
				fkV2Ds4PortControlFilterDelayCounter, fkV2Dhcp4PortLeaseIndex, fkV2Dhcp4PortLeaseLimit, fkV2Dhcp4PortLeaseCount, fkV2Dhcp4PortLeaseControlRequest, 
				fkV2Dhcp4PortLeaseControlStatus, fkV2Dhcp4PortLeaseControlTimer, fkV2Dhcp4PortLeaseControlTimeStamp, fkV2Dhcp4PortLeaseControlReqResult, fkV2Dhcp4PortLeaseControlIndex, 
				fkV2Dhcp4PortLeaseControlLimit, fkV2Dhcp4PacketStatsPortReceived, fkV2Dhcp4PacketStatsPortSent, fkV2Dhcp4PacketStatsPortReceivedError, fkV2Dhcp4PacketStatsPortSentError, 
				fkV2Dhcp4PacketStatsPortReceivedDiscover, fkV2Dhcp4PacketStatsPortReceivedRequest, fkV2Dhcp4PacketStatsPortReceivedRelease, fkV2Dhcp4PacketStatsPortReceivedInform, fkV2Dhcp4PacketStatsPortReceivedDecline, 
				fkV2Dhcp4PacketStatsPortSentOffer, fkV2Dhcp4PacketStatsPortSentAck, fkV2Dhcp4PacketStatsPortSentNak, fkV2Dhcp4PacketStatsPortIndex, fkV2Dhcp4PEStatus, 
				fkV2Dhcp4ControlPEStatus, fkV2Dhcp4PEVendorIfIndex, fkV2Dhcp4PEVendorID, fkV2Dhcp4PEVendorStart, fkV2Dhcp4PEVendorEnd, 
				fkV2Dhcp4PEVendorControlRequest, fkV2Dhcp4PEVendorControlStatus, fkV2Dhcp4PEVendorControlTimer, fkV2Dhcp4PEVendorControlTimeStamp, fkV2Dhcp4PEVendorControlReqResult, 
				fkV2Dhcp4PEVendorControlIfIndex, fkV2Dhcp4PEVendorControlVendorID, fkV2Dhcp4PEVendorControlStart, fkV2Dhcp4PEVendorControlEnd, fkV2Dhcp4PEAddressIfIndex, 
				fkV2Dhcp4PEAddressStart, fkV2Dhcp4PEAddressEnd, fkV2Dhcp4PEAddressControlRequest, fkV2Dhcp4PEAddressControlStatus, fkV2Dhcp4PEAddressControlTimer, 
				fkV2Dhcp4PEAddressControlTimeStamp, fkV2Dhcp4PEAddressControlReqResult, fkV2Dhcp4PEAddressControlStart, fkV2Dhcp4PEAddressControlEnd, fkV2Dhcp4PENonPEStart, 
				fkV2Dhcp4PENonPEEnd, fkV2Dhcp4PENonPEControlRequest, fkV2Dhcp4PENonPEControlStatus, fkV2Dhcp4PENonPEControlTimer, fkV2Dhcp4PENonPEControlTimeStamp, 
				fkV2Dhcp4PENonPEControlReqResult, fkV2Dhcp4PENonPEControlStart, fkV2Dhcp4PENonPEControlEnd, fkV2Dhcp4RCircuitControlClass, fkV2Dhcp4ArpPingFlag, 
				fkV2Dhcp4ArpRetransmits, fkV2Dhcp4ArpTimeout, fkV2Dhcp4PingRetransmits, fkV2Dhcp4ControlArpPingFlag, fkV2Dhcp4ControlArpRetransmits, 
				fkV2Dhcp4ControlArpTimeout, fkV2Dhcp4ControlPingRetransmits, fkV2Dhcp4PortAddrtLeaseIndex, fkV2Dhcp4PortAddrLeaseAddress, fkV2Dhcp4PortAddrLeasePoolIndex, 
				fkV2Dhcp4PortAddrLeaseStatus, fkV2Dhcp4PortAddrLeaseMac, fkV2Dhcp4PortAddrLeaseHostName, fkV2Dhcp4PortAddrLeaseClientId, fkV2Dhcp4PortAddrLeaseRemoteId, 
				fkV2Dhcp4PortAddrLeaseCircuitId, fkV2Dhcp4PortAddrLeaseStartTime, fkV2Dhcp4PortAddrLeaseFinishTime, fkV2Dhcp4PEVendorPoolIndex, fkV2Dhcp4PEVendorControlPoolIndex, 
				fkV2Dhcp4PEAddressPoolIndex, fkV2Dhcp4PEAddressControlIfIndex, fkV2Dhcp4PENonPEPoolIndex, fkV2Dhcp4PoolSummaryNetwork, fkV2Dhcp4SummaryAllocated, 
				fkV2Dhcp4StateIndex, fkV2Dhcp4StateTotal, fkV2Dhcp4StateFixed, fkV2Dhcp4StateDynamic, fkV2Dhcp4StatePEntry, 
				fkV2Dhcp4StateBindIpAddress, fkV2Dhcp4StateBindMac, fkV2Dhcp4StateBindState, fkV2Dhcp4StateBindType, fkV2Dhcp4StateBindExpiration, 
				fkV2Dhcp4StateBindPort, fkV2Dhcp4StatePoolTotal, fkV2Dhcp4StatePoolFixed, fkV2Dhcp4StatePoolDynamic, fkV2Dhcp4StatePoolPEntry, 
				fkV2Dhcp4StateBindPoolIndex, fkV2Dhcp4RemoteLeaseLimit, fkV2Dhcp4RemoteLeaseCnt, fkV4Dhcp4RemoteControlLeaseLimit, fkV2Dhcp4RCircuitLeaseLimit, 
				fkV2Dhcp4RCircuitLeaseCnt, fkV2Dhcp4RCircuitControlLeaseLimit, fkV2Dhcp4RelayIfMaxHops, fkV2Dhcp4RelayIfControlMaxHops, fkV2Dhcp4ClientIfLeasetimeOption, 
				fkV2Dhcp4ClientIfControlLeasetimeOption, fkV2Dhcp4PENonPEControlPoolIndex, fkV2Dhcp4FilterAddressType, fkV2Dhcp4FilterAddressControlType, fkV2Ds4ArpInspectionTime, 
				fkV2Ds4ControlArpInspectionTime, fkV2Dhcp4RelayIntrIndex, fkV2Dhcp4RelayIntrRcvd, fkV2Dhcp4RelayIntrSent, fkV2Dhcp4RelayIntrRcvdErrors, 
				fkV2Dhcp4RelayIntrSentErrors, fkV2Dhcp4RelayIntrRcvdBootpRequest, fkV2Dhcp4RelayIntrRcvdBootpReply, fkV2Dhcp4RelayIntrSentBootpRequest, fkV2Dhcp4RelayIntrSentBootpReply, 
				fkV2Dhcp4RelayIntrRcvdDiscover, fkV2Dhcp4RelayIntrRcvdRequest, fkV2Dhcp4RelayIntrRcvdRelease, fkV2Dhcp4RelayIntrRcvdInform, fkV2Dhcp4RelayIntrRcvdDecline, 
				fkV2Dhcp4RelayIntrSentDiscover, fkV2Dhcp4RelayIntrSentRequest, fkV2Dhcp4RelayIntrSentRelease, fkV2Dhcp4RelayIntrSentInform, fkV2Dhcp4RelayIntrSentDecline, 
				fkV2Dhcp4RelayIntrRcvdOffer, fkV2Dhcp4RelayIntrRcvdAck, fkV2Dhcp4RelayIntrRcvdNack, fkV2Dhcp4RelayIntrSentOffer, fkV2Dhcp4RelayIntrSentAck, 
				fkV2Dhcp4RelayIntrSentNack, fkV2Dhcp4RelayIntrStatsControlRequest, fkV2Dhcp4RelayIntrStatsControlStatus, fkV2Dhcp4RelayIntrStatsControlTimer, fkV2Dhcp4RelayIntrStatsControITimeStamp, 
				fkV2Dhcp4RelayIntrStatsControIResult, fkV2Dhcp4RelayIntrStatsControIndex, fkV2Dhcp4Option82SystemRemoteOption, fkV2Dhcp4ControlOption82SystemRemoteOption, fkV2Dhcp4OptionFormatName, 
				fkV2Dhcp4OptionFormatControlRequest, fkV2Dhcp4OptionFormatControlStatus, fkV2Dhcp4OptionFormatControlTimer, fkV2Dhcp4OptionFormatControlTimeStamp, fkV2Dhcp4OptionFormatControlReqResult, 
				fkV2Dhcp4OptionFormatControlName, fkV2Dhcp4OptionFormatAttrID, fkV2Dhcp4OptionFormatAttrLength, fkV2Dhcp4OptionFormatAttrHiddenLength, fkV2Dhcp4OptionFormatAttrType, 
				fkV2Dhcp4OptionFormatAttrVarType, fkV2Dhcp4OptionFormatAttrVarValue, fkV2Dhcp4OptionFormatAttrControlRequest, fkV2Dhcp4OptionFormatAttrControlStatus, fkV2Dhcp4OptionFormatAttrControlTimer, 
				fkV2Dhcp4OptionFormatAttrControlTimeStamp, fkV2Dhcp4OptionFormatAttrControlReqResult, fkV2Dhcp4OptionFormatAttrControlName, fkV2Dhcp4OptionFormatAttrControlID, fkV2Dhcp4OptionFormatAttrControlLength, 
				fkV2Dhcp4OptionFormatAttrControlHiddenLength, fkV2Dhcp4OptionFormatAttrControlType, fkV2Dhcp4OptionFormatAttrControlVarType, fkV2Dhcp4OptionFormatAttrControlVarValue, fkV2Dhcp4Option82PortPolicy, 
				fkV2Dhcp4Option82PortPolicyDrop, fkV2Dhcp4Option82PortControlPolicy, fkV2Dhcp4Option82PortControlPolicyDrop, fkV2Dhcp4Option82SystemCircuitPortType, fkV2Dhcp4ControlOption82SystemCircuitPortType, 
				fkV2Ds4LimitRateDiscover, fkV2Ds4LimitRateRequest, fkV2Ds4ControlLimitRateDiscover, fkV2Ds4ControlLimitRateRequest, fkV2Ds4InformationOption, 
				fkV2Ds4ControlInformationOption, fkV2Ds4VlanInfoOptState, fkV2Dhcp4PEAddressControlPoolIndex, fkV2Dhcp4AuthArpReadyTime, fkV2Dhcp4AuthArpRemainTime, 
				fkV2Dhcp4ControlAuthArpReadyTime, fkV2Ds4VlanInfoOptControlRequest, fkV2Ds4VlanInfoOptControlStatus, fkV2Ds4VlanInfoOptControlTimer, fkV2Ds4VlanInfoOptControlTimeStamp, 
				fkV2Ds4VlanInfoOptControlReqResult, fkV2Ds4VlanInfoOptControlIndex, fkV2Ds4VlanInfoOptControlState, fkV2Ds4VlanInfoOptIndex }
			STATUS current
			DESCRIPTION 
				"Description."
			::= { fkV2Dhcp 4 }

		
		-- 1.3.6.1.4.1.10428 9 1.102.6.5
		fkV2DhcpNotificationGroup NOTIFICATION-GROUP
			NOTIFICATIONS { fkV2Dhcp4RelayHelperCreated, fkV2Dhcp4RelayHelperDestroyed, fkV2Dhcp4LeasedAddressCleared, fkV2Dhcp4LeasedNetworkCleared, fkV2Dhcp4LeasedPoolCleared, 
				fkV2Dhcp4LeasedAllCleared, fkV2Dhcp4ServiceActivityChanged, fkV2Dhcp4ClassUsageChanged, fkV2Dhcp4SmartRelayUsageChanged, fkV2Dhcp4Option82UsageChanged, 
				fkV2Dhcp4DefaultGatewayDestroyed, fkV2Dhcp4FilterPortStateChanged, fkV2Dhcp4DatabaseProfileChanged, fkV2Dhcp4Option82PolicyChanged, fkV2Dhcp4Option82SystemRemoteIdChanged, 
				fkV2Dhcp4PoolCreated, fkV2Dhcp4PoolDestroyed, fkV2Dhcp4PoolLeaseTimeProfileChanged, fkV2Dhcp4PoolDomainNameChanged, fkV2Dhcp4PoolOriginProfileChanged, 
				fkV2Dhcp4NetworkCreated, fkV2Dhcp4NetworkDestroyed, fkV2Dhcp4RangeCreated, fkV2Dhcp4RangeDestroyed, fkV2Dhcp4FixedCreated, 
				fkV2Dhcp4FixedDestroyed, fkV2Dhcp4DnsCreated, fkV2Dhcp4DnsDestroyed, fkV2Dhcp4DefaultGatewayCreated, fkV2Dhcp4OptionCreated, 
				fkV2Dhcp4OptionDestroyed, fkV2Dhcp4ClassCreated, fkV2Dhcp4ClassDestroyed, fkV2Dhcp4Option82TrustDefaultChanged, fkV2Dhcp4FilterAddressCreated, 
				fkV2Dhcp4FilterAddressDestroyed, fkV2Dhcp4PacketStatsCleared, fkV2Dhcp4DatabaseKeyChanged, fkV2Dhcp4DebugStatusChanged, fkV2Dhcp4IllegalCleared, 
				fkV2Dhcp4AuthoArpTimeChanged, fkV2Dhcp4ClientIfReleased, fkV2Dhcp4ClientIfRenewed, fkV2Dhcp4ClientIfProfileChanged, fkV2Ds4ActivityChanged, 
				fkV2Ds4VerifyMacStateChanged, fkV2Ds4DatabaseProfileChanged, fkV2Ds4VlanStateChanged, fkV2Ds4PortTrustStateChanged, fkV2Ds4PortLimitProfileChagned, 
				fkV2Ds4PortSrcGuardStateChanged, fkV2Dhcp4ClientIfActivityChanged, fkV2Ds4BindingsCreated, fkV2Ds4DatabaseRenewed, fkV2Ds4BindingsDestroyed, 
				fkV2Dhcp4Option82PortCircuitIdChanged, fkV2Dhcp4Option82PortTrustStateChanged, fkV2Dhcp4RelayIfSimpleOpt82AdminStateChanged, fkV2Dhcp4ClassRangeCreated, fkV2Ds4BindingsCleared, 
				fkV2Dhcp4RelayHelperCleared, fkV2Dhcp4CRCMapCircuitCleared, fkV2Dhcp4CRCMapRemoteCleared, fkV2Dhcp4ClassRangeDestroyed, fkV2Dhcp4RemoteCreated, 
				fkV2Dhcp4RemoteDestroyed, fkV2Dhcp4RemoteChanged, fkV2Dhcp4RemoteCleared, fkV2Dhcp4RCircuitCreated, fkV2Dhcp4RCircuitDestroyed, 
				fkV2Dhcp4ClientHardwareAddressChanged, fkV2Dhcp4PoolMeritDumpPathChanged, fkV2Dhcp4LogsCreated, fkV2Dhcp4LogsDestroyed, fkV2Dhcp4NtpCreated, 
				fkV2Dhcp4NtpDestroyed, fkV2Ds4PortTimeoutChanged, fkV2Ds4PortStatusChanged, fkV2Ds4PortFilterModeChanged, fkV2Ds4PortFilterDelayChanged, 
				fkV2Dhcp4PortLeaseLimitChanged, fkV2Dhcp4PEStatusChanged, fkV2Dhcp4PEVendorCreated, fkV2Dhcp4PEVendorDestroyed, fkV2Dhcp4PEVendorAllDestroyed, 
				fkV2Dhcp4PEAddressCreated, fkV2Dhcp4PEAddressDestroyed, fkV2Dhcp4PEAddressAllDestroyed, fkV2Dhcp4PENonPECreated, fkV2Dhcp4PENonPEDestroyed, 
				fkV2Dhcp4RCircuitChanged, fkV2Dhcp4RelayIfMaxHopsChanged, fkV2Dhcp4ClientIfLeasetimeOptionChanged, fkV2Ds4ArpInspectionTimeChanged, fkV2Dhcp4RelayintrStatsCleared, 
				fkV2Dhcp4Option82SystemRemoteOptionChanged, fkV2Dhcp4Option82PortCircuitIdCleared, fkV2Dhcp4OptionFormatCreated, fkV2Dhcp4OptionFormatDestroyed, fkV2Dhcp4OptionFormatAttrAdded, 
				fkV2Dhcp4OptionFormatAttrDeleted, fkV2Dhcp4OptionFormatAttrModified, fkV2Dhcp4Option82PortPolicyChanged, fkV2DhcpOption82SystemCirucitIdPortTypeChanged, fkV2Ds4LimitRateDiscoverChanged, 
				fkV2Ds4LimitRateRequestChanged, fkV2Ds4InformationOptionChanged, fkV2Ds4VlanInfoOptStateChanged, fkV2Dhcp4RCircuitCleared, fkV2Dhcp4ArpPingProfileChanged, 
				fkV2Dhcp4PoolRootPathChanged }
			STATUS current
			DESCRIPTION 
				"Description."
			::= { fkV2Dhcp 5 }

		
	
	END

--
-- fkv2-dhcp-mib.mib
--
