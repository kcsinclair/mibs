--
-- FK-DEVICE-MIB.my
-- MIB generated by MG-SOFT Visual MIB Builder Version 6.0  Build 88
-- Tuesday, April 09, 2013 at 11:44:28
--

--  fk-device-mib.mib
-- MIB generated by MG-SOFT Visual MIB Builder Version 6.0  Build 88
-- Monday, August 27, 2012 at 13:36:26
-- 
--  fk-device-mib.mib
-- MIB generated by MG-SOFT Visual MIB Builder Version 6.0  Build 88
-- Tuesday, January 17, 2012 at 11:51:02
-- 
--  fk-device-mib.mib
-- MIB generated by MG-SOFT Visual MIB Builder Version 6.0  Build 88
-- Wednesday, January 04, 2012 at 10:43:50
-- 
--  fk-device-mib.mib
-- MIB generated by MG-SOFT Visual MIB Builder Version 6.0  Build 88
-- Wednesday, October 26, 2011 at 11:56:00
-- 

	FK-DEVICE-MIB DEFINITIONS ::= BEGIN
 
		IMPORTS
			fkMgmt			
				FROM FKOLTG1040-SMI			
			FkControlStatusType, FkControlRequestResultType			
				FROM FK-TC-MIB			
			OBJECT-GROUP, NOTIFICATION-GROUP			
				FROM SNMPv2-CONF			
			TimeTicks, IpAddress, Integer32, Unsigned32, Gauge32, OBJECT-TYPE, MODULE-IDENTITY, NOTIFICATION-TYPE			
				FROM SNMPv2-SMI;
	
	
--     1.3.6.1.4.1.10428 9 1.101.2
-- December 10, 2004 at 08:52 GMT
-- 1.3.6.1.4.1.10428 9 1.101.2
-- December 10, 2004 at 08:52 GMT
-- 1.3.6.1.4.1.10428 9 1.101.2
-- December 10, 2004 at 08:52 GMT
-- 1.3.6.1.4.1.10428 9 1.101.2
-- December 10, 2004 at 08:52 GMT
		-- 1.3.6.1.4.1.10428 9 1.101.2
		fkDevice MODULE-IDENTITY 
			LAST-UPDATED "200412100852Z"		-- December 10, 2004 at 08:52 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 2 }

		
	
	
--
-- Node definitions
--
	
--  Node definitions
-- 
-- Node definitions
-- 
-- Node definitions
-- 
-- Node definitions
-- 
-- 1.3.6.1.4.1.10428 9 1.101.2.1
-- 1.3.6.1.4.1.10428 9 1.101.2.1
-- 1.3.6.1.4.1.10428 9 1.101.2.1
-- 1.3.6.1.4.1.10428 9 1.101.2.1
		-- 1.3.6.1.4.1.10428 9 1.101.2.1
		fkDeviceBase OBJECT IDENTIFIER ::= { fkDevice 1 }

		
--     1.3.6.1.4.1.10428 9 1.101.2.1.1
-- 1.3.6.1.4.1.10428 9 1.101.2.1.1
-- 1.3.6.1.4.1.10428 9 1.101.2.1.1
-- 1.3.6.1.4.1.10428 9 1.101.2.1.1
		-- 1.3.6.1.4.1.10428 9 1.101.2.1.1
		fkDeviceBaseInfo OBJECT IDENTIFIER ::= { fkDeviceBase 1 }

		
--     1.3.6.1.4.1.10428 9 1.101.2.1.1.1
-- 1.3.6.1.4.1.10428 9 1.101.2.1.1.1
-- 1.3.6.1.4.1.10428 9 1.101.2.1.1.1
-- 1.3.6.1.4.1.10428 9 1.101.2.1.1.1
		-- 1.3.6.1.4.1.10428 9 1.101.2.1.1.1
		fkDeviceEthernetPortNum OBJECT-TYPE
			SYNTAX Integer32
			MAX-ACCESS read-only
			STATUS current
			DESCRIPTION
				"The number of ethernet port."
			::= { fkDeviceBaseInfo 1 }

		
--     1.3.6.1.4.1.10428 9 1.101.2.1.1.2
-- 1.3.6.1.4.1.10428 9 1.101.2.1.1.2
-- 1.3.6.1.4.1.10428 9 1.101.2.1.1.2
-- 1.3.6.1.4.1.10428 9 1.101.2.1.1.2
		-- 1.3.6.1.4.1.10428 9 1.101.2.1.1.2
		fkDevicePowerNum OBJECT-TYPE
			SYNTAX Integer32
			MAX-ACCESS read-only
			STATUS current
			DESCRIPTION
				"The number of power module"
			::= { fkDeviceBaseInfo 2 }

		
--     1.3.6.1.4.1.10428 9 1.101.2.1.1.3
-- 1.3.6.1.4.1.10428 9 1.101.2.1.1.3
-- 1.3.6.1.4.1.10428 9 1.101.2.1.1.3
-- 1.3.6.1.4.1.10428 9 1.101.2.1.1.3
		-- 1.3.6.1.4.1.10428 9 1.101.2.1.1.3
		fkDeviceFanModuleNum OBJECT-TYPE
			SYNTAX Integer32
			MAX-ACCESS read-only
			STATUS current
			DESCRIPTION
				"The number of FAN module"
			::= { fkDeviceBaseInfo 3 }

		
--     1.3.6.1.4.1.10428 9 1.101.2.1.1.4
-- 1.3.6.1.4.1.10428 9 1.101.2.1.1.4
-- 1.3.6.1.4.1.10428 9 1.101.2.1.1.4
-- 1.3.6.1.4.1.10428 9 1.101.2.1.1.4
		-- 1.3.6.1.4.1.10428 9 1.101.2.1.1.4
		fkDeviceTemperatureNum OBJECT-TYPE
			SYNTAX Integer32
			MAX-ACCESS read-only
			STATUS current
			DESCRIPTION
				"The number of temperature sensor"
			::= { fkDeviceBaseInfo 4 }

		
--     1.3.6.1.4.1.10428 9 1.101.2.1.1.5
-- 1.3.6.1.4.1.10428 9 1.101.2.1.1.5
-- 1.3.6.1.4.1.10428 9 1.101.2.1.1.5
-- 1.3.6.1.4.1.10428 9 1.101.2.1.1.5
		-- 1.3.6.1.4.1.10428 9 1.101.2.1.1.5
		fkDeviceFanStartTemperature OBJECT-TYPE
			SYNTAX Integer32
			MAX-ACCESS read-only
			STATUS current
			DESCRIPTION
				"The temperature value which begins to turn fan."
			::= { fkDeviceBaseInfo 5 }

		
--     1.3.6.1.4.1.10428 9 1.101.2.1.1.6
-- 1.3.6.1.4.1.10428 9 1.101.2.1.1.6
-- 1.3.6.1.4.1.10428 9 1.101.2.1.1.6
-- 1.3.6.1.4.1.10428 9 1.101.2.1.1.6
		-- 1.3.6.1.4.1.10428 9 1.101.2.1.1.6
		fkDeviceFanStopTemperature OBJECT-TYPE
			SYNTAX Integer32
			MAX-ACCESS read-only
			STATUS current
			DESCRIPTION
				"The temperature value which stops fan."
			::= { fkDeviceBaseInfo 6 }

		
--     1.3.6.1.4.1.10428 9 1.101.2.1.1.7
-- 1.3.6.1.4.1.10428 9 1.101.2.1.1.7
-- 1.3.6.1.4.1.10428 9 1.101.2.1.1.7
-- 1.3.6.1.4.1.10428 9 1.101.2.1.1.7
		-- 1.3.6.1.4.1.10428 9 1.101.2.1.1.7
		fkDeviceJumboFrameStatus OBJECT-TYPE
			SYNTAX INTEGER
				{
				enable(1),
				disable(2)
				}
			MAX-ACCESS read-only
			STATUS current
			DESCRIPTION
				"The global jumbo-frame status.
				2011/01/20 V5924CR only support this."
			::= { fkDeviceBaseInfo 7 }

		
--  1.3.6.1.4.1.10428 9 1.101.2.1.1.8
		-- 1.3.6.1.4.1.10428 9 1.101.2.1.1.8
		fkDeviceEnvironmentMonitoringStatus OBJECT-TYPE
			SYNTAX INTEGER
				{
				notInstallAIU(0),
				normalOpen(1),
				normalClose(2)
				}
			MAX-ACCESS read-only
			STATUS current
			DESCRIPTION
				"The alarm input mode of environment monitoring for AIU"
			::= { fkDeviceBaseInfo 8 }

		
--     1.3.6.1.4.1.10428 9 1.101.2.1.2
-- 1.3.6.1.4.1.10428 9 1.101.2.1.2
-- 1.3.6.1.4.1.10428 9 1.101.2.1.2
-- 1.3.6.1.4.1.10428 9 1.101.2.1.2
		-- 1.3.6.1.4.1.10428 9 1.101.2.1.2
		fkDeviceBaseControl OBJECT IDENTIFIER ::= { fkDeviceBase 2 }

		
--     1.3.6.1.4.1.10428 9 1.101.2.1.2.1
-- 1.3.6.1.4.1.10428 9 1.101.2.1.2.1
-- 1.3.6.1.4.1.10428 9 1.101.2.1.2.1
-- 1.3.6.1.4.1.10428 9 1.101.2.1.2.1
		-- 1.3.6.1.4.1.10428 9 1.101.2.1.2.1
		fkDeviceControlRequest OBJECT-TYPE
			SYNTAX INTEGER
				{
				setDeviceTemperatureThreshold(1),
				setDeviceJumboFrameStatus(2),
				setDeviceLEDTest(3),
				setEnvironmentMonitoringStatus(4)
				}
			MAX-ACCESS read-write
			STATUS current
			DESCRIPTION
				"set an administrative state of FAN module"
			::= { fkDeviceBaseControl 1 }

		
--     1.3.6.1.4.1.10428 9 1.101.2.1.2.2
-- 1.3.6.1.4.1.10428 9 1.101.2.1.2.2
-- 1.3.6.1.4.1.10428 9 1.101.2.1.2.2
-- 1.3.6.1.4.1.10428 9 1.101.2.1.2.2
		-- 1.3.6.1.4.1.10428 9 1.101.2.1.2.2
		fkDeviceControlStatus OBJECT-TYPE
			SYNTAX FkControlStatusType
			MAX-ACCESS read-only
			STATUS current
			DESCRIPTION
				"Description."
			::= { fkDeviceBaseControl 2 }

		
--     1.3.6.1.4.1.10428 9 1.101.2.1.2.3
-- 1.3.6.1.4.1.10428 9 1.101.2.1.2.3
-- 1.3.6.1.4.1.10428 9 1.101.2.1.2.3
-- 1.3.6.1.4.1.10428 9 1.101.2.1.2.3
		-- 1.3.6.1.4.1.10428 9 1.101.2.1.2.3
		fkDeviceControlTimer OBJECT-TYPE
			SYNTAX Gauge32
			MAX-ACCESS read-write
			STATUS current
			DESCRIPTION
				"Description."
			::= { fkDeviceBaseControl 3 }

		
--     1.3.6.1.4.1.10428 9 1.101.2.1.2.4
-- 1.3.6.1.4.1.10428 9 1.101.2.1.2.4
-- 1.3.6.1.4.1.10428 9 1.101.2.1.2.4
-- 1.3.6.1.4.1.10428 9 1.101.2.1.2.4
		-- 1.3.6.1.4.1.10428 9 1.101.2.1.2.4
		fkDeviceControlTimeStamp OBJECT-TYPE
			SYNTAX TimeTicks
			MAX-ACCESS read-only
			STATUS current
			DESCRIPTION
				"Description."
			::= { fkDeviceBaseControl 4 }

		
--     1.3.6.1.4.1.10428 9 1.101.2.1.2.5
-- 1.3.6.1.4.1.10428 9 1.101.2.1.2.5
-- 1.3.6.1.4.1.10428 9 1.101.2.1.2.5
-- 1.3.6.1.4.1.10428 9 1.101.2.1.2.5
		-- 1.3.6.1.4.1.10428 9 1.101.2.1.2.5
		fkDeviceControlReqResult OBJECT-TYPE
			SYNTAX FkControlRequestResultType
			MAX-ACCESS read-only
			STATUS current
			DESCRIPTION
				"Description."
			::= { fkDeviceBaseControl 5 }

		
--     1.3.6.1.4.1.10428 9 1.101.2.1.2.6
-- 1.3.6.1.4.1.10428 9 1.101.2.1.2.6
-- 1.3.6.1.4.1.10428 9 1.101.2.1.2.6
-- 1.3.6.1.4.1.10428 9 1.101.2.1.2.6
		-- 1.3.6.1.4.1.10428 9 1.101.2.1.2.6
		fkDeviceControlFanStartTemperature OBJECT-TYPE
			SYNTAX Integer32
			MAX-ACCESS read-write
			STATUS current
			DESCRIPTION
				"Description."
			::= { fkDeviceBaseControl 6 }

		
--     1.3.6.1.4.1.10428 9 1.101.2.1.2.7
-- 1.3.6.1.4.1.10428 9 1.101.2.1.2.7
-- 1.3.6.1.4.1.10428 9 1.101.2.1.2.7
-- 1.3.6.1.4.1.10428 9 1.101.2.1.2.7
		-- 1.3.6.1.4.1.10428 9 1.101.2.1.2.7
		fkDeviceControlFanStopTemperature OBJECT-TYPE
			SYNTAX Integer32
			MAX-ACCESS read-write
			STATUS current
			DESCRIPTION
				"Description."
			::= { fkDeviceBaseControl 7 }

		
--     1.3.6.1.4.1.10428 9 1.101.2.1.2.8
-- 1.3.6.1.4.1.10428 9 1.101.2.1.2.8
-- 1.3.6.1.4.1.10428 9 1.101.2.1.2.8
-- 1.3.6.1.4.1.10428 9 1.101.2.1.2.8
		-- 1.3.6.1.4.1.10428 9 1.101.2.1.2.8
		fkDeviceControlJumboFrameStatus OBJECT-TYPE
			SYNTAX INTEGER
				{
				enable(1),
				disable(2)
				}
			MAX-ACCESS read-write
			STATUS current
			DESCRIPTION
				"The global jumbo-frame status.
				2011/01/20 V5924CR only support this."
			::= { fkDeviceBaseControl 8 }

		
--  1.3.6.1.4.1.10428 9 1.101.2.1.2.9
		-- 1.3.6.1.4.1.10428 9 1.101.2.1.2.9
		fkDeviceControlEnvironmentMonitoringStatus OBJECT-TYPE
			SYNTAX INTEGER
				{
				normalOpen(1),
				normalClose(2)
				}
			MAX-ACCESS read-only
			STATUS current
			DESCRIPTION
				"The alarm input mode of environment monitoring for AIU"
			::= { fkDeviceBaseControl 9 }

		
--     1.3.6.1.4.1.10428 9 1.101.2.1.3
-- 1.3.6.1.4.1.10428 9 1.101.2.1.3
-- 1.3.6.1.4.1.10428 9 1.101.2.1.3
-- 1.3.6.1.4.1.10428 9 1.101.2.1.3
		-- 1.3.6.1.4.1.10428 9 1.101.2.1.3
		fkDeviceBaseNotification OBJECT IDENTIFIER ::= { fkDeviceBase 3 }

		
--     1.3.6.1.4.1.10428 9 1.101.2.1.3.1
-- 1.3.6.1.4.1.10428 9 1.101.2.1.3.1
-- 1.3.6.1.4.1.10428 9 1.101.2.1.3.1
-- 1.3.6.1.4.1.10428 9 1.101.2.1.3.1
		-- 1.3.6.1.4.1.10428 9 1.101.2.1.3.1
		fkDeviceTemperatureThresholdChanged NOTIFICATION-TYPE
			OBJECTS { fkDeviceFanStartTemperature, fkDeviceFanStopTemperature, fkDeviceControlRequest, fkDeviceControlTimeStamp, fkDeviceControlReqResult
				 }
			STATUS current
			DESCRIPTION 
				"Description."
			::= { fkDeviceBaseNotification 1 }

		
--     1.3.6.1.4.1.10428 9 1.101.2.1.3.2
-- 1.3.6.1.4.1.10428 9 1.101.2.1.3.2
-- 1.3.6.1.4.1.10428 9 1.101.2.1.3.2
-- 1.3.6.1.4.1.10428 9 1.101.2.1.3.2
		-- 1.3.6.1.4.1.10428 9 1.101.2.1.3.2
		fkDeviceJumboFrameChanged NOTIFICATION-TYPE
			OBJECTS { fkDeviceControlRequest, fkDeviceControlTimeStamp, fkDeviceControlReqResult, fkDeviceControlJumboFrameStatus }
			STATUS current
			DESCRIPTION 
				"Description."
			::= { fkDeviceBaseNotification 2 }

		
--     1.3.6.1.4.1.10428 9 1.101.2.1.3.3
-- 1.3.6.1.4.1.10428 9 1.101.2.1.3.3
-- 1.3.6.1.4.1.10428 9 1.101.2.1.3.3
-- 1.3.6.1.4.1.10428 9 1.101.2.1.3.3
		-- 1.3.6.1.4.1.10428 9 1.101.2.1.3.3
		fkDeviceLEDTestChanged NOTIFICATION-TYPE
			OBJECTS { fkDeviceControlRequest, fkDeviceControlTimeStamp, fkDeviceControlReqResult }
			STATUS current
			DESCRIPTION 
				"Description."
			::= { fkDeviceBaseNotification 3 }

		
--  1.3.6.1.4.1.10428 9 1.101.2.1.3.4
		-- 1.3.6.1.4.1.10428 9 1.101.2.1.3.4
		fkDeviceEnvironmentMonitoringStatusChanged NOTIFICATION-TYPE
			OBJECTS { fkDeviceControlRequest, fkDeviceControlTimeStamp, fkDeviceControlReqResult, fkDeviceEnvironmentMonitoringStatus }
			STATUS current
			DESCRIPTION 
				"setEnvironmentMonitoringStatus "
			::= { fkDeviceBaseNotification 4 }

		
--     1.3.6.1.4.1.10428 9 1.101.2.2
-- 1.3.6.1.4.1.10428 9 1.101.2.2
-- 1.3.6.1.4.1.10428 9 1.101.2.2
-- 1.3.6.1.4.1.10428 9 1.101.2.2
		-- 1.3.6.1.4.1.10428 9 1.101.2.2
		fkEthernetPort OBJECT IDENTIFIER ::= { fkDevice 2 }

		
--     1.3.6.1.4.1.10428 9 1.101.2.2.1
-- 1.3.6.1.4.1.10428 9 1.101.2.2.1
-- 1.3.6.1.4.1.10428 9 1.101.2.2.1
-- 1.3.6.1.4.1.10428 9 1.101.2.2.1
		-- 1.3.6.1.4.1.10428 9 1.101.2.2.1
		fkEthernetPortTable OBJECT-TYPE
			SYNTAX SEQUENCE OF FkEthernetPortEntry
			MAX-ACCESS not-accessible
			STATUS current
			DESCRIPTION
				"Description."
			::= { fkEthernetPort 1 }

		
--     1.3.6.1.4.1.10428 9 1.101.2.2.1.1
-- 1.3.6.1.4.1.10428 9 1.101.2.2.1.1
-- 1.3.6.1.4.1.10428 9 1.101.2.2.1.1
-- 1.3.6.1.4.1.10428 9 1.101.2.2.1.1
		-- 1.3.6.1.4.1.10428 9 1.101.2.2.1.1
		fkEthernetPortEntry OBJECT-TYPE
			SYNTAX FkEthernetPortEntry
			MAX-ACCESS not-accessible
			STATUS current
			DESCRIPTION
				"Description."
			INDEX { fkEthernetPortIndex }
			::= { fkEthernetPortTable 1 }

		
		FkEthernetPortEntry ::=
			SEQUENCE { 
				fkEthernetPortIndex
					INTEGER,
				fkEthernetPortPhyIndex
					Integer32,
				fkEthernetPortType
					INTEGER,
				fkEthernetPortAdminStatus
					INTEGER,
				fkEthernetPortOperStatus
					INTEGER,
				fkEthernetPortTransmissionRate
					Integer32,
				fkEthernetPortDuplexMode
					INTEGER,
				fkEthernetPortFlowControl
					INTEGER,
				fkEthernetPortNegotiationMode
					INTEGER,
				fkEthernetPortJumboFrameSize
					Integer32,
				fkEthernetPortSfpTransceiver
					INTEGER,
				fkEthernetPortSfpVendorName
					OCTET STRING,
				fkEthernetPortSfpVendorPartNumber
					OCTET STRING,
				fkEthernetPortSfpVendorRevision
					OCTET STRING,
				fkEthernetPortSfpVendorSerialNumber
					OCTET STRING,
				fkEthernetPortSfpDateCode
					OCTET STRING,
				fkEthernetPortPhysicalRemoteChassis
					OCTET STRING,
				fkEthernetPortPhysicalRemoteSlot
					Integer32,
				fkEthernetPortPhysicalRemotePort
					Integer32,
				fkEthernetPortPhysicalLinkDiscoveryMode
					INTEGER,
				fkEthernetPortSfpTransceiverType
					INTEGER,
				fkEthernetPortSfpTransceiverDetailType
					INTEGER,
				fkEthernetPortSlotIndex
					Integer32,
				fkEthernetPortSlotPortIndex
					Integer32,
				fkEthernetPortAdminTransmissionRate
					Integer32,
				fkEthernetPortAdminDuplexMode
					INTEGER,
				fkEthernetPortAdminFlowControl
					INTEGER,
				fkEthernetPortAdminNegotiationMode
					INTEGER,
				fkEthernetPortAdminReason
					INTEGER
			 }

--     1.3.6.1.4.1.10428 9 1.101.2.2.1.1.1
-- 1.3.6.1.4.1.10428 9 1.101.2.2.1.1.1
-- 1.3.6.1.4.1.10428 9 1.101.2.2.1.1.1
-- 1.3.6.1.4.1.10428 9 1.101.2.2.1.1.1
		-- 1.3.6.1.4.1.10428 9 1.101.2.2.1.1.1
		fkEthernetPortIndex OBJECT-TYPE
			SYNTAX INTEGER (1..255)
			MAX-ACCESS read-only
			STATUS current
			DESCRIPTION
				"The port index."
			::= { fkEthernetPortEntry 1 }

		
--     1.3.6.1.4.1.10428 9 1.101.2.2.1.1.2
-- 1.3.6.1.4.1.10428 9 1.101.2.2.1.1.2
-- 1.3.6.1.4.1.10428 9 1.101.2.2.1.1.2
-- 1.3.6.1.4.1.10428 9 1.101.2.2.1.1.2
		-- 1.3.6.1.4.1.10428 9 1.101.2.2.1.1.2
		fkEthernetPortPhyIndex OBJECT-TYPE
			SYNTAX Integer32
			MAX-ACCESS read-only
			STATUS current
			DESCRIPTION
				"The physical index of entity mib."
			::= { fkEthernetPortEntry 2 }

		
--     1.3.6.1.4.1.10428 9 1.101.2.2.1.1.3
-- 1.3.6.1.4.1.10428 9 1.101.2.2.1.1.3
-- 1.3.6.1.4.1.10428 9 1.101.2.2.1.1.3
-- 1.3.6.1.4.1.10428 9 1.101.2.2.1.1.3
		-- 1.3.6.1.4.1.10428 9 1.101.2.2.1.1.3
		fkEthernetPortType OBJECT-TYPE
			SYNTAX INTEGER
				{
				unknown(0),
				electrical(1),
				optical(2)
				}
			MAX-ACCESS read-only
			STATUS current
			DESCRIPTION
				"The type of port.
				It is not planed to made a automatic switchover between optical and electrical interfaces."
			::= { fkEthernetPortEntry 3 }

		
--     1.3.6.1.4.1.10428 9 1.101.2.2.1.1.4
-- 1.3.6.1.4.1.10428 9 1.101.2.2.1.1.4
-- 1.3.6.1.4.1.10428 9 1.101.2.2.1.1.4
-- 1.3.6.1.4.1.10428 9 1.101.2.2.1.1.4
		-- 1.3.6.1.4.1.10428 9 1.101.2.2.1.1.4
		fkEthernetPortAdminStatus OBJECT-TYPE
			SYNTAX INTEGER
				{
				up(1),
				down(2),
				notAvailable(3)
				}
			MAX-ACCESS read-only
			STATUS current
			DESCRIPTION
				"The admin status of port."
			::= { fkEthernetPortEntry 4 }

		
--     1.3.6.1.4.1.10428 9 1.101.2.2.1.1.5
-- 1.3.6.1.4.1.10428 9 1.101.2.2.1.1.5
-- 1.3.6.1.4.1.10428 9 1.101.2.2.1.1.5
-- 1.3.6.1.4.1.10428 9 1.101.2.2.1.1.5
		-- 1.3.6.1.4.1.10428 9 1.101.2.2.1.1.5
		fkEthernetPortOperStatus OBJECT-TYPE
			SYNTAX INTEGER
				{
				up(1),
				down(2),
				notAvailable(3)
				}
			MAX-ACCESS read-only
			STATUS current
			DESCRIPTION
				"The oper status of port"
			::= { fkEthernetPortEntry 5 }

		
--     1.3.6.1.4.1.10428 9 1.101.2.2.1.1.6
-- 1.3.6.1.4.1.10428 9 1.101.2.2.1.1.6
-- 1.3.6.1.4.1.10428 9 1.101.2.2.1.1.6
-- 1.3.6.1.4.1.10428 9 1.101.2.2.1.1.6
		-- 1.3.6.1.4.1.10428 9 1.101.2.2.1.1.6
		fkEthernetPortTransmissionRate OBJECT-TYPE
			SYNTAX Integer32 (10 | 100 | 1000 | 10000)
			MAX-ACCESS read-only
			STATUS current
			DESCRIPTION
				"The speed of port. Unit is Mbit/s.
				This configurations are only useful for electrical interfaces.
				Optical - interfaces will always support 1000 MBIT/s"
			::= { fkEthernetPortEntry 6 }

		
--     1.3.6.1.4.1.10428 9 1.101.2.2.1.1.7
-- 1.3.6.1.4.1.10428 9 1.101.2.2.1.1.7
-- 1.3.6.1.4.1.10428 9 1.101.2.2.1.1.7
-- 1.3.6.1.4.1.10428 9 1.101.2.2.1.1.7
		-- 1.3.6.1.4.1.10428 9 1.101.2.2.1.1.7
		fkEthernetPortDuplexMode OBJECT-TYPE
			SYNTAX INTEGER
				{
				full(1),
				half(2),
				notAvailable(3)
				}
			MAX-ACCESS read-only
			STATUS current
			DESCRIPTION
				"The duplex status of port."
			::= { fkEthernetPortEntry 7 }

		
--     1.3.6.1.4.1.10428 9 1.101.2.2.1.1.8
-- 1.3.6.1.4.1.10428 9 1.101.2.2.1.1.8
-- 1.3.6.1.4.1.10428 9 1.101.2.2.1.1.8
-- 1.3.6.1.4.1.10428 9 1.101.2.2.1.1.8
		-- 1.3.6.1.4.1.10428 9 1.101.2.2.1.1.8
		fkEthernetPortFlowControl OBJECT-TYPE
			SYNTAX INTEGER
				{
				disabled(1),
				enabledSymetrical(2),
				enabledAsymetrical(3),
				enabledBoth(4),
				notAvailable(5)
				}
			MAX-ACCESS read-only
			STATUS current
			DESCRIPTION
				"The flow-control mode of port."
			::= { fkEthernetPortEntry 8 }

		
--     1.3.6.1.4.1.10428 9 1.101.2.2.1.1.9
-- 1.3.6.1.4.1.10428 9 1.101.2.2.1.1.9
-- 1.3.6.1.4.1.10428 9 1.101.2.2.1.1.9
-- 1.3.6.1.4.1.10428 9 1.101.2.2.1.1.9
		-- 1.3.6.1.4.1.10428 9 1.101.2.2.1.1.9
		fkEthernetPortNegotiationMode OBJECT-TYPE
			SYNTAX INTEGER
				{
				auto(1),
				force(2),
				notAvailable(3)
				}
			MAX-ACCESS read-only
			STATUS current
			DESCRIPTION
				"The Auto Negotiation mode of port. "
			::= { fkEthernetPortEntry 9 }

		
--     1.3.6.1.4.1.10428 9 1.101.2.2.1.1.10
-- 1.3.6.1.4.1.10428 9 1.101.2.2.1.1.10
-- 1.3.6.1.4.1.10428 9 1.101.2.2.1.1.10
-- 1.3.6.1.4.1.10428 9 1.101.2.2.1.1.10
		-- 1.3.6.1.4.1.10428 9 1.101.2.2.1.1.10
		fkEthernetPortJumboFrameSize OBJECT-TYPE
			SYNTAX Integer32 (0 | 1518..9216)
			MAX-ACCESS read-only
			STATUS current
			DESCRIPTION
				"The jumbo frame's size of port.
				If the value is zero, it means that it is not set up."
			::= { fkEthernetPortEntry 10 }

		
--     1.3.6.1.4.1.10428 9 1.101.2.2.1.1.11
-- 1.3.6.1.4.1.10428 9 1.101.2.2.1.1.11
-- 1.3.6.1.4.1.10428 9 1.101.2.2.1.1.11
-- 1.3.6.1.4.1.10428 9 1.101.2.2.1.1.11
		-- 1.3.6.1.4.1.10428 9 1.101.2.2.1.1.11
		fkEthernetPortSfpTransceiver OBJECT-TYPE
			SYNTAX INTEGER
				{
				unknown(0),
				electrical(1),
				electricalCoaxial(2),
				opticalLongHaul(3),
				opticalShortHaul(4),
				optical10G(5),
				opticalGpon(6)
				}
			MAX-ACCESS read-only
			STATUS current
			DESCRIPTION
				"Description."
			::= { fkEthernetPortEntry 11 }

		
--     1.3.6.1.4.1.10428 9 1.101.2.2.1.1.12
-- 1.3.6.1.4.1.10428 9 1.101.2.2.1.1.12
-- 1.3.6.1.4.1.10428 9 1.101.2.2.1.1.12
-- 1.3.6.1.4.1.10428 9 1.101.2.2.1.1.12
		-- 1.3.6.1.4.1.10428 9 1.101.2.2.1.1.12
		fkEthernetPortSfpVendorName OBJECT-TYPE
			SYNTAX OCTET STRING
			MAX-ACCESS read-only
			STATUS current
			DESCRIPTION
				"Description."
			::= { fkEthernetPortEntry 12 }

		
--     1.3.6.1.4.1.10428 9 1.101.2.2.1.1.13
-- 1.3.6.1.4.1.10428 9 1.101.2.2.1.1.13
-- 1.3.6.1.4.1.10428 9 1.101.2.2.1.1.13
-- 1.3.6.1.4.1.10428 9 1.101.2.2.1.1.13
		-- 1.3.6.1.4.1.10428 9 1.101.2.2.1.1.13
		fkEthernetPortSfpVendorPartNumber OBJECT-TYPE
			SYNTAX OCTET STRING
			MAX-ACCESS read-only
			STATUS current
			DESCRIPTION
				"Description."
			::= { fkEthernetPortEntry 13 }

		
--     1.3.6.1.4.1.10428 9 1.101.2.2.1.1.14
-- 1.3.6.1.4.1.10428 9 1.101.2.2.1.1.14
-- 1.3.6.1.4.1.10428 9 1.101.2.2.1.1.14
-- 1.3.6.1.4.1.10428 9 1.101.2.2.1.1.14
		-- 1.3.6.1.4.1.10428 9 1.101.2.2.1.1.14
		fkEthernetPortSfpVendorRevision OBJECT-TYPE
			SYNTAX OCTET STRING
			MAX-ACCESS read-only
			STATUS current
			DESCRIPTION
				"Description."
			::= { fkEthernetPortEntry 14 }

		
--     1.3.6.1.4.1.10428 9 1.101.2.2.1.1.15
-- 1.3.6.1.4.1.10428 9 1.101.2.2.1.1.15
-- 1.3.6.1.4.1.10428 9 1.101.2.2.1.1.15
-- 1.3.6.1.4.1.10428 9 1.101.2.2.1.1.15
		-- 1.3.6.1.4.1.10428 9 1.101.2.2.1.1.15
		fkEthernetPortSfpVendorSerialNumber OBJECT-TYPE
			SYNTAX OCTET STRING
			MAX-ACCESS read-only
			STATUS current
			DESCRIPTION
				"Description."
			::= { fkEthernetPortEntry 15 }

		
--     1.3.6.1.4.1.10428 9 1.101.2.2.1.1.16
-- 1.3.6.1.4.1.10428 9 1.101.2.2.1.1.16
-- 1.3.6.1.4.1.10428 9 1.101.2.2.1.1.16
-- 1.3.6.1.4.1.10428 9 1.101.2.2.1.1.16
		-- 1.3.6.1.4.1.10428 9 1.101.2.2.1.1.16
		fkEthernetPortSfpDateCode OBJECT-TYPE
			SYNTAX OCTET STRING
			MAX-ACCESS read-only
			STATUS current
			DESCRIPTION
				"Description."
			::= { fkEthernetPortEntry 16 }

		
--     1.3.6.1.4.1.10428 9 1.101.2.2.1.1.17
-- 1.3.6.1.4.1.10428 9 1.101.2.2.1.1.17
-- 1.3.6.1.4.1.10428 9 1.101.2.2.1.1.17
-- 1.3.6.1.4.1.10428 9 1.101.2.2.1.1.17
		-- 1.3.6.1.4.1.10428 9 1.101.2.2.1.1.17
		fkEthernetPortPhysicalRemoteChassis OBJECT-TYPE
			SYNTAX OCTET STRING
			MAX-ACCESS read-only
			STATUS current
			DESCRIPTION
				"Description."
			::= { fkEthernetPortEntry 17 }

		
--     1.3.6.1.4.1.10428 9 1.101.2.2.1.1.18
-- 1.3.6.1.4.1.10428 9 1.101.2.2.1.1.18
-- 1.3.6.1.4.1.10428 9 1.101.2.2.1.1.18
-- 1.3.6.1.4.1.10428 9 1.101.2.2.1.1.18
		-- 1.3.6.1.4.1.10428 9 1.101.2.2.1.1.18
		fkEthernetPortPhysicalRemoteSlot OBJECT-TYPE
			SYNTAX Integer32
			MAX-ACCESS read-only
			STATUS current
			DESCRIPTION
				"Description."
			::= { fkEthernetPortEntry 18 }

		
--     1.3.6.1.4.1.10428 9 1.101.2.2.1.1.19
-- 1.3.6.1.4.1.10428 9 1.101.2.2.1.1.19
-- 1.3.6.1.4.1.10428 9 1.101.2.2.1.1.19
-- 1.3.6.1.4.1.10428 9 1.101.2.2.1.1.19
		-- 1.3.6.1.4.1.10428 9 1.101.2.2.1.1.19
		fkEthernetPortPhysicalRemotePort OBJECT-TYPE
			SYNTAX Integer32
			MAX-ACCESS read-only
			STATUS current
			DESCRIPTION
				"Description."
			::= { fkEthernetPortEntry 19 }

		
--     1.3.6.1.4.1.10428 9 1.101.2.2.1.1.20
-- 1.3.6.1.4.1.10428 9 1.101.2.2.1.1.20
-- 1.3.6.1.4.1.10428 9 1.101.2.2.1.1.20
-- 1.3.6.1.4.1.10428 9 1.101.2.2.1.1.20
		-- 1.3.6.1.4.1.10428 9 1.101.2.2.1.1.20
		fkEthernetPortPhysicalLinkDiscoveryMode OBJECT-TYPE
			SYNTAX INTEGER
				{
				none(1),
				manual(2),
				automatic(3)
				}
			MAX-ACCESS read-only
			STATUS current
			DESCRIPTION
				"Description."
			::= { fkEthernetPortEntry 20 }

		
--     1.3.6.1.4.1.10428 9 1.101.2.2.1.1.21
-- 1.3.6.1.4.1.10428 9 1.101.2.2.1.1.21
-- 1.3.6.1.4.1.10428 9 1.101.2.2.1.1.21
-- 1.3.6.1.4.1.10428 9 1.101.2.2.1.1.21
		-- 1.3.6.1.4.1.10428 9 1.101.2.2.1.1.21
		fkEthernetPortSfpTransceiverType OBJECT-TYPE
			SYNTAX INTEGER
				{
				sfp(1),
				gbit(2),
				xfp(3),
				unknown(255)
				}
			MAX-ACCESS read-only
			STATUS current
			DESCRIPTION
				"The type of SFP transceiver."
			::= { fkEthernetPortEntry 21 }

		
--     1.3.6.1.4.1.10428 9 1.101.2.2.1.1.22
-- 1.3.6.1.4.1.10428 9 1.101.2.2.1.1.22
-- 1.3.6.1.4.1.10428 9 1.101.2.2.1.1.22
-- 1.3.6.1.4.1.10428 9 1.101.2.2.1.1.22
		-- 1.3.6.1.4.1.10428 9 1.101.2.2.1.1.22
		fkEthernetPortSfpTransceiverDetailType OBJECT-TYPE
			SYNTAX INTEGER
				{
				fiber1000Sx(1),
				fiber1000Lx(2),
				fiber1000Cx(3),
				fiber1000T(4),
				fiber100lLxLx10(5),
				fiber100Fx(6),
				fiberBx10(7),
				fiberPx(8),
				fiberOc3MmSr(9),
				fiberOc3SmIr(10),
				fiberOc3SmLr(11),
				fiber1000Zx(12),
				unknown(255)
				}
			MAX-ACCESS read-write
			STATUS current
			DESCRIPTION
				"The detailed-type of SFP transceiver."
			::= { fkEthernetPortEntry 22 }

		
--     1.3.6.1.4.1.10428 9 1.101.2.2.1.1.23
-- 1.3.6.1.4.1.10428 9 1.101.2.2.1.1.23
-- 1.3.6.1.4.1.10428 9 1.101.2.2.1.1.23
-- 1.3.6.1.4.1.10428 9 1.101.2.2.1.1.23
		-- 1.3.6.1.4.1.10428 9 1.101.2.2.1.1.23
		fkEthernetPortSlotIndex OBJECT-TYPE
			SYNTAX Integer32
			MAX-ACCESS read-only
			STATUS current
			DESCRIPTION
				"The slot index."
			::= { fkEthernetPortEntry 23 }

		
--     1.3.6.1.4.1.10428 9 1.101.2.2.1.1.24
-- 1.3.6.1.4.1.10428 9 1.101.2.2.1.1.24
-- 1.3.6.1.4.1.10428 9 1.101.2.2.1.1.24
-- 1.3.6.1.4.1.10428 9 1.101.2.2.1.1.24
		-- 1.3.6.1.4.1.10428 9 1.101.2.2.1.1.24
		fkEthernetPortSlotPortIndex OBJECT-TYPE
			SYNTAX Integer32
			MAX-ACCESS read-only
			STATUS current
			DESCRIPTION
				"The slot's port index."
			::= { fkEthernetPortEntry 24 }

		
--   1.3.6.1.4.1.10428 9 1.101.2.2.1.1.25
-- 1.3.6.1.4.1.10428 9 1.101.2.2.1.1.25
		-- 1.3.6.1.4.1.10428 9 1.101.2.2.1.1.25
		fkEthernetPortAdminTransmissionRate OBJECT-TYPE
			SYNTAX Integer32 (10 | 100 | 1000 | 10000)
			MAX-ACCESS read-only
			STATUS current
			DESCRIPTION
				"The speed of port. Unit is Mbit/s.
				This configurations are only useful for electrical interfaces.
				Optical - interfaces will always support 1000 MBIT/s"
			::= { fkEthernetPortEntry 25 }

		
--   1.3.6.1.4.1.10428 9 1.101.2.2.1.1.26
-- 1.3.6.1.4.1.10428 9 1.101.2.2.1.1.26
		-- 1.3.6.1.4.1.10428 9 1.101.2.2.1.1.26
		fkEthernetPortAdminDuplexMode OBJECT-TYPE
			SYNTAX INTEGER
				{
				full(1),
				half(2),
				notAvailable(255)
				}
			MAX-ACCESS read-only
			STATUS current
			DESCRIPTION
				"The duplex status of port."
			::= { fkEthernetPortEntry 26 }

		
--   1.3.6.1.4.1.10428 9 1.101.2.2.1.1.27
-- 1.3.6.1.4.1.10428 9 1.101.2.2.1.1.27
		-- 1.3.6.1.4.1.10428 9 1.101.2.2.1.1.27
		fkEthernetPortAdminFlowControl OBJECT-TYPE
			SYNTAX INTEGER
				{
				disabled(1),
				enableSend(2),
				enableReceive(3),
				enabledBoth(4)
				}
			MAX-ACCESS read-only
			STATUS current
			DESCRIPTION
				"The flow-control mode of port."
			::= { fkEthernetPortEntry 27 }

		
--   1.3.6.1.4.1.10428 9 1.101.2.2.1.1.28
-- 1.3.6.1.4.1.10428 9 1.101.2.2.1.1.28
		-- 1.3.6.1.4.1.10428 9 1.101.2.2.1.1.28
		fkEthernetPortAdminNegotiationMode OBJECT-TYPE
			SYNTAX INTEGER
				{
				auto(1),
				force(2),
				notAvailable(255)
				}
			MAX-ACCESS read-only
			STATUS current
			DESCRIPTION
				"The Auto Negotiation mode of port. "
			::= { fkEthernetPortEntry 28 }

		
--  1.3.6.1.4.1.10428 9 1.101.2.2.1.1.4
-- 1.3.6.1.4.1.10428 9 1.101.2.2.1.1.4
-- 1.3.6.1.4.1.10428 9 1.101.2.2.1.1.4
-- 1.3.6.1.4.1.10428 9 1.101.2.2.1.1.29
		-- 1.3.6.1.4.1.10428 9 1.101.2.2.1.1.29
		fkEthernetPortAdminReason OBJECT-TYPE
			SYNTAX INTEGER
				{
				none(0),
				user(1),
				xllcf(2),
				all(3)
				}
			MAX-ACCESS read-only
			STATUS current
			DESCRIPTION
				"The admin down reason of port."
			::= { fkEthernetPortEntry 29 }

		
--     1.3.6.1.4.1.10428 9 1.101.2.2.2
-- 1.3.6.1.4.1.10428 9 1.101.2.2.2
-- 1.3.6.1.4.1.10428 9 1.101.2.2.2
-- 1.3.6.1.4.1.10428 9 1.101.2.2.2
		-- 1.3.6.1.4.1.10428 9 1.101.2.2.2
		fkEthernetPortControl OBJECT IDENTIFIER ::= { fkEthernetPort 2 }

		
--     1.3.6.1.4.1.10428 9 1.101.2.2.2.1
-- 1.3.6.1.4.1.10428 9 1.101.2.2.2.1
-- 1.3.6.1.4.1.10428 9 1.101.2.2.2.1
-- 1.3.6.1.4.1.10428 9 1.101.2.2.2.1
		-- 1.3.6.1.4.1.10428 9 1.101.2.2.2.1
		fkEthernetPortControlRequest OBJECT-TYPE
			SYNTAX INTEGER { setEthernetPortProfile(1) }
			MAX-ACCESS read-write
			STATUS current
			DESCRIPTION
				"Description."
			::= { fkEthernetPortControl 1 }

		
--     1.3.6.1.4.1.10428 9 1.101.2.2.2.2
-- 1.3.6.1.4.1.10428 9 1.101.2.2.2.2
-- 1.3.6.1.4.1.10428 9 1.101.2.2.2.2
-- 1.3.6.1.4.1.10428 9 1.101.2.2.2.2
		-- 1.3.6.1.4.1.10428 9 1.101.2.2.2.2
		fkEthernetPortControlStatus OBJECT-TYPE
			SYNTAX FkControlStatusType
			MAX-ACCESS read-only
			STATUS current
			DESCRIPTION
				"Description."
			::= { fkEthernetPortControl 2 }

		
--     1.3.6.1.4.1.10428 9 1.101.2.2.2.3
-- 1.3.6.1.4.1.10428 9 1.101.2.2.2.3
-- 1.3.6.1.4.1.10428 9 1.101.2.2.2.3
-- 1.3.6.1.4.1.10428 9 1.101.2.2.2.3
		-- 1.3.6.1.4.1.10428 9 1.101.2.2.2.3
		fkEthernetPortControlTimer OBJECT-TYPE
			SYNTAX Gauge32
			MAX-ACCESS read-write
			STATUS current
			DESCRIPTION
				"Description."
			::= { fkEthernetPortControl 3 }

		
--     1.3.6.1.4.1.10428 9 1.101.2.2.2.4
-- 1.3.6.1.4.1.10428 9 1.101.2.2.2.4
-- 1.3.6.1.4.1.10428 9 1.101.2.2.2.4
-- 1.3.6.1.4.1.10428 9 1.101.2.2.2.4
		-- 1.3.6.1.4.1.10428 9 1.101.2.2.2.4
		fkEthernetPortControlTimeStamp OBJECT-TYPE
			SYNTAX TimeTicks
			MAX-ACCESS read-only
			STATUS current
			DESCRIPTION
				"Description."
			::= { fkEthernetPortControl 4 }

		
--     1.3.6.1.4.1.10428 9 1.101.2.2.2.5
-- 1.3.6.1.4.1.10428 9 1.101.2.2.2.5
-- 1.3.6.1.4.1.10428 9 1.101.2.2.2.5
-- 1.3.6.1.4.1.10428 9 1.101.2.2.2.5
		-- 1.3.6.1.4.1.10428 9 1.101.2.2.2.5
		fkEthernetPortControlReqResult OBJECT-TYPE
			SYNTAX FkControlRequestResultType
			MAX-ACCESS read-only
			STATUS current
			DESCRIPTION
				"Description."
			::= { fkEthernetPortControl 5 }

		
--     1.3.6.1.4.1.10428 9 1.101.2.2.2.6
-- 1.3.6.1.4.1.10428 9 1.101.2.2.2.6
-- 1.3.6.1.4.1.10428 9 1.101.2.2.2.6
-- 1.3.6.1.4.1.10428 9 1.101.2.2.2.6
		-- 1.3.6.1.4.1.10428 9 1.101.2.2.2.6
		fkEthernetPortControlIndex OBJECT-TYPE
			SYNTAX Integer32
			MAX-ACCESS read-write
			STATUS current
			DESCRIPTION
				"Description."
			::= { fkEthernetPortControl 6 }

		
--     1.3.6.1.4.1.10428 9 1.101.2.2.2.7
-- 1.3.6.1.4.1.10428 9 1.101.2.2.2.7
-- 1.3.6.1.4.1.10428 9 1.101.2.2.2.7
-- 1.3.6.1.4.1.10428 9 1.101.2.2.2.7
		-- 1.3.6.1.4.1.10428 9 1.101.2.2.2.7
		fkEthernetPortControlType OBJECT-TYPE
			SYNTAX INTEGER
				{
				unknown(0),
				electrical(1),
				optical(2)
				}
			MAX-ACCESS read-write
			STATUS current
			DESCRIPTION
				"Description."
			::= { fkEthernetPortControl 7 }

		
--     1.3.6.1.4.1.10428 9 1.101.2.2.2.8
-- 1.3.6.1.4.1.10428 9 1.101.2.2.2.8
-- 1.3.6.1.4.1.10428 9 1.101.2.2.2.8
-- 1.3.6.1.4.1.10428 9 1.101.2.2.2.8
		-- 1.3.6.1.4.1.10428 9 1.101.2.2.2.8
		fkEthernetPortControlAdminStatus OBJECT-TYPE
			SYNTAX INTEGER
				{
				up(1),
				down(2),
				notAvailable(3)
				}
			MAX-ACCESS read-write
			STATUS current
			DESCRIPTION
				"Description."
			::= { fkEthernetPortControl 8 }

		
--     1.3.6.1.4.1.10428 9 1.101.2.2.2.9
-- 1.3.6.1.4.1.10428 9 1.101.2.2.2.9
-- 1.3.6.1.4.1.10428 9 1.101.2.2.2.9
-- 1.3.6.1.4.1.10428 9 1.101.2.2.2.9
		-- 1.3.6.1.4.1.10428 9 1.101.2.2.2.9
		fkEthernetPortControlTransmissionRate OBJECT-TYPE
			SYNTAX Integer32 (10 | 100 | 1000 | 10000)
			MAX-ACCESS read-write
			STATUS current
			DESCRIPTION
				"Description.The speed of port. Unit is Mbit/s.
				This configurations are only useful for electrical interfaces.
				Optical - interfaces will always support 1000 MBIT/s"
			::= { fkEthernetPortControl 9 }

		
--     1.3.6.1.4.1.10428 9 1.101.2.2.2.10
-- 1.3.6.1.4.1.10428 9 1.101.2.2.2.10
-- 1.3.6.1.4.1.10428 9 1.101.2.2.2.10
-- 1.3.6.1.4.1.10428 9 1.101.2.2.2.10
		-- 1.3.6.1.4.1.10428 9 1.101.2.2.2.10
		fkEthernetPortControlDuplexMode OBJECT-TYPE
			SYNTAX INTEGER
				{
				full(1),
				half(2),
				notAvailable(3)
				}
			MAX-ACCESS read-write
			STATUS current
			DESCRIPTION
				"Description."
			::= { fkEthernetPortControl 10 }

		
--     1.3.6.1.4.1.10428 9 1.101.2.2.2.11
-- 1.3.6.1.4.1.10428 9 1.101.2.2.2.11
-- 1.3.6.1.4.1.10428 9 1.101.2.2.2.11
-- 1.3.6.1.4.1.10428 9 1.101.2.2.2.11
		-- 1.3.6.1.4.1.10428 9 1.101.2.2.2.11
		fkEthernetPortControlFlowControl OBJECT-TYPE
			SYNTAX INTEGER
				{
				disabled(1),
				enabledSymetrical(2),
				enabledAsymetrical(3),
				enabledBoth(4),
				notAvailable(5)
				}
			MAX-ACCESS read-write
			STATUS current
			DESCRIPTION
				"Description."
			::= { fkEthernetPortControl 11 }

		
--     1.3.6.1.4.1.10428 9 1.101.2.2.2.12
-- 1.3.6.1.4.1.10428 9 1.101.2.2.2.12
-- 1.3.6.1.4.1.10428 9 1.101.2.2.2.12
-- 1.3.6.1.4.1.10428 9 1.101.2.2.2.12
		-- 1.3.6.1.4.1.10428 9 1.101.2.2.2.12
		fkEthernetPortControlNegotiationMode OBJECT-TYPE
			SYNTAX INTEGER
				{
				auto(1),
				force(2),
				notAvailable(3)
				}
			MAX-ACCESS read-write
			STATUS current
			DESCRIPTION
				"Description."
			::= { fkEthernetPortControl 12 }

		
--     1.3.6.1.4.1.10428 9 1.101.2.2.2.13
-- 1.3.6.1.4.1.10428 9 1.101.2.2.2.13
-- 1.3.6.1.4.1.10428 9 1.101.2.2.2.13
-- 1.3.6.1.4.1.10428 9 1.101.2.2.2.13
		-- 1.3.6.1.4.1.10428 9 1.101.2.2.2.13
		fkEthernetPortControlJumboFrameSize OBJECT-TYPE
			SYNTAX Integer32 (0 | 1518..9000)
			MAX-ACCESS read-write
			STATUS current
			DESCRIPTION
				"Description. If the value is zero, it means erasing the set-up value.
				"
			::= { fkEthernetPortControl 13 }

		
--     1.3.6.1.4.1.10428 9 1.101.2.2.2.14
-- 1.3.6.1.4.1.10428 9 1.101.2.2.2.14
-- 1.3.6.1.4.1.10428 9 1.101.2.2.2.14
-- 1.3.6.1.4.1.10428 9 1.101.2.2.2.14
		-- 1.3.6.1.4.1.10428 9 1.101.2.2.2.14
		fkEthernetPortControlPhysicalRemoteChassis OBJECT-TYPE
			SYNTAX OCTET STRING
			MAX-ACCESS read-write
			STATUS current
			DESCRIPTION
				"Description."
			::= { fkEthernetPortControl 14 }

		
--     1.3.6.1.4.1.10428 9 1.101.2.2.2.15
-- 1.3.6.1.4.1.10428 9 1.101.2.2.2.15
-- 1.3.6.1.4.1.10428 9 1.101.2.2.2.15
-- 1.3.6.1.4.1.10428 9 1.101.2.2.2.15
		-- 1.3.6.1.4.1.10428 9 1.101.2.2.2.15
		fkEthernetPortControlPhysicalRemoteSlot OBJECT-TYPE
			SYNTAX Integer32
			MAX-ACCESS read-write
			STATUS current
			DESCRIPTION
				"Description."
			::= { fkEthernetPortControl 15 }

		
--     1.3.6.1.4.1.10428 9 1.101.2.2.2.16
-- 1.3.6.1.4.1.10428 9 1.101.2.2.2.16
-- 1.3.6.1.4.1.10428 9 1.101.2.2.2.16
-- 1.3.6.1.4.1.10428 9 1.101.2.2.2.16
		-- 1.3.6.1.4.1.10428 9 1.101.2.2.2.16
		fkEthernetPortControlPhysicalRemotePort OBJECT-TYPE
			SYNTAX Integer32
			MAX-ACCESS read-write
			STATUS current
			DESCRIPTION
				"Description."
			::= { fkEthernetPortControl 16 }

		
--     1.3.6.1.4.1.10428 9 1.101.2.2.2.17
-- 1.3.6.1.4.1.10428 9 1.101.2.2.2.17
-- 1.3.6.1.4.1.10428 9 1.101.2.2.2.17
-- 1.3.6.1.4.1.10428 9 1.101.2.2.2.17
		-- 1.3.6.1.4.1.10428 9 1.101.2.2.2.17
		fkEthernetPortControlPhysicalLinkDiscoveryMode OBJECT-TYPE
			SYNTAX INTEGER
				{
				none(1),
				manual(2),
				automatic(3)
				}
			MAX-ACCESS read-write
			STATUS current
			DESCRIPTION
				"Description."
			::= { fkEthernetPortControl 17 }

		
--     1.3.6.1.4.1.10428 9 1.101.2.2.3
-- 1.3.6.1.4.1.10428 9 1.101.2.2.3
-- 1.3.6.1.4.1.10428 9 1.101.2.2.3
-- 1.3.6.1.4.1.10428 9 1.101.2.2.3
		-- 1.3.6.1.4.1.10428 9 1.101.2.2.3
		fkEthernetPortNotification OBJECT IDENTIFIER ::= { fkEthernetPort 3 }

		
--     1.3.6.1.4.1.10428 9 1.101.2.2.3.1
-- 1.3.6.1.4.1.10428 9 1.101.2.2.3.1
-- 1.3.6.1.4.1.10428 9 1.101.2.2.3.1
-- 1.3.6.1.4.1.10428 9 1.101.2.2.3.1
		-- 1.3.6.1.4.1.10428 9 1.101.2.2.3.1
		fkEthernetPortChanged NOTIFICATION-TYPE
			OBJECTS { fkEthernetPortType, fkEthernetPortAdminStatus, fkEthernetPortTransmissionRate, fkEthernetPortDuplexMode, fkEthernetPortFlowControl, 
				fkEthernetPortNegotiationMode, fkEthernetPortJumboFrameSize, fkEthernetPortSfpVendorName, fkEthernetPortSfpVendorPartNumber, fkEthernetPortSfpVendorRevision, 
				fkEthernetPortSfpVendorSerialNumber, fkEthernetPortSfpDateCode, fkEthernetPortPhysicalRemoteChassis, fkEthernetPortPhysicalRemoteSlot, fkEthernetPortPhysicalRemotePort, 
				fkEthernetPortPhysicalLinkDiscoveryMode, fkEthernetPortControlRequest, fkEthernetPortControlTimeStamp, fkEthernetPortControlReqResult }
			STATUS current
			DESCRIPTION 
				"Description."
			::= { fkEthernetPortNotification 1 }

		
--     1.3.6.1.4.1.10428 9 1.101.2.2.4
-- 1.3.6.1.4.1.10428 9 1.101.2.2.4
-- 1.3.6.1.4.1.10428 9 1.101.2.2.4
-- 1.3.6.1.4.1.10428 9 1.101.2.2.4
		-- 1.3.6.1.4.1.10428 9 1.101.2.2.4
		fkEthernetPortDMITable OBJECT-TYPE
			SYNTAX SEQUENCE OF FkEthernetPortDMIEntry
			MAX-ACCESS not-accessible
			STATUS current
			DESCRIPTION
				"Description."
			::= { fkEthernetPort 4 }

		
--     1.3.6.1.4.1.10428 9 1.101.2.2.4.1
-- 1.3.6.1.4.1.10428 9 1.101.2.2.4.1
-- 1.3.6.1.4.1.10428 9 1.101.2.2.4.1
-- 1.3.6.1.4.1.10428 9 1.101.2.2.4.1
		-- 1.3.6.1.4.1.10428 9 1.101.2.2.4.1
		fkEthernetPortDMIEntry OBJECT-TYPE
			SYNTAX FkEthernetPortDMIEntry
			MAX-ACCESS not-accessible
			STATUS current
			DESCRIPTION
				"Description."
			INDEX { fkEthernetPortDMIIndex }
			::= { fkEthernetPortDMITable 1 }

		
		FkEthernetPortDMIEntry ::=
			SEQUENCE { 
				fkEthernetPortDMIIndex
					INTEGER,
				fkEthernetPortDMITemper
					OCTET STRING,
				fkEthernetPortDMIVoltage
					OCTET STRING,
				fkEthernetPortDMITxBias
					OCTET STRING,
				fkEthernetPortDMITxPower
					OCTET STRING,
				fkEthernetPortDMIRxPower
					OCTET STRING
			 }

--     1.3.6.1.4.1.10428 9 1.101.2.2.4.1.1
-- 1.3.6.1.4.1.10428 9 1.101.2.2.4.1.1
-- 1.3.6.1.4.1.10428 9 1.101.2.2.4.1.1
-- 1.3.6.1.4.1.10428 9 1.101.2.2.4.1.1
		-- 1.3.6.1.4.1.10428 9 1.101.2.2.4.1.1
		fkEthernetPortDMIIndex OBJECT-TYPE
			SYNTAX INTEGER (1..255)
			MAX-ACCESS read-only
			STATUS current
			DESCRIPTION
				"Port Index."
			::= { fkEthernetPortDMIEntry 1 }

		
--     1.3.6.1.4.1.10428 9 1.101.2.2.4.1.2
-- 1.3.6.1.4.1.10428 9 1.101.2.2.4.1.2
-- 1.3.6.1.4.1.10428 9 1.101.2.2.4.1.2
-- 1.3.6.1.4.1.10428 9 1.101.2.2.4.1.2
		-- 1.3.6.1.4.1.10428 9 1.101.2.2.4.1.2
		fkEthernetPortDMITemper OBJECT-TYPE
			SYNTAX OCTET STRING
			MAX-ACCESS read-only
			STATUS current
			DESCRIPTION
				"Internally measured module temperature."
			::= { fkEthernetPortDMIEntry 2 }

		
--     1.3.6.1.4.1.10428 9 1.101.2.2.4.1.3
-- 1.3.6.1.4.1.10428 9 1.101.2.2.4.1.3
-- 1.3.6.1.4.1.10428 9 1.101.2.2.4.1.3
-- 1.3.6.1.4.1.10428 9 1.101.2.2.4.1.3
		-- 1.3.6.1.4.1.10428 9 1.101.2.2.4.1.3
		fkEthernetPortDMIVoltage OBJECT-TYPE
			SYNTAX OCTET STRING
			MAX-ACCESS read-only
			STATUS current
			DESCRIPTION
				"Internally measured supply voltage in transceiver."
			::= { fkEthernetPortDMIEntry 3 }

		
--     1.3.6.1.4.1.10428 9 1.101.2.2.4.1.4
-- 1.3.6.1.4.1.10428 9 1.101.2.2.4.1.4
-- 1.3.6.1.4.1.10428 9 1.101.2.2.4.1.4
-- 1.3.6.1.4.1.10428 9 1.101.2.2.4.1.4
		-- 1.3.6.1.4.1.10428 9 1.101.2.2.4.1.4
		fkEthernetPortDMITxBias OBJECT-TYPE
			SYNTAX OCTET STRING
			MAX-ACCESS read-only
			STATUS current
			DESCRIPTION
				"Internally measured TX Bias Current."
			::= { fkEthernetPortDMIEntry 4 }

		
--     1.3.6.1.4.1.10428 9 1.101.2.2.4.1.5
-- 1.3.6.1.4.1.10428 9 1.101.2.2.4.1.5
-- 1.3.6.1.4.1.10428 9 1.101.2.2.4.1.5
-- 1.3.6.1.4.1.10428 9 1.101.2.2.4.1.5
		-- 1.3.6.1.4.1.10428 9 1.101.2.2.4.1.5
		fkEthernetPortDMITxPower OBJECT-TYPE
			SYNTAX OCTET STRING
			MAX-ACCESS read-only
			STATUS current
			DESCRIPTION
				"Measured TX output power."
			::= { fkEthernetPortDMIEntry 5 }

		
--     1.3.6.1.4.1.10428 9 1.101.2.2.4.1.6
-- 1.3.6.1.4.1.10428 9 1.101.2.2.4.1.6
-- 1.3.6.1.4.1.10428 9 1.101.2.2.4.1.6
-- 1.3.6.1.4.1.10428 9 1.101.2.2.4.1.6
		-- 1.3.6.1.4.1.10428 9 1.101.2.2.4.1.6
		fkEthernetPortDMIRxPower OBJECT-TYPE
			SYNTAX OCTET STRING
			MAX-ACCESS read-only
			STATUS current
			DESCRIPTION
				"Measured RX input power."
			::= { fkEthernetPortDMIEntry 6 }

		
--     1.3.6.1.4.1.10428 9 1.101.2.2.5
-- 1.3.6.1.4.1.10428 9 1.101.2.2.5
-- 1.3.6.1.4.1.10428 9 1.101.2.2.5
-- 1.3.6.1.4.1.10428 9 1.101.2.2.5
		-- 1.3.6.1.4.1.10428 9 1.101.2.2.5
		fkEthernetSFPTable OBJECT-TYPE
			SYNTAX SEQUENCE OF FkEthernetSFPEntry
			MAX-ACCESS not-accessible
			STATUS current
			DESCRIPTION
				"Description."
			::= { fkEthernetPort 5 }

		
--     1.3.6.1.4.1.10428 9 1.101.2.2.5.1
-- 1.3.6.1.4.1.10428 9 1.101.2.2.5.1
-- 1.3.6.1.4.1.10428 9 1.101.2.2.5.1
-- 1.3.6.1.4.1.10428 9 1.101.2.2.5.1
		-- 1.3.6.1.4.1.10428 9 1.101.2.2.5.1
		fkEthernetSFPEntry OBJECT-TYPE
			SYNTAX FkEthernetSFPEntry
			MAX-ACCESS not-accessible
			STATUS current
			DESCRIPTION
				"Description."
			INDEX { fkEthernetSfpIndex }
			::= { fkEthernetSFPTable 1 }

		
		FkEthernetSFPEntry ::=
			SEQUENCE { 
				fkEthernetSfpIndex
					Integer32,
				fkEthernetSfpTransceiver
					INTEGER,
				fkEthernetSfpVendorName
					OCTET STRING,
				fkEthernetSfpVendorPartNumber
					OCTET STRING,
				fkEthernetSfpVendorRevision
					OCTET STRING,
				fkEthernetSfpVendorSerialNumber
					OCTET STRING,
				fkEthernetSfpDateCode
					OCTET STRING,
				fkEthernetSfpTransceiverType
					INTEGER,
				fkEthernetSfpTransceiverDetailType
					INTEGER,
				fkEthernetSfpTransceiverCodes
					OCTET STRING,
				fkEthernetSfpSpeed
					OCTET STRING,
				fkEthernetSfpLength
					Integer32,
				fkEthernetSfpWaveLength
					Integer32,
				fkEthernetSFPMultimodeLengthOm1
					Integer32,
				fkEthernetSFPMultimodeLengthOm2
					Integer32,
				fkEthernetSFPMultimodeLengthOm3
					Integer32
			 }

--     1.3.6.1.4.1.10428 9 1.101.2.2.5.1.1
-- 1.3.6.1.4.1.10428 9 1.101.2.2.5.1.1
-- 1.3.6.1.4.1.10428 9 1.101.2.2.5.1.1
-- 1.3.6.1.4.1.10428 9 1.101.2.2.5.1.1
		-- 1.3.6.1.4.1.10428 9 1.101.2.2.5.1.1
		fkEthernetSfpIndex OBJECT-TYPE
			SYNTAX Integer32 (1..65556)
			MAX-ACCESS read-only
			STATUS current
			DESCRIPTION
				"The SFP index."
			::= { fkEthernetSFPEntry 1 }

		
--     1.3.6.1.4.1.10428 9 1.101.2.2.5.1.2
-- 1.3.6.1.4.1.10428 9 1.101.2.2.5.1.2
-- 1.3.6.1.4.1.10428 9 1.101.2.2.5.1.2
-- 1.3.6.1.4.1.10428 9 1.101.2.2.5.1.2
		-- 1.3.6.1.4.1.10428 9 1.101.2.2.5.1.2
		fkEthernetSfpTransceiver OBJECT-TYPE
			SYNTAX INTEGER
				{
				unknown(0),
				electrical(1),
				electricalCoaxial(2),
				opticalLongHaul(3),
				opticalShortHaul(4),
				optical10G(5),
				opticalGpon(6)
				}
			MAX-ACCESS read-only
			STATUS current
			DESCRIPTION
				"The type of SFP"
			::= { fkEthernetSFPEntry 2 }

		
--     1.3.6.1.4.1.10428 9 1.101.2.2.5.1.3
-- 1.3.6.1.4.1.10428 9 1.101.2.2.5.1.3
-- 1.3.6.1.4.1.10428 9 1.101.2.2.5.1.3
-- 1.3.6.1.4.1.10428 9 1.101.2.2.5.1.3
		-- 1.3.6.1.4.1.10428 9 1.101.2.2.5.1.3
		fkEthernetSfpVendorName OBJECT-TYPE
			SYNTAX OCTET STRING
			MAX-ACCESS read-only
			STATUS current
			DESCRIPTION
				"The vendor name of SFP"
			::= { fkEthernetSFPEntry 3 }

		
--     1.3.6.1.4.1.10428 9 1.101.2.2.5.1.4
-- 1.3.6.1.4.1.10428 9 1.101.2.2.5.1.4
-- 1.3.6.1.4.1.10428 9 1.101.2.2.5.1.4
-- 1.3.6.1.4.1.10428 9 1.101.2.2.5.1.4
		-- 1.3.6.1.4.1.10428 9 1.101.2.2.5.1.4
		fkEthernetSfpVendorPartNumber OBJECT-TYPE
			SYNTAX OCTET STRING
			MAX-ACCESS read-only
			STATUS current
			DESCRIPTION
				"The part number of SFP"
			::= { fkEthernetSFPEntry 4 }

		
--     1.3.6.1.4.1.10428 9 1.101.2.2.5.1.5
-- 1.3.6.1.4.1.10428 9 1.101.2.2.5.1.5
-- 1.3.6.1.4.1.10428 9 1.101.2.2.5.1.5
-- 1.3.6.1.4.1.10428 9 1.101.2.2.5.1.5
		-- 1.3.6.1.4.1.10428 9 1.101.2.2.5.1.5
		fkEthernetSfpVendorRevision OBJECT-TYPE
			SYNTAX OCTET STRING
			MAX-ACCESS read-only
			STATUS current
			DESCRIPTION
				"The revision of SFP"
			::= { fkEthernetSFPEntry 5 }

		
--     1.3.6.1.4.1.10428 9 1.101.2.2.5.1.6
-- 1.3.6.1.4.1.10428 9 1.101.2.2.5.1.6
-- 1.3.6.1.4.1.10428 9 1.101.2.2.5.1.6
-- 1.3.6.1.4.1.10428 9 1.101.2.2.5.1.6
		-- 1.3.6.1.4.1.10428 9 1.101.2.2.5.1.6
		fkEthernetSfpVendorSerialNumber OBJECT-TYPE
			SYNTAX OCTET STRING
			MAX-ACCESS read-only
			STATUS current
			DESCRIPTION
				"The serial number of SFP"
			::= { fkEthernetSFPEntry 6 }

		
--     1.3.6.1.4.1.10428 9 1.101.2.2.5.1.7
-- 1.3.6.1.4.1.10428 9 1.101.2.2.5.1.7
-- 1.3.6.1.4.1.10428 9 1.101.2.2.5.1.7
-- 1.3.6.1.4.1.10428 9 1.101.2.2.5.1.7
		-- 1.3.6.1.4.1.10428 9 1.101.2.2.5.1.7
		fkEthernetSfpDateCode OBJECT-TYPE
			SYNTAX OCTET STRING
			MAX-ACCESS read-only
			STATUS current
			DESCRIPTION
				"The manufacturing date of SFP"
			::= { fkEthernetSFPEntry 7 }

		
--     1.3.6.1.4.1.10428 9 1.101.2.2.5.1.8
-- 1.3.6.1.4.1.10428 9 1.101.2.2.5.1.8
-- 1.3.6.1.4.1.10428 9 1.101.2.2.5.1.8
-- 1.3.6.1.4.1.10428 9 1.101.2.2.5.1.8
		-- 1.3.6.1.4.1.10428 9 1.101.2.2.5.1.8
		fkEthernetSfpTransceiverType OBJECT-TYPE
			SYNTAX INTEGER
				{
				sfp(1),
				gbit(2),
				xfp(3),
				unknown(255)
				}
			MAX-ACCESS read-only
			STATUS current
			DESCRIPTION
				"The type of SFP transceiver."
			::= { fkEthernetSFPEntry 8 }

		
--     1.3.6.1.4.1.10428 9 1.101.2.2.5.1.9
-- 1.3.6.1.4.1.10428 9 1.101.2.2.5.1.9
-- 1.3.6.1.4.1.10428 9 1.101.2.2.5.1.9
-- 1.3.6.1.4.1.10428 9 1.101.2.2.5.1.9
		-- 1.3.6.1.4.1.10428 9 1.101.2.2.5.1.9
		fkEthernetSfpTransceiverDetailType OBJECT-TYPE
			SYNTAX INTEGER
				{
				fiber1000Sx(1),
				fiber1000Lx(2),
				fiber1000Cx(3),
				fiber1000T(4),
				fiber100lLxLx10(5),
				fiber100Fx(6),
				fiberBx10(7),
				fiberPx(8),
				fiberOc3MmSr(9),
				fiberOc3SmIr(10),
				fiberOc3SmLr(11),
				fiber1000Zx(12),
				base10GSR(64),
				base10GLR(65),
				base10GER(66),
				base10GLRM(67),
				base10GSW(68),
				base10GLW(69),
				base10GEW(70),
				base10GEWorZW(71),
				unknown(255)
				}
			MAX-ACCESS read-write
			STATUS current
			DESCRIPTION
				"The detailed-type of SFP transceiver."
			::= { fkEthernetSFPEntry 9 }

		
--     1.3.6.1.4.1.10428 9 1.101.2.2.5.1.10
-- 1.3.6.1.4.1.10428 9 1.101.2.2.5.1.10
-- 1.3.6.1.4.1.10428 9 1.101.2.2.5.1.10
-- 1.3.6.1.4.1.10428 9 1.101.2.2.5.1.10
		-- 1.3.6.1.4.1.10428 9 1.101.2.2.5.1.10
		fkEthernetSfpTransceiverCodes OBJECT-TYPE
			SYNTAX OCTET STRING (SIZE (1..8))
			MAX-ACCESS read-only
			STATUS current
			DESCRIPTION
				"The transceiver codes.
				In case of SFP, reference SFP-8472 Rev 11.0
				  - Table 3.5: Transceiver codes (Address A0h)
				  - Table 3.5a: SONET Compliance Specifiers (A0h)
				In case of XFP, reference XFP Specification Revision 4.5 (August 31,2005)
				  - Table 40 Transceiver codes
				"
			::= { fkEthernetSFPEntry 10 }

		
--  1.3.6.1.4.1.10428 9 1.101.2.2.5.1.11
		-- 1.3.6.1.4.1.10428 9 1.101.2.2.5.1.11
		fkEthernetSfpSpeed OBJECT-TYPE
			SYNTAX OCTET STRING
			MAX-ACCESS read-only
			STATUS current
			DESCRIPTION
				"The speed of SFP"
			::= { fkEthernetSFPEntry 11 }

		
--  1.3.6.1.4.1.10428 9 1.101.2.2.5.1.12
		-- 1.3.6.1.4.1.10428 9 1.101.2.2.5.1.12
		fkEthernetSfpLength OBJECT-TYPE
			SYNTAX Integer32
			MAX-ACCESS read-only
			STATUS current
			DESCRIPTION
				"The length of SFP"
			::= { fkEthernetSFPEntry 12 }

		
--  1.3.6.1.4.1.10428 9 1.101.2.2.5.1.13
		-- 1.3.6.1.4.1.10428 9 1.101.2.2.5.1.13
		fkEthernetSfpWaveLength OBJECT-TYPE
			SYNTAX Integer32
			MAX-ACCESS read-only
			STATUS current
			DESCRIPTION
				"The wavelength of SFP"
			::= { fkEthernetSFPEntry 13 }

		
		-- 1.3.6.1.4.1.10428 9 1.101.2.2.5.1.14
		fkEthernetSFPMultimodeLengthOm1 OBJECT-TYPE
			SYNTAX Integer32
			MAX-ACCESS read-only
			STATUS current
			DESCRIPTION
				"The Flame rating is 62.5um(OM1). This is used only for 10G SFP module with multi-mode.
				ref) 50/125 Multimode Fiber Optic 
				50/125 is one of the most commonly used multimode optical fiber, the other commonly used is 62.5/125 types. 
				There is a special kind 50/125 multimode fibers, which is called OM3 50/125. People usually refer 62.5/125 as the OM1 MMF, 
				common type 50/125 MMF as OM2, OM3 is also 50/125, but it is different from OM2 because it support 10Gig data transmission. 
				The OM3 50/125 fiber optic cable is also called laser optimized fiber cable. 
				Both OM1 and OM2 multimode cables use the orange color jacket (standard practice for commonly used indoor multimode), 
				OM3 use a special color, which is called Aqua."
			::= { fkEthernetSFPEntry 14 }

		
		-- 1.3.6.1.4.1.10428 9 1.101.2.2.5.1.15
		fkEthernetSFPMultimodeLengthOm2 OBJECT-TYPE
			SYNTAX Integer32
			MAX-ACCESS read-only
			STATUS current
			DESCRIPTION
				"The Flame rating is 50um(OM2). This is used only for 10G SFP module with multi-mode.
				ref) 50/125 Multimode Fiber Optic 
				50/125 is one of the most commonly used multimode optical fiber, the other commonly used is 62.5/125 types. 
				There is a special kind 50/125 multimode fibers, which is called OM3 50/125. People usually refer 62.5/125 as the OM1 MMF, 
				common type 50/125 MMF as OM2, OM3 is also 50/125, but it is different from OM2 because it support 10Gig data transmission. 
				The OM3 50/125 fiber optic cable is also called laser optimized fiber cable. 
				Both OM1 and OM2 multimode cables use the orange color jacket (standard practice for commonly used indoor multimode), 
				OM3 use a special color, which is called Aqua."
			::= { fkEthernetSFPEntry 15 }

		
		-- 1.3.6.1.4.1.10428 9 1.101.2.2.5.1.16
		fkEthernetSFPMultimodeLengthOm3 OBJECT-TYPE
			SYNTAX Integer32
			MAX-ACCESS read-only
			STATUS current
			DESCRIPTION
				"The Flame rating is 50um(OM3). This is used only for 10G SFP module with multi-mode.
				ref) 50/125 Multimode Fiber Optic 
				50/125 is one of the most commonly used multimode optical fiber, the other commonly used is 62.5/125 types. 
				There is a special kind 50/125 multimode fibers, which is called OM3 50/125. People usually refer 62.5/125 as the OM1 MMF, 
				common type 50/125 MMF as OM2, OM3 is also 50/125, but it is different from OM2 because it support 10Gig data transmission. 
				The OM3 50/125 fiber optic cable is also called laser optimized fiber cable. 
				Both OM1 and OM2 multimode cables use the orange color jacket (standard practice for commonly used indoor multimode), 
				OM3 use a special color, which is called Aqua."
			::= { fkEthernetSFPEntry 16 }

		
--     1.3.6.1.4.1.10428 9 1.101.2.2.6
-- 1.3.6.1.4.1.10428 9 1.101.2.2.6
-- 1.3.6.1.4.1.10428 9 1.101.2.2.6
-- 1.3.6.1.4.1.10428 9 1.101.2.2.6
		-- 1.3.6.1.4.1.10428 9 1.101.2.2.6
		fkEthernetSFPControl OBJECT IDENTIFIER ::= { fkEthernetPort 6 }

		
--     1.3.6.1.4.1.10428 9 1.101.2.2.6.1
-- 1.3.6.1.4.1.10428 9 1.101.2.2.6.1
-- 1.3.6.1.4.1.10428 9 1.101.2.2.6.1
-- 1.3.6.1.4.1.10428 9 1.101.2.2.6.1
		-- 1.3.6.1.4.1.10428 9 1.101.2.2.6.1
		fkEthernetSFPControlRequest OBJECT-TYPE
			SYNTAX INTEGER { setSFPRemoteReset(1) }
			MAX-ACCESS read-write
			STATUS current
			DESCRIPTION
				"Description."
			::= { fkEthernetSFPControl 1 }

		
--     1.3.6.1.4.1.10428 9 1.101.2.2.6.2
-- 1.3.6.1.4.1.10428 9 1.101.2.2.6.2
-- 1.3.6.1.4.1.10428 9 1.101.2.2.6.2
-- 1.3.6.1.4.1.10428 9 1.101.2.2.6.2
		-- 1.3.6.1.4.1.10428 9 1.101.2.2.6.2
		fkEthernetSFPControlStatus OBJECT-TYPE
			SYNTAX FkControlStatusType
			MAX-ACCESS read-only
			STATUS current
			DESCRIPTION
				"Description."
			::= { fkEthernetSFPControl 2 }

		
--     1.3.6.1.4.1.10428 9 1.101.2.2.6.3
-- 1.3.6.1.4.1.10428 9 1.101.2.2.6.3
-- 1.3.6.1.4.1.10428 9 1.101.2.2.6.3
-- 1.3.6.1.4.1.10428 9 1.101.2.2.6.3
		-- 1.3.6.1.4.1.10428 9 1.101.2.2.6.3
		fkEthernetSFPControlTimer OBJECT-TYPE
			SYNTAX Gauge32
			MAX-ACCESS read-write
			STATUS current
			DESCRIPTION
				"Description."
			::= { fkEthernetSFPControl 3 }

		
--     1.3.6.1.4.1.10428 9 1.101.2.2.6.4
-- 1.3.6.1.4.1.10428 9 1.101.2.2.6.4
-- 1.3.6.1.4.1.10428 9 1.101.2.2.6.4
-- 1.3.6.1.4.1.10428 9 1.101.2.2.6.4
		-- 1.3.6.1.4.1.10428 9 1.101.2.2.6.4
		fkEthernetSFPControlTimeStamp OBJECT-TYPE
			SYNTAX TimeTicks
			MAX-ACCESS read-only
			STATUS current
			DESCRIPTION
				"Description."
			::= { fkEthernetSFPControl 4 }

		
--     1.3.6.1.4.1.10428 9 1.101.2.2.6.5
-- 1.3.6.1.4.1.10428 9 1.101.2.2.6.5
-- 1.3.6.1.4.1.10428 9 1.101.2.2.6.5
-- 1.3.6.1.4.1.10428 9 1.101.2.2.6.5
		-- 1.3.6.1.4.1.10428 9 1.101.2.2.6.5
		fkEthernetSFPControlReqResult OBJECT-TYPE
			SYNTAX FkControlRequestResultType
			MAX-ACCESS read-only
			STATUS current
			DESCRIPTION
				"Description."
			::= { fkEthernetSFPControl 5 }

		
--     1.3.6.1.4.1.10428 9 1.101.2.2.6.6
-- 1.3.6.1.4.1.10428 9 1.101.2.2.6.6
-- 1.3.6.1.4.1.10428 9 1.101.2.2.6.6
-- 1.3.6.1.4.1.10428 9 1.101.2.2.6.6
		-- 1.3.6.1.4.1.10428 9 1.101.2.2.6.6
		fkEthernetSFPControlIndex OBJECT-TYPE
			SYNTAX Integer32
			MAX-ACCESS read-write
			STATUS current
			DESCRIPTION
				"Description."
			::= { fkEthernetSFPControl 6 }

		
--     1.3.6.1.4.1.10428 9 1.101.2.2.7
-- 1.3.6.1.4.1.10428 9 1.101.2.2.7
-- 1.3.6.1.4.1.10428 9 1.101.2.2.7
-- 1.3.6.1.4.1.10428 9 1.101.2.2.7
		-- 1.3.6.1.4.1.10428 9 1.101.2.2.7
		fkEthernetSFPNotification OBJECT IDENTIFIER ::= { fkEthernetPort 7 }

		
--     1.3.6.1.4.1.10428 9 1.101.2.2.7.1
-- 1.3.6.1.4.1.10428 9 1.101.2.2.7.1
-- 1.3.6.1.4.1.10428 9 1.101.2.2.7.1
-- 1.3.6.1.4.1.10428 9 1.101.2.2.7.1
		-- 1.3.6.1.4.1.10428 9 1.101.2.2.7.1
		fkEthernetSFPRemoteReset NOTIFICATION-TYPE
			OBJECTS { fkEthernetSFPControlRequest, fkEthernetSFPControlTimeStamp, fkEthernetSFPControlReqResult, fkEthernetSFPControlIndex }
			STATUS current
			DESCRIPTION 
				"Description."
			::= { fkEthernetSFPNotification 1 }

		
--     1.3.6.1.4.1.10428 9 1.101.2.3
-- 1.3.6.1.4.1.10428 9 1.101.2.3
-- 1.3.6.1.4.1.10428 9 1.101.2.3
-- 1.3.6.1.4.1.10428 9 1.101.2.3
		-- 1.3.6.1.4.1.10428 9 1.101.2.3
		fkPower OBJECT IDENTIFIER ::= { fkDevice 3 }

		
--     1.3.6.1.4.1.10428 9 1.101.2.3.1
-- 1.3.6.1.4.1.10428 9 1.101.2.3.1
-- 1.3.6.1.4.1.10428 9 1.101.2.3.1
-- 1.3.6.1.4.1.10428 9 1.101.2.3.1
		-- 1.3.6.1.4.1.10428 9 1.101.2.3.1
		fkPowerTable OBJECT-TYPE
			SYNTAX SEQUENCE OF FkPowerEntry
			MAX-ACCESS not-accessible
			STATUS current
			DESCRIPTION
				"Description."
			::= { fkPower 1 }

		
--     1.3.6.1.4.1.10428 9 1.101.2.3.1.1
-- 1.3.6.1.4.1.10428 9 1.101.2.3.1.1
-- 1.3.6.1.4.1.10428 9 1.101.2.3.1.1
-- 1.3.6.1.4.1.10428 9 1.101.2.3.1.1
		-- 1.3.6.1.4.1.10428 9 1.101.2.3.1.1
		fkPowerEntry OBJECT-TYPE
			SYNTAX FkPowerEntry
			MAX-ACCESS not-accessible
			STATUS current
			DESCRIPTION
				"Description."
			INDEX { fkPowerIndex }
			::= { fkPowerTable 1 }

		
		FkPowerEntry ::=
			SEQUENCE { 
				fkPowerIndex
					INTEGER,
				fkPowerPhyIndex
					Integer32,
				fkPowerState
					INTEGER,
				fkPowerType
					INTEGER,
				fkPowerPSUType
					INTEGER
			 }

--     1.3.6.1.4.1.10428 9 1.101.2.3.1.1.1
-- 1.3.6.1.4.1.10428 9 1.101.2.3.1.1.1
-- 1.3.6.1.4.1.10428 9 1.101.2.3.1.1.1
-- 1.3.6.1.4.1.10428 9 1.101.2.3.1.1.1
		-- 1.3.6.1.4.1.10428 9 1.101.2.3.1.1.1
		fkPowerIndex OBJECT-TYPE
			SYNTAX INTEGER (1..255)
			MAX-ACCESS read-only
			STATUS current
			DESCRIPTION
				"A unique value, greater than zero, for each module. It is recommended that values are assigned contiguously starting from 1. The value for each interface sub-layer must remain constant at least from one re-initialization of the entity's network management system to the next re-initialization."
			::= { fkPowerEntry 1 }

		
--     1.3.6.1.4.1.10428 9 1.101.2.3.1.1.2
-- 1.3.6.1.4.1.10428 9 1.101.2.3.1.1.2
-- 1.3.6.1.4.1.10428 9 1.101.2.3.1.1.2
-- 1.3.6.1.4.1.10428 9 1.101.2.3.1.1.2
		-- 1.3.6.1.4.1.10428 9 1.101.2.3.1.1.2
		fkPowerPhyIndex OBJECT-TYPE
			SYNTAX Integer32
			MAX-ACCESS read-only
			STATUS current
			DESCRIPTION
				"entPhysicalIndex of Power Modules (0: Internal, -1: uninstalled)"
			::= { fkPowerEntry 2 }

		
--     1.3.6.1.4.1.10428 9 1.101.2.3.1.1.3
-- 1.3.6.1.4.1.10428 9 1.101.2.3.1.1.3
-- 1.3.6.1.4.1.10428 9 1.101.2.3.1.1.3
-- 1.3.6.1.4.1.10428 9 1.101.2.3.1.1.3
		-- 1.3.6.1.4.1.10428 9 1.101.2.3.1.1.3
		fkPowerState OBJECT-TYPE
			SYNTAX INTEGER
				{
				failure(0),
				ok(1)
				}
			MAX-ACCESS read-only
			STATUS current
			DESCRIPTION
				"Power status information."
			::= { fkPowerEntry 3 }

		
--     1.3.6.1.4.1.10428 9 1.101.2.3.1.1.4
-- 1.3.6.1.4.1.10428 9 1.101.2.3.1.1.4
-- 1.3.6.1.4.1.10428 9 1.101.2.3.1.1.4
-- 1.3.6.1.4.1.10428 9 1.101.2.3.1.1.4
		-- 1.3.6.1.4.1.10428 9 1.101.2.3.1.1.4
		fkPowerType OBJECT-TYPE
			SYNTAX INTEGER
				{
				ac(1),
				dc(2),
				unknown(3),
				psu(4)
				}
			MAX-ACCESS read-only
			STATUS current
			DESCRIPTION
				"Power type information."
			::= { fkPowerEntry 4 }

		
--     1.3.6.1.4.1.10428 9 1.101.2.3.1.1.5
-- 1.3.6.1.4.1.10428 9 1.101.2.3.1.1.5
-- 1.3.6.1.4.1.10428 9 1.101.2.3.1.1.5
-- 1.3.6.1.4.1.10428 9 1.101.2.3.1.1.5
		-- 1.3.6.1.4.1.10428 9 1.101.2.3.1.1.5
		fkPowerPSUType OBJECT-TYPE
			SYNTAX INTEGER
				{
				psuA(1),
				psuS(2),
				unknown(255)
				}
			MAX-ACCESS read-only
			STATUS current
			DESCRIPTION
				"The type of Power Supply Unit.(DC)"
			::= { fkPowerEntry 5 }

		
--     1.3.6.1.4.1.10428 9 1.101.2.4
-- 1.3.6.1.4.1.10428 9 1.101.2.4
-- 1.3.6.1.4.1.10428 9 1.101.2.4
-- 1.3.6.1.4.1.10428 9 1.101.2.4
		-- 1.3.6.1.4.1.10428 9 1.101.2.4
		fkFanModule OBJECT IDENTIFIER ::= { fkDevice 4 }

		
--     1.3.6.1.4.1.10428 9 1.101.2.4.1
-- 1.3.6.1.4.1.10428 9 1.101.2.4.1
-- 1.3.6.1.4.1.10428 9 1.101.2.4.1
-- 1.3.6.1.4.1.10428 9 1.101.2.4.1
		-- 1.3.6.1.4.1.10428 9 1.101.2.4.1
		fkFanModuleTable OBJECT-TYPE
			SYNTAX SEQUENCE OF FkFanModuleEntry
			MAX-ACCESS not-accessible
			STATUS current
			DESCRIPTION
				"Description."
			::= { fkFanModule 1 }

		
--     1.3.6.1.4.1.10428 9 1.101.2.4.1.1
-- 1.3.6.1.4.1.10428 9 1.101.2.4.1.1
-- 1.3.6.1.4.1.10428 9 1.101.2.4.1.1
-- 1.3.6.1.4.1.10428 9 1.101.2.4.1.1
		-- 1.3.6.1.4.1.10428 9 1.101.2.4.1.1
		fkFanModuleEntry OBJECT-TYPE
			SYNTAX FkFanModuleEntry
			MAX-ACCESS not-accessible
			STATUS current
			DESCRIPTION
				"Description."
			INDEX { fkFanModuleIndex }
			::= { fkFanModuleTable 1 }

		
		FkFanModuleEntry ::=
			SEQUENCE { 
				fkFanModuleIndex
					INTEGER,
				fkFanModulePhyIndex
					Integer32,
				fkFanModuleUnitNum
					Integer32,
				fkFanModuleAdminState
					INTEGER,
				fkFanModuleSpeedThreshold
					Integer32
			 }

--     1.3.6.1.4.1.10428 9 1.101.2.4.1.1.1
-- 1.3.6.1.4.1.10428 9 1.101.2.4.1.1.1
-- 1.3.6.1.4.1.10428 9 1.101.2.4.1.1.1
-- 1.3.6.1.4.1.10428 9 1.101.2.4.1.1.1
		-- 1.3.6.1.4.1.10428 9 1.101.2.4.1.1.1
		fkFanModuleIndex OBJECT-TYPE
			SYNTAX INTEGER (1..255)
			MAX-ACCESS read-only
			STATUS current
			DESCRIPTION
				"A unique value, greater than zero, for each module. It is recommended that values are assigned contiguously starting from 1."
			::= { fkFanModuleEntry 1 }

		
--     1.3.6.1.4.1.10428 9 1.101.2.4.1.1.2
-- 1.3.6.1.4.1.10428 9 1.101.2.4.1.1.2
-- 1.3.6.1.4.1.10428 9 1.101.2.4.1.1.2
-- 1.3.6.1.4.1.10428 9 1.101.2.4.1.1.2
		-- 1.3.6.1.4.1.10428 9 1.101.2.4.1.1.2
		fkFanModulePhyIndex OBJECT-TYPE
			SYNTAX Integer32
			MAX-ACCESS read-only
			STATUS current
			DESCRIPTION
				"entPhysicalIndex of FAN Modules. (0: Internal, -1: uninstalled)"
			::= { fkFanModuleEntry 2 }

		
--     1.3.6.1.4.1.10428 9 1.101.2.4.1.1.3
-- 1.3.6.1.4.1.10428 9 1.101.2.4.1.1.3
-- 1.3.6.1.4.1.10428 9 1.101.2.4.1.1.3
-- 1.3.6.1.4.1.10428 9 1.101.2.4.1.1.3
		-- 1.3.6.1.4.1.10428 9 1.101.2.4.1.1.3
		fkFanModuleUnitNum OBJECT-TYPE
			SYNTAX Integer32
			MAX-ACCESS read-only
			STATUS current
			DESCRIPTION
				"The number of unit in FAN module"
			::= { fkFanModuleEntry 3 }

		
--     1.3.6.1.4.1.10428 9 1.101.2.4.1.1.4
-- 1.3.6.1.4.1.10428 9 1.101.2.4.1.1.4
-- 1.3.6.1.4.1.10428 9 1.101.2.4.1.1.4
-- 1.3.6.1.4.1.10428 9 1.101.2.4.1.1.4
		-- 1.3.6.1.4.1.10428 9 1.101.2.4.1.1.4
		fkFanModuleAdminState OBJECT-TYPE
			SYNTAX INTEGER
				{
				off(0),
				on(1),
				auto(2)
				}
			MAX-ACCESS read-only
			STATUS current
			DESCRIPTION
				"An administrative state of FAN module"
			::= { fkFanModuleEntry 4 }

		
--     1.3.6.1.4.1.10428 9 1.101.2.4.1.1.5
-- 1.3.6.1.4.1.10428 9 1.101.2.4.1.1.5
-- 1.3.6.1.4.1.10428 9 1.101.2.4.1.1.5
-- 1.3.6.1.4.1.10428 9 1.101.2.4.1.1.5
		-- 1.3.6.1.4.1.10428 9 1.101.2.4.1.1.5
		fkFanModuleSpeedThreshold OBJECT-TYPE
			SYNTAX Integer32
			MAX-ACCESS read-only
			STATUS current
			DESCRIPTION
				"Fan-speed threshold"
			::= { fkFanModuleEntry 5 }

		
--     1.3.6.1.4.1.10428 9 1.101.2.4.2
-- 1.3.6.1.4.1.10428 9 1.101.2.4.2
-- 1.3.6.1.4.1.10428 9 1.101.2.4.2
-- 1.3.6.1.4.1.10428 9 1.101.2.4.2
		-- 1.3.6.1.4.1.10428 9 1.101.2.4.2
		fkFanModuleControl OBJECT IDENTIFIER ::= { fkFanModule 2 }

		
--     1.3.6.1.4.1.10428 9 1.101.2.4.2.1
-- 1.3.6.1.4.1.10428 9 1.101.2.4.2.1
-- 1.3.6.1.4.1.10428 9 1.101.2.4.2.1
-- 1.3.6.1.4.1.10428 9 1.101.2.4.2.1
		-- 1.3.6.1.4.1.10428 9 1.101.2.4.2.1
		fkFanModuleControlRequest OBJECT-TYPE
			SYNTAX INTEGER
				{
				setFanAdminState(1),
				setFanSpeedThreshold(2)
				}
			MAX-ACCESS read-write
			STATUS current
			DESCRIPTION
				"set an administrative state of FAN module"
			::= { fkFanModuleControl 1 }

		
--     1.3.6.1.4.1.10428 9 1.101.2.4.2.2
-- 1.3.6.1.4.1.10428 9 1.101.2.4.2.2
-- 1.3.6.1.4.1.10428 9 1.101.2.4.2.2
-- 1.3.6.1.4.1.10428 9 1.101.2.4.2.2
		-- 1.3.6.1.4.1.10428 9 1.101.2.4.2.2
		fkFanModuleControlStatus OBJECT-TYPE
			SYNTAX FkControlStatusType
			MAX-ACCESS read-only
			STATUS current
			DESCRIPTION
				"Description."
			::= { fkFanModuleControl 2 }

		
--     1.3.6.1.4.1.10428 9 1.101.2.4.2.3
-- 1.3.6.1.4.1.10428 9 1.101.2.4.2.3
-- 1.3.6.1.4.1.10428 9 1.101.2.4.2.3
-- 1.3.6.1.4.1.10428 9 1.101.2.4.2.3
		-- 1.3.6.1.4.1.10428 9 1.101.2.4.2.3
		fkFanModuleControlTimer OBJECT-TYPE
			SYNTAX Gauge32
			MAX-ACCESS read-write
			STATUS current
			DESCRIPTION
				"Description."
			::= { fkFanModuleControl 3 }

		
--     1.3.6.1.4.1.10428 9 1.101.2.4.2.4
-- 1.3.6.1.4.1.10428 9 1.101.2.4.2.4
-- 1.3.6.1.4.1.10428 9 1.101.2.4.2.4
-- 1.3.6.1.4.1.10428 9 1.101.2.4.2.4
		-- 1.3.6.1.4.1.10428 9 1.101.2.4.2.4
		fkFanModuleControlTimeStamp OBJECT-TYPE
			SYNTAX TimeTicks
			MAX-ACCESS read-only
			STATUS current
			DESCRIPTION
				"Description."
			::= { fkFanModuleControl 4 }

		
--     1.3.6.1.4.1.10428 9 1.101.2.4.2.5
-- 1.3.6.1.4.1.10428 9 1.101.2.4.2.5
-- 1.3.6.1.4.1.10428 9 1.101.2.4.2.5
-- 1.3.6.1.4.1.10428 9 1.101.2.4.2.5
		-- 1.3.6.1.4.1.10428 9 1.101.2.4.2.5
		fkFanModuleControlReqResult OBJECT-TYPE
			SYNTAX FkControlRequestResultType
			MAX-ACCESS read-only
			STATUS current
			DESCRIPTION
				"Description."
			::= { fkFanModuleControl 5 }

		
--     1.3.6.1.4.1.10428 9 1.101.2.4.2.6
-- 1.3.6.1.4.1.10428 9 1.101.2.4.2.6
-- 1.3.6.1.4.1.10428 9 1.101.2.4.2.6
-- 1.3.6.1.4.1.10428 9 1.101.2.4.2.6
		-- 1.3.6.1.4.1.10428 9 1.101.2.4.2.6
		fkFanModuleControlIndex OBJECT-TYPE
			SYNTAX Integer32
			MAX-ACCESS read-write
			STATUS current
			DESCRIPTION
				"Description."
			::= { fkFanModuleControl 6 }

		
--     1.3.6.1.4.1.10428 9 1.101.2.4.2.7
-- 1.3.6.1.4.1.10428 9 1.101.2.4.2.7
-- 1.3.6.1.4.1.10428 9 1.101.2.4.2.7
-- 1.3.6.1.4.1.10428 9 1.101.2.4.2.7
		-- 1.3.6.1.4.1.10428 9 1.101.2.4.2.7
		fkFanModuleControlAdminState OBJECT-TYPE
			SYNTAX INTEGER
				{
				off(0),
				on(1),
				auto(2)
				}
			MAX-ACCESS read-write
			STATUS current
			DESCRIPTION
				"An administrative state of FAN module"
			::= { fkFanModuleControl 7 }

		
--     1.3.6.1.4.1.10428 9 1.101.2.4.2.8
-- 1.3.6.1.4.1.10428 9 1.101.2.4.2.8
-- 1.3.6.1.4.1.10428 9 1.101.2.4.2.8
-- 1.3.6.1.4.1.10428 9 1.101.2.4.2.8
		-- 1.3.6.1.4.1.10428 9 1.101.2.4.2.8
		fkFanModuleControlSpeedThreshold OBJECT-TYPE
			SYNTAX Integer32
			MAX-ACCESS read-write
			STATUS current
			DESCRIPTION
				"Fan-speed threshold"
			::= { fkFanModuleControl 8 }

		
--     1.3.6.1.4.1.10428 9 1.101.2.4.3
-- 1.3.6.1.4.1.10428 9 1.101.2.4.3
-- 1.3.6.1.4.1.10428 9 1.101.2.4.3
-- 1.3.6.1.4.1.10428 9 1.101.2.4.3
		-- 1.3.6.1.4.1.10428 9 1.101.2.4.3
		fkFanModuleNotification OBJECT IDENTIFIER ::= { fkFanModule 3 }

		
--     1.3.6.1.4.1.10428 9 1.101.2.4.3.1
-- 1.3.6.1.4.1.10428 9 1.101.2.4.3.1
-- 1.3.6.1.4.1.10428 9 1.101.2.4.3.1
-- 1.3.6.1.4.1.10428 9 1.101.2.4.3.1
		-- 1.3.6.1.4.1.10428 9 1.101.2.4.3.1
		fkFanAdminStateChanged NOTIFICATION-TYPE
			OBJECTS { fkFanModuleAdminState, fkFanModuleControlRequest, fkFanModuleControlTimeStamp, fkFanModuleControlReqResult }
			STATUS current
			DESCRIPTION 
				"Description."
			::= { fkFanModuleNotification 1 }

		
--     1.3.6.1.4.1.10428 9 1.101.2.4.3.2
-- 1.3.6.1.4.1.10428 9 1.101.2.4.3.2
-- 1.3.6.1.4.1.10428 9 1.101.2.4.3.2
-- 1.3.6.1.4.1.10428 9 1.101.2.4.3.2
		-- 1.3.6.1.4.1.10428 9 1.101.2.4.3.2
		fkFanSpeedThresholdChanged NOTIFICATION-TYPE
			OBJECTS { fkFanModuleControlRequest, fkFanModuleControlTimeStamp, fkFanModuleControlReqResult, fkFanModuleControlIndex, fkFanModuleControlSpeedThreshold
				 }
			STATUS current
			DESCRIPTION 
				"Description."
			::= { fkFanModuleNotification 2 }

		
--     1.3.6.1.4.1.10428 9 1.101.2.5
-- 1.3.6.1.4.1.10428 9 1.101.2.5
-- 1.3.6.1.4.1.10428 9 1.101.2.5
-- 1.3.6.1.4.1.10428 9 1.101.2.5
		-- 1.3.6.1.4.1.10428 9 1.101.2.5
		fkFanUnit OBJECT IDENTIFIER ::= { fkDevice 5 }

		
--     1.3.6.1.4.1.10428 9 1.101.2.5.1
-- 1.3.6.1.4.1.10428 9 1.101.2.5.1
-- 1.3.6.1.4.1.10428 9 1.101.2.5.1
-- 1.3.6.1.4.1.10428 9 1.101.2.5.1
		-- 1.3.6.1.4.1.10428 9 1.101.2.5.1
		fkFanUnitTable OBJECT-TYPE
			SYNTAX SEQUENCE OF FkFanUnitEntry
			MAX-ACCESS not-accessible
			STATUS current
			DESCRIPTION
				"Description."
			::= { fkFanUnit 1 }

		
--     1.3.6.1.4.1.10428 9 1.101.2.5.1.1
-- 1.3.6.1.4.1.10428 9 1.101.2.5.1.1
-- 1.3.6.1.4.1.10428 9 1.101.2.5.1.1
-- 1.3.6.1.4.1.10428 9 1.101.2.5.1.1
		-- 1.3.6.1.4.1.10428 9 1.101.2.5.1.1
		fkFanUnitEntry OBJECT-TYPE
			SYNTAX FkFanUnitEntry
			MAX-ACCESS not-accessible
			STATUS current
			DESCRIPTION
				"Description."
			INDEX { fkFanModuleIndex, fkFanUnitIndex }
			::= { fkFanUnitTable 1 }

		
		FkFanUnitEntry ::=
			SEQUENCE { 
				fkFanUnitIndex
					INTEGER,
				fkFanUnitOperState
					INTEGER,
				fkFanUnitSpeed
					Integer32
			 }

--     1.3.6.1.4.1.10428 9 1.101.2.5.1.1.1
-- 1.3.6.1.4.1.10428 9 1.101.2.5.1.1.1
-- 1.3.6.1.4.1.10428 9 1.101.2.5.1.1.1
-- 1.3.6.1.4.1.10428 9 1.101.2.5.1.1.1
		-- 1.3.6.1.4.1.10428 9 1.101.2.5.1.1.1
		fkFanUnitIndex OBJECT-TYPE
			SYNTAX INTEGER (1..255)
			MAX-ACCESS read-only
			STATUS current
			DESCRIPTION
				"A unique number in FAN module"
			::= { fkFanUnitEntry 1 }

		
--     1.3.6.1.4.1.10428 9 1.101.2.5.1.1.2
-- 1.3.6.1.4.1.10428 9 1.101.2.5.1.1.2
-- 1.3.6.1.4.1.10428 9 1.101.2.5.1.1.2
-- 1.3.6.1.4.1.10428 9 1.101.2.5.1.1.2
		-- 1.3.6.1.4.1.10428 9 1.101.2.5.1.1.2
		fkFanUnitOperState OBJECT-TYPE
			SYNTAX INTEGER
				{
				failure(0),
				ok(1),
				stop(2)
				}
			MAX-ACCESS read-only
			STATUS current
			DESCRIPTION
				"An operational state of FAN unit"
			::= { fkFanUnitEntry 2 }

		
--     1.3.6.1.4.1.10428 9 1.101.2.5.1.1.3
-- 1.3.6.1.4.1.10428 9 1.101.2.5.1.1.3
-- 1.3.6.1.4.1.10428 9 1.101.2.5.1.1.3
-- 1.3.6.1.4.1.10428 9 1.101.2.5.1.1.3
		-- 1.3.6.1.4.1.10428 9 1.101.2.5.1.1.3
		fkFanUnitSpeed OBJECT-TYPE
			SYNTAX Integer32
			MAX-ACCESS read-only
			STATUS current
			DESCRIPTION
				"Speed of FAN unit"
			::= { fkFanUnitEntry 3 }

		
--     1.3.6.1.4.1.10428 9 1.101.2.6
-- 1.3.6.1.4.1.10428 9 1.101.2.6
-- 1.3.6.1.4.1.10428 9 1.101.2.6
-- 1.3.6.1.4.1.10428 9 1.101.2.6
		-- 1.3.6.1.4.1.10428 9 1.101.2.6
		fkTemperature OBJECT IDENTIFIER ::= { fkDevice 6 }

		
--     1.3.6.1.4.1.10428 9 1.101.2.6.1
-- 1.3.6.1.4.1.10428 9 1.101.2.6.1
-- 1.3.6.1.4.1.10428 9 1.101.2.6.1
-- 1.3.6.1.4.1.10428 9 1.101.2.6.1
		-- 1.3.6.1.4.1.10428 9 1.101.2.6.1
		fkTemperatureTable OBJECT-TYPE
			SYNTAX SEQUENCE OF FkTemperatureEntry
			MAX-ACCESS not-accessible
			STATUS current
			DESCRIPTION
				"Description."
			::= { fkTemperature 1 }

		
--     1.3.6.1.4.1.10428 9 1.101.2.6.1.1
-- 1.3.6.1.4.1.10428 9 1.101.2.6.1.1
-- 1.3.6.1.4.1.10428 9 1.101.2.6.1.1
-- 1.3.6.1.4.1.10428 9 1.101.2.6.1.1
		-- 1.3.6.1.4.1.10428 9 1.101.2.6.1.1
		fkTemperatureEntry OBJECT-TYPE
			SYNTAX FkTemperatureEntry
			MAX-ACCESS not-accessible
			STATUS current
			DESCRIPTION
				"Description."
			INDEX { fkTemperatureIndex }
			::= { fkTemperatureTable 1 }

		
		FkTemperatureEntry ::=
			SEQUENCE { 
				fkTemperatureIndex
					INTEGER,
				fkTemperatureState
					INTEGER,
				fkTemperatureValue
					Integer32,
				fkTemperatureHighThreshold
					Integer32,
				fkTemperatureLowThreshold
					Integer32,
				fkTemperatureWarnHighThreshold
					Integer32,
				fkTemperatureWarnLowThreshold
					Integer32,
				fkTemperatureWarnDuration
					Integer32,
				fkTemperatureAlarmHighThreshold
					Integer32,
				fkTemperatureAlarmLowThreshold
					Integer32,
				fkTemperatureAlarmDuration
					Integer32
			 }

--     1.3.6.1.4.1.10428 9 1.101.2.6.1.1.1
-- 1.3.6.1.4.1.10428 9 1.101.2.6.1.1.1
-- 1.3.6.1.4.1.10428 9 1.101.2.6.1.1.1
-- 1.3.6.1.4.1.10428 9 1.101.2.6.1.1.1
		-- 1.3.6.1.4.1.10428 9 1.101.2.6.1.1.1
		fkTemperatureIndex OBJECT-TYPE
			SYNTAX INTEGER (1..255)
			MAX-ACCESS read-only
			STATUS current
			DESCRIPTION
				"A unique value, greater than zero, for each module. It is recommended that values are assigned contiguously starting from 1."
			::= { fkTemperatureEntry 1 }

		
--     1.3.6.1.4.1.10428 9 1.101.2.6.1.1.2
-- 1.3.6.1.4.1.10428 9 1.101.2.6.1.1.2
-- 1.3.6.1.4.1.10428 9 1.101.2.6.1.1.2
-- 1.3.6.1.4.1.10428 9 1.101.2.6.1.1.2
		-- 1.3.6.1.4.1.10428 9 1.101.2.6.1.1.2
		fkTemperatureState OBJECT-TYPE
			SYNTAX INTEGER
				{
				failure(0),
				ok(1),
				others(2)
				}
			MAX-ACCESS read-only
			STATUS current
			DESCRIPTION
				"Temperature status information"
			::= { fkTemperatureEntry 2 }

		
--     1.3.6.1.4.1.10428 9 1.101.2.6.1.1.3
-- 1.3.6.1.4.1.10428 9 1.101.2.6.1.1.3
-- 1.3.6.1.4.1.10428 9 1.101.2.6.1.1.3
-- 1.3.6.1.4.1.10428 9 1.101.2.6.1.1.3
		-- 1.3.6.1.4.1.10428 9 1.101.2.6.1.1.3
		fkTemperatureValue OBJECT-TYPE
			SYNTAX Integer32
			MAX-ACCESS read-only
			STATUS current
			DESCRIPTION
				"The value of temperature sensor. (unit: C)"
			::= { fkTemperatureEntry 3 }

		
--     1.3.6.1.4.1.10428 9 1.101.2.6.1.1.4
-- 1.3.6.1.4.1.10428 9 1.101.2.6.1.1.4
-- 1.3.6.1.4.1.10428 9 1.101.2.6.1.1.4
-- 1.3.6.1.4.1.10428 9 1.101.2.6.1.1.4
		-- 1.3.6.1.4.1.10428 9 1.101.2.6.1.1.4
		fkTemperatureHighThreshold OBJECT-TYPE
			SYNTAX Integer32
			MAX-ACCESS read-only
			STATUS current
			DESCRIPTION
				"The High threshold of temperature."
			::= { fkTemperatureEntry 4 }

		
--     1.3.6.1.4.1.10428 9 1.101.2.6.1.1.5
-- 1.3.6.1.4.1.10428 9 1.101.2.6.1.1.5
-- 1.3.6.1.4.1.10428 9 1.101.2.6.1.1.5
-- 1.3.6.1.4.1.10428 9 1.101.2.6.1.1.5
		-- 1.3.6.1.4.1.10428 9 1.101.2.6.1.1.5
		fkTemperatureLowThreshold OBJECT-TYPE
			SYNTAX Integer32
			MAX-ACCESS read-only
			STATUS current
			DESCRIPTION
				"The Low threshold of temperature."
			::= { fkTemperatureEntry 5 }

		
--      1.3.6.1.4.1.10428 9 1.101.2.6.1.1.6
-- 1.3.6.1.4.1.10428 9 1.101.2.6.1.1.6
-- 1.3.6.1.4.1.10428 9 1.101.2.6.1.1.6
-- 1.3.6.1.4.1.10428 9 1.101.2.6.1.1.6
-- 1.3.6.1.4.1.10428 9 1.101.2.6.1.1.6
		-- 1.3.6.1.4.1.10428 9 1.101.2.6.1.1.6
		fkTemperatureWarnHighThreshold OBJECT-TYPE
			SYNTAX Integer32 (-40..100)
			MAX-ACCESS read-only
			STATUS current
			DESCRIPTION
				"The High threshold of temperature."
			::= { fkTemperatureEntry 6 }

		
--      1.3.6.1.4.1.10428 9 1.101.2.6.1.1.7
-- 1.3.6.1.4.1.10428 9 1.101.2.6.1.1.7
-- 1.3.6.1.4.1.10428 9 1.101.2.6.1.1.7
-- 1.3.6.1.4.1.10428 9 1.101.2.6.1.1.7
-- 1.3.6.1.4.1.10428 9 1.101.2.6.1.1.7
		-- 1.3.6.1.4.1.10428 9 1.101.2.6.1.1.7
		fkTemperatureWarnLowThreshold OBJECT-TYPE
			SYNTAX Integer32 (-40..100)
			MAX-ACCESS read-only
			STATUS current
			DESCRIPTION
				"The Low threshold of temperature."
			::= { fkTemperatureEntry 7 }

		
--      1.3.6.1.4.1.10428 9 1.101.2.6.1.1.8
-- 1.3.6.1.4.1.10428 9 1.101.2.6.1.1.8
-- 1.3.6.1.4.1.10428 9 1.101.2.6.1.1.8
-- 1.3.6.1.4.1.10428 9 1.101.2.6.1.1.8
-- 1.3.6.1.4.1.10428 9 1.101.2.6.1.1.8
		-- 1.3.6.1.4.1.10428 9 1.101.2.6.1.1.8
		fkTemperatureWarnDuration OBJECT-TYPE
			SYNTAX Integer32 (0..300)
			MAX-ACCESS read-only
			STATUS current
			DESCRIPTION
				"Duration-time units by the 5 sec.
				0: Clear threshold."
			::= { fkTemperatureEntry 8 }

		
--      1.3.6.1.4.1.10428 9 1.101.2.6.1.1.9
-- 1.3.6.1.4.1.10428 9 1.101.2.6.1.1.9
-- 1.3.6.1.4.1.10428 9 1.101.2.6.1.1.9
-- 1.3.6.1.4.1.10428 9 1.101.2.6.1.1.9
-- 1.3.6.1.4.1.10428 9 1.101.2.6.1.1.9
		-- 1.3.6.1.4.1.10428 9 1.101.2.6.1.1.9
		fkTemperatureAlarmHighThreshold OBJECT-TYPE
			SYNTAX Integer32 (-40..100)
			MAX-ACCESS read-only
			STATUS current
			DESCRIPTION
				"The High threshold of temperature."
			::= { fkTemperatureEntry 9 }

		
--      1.3.6.1.4.1.10428 9 1.101.2.6.1.1.10
-- 1.3.6.1.4.1.10428 9 1.101.2.6.1.1.10
-- 1.3.6.1.4.1.10428 9 1.101.2.6.1.1.10
-- 1.3.6.1.4.1.10428 9 1.101.2.6.1.1.10
-- 1.3.6.1.4.1.10428 9 1.101.2.6.1.1.10
		-- 1.3.6.1.4.1.10428 9 1.101.2.6.1.1.10
		fkTemperatureAlarmLowThreshold OBJECT-TYPE
			SYNTAX Integer32 (-40..100)
			MAX-ACCESS read-only
			STATUS current
			DESCRIPTION
				"The Low threshold of temperature."
			::= { fkTemperatureEntry 10 }

		
--      1.3.6.1.4.1.10428 9 1.101.2.6.1.1.11
-- 1.3.6.1.4.1.10428 9 1.101.2.6.1.1.11
-- 1.3.6.1.4.1.10428 9 1.101.2.6.1.1.11
-- 1.3.6.1.4.1.10428 9 1.101.2.6.1.1.11
-- 1.3.6.1.4.1.10428 9 1.101.2.6.1.1.11
		-- 1.3.6.1.4.1.10428 9 1.101.2.6.1.1.11
		fkTemperatureAlarmDuration OBJECT-TYPE
			SYNTAX Integer32 (0..300)
			MAX-ACCESS read-only
			STATUS current
			DESCRIPTION
				"Duration-time units by the 5 sec.
				0: Clear threshold."
			::= { fkTemperatureEntry 11 }

		
--     1.3.6.1.4.1.10428 9 1.101.2.6.2
-- 1.3.6.1.4.1.10428 9 1.101.2.6.2
-- 1.3.6.1.4.1.10428 9 1.101.2.6.2
-- 1.3.6.1.4.1.10428 9 1.101.2.6.2
		-- 1.3.6.1.4.1.10428 9 1.101.2.6.2
		fkTemperatureControl OBJECT IDENTIFIER ::= { fkTemperature 2 }

		
--     1.3.6.1.4.1.10428 9 1.101.2.6.2.1
-- 1.3.6.1.4.1.10428 9 1.101.2.6.2.1
-- 1.3.6.1.4.1.10428 9 1.101.2.6.2.1
-- 1.3.6.1.4.1.10428 9 1.101.2.6.2.1
		-- 1.3.6.1.4.1.10428 9 1.101.2.6.2.1
		fkTemperatureControlRequest OBJECT-TYPE
			SYNTAX INTEGER
				{
				setTempThreshold(1),
				setTempAlarmThreshold(2),
				setTempWarnThreshold(3)
				}
			MAX-ACCESS read-write
			STATUS current
			DESCRIPTION
				"set an administrative state of FAN module"
			::= { fkTemperatureControl 1 }

		
--     1.3.6.1.4.1.10428 9 1.101.2.6.2.2
-- 1.3.6.1.4.1.10428 9 1.101.2.6.2.2
-- 1.3.6.1.4.1.10428 9 1.101.2.6.2.2
-- 1.3.6.1.4.1.10428 9 1.101.2.6.2.2
		-- 1.3.6.1.4.1.10428 9 1.101.2.6.2.2
		fkTemperatureControlStatus OBJECT-TYPE
			SYNTAX FkControlStatusType
			MAX-ACCESS read-only
			STATUS current
			DESCRIPTION
				"Description."
			::= { fkTemperatureControl 2 }

		
--     1.3.6.1.4.1.10428 9 1.101.2.6.2.3
-- 1.3.6.1.4.1.10428 9 1.101.2.6.2.3
-- 1.3.6.1.4.1.10428 9 1.101.2.6.2.3
-- 1.3.6.1.4.1.10428 9 1.101.2.6.2.3
		-- 1.3.6.1.4.1.10428 9 1.101.2.6.2.3
		fkTemperatureControlTimer OBJECT-TYPE
			SYNTAX Gauge32
			MAX-ACCESS read-write
			STATUS current
			DESCRIPTION
				"Description."
			::= { fkTemperatureControl 3 }

		
--     1.3.6.1.4.1.10428 9 1.101.2.6.2.4
-- 1.3.6.1.4.1.10428 9 1.101.2.6.2.4
-- 1.3.6.1.4.1.10428 9 1.101.2.6.2.4
-- 1.3.6.1.4.1.10428 9 1.101.2.6.2.4
		-- 1.3.6.1.4.1.10428 9 1.101.2.6.2.4
		fkTemperatureControlTimeStamp OBJECT-TYPE
			SYNTAX TimeTicks
			MAX-ACCESS read-only
			STATUS current
			DESCRIPTION
				"Description."
			::= { fkTemperatureControl 4 }

		
--     1.3.6.1.4.1.10428 9 1.101.2.6.2.5
-- 1.3.6.1.4.1.10428 9 1.101.2.6.2.5
-- 1.3.6.1.4.1.10428 9 1.101.2.6.2.5
-- 1.3.6.1.4.1.10428 9 1.101.2.6.2.5
		-- 1.3.6.1.4.1.10428 9 1.101.2.6.2.5
		fkTemperatureControlReqResult OBJECT-TYPE
			SYNTAX FkControlRequestResultType
			MAX-ACCESS read-only
			STATUS current
			DESCRIPTION
				"Description."
			::= { fkTemperatureControl 5 }

		
--     1.3.6.1.4.1.10428 9 1.101.2.6.2.6
-- 1.3.6.1.4.1.10428 9 1.101.2.6.2.6
-- 1.3.6.1.4.1.10428 9 1.101.2.6.2.6
-- 1.3.6.1.4.1.10428 9 1.101.2.6.2.6
		-- 1.3.6.1.4.1.10428 9 1.101.2.6.2.6
		fkTemperatureControlIndex OBJECT-TYPE
			SYNTAX Integer32
			MAX-ACCESS read-write
			STATUS current
			DESCRIPTION
				"The Temperature index"
			::= { fkTemperatureControl 6 }

		
--     1.3.6.1.4.1.10428 9 1.101.2.6.2.7
-- 1.3.6.1.4.1.10428 9 1.101.2.6.2.7
-- 1.3.6.1.4.1.10428 9 1.101.2.6.2.7
-- 1.3.6.1.4.1.10428 9 1.101.2.6.2.7
		-- 1.3.6.1.4.1.10428 9 1.101.2.6.2.7
		fkTemperatureControlHighThreshold OBJECT-TYPE
			SYNTAX Integer32
			MAX-ACCESS read-write
			STATUS current
			DESCRIPTION
				"The High threshold of temperature."
			::= { fkTemperatureControl 7 }

		
--     1.3.6.1.4.1.10428 9 1.101.2.6.2.8
-- 1.3.6.1.4.1.10428 9 1.101.2.6.2.8
-- 1.3.6.1.4.1.10428 9 1.101.2.6.2.8
-- 1.3.6.1.4.1.10428 9 1.101.2.6.2.8
		-- 1.3.6.1.4.1.10428 9 1.101.2.6.2.8
		fkTemperatureControlLowThreshold OBJECT-TYPE
			SYNTAX Integer32
			MAX-ACCESS read-write
			STATUS current
			DESCRIPTION
				"The Low threshold of temperature."
			::= { fkTemperatureControl 8 }

		
--      1.3.6.1.4.1.10428 9 1.101.2.6.2.9
-- 1.3.6.1.4.1.10428 9 1.101.2.6.2.9
-- 1.3.6.1.4.1.10428 9 1.101.2.6.2.9
-- 1.3.6.1.4.1.10428 9 1.101.2.6.2.9
-- 1.3.6.1.4.1.10428 9 1.101.2.6.2.9
		-- 1.3.6.1.4.1.10428 9 1.101.2.6.2.9
		fkTemperatureControlDuration OBJECT-TYPE
			SYNTAX Integer32 (0..300)
			MAX-ACCESS read-write
			STATUS current
			DESCRIPTION
				"Duration-time units by the 5 sec.
				0: Clear threshold."
			::= { fkTemperatureControl 9 }

		
--     1.3.6.1.4.1.10428 9 1.101.2.6.3
-- 1.3.6.1.4.1.10428 9 1.101.2.6.3
-- 1.3.6.1.4.1.10428 9 1.101.2.6.3
-- 1.3.6.1.4.1.10428 9 1.101.2.6.3
		-- 1.3.6.1.4.1.10428 9 1.101.2.6.3
		fkTemperatureNotification OBJECT IDENTIFIER ::= { fkTemperature 3 }

		
--       1.3.6.1.4.1.10428 9 1.101.2.6.3.1
-- 1.3.6.1.4.1.10428 9 1.101.2.6.3.1
-- 1.3.6.1.4.1.10428 9 1.101.2.6.3.1
-- 1.3.6.1.4.1.10428 9 1.101.2.6.3.1
-- 1.3.6.1.4.1.10428 9 1.101.2.6.3.1
-- 1.3.6.1.4.1.10428 9 1.101.2.6.3.1
		-- 1.3.6.1.4.1.10428 9 1.101.2.6.3.1
		fkTemperatureThresholdChanged NOTIFICATION-TYPE
			OBJECTS { fkTemperatureControlRequest, fkTemperatureControlTimeStamp, fkTemperatureControlReqResult, fkTemperatureIndex, fkTemperatureWarnHighThreshold, 
				fkTemperatureWarnLowThreshold, fkTemperatureWarnDuration, fkTemperatureAlarmHighThreshold, fkTemperatureAlarmLowThreshold, fkTemperatureLowThreshold, 
				fkTemperatureAlarmDuration, fkTemperatureHighThreshold }
			STATUS current
			DESCRIPTION 
				"Description."
			::= { fkTemperatureNotification 1 }

		
--     1.3.6.1.4.1.10428 9 1.101.2.7
-- 1.3.6.1.4.1.10428 9 1.101.2.7
-- 1.3.6.1.4.1.10428 9 1.101.2.7
-- 1.3.6.1.4.1.10428 9 1.101.2.7
		-- 1.3.6.1.4.1.10428 9 1.101.2.7
		fkBattery OBJECT IDENTIFIER ::= { fkDevice 7 }

		
--     1.3.6.1.4.1.10428 9 1.101.2.7.1
-- 1.3.6.1.4.1.10428 9 1.101.2.7.1
-- 1.3.6.1.4.1.10428 9 1.101.2.7.1
-- 1.3.6.1.4.1.10428 9 1.101.2.7.1
		-- 1.3.6.1.4.1.10428 9 1.101.2.7.1
		fkBatteryTable OBJECT-TYPE
			SYNTAX SEQUENCE OF FkBatteryEntry
			MAX-ACCESS not-accessible
			STATUS current
			DESCRIPTION
				"Description."
			::= { fkBattery 1 }

		
--     1.3.6.1.4.1.10428 9 1.101.2.7.1.1
-- 1.3.6.1.4.1.10428 9 1.101.2.7.1.1
-- 1.3.6.1.4.1.10428 9 1.101.2.7.1.1
-- 1.3.6.1.4.1.10428 9 1.101.2.7.1.1
		-- 1.3.6.1.4.1.10428 9 1.101.2.7.1.1
		fkBatteryEntry OBJECT-TYPE
			SYNTAX FkBatteryEntry
			MAX-ACCESS not-accessible
			STATUS current
			DESCRIPTION
				"Description."
			INDEX { fkBatteryIndex }
			::= { fkBatteryTable 1 }

		
		FkBatteryEntry ::=
			SEQUENCE { 
				fkBatteryIndex
					INTEGER,
				fkOperationPowerType
					INTEGER,
				fkOperationPowerInfo
					OCTET STRING,
				fkPSUACPowerState
					INTEGER,
				fkPSUTemperture
					Integer32,
				fkPSUTempThreshold
					Integer32,
				fkPSUOutVoltage
					OCTET STRING,
				fkPSUOverTemp
					INTEGER,
				fkPSUFirmwareVer
					Integer32,
				fkRBUEquipState
					INTEGER,
				fkRBUModeStaus
					OCTET STRING,
				fkRBUTemperature1
					Integer32,
				fkRBUTemperature2
					Integer32,
				fkRBUTempLowThreshold
					Integer32,
				fkRBUOutVoltage
					OCTET STRING,
				fkRBUChargeCurrent
					Integer32,
				fkRBURemainCapacity
					Integer32,
				fkRBUOverTemp
					INTEGER,
				fkBatteryLow
					INTEGER,
				fkRBUTempHighThreshold
					Integer32,
				fkRBUBTStatus
					INTEGER,
				fkRBUBTThreshold
					Integer32,
				fkRBURechargeVoltage
					Integer32,
				fkBatteryCellStatus
					INTEGER,
				fkBPSUACHardwareVer
					Integer32
			 }

--     1.3.6.1.4.1.10428 9 1.101.2.7.1.1.1
-- 1.3.6.1.4.1.10428 9 1.101.2.7.1.1.1
-- 1.3.6.1.4.1.10428 9 1.101.2.7.1.1.1
-- 1.3.6.1.4.1.10428 9 1.101.2.7.1.1.1
		-- 1.3.6.1.4.1.10428 9 1.101.2.7.1.1.1
		fkBatteryIndex OBJECT-TYPE
			SYNTAX INTEGER (1..256)
			MAX-ACCESS read-only
			STATUS current
			DESCRIPTION
				"The index of battery charger."
			::= { fkBatteryEntry 1 }

		
--     1.3.6.1.4.1.10428 9 1.101.2.7.1.1.2
-- 1.3.6.1.4.1.10428 9 1.101.2.7.1.1.2
-- 1.3.6.1.4.1.10428 9 1.101.2.7.1.1.2
-- 1.3.6.1.4.1.10428 9 1.101.2.7.1.1.2
		-- 1.3.6.1.4.1.10428 9 1.101.2.7.1.1.2
		fkOperationPowerType OBJECT-TYPE
			SYNTAX INTEGER
				{
				ac(0),
				rbu(1)
				}
			MAX-ACCESS read-only
			STATUS current
			DESCRIPTION
				"Power Type."
			::= { fkBatteryEntry 2 }

		
--     1.3.6.1.4.1.10428 9 1.101.2.7.1.1.3
-- 1.3.6.1.4.1.10428 9 1.101.2.7.1.1.3
-- 1.3.6.1.4.1.10428 9 1.101.2.7.1.1.3
-- 1.3.6.1.4.1.10428 9 1.101.2.7.1.1.3
		-- 1.3.6.1.4.1.10428 9 1.101.2.7.1.1.3
		fkOperationPowerInfo OBJECT-TYPE
			SYNTAX OCTET STRING
			MAX-ACCESS read-only
			STATUS current
			DESCRIPTION
				"Operation Power Info."
			::= { fkBatteryEntry 3 }

		
--     1.3.6.1.4.1.10428 9 1.101.2.7.1.1.4
-- 1.3.6.1.4.1.10428 9 1.101.2.7.1.1.4
-- 1.3.6.1.4.1.10428 9 1.101.2.7.1.1.4
-- 1.3.6.1.4.1.10428 9 1.101.2.7.1.1.4
		-- 1.3.6.1.4.1.10428 9 1.101.2.7.1.1.4
		fkPSUACPowerState OBJECT-TYPE
			SYNTAX INTEGER
				{
				ok(0),
				fault(1)
				}
			MAX-ACCESS read-only
			STATUS current
			DESCRIPTION
				"Power State."
			::= { fkBatteryEntry 4 }

		
--     1.3.6.1.4.1.10428 9 1.101.2.7.1.1.5
-- 1.3.6.1.4.1.10428 9 1.101.2.7.1.1.5
-- 1.3.6.1.4.1.10428 9 1.101.2.7.1.1.5
-- 1.3.6.1.4.1.10428 9 1.101.2.7.1.1.5
		-- 1.3.6.1.4.1.10428 9 1.101.2.7.1.1.5
		fkPSUTemperture OBJECT-TYPE
			SYNTAX Integer32
			MAX-ACCESS read-only
			STATUS current
			DESCRIPTION
				"Temperture."
			::= { fkBatteryEntry 5 }

		
--     1.3.6.1.4.1.10428 9 1.101.2.7.1.1.6
-- 1.3.6.1.4.1.10428 9 1.101.2.7.1.1.6
-- 1.3.6.1.4.1.10428 9 1.101.2.7.1.1.6
-- 1.3.6.1.4.1.10428 9 1.101.2.7.1.1.6
		-- 1.3.6.1.4.1.10428 9 1.101.2.7.1.1.6
		fkPSUTempThreshold OBJECT-TYPE
			SYNTAX Integer32
			MAX-ACCESS read-only
			STATUS current
			DESCRIPTION
				"Temperture Threshold."
			::= { fkBatteryEntry 6 }

		
--     1.3.6.1.4.1.10428 9 1.101.2.7.1.1.7
-- 1.3.6.1.4.1.10428 9 1.101.2.7.1.1.7
-- 1.3.6.1.4.1.10428 9 1.101.2.7.1.1.7
-- 1.3.6.1.4.1.10428 9 1.101.2.7.1.1.7
		-- 1.3.6.1.4.1.10428 9 1.101.2.7.1.1.7
		fkPSUOutVoltage OBJECT-TYPE
			SYNTAX OCTET STRING
			MAX-ACCESS read-only
			STATUS current
			DESCRIPTION
				"Voltage."
			::= { fkBatteryEntry 7 }

		
--     1.3.6.1.4.1.10428 9 1.101.2.7.1.1.8
-- 1.3.6.1.4.1.10428 9 1.101.2.7.1.1.8
-- 1.3.6.1.4.1.10428 9 1.101.2.7.1.1.8
-- 1.3.6.1.4.1.10428 9 1.101.2.7.1.1.8
		-- 1.3.6.1.4.1.10428 9 1.101.2.7.1.1.8
		fkPSUOverTemp OBJECT-TYPE
			SYNTAX INTEGER
				{
				normal(0),
				over(1)
				}
			MAX-ACCESS read-only
			STATUS current
			DESCRIPTION
				"Description."
			::= { fkBatteryEntry 8 }

		
--     1.3.6.1.4.1.10428 9 1.101.2.7.1.1.9
-- 1.3.6.1.4.1.10428 9 1.101.2.7.1.1.9
-- 1.3.6.1.4.1.10428 9 1.101.2.7.1.1.9
-- 1.3.6.1.4.1.10428 9 1.101.2.7.1.1.9
		-- 1.3.6.1.4.1.10428 9 1.101.2.7.1.1.9
		fkPSUFirmwareVer OBJECT-TYPE
			SYNTAX Integer32
			MAX-ACCESS read-only
			STATUS current
			DESCRIPTION
				"The firmware version of battery charger for communication to system."
			::= { fkBatteryEntry 9 }

		
--     1.3.6.1.4.1.10428 9 1.101.2.7.1.1.10
-- 1.3.6.1.4.1.10428 9 1.101.2.7.1.1.10
-- 1.3.6.1.4.1.10428 9 1.101.2.7.1.1.10
-- 1.3.6.1.4.1.10428 9 1.101.2.7.1.1.10
		-- 1.3.6.1.4.1.10428 9 1.101.2.7.1.1.10
		fkRBUEquipState OBJECT-TYPE
			SYNTAX INTEGER
				{
				equipped(0),
				empty(1)
				}
			MAX-ACCESS read-only
			STATUS current
			DESCRIPTION
				"Equipment State."
			::= { fkBatteryEntry 10 }

		
--     1.3.6.1.4.1.10428 9 1.101.2.7.1.1.11
-- 1.3.6.1.4.1.10428 9 1.101.2.7.1.1.11
-- 1.3.6.1.4.1.10428 9 1.101.2.7.1.1.11
-- 1.3.6.1.4.1.10428 9 1.101.2.7.1.1.11
		-- 1.3.6.1.4.1.10428 9 1.101.2.7.1.1.11
		fkRBUModeStaus OBJECT-TYPE
			SYNTAX OCTET STRING
			MAX-ACCESS read-only
			STATUS current
			DESCRIPTION
				"Description."
			::= { fkBatteryEntry 11 }

		
--     1.3.6.1.4.1.10428 9 1.101.2.7.1.1.12
-- 1.3.6.1.4.1.10428 9 1.101.2.7.1.1.12
-- 1.3.6.1.4.1.10428 9 1.101.2.7.1.1.12
-- 1.3.6.1.4.1.10428 9 1.101.2.7.1.1.12
		-- 1.3.6.1.4.1.10428 9 1.101.2.7.1.1.12
		fkRBUTemperature1 OBJECT-TYPE
			SYNTAX Integer32
			MAX-ACCESS read-only
			STATUS current
			DESCRIPTION
				"Description."
			::= { fkBatteryEntry 12 }

		
--     1.3.6.1.4.1.10428 9 1.101.2.7.1.1.13
-- 1.3.6.1.4.1.10428 9 1.101.2.7.1.1.13
-- 1.3.6.1.4.1.10428 9 1.101.2.7.1.1.13
-- 1.3.6.1.4.1.10428 9 1.101.2.7.1.1.13
		-- 1.3.6.1.4.1.10428 9 1.101.2.7.1.1.13
		fkRBUTemperature2 OBJECT-TYPE
			SYNTAX Integer32
			MAX-ACCESS read-only
			STATUS current
			DESCRIPTION
				"."
			::= { fkBatteryEntry 13 }

		
--     1.3.6.1.4.1.10428 9 1.101.2.7.1.1.14
-- 1.3.6.1.4.1.10428 9 1.101.2.7.1.1.14
-- 1.3.6.1.4.1.10428 9 1.101.2.7.1.1.14
-- 1.3.6.1.4.1.10428 9 1.101.2.7.1.1.14
		-- 1.3.6.1.4.1.10428 9 1.101.2.7.1.1.14
		fkRBUTempLowThreshold OBJECT-TYPE
			SYNTAX Integer32
			MAX-ACCESS read-only
			STATUS current
			DESCRIPTION
				"RBU Low Temperature Threshold."
			::= { fkBatteryEntry 14 }

		
--     1.3.6.1.4.1.10428 9 1.101.2.7.1.1.15
-- 1.3.6.1.4.1.10428 9 1.101.2.7.1.1.15
-- 1.3.6.1.4.1.10428 9 1.101.2.7.1.1.15
-- 1.3.6.1.4.1.10428 9 1.101.2.7.1.1.15
		-- 1.3.6.1.4.1.10428 9 1.101.2.7.1.1.15
		fkRBUOutVoltage OBJECT-TYPE
			SYNTAX OCTET STRING
			MAX-ACCESS read-only
			STATUS current
			DESCRIPTION
				"RBU Out Voltage."
			::= { fkBatteryEntry 15 }

		
--     1.3.6.1.4.1.10428 9 1.101.2.7.1.1.16
-- 1.3.6.1.4.1.10428 9 1.101.2.7.1.1.16
-- 1.3.6.1.4.1.10428 9 1.101.2.7.1.1.16
-- 1.3.6.1.4.1.10428 9 1.101.2.7.1.1.16
		-- 1.3.6.1.4.1.10428 9 1.101.2.7.1.1.16
		fkRBUChargeCurrent OBJECT-TYPE
			SYNTAX Integer32
			MAX-ACCESS read-only
			STATUS current
			DESCRIPTION
				"Current Charge."
			::= { fkBatteryEntry 16 }

		
--     1.3.6.1.4.1.10428 9 1.101.2.7.1.1.17
-- 1.3.6.1.4.1.10428 9 1.101.2.7.1.1.17
-- 1.3.6.1.4.1.10428 9 1.101.2.7.1.1.17
-- 1.3.6.1.4.1.10428 9 1.101.2.7.1.1.17
		-- 1.3.6.1.4.1.10428 9 1.101.2.7.1.1.17
		fkRBURemainCapacity OBJECT-TYPE
			SYNTAX Integer32
			MAX-ACCESS read-only
			STATUS current
			DESCRIPTION
				"Remain Capacity."
			::= { fkBatteryEntry 17 }

		
--     1.3.6.1.4.1.10428 9 1.101.2.7.1.1.18
-- 1.3.6.1.4.1.10428 9 1.101.2.7.1.1.18
-- 1.3.6.1.4.1.10428 9 1.101.2.7.1.1.18
-- 1.3.6.1.4.1.10428 9 1.101.2.7.1.1.18
		-- 1.3.6.1.4.1.10428 9 1.101.2.7.1.1.18
		fkRBUOverTemp OBJECT-TYPE
			SYNTAX INTEGER
				{
				normal(0),
				over(1),
				under(2)
				}
			MAX-ACCESS read-only
			STATUS current
			DESCRIPTION
				"The  state of Temperature over."
			::= { fkBatteryEntry 18 }

		
--     1.3.6.1.4.1.10428 9 1.101.2.7.1.1.19
-- 1.3.6.1.4.1.10428 9 1.101.2.7.1.1.19
-- 1.3.6.1.4.1.10428 9 1.101.2.7.1.1.19
-- 1.3.6.1.4.1.10428 9 1.101.2.7.1.1.19
		-- 1.3.6.1.4.1.10428 9 1.101.2.7.1.1.19
		fkBatteryLow OBJECT-TYPE
			SYNTAX INTEGER
				{
				normal(0),
				low(1),
				notAvailable(2)
				}
			MAX-ACCESS read-only
			STATUS current
			DESCRIPTION
				"Battery state."
			::= { fkBatteryEntry 19 }

		
--     1.3.6.1.4.1.10428 9 1.101.2.7.1.1.20
-- 1.3.6.1.4.1.10428 9 1.101.2.7.1.1.20
-- 1.3.6.1.4.1.10428 9 1.101.2.7.1.1.20
-- 1.3.6.1.4.1.10428 9 1.101.2.7.1.1.20
		-- 1.3.6.1.4.1.10428 9 1.101.2.7.1.1.20
		fkRBUTempHighThreshold OBJECT-TYPE
			SYNTAX Integer32
			MAX-ACCESS read-only
			STATUS current
			DESCRIPTION
				"RBU High Temperature Threshold."
			::= { fkBatteryEntry 20 }

		
--     1.3.6.1.4.1.10428 9 1.101.2.7.1.1.21
-- 1.3.6.1.4.1.10428 9 1.101.2.7.1.1.21
-- 1.3.6.1.4.1.10428 9 1.101.2.7.1.1.21
-- 1.3.6.1.4.1.10428 9 1.101.2.7.1.1.21
		-- 1.3.6.1.4.1.10428 9 1.101.2.7.1.1.21
		fkRBUBTStatus OBJECT-TYPE
			SYNTAX INTEGER
				{
				enable(1),
				disable(2)
				}
			MAX-ACCESS read-only
			STATUS current
			DESCRIPTION
				"Description."
			::= { fkBatteryEntry 21 }

		
--     1.3.6.1.4.1.10428 9 1.101.2.7.1.1.22
-- 1.3.6.1.4.1.10428 9 1.101.2.7.1.1.22
-- 1.3.6.1.4.1.10428 9 1.101.2.7.1.1.22
-- 1.3.6.1.4.1.10428 9 1.101.2.7.1.1.22
		-- 1.3.6.1.4.1.10428 9 1.101.2.7.1.1.22
		fkRBUBTThreshold OBJECT-TYPE
			SYNTAX Integer32
			MAX-ACCESS read-only
			STATUS current
			DESCRIPTION
				"Description."
			::= { fkBatteryEntry 22 }

		
--     1.3.6.1.4.1.10428 9 1.101.2.7.1.1.23
-- 1.3.6.1.4.1.10428 9 1.101.2.7.1.1.23
-- 1.3.6.1.4.1.10428 9 1.101.2.7.1.1.23
-- 1.3.6.1.4.1.10428 9 1.101.2.7.1.1.23
		-- 1.3.6.1.4.1.10428 9 1.101.2.7.1.1.23
		fkRBURechargeVoltage OBJECT-TYPE
			SYNTAX Integer32
			MAX-ACCESS read-only
			STATUS current
			DESCRIPTION
				"Description."
			::= { fkBatteryEntry 23 }

		
--     1.3.6.1.4.1.10428 9 1.101.2.7.1.1.24
-- 1.3.6.1.4.1.10428 9 1.101.2.7.1.1.24
-- 1.3.6.1.4.1.10428 9 1.101.2.7.1.1.24
-- 1.3.6.1.4.1.10428 9 1.101.2.7.1.1.24
		-- 1.3.6.1.4.1.10428 9 1.101.2.7.1.1.24
		fkBatteryCellStatus OBJECT-TYPE
			SYNTAX INTEGER
				{
				ok(1),
				failure(2)
				}
			MAX-ACCESS read-only
			STATUS current
			DESCRIPTION
				"Description."
			::= { fkBatteryEntry 24 }

		
--     1.3.6.1.4.1.10428 9 1.101.2.7.1.1.25
-- 1.3.6.1.4.1.10428 9 1.101.2.7.1.1.25
-- 1.3.6.1.4.1.10428 9 1.101.2.7.1.1.25
-- 1.3.6.1.4.1.10428 9 1.101.2.7.1.1.25
		-- 1.3.6.1.4.1.10428 9 1.101.2.7.1.1.25
		fkBPSUACHardwareVer OBJECT-TYPE
			SYNTAX Integer32
			MAX-ACCESS read-only
			STATUS current
			DESCRIPTION
				"Description."
			::= { fkBatteryEntry 25 }

		
--     1.3.6.1.4.1.10428 9 1.101.2.7.2
-- 1.3.6.1.4.1.10428 9 1.101.2.7.2
-- 1.3.6.1.4.1.10428 9 1.101.2.7.2
-- 1.3.6.1.4.1.10428 9 1.101.2.7.2
		-- 1.3.6.1.4.1.10428 9 1.101.2.7.2
		fkBatteryControl OBJECT IDENTIFIER ::= { fkBattery 2 }

		
--     1.3.6.1.4.1.10428 9 1.101.2.7.2.1
-- 1.3.6.1.4.1.10428 9 1.101.2.7.2.1
-- 1.3.6.1.4.1.10428 9 1.101.2.7.2.1
-- 1.3.6.1.4.1.10428 9 1.101.2.7.2.1
		-- 1.3.6.1.4.1.10428 9 1.101.2.7.2.1
		fkBatteryControlRequest OBJECT-TYPE
			SYNTAX INTEGER
				{
				setBatteryForceCharge(1),
				setBatteryChargingStart(2),
				setBatteryForceChargeNonStop(3),
				setBatteryBootingTimeStatus(4),
				setBatteryBootingTime(5),
				setBatteryRechargeVoltage(6),
				setPsuAcTemperature(7),
				setBatteryTemperature(8)
				}
			MAX-ACCESS read-write
			STATUS current
			DESCRIPTION
				"Description."
			::= { fkBatteryControl 1 }

		
--     1.3.6.1.4.1.10428 9 1.101.2.7.2.2
-- 1.3.6.1.4.1.10428 9 1.101.2.7.2.2
-- 1.3.6.1.4.1.10428 9 1.101.2.7.2.2
-- 1.3.6.1.4.1.10428 9 1.101.2.7.2.2
		-- 1.3.6.1.4.1.10428 9 1.101.2.7.2.2
		fkBatteryControlStatus OBJECT-TYPE
			SYNTAX Integer32
			MAX-ACCESS read-write
			STATUS current
			DESCRIPTION
				"Description."
			::= { fkBatteryControl 2 }

		
--     1.3.6.1.4.1.10428 9 1.101.2.7.2.3
-- 1.3.6.1.4.1.10428 9 1.101.2.7.2.3
-- 1.3.6.1.4.1.10428 9 1.101.2.7.2.3
-- 1.3.6.1.4.1.10428 9 1.101.2.7.2.3
		-- 1.3.6.1.4.1.10428 9 1.101.2.7.2.3
		fkBatteryControlTimer OBJECT-TYPE
			SYNTAX Integer32
			MAX-ACCESS read-write
			STATUS current
			DESCRIPTION
				"Description."
			::= { fkBatteryControl 3 }

		
--     1.3.6.1.4.1.10428 9 1.101.2.7.2.4
-- 1.3.6.1.4.1.10428 9 1.101.2.7.2.4
-- 1.3.6.1.4.1.10428 9 1.101.2.7.2.4
-- 1.3.6.1.4.1.10428 9 1.101.2.7.2.4
		-- 1.3.6.1.4.1.10428 9 1.101.2.7.2.4
		fkBatteryControlTimeStamp OBJECT-TYPE
			SYNTAX Integer32
			MAX-ACCESS read-write
			STATUS current
			DESCRIPTION
				"Description."
			::= { fkBatteryControl 4 }

		
--     1.3.6.1.4.1.10428 9 1.101.2.7.2.5
-- 1.3.6.1.4.1.10428 9 1.101.2.7.2.5
-- 1.3.6.1.4.1.10428 9 1.101.2.7.2.5
-- 1.3.6.1.4.1.10428 9 1.101.2.7.2.5
		-- 1.3.6.1.4.1.10428 9 1.101.2.7.2.5
		fkBatteryControlReqResult OBJECT-TYPE
			SYNTAX Integer32
			MAX-ACCESS read-write
			STATUS current
			DESCRIPTION
				"Description."
			::= { fkBatteryControl 5 }

		
--     1.3.6.1.4.1.10428 9 1.101.2.7.2.6
-- 1.3.6.1.4.1.10428 9 1.101.2.7.2.6
-- 1.3.6.1.4.1.10428 9 1.101.2.7.2.6
-- 1.3.6.1.4.1.10428 9 1.101.2.7.2.6
		-- 1.3.6.1.4.1.10428 9 1.101.2.7.2.6
		fkBatteryControlRBUBTStatus OBJECT-TYPE
			SYNTAX INTEGER
				{
				enable(1),
				disable(2)
				}
			MAX-ACCESS read-write
			STATUS current
			DESCRIPTION
				"Description."
			::= { fkBatteryControl 6 }

		
--     1.3.6.1.4.1.10428 9 1.101.2.7.2.7
-- 1.3.6.1.4.1.10428 9 1.101.2.7.2.7
-- 1.3.6.1.4.1.10428 9 1.101.2.7.2.7
-- 1.3.6.1.4.1.10428 9 1.101.2.7.2.7
		-- 1.3.6.1.4.1.10428 9 1.101.2.7.2.7
		fkBatteryControlRBUBTThreshold OBJECT-TYPE
			SYNTAX Integer32
			MAX-ACCESS read-write
			STATUS current
			DESCRIPTION
				"Description."
			::= { fkBatteryControl 7 }

		
--     1.3.6.1.4.1.10428 9 1.101.2.7.2.8
-- 1.3.6.1.4.1.10428 9 1.101.2.7.2.8
-- 1.3.6.1.4.1.10428 9 1.101.2.7.2.8
-- 1.3.6.1.4.1.10428 9 1.101.2.7.2.8
		-- 1.3.6.1.4.1.10428 9 1.101.2.7.2.8
		fkBatteryControlRBURechargeVoltage OBJECT-TYPE
			SYNTAX Integer32
			MAX-ACCESS read-write
			STATUS current
			DESCRIPTION
				"Description."
			::= { fkBatteryControl 8 }

		
--     1.3.6.1.4.1.10428 9 1.101.2.7.2.9
-- 1.3.6.1.4.1.10428 9 1.101.2.7.2.9
-- 1.3.6.1.4.1.10428 9 1.101.2.7.2.9
-- 1.3.6.1.4.1.10428 9 1.101.2.7.2.9
		-- 1.3.6.1.4.1.10428 9 1.101.2.7.2.9
		fkBatteryControlTemperThresh1 OBJECT-TYPE
			SYNTAX Integer32
			MAX-ACCESS read-write
			STATUS current
			DESCRIPTION
				"Description."
			::= { fkBatteryControl 9 }

		
--     1.3.6.1.4.1.10428 9 1.101.2.7.2.10
-- 1.3.6.1.4.1.10428 9 1.101.2.7.2.10
-- 1.3.6.1.4.1.10428 9 1.101.2.7.2.10
-- 1.3.6.1.4.1.10428 9 1.101.2.7.2.10
		-- 1.3.6.1.4.1.10428 9 1.101.2.7.2.10
		fkBatteryControlTemperThresh2 OBJECT-TYPE
			SYNTAX Integer32
			MAX-ACCESS read-write
			STATUS current
			DESCRIPTION
				"Description."
			::= { fkBatteryControl 10 }

		
--     1.3.6.1.4.1.10428 9 1.101.2.7.3
-- 1.3.6.1.4.1.10428 9 1.101.2.7.3
-- 1.3.6.1.4.1.10428 9 1.101.2.7.3
-- 1.3.6.1.4.1.10428 9 1.101.2.7.3
		-- 1.3.6.1.4.1.10428 9 1.101.2.7.3
		fkBatteryNotification OBJECT IDENTIFIER ::= { fkBattery 3 }

		
--     1.3.6.1.4.1.10428 9 1.101.2.7.3.1
-- 1.3.6.1.4.1.10428 9 1.101.2.7.3.1
-- 1.3.6.1.4.1.10428 9 1.101.2.7.3.1
-- 1.3.6.1.4.1.10428 9 1.101.2.7.3.1
		-- 1.3.6.1.4.1.10428 9 1.101.2.7.3.1
		fkBatteryForceChargeChanged NOTIFICATION-TYPE
			OBJECTS { fkBatteryControlRequest, fkBatteryControlTimeStamp, fkBatteryControlReqResult }
			STATUS current
			DESCRIPTION 
				"Description."
			::= { fkBatteryNotification 1 }

		
--     1.3.6.1.4.1.10428 9 1.101.2.7.3.2
-- 1.3.6.1.4.1.10428 9 1.101.2.7.3.2
-- 1.3.6.1.4.1.10428 9 1.101.2.7.3.2
-- 1.3.6.1.4.1.10428 9 1.101.2.7.3.2
		-- 1.3.6.1.4.1.10428 9 1.101.2.7.3.2
		fkBatteryChargingStartChanged NOTIFICATION-TYPE
			OBJECTS { fkBatteryControlRequest, fkBatteryControlTimeStamp, fkBatteryControlReqResult }
			STATUS current
			DESCRIPTION 
				"Description."
			::= { fkBatteryNotification 2 }

		
--     1.3.6.1.4.1.10428 9 1.101.2.7.3.3
-- 1.3.6.1.4.1.10428 9 1.101.2.7.3.3
-- 1.3.6.1.4.1.10428 9 1.101.2.7.3.3
-- 1.3.6.1.4.1.10428 9 1.101.2.7.3.3
		-- 1.3.6.1.4.1.10428 9 1.101.2.7.3.3
		fkBatteryForceChargeNonStopChanged NOTIFICATION-TYPE
			OBJECTS { fkBatteryControlRequest, fkBatteryControlTimeStamp, fkBatteryControlReqResult }
			STATUS current
			DESCRIPTION 
				"Description."
			::= { fkBatteryNotification 3 }

		
--     1.3.6.1.4.1.10428 9 1.101.2.7.3.4
-- 1.3.6.1.4.1.10428 9 1.101.2.7.3.4
-- 1.3.6.1.4.1.10428 9 1.101.2.7.3.4
-- 1.3.6.1.4.1.10428 9 1.101.2.7.3.4
		-- 1.3.6.1.4.1.10428 9 1.101.2.7.3.4
		fkBatteryRBUBTStatusChanged NOTIFICATION-TYPE
			OBJECTS { fkBatteryControlRequest, fkBatteryControlTimeStamp, fkBatteryControlReqResult, fkRBUBTStatus }
			STATUS current
			DESCRIPTION 
				"Description."
			::= { fkBatteryNotification 4 }

		
--     1.3.6.1.4.1.10428 9 1.101.2.7.3.5
-- 1.3.6.1.4.1.10428 9 1.101.2.7.3.5
-- 1.3.6.1.4.1.10428 9 1.101.2.7.3.5
-- 1.3.6.1.4.1.10428 9 1.101.2.7.3.5
		-- 1.3.6.1.4.1.10428 9 1.101.2.7.3.5
		fkBatteryRBUBTThresholdChanged NOTIFICATION-TYPE
			OBJECTS { fkBatteryControlRequest, fkBatteryControlTimeStamp, fkBatteryControlReqResult, fkRBUBTThreshold }
			STATUS current
			DESCRIPTION 
				"Description."
			::= { fkBatteryNotification 5 }

		
--     1.3.6.1.4.1.10428 9 1.101.2.7.3.6
-- 1.3.6.1.4.1.10428 9 1.101.2.7.3.6
-- 1.3.6.1.4.1.10428 9 1.101.2.7.3.6
-- 1.3.6.1.4.1.10428 9 1.101.2.7.3.6
		-- 1.3.6.1.4.1.10428 9 1.101.2.7.3.6
		fkBatteryRBURechargeVoltageChanged NOTIFICATION-TYPE
			OBJECTS { fkBatteryControlRequest, fkBatteryControlTimeStamp, fkBatteryControlReqResult, fkRBURechargeVoltage }
			STATUS current
			DESCRIPTION 
				"Description."
			::= { fkBatteryNotification 6 }

		
--     1.3.6.1.4.1.10428 9 1.101.2.7.3.7
-- 1.3.6.1.4.1.10428 9 1.101.2.7.3.7
-- 1.3.6.1.4.1.10428 9 1.101.2.7.3.7
-- 1.3.6.1.4.1.10428 9 1.101.2.7.3.7
		-- 1.3.6.1.4.1.10428 9 1.101.2.7.3.7
		fkBatteryPsuAcTemperThreshChanged NOTIFICATION-TYPE
			OBJECTS { fkBatteryControlRequest, fkBatteryControlTimeStamp, fkBatteryControlReqResult, fkPSUTempThreshold }
			STATUS current
			DESCRIPTION 
				"Description."
			::= { fkBatteryNotification 7 }

		
--     1.3.6.1.4.1.10428 9 1.101.2.7.3.8
-- 1.3.6.1.4.1.10428 9 1.101.2.7.3.8
-- 1.3.6.1.4.1.10428 9 1.101.2.7.3.8
-- 1.3.6.1.4.1.10428 9 1.101.2.7.3.8
		-- 1.3.6.1.4.1.10428 9 1.101.2.7.3.8
		fkBatteryRBUTemperThreshChanged NOTIFICATION-TYPE
			OBJECTS { fkBatteryControlRequest, fkBatteryControlTimeStamp, fkBatteryControlReqResult, fkRBUTempLowThreshold, fkRBUTempHighThreshold
				 }
			STATUS current
			DESCRIPTION 
				"Description."
			::= { fkBatteryNotification 8 }

		
--     1.3.6.1.4.1.10428 9 1.101.2.7.4
-- 1.3.6.1.4.1.10428 9 1.101.2.7.4
-- 1.3.6.1.4.1.10428 9 1.101.2.7.4
-- 1.3.6.1.4.1.10428 9 1.101.2.7.4
		-- 1.3.6.1.4.1.10428 9 1.101.2.7.4
		fkBatteryBackupTable OBJECT-TYPE
			SYNTAX SEQUENCE OF FkBatteryBackupEntry
			MAX-ACCESS not-accessible
			STATUS current
			DESCRIPTION
				"Description."
			::= { fkBattery 4 }

		
--     1.3.6.1.4.1.10428 9 1.101.2.7.4.1
-- 1.3.6.1.4.1.10428 9 1.101.2.7.4.1
-- 1.3.6.1.4.1.10428 9 1.101.2.7.4.1
-- 1.3.6.1.4.1.10428 9 1.101.2.7.4.1
		-- 1.3.6.1.4.1.10428 9 1.101.2.7.4.1
		fkBatteryBackupEntry OBJECT-TYPE
			SYNTAX FkBatteryBackupEntry
			MAX-ACCESS not-accessible
			STATUS current
			DESCRIPTION
				"Description."
			INDEX { fkBatteryBackupFile }
			::= { fkBatteryBackupTable 1 }

		
		FkBatteryBackupEntry ::=
			SEQUENCE { 
				fkBatteryBackupFile
					OCTET STRING
			 }

--     1.3.6.1.4.1.10428 9 1.101.2.7.4.1.1
-- 1.3.6.1.4.1.10428 9 1.101.2.7.4.1.1
-- 1.3.6.1.4.1.10428 9 1.101.2.7.4.1.1
-- 1.3.6.1.4.1.10428 9 1.101.2.7.4.1.1
		-- 1.3.6.1.4.1.10428 9 1.101.2.7.4.1.1
		fkBatteryBackupFile OBJECT-TYPE
			SYNTAX OCTET STRING (SIZE (1..64))
			MAX-ACCESS read-only
			STATUS current
			DESCRIPTION
				"Description."
			::= { fkBatteryBackupEntry 1 }

		
--     1.3.6.1.4.1.10428 9 1.101.2.7.5
-- 1.3.6.1.4.1.10428 9 1.101.2.7.5
-- 1.3.6.1.4.1.10428 9 1.101.2.7.5
-- 1.3.6.1.4.1.10428 9 1.101.2.7.5
		-- 1.3.6.1.4.1.10428 9 1.101.2.7.5
		fkBatteryBackupControl OBJECT IDENTIFIER ::= { fkBattery 5 }

		
--     1.3.6.1.4.1.10428 9 1.101.2.7.5.1
-- 1.3.6.1.4.1.10428 9 1.101.2.7.5.1
-- 1.3.6.1.4.1.10428 9 1.101.2.7.5.1
-- 1.3.6.1.4.1.10428 9 1.101.2.7.5.1
		-- 1.3.6.1.4.1.10428 9 1.101.2.7.5.1
		fkBatteryBackupControlRequest OBJECT-TYPE
			SYNTAX INTEGER
				{
				setBatteryBackupProfile(1),
				setBatteryUpgrade(2),
				clearBatteryBackupTable(3)
				}
			MAX-ACCESS read-write
			STATUS current
			DESCRIPTION
				"Description."
			::= { fkBatteryBackupControl 1 }

		
--     1.3.6.1.4.1.10428 9 1.101.2.7.5.2
-- 1.3.6.1.4.1.10428 9 1.101.2.7.5.2
-- 1.3.6.1.4.1.10428 9 1.101.2.7.5.2
-- 1.3.6.1.4.1.10428 9 1.101.2.7.5.2
		-- 1.3.6.1.4.1.10428 9 1.101.2.7.5.2
		fkBatteryBackupControlStatus OBJECT-TYPE
			SYNTAX FkControlStatusType
			MAX-ACCESS read-only
			STATUS current
			DESCRIPTION
				"Description."
			::= { fkBatteryBackupControl 2 }

		
--     1.3.6.1.4.1.10428 9 1.101.2.7.5.3
-- 1.3.6.1.4.1.10428 9 1.101.2.7.5.3
-- 1.3.6.1.4.1.10428 9 1.101.2.7.5.3
-- 1.3.6.1.4.1.10428 9 1.101.2.7.5.3
		-- 1.3.6.1.4.1.10428 9 1.101.2.7.5.3
		fkBatteryBackupControlTimer OBJECT-TYPE
			SYNTAX Gauge32
			MAX-ACCESS read-write
			STATUS current
			DESCRIPTION
				"Description."
			::= { fkBatteryBackupControl 3 }

		
--     1.3.6.1.4.1.10428 9 1.101.2.7.5.4
-- 1.3.6.1.4.1.10428 9 1.101.2.7.5.4
-- 1.3.6.1.4.1.10428 9 1.101.2.7.5.4
-- 1.3.6.1.4.1.10428 9 1.101.2.7.5.4
		-- 1.3.6.1.4.1.10428 9 1.101.2.7.5.4
		fkBatteryBackupControlTimeStamp OBJECT-TYPE
			SYNTAX TimeTicks
			MAX-ACCESS read-only
			STATUS current
			DESCRIPTION
				"Description."
			::= { fkBatteryBackupControl 4 }

		
--     1.3.6.1.4.1.10428 9 1.101.2.7.5.5
-- 1.3.6.1.4.1.10428 9 1.101.2.7.5.5
-- 1.3.6.1.4.1.10428 9 1.101.2.7.5.5
-- 1.3.6.1.4.1.10428 9 1.101.2.7.5.5
		-- 1.3.6.1.4.1.10428 9 1.101.2.7.5.5
		fkBatteryBackupControlReqResult OBJECT-TYPE
			SYNTAX FkControlRequestResultType
			MAX-ACCESS read-only
			STATUS current
			DESCRIPTION
				"Description."
			::= { fkBatteryBackupControl 5 }

		
--     1.3.6.1.4.1.10428 9 1.101.2.7.5.6
-- 1.3.6.1.4.1.10428 9 1.101.2.7.5.6
-- 1.3.6.1.4.1.10428 9 1.101.2.7.5.6
-- 1.3.6.1.4.1.10428 9 1.101.2.7.5.6
		-- 1.3.6.1.4.1.10428 9 1.101.2.7.5.6
		fkBatteryBackupControlServerIP OBJECT-TYPE
			SYNTAX IpAddress
			MAX-ACCESS read-write
			STATUS current
			DESCRIPTION
				"Description."
			::= { fkBatteryBackupControl 6 }

		
--     1.3.6.1.4.1.10428 9 1.101.2.7.5.7
-- 1.3.6.1.4.1.10428 9 1.101.2.7.5.7
-- 1.3.6.1.4.1.10428 9 1.101.2.7.5.7
-- 1.3.6.1.4.1.10428 9 1.101.2.7.5.7
		-- 1.3.6.1.4.1.10428 9 1.101.2.7.5.7
		fkBatteryBackupControlUserID OBJECT-TYPE
			SYNTAX OCTET STRING (SIZE (1..64))
			MAX-ACCESS read-write
			STATUS current
			DESCRIPTION
				"Description."
			::= { fkBatteryBackupControl 7 }

		
--     1.3.6.1.4.1.10428 9 1.101.2.7.5.8
-- 1.3.6.1.4.1.10428 9 1.101.2.7.5.8
-- 1.3.6.1.4.1.10428 9 1.101.2.7.5.8
-- 1.3.6.1.4.1.10428 9 1.101.2.7.5.8
		-- 1.3.6.1.4.1.10428 9 1.101.2.7.5.8
		fkBatteryBackupControlPassword OBJECT-TYPE
			SYNTAX OCTET STRING (SIZE (1..64))
			MAX-ACCESS read-write
			STATUS current
			DESCRIPTION
				"Description."
			::= { fkBatteryBackupControl 8 }

		
--     1.3.6.1.4.1.10428 9 1.101.2.7.5.9
-- 1.3.6.1.4.1.10428 9 1.101.2.7.5.9
-- 1.3.6.1.4.1.10428 9 1.101.2.7.5.9
-- 1.3.6.1.4.1.10428 9 1.101.2.7.5.9
		-- 1.3.6.1.4.1.10428 9 1.101.2.7.5.9
		fkBatteryBackupControlFlag OBJECT-TYPE
			SYNTAX INTEGER
				{
				download(1),
				upload(2)
				}
			MAX-ACCESS read-write
			STATUS current
			DESCRIPTION
				"Description."
			::= { fkBatteryBackupControl 9 }

		
--     1.3.6.1.4.1.10428 9 1.101.2.7.5.10
-- 1.3.6.1.4.1.10428 9 1.101.2.7.5.10
-- 1.3.6.1.4.1.10428 9 1.101.2.7.5.10
-- 1.3.6.1.4.1.10428 9 1.101.2.7.5.10
		-- 1.3.6.1.4.1.10428 9 1.101.2.7.5.10
		fkBatteryBackupControlLocalFile OBJECT-TYPE
			SYNTAX OCTET STRING (SIZE (1..64))
			MAX-ACCESS read-write
			STATUS current
			DESCRIPTION
				"Description."
			::= { fkBatteryBackupControl 10 }

		
--     1.3.6.1.4.1.10428 9 1.101.2.7.5.11
-- 1.3.6.1.4.1.10428 9 1.101.2.7.5.11
-- 1.3.6.1.4.1.10428 9 1.101.2.7.5.11
-- 1.3.6.1.4.1.10428 9 1.101.2.7.5.11
		-- 1.3.6.1.4.1.10428 9 1.101.2.7.5.11
		fkBatteryBackupControlRemoteFile OBJECT-TYPE
			SYNTAX OCTET STRING (SIZE (1..64))
			MAX-ACCESS read-write
			STATUS current
			DESCRIPTION
				"Description."
			::= { fkBatteryBackupControl 11 }

		
--     1.3.6.1.4.1.10428 9 1.101.2.7.6
-- 1.3.6.1.4.1.10428 9 1.101.2.7.6
-- 1.3.6.1.4.1.10428 9 1.101.2.7.6
-- 1.3.6.1.4.1.10428 9 1.101.2.7.6
		-- 1.3.6.1.4.1.10428 9 1.101.2.7.6
		fkBatterBackupNotification OBJECT IDENTIFIER ::= { fkBattery 6 }

		
--     1.3.6.1.4.1.10428 9 1.101.2.7.6.1
-- 1.3.6.1.4.1.10428 9 1.101.2.7.6.1
-- 1.3.6.1.4.1.10428 9 1.101.2.7.6.1
-- 1.3.6.1.4.1.10428 9 1.101.2.7.6.1
		-- 1.3.6.1.4.1.10428 9 1.101.2.7.6.1
		fkBatteryBackupProfileChanged NOTIFICATION-TYPE
			OBJECTS { fkBatteryBackupControlRequest, fkBatteryBackupControlTimeStamp, fkBatteryBackupControlReqResult, fkBatteryBackupControlServerIP, fkBatteryBackupControlUserID, 
				fkBatteryBackupControlPassword, fkBatteryBackupControlFlag, fkBatteryBackupControlLocalFile, fkBatteryBackupControlRemoteFile }
			STATUS current
			DESCRIPTION 
				"Description."
			::= { fkBatterBackupNotification 1 }

		
--     1.3.6.1.4.1.10428 9 1.101.2.7.6.2
-- 1.3.6.1.4.1.10428 9 1.101.2.7.6.2
-- 1.3.6.1.4.1.10428 9 1.101.2.7.6.2
-- 1.3.6.1.4.1.10428 9 1.101.2.7.6.2
		-- 1.3.6.1.4.1.10428 9 1.101.2.7.6.2
		fkBatteryBackupUpgraded NOTIFICATION-TYPE
			OBJECTS { fkBatteryBackupControlRequest, fkBatteryBackupControlTimeStamp, fkBatteryBackupControlReqResult, fkBatteryBackupControlLocalFile }
			STATUS current
			DESCRIPTION 
				"Description."
			::= { fkBatterBackupNotification 2 }

		
--     1.3.6.1.4.1.10428 9 1.101.2.7.6.3
-- 1.3.6.1.4.1.10428 9 1.101.2.7.6.3
-- 1.3.6.1.4.1.10428 9 1.101.2.7.6.3
-- 1.3.6.1.4.1.10428 9 1.101.2.7.6.3
		-- 1.3.6.1.4.1.10428 9 1.101.2.7.6.3
		fkBatteryBackupTableCleared NOTIFICATION-TYPE
			OBJECTS { fkBatteryBackupControlRequest, fkBatteryBackupControlTimeStamp, fkBatteryBackupControlReqResult, fkBatteryBackupControlLocalFile }
			STATUS current
			DESCRIPTION 
				"Description."
			::= { fkBatterBackupNotification 3 }

		
--     1.3.6.1.4.1.10428 9 1.101.2.8
-- 1.3.6.1.4.1.10428 9 1.101.2.8
-- 1.3.6.1.4.1.10428 9 1.101.2.8
-- 1.3.6.1.4.1.10428 9 1.101.2.8
		-- 1.3.6.1.4.1.10428 9 1.101.2.8
		fkDoor OBJECT IDENTIFIER ::= { fkDevice 8 }

		
--     1.3.6.1.4.1.10428 9 1.101.2.8.1
-- 1.3.6.1.4.1.10428 9 1.101.2.8.1
-- 1.3.6.1.4.1.10428 9 1.101.2.8.1
-- 1.3.6.1.4.1.10428 9 1.101.2.8.1
		-- 1.3.6.1.4.1.10428 9 1.101.2.8.1
		fkDoorInfo OBJECT IDENTIFIER ::= { fkDoor 1 }

		
--     1.3.6.1.4.1.10428 9 1.101.2.8.1.1
-- 1.3.6.1.4.1.10428 9 1.101.2.8.1.1
-- 1.3.6.1.4.1.10428 9 1.101.2.8.1.1
-- 1.3.6.1.4.1.10428 9 1.101.2.8.1.1
		-- 1.3.6.1.4.1.10428 9 1.101.2.8.1.1
		fkDoorStatus OBJECT-TYPE
			SYNTAX INTEGER
				{
				close(0),
				open(1)
				}
			MAX-ACCESS read-only
			STATUS current
			DESCRIPTION
				"Description."
			::= { fkDoorInfo 1 }

		
--     1.3.6.1.4.1.10428 9 1.101.2.9
-- 1.3.6.1.4.1.10428 9 1.101.2.9
-- 1.3.6.1.4.1.10428 9 1.101.2.9
-- 1.3.6.1.4.1.10428 9 1.101.2.9
		-- 1.3.6.1.4.1.10428 9 1.101.2.9
		fkCpu OBJECT IDENTIFIER ::= { fkDevice 9 }

		
--     1.3.6.1.4.1.10428 9 1.101.2.9.1
-- 1.3.6.1.4.1.10428 9 1.101.2.9.1
-- 1.3.6.1.4.1.10428 9 1.101.2.9.1
-- 1.3.6.1.4.1.10428 9 1.101.2.9.1
		-- 1.3.6.1.4.1.10428 9 1.101.2.9.1
		fkCpuInfo OBJECT IDENTIFIER ::= { fkCpu 1 }

		
--     1.3.6.1.4.1.10428 9 1.101.2.9.1.1
-- 1.3.6.1.4.1.10428 9 1.101.2.9.1.1
-- 1.3.6.1.4.1.10428 9 1.101.2.9.1.1
-- 1.3.6.1.4.1.10428 9 1.101.2.9.1.1
		-- 1.3.6.1.4.1.10428 9 1.101.2.9.1.1
		fkCpuProcessor OBJECT-TYPE
			SYNTAX OCTET STRING
			MAX-ACCESS read-only
			STATUS current
			DESCRIPTION
				"Description."
			::= { fkCpuInfo 1 }

		
--     1.3.6.1.4.1.10428 9 1.101.2.9.1.2
-- 1.3.6.1.4.1.10428 9 1.101.2.9.1.2
-- 1.3.6.1.4.1.10428 9 1.101.2.9.1.2
-- 1.3.6.1.4.1.10428 9 1.101.2.9.1.2
		-- 1.3.6.1.4.1.10428 9 1.101.2.9.1.2
		fkCpuModel OBJECT-TYPE
			SYNTAX OCTET STRING
			MAX-ACCESS read-only
			STATUS current
			DESCRIPTION
				"Description."
			::= { fkCpuInfo 2 }

		
--     1.3.6.1.4.1.10428 9 1.101.2.9.1.3
-- 1.3.6.1.4.1.10428 9 1.101.2.9.1.3
-- 1.3.6.1.4.1.10428 9 1.101.2.9.1.3
-- 1.3.6.1.4.1.10428 9 1.101.2.9.1.3
		-- 1.3.6.1.4.1.10428 9 1.101.2.9.1.3
		fkCpuRevision OBJECT-TYPE
			SYNTAX OCTET STRING
			MAX-ACCESS read-only
			STATUS current
			DESCRIPTION
				"Description."
			::= { fkCpuInfo 3 }

		
--     1.3.6.1.4.1.10428 9 1.101.2.9.1.4
-- 1.3.6.1.4.1.10428 9 1.101.2.9.1.4
-- 1.3.6.1.4.1.10428 9 1.101.2.9.1.4
-- 1.3.6.1.4.1.10428 9 1.101.2.9.1.4
		-- 1.3.6.1.4.1.10428 9 1.101.2.9.1.4
		fkCpuBogomips OBJECT-TYPE
			SYNTAX OCTET STRING
			MAX-ACCESS read-only
			STATUS current
			DESCRIPTION
				"Description."
			::= { fkCpuInfo 4 }

		
--     1.3.6.1.4.1.10428 9 1.101.2.9.1.5
-- 1.3.6.1.4.1.10428 9 1.101.2.9.1.5
-- 1.3.6.1.4.1.10428 9 1.101.2.9.1.5
-- 1.3.6.1.4.1.10428 9 1.101.2.9.1.5
		-- 1.3.6.1.4.1.10428 9 1.101.2.9.1.5
		fkCpuManufacturer OBJECT-TYPE
			SYNTAX OCTET STRING
			MAX-ACCESS read-only
			STATUS current
			DESCRIPTION
				"Description."
			::= { fkCpuInfo 5 }

		
--     1.3.6.1.4.1.10428 9 1.101.2.9.1.6
-- 1.3.6.1.4.1.10428 9 1.101.2.9.1.6
-- 1.3.6.1.4.1.10428 9 1.101.2.9.1.6
-- 1.3.6.1.4.1.10428 9 1.101.2.9.1.6
		-- 1.3.6.1.4.1.10428 9 1.101.2.9.1.6
		fkCpuClock OBJECT-TYPE
			SYNTAX Integer32
			MAX-ACCESS read-only
			STATUS current
			DESCRIPTION
				"Description."
			::= { fkCpuInfo 6 }

		
--     1.3.6.1.4.1.10428 9 1.101.2.9.1.7
-- 1.3.6.1.4.1.10428 9 1.101.2.9.1.7
-- 1.3.6.1.4.1.10428 9 1.101.2.9.1.7
-- 1.3.6.1.4.1.10428 9 1.101.2.9.1.7
		-- 1.3.6.1.4.1.10428 9 1.101.2.9.1.7
		fkCpuBusClock OBJECT-TYPE
			SYNTAX Integer32
			MAX-ACCESS read-only
			STATUS current
			DESCRIPTION
				"Description."
			::= { fkCpuInfo 7 }

		
--     1.3.6.1.4.1.10428 9 1.101.2.10
-- 1.3.6.1.4.1.10428 9 1.101.2.10
-- 1.3.6.1.4.1.10428 9 1.101.2.10
-- 1.3.6.1.4.1.10428 9 1.101.2.10
		-- 1.3.6.1.4.1.10428 9 1.101.2.10
		fkClockModule OBJECT IDENTIFIER ::= { fkDevice 10 }

		
--     1.3.6.1.4.1.10428 9 1.101.2.10.1
-- 1.3.6.1.4.1.10428 9 1.101.2.10.1
-- 1.3.6.1.4.1.10428 9 1.101.2.10.1
-- 1.3.6.1.4.1.10428 9 1.101.2.10.1
		-- 1.3.6.1.4.1.10428 9 1.101.2.10.1
		fkClockModuleTable OBJECT-TYPE
			SYNTAX SEQUENCE OF FkClockModuleEntry
			MAX-ACCESS not-accessible
			STATUS current
			DESCRIPTION
				"Description."
			::= { fkClockModule 1 }

		
--     1.3.6.1.4.1.10428 9 1.101.2.10.1.1
-- 1.3.6.1.4.1.10428 9 1.101.2.10.1.1
-- 1.3.6.1.4.1.10428 9 1.101.2.10.1.1
-- 1.3.6.1.4.1.10428 9 1.101.2.10.1.1
		-- 1.3.6.1.4.1.10428 9 1.101.2.10.1.1
		fkClockModuleEntry OBJECT-TYPE
			SYNTAX FkClockModuleEntry
			MAX-ACCESS not-accessible
			STATUS current
			DESCRIPTION
				"Description."
			INDEX { fkClockModuleIndex }
			::= { fkClockModuleTable 1 }

		
		FkClockModuleEntry ::=
			SEQUENCE { 
				fkClockModuleIndex
					INTEGER,
				fkClockModuleBoardId
					INTEGER,
				fkClockModuleInstallStatus
					INTEGER,
				fkClockModuleInitStatus
					INTEGER,
				fkClockModuleOPMode
					INTEGER
			 }

--     1.3.6.1.4.1.10428 9 1.101.2.10.1.1.1
-- 1.3.6.1.4.1.10428 9 1.101.2.10.1.1.1
-- 1.3.6.1.4.1.10428 9 1.101.2.10.1.1.1
-- 1.3.6.1.4.1.10428 9 1.101.2.10.1.1.1
		-- 1.3.6.1.4.1.10428 9 1.101.2.10.1.1.1
		fkClockModuleIndex OBJECT-TYPE
			SYNTAX INTEGER (1..255)
			MAX-ACCESS read-only
			STATUS current
			DESCRIPTION
				"A unique value, greater than zero, for each module. It is recommended that values are assigned contiguously starting from 1."
			::= { fkClockModuleEntry 1 }

		
--     1.3.6.1.4.1.10428 9 1.101.2.10.1.1.2
-- 1.3.6.1.4.1.10428 9 1.101.2.10.1.1.2
-- 1.3.6.1.4.1.10428 9 1.101.2.10.1.1.2
-- 1.3.6.1.4.1.10428 9 1.101.2.10.1.1.2
		-- 1.3.6.1.4.1.10428 9 1.101.2.10.1.1.2
		fkClockModuleBoardId OBJECT-TYPE
			SYNTAX INTEGER
				{
				sfuA(1),
				sfuB(2)
				}
			MAX-ACCESS read-only
			STATUS current
			DESCRIPTION
				"Indication of the board identifier."
			::= { fkClockModuleEntry 2 }

		
--     1.3.6.1.4.1.10428 9 1.101.2.10.1.1.3
-- 1.3.6.1.4.1.10428 9 1.101.2.10.1.1.3
-- 1.3.6.1.4.1.10428 9 1.101.2.10.1.1.3
-- 1.3.6.1.4.1.10428 9 1.101.2.10.1.1.3
		-- 1.3.6.1.4.1.10428 9 1.101.2.10.1.1.3
		fkClockModuleInstallStatus OBJECT-TYPE
			SYNTAX INTEGER
				{
				removed(0),
				installed(1)
				}
			MAX-ACCESS read-only
			STATUS current
			DESCRIPTION
				"The install status of clock module."
			::= { fkClockModuleEntry 3 }

		
--     1.3.6.1.4.1.10428 9 1.101.2.10.1.1.4
-- 1.3.6.1.4.1.10428 9 1.101.2.10.1.1.4
-- 1.3.6.1.4.1.10428 9 1.101.2.10.1.1.4
-- 1.3.6.1.4.1.10428 9 1.101.2.10.1.1.4
		-- 1.3.6.1.4.1.10428 9 1.101.2.10.1.1.4
		fkClockModuleInitStatus OBJECT-TYPE
			SYNTAX INTEGER
				{
				failure(0),
				ok(1)
				}
			MAX-ACCESS read-only
			STATUS current
			DESCRIPTION
				"The initialization status of clock module."
			::= { fkClockModuleEntry 4 }

		
--     1.3.6.1.4.1.10428 9 1.101.2.10.1.1.5
-- 1.3.6.1.4.1.10428 9 1.101.2.10.1.1.5
-- 1.3.6.1.4.1.10428 9 1.101.2.10.1.1.5
-- 1.3.6.1.4.1.10428 9 1.101.2.10.1.1.5
		-- 1.3.6.1.4.1.10428 9 1.101.2.10.1.1.5
		fkClockModuleOPMode OBJECT-TYPE
			SYNTAX INTEGER
				{
				freerun(1),
				holdover(2),
				locked(3),
				prelocked2(4),
				prelocked(5),
				lostphase(6),
				unknown(255)
				}
			MAX-ACCESS read-write
			STATUS current
			DESCRIPTION
				"The CM operating mode"
			::= { fkClockModuleEntry 5 }

		
--     1.3.6.1.4.1.10428 9 1.101.2.10.2
-- 1.3.6.1.4.1.10428 9 1.101.2.10.2
-- 1.3.6.1.4.1.10428 9 1.101.2.10.2
-- 1.3.6.1.4.1.10428 9 1.101.2.10.2
		-- 1.3.6.1.4.1.10428 9 1.101.2.10.2
		fkClockInfo OBJECT IDENTIFIER ::= { fkClockModule 2 }

		
--     1.3.6.1.4.1.10428 9 1.101.2.10.2.1
-- 1.3.6.1.4.1.10428 9 1.101.2.10.2.1
-- 1.3.6.1.4.1.10428 9 1.101.2.10.2.1
-- 1.3.6.1.4.1.10428 9 1.101.2.10.2.1
		-- 1.3.6.1.4.1.10428 9 1.101.2.10.2.1
		fkClockInfoInSrcType OBJECT-TYPE
			SYNTAX INTEGER
				{
				ntt(1),
				ntt2(2),
				e1(3),
				t1(4),
				unknown(255)
				}
			MAX-ACCESS accessible-for-notify
			STATUS current
			DESCRIPTION
				"The clock input source type."
			::= { fkClockInfo 1 }

		
--     1.3.6.1.4.1.10428 9 1.101.2.10.2.2
-- 1.3.6.1.4.1.10428 9 1.101.2.10.2.2
-- 1.3.6.1.4.1.10428 9 1.101.2.10.2.2
-- 1.3.6.1.4.1.10428 9 1.101.2.10.2.2
		-- 1.3.6.1.4.1.10428 9 1.101.2.10.2.2
		fkClockInfoInSrcStatus OBJECT-TYPE
			SYNTAX INTEGER
				{
				true(1),
				false(2)
				}
			MAX-ACCESS accessible-for-notify
			STATUS current
			DESCRIPTION
				"The input source is Valid or Invalid."
			::= { fkClockInfo 2 }

		
--     1.3.6.1.4.1.10428 9 1.101.2.10.2.3
-- 1.3.6.1.4.1.10428 9 1.101.2.10.2.3
-- 1.3.6.1.4.1.10428 9 1.101.2.10.2.3
-- 1.3.6.1.4.1.10428 9 1.101.2.10.2.3
		-- 1.3.6.1.4.1.10428 9 1.101.2.10.2.3
		fkClockInfoInSrcAISStatus OBJECT-TYPE
			SYNTAX INTEGER
				{
				true(1),
				false(2)
				}
			MAX-ACCESS accessible-for-notify
			STATUS current
			DESCRIPTION
				"The AIS is detected or not detected."
			::= { fkClockInfo 3 }

		
--     1.3.6.1.4.1.10428 9 1.101.2.10.2.4
-- 1.3.6.1.4.1.10428 9 1.101.2.10.2.4
-- 1.3.6.1.4.1.10428 9 1.101.2.10.2.4
-- 1.3.6.1.4.1.10428 9 1.101.2.10.2.4
		-- 1.3.6.1.4.1.10428 9 1.101.2.10.2.4
		fkClockInfoInSrcLoSStatus OBJECT-TYPE
			SYNTAX INTEGER
				{
				true(1),
				false(2)
				}
			MAX-ACCESS accessible-for-notify
			STATUS current
			DESCRIPTION
				"The LoS is detected or not detected"
			::= { fkClockInfo 4 }

		
--     1.3.6.1.4.1.10428 9 1.101.2.10.2.5
-- 1.3.6.1.4.1.10428 9 1.101.2.10.2.5
-- 1.3.6.1.4.1.10428 9 1.101.2.10.2.5
-- 1.3.6.1.4.1.10428 9 1.101.2.10.2.5
		-- 1.3.6.1.4.1.10428 9 1.101.2.10.2.5
		fkClockInfoInSrcLDSCStatus OBJECT-TYPE
			SYNTAX INTEGER
				{
				true(1),
				false(2)
				}
			MAX-ACCESS accessible-for-notify
			STATUS current
			DESCRIPTION
				"The Line Driver Short Circuit is detected or not detected"
			::= { fkClockInfo 5 }

		
--     1.3.6.1.4.1.10428 9 1.101.2.10.2.6
-- 1.3.6.1.4.1.10428 9 1.101.2.10.2.6
-- 1.3.6.1.4.1.10428 9 1.101.2.10.2.6
-- 1.3.6.1.4.1.10428 9 1.101.2.10.2.6
		-- 1.3.6.1.4.1.10428 9 1.101.2.10.2.6
		fkClockInfoInSrcNtrClockType OBJECT-TYPE
			SYNTAX BITS
				{
				bit64Khz(0),
				bit8Khz(1),
				bit04Khz(2)
				}
			MAX-ACCESS accessible-for-notify
			STATUS current
			DESCRIPTION
				"The ntr clock is changed."
			::= { fkClockInfo 6 }

		
--     1.3.6.1.4.1.10428 9 1.101.2.11
-- 1.3.6.1.4.1.10428 9 1.101.2.11
-- 1.3.6.1.4.1.10428 9 1.101.2.11
-- 1.3.6.1.4.1.10428 9 1.101.2.11
		-- 1.3.6.1.4.1.10428 9 1.101.2.11
		fkSlot OBJECT IDENTIFIER ::= { fkDevice 11 }

		
--     1.3.6.1.4.1.10428 9 1.101.2.11.1
-- 1.3.6.1.4.1.10428 9 1.101.2.11.1
-- 1.3.6.1.4.1.10428 9 1.101.2.11.1
-- 1.3.6.1.4.1.10428 9 1.101.2.11.1
		-- 1.3.6.1.4.1.10428 9 1.101.2.11.1
		fkSlotSystemInfo OBJECT IDENTIFIER ::= { fkSlot 1 }

		
--     1.3.6.1.4.1.10428 9 1.101.2.11.1.1
-- 1.3.6.1.4.1.10428 9 1.101.2.11.1.1
-- 1.3.6.1.4.1.10428 9 1.101.2.11.1.1
-- 1.3.6.1.4.1.10428 9 1.101.2.11.1.1
		-- 1.3.6.1.4.1.10428 9 1.101.2.11.1.1
		fkSlotSystemInfoTable OBJECT-TYPE
			SYNTAX SEQUENCE OF FkSlotSystemInfoEntry
			MAX-ACCESS not-accessible
			STATUS current
			DESCRIPTION
				"Description."
			::= { fkSlotSystemInfo 1 }

		
--     1.3.6.1.4.1.10428 9 1.101.2.11.1.1.1
-- 1.3.6.1.4.1.10428 9 1.101.2.11.1.1.1
-- 1.3.6.1.4.1.10428 9 1.101.2.11.1.1.1
-- 1.3.6.1.4.1.10428 9 1.101.2.11.1.1.1
		-- 1.3.6.1.4.1.10428 9 1.101.2.11.1.1.1
		fkSlotSystemInfoEntry OBJECT-TYPE
			SYNTAX FkSlotSystemInfoEntry
			MAX-ACCESS not-accessible
			STATUS current
			DESCRIPTION
				"Description."
			INDEX { fkSlotSystemIndex }
			::= { fkSlotSystemInfoTable 1 }

		
		FkSlotSystemInfoEntry ::=
			SEQUENCE { 
				fkSlotSystemIndex
					Integer32,
				fkSlotSystemUptime
					TimeTicks,
				fkSlotSystemModelName
					OCTET STRING,
				fkSlotSystemSerialNumber
					OCTET STRING,
				fkSlotSystemHWVersion
					OCTET STRING,
				fkSlotSystemBLVersion
					OCTET STRING,
				fkSlotSystemSWCompatibility
					OCTET STRING,
				fkSlotSystemOSVersion
					OCTET STRING,
				fkSlotSystemMacAddress
					OCTET STRING,
				fkSlotSystemCPULoadAll
					OCTET STRING,
				fkSlotSystemCPULoadInterrupt
					OCTET STRING,
				fkSlotSystemMemoryTotal
					Gauge32,
				fkSlotSystemMemoryFree
					Gauge32,
				fkSlotSystemMemoryShared
					Gauge32,
				fkSlotSystemMemoryBuffers
					Gauge32,
				fkSlotSystemMemoryCached
					Gauge32,
				fkSlotSystemMemorySwapTotal
					Gauge32,
				fkSlotSystemMemorySwapFree
					Gauge32,
				fkSlotSystemBootReason
					INTEGER,
				fkSlotSystemBootTime
					Gauge32,
				fkSlotSystemVoltage
					Gauge32,
				fkSlotSystemPowerLevelStatus
					INTEGER,
				fkSlotSystemInfoLEDStatus
					BITS,
				fkSlotSystemInfoPackageVersion
					OCTET STRING
			 }

--     1.3.6.1.4.1.10428 9 1.101.2.11.1.1.1.1
-- 1.3.6.1.4.1.10428 9 1.101.2.11.1.1.1.1
-- 1.3.6.1.4.1.10428 9 1.101.2.11.1.1.1.1
-- 1.3.6.1.4.1.10428 9 1.101.2.11.1.1.1.1
		-- 1.3.6.1.4.1.10428 9 1.101.2.11.1.1.1.1
		fkSlotSystemIndex OBJECT-TYPE
			SYNTAX Integer32 (1..8)
			MAX-ACCESS read-only
			STATUS current
			DESCRIPTION
				"The system slot index."
			::= { fkSlotSystemInfoEntry 1 }

		
--     1.3.6.1.4.1.10428 9 1.101.2.11.1.1.1.2
-- 1.3.6.1.4.1.10428 9 1.101.2.11.1.1.1.2
-- 1.3.6.1.4.1.10428 9 1.101.2.11.1.1.1.2
-- 1.3.6.1.4.1.10428 9 1.101.2.11.1.1.1.2
		-- 1.3.6.1.4.1.10428 9 1.101.2.11.1.1.1.2
		fkSlotSystemUptime OBJECT-TYPE
			SYNTAX TimeTicks
			MAX-ACCESS read-only
			STATUS current
			DESCRIPTION
				"The time since the network management portion of the system was last re-initialized."
			::= { fkSlotSystemInfoEntry 2 }

		
--     1.3.6.1.4.1.10428 9 1.101.2.11.1.1.1.3
-- 1.3.6.1.4.1.10428 9 1.101.2.11.1.1.1.3
-- 1.3.6.1.4.1.10428 9 1.101.2.11.1.1.1.3
-- 1.3.6.1.4.1.10428 9 1.101.2.11.1.1.1.3
		-- 1.3.6.1.4.1.10428 9 1.101.2.11.1.1.1.3
		fkSlotSystemModelName OBJECT-TYPE
			SYNTAX OCTET STRING
			MAX-ACCESS read-only
			STATUS current
			DESCRIPTION
				"The model name."
			::= { fkSlotSystemInfoEntry 3 }

		
--     1.3.6.1.4.1.10428 9 1.101.2.11.1.1.1.4
-- 1.3.6.1.4.1.10428 9 1.101.2.11.1.1.1.4
-- 1.3.6.1.4.1.10428 9 1.101.2.11.1.1.1.4
-- 1.3.6.1.4.1.10428 9 1.101.2.11.1.1.1.4
		-- 1.3.6.1.4.1.10428 9 1.101.2.11.1.1.1.4
		fkSlotSystemSerialNumber OBJECT-TYPE
			SYNTAX OCTET STRING
			MAX-ACCESS read-only
			STATUS current
			DESCRIPTION
				"The serial number "
			::= { fkSlotSystemInfoEntry 4 }

		
--     1.3.6.1.4.1.10428 9 1.101.2.11.1.1.1.5
-- 1.3.6.1.4.1.10428 9 1.101.2.11.1.1.1.5
-- 1.3.6.1.4.1.10428 9 1.101.2.11.1.1.1.5
-- 1.3.6.1.4.1.10428 9 1.101.2.11.1.1.1.5
		-- 1.3.6.1.4.1.10428 9 1.101.2.11.1.1.1.5
		fkSlotSystemHWVersion OBJECT-TYPE
			SYNTAX OCTET STRING
			MAX-ACCESS read-only
			STATUS current
			DESCRIPTION
				"The H/W version."
			::= { fkSlotSystemInfoEntry 5 }

		
--     1.3.6.1.4.1.10428 9 1.101.2.11.1.1.1.6
-- 1.3.6.1.4.1.10428 9 1.101.2.11.1.1.1.6
-- 1.3.6.1.4.1.10428 9 1.101.2.11.1.1.1.6
-- 1.3.6.1.4.1.10428 9 1.101.2.11.1.1.1.6
		-- 1.3.6.1.4.1.10428 9 1.101.2.11.1.1.1.6
		fkSlotSystemBLVersion OBJECT-TYPE
			SYNTAX OCTET STRING
			MAX-ACCESS read-only
			STATUS current
			DESCRIPTION
				"The boot loader’s S/W version."
			::= { fkSlotSystemInfoEntry 6 }

		
--     1.3.6.1.4.1.10428 9 1.101.2.11.1.1.1.7
-- 1.3.6.1.4.1.10428 9 1.101.2.11.1.1.1.7
-- 1.3.6.1.4.1.10428 9 1.101.2.11.1.1.1.7
-- 1.3.6.1.4.1.10428 9 1.101.2.11.1.1.1.7
		-- 1.3.6.1.4.1.10428 9 1.101.2.11.1.1.1.7
		fkSlotSystemSWCompatibility OBJECT-TYPE
			SYNTAX OCTET STRING
			MAX-ACCESS read-only
			STATUS current
			DESCRIPTION
				"The system compatibility."
			::= { fkSlotSystemInfoEntry 7 }

		
--     1.3.6.1.4.1.10428 9 1.101.2.11.1.1.1.8
-- 1.3.6.1.4.1.10428 9 1.101.2.11.1.1.1.8
-- 1.3.6.1.4.1.10428 9 1.101.2.11.1.1.1.8
-- 1.3.6.1.4.1.10428 9 1.101.2.11.1.1.1.8
		-- 1.3.6.1.4.1.10428 9 1.101.2.11.1.1.1.8
		fkSlotSystemOSVersion OBJECT-TYPE
			SYNTAX OCTET STRING
			MAX-ACCESS read-only
			STATUS current
			DESCRIPTION
				"The version information of current os."
			::= { fkSlotSystemInfoEntry 8 }

		
--     1.3.6.1.4.1.10428 9 1.101.2.11.1.1.1.9
-- 1.3.6.1.4.1.10428 9 1.101.2.11.1.1.1.9
-- 1.3.6.1.4.1.10428 9 1.101.2.11.1.1.1.9
-- 1.3.6.1.4.1.10428 9 1.101.2.11.1.1.1.9
		-- 1.3.6.1.4.1.10428 9 1.101.2.11.1.1.1.9
		fkSlotSystemMacAddress OBJECT-TYPE
			SYNTAX OCTET STRING
			MAX-ACCESS read-only
			STATUS current
			DESCRIPTION
				"The system’s MAC address."
			::= { fkSlotSystemInfoEntry 9 }

		
--     1.3.6.1.4.1.10428 9 1.101.2.11.1.1.1.10
-- 1.3.6.1.4.1.10428 9 1.101.2.11.1.1.1.10
-- 1.3.6.1.4.1.10428 9 1.101.2.11.1.1.1.10
-- 1.3.6.1.4.1.10428 9 1.101.2.11.1.1.1.10
		-- 1.3.6.1.4.1.10428 9 1.101.2.11.1.1.1.10
		fkSlotSystemCPULoadAll OBJECT-TYPE
			SYNTAX OCTET STRING
			MAX-ACCESS read-only
			STATUS current
			DESCRIPTION
				"The CPU all load for 5/60/600 second. (unit: 0.01%)"
			::= { fkSlotSystemInfoEntry 10 }

		
--     1.3.6.1.4.1.10428 9 1.101.2.11.1.1.1.11
-- 1.3.6.1.4.1.10428 9 1.101.2.11.1.1.1.11
-- 1.3.6.1.4.1.10428 9 1.101.2.11.1.1.1.11
-- 1.3.6.1.4.1.10428 9 1.101.2.11.1.1.1.11
		-- 1.3.6.1.4.1.10428 9 1.101.2.11.1.1.1.11
		fkSlotSystemCPULoadInterrupt OBJECT-TYPE
			SYNTAX OCTET STRING
			MAX-ACCESS read-only
			STATUS current
			DESCRIPTION
				"The CPU interrupt load for 5/60/600 second. (unit: 0.01%)"
			::= { fkSlotSystemInfoEntry 11 }

		
--     1.3.6.1.4.1.10428 9 1.101.2.11.1.1.1.12
-- 1.3.6.1.4.1.10428 9 1.101.2.11.1.1.1.12
-- 1.3.6.1.4.1.10428 9 1.101.2.11.1.1.1.12
-- 1.3.6.1.4.1.10428 9 1.101.2.11.1.1.1.12
		-- 1.3.6.1.4.1.10428 9 1.101.2.11.1.1.1.12
		fkSlotSystemMemoryTotal OBJECT-TYPE
			SYNTAX Gauge32
			MAX-ACCESS read-only
			STATUS current
			DESCRIPTION
				"The total memory size (unit: kb)"
			::= { fkSlotSystemInfoEntry 12 }

		
--     1.3.6.1.4.1.10428 9 1.101.2.11.1.1.1.13
-- 1.3.6.1.4.1.10428 9 1.101.2.11.1.1.1.13
-- 1.3.6.1.4.1.10428 9 1.101.2.11.1.1.1.13
-- 1.3.6.1.4.1.10428 9 1.101.2.11.1.1.1.13
		-- 1.3.6.1.4.1.10428 9 1.101.2.11.1.1.1.13
		fkSlotSystemMemoryFree OBJECT-TYPE
			SYNTAX Gauge32
			MAX-ACCESS read-only
			STATUS current
			DESCRIPTION
				"The freed memory size (unit: kb)"
			::= { fkSlotSystemInfoEntry 13 }

		
--     1.3.6.1.4.1.10428 9 1.101.2.11.1.1.1.14
-- 1.3.6.1.4.1.10428 9 1.101.2.11.1.1.1.14
-- 1.3.6.1.4.1.10428 9 1.101.2.11.1.1.1.14
-- 1.3.6.1.4.1.10428 9 1.101.2.11.1.1.1.14
		-- 1.3.6.1.4.1.10428 9 1.101.2.11.1.1.1.14
		fkSlotSystemMemoryShared OBJECT-TYPE
			SYNTAX Gauge32
			MAX-ACCESS read-only
			STATUS current
			DESCRIPTION
				"The shared memory size (unit: kb)"
			::= { fkSlotSystemInfoEntry 14 }

		
--     1.3.6.1.4.1.10428 9 1.101.2.11.1.1.1.15
-- 1.3.6.1.4.1.10428 9 1.101.2.11.1.1.1.15
-- 1.3.6.1.4.1.10428 9 1.101.2.11.1.1.1.15
-- 1.3.6.1.4.1.10428 9 1.101.2.11.1.1.1.15
		-- 1.3.6.1.4.1.10428 9 1.101.2.11.1.1.1.15
		fkSlotSystemMemoryBuffers OBJECT-TYPE
			SYNTAX Gauge32
			MAX-ACCESS read-only
			STATUS current
			DESCRIPTION
				"The buffer size (unit: kb)"
			::= { fkSlotSystemInfoEntry 15 }

		
--     1.3.6.1.4.1.10428 9 1.101.2.11.1.1.1.16
-- 1.3.6.1.4.1.10428 9 1.101.2.11.1.1.1.16
-- 1.3.6.1.4.1.10428 9 1.101.2.11.1.1.1.16
-- 1.3.6.1.4.1.10428 9 1.101.2.11.1.1.1.16
		-- 1.3.6.1.4.1.10428 9 1.101.2.11.1.1.1.16
		fkSlotSystemMemoryCached OBJECT-TYPE
			SYNTAX Gauge32
			MAX-ACCESS read-only
			STATUS current
			DESCRIPTION
				"The cached memory size (unit: kb)"
			::= { fkSlotSystemInfoEntry 16 }

		
--     1.3.6.1.4.1.10428 9 1.101.2.11.1.1.1.17
-- 1.3.6.1.4.1.10428 9 1.101.2.11.1.1.1.17
-- 1.3.6.1.4.1.10428 9 1.101.2.11.1.1.1.17
-- 1.3.6.1.4.1.10428 9 1.101.2.11.1.1.1.17
		-- 1.3.6.1.4.1.10428 9 1.101.2.11.1.1.1.17
		fkSlotSystemMemorySwapTotal OBJECT-TYPE
			SYNTAX Gauge32
			MAX-ACCESS read-only
			STATUS current
			DESCRIPTION
				"The total swap memory size (unit: kb)"
			::= { fkSlotSystemInfoEntry 17 }

		
--     1.3.6.1.4.1.10428 9 1.101.2.11.1.1.1.18
-- 1.3.6.1.4.1.10428 9 1.101.2.11.1.1.1.18
-- 1.3.6.1.4.1.10428 9 1.101.2.11.1.1.1.18
-- 1.3.6.1.4.1.10428 9 1.101.2.11.1.1.1.18
		-- 1.3.6.1.4.1.10428 9 1.101.2.11.1.1.1.18
		fkSlotSystemMemorySwapFree OBJECT-TYPE
			SYNTAX Gauge32
			MAX-ACCESS read-only
			STATUS current
			DESCRIPTION
				"The freed swap memory size (unit: kb)"
			::= { fkSlotSystemInfoEntry 18 }

		
--     1.3.6.1.4.1.10428 9 1.101.2.11.1.1.1.19
-- 1.3.6.1.4.1.10428 9 1.101.2.11.1.1.1.19
-- 1.3.6.1.4.1.10428 9 1.101.2.11.1.1.1.19
-- 1.3.6.1.4.1.10428 9 1.101.2.11.1.1.1.19
		-- 1.3.6.1.4.1.10428 9 1.101.2.11.1.1.1.19
		fkSlotSystemBootReason OBJECT-TYPE
			SYNTAX INTEGER
				{
				powerBoot(1),
				powerBootByLocal(2),
				hwResetBySW(3),
				hardWdogByLocal(4),
				hwRebootByMate(5),
				hwRebootBySwitchover(6),
				swReboot(10),
				swRebootByLocal(11),
				swRebootBySFU(12),
				swRebootBySwitchover(13),
				swRebootByPanic(14),
				watchdog(20),
				watchdogByLocal(21),
				swWatchdog(30),
				swWatchdogByCpuOver(31),
				swWatchdogByMemoryLow(32),
				error(255)
				}
			MAX-ACCESS read-only
			STATUS current
			DESCRIPTION
				"The system slot boot reason."
			::= { fkSlotSystemInfoEntry 19 }

		
--     1.3.6.1.4.1.10428 9 1.101.2.11.1.1.1.20
-- 1.3.6.1.4.1.10428 9 1.101.2.11.1.1.1.20
-- 1.3.6.1.4.1.10428 9 1.101.2.11.1.1.1.20
-- 1.3.6.1.4.1.10428 9 1.101.2.11.1.1.1.20
		-- 1.3.6.1.4.1.10428 9 1.101.2.11.1.1.1.20
		fkSlotSystemBootTime OBJECT-TYPE
			SYNTAX Gauge32
			UNITS "1 second"
			MAX-ACCESS read-only
			STATUS current
			DESCRIPTION
				"The system slot boot time.
				The time since the Epoch (00:00:00 UTC, January 1, 1970), measured in seconds.
				"
			::= { fkSlotSystemInfoEntry 20 }

		
--     1.3.6.1.4.1.10428 9 1.101.2.11.1.1.1.21
-- 1.3.6.1.4.1.10428 9 1.101.2.11.1.1.1.21
-- 1.3.6.1.4.1.10428 9 1.101.2.11.1.1.1.21
-- 1.3.6.1.4.1.10428 9 1.101.2.11.1.1.1.21
		-- 1.3.6.1.4.1.10428 9 1.101.2.11.1.1.1.21
		fkSlotSystemVoltage OBJECT-TYPE
			SYNTAX Gauge32
			UNITS "0.1 v"
			MAX-ACCESS read-only
			STATUS current
			DESCRIPTION
				"The system slot voltage."
			::= { fkSlotSystemInfoEntry 21 }

		
--     1.3.6.1.4.1.10428 9 1.101.2.11.1.1.1.22
-- 1.3.6.1.4.1.10428 9 1.101.2.11.1.1.1.22
-- 1.3.6.1.4.1.10428 9 1.101.2.11.1.1.1.22
-- 1.3.6.1.4.1.10428 9 1.101.2.11.1.1.1.22
		-- 1.3.6.1.4.1.10428 9 1.101.2.11.1.1.1.22
		fkSlotSystemPowerLevelStatus OBJECT-TYPE
			SYNTAX INTEGER
				{
				good(1),
				bad(2)
				}
			MAX-ACCESS read-only
			STATUS current
			DESCRIPTION
				"PCB Power level status."
			::= { fkSlotSystemInfoEntry 22 }

		
--     1.3.6.1.4.1.10428 9 1.101.2.11.1.1.1.23
-- 1.3.6.1.4.1.10428 9 1.101.2.11.1.1.1.23
-- 1.3.6.1.4.1.10428 9 1.101.2.11.1.1.1.23
-- 1.3.6.1.4.1.10428 9 1.101.2.11.1.1.1.23
		-- 1.3.6.1.4.1.10428 9 1.101.2.11.1.1.1.23
		fkSlotSystemInfoLEDStatus OBJECT-TYPE
			SYNTAX BITS
				{
				pwr(0),
				run(1),
				critical(2),
				major(3),
				minor(4),
				error(5)
				}
			MAX-ACCESS read-only
			STATUS current
			DESCRIPTION
				"The LED status of each slot."
			::= { fkSlotSystemInfoEntry 23 }

		
--     1.3.6.1.4.1.10428 9 1.101.2.11.1.1.1.24
-- 1.3.6.1.4.1.10428 9 1.101.2.11.1.1.1.24
-- 1.3.6.1.4.1.10428 9 1.101.2.11.1.1.1.24
-- 1.3.6.1.4.1.10428 9 1.101.2.11.1.1.1.24
		-- 1.3.6.1.4.1.10428 9 1.101.2.11.1.1.1.24
		fkSlotSystemInfoPackageVersion OBJECT-TYPE
			SYNTAX OCTET STRING
			MAX-ACCESS read-only
			STATUS current
			DESCRIPTION
				"The applied package revision."
			::= { fkSlotSystemInfoEntry 24 }

		
--     1.3.6.1.4.1.10428 9 1.101.2.11.1.2
-- 1.3.6.1.4.1.10428 9 1.101.2.11.1.2
-- 1.3.6.1.4.1.10428 9 1.101.2.11.1.2
-- 1.3.6.1.4.1.10428 9 1.101.2.11.1.2
		-- 1.3.6.1.4.1.10428 9 1.101.2.11.1.2
		fkSlotSystemControl OBJECT IDENTIFIER ::= { fkSlotSystemInfo 2 }

		
--     1.3.6.1.4.1.10428 9 1.101.2.11.1.2.1
-- 1.3.6.1.4.1.10428 9 1.101.2.11.1.2.1
-- 1.3.6.1.4.1.10428 9 1.101.2.11.1.2.1
-- 1.3.6.1.4.1.10428 9 1.101.2.11.1.2.1
		-- 1.3.6.1.4.1.10428 9 1.101.2.11.1.2.1
		fkSlotSystemControlRequest OBJECT-TYPE
			SYNTAX INTEGER { setSlotRestart(1) }
			MAX-ACCESS read-write
			STATUS current
			DESCRIPTION
				"The request of a user command"
			::= { fkSlotSystemControl 1 }

		
--     1.3.6.1.4.1.10428 9 1.101.2.11.1.2.2
-- 1.3.6.1.4.1.10428 9 1.101.2.11.1.2.2
-- 1.3.6.1.4.1.10428 9 1.101.2.11.1.2.2
-- 1.3.6.1.4.1.10428 9 1.101.2.11.1.2.2
		-- 1.3.6.1.4.1.10428 9 1.101.2.11.1.2.2
		fkSlotSystemControlStatus OBJECT-TYPE
			SYNTAX FkControlStatusType
			MAX-ACCESS read-only
			STATUS current
			DESCRIPTION
				"The status of user command"
			::= { fkSlotSystemControl 2 }

		
--     1.3.6.1.4.1.10428 9 1.101.2.11.1.2.3
-- 1.3.6.1.4.1.10428 9 1.101.2.11.1.2.3
-- 1.3.6.1.4.1.10428 9 1.101.2.11.1.2.3
-- 1.3.6.1.4.1.10428 9 1.101.2.11.1.2.3
		-- 1.3.6.1.4.1.10428 9 1.101.2.11.1.2.3
		fkSlotSystemControlTimer OBJECT-TYPE
			SYNTAX Gauge32
			MAX-ACCESS read-write
			STATUS current
			DESCRIPTION
				"The maximum time for the manager for a long running user command"
			::= { fkSlotSystemControl 3 }

		
--     1.3.6.1.4.1.10428 9 1.101.2.11.1.2.4
-- 1.3.6.1.4.1.10428 9 1.101.2.11.1.2.4
-- 1.3.6.1.4.1.10428 9 1.101.2.11.1.2.4
-- 1.3.6.1.4.1.10428 9 1.101.2.11.1.2.4
		-- 1.3.6.1.4.1.10428 9 1.101.2.11.1.2.4
		fkSlotSystemControlTimeStamp OBJECT-TYPE
			SYNTAX TimeTicks
			MAX-ACCESS read-only
			STATUS current
			DESCRIPTION
				"The time stamp of the last command(end of command)"
			::= { fkSlotSystemControl 4 }

		
--     1.3.6.1.4.1.10428 9 1.101.2.11.1.2.5
-- 1.3.6.1.4.1.10428 9 1.101.2.11.1.2.5
-- 1.3.6.1.4.1.10428 9 1.101.2.11.1.2.5
-- 1.3.6.1.4.1.10428 9 1.101.2.11.1.2.5
		-- 1.3.6.1.4.1.10428 9 1.101.2.11.1.2.5
		fkSlotSystemControlReqResult OBJECT-TYPE
			SYNTAX FkControlRequestResultType
			MAX-ACCESS read-only
			STATUS current
			DESCRIPTION
				"The result of the last user command"
			::= { fkSlotSystemControl 5 }

		
--     1.3.6.1.4.1.10428 9 1.101.2.11.1.2.6
-- 1.3.6.1.4.1.10428 9 1.101.2.11.1.2.6
-- 1.3.6.1.4.1.10428 9 1.101.2.11.1.2.6
-- 1.3.6.1.4.1.10428 9 1.101.2.11.1.2.6
		-- 1.3.6.1.4.1.10428 9 1.101.2.11.1.2.6
		fkSlotSystemControlSlotIndex OBJECT-TYPE
			SYNTAX Integer32
			MAX-ACCESS read-write
			STATUS current
			DESCRIPTION
				"The system slot index."
			::= { fkSlotSystemControl 6 }

		
--     1.3.6.1.4.1.10428 9 1.101.2.11.1.3
-- 1.3.6.1.4.1.10428 9 1.101.2.11.1.3
-- 1.3.6.1.4.1.10428 9 1.101.2.11.1.3
-- 1.3.6.1.4.1.10428 9 1.101.2.11.1.3
		-- 1.3.6.1.4.1.10428 9 1.101.2.11.1.3
		fkSlotSystemNotification OBJECT IDENTIFIER ::= { fkSlotSystemInfo 3 }

		
--     1.3.6.1.4.1.10428 9 1.101.2.11.1.3.1
-- 1.3.6.1.4.1.10428 9 1.101.2.11.1.3.1
-- 1.3.6.1.4.1.10428 9 1.101.2.11.1.3.1
-- 1.3.6.1.4.1.10428 9 1.101.2.11.1.3.1
		-- 1.3.6.1.4.1.10428 9 1.101.2.11.1.3.1
		fkSlotSystemRestart NOTIFICATION-TYPE
			OBJECTS { fkSlotSystemControlRequest, fkSlotSystemControlTimeStamp, fkSlotSystemControlReqResult, fkSlotSystemControlSlotIndex }
			STATUS current
			DESCRIPTION 
				"Description."
			::= { fkSlotSystemNotification 1 }

		
--     1.3.6.1.4.1.10428 9 1.101.2.11.2
-- 1.3.6.1.4.1.10428 9 1.101.2.11.2
-- 1.3.6.1.4.1.10428 9 1.101.2.11.2
-- 1.3.6.1.4.1.10428 9 1.101.2.11.2
		-- 1.3.6.1.4.1.10428 9 1.101.2.11.2
		fkSlotStatusInfo OBJECT IDENTIFIER ::= { fkSlot 2 }

		
--     1.3.6.1.4.1.10428 9 1.101.2.11.2.1
-- 1.3.6.1.4.1.10428 9 1.101.2.11.2.1
-- 1.3.6.1.4.1.10428 9 1.101.2.11.2.1
-- 1.3.6.1.4.1.10428 9 1.101.2.11.2.1
		-- 1.3.6.1.4.1.10428 9 1.101.2.11.2.1
		fkSlotStatusInfoTable OBJECT-TYPE
			SYNTAX SEQUENCE OF FkSlotStatusInfoEntry
			MAX-ACCESS not-accessible
			STATUS current
			DESCRIPTION
				"Description."
			::= { fkSlotStatusInfo 1 }

		
--     1.3.6.1.4.1.10428 9 1.101.2.11.2.1.1
-- 1.3.6.1.4.1.10428 9 1.101.2.11.2.1.1
-- 1.3.6.1.4.1.10428 9 1.101.2.11.2.1.1
-- 1.3.6.1.4.1.10428 9 1.101.2.11.2.1.1
		-- 1.3.6.1.4.1.10428 9 1.101.2.11.2.1.1
		fkSlotStatusInfoEntry OBJECT-TYPE
			SYNTAX FkSlotStatusInfoEntry
			MAX-ACCESS not-accessible
			STATUS current
			DESCRIPTION
				"Description."
			INDEX { fkSlotSystemIndex }
			::= { fkSlotStatusInfoTable 1 }

		
		FkSlotStatusInfoEntry ::=
			SEQUENCE { 
				fkSlotStatusPlan
					INTEGER,
				fkSlotStatusPlanCardType
					INTEGER,
				fkSlotStatusCurrentInstall
					INTEGER,
				fkSlotStatusCurrentInstallCardType
					INTEGER,
				fkSlotStatusCardOperation
					INTEGER,
				fkSlotStatusLock
					INTEGER,
				fkSlotStatusUpgradeMode
					INTEGER,
				fkSlotStatusActionEvent
					INTEGER,
				fkSlotStatusState
					INTEGER,
				fkSlotStatusPower
					INTEGER,
				fkSlotStatusSerialNumber
					OCTET STRING
			 }

--     1.3.6.1.4.1.10428 9 1.101.2.11.2.1.1.1
-- 1.3.6.1.4.1.10428 9 1.101.2.11.2.1.1.1
-- 1.3.6.1.4.1.10428 9 1.101.2.11.2.1.1.1
-- 1.3.6.1.4.1.10428 9 1.101.2.11.2.1.1.1
		-- 1.3.6.1.4.1.10428 9 1.101.2.11.2.1.1.1
		fkSlotStatusPlan OBJECT-TYPE
			SYNTAX INTEGER
				{
				notPlanned(1),
				planned(2)
				}
			MAX-ACCESS read-only
			STATUS current
			DESCRIPTION
				"Planning status of slot."
			::= { fkSlotStatusInfoEntry 1 }

		
--     1.3.6.1.4.1.10428 9 1.101.2.11.2.1.1.2
-- 1.3.6.1.4.1.10428 9 1.101.2.11.2.1.1.2
-- 1.3.6.1.4.1.10428 9 1.101.2.11.2.1.1.2
-- 1.3.6.1.4.1.10428 9 1.101.2.11.2.1.1.2
		-- 1.3.6.1.4.1.10428 9 1.101.2.11.2.1.1.2
		fkSlotStatusPlanCardType OBJECT-TYPE
			SYNTAX INTEGER
				{
				unknown(1),
				siuGE12(2),
				siuEPON12(3),
				siuGPON4(4),
				niuGE12(5),
				sfu(6),
				v5548gGE12(7),
				siuGPON4r(8),
				niuGE8(9),
				siuGE4(10),
				niu10GPlus(11),
				iu10GE(12),
				iuGE6(13),
				iuGE4(14),
				siuTDM(15),
				siuGE24(16),
				siuFE48(17),
				niu10GE2(18),
				siu10GE48(19),
				siuGE10(20),
				niu10Ge2Plus(21),
				iuGT4(22),
				iuGT6(23),
				iuTDM6(24),
				siuGE6(25),
				siuGE8(26),
				siuGT6(27),
				niuGE2(28),
				niuGE4(29),
				iuGEPON4(30)
				}
			MAX-ACCESS read-only
			STATUS current
			DESCRIPTION
				"Planning card type status of slot."
			::= { fkSlotStatusInfoEntry 2 }

		
--     1.3.6.1.4.1.10428 9 1.101.2.11.2.1.1.3
-- 1.3.6.1.4.1.10428 9 1.101.2.11.2.1.1.3
-- 1.3.6.1.4.1.10428 9 1.101.2.11.2.1.1.3
-- 1.3.6.1.4.1.10428 9 1.101.2.11.2.1.1.3
		-- 1.3.6.1.4.1.10428 9 1.101.2.11.2.1.1.3
		fkSlotStatusCurrentInstall OBJECT-TYPE
			SYNTAX INTEGER
				{
				notInstalled(1),
				installed(2),
				failed(3)
				}
			MAX-ACCESS read-only
			STATUS current
			DESCRIPTION
				"Currently installation status of slot."
			::= { fkSlotStatusInfoEntry 3 }

		
--     1.3.6.1.4.1.10428 9 1.101.2.11.2.1.1.4
-- 1.3.6.1.4.1.10428 9 1.101.2.11.2.1.1.4
-- 1.3.6.1.4.1.10428 9 1.101.2.11.2.1.1.4
-- 1.3.6.1.4.1.10428 9 1.101.2.11.2.1.1.4
		-- 1.3.6.1.4.1.10428 9 1.101.2.11.2.1.1.4
		fkSlotStatusCurrentInstallCardType OBJECT-TYPE
			SYNTAX INTEGER
				{
				unknown(1),
				siuGE12(2),
				siuEPON12(3),
				siuGPON4(4),
				niuGE12(5),
				sfu(6),
				v5548gGE12(7),
				siuGPON4r(8),
				niuGE8(9),
				siuGE4(10),
				niu10GPlus(11),
				iuGE10(12),
				iuGE6(13),
				iuGE4(14),
				siuTDM(15),
				siuGE24(16),
				siuFE48(17),
				niu10GE2(18),
				siu10GE48(19),
				siuGE10(20),
				niu10Ge2Plus(21),
				iuGT4(22),
				iuGT6(23),
				iuTDM6(24),
				siuGE6(25),
				siuGE8(26),
				siuGT6(27),
				niuGE2(28),
				niuGE4(29),
				iuGEPON4(30)
				}
			MAX-ACCESS read-only
			STATUS current
			DESCRIPTION
				"Currently installation card type status of slot."
			::= { fkSlotStatusInfoEntry 4 }

		
--     1.3.6.1.4.1.10428 9 1.101.2.11.2.1.1.5
-- 1.3.6.1.4.1.10428 9 1.101.2.11.2.1.1.5
-- 1.3.6.1.4.1.10428 9 1.101.2.11.2.1.1.5
-- 1.3.6.1.4.1.10428 9 1.101.2.11.2.1.1.5
		-- 1.3.6.1.4.1.10428 9 1.101.2.11.2.1.1.5
		fkSlotStatusCardOperation OBJECT-TYPE
			SYNTAX INTEGER
				{
				disable(1),
				init(2),
				enable(3),
				enableActive(4),
				enableStandby(5)
				}
			MAX-ACCESS read-only
			STATUS current
			DESCRIPTION
				"Currently operation status of slot."
			::= { fkSlotStatusInfoEntry 5 }

		
--     1.3.6.1.4.1.10428 9 1.101.2.11.2.1.1.6
-- 1.3.6.1.4.1.10428 9 1.101.2.11.2.1.1.6
-- 1.3.6.1.4.1.10428 9 1.101.2.11.2.1.1.6
-- 1.3.6.1.4.1.10428 9 1.101.2.11.2.1.1.6
		-- 1.3.6.1.4.1.10428 9 1.101.2.11.2.1.1.6
		fkSlotStatusLock OBJECT-TYPE
			SYNTAX INTEGER
				{
				unlocked(1),
				locked(2)
				}
			MAX-ACCESS read-only
			STATUS current
			DESCRIPTION
				"Lock status of slot."
			::= { fkSlotStatusInfoEntry 6 }

		
--     1.3.6.1.4.1.10428 9 1.101.2.11.2.1.1.7
-- 1.3.6.1.4.1.10428 9 1.101.2.11.2.1.1.7
-- 1.3.6.1.4.1.10428 9 1.101.2.11.2.1.1.7
-- 1.3.6.1.4.1.10428 9 1.101.2.11.2.1.1.7
		-- 1.3.6.1.4.1.10428 9 1.101.2.11.2.1.1.7
		fkSlotStatusUpgradeMode OBJECT-TYPE
			SYNTAX INTEGER
				{
				manual(1),
				auto(2)
				}
			MAX-ACCESS read-only
			STATUS current
			DESCRIPTION
				"Upgrade mode status of slot."
			::= { fkSlotStatusInfoEntry 7 }

		
--     1.3.6.1.4.1.10428 9 1.101.2.11.2.1.1.8
-- 1.3.6.1.4.1.10428 9 1.101.2.11.2.1.1.8
-- 1.3.6.1.4.1.10428 9 1.101.2.11.2.1.1.8
-- 1.3.6.1.4.1.10428 9 1.101.2.11.2.1.1.8
		-- 1.3.6.1.4.1.10428 9 1.101.2.11.2.1.1.8
		fkSlotStatusActionEvent OBJECT-TYPE
			SYNTAX INTEGER
				{
				uninstallAction(1),
				installAction(2),
				noPlanningAction(3),
				planningAction(4),
				lockAction(5),
				unlockAction(6),
				matchedEvent(7),
				unMatchedEvent(8),
				bootEndEvent(9),
				configEndEvent(10),
				configFailEvent(11)
				}
			MAX-ACCESS accessible-for-notify
			STATUS current
			DESCRIPTION
				"Event of slot. (accessible-for-notify)"
			::= { fkSlotStatusInfoEntry 8 }

		
--     1.3.6.1.4.1.10428 9 1.101.2.11.2.1.1.9
-- 1.3.6.1.4.1.10428 9 1.101.2.11.2.1.1.9
-- 1.3.6.1.4.1.10428 9 1.101.2.11.2.1.1.9
-- 1.3.6.1.4.1.10428 9 1.101.2.11.2.1.1.9
		-- 1.3.6.1.4.1.10428 9 1.101.2.11.2.1.1.9
		fkSlotStatusState OBJECT-TYPE
			SYNTAX INTEGER
				{
				default(1),
				planningWait(2),
				installWait(3),
				operationReady(4),
				actionBootReady(5),
				actionConfig(6),
				actionEnableReady(7),
				actionEnable(8),
				actionEnableLock(9),
				actionDisable(10)
				}
			MAX-ACCESS accessible-for-notify
			STATUS current
			DESCRIPTION
				"Status of slot. (accessible-for-notify)"
			::= { fkSlotStatusInfoEntry 9 }

		
--     1.3.6.1.4.1.10428 9 1.101.2.11.2.1.1.10
-- 1.3.6.1.4.1.10428 9 1.101.2.11.2.1.1.10
-- 1.3.6.1.4.1.10428 9 1.101.2.11.2.1.1.10
-- 1.3.6.1.4.1.10428 9 1.101.2.11.2.1.1.10
		-- 1.3.6.1.4.1.10428 9 1.101.2.11.2.1.1.10
		fkSlotStatusPower OBJECT-TYPE
			SYNTAX INTEGER
				{
				up(1),
				down(2)
				}
			MAX-ACCESS read-only
			STATUS current
			DESCRIPTION
				"Currently power status of slot."
			::= { fkSlotStatusInfoEntry 10 }

		
--     1.3.6.1.4.1.10428 9 1.101.2.11.2.1.1.11
-- 1.3.6.1.4.1.10428 9 1.101.2.11.2.1.1.11
-- 1.3.6.1.4.1.10428 9 1.101.2.11.2.1.1.11
-- 1.3.6.1.4.1.10428 9 1.101.2.11.2.1.1.11
		-- 1.3.6.1.4.1.10428 9 1.101.2.11.2.1.1.11
		fkSlotStatusSerialNumber OBJECT-TYPE
			SYNTAX OCTET STRING
			MAX-ACCESS read-only
			STATUS current
			DESCRIPTION
				"The serial number"
			::= { fkSlotStatusInfoEntry 11 }

		
--     1.3.6.1.4.1.10428 9 1.101.2.11.2.2
-- 1.3.6.1.4.1.10428 9 1.101.2.11.2.2
-- 1.3.6.1.4.1.10428 9 1.101.2.11.2.2
-- 1.3.6.1.4.1.10428 9 1.101.2.11.2.2
		-- 1.3.6.1.4.1.10428 9 1.101.2.11.2.2
		fkSlotStatusControl OBJECT IDENTIFIER ::= { fkSlotStatusInfo 2 }

		
--     1.3.6.1.4.1.10428 9 1.101.2.11.2.2.1
-- 1.3.6.1.4.1.10428 9 1.101.2.11.2.2.1
-- 1.3.6.1.4.1.10428 9 1.101.2.11.2.2.1
-- 1.3.6.1.4.1.10428 9 1.101.2.11.2.2.1
		-- 1.3.6.1.4.1.10428 9 1.101.2.11.2.2.1
		fkSlotStatusControlRequest OBJECT-TYPE
			SYNTAX INTEGER
				{
				setSlotLock(1),
				setSlotUnlock(2),
				setSlotPlanning(3),
				setSlotNoplanning(4),
				setSlotUpgradeMode(5),
				setSlotPowerUp(6),
				setSlotPowerDown(7),
				setSlotPowerReset(8)
				}
			MAX-ACCESS read-write
			STATUS current
			DESCRIPTION
				"The request of a user command"
			::= { fkSlotStatusControl 1 }

		
--     1.3.6.1.4.1.10428 9 1.101.2.11.2.2.2
-- 1.3.6.1.4.1.10428 9 1.101.2.11.2.2.2
-- 1.3.6.1.4.1.10428 9 1.101.2.11.2.2.2
-- 1.3.6.1.4.1.10428 9 1.101.2.11.2.2.2
		-- 1.3.6.1.4.1.10428 9 1.101.2.11.2.2.2
		fkSlotStatusControlStatus OBJECT-TYPE
			SYNTAX FkControlStatusType
			MAX-ACCESS read-only
			STATUS current
			DESCRIPTION
				"The status of user command"
			::= { fkSlotStatusControl 2 }

		
--     1.3.6.1.4.1.10428 9 1.101.2.11.2.2.3
-- 1.3.6.1.4.1.10428 9 1.101.2.11.2.2.3
-- 1.3.6.1.4.1.10428 9 1.101.2.11.2.2.3
-- 1.3.6.1.4.1.10428 9 1.101.2.11.2.2.3
		-- 1.3.6.1.4.1.10428 9 1.101.2.11.2.2.3
		fkSlotStatusControlTimer OBJECT-TYPE
			SYNTAX Gauge32
			MAX-ACCESS read-write
			STATUS current
			DESCRIPTION
				"The maximum time for the manager for a long running user command"
			::= { fkSlotStatusControl 3 }

		
--     1.3.6.1.4.1.10428 9 1.101.2.11.2.2.4
-- 1.3.6.1.4.1.10428 9 1.101.2.11.2.2.4
-- 1.3.6.1.4.1.10428 9 1.101.2.11.2.2.4
-- 1.3.6.1.4.1.10428 9 1.101.2.11.2.2.4
		-- 1.3.6.1.4.1.10428 9 1.101.2.11.2.2.4
		fkSlotStatusControlTimeStamp OBJECT-TYPE
			SYNTAX TimeTicks
			MAX-ACCESS read-only
			STATUS current
			DESCRIPTION
				"The time stamp of the last command(end of command)"
			::= { fkSlotStatusControl 4 }

		
--     1.3.6.1.4.1.10428 9 1.101.2.11.2.2.5
-- 1.3.6.1.4.1.10428 9 1.101.2.11.2.2.5
-- 1.3.6.1.4.1.10428 9 1.101.2.11.2.2.5
-- 1.3.6.1.4.1.10428 9 1.101.2.11.2.2.5
		-- 1.3.6.1.4.1.10428 9 1.101.2.11.2.2.5
		fkSlotStatusControlReqResult OBJECT-TYPE
			SYNTAX FkControlRequestResultType
			MAX-ACCESS read-only
			STATUS current
			DESCRIPTION
				"The result of the last user command"
			::= { fkSlotStatusControl 5 }

		
--     1.3.6.1.4.1.10428 9 1.101.2.11.2.2.6
-- 1.3.6.1.4.1.10428 9 1.101.2.11.2.2.6
-- 1.3.6.1.4.1.10428 9 1.101.2.11.2.2.6
-- 1.3.6.1.4.1.10428 9 1.101.2.11.2.2.6
		-- 1.3.6.1.4.1.10428 9 1.101.2.11.2.2.6
		fkSlotStatusControlSlotIndex OBJECT-TYPE
			SYNTAX Integer32
			MAX-ACCESS read-write
			STATUS current
			DESCRIPTION
				"The system slot index.
				255 is means all slot."
			::= { fkSlotStatusControl 6 }

		
--     1.3.6.1.4.1.10428 9 1.101.2.11.2.2.7
-- 1.3.6.1.4.1.10428 9 1.101.2.11.2.2.7
-- 1.3.6.1.4.1.10428 9 1.101.2.11.2.2.7
-- 1.3.6.1.4.1.10428 9 1.101.2.11.2.2.7
		-- 1.3.6.1.4.1.10428 9 1.101.2.11.2.2.7
		fkSlotStatusControlPlanCardType OBJECT-TYPE
			SYNTAX INTEGER
				{
				unknown(1),
				siuGE12(2),
				siuEPON12(3),
				siuGPON4(4),
				niuGE12(5),
				sfu(6),
				v5548gGE12(7),
				siuGPON4r(8),
				niuGE8(9),
				siuGE4(10),
				niu10GPlus(11),
				iuGE10(12),
				iuGE6(13),
				iuGE4(14),
				siuTDM(15),
				siuGE24(16),
				siuFE48(17),
				niu10GE2(18),
				siu10GE48(19),
				siuGE10(20),
				niu10Ge2Plus(21),
				iuGT4(22),
				iuGT6(23),
				iuTDM6(24),
				siuGE6(25),
				siuGE8(26),
				siuGT6(27),
				niuGE2(28),
				niuGE4(29),
				iuGEPON4(30)
				}
			MAX-ACCESS read-write
			STATUS current
			DESCRIPTION
				"Planning card type status of slot."
			::= { fkSlotStatusControl 7 }

		
--     1.3.6.1.4.1.10428 9 1.101.2.11.2.2.8
-- 1.3.6.1.4.1.10428 9 1.101.2.11.2.2.8
-- 1.3.6.1.4.1.10428 9 1.101.2.11.2.2.8
-- 1.3.6.1.4.1.10428 9 1.101.2.11.2.2.8
		-- 1.3.6.1.4.1.10428 9 1.101.2.11.2.2.8
		fkSlotStatusControlUpgradeMode OBJECT-TYPE
			SYNTAX INTEGER
				{
				manual(1),
				auto(2)
				}
			MAX-ACCESS read-write
			STATUS current
			DESCRIPTION
				"Upgrade mode status of slot."
			::= { fkSlotStatusControl 8 }

		
--     1.3.6.1.4.1.10428 9 1.101.2.11.2.3
-- 1.3.6.1.4.1.10428 9 1.101.2.11.2.3
-- 1.3.6.1.4.1.10428 9 1.101.2.11.2.3
-- 1.3.6.1.4.1.10428 9 1.101.2.11.2.3
		-- 1.3.6.1.4.1.10428 9 1.101.2.11.2.3
		fkSlotStatusNotification OBJECT IDENTIFIER ::= { fkSlotStatusInfo 3 }

		
--     1.3.6.1.4.1.10428 9 1.101.2.11.2.3.1
-- 1.3.6.1.4.1.10428 9 1.101.2.11.2.3.1
-- 1.3.6.1.4.1.10428 9 1.101.2.11.2.3.1
-- 1.3.6.1.4.1.10428 9 1.101.2.11.2.3.1
		-- 1.3.6.1.4.1.10428 9 1.101.2.11.2.3.1
		fkSlotStatusLocked NOTIFICATION-TYPE
			OBJECTS { fkSlotStatusControlRequest, fkSlotStatusControlTimeStamp, fkSlotStatusControlReqResult, fkSlotStatusControlSlotIndex }
			STATUS current
			DESCRIPTION 
				"Description."
			::= { fkSlotStatusNotification 1 }

		
--     1.3.6.1.4.1.10428 9 1.101.2.11.2.3.2
-- 1.3.6.1.4.1.10428 9 1.101.2.11.2.3.2
-- 1.3.6.1.4.1.10428 9 1.101.2.11.2.3.2
-- 1.3.6.1.4.1.10428 9 1.101.2.11.2.3.2
		-- 1.3.6.1.4.1.10428 9 1.101.2.11.2.3.2
		fkSlotStatusUnlocked NOTIFICATION-TYPE
			OBJECTS { fkSlotStatusControlRequest, fkSlotStatusControlTimeStamp, fkSlotStatusControlReqResult, fkSlotStatusControlSlotIndex }
			STATUS current
			DESCRIPTION 
				"Description."
			::= { fkSlotStatusNotification 2 }

		
--     1.3.6.1.4.1.10428 9 1.101.2.11.2.3.3
-- 1.3.6.1.4.1.10428 9 1.101.2.11.2.3.3
-- 1.3.6.1.4.1.10428 9 1.101.2.11.2.3.3
-- 1.3.6.1.4.1.10428 9 1.101.2.11.2.3.3
		-- 1.3.6.1.4.1.10428 9 1.101.2.11.2.3.3
		fkSlotStatusPlanning NOTIFICATION-TYPE
			OBJECTS { fkSlotStatusControlRequest, fkSlotStatusControlTimeStamp, fkSlotStatusControlReqResult, fkSlotStatusControlSlotIndex, fkSlotStatusControlPlanCardType
				 }
			STATUS current
			DESCRIPTION 
				"Description."
			::= { fkSlotStatusNotification 3 }

		
--     1.3.6.1.4.1.10428 9 1.101.2.11.2.3.4
-- 1.3.6.1.4.1.10428 9 1.101.2.11.2.3.4
-- 1.3.6.1.4.1.10428 9 1.101.2.11.2.3.4
-- 1.3.6.1.4.1.10428 9 1.101.2.11.2.3.4
		-- 1.3.6.1.4.1.10428 9 1.101.2.11.2.3.4
		fkSlotStatusNoPlanning NOTIFICATION-TYPE
			OBJECTS { fkSlotStatusControlRequest, fkSlotStatusControlTimeStamp, fkSlotStatusControlReqResult, fkSlotStatusControlSlotIndex }
			STATUS current
			DESCRIPTION 
				"Description."
			::= { fkSlotStatusNotification 4 }

		
--     1.3.6.1.4.1.10428 9 1.101.2.11.2.3.5
-- 1.3.6.1.4.1.10428 9 1.101.2.11.2.3.5
-- 1.3.6.1.4.1.10428 9 1.101.2.11.2.3.5
-- 1.3.6.1.4.1.10428 9 1.101.2.11.2.3.5
		-- 1.3.6.1.4.1.10428 9 1.101.2.11.2.3.5
		fkSlotStatusUpgradeModeChanged NOTIFICATION-TYPE
			OBJECTS { fkSlotStatusControlRequest, fkSlotStatusControlTimeStamp, fkSlotStatusControlReqResult, fkSlotStatusControlSlotIndex, fkSlotStatusControlUpgradeMode
				 }
			STATUS current
			DESCRIPTION 
				"Description."
			::= { fkSlotStatusNotification 5 }

		
--     1.3.6.1.4.1.10428 9 1.101.2.11.2.3.6
-- 1.3.6.1.4.1.10428 9 1.101.2.11.2.3.6
-- 1.3.6.1.4.1.10428 9 1.101.2.11.2.3.6
-- 1.3.6.1.4.1.10428 9 1.101.2.11.2.3.6
		-- 1.3.6.1.4.1.10428 9 1.101.2.11.2.3.6
		fkSlotStatusPowerUp NOTIFICATION-TYPE
			OBJECTS { fkSlotStatusControlRequest, fkSlotStatusControlTimeStamp, fkSlotStatusControlReqResult, fkSlotStatusControlSlotIndex }
			STATUS current
			DESCRIPTION 
				"Description."
			::= { fkSlotStatusNotification 6 }

		
--     1.3.6.1.4.1.10428 9 1.101.2.11.2.3.7
-- 1.3.6.1.4.1.10428 9 1.101.2.11.2.3.7
-- 1.3.6.1.4.1.10428 9 1.101.2.11.2.3.7
-- 1.3.6.1.4.1.10428 9 1.101.2.11.2.3.7
		-- 1.3.6.1.4.1.10428 9 1.101.2.11.2.3.7
		fkSlotStatusPowerDown NOTIFICATION-TYPE
			OBJECTS { fkSlotStatusControlRequest, fkSlotStatusControlTimeStamp, fkSlotStatusControlReqResult, fkSlotStatusControlSlotIndex }
			STATUS current
			DESCRIPTION 
				"Description."
			::= { fkSlotStatusNotification 7 }

		
--     1.3.6.1.4.1.10428 9 1.101.2.11.2.3.8
-- 1.3.6.1.4.1.10428 9 1.101.2.11.2.3.8
-- 1.3.6.1.4.1.10428 9 1.101.2.11.2.3.8
-- 1.3.6.1.4.1.10428 9 1.101.2.11.2.3.8
		-- 1.3.6.1.4.1.10428 9 1.101.2.11.2.3.8
		fkSlotStatusPowerReset NOTIFICATION-TYPE
			OBJECTS { fkSlotStatusControlRequest, fkSlotStatusControlTimeStamp, fkSlotStatusControlReqResult, fkSlotStatusControlSlotIndex }
			STATUS current
			DESCRIPTION 
				"Description."
			::= { fkSlotStatusNotification 8 }

		
--     1.3.6.1.4.1.10428 9 1.101.2.11.3
-- 1.3.6.1.4.1.10428 9 1.101.2.11.3
-- 1.3.6.1.4.1.10428 9 1.101.2.11.3
-- 1.3.6.1.4.1.10428 9 1.101.2.11.3
		-- 1.3.6.1.4.1.10428 9 1.101.2.11.3
		fkSlotNosInfo OBJECT IDENTIFIER ::= { fkSlot 3 }

		
--     1.3.6.1.4.1.10428 9 1.101.2.11.3.1
-- 1.3.6.1.4.1.10428 9 1.101.2.11.3.1
-- 1.3.6.1.4.1.10428 9 1.101.2.11.3.1
-- 1.3.6.1.4.1.10428 9 1.101.2.11.3.1
		-- 1.3.6.1.4.1.10428 9 1.101.2.11.3.1
		fkSlotNosInfoTable OBJECT-TYPE
			SYNTAX SEQUENCE OF FkSlotNosInfoEntry
			MAX-ACCESS not-accessible
			STATUS current
			DESCRIPTION
				"Description."
			::= { fkSlotNosInfo 1 }

		
--     1.3.6.1.4.1.10428 9 1.101.2.11.3.1.1
-- 1.3.6.1.4.1.10428 9 1.101.2.11.3.1.1
-- 1.3.6.1.4.1.10428 9 1.101.2.11.3.1.1
-- 1.3.6.1.4.1.10428 9 1.101.2.11.3.1.1
		-- 1.3.6.1.4.1.10428 9 1.101.2.11.3.1.1
		fkSlotNosInfoEntry OBJECT-TYPE
			SYNTAX FkSlotNosInfoEntry
			MAX-ACCESS not-accessible
			STATUS current
			DESCRIPTION
				"Description."
			INDEX { fkSlotSystemIndex }
			::= { fkSlotNosInfoTable 1 }

		
		FkSlotNosInfoEntry ::=
			SEQUENCE { 
				fkSlotNosVersion
					OCTET STRING,
				fkSlotNosRevision
					OCTET STRING,
				fkSlotNosSize
					Unsigned32,
				fkSlotNosUpgradeStatus
					INTEGER,
				fkSlotNosStbVersion
					OCTET STRING,
				fkSlotNosStbRevision
					OCTET STRING,
				fkSlotNosStbSize
					Unsigned32
			 }

--     1.3.6.1.4.1.10428 9 1.101.2.11.3.1.1.1
-- 1.3.6.1.4.1.10428 9 1.101.2.11.3.1.1.1
-- 1.3.6.1.4.1.10428 9 1.101.2.11.3.1.1.1
-- 1.3.6.1.4.1.10428 9 1.101.2.11.3.1.1.1
		-- 1.3.6.1.4.1.10428 9 1.101.2.11.3.1.1.1
		fkSlotNosVersion OBJECT-TYPE
			SYNTAX OCTET STRING
			MAX-ACCESS read-only
			STATUS current
			DESCRIPTION
				"NOS version of slot."
			::= { fkSlotNosInfoEntry 1 }

		
--     1.3.6.1.4.1.10428 9 1.101.2.11.3.1.1.2
-- 1.3.6.1.4.1.10428 9 1.101.2.11.3.1.1.2
-- 1.3.6.1.4.1.10428 9 1.101.2.11.3.1.1.2
-- 1.3.6.1.4.1.10428 9 1.101.2.11.3.1.1.2
		-- 1.3.6.1.4.1.10428 9 1.101.2.11.3.1.1.2
		fkSlotNosRevision OBJECT-TYPE
			SYNTAX OCTET STRING
			MAX-ACCESS read-only
			STATUS current
			DESCRIPTION
				"NOS revision of slot."
			::= { fkSlotNosInfoEntry 2 }

		
--     1.3.6.1.4.1.10428 9 1.101.2.11.3.1.1.3
-- 1.3.6.1.4.1.10428 9 1.101.2.11.3.1.1.3
-- 1.3.6.1.4.1.10428 9 1.101.2.11.3.1.1.3
-- 1.3.6.1.4.1.10428 9 1.101.2.11.3.1.1.3
		-- 1.3.6.1.4.1.10428 9 1.101.2.11.3.1.1.3
		fkSlotNosSize OBJECT-TYPE
			SYNTAX Unsigned32
			MAX-ACCESS read-only
			STATUS current
			DESCRIPTION
				"NOS size of slot."
			::= { fkSlotNosInfoEntry 3 }

		
--     1.3.6.1.4.1.10428 9 1.101.2.11.3.1.1.4
-- 1.3.6.1.4.1.10428 9 1.101.2.11.3.1.1.4
-- 1.3.6.1.4.1.10428 9 1.101.2.11.3.1.1.4
-- 1.3.6.1.4.1.10428 9 1.101.2.11.3.1.1.4
		-- 1.3.6.1.4.1.10428 9 1.101.2.11.3.1.1.4
		fkSlotNosUpgradeStatus OBJECT-TYPE
			SYNTAX INTEGER
				{
				upgradeIdle(1),
				upgradeStart(2),
				upgradeDone(3),
				upgradeFail(4)
				}
			MAX-ACCESS read-only
			STATUS current
			DESCRIPTION
				"NOS upgrade status of slot."
			::= { fkSlotNosInfoEntry 4 }

		
--     1.3.6.1.4.1.10428 9 1.101.2.11.3.1.1.5
-- 1.3.6.1.4.1.10428 9 1.101.2.11.3.1.1.5
-- 1.3.6.1.4.1.10428 9 1.101.2.11.3.1.1.5
-- 1.3.6.1.4.1.10428 9 1.101.2.11.3.1.1.5
		-- 1.3.6.1.4.1.10428 9 1.101.2.11.3.1.1.5
		fkSlotNosStbVersion OBJECT-TYPE
			SYNTAX OCTET STRING
			MAX-ACCESS read-only
			STATUS current
			DESCRIPTION
				"Stand by NOS version of slot"
			::= { fkSlotNosInfoEntry 5 }

		
--     1.3.6.1.4.1.10428 9 1.101.2.11.3.1.1.6
-- 1.3.6.1.4.1.10428 9 1.101.2.11.3.1.1.6
-- 1.3.6.1.4.1.10428 9 1.101.2.11.3.1.1.6
-- 1.3.6.1.4.1.10428 9 1.101.2.11.3.1.1.6
		-- 1.3.6.1.4.1.10428 9 1.101.2.11.3.1.1.6
		fkSlotNosStbRevision OBJECT-TYPE
			SYNTAX OCTET STRING
			MAX-ACCESS read-only
			STATUS current
			DESCRIPTION
				"Stand by NOS revision of slot."
			::= { fkSlotNosInfoEntry 6 }

		
--     1.3.6.1.4.1.10428 9 1.101.2.11.3.1.1.7
-- 1.3.6.1.4.1.10428 9 1.101.2.11.3.1.1.7
-- 1.3.6.1.4.1.10428 9 1.101.2.11.3.1.1.7
-- 1.3.6.1.4.1.10428 9 1.101.2.11.3.1.1.7
		-- 1.3.6.1.4.1.10428 9 1.101.2.11.3.1.1.7
		fkSlotNosStbSize OBJECT-TYPE
			SYNTAX Unsigned32
			MAX-ACCESS read-only
			STATUS current
			DESCRIPTION
				"Stand by NOS size of slot."
			::= { fkSlotNosInfoEntry 7 }

		
--     1.3.6.1.4.1.10428 9 1.101.2.11.3.2
-- 1.3.6.1.4.1.10428 9 1.101.2.11.3.2
-- 1.3.6.1.4.1.10428 9 1.101.2.11.3.2
-- 1.3.6.1.4.1.10428 9 1.101.2.11.3.2
		-- 1.3.6.1.4.1.10428 9 1.101.2.11.3.2
		fkSlotNosControl OBJECT IDENTIFIER ::= { fkSlotNosInfo 2 }

		
--     1.3.6.1.4.1.10428 9 1.101.2.11.3.2.1
-- 1.3.6.1.4.1.10428 9 1.101.2.11.3.2.1
-- 1.3.6.1.4.1.10428 9 1.101.2.11.3.2.1
-- 1.3.6.1.4.1.10428 9 1.101.2.11.3.2.1
		-- 1.3.6.1.4.1.10428 9 1.101.2.11.3.2.1
		fkSlotNosControlRequest OBJECT-TYPE
			SYNTAX INTEGER
				{
				setSlotUpgrade(1),
				downloadSlotNos(2),
				upgradeSlotBootloader(3)
				}
			MAX-ACCESS read-write
			STATUS current
			DESCRIPTION
				"The request of a user command"
			::= { fkSlotNosControl 1 }

		
--     1.3.6.1.4.1.10428 9 1.101.2.11.3.2.2
-- 1.3.6.1.4.1.10428 9 1.101.2.11.3.2.2
-- 1.3.6.1.4.1.10428 9 1.101.2.11.3.2.2
-- 1.3.6.1.4.1.10428 9 1.101.2.11.3.2.2
		-- 1.3.6.1.4.1.10428 9 1.101.2.11.3.2.2
		fkSlotNosControlStatus OBJECT-TYPE
			SYNTAX FkControlStatusType
			MAX-ACCESS read-only
			STATUS current
			DESCRIPTION
				"The status of user command"
			::= { fkSlotNosControl 2 }

		
--     1.3.6.1.4.1.10428 9 1.101.2.11.3.2.3
-- 1.3.6.1.4.1.10428 9 1.101.2.11.3.2.3
-- 1.3.6.1.4.1.10428 9 1.101.2.11.3.2.3
-- 1.3.6.1.4.1.10428 9 1.101.2.11.3.2.3
		-- 1.3.6.1.4.1.10428 9 1.101.2.11.3.2.3
		fkSlotNosControlTimer OBJECT-TYPE
			SYNTAX Gauge32
			MAX-ACCESS read-write
			STATUS current
			DESCRIPTION
				"The maximum time for the manager for a long running user command"
			::= { fkSlotNosControl 3 }

		
--     1.3.6.1.4.1.10428 9 1.101.2.11.3.2.4
-- 1.3.6.1.4.1.10428 9 1.101.2.11.3.2.4
-- 1.3.6.1.4.1.10428 9 1.101.2.11.3.2.4
-- 1.3.6.1.4.1.10428 9 1.101.2.11.3.2.4
		-- 1.3.6.1.4.1.10428 9 1.101.2.11.3.2.4
		fkSlotNosControlTimeStamp OBJECT-TYPE
			SYNTAX TimeTicks
			MAX-ACCESS read-only
			STATUS current
			DESCRIPTION
				"The time stamp of the last command(end of command)"
			::= { fkSlotNosControl 4 }

		
--     1.3.6.1.4.1.10428 9 1.101.2.11.3.2.5
-- 1.3.6.1.4.1.10428 9 1.101.2.11.3.2.5
-- 1.3.6.1.4.1.10428 9 1.101.2.11.3.2.5
-- 1.3.6.1.4.1.10428 9 1.101.2.11.3.2.5
		-- 1.3.6.1.4.1.10428 9 1.101.2.11.3.2.5
		fkSlotNosControlReqResult OBJECT-TYPE
			SYNTAX FkControlRequestResultType
			MAX-ACCESS read-only
			STATUS current
			DESCRIPTION
				"The result of the last user command"
			::= { fkSlotNosControl 5 }

		
--     1.3.6.1.4.1.10428 9 1.101.2.11.3.2.6
-- 1.3.6.1.4.1.10428 9 1.101.2.11.3.2.6
-- 1.3.6.1.4.1.10428 9 1.101.2.11.3.2.6
-- 1.3.6.1.4.1.10428 9 1.101.2.11.3.2.6
		-- 1.3.6.1.4.1.10428 9 1.101.2.11.3.2.6
		fkSlotNosControlSlotIndex OBJECT-TYPE
			SYNTAX Integer32
			MAX-ACCESS read-write
			STATUS current
			DESCRIPTION
				"The system slot index."
			::= { fkSlotNosControl 6 }

		
--     1.3.6.1.4.1.10428 9 1.101.2.11.3.2.7
-- 1.3.6.1.4.1.10428 9 1.101.2.11.3.2.7
-- 1.3.6.1.4.1.10428 9 1.101.2.11.3.2.7
-- 1.3.6.1.4.1.10428 9 1.101.2.11.3.2.7
		-- 1.3.6.1.4.1.10428 9 1.101.2.11.3.2.7
		fkSlotNosControlUpDownMethod OBJECT-TYPE
			SYNTAX INTEGER
				{
				ftp(1),
				tftp(2)
				}
			MAX-ACCESS read-write
			STATUS current
			DESCRIPTION
				"1: using FTP
				2: using TFTP
				"
			::= { fkSlotNosControl 7 }

		
--     1.3.6.1.4.1.10428 9 1.101.2.11.3.2.8
-- 1.3.6.1.4.1.10428 9 1.101.2.11.3.2.8
-- 1.3.6.1.4.1.10428 9 1.101.2.11.3.2.8
-- 1.3.6.1.4.1.10428 9 1.101.2.11.3.2.8
		-- 1.3.6.1.4.1.10428 9 1.101.2.11.3.2.8
		fkSlotNosControlUpDownFlag OBJECT-TYPE
			SYNTAX INTEGER
				{
				upload(1),
				download(2)
				}
			MAX-ACCESS read-write
			STATUS current
			DESCRIPTION
				"1. Uploading slot nos to the remote-host.
				2. Downloading slot nos from the remote-host."
			::= { fkSlotNosControl 8 }

		
--     1.3.6.1.4.1.10428 9 1.101.2.11.3.2.9
-- 1.3.6.1.4.1.10428 9 1.101.2.11.3.2.9
-- 1.3.6.1.4.1.10428 9 1.101.2.11.3.2.9
-- 1.3.6.1.4.1.10428 9 1.101.2.11.3.2.9
		-- 1.3.6.1.4.1.10428 9 1.101.2.11.3.2.9
		fkSlotNosControlServerAddress OBJECT-TYPE
			SYNTAX IpAddress
			MAX-ACCESS read-write
			STATUS current
			DESCRIPTION
				"The remote-host's IP address."
			::= { fkSlotNosControl 9 }

		
--     1.3.6.1.4.1.10428 9 1.101.2.11.3.2.10
-- 1.3.6.1.4.1.10428 9 1.101.2.11.3.2.10
-- 1.3.6.1.4.1.10428 9 1.101.2.11.3.2.10
-- 1.3.6.1.4.1.10428 9 1.101.2.11.3.2.10
		-- 1.3.6.1.4.1.10428 9 1.101.2.11.3.2.10
		fkSlotNosControlUserID OBJECT-TYPE
			SYNTAX OCTET STRING
			MAX-ACCESS read-write
			STATUS current
			DESCRIPTION
				"Account-name."
			::= { fkSlotNosControl 10 }

		
--     1.3.6.1.4.1.10428 9 1.101.2.11.3.2.11
-- 1.3.6.1.4.1.10428 9 1.101.2.11.3.2.11
-- 1.3.6.1.4.1.10428 9 1.101.2.11.3.2.11
-- 1.3.6.1.4.1.10428 9 1.101.2.11.3.2.11
		-- 1.3.6.1.4.1.10428 9 1.101.2.11.3.2.11
		fkSlotNosControlPassword OBJECT-TYPE
			SYNTAX OCTET STRING
			MAX-ACCESS read-write
			STATUS current
			DESCRIPTION
				"Account-password."
			::= { fkSlotNosControl 11 }

		
--     1.3.6.1.4.1.10428 9 1.101.2.11.3.2.12
-- 1.3.6.1.4.1.10428 9 1.101.2.11.3.2.12
-- 1.3.6.1.4.1.10428 9 1.101.2.11.3.2.12
-- 1.3.6.1.4.1.10428 9 1.101.2.11.3.2.12
		-- 1.3.6.1.4.1.10428 9 1.101.2.11.3.2.12
		fkSlotNosControlFileName OBJECT-TYPE
			SYNTAX OCTET STRING
			MAX-ACCESS read-write
			STATUS current
			DESCRIPTION
				"Slot nos file name."
			::= { fkSlotNosControl 12 }

		
--     1.3.6.1.4.1.10428 9 1.101.2.11.3.3
-- 1.3.6.1.4.1.10428 9 1.101.2.11.3.3
-- 1.3.6.1.4.1.10428 9 1.101.2.11.3.3
-- 1.3.6.1.4.1.10428 9 1.101.2.11.3.3
		-- 1.3.6.1.4.1.10428 9 1.101.2.11.3.3
		fkSlotNosNotification OBJECT IDENTIFIER ::= { fkSlotNosInfo 3 }

		
--     1.3.6.1.4.1.10428 9 1.101.2.11.3.3.1
-- 1.3.6.1.4.1.10428 9 1.101.2.11.3.3.1
-- 1.3.6.1.4.1.10428 9 1.101.2.11.3.3.1
-- 1.3.6.1.4.1.10428 9 1.101.2.11.3.3.1
		-- 1.3.6.1.4.1.10428 9 1.101.2.11.3.3.1
		fkSlotNosUpgrade NOTIFICATION-TYPE
			OBJECTS { fkSlotNosControlRequest, fkSlotNosControlTimeStamp, fkSlotNosControlReqResult, fkSlotNosControlSlotIndex }
			STATUS current
			DESCRIPTION 
				"Description."
			::= { fkSlotNosNotification 1 }

		
--     1.3.6.1.4.1.10428 9 1.101.2.11.3.3.2
-- 1.3.6.1.4.1.10428 9 1.101.2.11.3.3.2
-- 1.3.6.1.4.1.10428 9 1.101.2.11.3.3.2
-- 1.3.6.1.4.1.10428 9 1.101.2.11.3.3.2
		-- 1.3.6.1.4.1.10428 9 1.101.2.11.3.3.2
		fkSlotNosDownload NOTIFICATION-TYPE
			OBJECTS { fkSlotNosControlRequest, fkSlotNosControlTimeStamp, fkSlotNosControlReqResult, fkSlotNosControlUpDownMethod, fkSlotNosControlUpDownFlag, 
				fkSlotNosControlServerAddress, fkSlotNosControlUserID, fkSlotNosControlPassword, fkSlotNosControlFileName }
			STATUS current
			DESCRIPTION 
				"Description."
			::= { fkSlotNosNotification 2 }

		
--     1.3.6.1.4.1.10428 9 1.101.2.11.3.3.3
-- 1.3.6.1.4.1.10428 9 1.101.2.11.3.3.3
-- 1.3.6.1.4.1.10428 9 1.101.2.11.3.3.3
-- 1.3.6.1.4.1.10428 9 1.101.2.11.3.3.3
		-- 1.3.6.1.4.1.10428 9 1.101.2.11.3.3.3
		fkSlotNosBootloaderUpgrade NOTIFICATION-TYPE
			OBJECTS { fkSlotNosControlRequest, fkSlotNosControlTimeStamp, fkSlotNosControlReqResult, fkSlotNosControlSlotIndex, fkSlotNosControlServerAddress, 
				fkSlotNosControlUserID, fkSlotNosControlPassword, fkSlotNosControlFileName }
			STATUS current
			DESCRIPTION 
				"Description."
			::= { fkSlotNosNotification 3 }

		
--     1.3.6.1.4.1.10428 9 1.101.2.11.4
-- 1.3.6.1.4.1.10428 9 1.101.2.11.4
-- 1.3.6.1.4.1.10428 9 1.101.2.11.4
-- 1.3.6.1.4.1.10428 9 1.101.2.11.4
		-- 1.3.6.1.4.1.10428 9 1.101.2.11.4
		fkSlotReleasedIUNosInfo OBJECT IDENTIFIER ::= { fkSlot 4 }

		
--     1.3.6.1.4.1.10428 9 1.101.2.11.4.1
-- 1.3.6.1.4.1.10428 9 1.101.2.11.4.1
-- 1.3.6.1.4.1.10428 9 1.101.2.11.4.1
-- 1.3.6.1.4.1.10428 9 1.101.2.11.4.1
		-- 1.3.6.1.4.1.10428 9 1.101.2.11.4.1
		fkSlotReleasedNIUNosVersion OBJECT-TYPE
			SYNTAX OCTET STRING
			MAX-ACCESS read-only
			STATUS current
			DESCRIPTION
				"Released NIU NOS image version on SFU."
			::= { fkSlotReleasedIUNosInfo 1 }

		
--     1.3.6.1.4.1.10428 9 1.101.2.11.4.2
-- 1.3.6.1.4.1.10428 9 1.101.2.11.4.2
-- 1.3.6.1.4.1.10428 9 1.101.2.11.4.2
-- 1.3.6.1.4.1.10428 9 1.101.2.11.4.2
		-- 1.3.6.1.4.1.10428 9 1.101.2.11.4.2
		fkSlotReleasedNIUNosRevision OBJECT-TYPE
			SYNTAX OCTET STRING
			MAX-ACCESS read-only
			STATUS current
			DESCRIPTION
				"Released NIU NOS image revision on SFU."
			::= { fkSlotReleasedIUNosInfo 2 }

		
--     1.3.6.1.4.1.10428 9 1.101.2.11.4.3
-- 1.3.6.1.4.1.10428 9 1.101.2.11.4.3
-- 1.3.6.1.4.1.10428 9 1.101.2.11.4.3
-- 1.3.6.1.4.1.10428 9 1.101.2.11.4.3
		-- 1.3.6.1.4.1.10428 9 1.101.2.11.4.3
		fkSlotReleasedNIUNosSize OBJECT-TYPE
			SYNTAX Unsigned32
			MAX-ACCESS read-only
			STATUS current
			DESCRIPTION
				"Released NIU NOS image size on SFU."
			::= { fkSlotReleasedIUNosInfo 3 }

		
--     1.3.6.1.4.1.10428 9 1.101.2.11.4.4
-- 1.3.6.1.4.1.10428 9 1.101.2.11.4.4
-- 1.3.6.1.4.1.10428 9 1.101.2.11.4.4
-- 1.3.6.1.4.1.10428 9 1.101.2.11.4.4
		-- 1.3.6.1.4.1.10428 9 1.101.2.11.4.4
		fkSlotReleasedGPIUNosVersion OBJECT-TYPE
			SYNTAX OCTET STRING
			MAX-ACCESS read-only
			STATUS current
			DESCRIPTION
				"Released GPIU NOS image version on SFU."
			::= { fkSlotReleasedIUNosInfo 4 }

		
--     1.3.6.1.4.1.10428 9 1.101.2.11.4.5
-- 1.3.6.1.4.1.10428 9 1.101.2.11.4.5
-- 1.3.6.1.4.1.10428 9 1.101.2.11.4.5
-- 1.3.6.1.4.1.10428 9 1.101.2.11.4.5
		-- 1.3.6.1.4.1.10428 9 1.101.2.11.4.5
		fkSlotReleasedGPIUNosRevision OBJECT-TYPE
			SYNTAX OCTET STRING
			MAX-ACCESS read-only
			STATUS current
			DESCRIPTION
				"Released GPIU NOS image revision on SFU."
			::= { fkSlotReleasedIUNosInfo 5 }

		
--     1.3.6.1.4.1.10428 9 1.101.2.11.4.6
-- 1.3.6.1.4.1.10428 9 1.101.2.11.4.6
-- 1.3.6.1.4.1.10428 9 1.101.2.11.4.6
-- 1.3.6.1.4.1.10428 9 1.101.2.11.4.6
		-- 1.3.6.1.4.1.10428 9 1.101.2.11.4.6
		fkSlotReleasedGPIUNosSize OBJECT-TYPE
			SYNTAX Unsigned32
			MAX-ACCESS read-only
			STATUS current
			DESCRIPTION
				"Released GPIU NOS image size on SFU."
			::= { fkSlotReleasedIUNosInfo 6 }

		
--  1.3.6.1.4.1.10428 9 1.101.2.11.4.7
		-- 1.3.6.1.4.1.10428 9 1.101.2.11.4.7
		fkSlotReleasedSIUNosVersion OBJECT-TYPE
			SYNTAX OCTET STRING
			MAX-ACCESS read-only
			STATUS current
			DESCRIPTION
				"Released SIU NOS image version on SFU."
			::= { fkSlotReleasedIUNosInfo 7 }

		
--  1.3.6.1.4.1.10428 9 1.101.2.11.4.8
		-- 1.3.6.1.4.1.10428 9 1.101.2.11.4.8
		fkSlotReleasedSIUNosRevision OBJECT-TYPE
			SYNTAX OCTET STRING
			MAX-ACCESS read-only
			STATUS current
			DESCRIPTION
				"Released SIU NOS image revision on SFU."
			::= { fkSlotReleasedIUNosInfo 8 }

		
--  1.3.6.1.4.1.10428 9 1.101.2.11.4.9
		-- 1.3.6.1.4.1.10428 9 1.101.2.11.4.9
		fkSlotReleasedSIUNosSize OBJECT-TYPE
			SYNTAX Integer32
			MAX-ACCESS read-only
			STATUS current
			DESCRIPTION
				"Released SIU NOS image size on SFU."
			::= { fkSlotReleasedIUNosInfo 9 }

		
--     1.3.6.1.4.1.10428 9 1.101.2.11.5
-- 1.3.6.1.4.1.10428 9 1.101.2.11.5
-- 1.3.6.1.4.1.10428 9 1.101.2.11.5
-- 1.3.6.1.4.1.10428 9 1.101.2.11.5
		-- 1.3.6.1.4.1.10428 9 1.101.2.11.5
		fkSlotPowerMon OBJECT IDENTIFIER ::= { fkSlot 5 }

		
--     1.3.6.1.4.1.10428 9 1.101.2.11.5.1
-- 1.3.6.1.4.1.10428 9 1.101.2.11.5.1
-- 1.3.6.1.4.1.10428 9 1.101.2.11.5.1
-- 1.3.6.1.4.1.10428 9 1.101.2.11.5.1
		-- 1.3.6.1.4.1.10428 9 1.101.2.11.5.1
		fkSlotPowerMonTable OBJECT-TYPE
			SYNTAX SEQUENCE OF FkSlotPowerMonEntry
			MAX-ACCESS not-accessible
			STATUS current
			DESCRIPTION
				"The Power-Monitoring table."
			::= { fkSlotPowerMon 1 }

		
--     1.3.6.1.4.1.10428 9 1.101.2.11.5.1.1
-- 1.3.6.1.4.1.10428 9 1.101.2.11.5.1.1
-- 1.3.6.1.4.1.10428 9 1.101.2.11.5.1.1
-- 1.3.6.1.4.1.10428 9 1.101.2.11.5.1.1
		-- 1.3.6.1.4.1.10428 9 1.101.2.11.5.1.1
		fkSlotPowerMonEntry OBJECT-TYPE
			SYNTAX FkSlotPowerMonEntry
			MAX-ACCESS not-accessible
			STATUS current
			DESCRIPTION
				"The Power-Monitoring entry."
			INDEX { fkSlotSystemIndex, fkSlotPowerMonIndex }
			::= { fkSlotPowerMonTable 1 }

		
		FkSlotPowerMonEntry ::=
			SEQUENCE { 
				fkSlotPowerMonIndex
					INTEGER,
				fkSlotPowerMonStatus
					INTEGER,
				fkSlotPowerMonVoltage
					Gauge32
			 }

--     1.3.6.1.4.1.10428 9 1.101.2.11.5.1.1.1
-- 1.3.6.1.4.1.10428 9 1.101.2.11.5.1.1.1
-- 1.3.6.1.4.1.10428 9 1.101.2.11.5.1.1.1
-- 1.3.6.1.4.1.10428 9 1.101.2.11.5.1.1.1
		-- 1.3.6.1.4.1.10428 9 1.101.2.11.5.1.1.1
		fkSlotPowerMonIndex OBJECT-TYPE
			SYNTAX INTEGER (1..255)
			MAX-ACCESS read-only
			STATUS current
			DESCRIPTION
				"The physical index of power-monitoring object."
			::= { fkSlotPowerMonEntry 1 }

		
--     1.3.6.1.4.1.10428 9 1.101.2.11.5.1.1.2
-- 1.3.6.1.4.1.10428 9 1.101.2.11.5.1.1.2
-- 1.3.6.1.4.1.10428 9 1.101.2.11.5.1.1.2
-- 1.3.6.1.4.1.10428 9 1.101.2.11.5.1.1.2
		-- 1.3.6.1.4.1.10428 9 1.101.2.11.5.1.1.2
		fkSlotPowerMonStatus OBJECT-TYPE
			SYNTAX INTEGER
				{
				unknown(1),
				good(2),
				bad(3),
				over(4),
				under(5),
				overUnder(6)
				}
			MAX-ACCESS read-only
			STATUS current
			DESCRIPTION
				"The monitoring status of power-monitoring object."
			::= { fkSlotPowerMonEntry 2 }

		
--     1.3.6.1.4.1.10428 9 1.101.2.11.5.1.1.3
-- 1.3.6.1.4.1.10428 9 1.101.2.11.5.1.1.3
-- 1.3.6.1.4.1.10428 9 1.101.2.11.5.1.1.3
-- 1.3.6.1.4.1.10428 9 1.101.2.11.5.1.1.3
		-- 1.3.6.1.4.1.10428 9 1.101.2.11.5.1.1.3
		fkSlotPowerMonVoltage OBJECT-TYPE
			SYNTAX Gauge32
			UNITS "0.1v"
			MAX-ACCESS read-only
			STATUS current
			DESCRIPTION
				"The voltage value of power-monitoring object.
				value 10000(1000v) indicate that FUSE."
			::= { fkSlotPowerMonEntry 3 }

		
--  1.3.6.1.4.1.10428 9 1.101.2.11.6
		-- 1.3.6.1.4.1.10428 9 1.101.2.11.6
		fkSlotAiu OBJECT IDENTIFIER ::= { fkSlot 6 }

		
--  1.3.6.1.4.1.10428 9 1.101.2.11.6.1
		-- 1.3.6.1.4.1.10428 9 1.101.2.11.6.1
		fkSlotAiuRunStatus OBJECT-TYPE
			SYNTAX INTEGER
				{
				off(0),
				on(1)
				}
			MAX-ACCESS read-only
			STATUS current
			DESCRIPTION
				"The slot AIU run status."
			::= { fkSlotAiu 1 }

		
--  1.3.6.1.4.1.10428 9 1.101.2.11.6.2
		-- 1.3.6.1.4.1.10428 9 1.101.2.11.6.2
		fkSlotAiuAlarmStatus OBJECT-TYPE
			SYNTAX INTEGER
				{
				off(0),
				on(1)
				}
			MAX-ACCESS read-only
			STATUS current
			DESCRIPTION
				"The slot AIU alarm status."
			::= { fkSlotAiu 2 }

		
--     1.3.6.1.4.1.10428 9 1.101.2.12
-- 1.3.6.1.4.1.10428 9 1.101.2.12
-- 1.3.6.1.4.1.10428 9 1.101.2.12
-- 1.3.6.1.4.1.10428 9 1.101.2.12
		-- 1.3.6.1.4.1.10428 9 1.101.2.12
		fkRF OBJECT IDENTIFIER ::= { fkDevice 12 }

		
--     1.3.6.1.4.1.10428 9 1.101.2.12.1
-- 1.3.6.1.4.1.10428 9 1.101.2.12.1
-- 1.3.6.1.4.1.10428 9 1.101.2.12.1
-- 1.3.6.1.4.1.10428 9 1.101.2.12.1
		-- 1.3.6.1.4.1.10428 9 1.101.2.12.1
		fkRfBaseInfo OBJECT IDENTIFIER ::= { fkRF 1 }

		
--     1.3.6.1.4.1.10428 9 1.101.2.12.1.1
-- 1.3.6.1.4.1.10428 9 1.101.2.12.1.1
-- 1.3.6.1.4.1.10428 9 1.101.2.12.1.1
-- 1.3.6.1.4.1.10428 9 1.101.2.12.1.1
		-- 1.3.6.1.4.1.10428 9 1.101.2.12.1.1
		fkRfConnectStatus OBJECT-TYPE
			SYNTAX INTEGER
				{
				connect(1),
				disconnect(2)
				}
			MAX-ACCESS read-only
			STATUS current
			DESCRIPTION
				"The RF connect status."
			::= { fkRfBaseInfo 1 }

		
--     1.3.6.1.4.1.10428 9 1.101.2.12.1.1
-- 1.3.6.1.4.1.10428 9 1.101.2.12.1.1
-- 1.3.6.1.4.1.10428 9 1.101.2.12.1.2
-- 1.3.6.1.4.1.10428 9 1.101.2.12.1.2
		-- 1.3.6.1.4.1.10428 9 1.101.2.12.1.2
		fkRfPowerStatus OBJECT-TYPE
			SYNTAX INTEGER
				{
				poweroff(0),
				poweron(1)
				}
			MAX-ACCESS read-only
			STATUS current
			DESCRIPTION
				"The RF power status."
			::= { fkRfBaseInfo 2 }

		
--   1.3.6.1.4.1.10428 9 1.101.2.12.1.3
-- 1.3.6.1.4.1.10428 9 1.101.2.12.1.3
		-- 1.3.6.1.4.1.10428 9 1.101.2.12.1.3
		fkRfEthertype OBJECT-TYPE
			SYNTAX OCTET STRING
			MAX-ACCESS read-only
			STATUS current
			DESCRIPTION
				"The RF ethertype."
			::= { fkRfBaseInfo 3 }

		
--   1.3.6.1.4.1.10428 9 1.101.2.12.1.4
-- 1.3.6.1.4.1.10428 9 1.101.2.12.1.4
		-- 1.3.6.1.4.1.10428 9 1.101.2.12.1.4
		fkRfSrcAddress OBJECT-TYPE
			SYNTAX OCTET STRING
			MAX-ACCESS read-only
			STATUS current
			DESCRIPTION
				"The RF source address."
			::= { fkRfBaseInfo 4 }

		
--   1.3.6.1.4.1.10428 9 1.101.2.12.1.5
-- 1.3.6.1.4.1.10428 9 1.101.2.12.1.5
		-- 1.3.6.1.4.1.10428 9 1.101.2.12.1.5
		fkRfDesAddress OBJECT-TYPE
			SYNTAX OCTET STRING
			MAX-ACCESS read-only
			STATUS current
			DESCRIPTION
				"The RF destination address."
			::= { fkRfBaseInfo 5 }

		
--   1.3.6.1.4.1.10428 9 1.101.2.12.2
-- 1.3.6.1.4.1.10428 9 1.101.2.12.2
		-- 1.3.6.1.4.1.10428 9 1.101.2.12.2
		fkRfBaseControl OBJECT IDENTIFIER ::= { fkRF 2 }

		
--   1.3.6.1.4.1.10428 9 1.101.2.12.2.1
-- 1.3.6.1.4.1.10428 9 1.101.2.12.2.1
		-- 1.3.6.1.4.1.10428 9 1.101.2.12.2.1
		fkRfBaseControlRequest OBJECT-TYPE
			SYNTAX INTEGER
				{
				setRfEthertype(1),
				resetRfEthertype(2)
				}
			MAX-ACCESS read-write
			STATUS current
			DESCRIPTION
				"The request of a user command."
			::= { fkRfBaseControl 1 }

		
--   1.3.6.1.4.1.10428 9 1.101.2.12.2.2
-- 1.3.6.1.4.1.10428 9 1.101.2.12.2.2
		-- 1.3.6.1.4.1.10428 9 1.101.2.12.2.2
		fkRfBaseControlStatus OBJECT-TYPE
			SYNTAX FkControlStatusType
			MAX-ACCESS read-only
			STATUS current
			DESCRIPTION
				"The status of user command."
			::= { fkRfBaseControl 2 }

		
--   1.3.6.1.4.1.10428 9 1.101.2.12.2.3
-- 1.3.6.1.4.1.10428 9 1.101.2.12.2.3
		-- 1.3.6.1.4.1.10428 9 1.101.2.12.2.3
		fkRfBaseControlTimer OBJECT-TYPE
			SYNTAX Integer32
			MAX-ACCESS read-write
			STATUS current
			DESCRIPTION
				"The maximum time for the manager for a long running user command."
			::= { fkRfBaseControl 3 }

		
--   1.3.6.1.4.1.10428 9 1.101.2.12.2.4
-- 1.3.6.1.4.1.10428 9 1.101.2.12.2.4
		-- 1.3.6.1.4.1.10428 9 1.101.2.12.2.4
		fkRfBaseControlTimeStamp OBJECT-TYPE
			SYNTAX TimeTicks
			MAX-ACCESS read-only
			STATUS current
			DESCRIPTION
				"The time stamp of the last command(end of command)."
			::= { fkRfBaseControl 4 }

		
--   1.3.6.1.4.1.10428 9 1.101.2.12.2.5
-- 1.3.6.1.4.1.10428 9 1.101.2.12.2.5
		-- 1.3.6.1.4.1.10428 9 1.101.2.12.2.5
		fkRfBaseControlReqResult OBJECT-TYPE
			SYNTAX FkControlRequestResultType
			MAX-ACCESS read-only
			STATUS current
			DESCRIPTION
				"The result of user command."
			::= { fkRfBaseControl 5 }

		
--   1.3.6.1.4.1.10428 9 1.101.2.12.2.6
-- 1.3.6.1.4.1.10428 9 1.101.2.12.2.6
		-- 1.3.6.1.4.1.10428 9 1.101.2.12.2.6
		fkRfBaseControlRfEthertype OBJECT-TYPE
			SYNTAX OCTET STRING
			MAX-ACCESS read-write
			STATUS current
			DESCRIPTION
				"The Rf ethertype ,the format is 0xXXXX, default value is 0x8864."
			::= { fkRfBaseControl 6 }

		
--   1.3.6.1.4.1.10428 9 1.101.2.12.3
-- 1.3.6.1.4.1.10428 9 1.101.2.12.3
		-- 1.3.6.1.4.1.10428 9 1.101.2.12.3
		fkRfBaseNotification OBJECT IDENTIFIER ::= { fkRF 3 }

		
--   1.3.6.1.4.1.10428 9 1.101.2.12.3.1
-- 1.3.6.1.4.1.10428 9 1.101.2.12.3.1
		-- 1.3.6.1.4.1.10428 9 1.101.2.12.3.1
		fkRFBaseEthertypeChanged NOTIFICATION-TYPE
			OBJECTS { fkRfBaseControlRequest, fkRfBaseControlTimeStamp, fkRfBaseControlReqResult, fkRfBaseControlRfEthertype }
			STATUS current
			DESCRIPTION 
				"Description."
			::= { fkRfBaseNotification 1 }

		
--   1.3.6.1.4.1.10428 9 1.101.2.12.3.2
-- 1.3.6.1.4.1.10428 9 1.101.2.12.3.2
		-- 1.3.6.1.4.1.10428 9 1.101.2.12.3.2
		fkRFBaseEthertypeResetChanged NOTIFICATION-TYPE
			OBJECTS { fkRfBaseControlRequest, fkRfBaseControlTimeStamp, fkRfBaseControlReqResult, fkRfBaseControlRfEthertype }
			STATUS current
			DESCRIPTION 
				"Description."
			::= { fkRfBaseNotification 2 }

		
--   1.3.6.1.4.1.10428 9 1.101.2.12.4
-- 1.3.6.1.4.1.10428 9 1.101.2.12.4
		-- 1.3.6.1.4.1.10428 9 1.101.2.12.4
		fkRfPortTable OBJECT-TYPE
			SYNTAX SEQUENCE OF FkRfPortEntry
			MAX-ACCESS not-accessible
			STATUS current
			DESCRIPTION
				"Description."
			::= { fkRF 4 }

		
--   1.3.6.1.4.1.10428 9 1.101.2.12.4.1
-- 1.3.6.1.4.1.10428 9 1.101.2.12.4.1
-- 1.3.6.1.4.1.10428 9 1.101.2.12.4.1
		-- 1.3.6.1.4.1.10428 9 1.101.2.12.4.1
		fkRfPortEntry OBJECT-TYPE
			SYNTAX FkRfPortEntry
			MAX-ACCESS not-accessible
			STATUS current
			DESCRIPTION
				"Description."
			INDEX { fkRfPortIndex }
			::= { fkRfPortTable 1 }

		
		FkRfPortEntry ::=
			SEQUENCE { 
				fkRfPortIndex
					INTEGER,
				fkRfPortAdminStatus
					INTEGER,
				fkRfPortOperStatus
					INTEGER
			 }

--   1.3.6.1.4.1.10428 9 1.101.2.12.4.1.1
-- 1.3.6.1.4.1.10428 9 1.101.2.12.4.1.1
		-- 1.3.6.1.4.1.10428 9 1.101.2.12.4.1.1
		fkRfPortIndex OBJECT-TYPE
			SYNTAX INTEGER (1..256)
			MAX-ACCESS read-write
			STATUS current
			DESCRIPTION
				"The RF port index."
			::= { fkRfPortEntry 1 }

		
--   1.3.6.1.4.1.10428 9 1.101.2.12.4.1.2
-- 1.3.6.1.4.1.10428 9 1.101.2.12.4.1.2
		-- 1.3.6.1.4.1.10428 9 1.101.2.12.4.1.2
		fkRfPortAdminStatus OBJECT-TYPE
			SYNTAX INTEGER
				{
				enable(1),
				disable(2),
				na(255)
				}
			MAX-ACCESS read-write
			STATUS current
			DESCRIPTION
				"The RF port adminStatus."
			::= { fkRfPortEntry 2 }

		
--   1.3.6.1.4.1.10428 9 1.101.2.12.4.1.3
-- 1.3.6.1.4.1.10428 9 1.101.2.12.4.1.3
		-- 1.3.6.1.4.1.10428 9 1.101.2.12.4.1.3
		fkRfPortOperStatus OBJECT-TYPE
			SYNTAX INTEGER
				{
				enable(1),
				disable(2),
				na(255)
				}
			MAX-ACCESS read-write
			STATUS current
			DESCRIPTION
				"The RF port operStatus."
			::= { fkRfPortEntry 3 }

		
--   1.3.6.1.4.1.10428 9 1.101.2.12.5
-- 1.3.6.1.4.1.10428 9 1.101.2.12.5
		-- 1.3.6.1.4.1.10428 9 1.101.2.12.5
		fkRFPortControl OBJECT IDENTIFIER ::= { fkRF 5 }

		
--   1.3.6.1.4.1.10428 9 1.101.2.12.5.1
-- 1.3.6.1.4.1.10428 9 1.101.2.12.5.1
		-- 1.3.6.1.4.1.10428 9 1.101.2.12.5.1
		fkRfPortControlRequest OBJECT-TYPE
			SYNTAX INTEGER { setRfPortStatus(1) }
			MAX-ACCESS read-write
			STATUS current
			DESCRIPTION
				"The request of a user command."
			::= { fkRFPortControl 1 }

		
--   1.3.6.1.4.1.10428 9 1.101.2.12.5.2
-- 1.3.6.1.4.1.10428 9 1.101.2.12.5.2
		-- 1.3.6.1.4.1.10428 9 1.101.2.12.5.2
		fkRfPortControlStatus OBJECT-TYPE
			SYNTAX FkControlStatusType
			MAX-ACCESS read-only
			STATUS current
			DESCRIPTION
				"The status of user command."
			::= { fkRFPortControl 2 }

		
--   1.3.6.1.4.1.10428 9 1.101.2.12.5.3
-- 1.3.6.1.4.1.10428 9 1.101.2.12.5.3
		-- 1.3.6.1.4.1.10428 9 1.101.2.12.5.3
		fkRfPortControlTimer OBJECT-TYPE
			SYNTAX Integer32
			MAX-ACCESS read-write
			STATUS current
			DESCRIPTION
				"The maximum time for the manager for a long running user command."
			::= { fkRFPortControl 3 }

		
--   1.3.6.1.4.1.10428 9 1.101.2.12.5.4
-- 1.3.6.1.4.1.10428 9 1.101.2.12.5.4
		-- 1.3.6.1.4.1.10428 9 1.101.2.12.5.4
		fkRfPortControlTimeStamp OBJECT-TYPE
			SYNTAX TimeTicks
			MAX-ACCESS read-only
			STATUS current
			DESCRIPTION
				"The time stamp of the last command(end of command)."
			::= { fkRFPortControl 4 }

		
--   1.3.6.1.4.1.10428 9 1.101.2.12.5.5
-- 1.3.6.1.4.1.10428 9 1.101.2.12.5.5
		-- 1.3.6.1.4.1.10428 9 1.101.2.12.5.5
		fkRfPortControlReqResult OBJECT-TYPE
			SYNTAX FkControlRequestResultType
			MAX-ACCESS read-only
			STATUS current
			DESCRIPTION
				"The result of user command.
				"
			::= { fkRFPortControl 5 }

		
--   1.3.6.1.4.1.10428 9 1.101.2.12.5.6
-- 1.3.6.1.4.1.10428 9 1.101.2.12.5.6
		-- 1.3.6.1.4.1.10428 9 1.101.2.12.5.6
		fkRfPortControlIndex OBJECT-TYPE
			SYNTAX Integer32 (1..8)
			MAX-ACCESS read-write
			STATUS current
			DESCRIPTION
				"The RF port index <1-8>."
			::= { fkRFPortControl 6 }

		
--   1.3.6.1.4.1.10428 9 1.101.2.12.5.7
-- 1.3.6.1.4.1.10428 9 1.101.2.12.5.7
		-- 1.3.6.1.4.1.10428 9 1.101.2.12.5.7
		fkRfPortControlAdminStatus OBJECT-TYPE
			SYNTAX INTEGER
				{
				enable(1),
				disable(2)
				}
			MAX-ACCESS read-write
			STATUS current
			DESCRIPTION
				"The RF port adminStatus."
			::= { fkRFPortControl 7 }

		
--   1.3.6.1.4.1.10428 9 1.101.2.12.6
-- 1.3.6.1.4.1.10428 9 1.101.2.12.6
		-- 1.3.6.1.4.1.10428 9 1.101.2.12.6
		fkRFPortNotification OBJECT IDENTIFIER ::= { fkRF 6 }

		
--   1.3.6.1.4.1.10428 9 1.101.2.12.6.1
-- 1.3.6.1.4.1.10428 9 1.101.2.12.6.1
		-- 1.3.6.1.4.1.10428 9 1.101.2.12.6.1
		fkRfPortStatusChanged NOTIFICATION-TYPE
			OBJECTS { fkRfPortControlRequest, fkRfPortControlTimeStamp, fkRfPortControlReqResult, fkRfPortControlIndex, fkRfPortControlAdminStatus
				 }
			STATUS current
			DESCRIPTION 
				"Description."
			::= { fkRFPortNotification 1 }

		
--  1.3.6.1.4.1.10428 9 1.101.2.13
		-- 1.3.6.1.4.1.10428 9 1.101.2.13
		fkEnvironmentMonitor OBJECT IDENTIFIER ::= { fkDevice 13 }

		
--  1.3.6.1.4.1.10428 9 1.101.2.13.1
		-- 1.3.6.1.4.1.10428 9 1.101.2.13.1
		fkEMTable OBJECT-TYPE
			SYNTAX SEQUENCE OF FkEMEntry
			MAX-ACCESS not-accessible
			STATUS current
			DESCRIPTION
				"Description."
			::= { fkEnvironmentMonitor 1 }

		
--  1.3.6.1.4.1.10428 9 1.101.2.13.1.1
		-- 1.3.6.1.4.1.10428 9 1.101.2.13.1.1
		fkEMEntry OBJECT-TYPE
			SYNTAX FkEMEntry
			MAX-ACCESS not-accessible
			STATUS current
			DESCRIPTION
				"Description."
			INDEX { fkEMInputIndex }
			::= { fkEMTable 1 }

		
		FkEMEntry ::=
			SEQUENCE { 
				fkEMInputIndex
					Integer32,
				fkEMAlarmString
					OCTET STRING,
				fkEMAlarmSeverity
					INTEGER,
				fkEMmode
					INTEGER
			 }

--  1.3.6.1.4.1.10428 9 1.101.2.13.1.1.1
		-- 1.3.6.1.4.1.10428 9 1.101.2.13.1.1.1
		fkEMInputIndex OBJECT-TYPE
			SYNTAX Integer32 (1..4)
			MAX-ACCESS read-only
			STATUS current
			DESCRIPTION
				"The environment monitoring input index(1-4)."
			::= { fkEMEntry 1 }

		
--  1.3.6.1.4.1.10428 9 1.101.2.13.1.1.2
		-- 1.3.6.1.4.1.10428 9 1.101.2.13.1.1.2
		fkEMAlarmString OBJECT-TYPE
			SYNTAX OCTET STRING
			MAX-ACCESS read-only
			STATUS current
			DESCRIPTION
				"The alarm string"
			::= { fkEMEntry 2 }

		
--  1.3.6.1.4.1.10428 9 1.101.2.13.1.1.3
		-- 1.3.6.1.4.1.10428 9 1.101.2.13.1.1.3
		fkEMAlarmSeverity OBJECT-TYPE
			SYNTAX INTEGER
				{
				none(0),
				critical(1),
				major(2),
				minor(3),
				warning(4),
				intermediate(5)
				}
			MAX-ACCESS read-only
			STATUS current
			DESCRIPTION
				"The alarm severity."
			::= { fkEMEntry 3 }

		
--  1.3.6.1.4.1.10428 9 1.101.2.13.1.1.4
		-- 1.3.6.1.4.1.10428 9 1.101.2.13.1.1.4
		fkEMmode OBJECT-TYPE
			SYNTAX INTEGER
				{
				normalClose(0),
				normalOpen(1)
				}
			MAX-ACCESS read-only
			STATUS current
			DESCRIPTION
				"The environment monitoring mode.(default:normal-close)"
			::= { fkEMEntry 4 }

		
--  1.3.6.1.4.1.10428 9 1.101.2.13.2
		-- 1.3.6.1.4.1.10428 9 1.101.2.13.2
		fkEMControl OBJECT IDENTIFIER ::= { fkEnvironmentMonitor 2 }

		
--  1.3.6.1.4.1.10428 9 1.101.2.13.2.1
		-- 1.3.6.1.4.1.10428 9 1.101.2.13.2.1
		fkEMControlRequest OBJECT-TYPE
			SYNTAX INTEGER
				{
				setEM(1),
				delEM(2)
				}
			MAX-ACCESS read-write
			STATUS current
			DESCRIPTION
				"The request of a user command."
			::= { fkEMControl 1 }

		
--    1.3.6.1.4.1.10428 9 1.101.2.12.3.2
-- 1.3.6.1.4.1.10428 9 1.101.2.12.3.2
-- 1.3.6.1.4.1.10428 9 1.101.2.13.2.2
		-- 1.3.6.1.4.1.10428 9 1.101.2.13.2.2
		fkEMControlStatus OBJECT-TYPE
			SYNTAX FkControlStatusType
			MAX-ACCESS read-only
			STATUS current
			DESCRIPTION
				"Description."
			::= { fkEMControl 2 }

		
--  1.3.6.1.4.1.10428 9 1.101.2.13.2.3
		-- 1.3.6.1.4.1.10428 9 1.101.2.13.2.3
		fkEMControlTimer OBJECT-TYPE
			SYNTAX Gauge32
			MAX-ACCESS read-only
			STATUS current
			DESCRIPTION
				"The maximum time for the manager for a long running user command.
				Apply your setting.
				"
			::= { fkEMControl 3 }

		
--  1.3.6.1.4.1.10428 9 1.101.2.13.2.4
		-- 1.3.6.1.4.1.10428 9 1.101.2.13.2.4
		fkEMControlTimeStamp OBJECT-TYPE
			SYNTAX TimeTicks
			MAX-ACCESS read-only
			STATUS current
			DESCRIPTION
				"Description."
			::= { fkEMControl 4 }

		
--  1.3.6.1.4.1.10428 9 1.101.2.13.2.5
		-- 1.3.6.1.4.1.10428 9 1.101.2.13.2.5
		fkEMControlReqResult OBJECT-TYPE
			SYNTAX FkControlRequestResultType
			MAX-ACCESS read-only
			STATUS current
			DESCRIPTION
				"Description."
			::= { fkEMControl 5 }

		
--  1.3.6.1.4.1.10428 9 1.101.2.13.2.6
		-- 1.3.6.1.4.1.10428 9 1.101.2.13.2.6
		fkEMControlInputIndex OBJECT-TYPE
			SYNTAX Integer32 (1..4)
			MAX-ACCESS read-write
			STATUS current
			DESCRIPTION
				"The environment monitoring input index(1-4)."
			::= { fkEMControl 6 }

		
--  1.3.6.1.4.1.10428 9 1.101.2.13.2.7
		-- 1.3.6.1.4.1.10428 9 1.101.2.13.2.7
		fkEMControlAlarmString OBJECT-TYPE
			SYNTAX OCTET STRING
			MAX-ACCESS read-write
			STATUS current
			DESCRIPTION
				"The alarm string"
			::= { fkEMControl 7 }

		
--  1.3.6.1.4.1.10428 9 1.101.2.13.2.8
		-- 1.3.6.1.4.1.10428 9 1.101.2.13.2.8
		fkEMControlAlarmSeverity OBJECT-TYPE
			SYNTAX INTEGER
				{
				none(0),
				critical(1),
				major(2),
				minor(3),
				warning(4),
				intermediate(5)
				}
			MAX-ACCESS read-write
			STATUS current
			DESCRIPTION
				"The alarm severity."
			::= { fkEMControl 8 }

		
--  1.3.6.1.4.1.10428 9 1.101.2.13.2.9
		-- 1.3.6.1.4.1.10428 9 1.101.2.13.2.9
		fkEMControlmode OBJECT-TYPE
			SYNTAX INTEGER
				{
				normalClose(0),
				normalOpen(1)
				}
			MAX-ACCESS read-write
			STATUS current
			DESCRIPTION
				"The environment monitoring mode.(default:normal-close)"
			::= { fkEMControl 9 }

		
--  1.3.6.1.4.1.10428 9 1.101.2.13.3
		-- 1.3.6.1.4.1.10428 9 1.101.2.13.3
		fkEMNotification OBJECT IDENTIFIER ::= { fkEnvironmentMonitor 3 }

		
--  1.3.6.1.4.1.10428 9 1.101.2.13.3.1
		-- 1.3.6.1.4.1.10428 9 1.101.2.13.3.1
		fkEMChanged NOTIFICATION-TYPE
			OBJECTS { fkEMControlRequest, fkEMControlTimeStamp, fkEMControlReqResult, fkEMControlInputIndex, fkEMControlAlarmString, 
				fkEMControlAlarmSeverity, fkEMControlmode }
			STATUS current
			DESCRIPTION 
				"Description."
			::= { fkEMNotification 1 }

		
--  1.3.6.1.4.1.10428 9 1.101.2.13.3.2
		-- 1.3.6.1.4.1.10428 9 1.101.2.13.3.2
		fkEMDeleted NOTIFICATION-TYPE
			OBJECTS { fkEMControlRequest, fkEMControlTimeStamp, fkEMControlReqResult, fkEMControlInputIndex }
			STATUS current
			DESCRIPTION 
				"Description."
			::= { fkEMNotification 2 }

		
		-- 1.3.6.1.4.1.10428 9 1.101.2.14
		fkBypass OBJECT IDENTIFIER ::= { fkDevice 14 }

		
		-- 1.3.6.1.4.1.10428 9 1.101.2.14.1
		fkBypassBase OBJECT IDENTIFIER ::= { fkBypass 1 }

		
		-- 1.3.6.1.4.1.10428 9 1.101.2.14.1.1
		fkBypassBaseInfo OBJECT IDENTIFIER ::= { fkBypassBase 1 }

		
		-- 1.3.6.1.4.1.10428 9 1.101.2.14.1.1.1
		fkBypassMode OBJECT-TYPE
			SYNTAX INTEGER
				{
				on(1),
				off(2),
				auto(3)
				}
			MAX-ACCESS read-only
			STATUS current
			DESCRIPTION
				"optic bypass mode"
			DEFVAL { off }
			::= { fkBypassBaseInfo 1 }

		
		-- 1.3.6.1.4.1.10428 9 1.101.2.14.1.1.2
		fkBypassStatus OBJECT-TYPE
			SYNTAX INTEGER
				{
				enable(1),
				disable(2)
				}
			MAX-ACCESS read-only
			STATUS current
			DESCRIPTION
				"optic bypass status
				"
			::= { fkBypassBaseInfo 2 }

		
		-- 1.3.6.1.4.1.10428 9 1.101.2.14.1.2
		fkBypassBaseControl OBJECT IDENTIFIER ::= { fkBypassBase 2 }

		
		-- 1.3.6.1.4.1.10428 9 1.101.2.14.1.2.1
		fkBypassBaseControlRequest OBJECT-TYPE
			SYNTAX INTEGER { setBypassMode(1) }
			MAX-ACCESS read-write
			STATUS current
			DESCRIPTION
				"Description."
			::= { fkBypassBaseControl 1 }

		
--   1.3.6.1.4.1.10428 9 1.101.2.12.2.2
-- 1.3.6.1.4.1.10428 9 1.101.2.12.2.2
		-- 1.3.6.1.4.1.10428 9 1.101.2.14.1.2.2
		fkBypassBaseControlStatus OBJECT-TYPE
			SYNTAX FkControlStatusType
			MAX-ACCESS read-only
			STATUS current
			DESCRIPTION
				"The status of user command."
			::= { fkBypassBaseControl 2 }

		
--   1.3.6.1.4.1.10428 9 1.101.2.12.2.3
-- 1.3.6.1.4.1.10428 9 1.101.2.12.2.3
		-- 1.3.6.1.4.1.10428 9 1.101.2.14.1.2.3
		fkBypassBaseControlTimer OBJECT-TYPE
			SYNTAX Integer32
			MAX-ACCESS read-write
			STATUS current
			DESCRIPTION
				"The maximum time for the manager for a long running user command."
			::= { fkBypassBaseControl 3 }

		
--   1.3.6.1.4.1.10428 9 1.101.2.12.2.4
-- 1.3.6.1.4.1.10428 9 1.101.2.12.2.4
		-- 1.3.6.1.4.1.10428 9 1.101.2.14.1.2.4
		fkBypassBaseControlTimeStamp OBJECT-TYPE
			SYNTAX TimeTicks
			MAX-ACCESS read-only
			STATUS current
			DESCRIPTION
				"The time stamp of the last command(end of command)."
			::= { fkBypassBaseControl 4 }

		
--   1.3.6.1.4.1.10428 9 1.101.2.12.2.5
-- 1.3.6.1.4.1.10428 9 1.101.2.12.2.5
		-- 1.3.6.1.4.1.10428 9 1.101.2.14.1.2.5
		fkBypassBaseControlReqResult OBJECT-TYPE
			SYNTAX FkControlRequestResultType
			MAX-ACCESS read-only
			STATUS current
			DESCRIPTION
				"The result of user command."
			::= { fkBypassBaseControl 5 }

		
		-- 1.3.6.1.4.1.10428 9 1.101.2.14.1.2.6
		fkBypassBaseControlMode OBJECT-TYPE
			SYNTAX INTEGER
				{
				on(1),
				off(2),
				auto(3)
				}
			MAX-ACCESS read-write
			STATUS current
			DESCRIPTION
				"optic bypass mode"
			::= { fkBypassBaseControl 6 }

		
		-- 1.3.6.1.4.1.10428 9 1.101.2.14.1.3
		fkBypassBaseNotification OBJECT IDENTIFIER ::= { fkBypassBase 3 }

		
		-- 1.3.6.1.4.1.10428 9 1.101.2.14.1.3.1
		fkBypassModeChanged NOTIFICATION-TYPE
			OBJECTS { fkBypassBaseControlRequest, fkBypassBaseControlTimeStamp, fkBypassBaseControlReqResult, fkBypassBaseControlMode }
			STATUS current
			DESCRIPTION 
				"setBypassMode(1)"
			::= { fkBypassBaseNotification 1 }

		
		-- 1.3.6.1.4.1.10428 9 1.101.2.14.2
		fkBypassOption OBJECT IDENTIFIER ::= { fkBypass 2 }

		
		-- 1.3.6.1.4.1.10428 9 1.101.2.14.2.1
		fkBypassOptionConnectivityTable OBJECT-TYPE
			SYNTAX SEQUENCE OF FkBypassOptionConnectivityEntry
			MAX-ACCESS not-accessible
			STATUS current
			DESCRIPTION
				"The connectivity option of bypass"
			::= { fkBypassOption 1 }

		
		-- 1.3.6.1.4.1.10428 9 1.101.2.14.2.1.1
		fkBypassOptionConnectivityEntry OBJECT-TYPE
			SYNTAX FkBypassOptionConnectivityEntry
			MAX-ACCESS not-accessible
			STATUS current
			DESCRIPTION
				"Description."
			INDEX { fkBypassOptionConnectivityAddress, fkBypassOptionConnectivityPort }
			::= { fkBypassOptionConnectivityTable 1 }

		
		FkBypassOptionConnectivityEntry ::=
			SEQUENCE { 
				fkBypassOptionConnectivityAddress
					IpAddress,
				fkBypassOptionConnectivityPort
					Integer32
			 }

		-- 1.3.6.1.4.1.10428 9 1.101.2.14.2.1.1.1
		fkBypassOptionConnectivityAddress OBJECT-TYPE
			SYNTAX IpAddress
			MAX-ACCESS read-only
			STATUS current
			DESCRIPTION
				"The target IP address of bypass health-checking"
			::= { fkBypassOptionConnectivityEntry 1 }

		
		-- 1.3.6.1.4.1.10428 9 1.101.2.14.2.1.1.2
		fkBypassOptionConnectivityPort OBJECT-TYPE
			SYNTAX Integer32 (1..65535)
			MAX-ACCESS read-only
			STATUS current
			DESCRIPTION
				"The target port of bypass health-checking."
			::= { fkBypassOptionConnectivityEntry 2 }

		
		-- 1.3.6.1.4.1.10428 9 1.101.2.14.2.2
		fkBypassOptionConnectivityControl OBJECT IDENTIFIER ::= { fkBypassOption 2 }

		
		-- 1.3.6.1.4.1.10428 9 1.101.2.14.2.2.1
		fkBypassOptionConnectivityControlRequest OBJECT-TYPE
			SYNTAX INTEGER
				{
				setBypassConnectivity(1),
				unsetBypassConnectivity(2)
				}
			MAX-ACCESS read-write
			STATUS current
			DESCRIPTION
				"setBypassConnectivity(1)   : bypass-check-option connectivity (A.B.C.D) PORT
				unsetBypassConnectivity(2) : no bypass-check option connectivity"
			::= { fkBypassOptionConnectivityControl 1 }

		
--   1.3.6.1.4.1.10428 9 1.101.2.12.2.2
-- 1.3.6.1.4.1.10428 9 1.101.2.12.2.2
		-- 1.3.6.1.4.1.10428 9 1.101.2.14.2.2.2
		fkBypassOptionConnectivityControlStatus OBJECT-TYPE
			SYNTAX FkControlStatusType
			MAX-ACCESS read-only
			STATUS current
			DESCRIPTION
				"The status of user command."
			::= { fkBypassOptionConnectivityControl 2 }

		
--   1.3.6.1.4.1.10428 9 1.101.2.12.2.3
-- 1.3.6.1.4.1.10428 9 1.101.2.12.2.3
		-- 1.3.6.1.4.1.10428 9 1.101.2.14.2.2.3
		fkBypassOptionConnectivityControlTimer OBJECT-TYPE
			SYNTAX Integer32
			MAX-ACCESS read-write
			STATUS current
			DESCRIPTION
				"The maximum time for the manager for a long running user command."
			::= { fkBypassOptionConnectivityControl 3 }

		
--   1.3.6.1.4.1.10428 9 1.101.2.12.2.4
-- 1.3.6.1.4.1.10428 9 1.101.2.12.2.4
		-- 1.3.6.1.4.1.10428 9 1.101.2.14.2.2.4
		fkBypassOptionConnectivityControlTimeStamp OBJECT-TYPE
			SYNTAX TimeTicks
			MAX-ACCESS read-only
			STATUS current
			DESCRIPTION
				"The time stamp of the last command(end of command)."
			::= { fkBypassOptionConnectivityControl 4 }

		
--   1.3.6.1.4.1.10428 9 1.101.2.12.2.5
-- 1.3.6.1.4.1.10428 9 1.101.2.12.2.5
		-- 1.3.6.1.4.1.10428 9 1.101.2.14.2.2.5
		fkBypassOptionConnectivityControlReqResult OBJECT-TYPE
			SYNTAX FkControlRequestResultType
			MAX-ACCESS read-only
			STATUS current
			DESCRIPTION
				"The result of user command."
			::= { fkBypassOptionConnectivityControl 5 }

		
		-- 1.3.6.1.4.1.10428 9 1.101.2.14.2.2.6
		fkBypassOptionConnectivityControlAddress OBJECT-TYPE
			SYNTAX IpAddress
			MAX-ACCESS read-write
			STATUS current
			DESCRIPTION
				"The target IP address of bypass health-checking"
			::= { fkBypassOptionConnectivityControl 6 }

		
		-- 1.3.6.1.4.1.10428 9 1.101.2.14.2.2.7
		fkBypassOptionConnectivityControlPort OBJECT-TYPE
			SYNTAX Integer32
			MAX-ACCESS read-write
			STATUS current
			DESCRIPTION
				"he target port of bypass health-checking"
			::= { fkBypassOptionConnectivityControl 7 }

		
		-- 1.3.6.1.4.1.10428 9 1.101.2.14.2.3
		fkBypassOptionConnectivityNotification OBJECT IDENTIFIER ::= { fkBypassOption 3 }

		
		-- 1.3.6.1.4.1.10428 9 1.101.2.14.2.3.1
		fkBypassOptionConnectivitySet NOTIFICATION-TYPE
			OBJECTS { fkBypassOptionConnectivityControlRequest, fkBypassOptionConnectivityControlTimeStamp, fkBypassOptionConnectivityControlReqResult, fkBypassOptionConnectivityControlAddress, fkBypassOptionConnectivityControlPort
				 }
			STATUS current
			DESCRIPTION 
				"Description."
			::= { fkBypassOptionConnectivityNotification 1 }

		
		-- 1.3.6.1.4.1.10428 9 1.101.2.14.2.3.2
		fkBypassOptionConnectivityUnset NOTIFICATION-TYPE
			OBJECTS { fkBypassOptionConnectivityControlRequest, fkBypassOptionConnectivityControlTimeStamp, fkBypassOptionConnectivityControlReqResult, fkBypassOptionConnectivityControlAddress, fkBypassOptionConnectivityControlPort
				 }
			STATUS current
			DESCRIPTION 
				"Description."
			::= { fkBypassOptionConnectivityNotification 2 }

		
		-- 1.3.6.1.4.1.10428 9 1.101.2.14.2.4
		fkBypassOptionPingTable OBJECT-TYPE
			SYNTAX SEQUENCE OF FkBypassOptionPingEntry
			MAX-ACCESS not-accessible
			STATUS current
			DESCRIPTION
				"Description."
			::= { fkBypassOption 4 }

		
		-- 1.3.6.1.4.1.10428 9 1.101.2.14.2.4.1
		fkBypassOptionPingEntry OBJECT-TYPE
			SYNTAX FkBypassOptionPingEntry
			MAX-ACCESS not-accessible
			STATUS current
			DESCRIPTION
				"Description."
			INDEX { fkBypassOptionPingAddress }
			::= { fkBypassOptionPingTable 1 }

		
		FkBypassOptionPingEntry ::=
			SEQUENCE { 
				fkBypassOptionPingAddress
					IpAddress,
				fkBypassOptionPingTransInterval
					Integer32,
				fkBypassOptionPingTranNumber
					Integer32,
				fkBypassOptionPingReqInterval
					Integer32,
				fkBypassOptionPingReqTimeout
					Integer32,
				fkBypassOptionPingLossThresh
					Integer32
			 }

		-- 1.3.6.1.4.1.10428 9 1.101.2.14.2.4.1.1
		fkBypassOptionPingAddress OBJECT-TYPE
			SYNTAX IpAddress
			MAX-ACCESS read-only
			STATUS current
			DESCRIPTION
				"The target IP address of bypass ping health checking"
			::= { fkBypassOptionPingEntry 1 }

		
		-- 1.3.6.1.4.1.10428 9 1.101.2.14.2.4.1.2
		fkBypassOptionPingTransInterval OBJECT-TYPE
			SYNTAX Integer32
			MAX-ACCESS read-only
			STATUS current
			DESCRIPTION
				"The ping transaction interval"
			::= { fkBypassOptionPingEntry 2 }

		
		-- 1.3.6.1.4.1.10428 9 1.101.2.14.2.4.1.3
		fkBypassOptionPingTranNumber OBJECT-TYPE
			SYNTAX Integer32
			MAX-ACCESS read-only
			STATUS current
			DESCRIPTION
				"The ping transaction request number"
			::= { fkBypassOptionPingEntry 3 }

		
		-- 1.3.6.1.4.1.10428 9 1.101.2.14.2.4.1.4
		fkBypassOptionPingReqInterval OBJECT-TYPE
			SYNTAX Integer32
			MAX-ACCESS read-only
			STATUS current
			DESCRIPTION
				"The ping request interval"
			::= { fkBypassOptionPingEntry 4 }

		
		-- 1.3.6.1.4.1.10428 9 1.101.2.14.2.4.1.5
		fkBypassOptionPingReqTimeout OBJECT-TYPE
			SYNTAX Integer32
			MAX-ACCESS read-only
			STATUS current
			DESCRIPTION
				"The ping request timeout"
			::= { fkBypassOptionPingEntry 5 }

		
		-- 1.3.6.1.4.1.10428 9 1.101.2.14.2.4.1.6
		fkBypassOptionPingLossThresh OBJECT-TYPE
			SYNTAX Integer32
			MAX-ACCESS read-only
			STATUS current
			DESCRIPTION
				"The ping loss threshold"
			::= { fkBypassOptionPingEntry 6 }

		
		-- 1.3.6.1.4.1.10428 9 1.101.2.14.2.5
		fkBypassOptionPingControl OBJECT IDENTIFIER ::= { fkBypassOption 5 }

		
		-- 1.3.6.1.4.1.10428 9 1.101.2.14.2.5.1
		fkBypassOptionPingControlRequest OBJECT-TYPE
			SYNTAX INTEGER
				{
				setBypassPing(1),
				unsetBypassPing(2)
				}
			MAX-ACCESS read-write
			STATUS current
			DESCRIPTION
				"The request of a user command."
			::= { fkBypassOptionPingControl 1 }
-- 
-- 
		
--   1.3.6.1.4.1.10428 9 1.101.2.12.2.2
-- 1.3.6.1.4.1.10428 9 1.101.2.12.2.2
		-- 1.3.6.1.4.1.10428 9 1.101.2.14.2.5.2
		fkBypassOptionPingControlStatus OBJECT-TYPE
			SYNTAX FkControlStatusType
			MAX-ACCESS read-only
			STATUS current
			DESCRIPTION
				"The status of user command."
			::= { fkBypassOptionPingControl 2 }

		
--   1.3.6.1.4.1.10428 9 1.101.2.12.2.3
-- 1.3.6.1.4.1.10428 9 1.101.2.12.2.3
		-- 1.3.6.1.4.1.10428 9 1.101.2.14.2.5.3
		fkBypassOptionPingControlTimer OBJECT-TYPE
			SYNTAX Integer32
			MAX-ACCESS read-write
			STATUS current
			DESCRIPTION
				"The maximum time for the manager for a long running user command."
			::= { fkBypassOptionPingControl 3 }

		
--   1.3.6.1.4.1.10428 9 1.101.2.12.2.4
-- 1.3.6.1.4.1.10428 9 1.101.2.12.2.4
		-- 1.3.6.1.4.1.10428 9 1.101.2.14.2.5.4
		fkBypassOptionPingControlTimeStamp OBJECT-TYPE
			SYNTAX TimeTicks
			MAX-ACCESS read-only
			STATUS current
			DESCRIPTION
				"The time stamp of the last command(end of command)."
			::= { fkBypassOptionPingControl 4 }

		
--   1.3.6.1.4.1.10428 9 1.101.2.12.2.5
-- 1.3.6.1.4.1.10428 9 1.101.2.12.2.5
		-- 1.3.6.1.4.1.10428 9 1.101.2.14.2.5.5
		fkBypassOptionPingControlReqResult OBJECT-TYPE
			SYNTAX FkControlRequestResultType
			MAX-ACCESS read-only
			STATUS current
			DESCRIPTION
				"The result of user command."
			::= { fkBypassOptionPingControl 5 }

		
		-- 1.3.6.1.4.1.10428 9 1.101.2.14.2.5.6
		fkBypassOptionPingControlAddress OBJECT-TYPE
			SYNTAX IpAddress
			MAX-ACCESS read-write
			STATUS current
			DESCRIPTION
				"The target IP address of bypass ping health-checking"
			::= { fkBypassOptionPingControl 6 }

		
		-- 1.3.6.1.4.1.10428 9 1.101.2.14.2.5.7
		fkBypassOptionPingControlTransInterval OBJECT-TYPE
			SYNTAX Integer32
			MAX-ACCESS read-write
			STATUS current
			DESCRIPTION
				"The ping transaction interval"
			::= { fkBypassOptionPingControl 7 }

		
		-- 1.3.6.1.4.1.10428 9 1.101.2.14.2.5.8
		fkBypassOptionPingControlTranNumber OBJECT-TYPE
			SYNTAX Integer32
			MAX-ACCESS read-write
			STATUS current
			DESCRIPTION
				"The ping transaction request number"
			::= { fkBypassOptionPingControl 8 }

		
		-- 1.3.6.1.4.1.10428 9 1.101.2.14.2.5.9
		fkBypassOptionPingControlReqInterval OBJECT-TYPE
			SYNTAX Integer32
			MAX-ACCESS read-write
			STATUS current
			DESCRIPTION
				"The ping request interval"
			::= { fkBypassOptionPingControl 9 }

		
		-- 1.3.6.1.4.1.10428 9 1.101.2.14.2.5.10
		fkBypassOptionPingControlReqTimeout OBJECT-TYPE
			SYNTAX Integer32
			MAX-ACCESS read-write
			STATUS current
			DESCRIPTION
				"The ping request timeout"
			::= { fkBypassOptionPingControl 10 }

		
		-- 1.3.6.1.4.1.10428 9 1.101.2.14.2.5.11
		fkBypassOptionPingControlLossThresh OBJECT-TYPE
			SYNTAX Integer32
			MAX-ACCESS read-write
			STATUS current
			DESCRIPTION
				"The ping loss threshold"
			::= { fkBypassOptionPingControl 11 }

		
		-- 1.3.6.1.4.1.10428 9 1.101.2.14.2.6
		fkBypassOptionPingNotification OBJECT IDENTIFIER ::= { fkBypassOption 6 }

		
		-- 1.3.6.1.4.1.10428 9 1.101.2.14.2.6.1
		fkBypassOptionPingSet NOTIFICATION-TYPE
			OBJECTS { fkBypassOptionPingControlRequest, fkBypassOptionPingControlTimeStamp, fkBypassOptionPingControlReqResult, fkBypassOptionPingControlTranNumber, fkBypassOptionPingControlReqInterval, 
				fkBypassOptionPingControlReqTimeout, fkBypassOptionPingControlLossThresh, fkBypassOptionPingControlAddress, fkBypassOptionPingControlTransInterval }
			STATUS current
			DESCRIPTION 
				"Description."
			::= { fkBypassOptionPingNotification 1 }

		
		-- 1.3.6.1.4.1.10428 9 1.101.2.14.2.6.2
		fkBypassOptionPingUnset NOTIFICATION-TYPE
			OBJECTS { fkBypassOptionPingControlRequest, fkBypassOptionPingControlTimeStamp, fkBypassOptionPingControlReqResult, fkBypassOptionPingControlAddress }
			STATUS current
			DESCRIPTION 
				"Description."
			::= { fkBypassOptionPingNotification 2 }

		
		-- 1.3.6.1.4.1.10428 9 1.101.2.14.2.7
		fkBypassOptionLinkMonitorTable OBJECT-TYPE
			SYNTAX SEQUENCE OF FkBypassOptionLinkMonitorEntry
			MAX-ACCESS not-accessible
			STATUS current
			DESCRIPTION
				"Description."
			::= { fkBypassOption 7 }

		
		-- 1.3.6.1.4.1.10428 9 1.101.2.14.2.7.1
		fkBypassOptionLinkMonitorEntry OBJECT-TYPE
			SYNTAX FkBypassOptionLinkMonitorEntry
			MAX-ACCESS not-accessible
			STATUS current
			DESCRIPTION
				"Description."
			INDEX { fkBypassOptionLinkMonitorPort }
			::= { fkBypassOptionLinkMonitorTable 1 }

		
		FkBypassOptionLinkMonitorEntry ::=
			SEQUENCE { 
				fkBypassOptionLinkMonitorPort
					Integer32,
				fkBypassOptionLinkMonitorPortStatus
					INTEGER
			 }

		-- 1.3.6.1.4.1.10428 9 1.101.2.14.2.7.1.1
		fkBypassOptionLinkMonitorPort OBJECT-TYPE
			SYNTAX Integer32 (1..65535)
			MAX-ACCESS read-only
			STATUS current
			DESCRIPTION
				"The port of bypass link health-checking"
			::= { fkBypassOptionLinkMonitorEntry 1 }

		
		-- 1.3.6.1.4.1.10428 9 1.101.2.14.2.7.1.2
		fkBypassOptionLinkMonitorPortStatus OBJECT-TYPE
			SYNTAX INTEGER { enable(1) }
			MAX-ACCESS read-only
			STATUS current
			DESCRIPTION
				"The port status of bypass link health-checking"
			::= { fkBypassOptionLinkMonitorEntry 2 }

		
		-- 1.3.6.1.4.1.10428 9 1.101.2.14.2.8
		fkBypassOptionLinkMonitorControl OBJECT IDENTIFIER ::= { fkBypassOption 8 }

		
		-- 1.3.6.1.4.1.10428 9 1.101.2.14.2.8.1
		fkBypassOptionLinkMonitorControlRequest OBJECT-TYPE
			SYNTAX INTEGER { setBypassLinkMonitor(1) }
			MAX-ACCESS read-write
			STATUS current
			DESCRIPTION
				"The request of a user command."
			::= { fkBypassOptionLinkMonitorControl 1 }
-- 
-- 
		
--   1.3.6.1.4.1.10428 9 1.101.2.12.2.2
-- 1.3.6.1.4.1.10428 9 1.101.2.12.2.2
		-- 1.3.6.1.4.1.10428 9 1.101.2.14.2.8.2
		fkBypassOptionLinkMonitorControlStatus OBJECT-TYPE
			SYNTAX FkControlStatusType
			MAX-ACCESS read-only
			STATUS current
			DESCRIPTION
				"The status of user command."
			::= { fkBypassOptionLinkMonitorControl 2 }

		
--   1.3.6.1.4.1.10428 9 1.101.2.12.2.3
-- 1.3.6.1.4.1.10428 9 1.101.2.12.2.3
		-- 1.3.6.1.4.1.10428 9 1.101.2.14.2.8.3
		fkBypassOptionLinkMonitorControlTimer OBJECT-TYPE
			SYNTAX Integer32
			MAX-ACCESS read-write
			STATUS current
			DESCRIPTION
				"The maximum time for the manager for a long running user command."
			::= { fkBypassOptionLinkMonitorControl 3 }

		
--   1.3.6.1.4.1.10428 9 1.101.2.12.2.4
-- 1.3.6.1.4.1.10428 9 1.101.2.12.2.4
		-- 1.3.6.1.4.1.10428 9 1.101.2.14.2.8.4
		fkBypassOptionLinkMonitorControlTimeStamp OBJECT-TYPE
			SYNTAX TimeTicks
			MAX-ACCESS read-only
			STATUS current
			DESCRIPTION
				"The time stamp of the last command(end of command)."
			::= { fkBypassOptionLinkMonitorControl 4 }

		
--   1.3.6.1.4.1.10428 9 1.101.2.12.2.5
-- 1.3.6.1.4.1.10428 9 1.101.2.12.2.5
		-- 1.3.6.1.4.1.10428 9 1.101.2.14.2.8.5
		fkBypassOptionLinkMonitorControlReqResult OBJECT-TYPE
			SYNTAX FkControlRequestResultType
			MAX-ACCESS read-only
			STATUS current
			DESCRIPTION
				"The result of user command."
			::= { fkBypassOptionLinkMonitorControl 5 }

		
		-- 1.3.6.1.4.1.10428 9 1.101.2.14.2.8.6
		fkBypassOptionLinkMonitorControlPort OBJECT-TYPE
			SYNTAX Integer32
			MAX-ACCESS read-write
			STATUS current
			DESCRIPTION
				"The port of bypass link health-checking"
			::= { fkBypassOptionLinkMonitorControl 6 }

		
		-- 1.3.6.1.4.1.10428 9 1.101.2.14.2.8.7
		fkBypassOptionLinkMonitorControlPortStatus OBJECT-TYPE
			SYNTAX INTEGER
				{
				enable(1),
				disable(2)
				}
			MAX-ACCESS read-write
			STATUS current
			DESCRIPTION
				"The port status of bypass link health-checking"
			::= { fkBypassOptionLinkMonitorControl 7 }

		
		-- 1.3.6.1.4.1.10428 9 1.101.2.14.2.9
		fkBypassOptioLinkMonitorNotification OBJECT IDENTIFIER ::= { fkBypassOption 9 }

		
		-- 1.3.6.1.4.1.10428 9 1.101.2.14.2.9.1
		fkBypassOptionLinkMonitorChanged NOTIFICATION-TYPE
			OBJECTS { fkBypassOptionLinkMonitorControlRequest, fkBypassOptionLinkMonitorControlStatus, fkBypassOptionLinkMonitorControlTimeStamp, fkBypassOptionLinkMonitorControlReqResult, fkBypassOptionLinkMonitorControlPort, 
				fkBypassOptionLinkMonitorControlPortStatus }
			STATUS current
			DESCRIPTION 
				"Description."
			::= { fkBypassOptioLinkMonitorNotification 1 }

		
--     1.3.6.1.4.1.10428 9 1.101.2.12
-- 1.3.6.1.4.1.10428 9 1.101.2.13
-- 1.3.6.1.4.1.10428 9 1.101.2.13
-- 1.3.6.1.4.1.10428 9 1.101.2.14
		-- 1.3.6.1.4.1.10428 9 1.101.2.15
		fkDeviceGroup OBJECT-GROUP
			OBJECTS { fkRfConnectStatus, fkRfPortIndex, fkRfPortAdminStatus, fkRfPortOperStatus, fkDeviceEthernetPortNum, 
				fkDevicePowerNum, fkDeviceFanModuleNum, fkDeviceTemperatureNum, fkDeviceFanStartTemperature, fkDeviceFanStopTemperature, 
				fkDeviceControlRequest, fkDeviceControlStatus, fkDeviceControlTimer, fkDeviceControlTimeStamp, fkDeviceControlReqResult, 
				fkDeviceControlFanStartTemperature, fkDeviceControlFanStopTemperature, fkEthernetPortIndex, fkEthernetPortPhyIndex, fkEthernetPortType, 
				fkEthernetPortAdminStatus, fkEthernetPortOperStatus, fkEthernetPortTransmissionRate, fkEthernetPortDuplexMode, fkEthernetPortFlowControl, 
				fkEthernetPortNegotiationMode, fkEthernetPortJumboFrameSize, fkEthernetPortSfpTransceiver, fkEthernetPortSfpVendorName, fkEthernetPortSfpVendorPartNumber, 
				fkEthernetPortSfpVendorRevision, fkEthernetPortSfpVendorSerialNumber, fkEthernetPortSfpDateCode, fkEthernetPortPhysicalRemoteChassis, fkEthernetPortPhysicalRemoteSlot, 
				fkEthernetPortPhysicalRemotePort, fkEthernetPortPhysicalLinkDiscoveryMode, fkEthernetPortControlRequest, fkEthernetPortControlStatus, fkEthernetPortControlTimer, 
				fkEthernetPortControlTimeStamp, fkEthernetPortControlReqResult, fkEthernetPortControlIndex, fkEthernetPortControlType, fkEthernetPortControlAdminStatus, 
				fkEthernetPortControlTransmissionRate, fkEthernetPortControlDuplexMode, fkEthernetPortControlFlowControl, fkEthernetPortControlJumboFrameSize, fkEthernetPortControlPhysicalRemoteChassis, 
				fkEthernetPortControlPhysicalRemoteSlot, fkEthernetPortControlPhysicalRemotePort, fkEthernetPortControlPhysicalLinkDiscoveryMode, fkPowerIndex, fkPowerPhyIndex, 
				fkPowerState, fkFanModuleIndex, fkFanModulePhyIndex, fkFanModuleUnitNum, fkFanModuleAdminState, 
				fkFanModuleControlRequest, fkFanModuleControlStatus, fkFanModuleControlTimer, fkFanModuleControlTimeStamp, fkFanModuleControlReqResult, 
				fkFanModuleControlIndex, fkFanModuleControlAdminState, fkFanUnitIndex, fkFanUnitOperState, fkTemperatureIndex, 
				fkTemperatureState, fkTemperatureValue, fkBatteryIndex, fkDoorStatus, fkOperationPowerType, 
				fkOperationPowerInfo, fkPSUACPowerState, fkPSUTemperture, fkPSUOutVoltage, fkPSUOverTemp, 
				fkPSUFirmwareVer, fkRBUEquipState, fkRBUModeStaus, fkBatteryBackupFile, fkBatteryBackupControlRequest, 
				fkBatteryBackupControlStatus, fkBatteryBackupControlTimer, fkBatteryBackupControlTimeStamp, fkBatteryBackupControlReqResult, fkBatteryBackupControlServerIP, 
				fkBatteryBackupControlUserID, fkBatteryBackupControlPassword, fkBatteryBackupControlFlag, fkBatteryBackupControlLocalFile, fkBatteryBackupControlRemoteFile, 
				fkCpuProcessor, fkCpuModel, fkCpuRevision, fkCpuBogomips, fkCpuManufacturer, 
				fkCpuClock, fkCpuBusClock, fkRBUTemperature1, fkPSUTempThreshold, fkRBUTemperature2, 
				fkRBUOutVoltage, fkRBUChargeCurrent, fkRBURemainCapacity, fkRBUOverTemp, fkBatteryLow, 
				fkRBUBTStatus, fkRBUBTThreshold, fkRBURechargeVoltage, fkBatteryCellStatus, fkBPSUACHardwareVer, 
				fkBatteryControlRequest, fkBatteryControlStatus, fkBatteryControlTimer, fkBatteryControlTimeStamp, fkBatteryControlReqResult, 
				fkBatteryControlRBUBTStatus, fkBatteryControlRBUBTThreshold, fkBatteryControlRBURechargeVoltage, fkBatteryControlTemperThresh1, fkBatteryControlTemperThresh2, 
				fkRBUTempHighThreshold, fkPowerType, fkClockModuleIndex, fkClockModuleBoardId, fkClockModuleInstallStatus, 
				fkClockModuleInitStatus, fkSlotSystemIndex, fkSlotSystemUptime, fkSlotSystemModelName, fkSlotSystemSerialNumber, 
				fkSlotSystemHWVersion, fkSlotSystemBLVersion, fkSlotSystemSWCompatibility, fkSlotSystemOSVersion, fkSlotSystemMacAddress, 
				fkSlotSystemCPULoadAll, fkSlotSystemCPULoadInterrupt, fkSlotSystemMemoryTotal, fkSlotSystemMemoryFree, fkSlotSystemMemoryShared, 
				fkSlotSystemMemoryBuffers, fkSlotSystemMemoryCached, fkSlotSystemMemorySwapTotal, fkSlotSystemMemorySwapFree, fkSlotSystemBootReason, 
				fkSlotSystemBootTime, fkSlotSystemVoltage, fkSlotSystemControlRequest, fkSlotSystemControlStatus, fkSlotSystemControlTimer, 
				fkSlotSystemControlTimeStamp, fkSlotSystemControlReqResult, fkSlotSystemControlSlotIndex, fkSlotStatusPlan, fkSlotStatusPlanCardType, 
				fkSlotStatusCurrentInstall, fkSlotStatusCurrentInstallCardType, fkSlotStatusCardOperation, fkSlotStatusLock, fkSlotStatusUpgradeMode, 
				fkSlotStatusActionEvent, fkSlotStatusState, fkSlotStatusControlRequest, fkSlotStatusControlStatus, fkSlotStatusControlTimer, 
				fkSlotStatusControlTimeStamp, fkSlotStatusControlReqResult, fkSlotStatusControlSlotIndex, fkSlotStatusControlPlanCardType, fkSlotStatusControlUpgradeMode, 
				fkSlotNosVersion, fkSlotNosRevision, fkSlotNosSize, fkSlotNosUpgradeStatus, fkSlotNosControlRequest, 
				fkSlotNosControlStatus, fkSlotNosControlTimer, fkSlotNosControlTimeStamp, fkSlotNosControlReqResult, fkSlotNosControlSlotIndex, 
				fkSlotReleasedNIUNosVersion, fkSlotReleasedNIUNosRevision, fkSlotReleasedNIUNosSize, fkSlotReleasedGPIUNosVersion, fkSlotReleasedGPIUNosRevision, 
				fkSlotReleasedGPIUNosSize, fkSlotSystemPowerLevelStatus, fkSlotPowerMonStatus, fkSlotPowerMonVoltage, fkEthernetPortDMIIndex, 
				fkEthernetPortDMITemper, fkEthernetPortDMIVoltage, fkEthernetPortDMITxBias, fkEthernetPortDMITxPower, fkEthernetPortDMIRxPower, 
				fkEthernetPortSfpTransceiverType, fkSlotNosControlUpDownMethod, fkSlotNosControlUpDownFlag, fkSlotNosControlServerAddress, fkSlotNosControlUserID, 
				fkSlotNosControlPassword, fkSlotNosControlFileName, fkFanUnitSpeed, fkSlotSystemInfoLEDStatus, fkFanModuleSpeedThreshold, 
				fkFanModuleControlSpeedThreshold, fkEthernetPortSfpTransceiverDetailType, fkClockModuleOPMode, fkClockInfoInSrcType, fkClockInfoInSrcAISStatus, 
				fkClockInfoInSrcLoSStatus, fkClockInfoInSrcLDSCStatus, fkClockInfoInSrcNtrClockType, fkDeviceJumboFrameStatus, fkDeviceControlJumboFrameStatus, 
				fkPowerPSUType, fkSlotSystemInfoPackageVersion, fkEthernetSfpIndex, fkEthernetSfpTransceiver, fkEthernetSfpVendorName, 
				fkEthernetSfpVendorPartNumber, fkEthernetSfpDateCode, fkEthernetSfpTransceiverType, fkEthernetSfpTransceiverDetailType, fkTemperatureHighThreshold, 
				fkTemperatureLowThreshold, fkTemperatureControlRequest, fkTemperatureControlStatus, fkTemperatureControlTimer, fkTemperatureControlTimeStamp, 
				fkTemperatureControlReqResult, fkTemperatureControlIndex, fkTemperatureControlHighThreshold, fkTemperatureControlLowThreshold, fkEthernetSFPControlRequest, 
				fkEthernetSFPControlStatus, fkEthernetSFPControlTimer, fkEthernetSFPControlTimeStamp, fkEthernetSFPControlReqResult, fkEthernetSFPControlIndex, 
				fkTemperatureWarnHighThreshold, fkTemperatureWarnLowThreshold, fkTemperatureWarnDuration, fkTemperatureAlarmHighThreshold, fkTemperatureAlarmLowThreshold, 
				fkTemperatureAlarmDuration, fkTemperatureControlDuration, fkSlotPowerMonIndex, fkEthernetPortSlotIndex, fkEthernetPortSlotPortIndex, 
				fkEthernetSfpVendorRevision, fkEthernetSfpVendorSerialNumber, fkEthernetSfpTransceiverCodes, fkSlotNosStbVersion, fkSlotNosStbRevision, 
				fkSlotNosStbSize, fkDeviceEnvironmentMonitoringStatus, fkDeviceControlEnvironmentMonitoringStatus, fkRfPowerStatus, fkSlotAiuRunStatus, 
				fkSlotAiuAlarmStatus, fkEthernetPortAdminTransmissionRate, fkEthernetPortAdminDuplexMode, fkEthernetPortAdminFlowControl, fkEthernetPortAdminNegotiationMode, 
				fkSlotReleasedSIUNosVersion, fkSlotReleasedSIUNosRevision, fkSlotReleasedSIUNosSize, fkEMInputIndex, fkEMAlarmString, 
				fkEMAlarmSeverity, fkEMmode, fkEMControlRequest, fkEMControlStatus, fkEMControlInputIndex, 
				fkEMControlAlarmString, fkEMControlAlarmSeverity, fkEMControlmode, fkEthernetSfpSpeed, fkEthernetSfpLength, 
				fkEthernetSfpWaveLength, fkRfEthertype, fkRfSrcAddress, fkRfDesAddress, fkRBUTempLowThreshold, 
				fkEthernetPortControlNegotiationMode, fkSlotStatusPower, fkSlotStatusSerialNumber, fkEMControlTimer, fkEMControlTimeStamp, 
				fkEthernetPortAdminReason, fkEthernetSFPMultimodeLengthOm1, fkEthernetSFPMultimodeLengthOm2, fkEthernetSFPMultimodeLengthOm3, fkEMControlReqResult, 
				fkRfBaseControlRequest, fkRfBaseControlStatus, fkRfBaseControlTimer, fkRfBaseControlTimeStamp, fkRfBaseControlReqResult, 
				fkRfBaseControlRfEthertype, fkRfPortControlRequest, fkRfPortControlStatus, fkRfPortControlTimer, fkRfPortControlTimeStamp, 
				fkRfPortControlReqResult, fkRfPortControlIndex, fkBypassMode, fkBypassStatus, fkBypassBaseControlRequest, 
				fkBypassBaseControlStatus, fkBypassBaseControlTimer, fkBypassBaseControlTimeStamp, fkBypassBaseControlReqResult, fkBypassBaseControlMode, 
				fkBypassOptionConnectivityAddress, fkBypassOptionConnectivityPort, fkBypassOptionConnectivityControlRequest, fkBypassOptionConnectivityControlStatus, fkBypassOptionConnectivityControlTimer, 
				fkBypassOptionConnectivityControlTimeStamp, fkBypassOptionConnectivityControlReqResult, fkBypassOptionConnectivityControlAddress, fkBypassOptionConnectivityControlPort, fkBypassOptionPingAddress, 
				fkBypassOptionPingTransInterval, fkBypassOptionPingTranNumber, fkBypassOptionPingReqInterval, fkBypassOptionPingReqTimeout, fkBypassOptionPingLossThresh, 
				fkBypassOptionPingControlRequest, fkBypassOptionPingControlStatus, fkBypassOptionPingControlTimer, fkBypassOptionPingControlTimeStamp, fkBypassOptionPingControlReqResult, 
				fkBypassOptionPingControlAddress, fkBypassOptionPingControlTransInterval, fkBypassOptionPingControlTranNumber, fkBypassOptionPingControlReqInterval, fkBypassOptionPingControlReqTimeout, 
				fkBypassOptionPingControlLossThresh, fkBypassOptionLinkMonitorPort, fkBypassOptionLinkMonitorPortStatus, fkBypassOptionLinkMonitorControlRequest, fkBypassOptionLinkMonitorControlStatus, 
				fkBypassOptionLinkMonitorControlTimer, fkBypassOptionLinkMonitorControlTimeStamp, fkBypassOptionLinkMonitorControlReqResult, fkBypassOptionLinkMonitorControlPort, fkBypassOptionLinkMonitorControlPortStatus, 
				fkRfPortControlAdminStatus, fkClockInfoInSrcStatus }
			STATUS current
			DESCRIPTION 
				"Description."
			::= { fkDevice 15 }

		
--     1.3.6.1.4.1.10428 9 1.101.2.13
-- 1.3.6.1.4.1.10428 9 1.101.2.14
-- 1.3.6.1.4.1.10428 9 1.101.2.14
-- 1.3.6.1.4.1.10428 9 1.101.2.15
		-- 1.3.6.1.4.1.10428 9 1.101.2.16
		fkDeviceNotificationGroup NOTIFICATION-GROUP
			NOTIFICATIONS { fkDeviceTemperatureThresholdChanged, fkEthernetPortChanged, fkFanAdminStateChanged, fkBatteryBackupProfileChanged, fkBatteryBackupUpgraded, 
				fkSlotSystemRestart, fkSlotStatusLocked, fkSlotStatusUnlocked, fkSlotStatusPlanning, fkSlotStatusNoPlanning, 
				fkSlotStatusUpgradeModeChanged, fkSlotNosUpgrade, fkSlotStatusPowerUp, fkSlotStatusPowerDown, fkSlotStatusPowerReset, 
				fkSlotNosDownload, fkSlotNosBootloaderUpgrade, fkFanSpeedThresholdChanged, fkDeviceJumboFrameChanged, fkTemperatureThresholdChanged, 
				fkDeviceLEDTestChanged, fkEthernetSFPRemoteReset, fkRfPortStatusChanged, fkDeviceEnvironmentMonitoringStatusChanged, fkEMChanged, 
				fkEMDeleted, fkRFBaseEthertypeChanged, fkRFBaseEthertypeResetChanged, fkBypassModeChanged, fkBypassOptionConnectivitySet, 
				fkBypassOptionConnectivityUnset, fkBypassOptionPingSet, fkBypassOptionPingUnset, fkBypassOptionLinkMonitorChanged, fkBatteryBackupTableCleared, 
				fkBatteryForceChargeChanged, fkBatteryChargingStartChanged, fkBatteryForceChargeNonStopChanged, fkBatteryRBUBTStatusChanged, fkBatteryRBUBTThresholdChanged, 
				fkBatteryRBURechargeVoltageChanged, fkBatteryPsuAcTemperThreshChanged, fkBatteryRBUTemperThreshChanged }
			STATUS current
			DESCRIPTION 
				"Description."
			::= { fkDevice 16 }

		
	
	END

--
-- FK-DEVICE-MIB.my
--
