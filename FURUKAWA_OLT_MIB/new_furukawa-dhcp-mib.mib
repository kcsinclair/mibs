FKOLTG1040-DHCP-MIB DEFINITIONS ::= BEGIN

IMPORTS
    TimeTicks, MODULE-IDENTITY, enterprises, mib-2
        FROM SNMPv2-SMI
    OBJECT-TYPE
        FROM RFC-1212
    IpAddress
        FROM RFC1155-SMI
    DisplayString
        FROM SNMPv2-TC
    SubnetConfRangeIndex, SubnetConfIndex
        FROM FKOLTG1040-TC
    fkoltg1040Mgmt
        FROM FKOLTG1040-SMI;
    
transmission   OBJECT IDENTIFIER ::= { mib-2 10 }

snmpV2         OBJECT IDENTIFIER ::= { internet 6 }

fkoltg1040SwitchMIB OBJECT IDENTIFIER ::= { fkoltg1040Mgmt 1 }

fkoltg1040SwitchMIBObjects  OBJECT IDENTIFIER ::= { fkoltg1040SwitchMIB 1 }

dsDhcpMIBObjects  OBJECT IDENTIFIER ::= { fkoltg1040SwitchMIBObjects 5 }

dsDhcpDaemonConf OBJECT IDENTIFIER ::= { dsDhcpMIBObjects 1 }

dsDefaultLeaseTime      OBJECT-TYPE
    SYNTAX      INTEGER
    ACCESS  read-only   -- read-write -> read-only
    STATUS      mandatory
    DESCRIPTION
        "The default ip-address lease time."
    ::= { dsDhcpDaemonConf 1 }

dsMaxLeaseTime          OBJECT-TYPE
    SYNTAX      INTEGER
    ACCESS  read-only
    STATUS      mandatory
    DESCRIPTION
        "The maximum ip-address lease time."
    ::= { dsDhcpDaemonConf 2 }

dsSubnetMask            OBJECT-TYPE
    SYNTAX      IpAddress
    ACCESS  read-only
    STATUS      mandatory
    DESCRIPTION
        "The default sub-net mask."
    ::= { dsDhcpDaemonConf 3 }

dsBroadcastAddress      OBJECT-TYPE
    SYNTAX      IpAddress
    ACCESS  read-only
    STATUS      obsolete
    DESCRIPTION
        "The default broadcast address."
    ::= { dsDhcpDaemonConf 4 }
         
dsDomainName            OBJECT-TYPE
    SYNTAX      DisplayString
    ACCESS  read-only
    STATUS      mandatory
    DESCRIPTION
        "The name of domain."
    ::= { dsDhcpDaemonConf 5 }

dsDomainNameServerTable OBJECT-TYPE
    SYNTAX      SEQUENCE OF DomainNameServerEntry
    ACCESS  not-accessible
    STATUS      mandatory
    DESCRIPTION
        "This table contains all server ip address"    
    ::= { dsDhcpDaemonConf 6 }

dsDomainNameServerEntry         OBJECT-TYPE
    SYNTAX      DomainNameServerEntry
    ACCESS  not-accessible
    STATUS      mandatory
    DESCRIPTION
        "This table contains all server ip address"
    INDEX       { dsDomainNameServerIpIdx }
    ::= { dsDomainNameServerTable 1 }

DomainNameServerEntry   ::= SEQUENCE {
    dsDomainNameServerIpIdx     INTEGER,
    dsDomainNameServerIp                IpAddress
        }

dsDomainNameServerIpIdx OBJECT-TYPE
    SYNTAX      INTEGER
    ACCESS  read-only
    STATUS      mandatory
    DESCRIPTION
        "The index of ip address."
    ::= { dsDomainNameServerEntry 1 }

dsDomainNameServerIp    OBJECT-TYPE
    SYNTAX      IpAddress
    ACCESS  read-only
    STATUS      mandatory
    DESCRIPTION
        "The ip address of domain name server."
    ::= { dsDomainNameServerEntry 2 }

dsSubnetConfTable               OBJECT-TYPE
    SYNTAX      SEQUENCE OF SubnetConfEntry
    ACCESS  not-accessible
    STATUS      mandatory
    DESCRIPTION
        "The subnet address table"
    ::= { dsDhcpDaemonConf 7 }

dsSubnetConfEntry       OBJECT-TYPE
    SYNTAX      SubnetConfEntry
    ACCESS  not-accessible
    STATUS      mandatory
    DESCRIPTION
        "The subnet address table." 
        INDEX   { dsSubnetConfIndex }  
    ::= { dsSubnetConfTable 1 }

SubnetConfEntry ::= SEQUENCE {
    dsSubnetConfName            DisplayString,
    dsSubnetConfSubnet          IpAddress,
    dsSubnetConfNetmask         IpAddress,
    dsSubnetConfBroadcastAddr   IpAddress,
    dsSubnetConfDefaultLeaseTime        INTEGER,
    dsSubnetConfMaxLeaseTime    INTEGER,
    dsSubnetConfTotalCount      INTEGER,
    dsSubnetConfAllocatedCount  INTEGER,
    dsSubnetConfRouters         IpAddress,
    dsSubnetConfRangeBitmap             OCTET STRING,
    dsSubnetConfIndex           SubnetConfIndex,
    dsSubnetConfDomainName  OCTET STRING
        }

dsSubnetConfName                OBJECT-TYPE
    SYNTAX      DisplayString
    ACCESS  read-only
    STATUS      mandatory
    DESCRIPTION
        "The subnet of this table entry." 
    ::= { dsSubnetConfEntry 1 }

dsSubnetConfSubnet      OBJECT-TYPE
    SYNTAX      IpAddress
    ACCESS  read-only
    STATUS      mandatory
    DESCRIPTION
        "The subnet of this table entry." 
    ::= { dsSubnetConfEntry 2 }
    
dsSubnetConfNetmask     OBJECT-TYPE
    SYNTAX      IpAddress
    ACCESS  read-only
    STATUS      mandatory
    DESCRIPTION
        "The netmask of this table entry."
    ::= { dsSubnetConfEntry 3 }

dsSubnetConfBroadcastAddr       OBJECT-TYPE
    SYNTAX      IpAddress
    ACCESS  read-only
    STATUS      obsolete
    DESCRIPTION
        "The Broadcast address of this table entry."
    ::= { dsSubnetConfEntry 4 }

dsSubnetConfDefaultLeaseTime    OBJECT-TYPE
    SYNTAX      INTEGER
    ACCESS  read-only
    STATUS      mandatory
    DESCRIPTION
        "The default ip-address lease time."
    ::= { dsSubnetConfEntry 5 }

dsSubnetConfMaxLeaseTime        OBJECT-TYPE
    SYNTAX      INTEGER
    ACCESS  read-only
    STATUS      mandatory
    DESCRIPTION
        "The maximum ip-address lease time."
    ::= { dsSubnetConfEntry 6 }

dsSubnetConfTotalCount  OBJECT-TYPE
    SYNTAX      INTEGER
    ACCESS  read-only
    STATUS      mandatory
    DESCRIPTION
        "The total number of ip-addresses in this group."
    ::= { dsSubnetConfEntry 7 }

dsSubnetConfAllocatedCount      OBJECT-TYPE
    SYNTAX      INTEGER
    ACCESS  read-only
    STATUS      mandatory
    DESCRIPTION
        "The total number of allocated ip-addresses in this group."
    ::= { dsSubnetConfEntry 8 }

dsSubnetConfRouters     OBJECT-TYPE
    SYNTAX      IpAddress
    ACCESS  read-only
    STATUS      mandatory
    DESCRIPTION
        "The router address of this table entry."
    ::= { dsSubnetConfEntry 9 }

dsSubnetConfRangeBitmap OBJECT-TYPE
    SYNTAX      OCTET STRING (SIZE(0..32))
    ACCESS  read-only
    STATUS      obsolete
    DESCRIPTION
        "The bitmap of free addresses."
    ::= { dsSubnetConfEntry 10 }    
        
dsSubnetConfIndex OBJECT-TYPE
    SYNTAX SubnetConfIndex
    ACCESS  not-accessible
    STATUS      mandatory
    DESCRIPTION
        "The Index of subnet."
    ::= { dsSubnetConfEntry 11 }    

dsSubnetConfDomainName OBJECT-TYPE
        SYNTAX OCTET STRING (SIZE(0..64))
    ACCESS  read-only
    STATUS      mandatory
    DESCRIPTION
        "The domain suffix of subnet."
    ::= { dsSubnetConfEntry 12 }    
   
   
dsSubnetConfRangeTable  OBJECT-TYPE
    SYNTAX      SEQUENCE OF SubnetConfRangeEntry
    ACCESS  not-accessible
    STATUS      mandatory   
    DESCRIPTION
        "The subnet ip table."    
    ::= { dsDhcpDaemonConf 8 }

dsSubnetConfRangeEntry  OBJECT-TYPE
    SYNTAX      SubnetConfRangeEntry
    ACCESS  not-accessible
    STATUS      mandatory
    DESCRIPTION
        "The subnet ip table."
    INDEX { dsSubnetConfIndex, dsSubnetConfRangeIndex }
--      INDEX   { SubnetConfIndex, SubnetConfRangeIndex }
    ::= { dsSubnetConfRangeTable 1 }

SubnetConfRangeEntry    ::= SEQUENCE {
    dsSubnetConfRangeStart      IpAddress,
    dsSubnetConfRangeEnd        IpAddress,
    dsSubnetConfRangeIndex      SubnetConfRangeIndex
        }
    
dsSubnetConfRangeStart  OBJECT-TYPE
    SYNTAX      IpAddress
    ACCESS  read-only
    STATUS      mandatory
    DESCRIPTION
        "The start ip address allocatable." 
    ::= { dsSubnetConfRangeEntry 1 }

dsSubnetConfRangeEnd            OBJECT-TYPE
    SYNTAX      IpAddress
    ACCESS  read-only
    STATUS      mandatory
    DESCRIPTION
        "The end ip address allocatable." 
    ::= { dsSubnetConfRangeEntry 2 }   
    
dsSubnetConfRangeIndex          OBJECT-TYPE
    SYNTAX      SubnetConfRangeIndex
    ACCESS  not-accessible
    STATUS      mandatory
    DESCRIPTION
        "The index of Range Entry." 
    ::= { dsSubnetConfRangeEntry 3 } 

END
