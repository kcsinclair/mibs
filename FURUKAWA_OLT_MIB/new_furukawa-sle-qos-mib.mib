--
-- fk-qos-mib.mib
-- MIB generated by MG-SOFT Visual MIB Builder Version 6.0  Build 88
-- Monday, April 18, 2011 at 12:24:04
--

	FK-QOS-MIB DEFINITIONS ::= BEGIN
 
		IMPORTS
			fkMgmt			
				FROM FKOLTG1040-SMI			
			FkControlRequestResultType, FkControlStatusType			
				FROM FK-TC-MIB			
			OBJECT-GROUP, NOTIFICATION-GROUP			
				FROM SNMPv2-CONF			
			TimeTicks, IpAddress, Integer32, Unsigned32, Gauge32, 
			Counter32, BITS, OBJECT-TYPE, MODULE-IDENTITY, NOTIFICATION-TYPE			
				FROM SNMPv2-SMI;
	
	
--  2
-- December 09, 2004 at 17:33 GMT
		-- 1.3.6.1.4.1.10428 9 1.101.10
		fkQoS MODULE-IDENTITY 
			LAST-UPDATED "200412091733Z"		-- December 09, 2004 at 17:33 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 10 }

		
	
--
-- Type definitions
--
	
--  Type definitions
-- 
		FkTrafficProfileControlRequestType ::= INTEGER { setTrafficProfile(1) }

		FkUserFlowMatchType ::= BITS
			{
			ufIngressPort(0),
			ufEgressPort(1),
			ufEthernetType(2),
			ufSrcMacAddress(3),
			ufDstMacAddress(4),
			ufVlanId(5),
			uf8021p(6),
			ufSrcIpAddress(7),
			ufSrcPrefixLength(8),
			ufDstIpAddress(9),
			ufDstPrefixLength(10),
			ufDscp(11),
			ufProtocolType(12),
			ufTcpFlag(13),
			ufSrcL4Port(14),
			ufDstL4Port(15),
			ufPacketLength(16)
			}

		FkUserFlowActionType ::= BITS
			{
			ufActPermit(0),
			ufActCopyCpu(1),
			ufActSameAsTos(2),
			ufActSameAsCos(3),
			ufActMirror(4)
			}

		FkBooleanType ::= INTEGER
			{
			disable(0),
			enable(1)
			}

		FkPortScheduleControlRequestType ::= INTEGER { setPortScheduleMode(1) }

		FkQueueControlRequestType ::= INTEGER { setQueueProfile(1) }

		FkUserFlowControlRequestType ::= INTEGER
			{
			createUserFlow(1),
			destroyUserFlow(2),
			setUserFlowClassifierProfile(3),
			setUserFlowMatchActionProfile(4),
			setUserFlowNomatchActionProfile(5)
			}

	
	
--
-- Node definitions
--
	
--  Node definitions
-- 
-- 2.2
		-- 1.3.6.1.4.1.10428 9 1.101.10.1
		fkQoSBase OBJECT IDENTIFIER ::= { fkQoS 1 }

		
		-- 1.3.6.1.4.1.10428 9 1.101.10.1.1
		fkQoSBaseInfo OBJECT IDENTIFIER ::= { fkQoSBase 1 }

		
--  2.2.1
		-- 1.3.6.1.4.1.10428 9 1.101.10.1.1.1
		fkQosUserFlowNum OBJECT-TYPE
			SYNTAX Unsigned32
			MAX-ACCESS read-only
			STATUS current
			DESCRIPTION
				"Description."
			::= { fkQoSBaseInfo 1 }

		
--  2.2.2
		-- 1.3.6.1.4.1.10428 9 1.101.10.1.1.2
		fkQosTrafficProfileNum OBJECT-TYPE
			SYNTAX Unsigned32
			MAX-ACCESS read-only
			STATUS current
			DESCRIPTION
				"Description."
			::= { fkQoSBaseInfo 2 }

		
		-- 1.3.6.1.4.1.10428 9 1.101.10.1.1.3
		fkQosCounterNum OBJECT-TYPE
			SYNTAX Unsigned32
			MAX-ACCESS read-only
			STATUS current
			DESCRIPTION
				"Description."
			::= { fkQoSBaseInfo 3 }

		
--  2.2.4
		-- 1.3.6.1.4.1.10428 9 1.101.10.1.1.4
		fkQosQueueNum OBJECT-TYPE
			SYNTAX Unsigned32
			MAX-ACCESS read-only
			STATUS current
			DESCRIPTION
				"Description."
			::= { fkQoSBaseInfo 4 }

		
		-- 1.3.6.1.4.1.10428 9 1.101.10.1.1.5
		fkQosColorMarkingProfileNum OBJECT-TYPE
			SYNTAX Integer32
			MAX-ACCESS read-only
			STATUS current
			DESCRIPTION
				"Description."
			::= { fkQoSBaseInfo 5 }

		
		-- 1.3.6.1.4.1.10428 9 1.101.10.1.1.6
		fkQosRuleMode OBJECT-TYPE
			SYNTAX INTEGER
				{
				default(0),
				extension(1)
				}
			MAX-ACCESS read-only
			STATUS current
			DESCRIPTION
				"Description."
			::= { fkQoSBaseInfo 6 }

		
		-- 1.3.6.1.4.1.10428 9 1.101.10.1.2
		fkQoSBaseControl OBJECT IDENTIFIER ::= { fkQoSBase 2 }

		
		-- 1.3.6.1.4.1.10428 9 1.101.10.1.2.1
		fkQoSBaseControlRequest OBJECT-TYPE
			SYNTAX INTEGER { setQoSBaseRuleMode(1) }
			MAX-ACCESS read-write
			STATUS current
			DESCRIPTION
				"Description."
			::= { fkQoSBaseControl 1 }

		
		-- 1.3.6.1.4.1.10428 9 1.101.10.1.2.2
		fkQoSBaseControlStatus OBJECT-TYPE
			SYNTAX FkControlStatusType
			MAX-ACCESS read-only
			STATUS current
			DESCRIPTION
				"Description."
			::= { fkQoSBaseControl 2 }

		
		-- 1.3.6.1.4.1.10428 9 1.101.10.1.2.3
		fkQoSBaseControlTimer OBJECT-TYPE
			SYNTAX Gauge32
			MAX-ACCESS read-write
			STATUS current
			DESCRIPTION
				"Description."
			::= { fkQoSBaseControl 3 }

		
		-- 1.3.6.1.4.1.10428 9 1.101.10.1.2.4
		fkQoSBaseControlTimeStamp OBJECT-TYPE
			SYNTAX TimeTicks
			MAX-ACCESS read-only
			STATUS current
			DESCRIPTION
				"Description."
			::= { fkQoSBaseControl 4 }

		
		-- 1.3.6.1.4.1.10428 9 1.101.10.1.2.5
		fkQoSBaseControlReqResult OBJECT-TYPE
			SYNTAX FkControlRequestResultType
			MAX-ACCESS read-only
			STATUS current
			DESCRIPTION
				"Description."
			::= { fkQoSBaseControl 5 }

		
		-- 1.3.6.1.4.1.10428 9 1.101.10.1.2.6
		fkQoSBaseControlRuleMode OBJECT-TYPE
			SYNTAX INTEGER
				{
				default(0),
				extension(1)
				}
			MAX-ACCESS read-write
			STATUS current
			DESCRIPTION
				"Description."
			::= { fkQoSBaseControl 6 }

		
		-- 1.3.6.1.4.1.10428 9 1.101.10.1.3
		fkQoSBaseNotification OBJECT IDENTIFIER ::= { fkQoSBase 3 }

		
		-- 1.3.6.1.4.1.10428 9 1.101.10.1.3.1
		fkQoSBaseRuleModeChanged NOTIFICATION-TYPE
			OBJECTS { fkQoSBaseControlRequest, fkQoSBaseControlTimeStamp, fkQoSBaseControlReqResult, fkQosRuleMode }
			STATUS current
			DESCRIPTION 
				"Description."
			::= { fkQoSBaseNotification 1 }

		
--  2.4
		-- 1.3.6.1.4.1.10428 9 1.101.10.2
		fkTrafficProfile OBJECT IDENTIFIER ::= { fkQoS 2 }

		
--  2.4.1
		-- 1.3.6.1.4.1.10428 9 1.101.10.2.1
		fkTrafficProfileTable OBJECT-TYPE
			SYNTAX SEQUENCE OF FkTrafficProfileEntry
			MAX-ACCESS not-accessible
			STATUS current
			DESCRIPTION
				"Description."
			::= { fkTrafficProfile 1 }

		
--  2.4.1.1
		-- 1.3.6.1.4.1.10428 9 1.101.10.2.1.1
		fkTrafficProfileEntry OBJECT-TYPE
			SYNTAX FkTrafficProfileEntry
			MAX-ACCESS not-accessible
			STATUS current
			DESCRIPTION
				"Description."
			INDEX { fkTrafficProfileIndex }
			::= { fkTrafficProfileTable 1 }

		
		FkTrafficProfileEntry ::=
			SEQUENCE { 
				fkTrafficProfileIndex
					Unsigned32,
				fkTrafficProfileMinBandwidth
					Integer32,
				fkTrafficProfileMaxBandwidth
					Integer32,
				fkTrafficProfileMaxBurstSize
					Integer32,
				fkTrafficProfileUseCount
					Integer32
			 }

--  2.4.1.1.1
		-- 1.3.6.1.4.1.10428 9 1.101.10.2.1.1.1
		fkTrafficProfileIndex OBJECT-TYPE
			SYNTAX Unsigned32 (1..65535)
			MAX-ACCESS read-only
			STATUS current
			DESCRIPTION
				"meter Index"
			::= { fkTrafficProfileEntry 1 }

		
--  2.4.1.1.2
		-- 1.3.6.1.4.1.10428 9 1.101.10.2.1.1.2
		fkTrafficProfileMinBandwidth OBJECT-TYPE
			SYNTAX Integer32
			MAX-ACCESS read-only
			STATUS current
			DESCRIPTION
				"The value is in unit for 64 kbps"
			::= { fkTrafficProfileEntry 2 }

		
--  2.4.1.1.3
		-- 1.3.6.1.4.1.10428 9 1.101.10.2.1.1.3
		fkTrafficProfileMaxBandwidth OBJECT-TYPE
			SYNTAX Integer32
			MAX-ACCESS read-only
			STATUS current
			DESCRIPTION
				"The value is in unit for 64 kbps"
			::= { fkTrafficProfileEntry 3 }

		
--  2.4.1.1.4
		-- 1.3.6.1.4.1.10428 9 1.101.10.2.1.1.4
		fkTrafficProfileMaxBurstSize OBJECT-TYPE
			SYNTAX Integer32
			MAX-ACCESS read-only
			STATUS current
			DESCRIPTION
				"The size of the bucket used for metering"
			::= { fkTrafficProfileEntry 4 }

		
		-- 1.3.6.1.4.1.10428 9 1.101.10.2.1.1.5
		fkTrafficProfileUseCount OBJECT-TYPE
			SYNTAX Integer32
			MAX-ACCESS read-only
			STATUS current
			DESCRIPTION
				"Description."
			::= { fkTrafficProfileEntry 5 }

		
--  2.4.2
		-- 1.3.6.1.4.1.10428 9 1.101.10.2.2
		fkTrafficProfileControl OBJECT IDENTIFIER ::= { fkTrafficProfile 2 }

		
--  2.4.2.1
		-- 1.3.6.1.4.1.10428 9 1.101.10.2.2.1
		fkTrafficProfileControlRequest OBJECT-TYPE
			SYNTAX FkTrafficProfileControlRequestType
			MAX-ACCESS read-write
			STATUS current
			DESCRIPTION
				"Description."
			::= { fkTrafficProfileControl 1 }

		
--  2.4.2.2
		-- 1.3.6.1.4.1.10428 9 1.101.10.2.2.2
		fkTrafficProfileControlStatus OBJECT-TYPE
			SYNTAX FkControlStatusType
			MAX-ACCESS read-only
			STATUS current
			DESCRIPTION
				"Description."
			::= { fkTrafficProfileControl 2 }

		
--  2.4.2.3
		-- 1.3.6.1.4.1.10428 9 1.101.10.2.2.3
		fkTrafficProfileControlTimer OBJECT-TYPE
			SYNTAX Gauge32
			MAX-ACCESS read-write
			STATUS current
			DESCRIPTION
				"Description."
			::= { fkTrafficProfileControl 3 }

		
--  2.4.2.4
		-- 1.3.6.1.4.1.10428 9 1.101.10.2.2.4
		fkTrafficProfileControlTimeStamp OBJECT-TYPE
			SYNTAX TimeTicks
			MAX-ACCESS read-only
			STATUS current
			DESCRIPTION
				"Description."
			::= { fkTrafficProfileControl 4 }

		
--  2.4.2.5
		-- 1.3.6.1.4.1.10428 9 1.101.10.2.2.5
		fkTrafficProfileControlReqResult OBJECT-TYPE
			SYNTAX FkControlRequestResultType
			MAX-ACCESS read-only
			STATUS current
			DESCRIPTION
				"Result of last command"
			::= { fkTrafficProfileControl 5 }

		
--  2.4.2.6
		-- 1.3.6.1.4.1.10428 9 1.101.10.2.2.6
		fkTrafficProfileControlIndex OBJECT-TYPE
			SYNTAX Integer32
			MAX-ACCESS read-write
			STATUS current
			DESCRIPTION
				"meter Index"
			::= { fkTrafficProfileControl 6 }

		
--  2.4.2.7
		-- 1.3.6.1.4.1.10428 9 1.101.10.2.2.7
		fkTrafficProfileControlMinBandwidth OBJECT-TYPE
			SYNTAX Integer32
			MAX-ACCESS read-write
			STATUS current
			DESCRIPTION
				"The value is in unit for 64 kbps"
			::= { fkTrafficProfileControl 7 }

		
--  2.4.2.8
		-- 1.3.6.1.4.1.10428 9 1.101.10.2.2.8
		fkTrafficProfileControlMaxBandwidth OBJECT-TYPE
			SYNTAX Integer32
			MAX-ACCESS read-write
			STATUS current
			DESCRIPTION
				"The value is in unit for 64 kbps"
			::= { fkTrafficProfileControl 8 }

		
--  2.4.2.9
		-- 1.3.6.1.4.1.10428 9 1.101.10.2.2.9
		fkTrafficProfileControlMaxBurstSize OBJECT-TYPE
			SYNTAX Integer32
			MAX-ACCESS read-write
			STATUS current
			DESCRIPTION
				"The size of the bucket used for metering"
			::= { fkTrafficProfileControl 9 }

		
--  2.4.3
		-- 1.3.6.1.4.1.10428 9 1.101.10.2.3
		fkTrafficProfileNotification OBJECT IDENTIFIER ::= { fkTrafficProfile 3 }

		
--  2.4.3.1
		-- 1.3.6.1.4.1.10428 9 1.101.10.2.3.1
		fkTrafficProfileChanged NOTIFICATION-TYPE
			OBJECTS { fkTrafficProfileMinBandwidth, fkTrafficProfileControlTimeStamp, fkTrafficProfileControlReqResult, fkTrafficProfileControlRequest, fkTrafficProfileMaxBurstSize, 
				fkTrafficProfileMaxBandwidth }
			STATUS current
			DESCRIPTION 
				"Description."
			::= { fkTrafficProfileNotification 1 }

		
--  2.5
		-- 1.3.6.1.4.1.10428 9 1.101.10.3
		fkUserFlow OBJECT IDENTIFIER ::= { fkQoS 3 }

		
--  2.5.1
		-- 1.3.6.1.4.1.10428 9 1.101.10.3.1
		fkUserFlowTable OBJECT-TYPE
			SYNTAX SEQUENCE OF FkUserFlowEntry
			MAX-ACCESS not-accessible
			STATUS current
			DESCRIPTION
				"Description."
			::= { fkUserFlow 1 }

		
--  2.5.1.1
		-- 1.3.6.1.4.1.10428 9 1.101.10.3.1.1
		fkUserFlowEntry OBJECT-TYPE
			SYNTAX FkUserFlowEntry
			MAX-ACCESS not-accessible
			STATUS current
			DESCRIPTION
				"Description."
			INDEX { fkUserFlowName }
			::= { fkUserFlowTable 1 }

		
		FkUserFlowEntry ::=
			SEQUENCE { 
				fkUserFlowName
					OCTET STRING,
				fkUserFlowIngressPorts
					OCTET STRING,
				fkUserFlowEgressPorts
					OCTET STRING,
				fkUserFlowEthernetType
					Integer32,
				fkUserFlowSrcMacAddr
					OCTET STRING,
				fkUserFlowDstMacAddr
					OCTET STRING,
				fkUserFlowVlan
					Integer32,
				fkUserFlow8021p
					Integer32,
				fkUserFlowSrcIpAddr
					IpAddress,
				fkUserFlowSrcPrefixLength
					Integer32,
				fkUserFlowDstIpAddr
					IpAddress,
				fkUserFlowDstPrefixLength
					Integer32,
				fkUserFlowIpPktPriorityType
					INTEGER,
				fkUserFlowIpPktPriority
					Integer32,
				fkUserFlowProtocolType
					Integer32,
				fkUserFlowTcpFlag
					BITS,
				fkUserFlowSrcL4Port
					Integer32,
				fkUserFlowDstL4Port
					Integer32,
				fkUserFlowPktLen
					Integer32,
				fkUserFlowValidFlags
					BITS,
				fkUserFlowMatchFlags
					BITS,
				fkUserFlowPriority
					INTEGER,
				fkUserFlowMatchCounterId
					Integer32,
				fkUserFlowMatchTrafficProfileId
					Integer32,
				fkUserFlowMatchQueue
					Integer32,
				fkUserFlowMatchIpPktPriorityType
					INTEGER,
				fkUserFlowMatchIpPktPriority
					Integer32,
				fkUserFlowMatchRedirPort
					Integer32,
				fkUserFlowMatchVid
					Integer32,
				fkUserFlowMatchDstMac
					OCTET STRING,
				fkUserFlowMatchPortMap
					OCTET STRING,
				fkUserFlowMatchEgressType
					INTEGER,
				fkUserFlowMatchAction
					BITS,
				fkUserFlowNomatchCounterId
					Integer32,
				fkUserFlowNomatchTrafficProfileId
					Integer32,
				fkUserFlowNomatchQueue
					Integer32,
				fkUserFlowNomatchIpPktPriorityType
					INTEGER,
				fkUserFlowNomatchIpPktPriority
					Integer32,
				fkUserFlowNomatchRedirPort
					Integer32,
				fkUserFlowNomatchVid
					Integer32,
				fkUserFlowNomatchAction
					BITS,
				fkUserFlowMatchColorMarkingId
					Integer32,
				fkUserFlowNomatchColorMarkingId
					Integer32,
				fkUserFlowInnerVlan
					Integer32,
				fkUserFlowInner8021p
					Integer32,
				fkUserFlowMatchRoutePrimary
					IpAddress,
				fkUserFlowMatchRouteSecondary
					IpAddress
			 }

--  2.5.1.1.1
		-- 1.3.6.1.4.1.10428 9 1.101.10.3.1.1.1
		fkUserFlowName OBJECT-TYPE
			SYNTAX OCTET STRING (SIZE (1..63))
			MAX-ACCESS read-only
			STATUS current
			DESCRIPTION
				"The name of this user flow."
			::= { fkUserFlowEntry 1 }

		
--  2.5.1.1.2
		-- 1.3.6.1.4.1.10428 9 1.101.10.3.1.1.2
		fkUserFlowIngressPorts OBJECT-TYPE
			SYNTAX OCTET STRING
			MAX-ACCESS read-only
			STATUS current
			DESCRIPTION
				"Ingress port number"
			::= { fkUserFlowEntry 2 }

		
--  2.5.1.1.4
		-- 1.3.6.1.4.1.10428 9 1.101.10.3.1.1.3
		fkUserFlowEgressPorts OBJECT-TYPE
			SYNTAX OCTET STRING
			MAX-ACCESS read-only
			STATUS current
			DESCRIPTION
				"Egress Port Number"
			::= { fkUserFlowEntry 3 }

		
--  2.5.1.1.6
		-- 1.3.6.1.4.1.10428 9 1.101.10.3.1.1.4
		fkUserFlowEthernetType OBJECT-TYPE
			SYNTAX Integer32 (0..65535)
			MAX-ACCESS read-only
			STATUS current
			DESCRIPTION
				"The ethernet type value in incoming frames"
			::= { fkUserFlowEntry 4 }

		
--  2.5.1.1.8
		-- 1.3.6.1.4.1.10428 9 1.101.10.3.1.1.5
		fkUserFlowSrcMacAddr OBJECT-TYPE
			SYNTAX OCTET STRING (SIZE (6))
			MAX-ACCESS read-only
			STATUS current
			DESCRIPTION
				"Source MAC address"
			::= { fkUserFlowEntry 5 }

		
--  2.5.1.1.10
		-- 1.3.6.1.4.1.10428 9 1.101.10.3.1.1.6
		fkUserFlowDstMacAddr OBJECT-TYPE
			SYNTAX OCTET STRING (SIZE (6))
			MAX-ACCESS read-only
			STATUS current
			DESCRIPTION
				"Destination MAC address"
			::= { fkUserFlowEntry 6 }

		
--  2.5.1.1.12
		-- 1.3.6.1.4.1.10428 9 1.101.10.3.1.1.7
		fkUserFlowVlan OBJECT-TYPE
			SYNTAX Integer32 (0..4094)
			MAX-ACCESS read-only
			STATUS current
			DESCRIPTION
				"VLAN ID"
			::= { fkUserFlowEntry 7 }

		
--  2.5.1.1.14
		-- 1.3.6.1.4.1.10428 9 1.101.10.3.1.1.8
		fkUserFlow8021p OBJECT-TYPE
			SYNTAX Integer32 (0..7)
			MAX-ACCESS read-only
			STATUS current
			DESCRIPTION
				"The value of the IEEE802.1p priority in the packet"
			::= { fkUserFlowEntry 8 }

		
--  2.5.1.1.16
		-- 1.3.6.1.4.1.10428 9 1.101.10.3.1.1.9
		fkUserFlowSrcIpAddr OBJECT-TYPE
			SYNTAX IpAddress
			MAX-ACCESS read-only
			STATUS current
			DESCRIPTION
				"The IP address to match against the packet's 
				source IP address."
			::= { fkUserFlowEntry 9 }

		
--  2.5.1.1.18
		-- 1.3.6.1.4.1.10428 9 1.101.10.3.1.1.10
		fkUserFlowSrcPrefixLength OBJECT-TYPE
			SYNTAX Integer32 (0..31)
			MAX-ACCESS read-only
			STATUS current
			DESCRIPTION
				"Subnet mask. The length of 0 indicates a match of any address"
			::= { fkUserFlowEntry 10 }

		
--  2.5.1.1.20
		-- 1.3.6.1.4.1.10428 9 1.101.10.3.1.1.11
		fkUserFlowDstIpAddr OBJECT-TYPE
			SYNTAX IpAddress
			MAX-ACCESS read-only
			STATUS current
			DESCRIPTION
				"The IP address to match against the packet's 
				destination IP address."
			::= { fkUserFlowEntry 11 }

		
--  2.5.1.1.22
		-- 1.3.6.1.4.1.10428 9 1.101.10.3.1.1.12
		fkUserFlowDstPrefixLength OBJECT-TYPE
			SYNTAX Integer32 (0..32)
			MAX-ACCESS read-only
			STATUS current
			DESCRIPTION
				"Subnet mask. The length of 0 indicates a match of any address"
			::= { fkUserFlowEntry 12 }

		
		-- 1.3.6.1.4.1.10428 9 1.101.10.3.1.1.13
		fkUserFlowIpPktPriorityType OBJECT-TYPE
			SYNTAX INTEGER
				{
				ipPrecedence(1),
				diffServ(2),
				ipToS(3)
				}
			MAX-ACCESS read-only
			STATUS current
			DESCRIPTION
				"Description."
			::= { fkUserFlowEntry 13 }

		
--  2.5.1.1.24
		-- 1.3.6.1.4.1.10428 9 1.101.10.3.1.1.14
		fkUserFlowIpPktPriority OBJECT-TYPE
			SYNTAX Integer32 (0..63)
			MAX-ACCESS read-only
			STATUS current
			DESCRIPTION
				"The Priority value in incoming IP packet.
				If fkUserFlowIpPktPriorityType is 1, 
				this value's range is 0-7.
				If fkUserFlowIpPktPriorityType is 2, 
				this value's range is 0-63.
				If fkUserFlowIpPktPriorityType is 3, 
				this value's range is 0-255.
				"
			::= { fkUserFlowEntry 14 }

		
--  2.5.1.1.26
		-- 1.3.6.1.4.1.10428 9 1.101.10.3.1.1.15
		fkUserFlowProtocolType OBJECT-TYPE
			SYNTAX Integer32 (0..255)
			MAX-ACCESS read-only
			STATUS current
			DESCRIPTION
				"The IP protocol type value"
			::= { fkUserFlowEntry 15 }

		
		-- 1.3.6.1.4.1.10428 9 1.101.10.3.1.1.16
		fkUserFlowTcpFlag OBJECT-TYPE
			SYNTAX BITS
				{
				reserv0(0),
				reserv1(1),
				urg(2),
				ack(3),
				psh(4),
				rst(5),
				syn(6),
				fin(7)
				}
			MAX-ACCESS read-only
			STATUS current
			DESCRIPTION
				"TCP Flags"
			::= { fkUserFlowEntry 16 }

		
--  2.5.1.1.30
		-- 1.3.6.1.4.1.10428 9 1.101.10.3.1.1.17
		fkUserFlowSrcL4Port OBJECT-TYPE
			SYNTAX Integer32 (0..65535)
			MAX-ACCESS read-only
			STATUS current
			DESCRIPTION
				"The source L4 port number, only valid for 
				TCP or UDP packets."
			::= { fkUserFlowEntry 17 }

		
--  2.5.1.1.32
		-- 1.3.6.1.4.1.10428 9 1.101.10.3.1.1.18
		fkUserFlowDstL4Port OBJECT-TYPE
			SYNTAX Integer32 (0..65535)
			MAX-ACCESS read-only
			STATUS current
			DESCRIPTION
				"The destination L4 port number, only valid for 
				TCP or UDP packets."
			::= { fkUserFlowEntry 18 }

		
--  2.5.1.1.28
		-- 1.3.6.1.4.1.10428 9 1.101.10.3.1.1.19
		fkUserFlowPktLen OBJECT-TYPE
			SYNTAX Integer32 (21..65535)
			MAX-ACCESS read-only
			STATUS current
			DESCRIPTION
				"The packet length of the incoming packet"
			::= { fkUserFlowEntry 19 }

		
		-- 1.3.6.1.4.1.10428 9 1.101.10.3.1.1.20
		fkUserFlowValidFlags OBJECT-TYPE
			SYNTAX BITS
				{
				ufIngressPort(0),
				ufEgressPort(1),
				ufEthernetType(2),
				ufSrcMacAddress(3),
				ufDstMacAddress(4),
				ufVlanId(5),
				uf8021p(6),
				ufSrcIpAddress(7),
				ufSrcPrefixLength(8),
				ufDstIpAddress(9),
				ufDstPrefixLength(10),
				ufIpPktPriority(11),
				ufProtocolType(12),
				ufTcpFlag(13),
				ufSrcL4Port(14),
				ufDstL4Port(15),
				ufPacketLength(16),
				ufPriority(17),
				ufInnerVlanId(18),
				ufInner8021p(19)
				}
			MAX-ACCESS read-only
			STATUS current
			DESCRIPTION
				"User Flow Valid Flags"
			::= { fkUserFlowEntry 20 }

		
		-- 1.3.6.1.4.1.10428 9 1.101.10.3.1.1.21
		fkUserFlowMatchFlags OBJECT-TYPE
			SYNTAX BITS
				{
				ufIngressPort(0),
				ufEgressPort(1),
				ufEthernetType(2),
				ufSrcMacAddress(3),
				ufDstMacAddress(4),
				ufVlanId(5),
				uf8021p(6),
				ufSrcIpAddress(7),
				ufSrcPrefixLength(8),
				ufDstIpAddress(9),
				ufDstPrefixLength(10),
				ufIpPktPriority(11),
				ufProtocolType(12),
				ufTcpFlag(13),
				ufSrcL4Port(14),
				ufDstL4Port(15),
				ufPacketLength(16),
				ufPriority(17)
				}
			MAX-ACCESS read-only
			STATUS current
			DESCRIPTION
				"User Flow Matching Flags"
			::= { fkUserFlowEntry 21 }

		
--  2.5.1.1.38
		-- 1.3.6.1.4.1.10428 9 1.101.10.3.1.1.22
		fkUserFlowPriority OBJECT-TYPE
			SYNTAX INTEGER
				{
				low(1),
				medium(2),
				high(3),
				highest(4)
				}
			MAX-ACCESS read-only
			STATUS current
			DESCRIPTION
				"The priority of this user flow"
			::= { fkUserFlowEntry 22 }

		
--  2.5.1.1.39
		-- 1.3.6.1.4.1.10428 9 1.101.10.3.1.1.23
		fkUserFlowMatchCounterId OBJECT-TYPE
			SYNTAX Integer32
			MAX-ACCESS read-only
			STATUS current
			DESCRIPTION
				"The counter index to be apply for the matched packets."
			::= { fkUserFlowEntry 23 }

		
--  2.5.1.1.40
		-- 1.3.6.1.4.1.10428 9 1.101.10.3.1.1.24
		fkUserFlowMatchTrafficProfileId OBJECT-TYPE
			SYNTAX Integer32
			MAX-ACCESS read-only
			STATUS current
			DESCRIPTION
				"The traffic profile index to be apply 
				for the matched packets."
			::= { fkUserFlowEntry 24 }

		
--  2.5.1.1.45
		-- 1.3.6.1.4.1.10428 9 1.101.10.3.1.1.25
		fkUserFlowMatchQueue OBJECT-TYPE
			SYNTAX Integer32 (0..63)
			MAX-ACCESS read-only
			STATUS current
			DESCRIPTION
				"TThe CoS value to be assign for the nomatched packets"
			::= { fkUserFlowEntry 25 }

		
--  2.5.1.1.43
		-- 1.3.6.1.4.1.10428 9 1.101.10.3.1.1.26
		fkUserFlowMatchIpPktPriorityType OBJECT-TYPE
			SYNTAX INTEGER
				{
				ipPrecedence(1),
				diffServ(2),
				ipToS(3)
				}
			MAX-ACCESS read-only
			STATUS current
			DESCRIPTION
				"The Priority type to be applied to incoming IP packet."
			::= { fkUserFlowEntry 26 }

		
		-- 1.3.6.1.4.1.10428 9 1.101.10.3.1.1.27
		fkUserFlowMatchIpPktPriority OBJECT-TYPE
			SYNTAX Integer32
			MAX-ACCESS read-only
			STATUS current
			DESCRIPTION
				"The Priority value in incoming IP packet.
				If fkUserFlowMatchIpPktPriorityType is 1, 
				then this value's range is 0-7.
				If fkUserFlowMatchIpPktPriorityType is 2, 
				then this value's range is 0-63.
				If fkUserFlowMatchIpPktPriorityType is 3, 
				then this value's range is 0-255.
				"
			DEFVAL { -1 }
			::= { fkUserFlowEntry 27 }

		
--  2.5.1.1.46
		-- 1.3.6.1.4.1.10428 9 1.101.10.3.1.1.28
		fkUserFlowMatchRedirPort OBJECT-TYPE
			SYNTAX Integer32
			MAX-ACCESS read-only
			STATUS current
			DESCRIPTION
				"The port to redirect to a matched packet."
			::= { fkUserFlowEntry 28 }

		
--  2.5.1.1.50
		-- 1.3.6.1.4.1.10428 9 1.101.10.3.1.1.29
		fkUserFlowMatchVid OBJECT-TYPE
			SYNTAX Integer32 (1..4096)
			MAX-ACCESS read-only
			STATUS current
			DESCRIPTION
				"The vlan id to be assigned for the matched packets"
			::= { fkUserFlowEntry 29 }

		
		-- 1.3.6.1.4.1.10428 9 1.101.10.3.1.1.30
		fkUserFlowMatchDstMac OBJECT-TYPE
			SYNTAX OCTET STRING
			MAX-ACCESS read-only
			STATUS current
			DESCRIPTION
				"Description."
			::= { fkUserFlowEntry 30 }

		
		-- 1.3.6.1.4.1.10428 9 1.101.10.3.1.1.31
		fkUserFlowMatchPortMap OBJECT-TYPE
			SYNTAX OCTET STRING
			MAX-ACCESS read-only
			STATUS current
			DESCRIPTION
				"Description."
			::= { fkUserFlowEntry 31 }

		
		-- 1.3.6.1.4.1.10428 9 1.101.10.3.1.1.32
		fkUserFlowMatchEgressType OBJECT-TYPE
			SYNTAX INTEGER
				{
				dmac(0),
				egressPorts(1),
				filterPorts(2)
				}
			MAX-ACCESS read-only
			STATUS current
			DESCRIPTION
				"Description."
			::= { fkUserFlowEntry 32 }

		
--  2.5.1.1.41
		-- 1.3.6.1.4.1.10428 9 1.101.10.3.1.1.33
		fkUserFlowMatchAction OBJECT-TYPE
			SYNTAX BITS
				{
				ufActDeny(0),
				ufActCopytoCpu(1),
				ufActSameAsTos(2),
				ufActSameAsCos(3),
				ufActMirror(4),
				ufActCounter(5),
				ufActTrafficeProfile(6),
				ufActQueue(7),
				ufActIpPktPriority(8),
				ufActRedirPort(9),
				ufAct8021p(10),
				ufActVid(11),
				ufActEgress(12),
				ufActColorMarking(13),
				ufActRoute(14),
				ufActRouteReachability(15)
				}
			MAX-ACCESS read-only
			STATUS current
			DESCRIPTION
				"The action to be apply for matched packets."
			::= { fkUserFlowEntry 33 }

		
--  2.5.1.1.51
		-- 1.3.6.1.4.1.10428 9 1.101.10.3.1.1.34
		fkUserFlowNomatchCounterId OBJECT-TYPE
			SYNTAX Integer32
			MAX-ACCESS read-only
			STATUS current
			DESCRIPTION
				"The counter index to be apply for the nomatched packets."
			::= { fkUserFlowEntry 34 }

		
--  2.5.1.1.40
		-- 1.3.6.1.4.1.10428 9 1.101.10.3.1.1.35
		fkUserFlowNomatchTrafficProfileId OBJECT-TYPE
			SYNTAX Integer32
			MAX-ACCESS read-only
			STATUS current
			DESCRIPTION
				"The traffic profile index to be apply 
				for the nomatched packets."
			::= { fkUserFlowEntry 35 }

		
--  2.5.1.1.43
		-- 1.3.6.1.4.1.10428 9 1.101.10.3.1.1.36
		fkUserFlowNomatchQueue OBJECT-TYPE
			SYNTAX Integer32 (0..7)
			MAX-ACCESS read-only
			STATUS current
			DESCRIPTION
				"The CoS value to be assign for the nomatched packets"
			::= { fkUserFlowEntry 36 }

		
--  2.5.1.1.45
		-- 1.3.6.1.4.1.10428 9 1.101.10.3.1.1.37
		fkUserFlowNomatchIpPktPriorityType OBJECT-TYPE
			SYNTAX INTEGER
				{
				ipPrecedence(1),
				diffServ(2),
				ipToS(3)
				}
			MAX-ACCESS read-only
			STATUS current
			DESCRIPTION
				"The Priority type to be applied to incoming IP packet, in case nomatched."
			::= { fkUserFlowEntry 37 }

		
		-- 1.3.6.1.4.1.10428 9 1.101.10.3.1.1.38
		fkUserFlowNomatchIpPktPriority OBJECT-TYPE
			SYNTAX Integer32
			MAX-ACCESS read-only
			STATUS current
			DESCRIPTION
				"The Priority value in incoming IP packet.
				If fkUserFlowNomatchIpPktPriorityType is 1, 
				then this value's range is 0-7.
				If fkUserFlowNomatchIpPktPriorityType is 2, 
				then this value's range is 0-63.
				If fkUserFlowNomatchIpPktPriorityType is 3, 
				then this value's range is 0-255.
				"
			DEFVAL { -1 }
			::= { fkUserFlowEntry 38 }

		
--  2.5.1.1.46
		-- 1.3.6.1.4.1.10428 9 1.101.10.3.1.1.39
		fkUserFlowNomatchRedirPort OBJECT-TYPE
			SYNTAX Integer32
			MAX-ACCESS read-only
			STATUS current
			DESCRIPTION
				"The port to redirect to nomatched packet."
			::= { fkUserFlowEntry 39 }

		
--  2.5.1.1.50
		-- 1.3.6.1.4.1.10428 9 1.101.10.3.1.1.40
		fkUserFlowNomatchVid OBJECT-TYPE
			SYNTAX Integer32 (0..4096)
			MAX-ACCESS read-only
			STATUS current
			DESCRIPTION
				"The vlan id to be assigned for the nomatched packets"
			::= { fkUserFlowEntry 40 }

		
--  2.5.1.1.41
		-- 1.3.6.1.4.1.10428 9 1.101.10.3.1.1.41
		fkUserFlowNomatchAction OBJECT-TYPE
			SYNTAX BITS
				{
				ufActDeny(0),
				ufActCopytoCpu(1),
				ufActSameAsTos(2),
				ufActSameAsCos(3),
				ufActMirror(4),
				ufActCounter(5),
				ufActTrafficeProfile(6),
				ufActQueue(7),
				ufActIpPktPriority(8),
				ufActRedirPort(9),
				ufAct8021p(10),
				ufActVid(11),
				ufActEgress(12)
				}
			MAX-ACCESS read-only
			STATUS current
			DESCRIPTION
				"The action to be apply for nomatched packets."
			::= { fkUserFlowEntry 41 }

		
		-- 1.3.6.1.4.1.10428 9 1.101.10.3.1.1.42
		fkUserFlowMatchColorMarkingId OBJECT-TYPE
			SYNTAX Integer32
			MAX-ACCESS read-only
			STATUS current
			DESCRIPTION
				"The colormarking profile index to be apply for the matched packet."
			::= { fkUserFlowEntry 42 }

		
		-- 1.3.6.1.4.1.10428 9 1.101.10.3.1.1.43
		fkUserFlowNomatchColorMarkingId OBJECT-TYPE
			SYNTAX Integer32
			MAX-ACCESS read-only
			STATUS current
			DESCRIPTION
				"The colormarking profile index to be apply for the unmatched packet. (not supported)"
			::= { fkUserFlowEntry 43 }

		
		-- 1.3.6.1.4.1.10428 9 1.101.10.3.1.1.44
		fkUserFlowInnerVlan OBJECT-TYPE
			SYNTAX Integer32 (1..4094)
			MAX-ACCESS read-only
			STATUS current
			DESCRIPTION
				"Inner VLAN ID in QinQ"
			::= { fkUserFlowEntry 44 }

		
		-- 1.3.6.1.4.1.10428 9 1.101.10.3.1.1.45
		fkUserFlowInner8021p OBJECT-TYPE
			SYNTAX Integer32 (0..7)
			MAX-ACCESS read-only
			STATUS current
			DESCRIPTION
				"The value of the inner IEEE802.1p priority in the packet"
			::= { fkUserFlowEntry 45 }

		
		-- 1.3.6.1.4.1.10428 9 1.101.10.3.1.1.46
		fkUserFlowMatchRoutePrimary OBJECT-TYPE
			SYNTAX IpAddress
			MAX-ACCESS read-only
			STATUS current
			DESCRIPTION
				"The policy-based-routing primary route"
			::= { fkUserFlowEntry 46 }

		
		-- 1.3.6.1.4.1.10428 9 1.101.10.3.1.1.47
		fkUserFlowMatchRouteSecondary OBJECT-TYPE
			SYNTAX IpAddress
			MAX-ACCESS read-only
			STATUS current
			DESCRIPTION
				"The policy-based-routing secondary route"
			::= { fkUserFlowEntry 47 }

		
--  2.5.2
		-- 1.3.6.1.4.1.10428 9 1.101.10.3.2
		fkUserFlowControl OBJECT IDENTIFIER ::= { fkUserFlow 2 }

		
		-- 1.3.6.1.4.1.10428 9 1.101.10.3.2.1
		fkUserFlowControlRequest OBJECT-TYPE
			SYNTAX FkUserFlowControlRequestType
			MAX-ACCESS read-write
			STATUS current
			DESCRIPTION
				"Description."
			::= { fkUserFlowControl 1 }

		
		-- 1.3.6.1.4.1.10428 9 1.101.10.3.2.2
		fkUserFlowControlStatus OBJECT-TYPE
			SYNTAX FkControlStatusType
			MAX-ACCESS read-only
			STATUS current
			DESCRIPTION
				"Description."
			::= { fkUserFlowControl 2 }

		
		-- 1.3.6.1.4.1.10428 9 1.101.10.3.2.3
		fkUserFlowControlTimer OBJECT-TYPE
			SYNTAX Gauge32
			MAX-ACCESS read-write
			STATUS current
			DESCRIPTION
				"Description."
			::= { fkUserFlowControl 3 }

		
		-- 1.3.6.1.4.1.10428 9 1.101.10.3.2.4
		fkUserFlowControlTimeStamp OBJECT-TYPE
			SYNTAX TimeTicks
			MAX-ACCESS read-only
			STATUS current
			DESCRIPTION
				"Description."
			::= { fkUserFlowControl 4 }

		
		-- 1.3.6.1.4.1.10428 9 1.101.10.3.2.5
		fkUserFlowControlReqResult OBJECT-TYPE
			SYNTAX FkControlRequestResultType
			MAX-ACCESS read-only
			STATUS current
			DESCRIPTION
				"Description."
			::= { fkUserFlowControl 5 }

		
		-- 1.3.6.1.4.1.10428 9 1.101.10.3.2.6
		fkUserFlowControlName OBJECT-TYPE
			SYNTAX OCTET STRING (SIZE (1..63))
			MAX-ACCESS read-write
			STATUS current
			DESCRIPTION
				"Description."
			::= { fkUserFlowControl 6 }

		
		-- 1.3.6.1.4.1.10428 9 1.101.10.3.2.7
		fkUserFlowControlIngressPorts OBJECT-TYPE
			SYNTAX OCTET STRING
			MAX-ACCESS read-write
			STATUS current
			DESCRIPTION
				"Ingress port"
			::= { fkUserFlowControl 7 }

		
		-- 1.3.6.1.4.1.10428 9 1.101.10.3.2.8
		fkUserFlowControlEgressPorts OBJECT-TYPE
			SYNTAX OCTET STRING
			MAX-ACCESS read-write
			STATUS current
			DESCRIPTION
				"Egress port"
			::= { fkUserFlowControl 8 }

		
		-- 1.3.6.1.4.1.10428 9 1.101.10.3.2.9
		fkUserFlowControlEthernetType OBJECT-TYPE
			SYNTAX Integer32 (0..65535)
			MAX-ACCESS read-write
			STATUS current
			DESCRIPTION
				"Description."
			::= { fkUserFlowControl 9 }

		
		-- 1.3.6.1.4.1.10428 9 1.101.10.3.2.10
		fkUserFlowControlSrcMacAddr OBJECT-TYPE
			SYNTAX OCTET STRING (SIZE (6))
			MAX-ACCESS read-write
			STATUS current
			DESCRIPTION
				"Source MAC address"
			::= { fkUserFlowControl 10 }

		
		-- 1.3.6.1.4.1.10428 9 1.101.10.3.2.11
		fkUserFlowControlDstMacAddr OBJECT-TYPE
			SYNTAX OCTET STRING (SIZE (6))
			MAX-ACCESS read-write
			STATUS current
			DESCRIPTION
				"Destination MAC address"
			::= { fkUserFlowControl 11 }

		
		-- 1.3.6.1.4.1.10428 9 1.101.10.3.2.12
		fkUserFlowControlVlan OBJECT-TYPE
			SYNTAX Integer32 (1..4096)
			MAX-ACCESS read-write
			STATUS current
			DESCRIPTION
				"Vlan ID"
			::= { fkUserFlowControl 12 }

		
		-- 1.3.6.1.4.1.10428 9 1.101.10.3.2.13
		fkUserFlowControl8021p OBJECT-TYPE
			SYNTAX Integer32 (0..7)
			MAX-ACCESS read-write
			STATUS current
			DESCRIPTION
				"The value of the IEEE802.1p priority in the packet"
			::= { fkUserFlowControl 13 }

		
		-- 1.3.6.1.4.1.10428 9 1.101.10.3.2.14
		fkUserFlowControlSrcIpAddr OBJECT-TYPE
			SYNTAX IpAddress
			MAX-ACCESS read-write
			STATUS current
			DESCRIPTION
				"The IP address to match against the packet's source IP address."
			::= { fkUserFlowControl 14 }

		
		-- 1.3.6.1.4.1.10428 9 1.101.10.3.2.15
		fkUserFlowControlSrcPrefixLength OBJECT-TYPE
			SYNTAX Integer32
			MAX-ACCESS read-write
			STATUS current
			DESCRIPTION
				"Subnet mask. The length of 0 indicates a match of any address"
			::= { fkUserFlowControl 15 }

		
		-- 1.3.6.1.4.1.10428 9 1.101.10.3.2.16
		fkUserFlowControlDstIpAddr OBJECT-TYPE
			SYNTAX IpAddress
			MAX-ACCESS read-write
			STATUS current
			DESCRIPTION
				"The IP address to match against the packet's destination IP address."
			::= { fkUserFlowControl 16 }

		
		-- 1.3.6.1.4.1.10428 9 1.101.10.3.2.17
		fkUserFlowControlDstPrefixLength OBJECT-TYPE
			SYNTAX Integer32
			MAX-ACCESS read-write
			STATUS current
			DESCRIPTION
				"Subnet mask. The length of 0 indicates a match of any address"
			::= { fkUserFlowControl 17 }

		
		-- 1.3.6.1.4.1.10428 9 1.101.10.3.2.18
		fkUserFlowControlIpPktPriorityType OBJECT-TYPE
			SYNTAX INTEGER
				{
				ipPrecedence(1),
				diffServ(2),
				ipToS(3)
				}
			MAX-ACCESS read-write
			STATUS current
			DESCRIPTION
				"Description."
			::= { fkUserFlowControl 18 }

		
		-- 1.3.6.1.4.1.10428 9 1.101.10.3.2.19
		fkUserFlowControlIpPktPriority OBJECT-TYPE
			SYNTAX Integer32
			MAX-ACCESS read-write
			STATUS current
			DESCRIPTION
				"The Priority value in incoming IP packet.
				If fkUserFlowControlIpPktPriorityType is 1, 
				this value's range is 0-7.
				If fkUserFlowControlIpPktPriorityType is 2, 
				this value's range is 0-63.
				If fkUserFlowControlIpPktPriorityType is 3, 
				this value's range is 0-255.
				"
			::= { fkUserFlowControl 19 }

		
		-- 1.3.6.1.4.1.10428 9 1.101.10.3.2.20
		fkUserFlowControlProtocolType OBJECT-TYPE
			SYNTAX Integer32 (0..255)
			MAX-ACCESS read-write
			STATUS current
			DESCRIPTION
				"The IP protocol type value"
			::= { fkUserFlowControl 20 }

		
		-- 1.3.6.1.4.1.10428 9 1.101.10.3.2.21
		fkUserFlowControlTcpFlag OBJECT-TYPE
			SYNTAX BITS
				{
				reserv0(0),
				reserv1(1),
				urg(2),
				ack(3),
				psh(4),
				rst(5),
				syn(6),
				fin(7)
				}
			MAX-ACCESS read-write
			STATUS current
			DESCRIPTION
				"Description."
			::= { fkUserFlowControl 21 }

		
		-- 1.3.6.1.4.1.10428 9 1.101.10.3.2.22
		fkUserFlowControlSrcL4Port OBJECT-TYPE
			SYNTAX Integer32 (0..65535)
			MAX-ACCESS read-write
			STATUS current
			DESCRIPTION
				"The source L4 port number, only valid for TCP or UDP packets."
			::= { fkUserFlowControl 22 }

		
		-- 1.3.6.1.4.1.10428 9 1.101.10.3.2.23
		fkUserFlowControlDstL4Port OBJECT-TYPE
			SYNTAX Integer32 (0..65535)
			MAX-ACCESS read-write
			STATUS current
			DESCRIPTION
				"The destination L4 port number, only valid for TCP or UDP packets."
			::= { fkUserFlowControl 23 }

		
		-- 1.3.6.1.4.1.10428 9 1.101.10.3.2.24
		fkUserFlowControlPktLen OBJECT-TYPE
			SYNTAX Integer32 (21..65535)
			MAX-ACCESS read-write
			STATUS current
			DESCRIPTION
				"The packet length of the incoming packet"
			::= { fkUserFlowControl 24 }

		
		-- 1.3.6.1.4.1.10428 9 1.101.10.3.2.25
		fkUserFlowControlValidFlag OBJECT-TYPE
			SYNTAX BITS
				{
				ufIngressPort(0),
				ufEgressPort(1),
				ufEthernetType(2),
				ufSrcMacAddress(3),
				ufDstMacAddress(4),
				ufVlanId(5),
				uf8021p(6),
				ufSrcIpAddress(7),
				ufSrcPrefixLength(8),
				ufDstIpAddress(9),
				ufDstPrefixLength(10),
				ufIpPktPriority(11),
				ufProtocolType(12),
				ufTcpFlag(13),
				ufSrcL4Port(14),
				ufDstL4Port(15),
				ufPacketLength(16),
				ufPriority(17),
				ufInnerVlanId(18),
				ufInner8021p(19)
				}
			MAX-ACCESS read-write
			STATUS current
			DESCRIPTION
				"The ICMP type, only valid for ICMP packets."
			::= { fkUserFlowControl 25 }

		
		-- 1.3.6.1.4.1.10428 9 1.101.10.3.2.26
		fkUserFlowControlMatchFlag OBJECT-TYPE
			SYNTAX BITS
				{
				ufIngressPort(0),
				ufEgressPort(1),
				ufEthernetType(2),
				ufSrcMacAddress(3),
				ufDstMacAddress(4),
				ufVlanId(5),
				uf8021p(6),
				ufSrcIpAddress(7),
				ufSrcPrefixLength(8),
				ufDstIpAddress(9),
				ufDstPrefixLength(10),
				ufIpPktPriority(11),
				ufProtocolType(12),
				ufTcpFlag(13),
				ufSrcL4Port(14),
				ufDstL4Port(15),
				ufPacketLength(16),
				ufPriority(17)
				}
			MAX-ACCESS read-write
			STATUS current
			DESCRIPTION
				"The ICMP code, only valid for ICMP packets."
			::= { fkUserFlowControl 26 }

		
		-- 1.3.6.1.4.1.10428 9 1.101.10.3.2.27
		fkUserFlowControlPriority OBJECT-TYPE
			SYNTAX INTEGER
				{
				low(1),
				medium(2),
				high(3),
				highest(4)
				}
			MAX-ACCESS read-write
			STATUS current
			DESCRIPTION
				"The priority of this user flow"
			::= { fkUserFlowControl 27 }

		
		-- 1.3.6.1.4.1.10428 9 1.101.10.3.2.28
		fkUserFlowControlMatchCounterId OBJECT-TYPE
			SYNTAX Integer32
			MAX-ACCESS read-write
			STATUS current
			DESCRIPTION
				"The counter index to be apply for the matched packets."
			::= { fkUserFlowControl 28 }

		
		-- 1.3.6.1.4.1.10428 9 1.101.10.3.2.29
		fkUserFlowControlMatchTrafficProfileId OBJECT-TYPE
			SYNTAX Integer32
			MAX-ACCESS read-write
			STATUS current
			DESCRIPTION
				"The traffic profile index to be apply for the matched packets."
			::= { fkUserFlowControl 29 }

		
		-- 1.3.6.1.4.1.10428 9 1.101.10.3.2.30
		fkUserFlowControlMatchQueue OBJECT-TYPE
			SYNTAX Integer32 (0..7)
			MAX-ACCESS read-write
			STATUS current
			DESCRIPTION
				"The CoS value to be assign for the matched packets"
			::= { fkUserFlowControl 30 }

		
		-- 1.3.6.1.4.1.10428 9 1.101.10.3.2.31
		fkUserFlowControlMatchIpPktPriorityType OBJECT-TYPE
			SYNTAX INTEGER
				{
				ipPrecedence(1),
				diffServ(2),
				ipToS(3)
				}
			MAX-ACCESS read-write
			STATUS current
			DESCRIPTION
				"Description."
			::= { fkUserFlowControl 31 }

		
		-- 1.3.6.1.4.1.10428 9 1.101.10.3.2.32
		fkUserFlowControlMatchIpPktPriority OBJECT-TYPE
			SYNTAX Integer32
			MAX-ACCESS read-write
			STATUS current
			DESCRIPTION
				"The Priority value in incoming IP packet.
				If type is 1, then this value's range is 0-7.
				If type is 2, then this value's range is 0-63.
				If type is 3, then this value's range is 0-255.
				"
			DEFVAL { -1 }
			::= { fkUserFlowControl 32 }

		
		-- 1.3.6.1.4.1.10428 9 1.101.10.3.2.33
		fkUserFlowControlMatchRedirPort OBJECT-TYPE
			SYNTAX Integer32
			MAX-ACCESS read-write
			STATUS current
			DESCRIPTION
				"The port to redirect to a matched packet."
			::= { fkUserFlowControl 33 }

		
		-- 1.3.6.1.4.1.10428 9 1.101.10.3.2.34
		fkUserFlowControlMatchVid OBJECT-TYPE
			SYNTAX Integer32 (1..4096)
			MAX-ACCESS read-write
			STATUS current
			DESCRIPTION
				"The vlan id to be assigned for the matched packets"
			::= { fkUserFlowControl 34 }

		
		-- 1.3.6.1.4.1.10428 9 1.101.10.3.2.35
		fkUserFlowControlMatchDstMac OBJECT-TYPE
			SYNTAX OCTET STRING
			MAX-ACCESS read-write
			STATUS current
			DESCRIPTION
				"Description."
			::= { fkUserFlowControl 35 }

		
		-- 1.3.6.1.4.1.10428 9 1.101.10.3.2.36
		fkUserFlowControlMatchPortMap OBJECT-TYPE
			SYNTAX OCTET STRING
			MAX-ACCESS read-write
			STATUS current
			DESCRIPTION
				"Description."
			::= { fkUserFlowControl 36 }

		
		-- 1.3.6.1.4.1.10428 9 1.101.10.3.2.37
		fkUserFlowControlMatchEgressType OBJECT-TYPE
			SYNTAX INTEGER
				{
				dmac(0),
				egressPorts(1),
				filterPorts(2)
				}
			MAX-ACCESS read-write
			STATUS current
			DESCRIPTION
				"Description."
			::= { fkUserFlowControl 37 }

		
		-- 1.3.6.1.4.1.10428 9 1.101.10.3.2.38
		fkUserFlowControlMatchAction OBJECT-TYPE
			SYNTAX BITS
				{
				ufActDeny(0),
				ufActCopytoCpu(1),
				ufActSameAsTos(2),
				ufActSameAsCos(3),
				ufActMirror(4),
				ufActCounter(5),
				ufActTrafficeProfile(6),
				ufActQueue(7),
				ufActIpPktPriority(8),
				ufActRedirPort(9),
				ufAct8021p(10),
				ufActVid(11),
				ufActEgress(12),
				ufActColorMarking(13),
				ufActRoute(14),
				ufActRouteReachability(15)
				}
			MAX-ACCESS read-write
			STATUS current
			DESCRIPTION
				"The action to be apply for matched packets."
			::= { fkUserFlowControl 38 }

		
		-- 1.3.6.1.4.1.10428 9 1.101.10.3.2.39
		fkUserFlowControlNomatchCounterId OBJECT-TYPE
			SYNTAX Integer32
			MAX-ACCESS read-write
			STATUS current
			DESCRIPTION
				"The counter index to be apply for the unmatched packets."
			::= { fkUserFlowControl 39 }

		
		-- 1.3.6.1.4.1.10428 9 1.101.10.3.2.40
		fkUserFlowControlNomatchTrafficProfileId OBJECT-TYPE
			SYNTAX Integer32
			MAX-ACCESS read-write
			STATUS current
			DESCRIPTION
				"The traffic profile index to be apply for the unmatched packets."
			::= { fkUserFlowControl 40 }

		
		-- 1.3.6.1.4.1.10428 9 1.101.10.3.2.41
		fkUserFlowControlNomatchQueue OBJECT-TYPE
			SYNTAX Integer32 (0..7)
			MAX-ACCESS read-write
			STATUS current
			DESCRIPTION
				"The CoS value to be assign for the unmatched packets"
			::= { fkUserFlowControl 41 }

		
		-- 1.3.6.1.4.1.10428 9 1.101.10.3.2.42
		fkUserFlowControlNomatchIpPktPriorityType OBJECT-TYPE
			SYNTAX INTEGER
				{
				ipPrecedence(1),
				diffServ(2),
				ipToS(3)
				}
			MAX-ACCESS read-write
			STATUS current
			DESCRIPTION
				"Description."
			::= { fkUserFlowControl 42 }

		
		-- 1.3.6.1.4.1.10428 9 1.101.10.3.2.43
		fkUserFlowControlNomatchIpPktPriority OBJECT-TYPE
			SYNTAX Integer32
			MAX-ACCESS read-write
			STATUS current
			DESCRIPTION
				"The Priority value in incoming IP packet.
				If type is 1, then this value's range is 0-7.
				If type is 2, then this value's range is 0-63.
				If type is 3, then this value's range is 0-255.
				"
			DEFVAL { -1 }
			::= { fkUserFlowControl 43 }

		
		-- 1.3.6.1.4.1.10428 9 1.101.10.3.2.44
		fkUserFlowControlNomatchRedirPort OBJECT-TYPE
			SYNTAX Integer32
			MAX-ACCESS read-write
			STATUS current
			DESCRIPTION
				"The port to redirect a unmatched packet."
			::= { fkUserFlowControl 44 }

		
		-- 1.3.6.1.4.1.10428 9 1.101.10.3.2.45
		fkUserFlowControlNomatchVid OBJECT-TYPE
			SYNTAX Integer32 (0..4096)
			MAX-ACCESS read-write
			STATUS current
			DESCRIPTION
				"The vlan id to be assigned for the unmatched packets"
			::= { fkUserFlowControl 45 }

		
		-- 1.3.6.1.4.1.10428 9 1.101.10.3.2.46
		fkUserFlowControlNomatchAction OBJECT-TYPE
			SYNTAX BITS
				{
				ufActDeny(0),
				ufActCopytoCpu(1),
				ufActSameAsTos(2),
				ufActSameAsCos(3),
				ufActMirror(4),
				ufActCounter(5),
				ufActTrafficeProfile(6),
				ufActQueue(7),
				ufActIpPktPriority(8),
				ufActRedirPort(9),
				ufAct8021p(10),
				ufActVid(11),
				ufActEgress(12)
				}
			MAX-ACCESS read-write
			STATUS current
			DESCRIPTION
				"The action to be apply for unmatched packets."
			::= { fkUserFlowControl 46 }

		
		-- 1.3.6.1.4.1.10428 9 1.101.10.3.2.47
		fkUserFlowControlMatchColorMarkingId OBJECT-TYPE
			SYNTAX Integer32
			MAX-ACCESS read-write
			STATUS current
			DESCRIPTION
				"The color marking profile index to be apply for the matched packet."
			::= { fkUserFlowControl 47 }

		
		-- 1.3.6.1.4.1.10428 9 1.101.10.3.2.48
		fkUserFlowControlNomatchColorMarkingId OBJECT-TYPE
			SYNTAX Integer32
			MAX-ACCESS read-write
			STATUS current
			DESCRIPTION
				"The color marking profile index to be apply for the nomatched packet."
			::= { fkUserFlowControl 48 }

		
		-- 1.3.6.1.4.1.10428 9 1.101.10.3.2.49
		fkUserFlowControlInnerVlan OBJECT-TYPE
			SYNTAX Integer32 (1..4094)
			MAX-ACCESS read-write
			STATUS current
			DESCRIPTION
				"Inner VLAN ID"
			::= { fkUserFlowControl 49 }

		
		-- 1.3.6.1.4.1.10428 9 1.101.10.3.2.50
		fkUserFlowControlInner8021p OBJECT-TYPE
			SYNTAX Integer32 (0..7)
			MAX-ACCESS read-write
			STATUS current
			DESCRIPTION
				"The value of the Inner IEEE802.1p priority in the packet"
			::= { fkUserFlowControl 50 }

		
		-- 1.3.6.1.4.1.10428 9 1.101.10.3.2.51
		fkUserFlowControlMatchRoutePrimary OBJECT-TYPE
			SYNTAX IpAddress
			MAX-ACCESS read-write
			STATUS current
			DESCRIPTION
				"Description."
			::= { fkUserFlowControl 51 }

		
		-- 1.3.6.1.4.1.10428 9 1.101.10.3.2.52
		fkUserFlowControlMatchRouteSecondary OBJECT-TYPE
			SYNTAX IpAddress
			MAX-ACCESS read-write
			STATUS current
			DESCRIPTION
				"Description."
			::= { fkUserFlowControl 52 }

		
		-- 1.3.6.1.4.1.10428 9 1.101.10.3.3
		fkUserFlowNotification OBJECT IDENTIFIER ::= { fkUserFlow 3 }

		
		-- 1.3.6.1.4.1.10428 9 1.101.10.3.3.1
		fkUserFlowCreated NOTIFICATION-TYPE
			OBJECTS { fkUserFlowControlRequest, fkUserFlowControlTimeStamp, fkUserFlowControlReqResult, fkUserFlowControlName }
			STATUS current
			DESCRIPTION 
				"Description."
			::= { fkUserFlowNotification 1 }

		
		-- 1.3.6.1.4.1.10428 9 1.101.10.3.3.2
		fkUserFlowDestroyed NOTIFICATION-TYPE
			OBJECTS { fkUserFlowControlRequest, fkUserFlowControlTimeStamp, fkUserFlowControlReqResult, fkUserFlowControlName }
			STATUS current
			DESCRIPTION 
				"Description."
			::= { fkUserFlowNotification 2 }

		
		-- 1.3.6.1.4.1.10428 9 1.101.10.3.3.3
		fkUserFlowClassifierProfileChanged NOTIFICATION-TYPE
			OBJECTS { fkUserFlowControlRequest, fkUserFlowControlTimeStamp, fkUserFlowControlReqResult, fkUserFlowControlName }
			STATUS current
			DESCRIPTION 
				"Description."
			::= { fkUserFlowNotification 3 }

		
		-- 1.3.6.1.4.1.10428 9 1.101.10.3.3.4
		fkUserFlowMatchActionProfileChanged NOTIFICATION-TYPE
			OBJECTS { fkUserFlowControlRequest, fkUserFlowControlTimeStamp, fkUserFlowControlReqResult, fkUserFlowControlName }
			STATUS current
			DESCRIPTION 
				"Description."
			::= { fkUserFlowNotification 4 }

		
		-- 1.3.6.1.4.1.10428 9 1.101.10.3.3.5
		fkUserFlowNomatchActionProfileChanged NOTIFICATION-TYPE
			OBJECTS { fkUserFlowControlRequest, fkUserFlowControlTimeStamp, fkUserFlowControlReqResult, fkUserFlowControlName }
			STATUS current
			DESCRIPTION 
				"Description."
			::= { fkUserFlowNotification 5 }

		
--  2.6
		-- 1.3.6.1.4.1.10428 9 1.101.10.4
		fkPortSchedule OBJECT IDENTIFIER ::= { fkQoS 4 }

		
		-- 1.3.6.1.4.1.10428 9 1.101.10.4.1
		fkPortSchedultTable OBJECT-TYPE
			SYNTAX SEQUENCE OF FkPortSchedultEntry
			MAX-ACCESS not-accessible
			STATUS current
			DESCRIPTION
				"Description."
			::= { fkPortSchedule 1 }

		
		-- 1.3.6.1.4.1.10428 9 1.101.10.4.1.1
		fkPortSchedultEntry OBJECT-TYPE
			SYNTAX FkPortSchedultEntry
			MAX-ACCESS not-accessible
			STATUS current
			DESCRIPTION
				"Description."
			INDEX { fkPortSchedulInterfaceIndex }
			::= { fkPortSchedultTable 1 }

		
		FkPortSchedultEntry ::=
			SEQUENCE { 
				fkPortSchedulInterfaceIndex
					Integer32,
				fkPortScheduleMode
					INTEGER
			 }

		-- 1.3.6.1.4.1.10428 9 1.101.10.4.1.1.1
		fkPortSchedulInterfaceIndex OBJECT-TYPE
			SYNTAX Integer32 (1..256)
			MAX-ACCESS read-only
			STATUS current
			DESCRIPTION
				"Interface Index"
			::= { fkPortSchedultEntry 1 }

		
		-- 1.3.6.1.4.1.10428 9 1.101.10.4.1.1.2
		fkPortScheduleMode OBJECT-TYPE
			SYNTAX INTEGER
				{
				strictqueueing(1),
				wrr(2),
				wfq(3),
				rr(4),
				drr(5)
				}
			MAX-ACCESS read-only
			STATUS current
			DESCRIPTION
				"The scheduling mode of port"
			::= { fkPortSchedultEntry 2 }

		
		-- 1.3.6.1.4.1.10428 9 1.101.10.4.2
		fkPortScheduleControl OBJECT IDENTIFIER ::= { fkPortSchedule 2 }

		
		-- 1.3.6.1.4.1.10428 9 1.101.10.4.2.1
		fkPortScheduleControlRequest OBJECT-TYPE
			SYNTAX FkPortScheduleControlRequestType
			MAX-ACCESS read-write
			STATUS current
			DESCRIPTION
				"Description."
			::= { fkPortScheduleControl 1 }

		
		-- 1.3.6.1.4.1.10428 9 1.101.10.4.2.2
		fkScheduleControlStatus OBJECT-TYPE
			SYNTAX FkControlStatusType
			MAX-ACCESS read-only
			STATUS current
			DESCRIPTION
				"Description."
			::= { fkPortScheduleControl 2 }

		
		-- 1.3.6.1.4.1.10428 9 1.101.10.4.2.3
		fkPortScheduleControlTimer OBJECT-TYPE
			SYNTAX Gauge32
			MAX-ACCESS read-write
			STATUS current
			DESCRIPTION
				"Description."
			::= { fkPortScheduleControl 3 }

		
		-- 1.3.6.1.4.1.10428 9 1.101.10.4.2.4
		fkPortScheduleControlTimeStamp OBJECT-TYPE
			SYNTAX TimeTicks
			MAX-ACCESS read-only
			STATUS current
			DESCRIPTION
				"Description."
			::= { fkPortScheduleControl 4 }

		
		-- 1.3.6.1.4.1.10428 9 1.101.10.4.2.5
		fkPortScheduleControlReqResult OBJECT-TYPE
			SYNTAX FkControlRequestResultType
			MAX-ACCESS read-only
			STATUS current
			DESCRIPTION
				"Description."
			::= { fkPortScheduleControl 5 }

		
		-- 1.3.6.1.4.1.10428 9 1.101.10.4.2.6
		fkPortScheduleControlInterfaceIndex OBJECT-TYPE
			SYNTAX Integer32
			MAX-ACCESS read-write
			STATUS current
			DESCRIPTION
				"Interface Index"
			::= { fkPortScheduleControl 6 }

		
		-- 1.3.6.1.4.1.10428 9 1.101.10.4.2.7
		fkPortScheduleControlMode OBJECT-TYPE
			SYNTAX INTEGER
				{
				strictqueueing(1),
				wrr(2),
				wfq(3),
				rr(4),
				drr(5)
				}
			MAX-ACCESS read-write
			STATUS current
			DESCRIPTION
				"The scheduling mode of port"
			::= { fkPortScheduleControl 7 }

		
		-- 1.3.6.1.4.1.10428 9 1.101.10.4.3
		fkPortScheduleNotification OBJECT IDENTIFIER ::= { fkPortSchedule 3 }

		
		-- 1.3.6.1.4.1.10428 9 1.101.10.4.3.1
		fkPortScheduleModeChanged NOTIFICATION-TYPE
			OBJECTS { fkPortScheduleMode, fkPortScheduleControlRequest, fkPortScheduleControlTimeStamp, fkPortScheduleControlReqResult }
			STATUS current
			DESCRIPTION 
				"Description."
			::= { fkPortScheduleNotification 1 }

		
--  2.7
		-- 1.3.6.1.4.1.10428 9 1.101.10.5
		fkQueue OBJECT IDENTIFIER ::= { fkQoS 5 }

		
		-- 1.3.6.1.4.1.10428 9 1.101.10.5.1
		fkQueueTable OBJECT-TYPE
			SYNTAX SEQUENCE OF FkQueueEntry
			MAX-ACCESS not-accessible
			STATUS current
			DESCRIPTION
				"Description."
			::= { fkQueue 1 }

		
		-- 1.3.6.1.4.1.10428 9 1.101.10.5.1.1
		fkQueueEntry OBJECT-TYPE
			SYNTAX FkQueueEntry
			MAX-ACCESS not-accessible
			STATUS current
			DESCRIPTION
				"Description."
			INDEX { fkPortSchedulInterfaceIndex, fkQueueId }
			::= { fkQueueTable 1 }

		
		FkQueueEntry ::=
			SEQUENCE { 
				fkQueueId
					Integer32,
				fkQueueREDEnable
					INTEGER,
				fkQueueMappedCoS
					BITS,
				fkQueueWREDMinThreshold
					Integer32,
				fkQueueWREDMaxThreshold
					Integer32,
				fkQueueWREDProbMax
					Integer32,
				fkQueueMinBandwidth
					Integer32,
				fkQueueMaxBandwidth
					Integer32,
				fkQueueWeight
					Integer32,
				fkQueueMaxLatency
					Integer32,
				fkQueueMaxPackets
					Integer32,
				fkQueueQuantum
					INTEGER,
				fkQueueUsedPkts
					Counter32,
				fkQueueUsedBytes
					Counter32
			 }

		-- 1.3.6.1.4.1.10428 9 1.101.10.5.1.1.1
		fkQueueId OBJECT-TYPE
			SYNTAX Integer32 (0..7)
			MAX-ACCESS read-only
			STATUS current
			DESCRIPTION
				"queue index"
			::= { fkQueueEntry 1 }

		
		-- 1.3.6.1.4.1.10428 9 1.101.10.5.1.1.2
		fkQueueREDEnable OBJECT-TYPE
			SYNTAX INTEGER
				{
				disable(0),
				enable(1)
				}
			MAX-ACCESS read-only
			STATUS current
			DESCRIPTION
				"Description."
			DEFVAL { disable }
			::= { fkQueueEntry 2 }

		
		-- 1.3.6.1.4.1.10428 9 1.101.10.5.1.1.3
		fkQueueMappedCoS OBJECT-TYPE
			SYNTAX BITS
				{
				cos0(0),
				cos1(1),
				cos2(2),
				cos3(3),
				cos4(4),
				cos5(5),
				cos6(6),
				cos7(7)
				}
			MAX-ACCESS read-only
			STATUS current
			DESCRIPTION
				"Description."
			::= { fkQueueEntry 3 }

		
		-- 1.3.6.1.4.1.10428 9 1.101.10.5.1.1.4
		fkQueueWREDMinThreshold OBJECT-TYPE
			SYNTAX Integer32
			MAX-ACCESS read-only
			STATUS current
			DESCRIPTION
				"The total number of packets where WRED can start"
			::= { fkQueueEntry 4 }

		
		-- 1.3.6.1.4.1.10428 9 1.101.10.5.1.1.5
		fkQueueWREDMaxThreshold OBJECT-TYPE
			SYNTAX Integer32
			MAX-ACCESS read-only
			STATUS current
			DESCRIPTION
				"Above max threshold, queue drops all ingress"
			::= { fkQueueEntry 5 }

		
		-- 1.3.6.1.4.1.10428 9 1.101.10.5.1.1.6
		fkQueueWREDProbMax OBJECT-TYPE
			SYNTAX Integer32 (1..15)
			MAX-ACCESS read-only
			STATUS current
			DESCRIPTION
				"The worst case random drop probability"
			::= { fkQueueEntry 6 }

		
		-- 1.3.6.1.4.1.10428 9 1.101.10.5.1.1.7
		fkQueueMinBandwidth OBJECT-TYPE
			SYNTAX Integer32
			MAX-ACCESS read-only
			STATUS current
			DESCRIPTION
				"The value is unit of 64kbps"
			::= { fkQueueEntry 7 }

		
		-- 1.3.6.1.4.1.10428 9 1.101.10.5.1.1.8
		fkQueueMaxBandwidth OBJECT-TYPE
			SYNTAX Integer32
			MAX-ACCESS read-only
			STATUS current
			DESCRIPTION
				"The value is unit of 64 kbps."
			::= { fkQueueEntry 8 }

		
		-- 1.3.6.1.4.1.10428 9 1.101.10.5.1.1.9
		fkQueueWeight OBJECT-TYPE
			SYNTAX Integer32 (-1 | 1..255)
			MAX-ACCESS read-only
			STATUS current
			DESCRIPTION
				"The weight of this queue.
				The value of -1 is unlimited"
			::= { fkQueueEntry 9 }

		
		-- 1.3.6.1.4.1.10428 9 1.101.10.5.1.1.10
		fkQueueMaxLatency OBJECT-TYPE
			SYNTAX Integer32
			MAX-ACCESS read-only
			STATUS current
			DESCRIPTION
				"Description."
			::= { fkQueueEntry 10 }

		
		-- 1.3.6.1.4.1.10428 9 1.101.10.5.1.1.11
		fkQueueMaxPackets OBJECT-TYPE
			SYNTAX Integer32
			MAX-ACCESS read-only
			STATUS current
			DESCRIPTION
				"Description."
			::= { fkQueueEntry 11 }

		
		-- 1.3.6.1.4.1.10428 9 1.101.10.5.1.1.12
		fkQueueQuantum OBJECT-TYPE
			SYNTAX INTEGER (-1 | 1..127)
			MAX-ACCESS read-only
			STATUS current
			DESCRIPTION
				"The DRR quantum value."
			::= { fkQueueEntry 12 }

		
		-- 1.3.6.1.4.1.10428 9 1.101.10.5.1.1.13
		fkQueueUsedPkts OBJECT-TYPE
			SYNTAX Counter32
			MAX-ACCESS read-only
			STATUS current
			DESCRIPTION
				"The used packets of port/queue."
			::= { fkQueueEntry 13 }

		
		-- 1.3.6.1.4.1.10428 9 1.101.10.5.1.1.14
		fkQueueUsedBytes OBJECT-TYPE
			SYNTAX Counter32
			MAX-ACCESS read-only
			STATUS current
			DESCRIPTION
				"The used bytes of port/queue."
			::= { fkQueueEntry 14 }

		
		-- 1.3.6.1.4.1.10428 9 1.101.10.5.2
		fkQueueControl OBJECT IDENTIFIER ::= { fkQueue 2 }

		
		-- 1.3.6.1.4.1.10428 9 1.101.10.5.2.1
		fkQueueControlRequest OBJECT-TYPE
			SYNTAX INTEGER
				{
				setQueueProfile(1),
				setQuantum(2)
				}
			MAX-ACCESS read-write
			STATUS current
			DESCRIPTION
				"Description."
			::= { fkQueueControl 1 }

		
		-- 1.3.6.1.4.1.10428 9 1.101.10.5.2.2
		fkQueueControlStatus OBJECT-TYPE
			SYNTAX Integer32
			MAX-ACCESS read-only
			STATUS current
			DESCRIPTION
				"Description."
			::= { fkQueueControl 2 }

		
		-- 1.3.6.1.4.1.10428 9 1.101.10.5.2.3
		fkQueueControlTimer OBJECT-TYPE
			SYNTAX Gauge32
			MAX-ACCESS read-write
			STATUS current
			DESCRIPTION
				"Description."
			::= { fkQueueControl 3 }

		
		-- 1.3.6.1.4.1.10428 9 1.101.10.5.2.4
		fkQueueControlTimeStamp OBJECT-TYPE
			SYNTAX Integer32
			MAX-ACCESS read-only
			STATUS current
			DESCRIPTION
				"Description."
			::= { fkQueueControl 4 }

		
		-- 1.3.6.1.4.1.10428 9 1.101.10.5.2.5
		fkQueueControlReqResult OBJECT-TYPE
			SYNTAX FkControlRequestResultType
			MAX-ACCESS read-only
			STATUS current
			DESCRIPTION
				"Description."
			::= { fkQueueControl 5 }

		
		-- 1.3.6.1.4.1.10428 9 1.101.10.5.2.6
		fkQueueControlInterfaceIndex OBJECT-TYPE
			SYNTAX Integer32
			MAX-ACCESS read-write
			STATUS current
			DESCRIPTION
				"Interface Index"
			::= { fkQueueControl 6 }

		
		-- 1.3.6.1.4.1.10428 9 1.101.10.5.2.7
		fkQueueControlId OBJECT-TYPE
			SYNTAX Integer32 (0..7)
			MAX-ACCESS read-write
			STATUS current
			DESCRIPTION
				"Queue index"
			::= { fkQueueControl 7 }

		
		-- 1.3.6.1.4.1.10428 9 1.101.10.5.2.8
		fkQueueControlREDEnable OBJECT-TYPE
			SYNTAX INTEGER
				{
				disable(0),
				enable(1)
				}
			MAX-ACCESS read-write
			STATUS current
			DESCRIPTION
				"Description."
			DEFVAL { disable }
			::= { fkQueueControl 8 }

		
		-- 1.3.6.1.4.1.10428 9 1.101.10.5.2.9
		fkQueueControlMappedCoS OBJECT-TYPE
			SYNTAX BITS
				{
				cos0(0),
				cos1(1),
				cos2(2),
				cos3(3),
				cos4(4),
				cos5(5),
				cos6(6),
				cos7(7)
				}
			MAX-ACCESS read-write
			STATUS current
			DESCRIPTION
				"Description."
			::= { fkQueueControl 9 }

		
		-- 1.3.6.1.4.1.10428 9 1.101.10.5.2.10
		fkQueueControlWREDMinThreshold OBJECT-TYPE
			SYNTAX Integer32
			MAX-ACCESS read-write
			STATUS current
			DESCRIPTION
				"The total number of packets where WRED can start"
			::= { fkQueueControl 10 }

		
		-- 1.3.6.1.4.1.10428 9 1.101.10.5.2.11
		fkQueueControlWREDMaxThreshold OBJECT-TYPE
			SYNTAX Integer32
			MAX-ACCESS read-write
			STATUS current
			DESCRIPTION
				"Above max threshold, queue drops all ingress"
			::= { fkQueueControl 11 }

		
		-- 1.3.6.1.4.1.10428 9 1.101.10.5.2.12
		fkQueueControlWREDProbMax OBJECT-TYPE
			SYNTAX Integer32 (1..15)
			MAX-ACCESS read-write
			STATUS current
			DESCRIPTION
				"The worst case random drop probability"
			::= { fkQueueControl 12 }

		
		-- 1.3.6.1.4.1.10428 9 1.101.10.5.2.13
		fkQueueControlMinBandwidth OBJECT-TYPE
			SYNTAX Integer32
			MAX-ACCESS read-write
			STATUS current
			DESCRIPTION
				"The value is unit of 64kbps"
			::= { fkQueueControl 13 }

		
		-- 1.3.6.1.4.1.10428 9 1.101.10.5.2.14
		fkQueueControlMaxBandwidth OBJECT-TYPE
			SYNTAX Integer32
			MAX-ACCESS read-write
			STATUS current
			DESCRIPTION
				"The value is unit of 64kbps"
			::= { fkQueueControl 14 }

		
		-- 1.3.6.1.4.1.10428 9 1.101.10.5.2.15
		fkQueueControlWeight OBJECT-TYPE
			SYNTAX Integer32 (-1 | 1..255)
			MAX-ACCESS read-write
			STATUS current
			DESCRIPTION
				"The weight of this queue.
				The value of -1 is unlimited"
			::= { fkQueueControl 15 }

		
		-- 1.3.6.1.4.1.10428 9 1.101.10.5.2.16
		fkQueueControlMaxLatency OBJECT-TYPE
			SYNTAX Integer32
			MAX-ACCESS read-write
			STATUS current
			DESCRIPTION
				"Description."
			::= { fkQueueControl 16 }

		
		-- 1.3.6.1.4.1.10428 9 1.101.10.5.2.17
		fkQueueControlMaxPackets OBJECT-TYPE
			SYNTAX Integer32
			MAX-ACCESS read-write
			STATUS current
			DESCRIPTION
				"Description."
			::= { fkQueueControl 17 }

		
		-- 1.3.6.1.4.1.10428 9 1.101.10.5.2.18
		fkQueueControlQuantum OBJECT-TYPE
			SYNTAX INTEGER (-1 | 1..127)
			MAX-ACCESS read-write
			STATUS current
			DESCRIPTION
				"The DRR quantum value."
			::= { fkQueueControl 18 }

		
		-- 1.3.6.1.4.1.10428 9 1.101.10.5.3
		fkQueueNotification OBJECT IDENTIFIER ::= { fkQueue 3 }

		
		-- 1.3.6.1.4.1.10428 9 1.101.10.5.3.1
		fkQueueProfileChanged NOTIFICATION-TYPE
			OBJECTS { fkQueueWREDMinThreshold, fkQueueWREDMaxThreshold, fkQueueWREDProbMax, fkQueueMinBandwidth, fkQueueMaxBandwidth, 
				fkQueueControlTimeStamp, fkQueueControlReqResult, fkQueueControlRequest, fkQueueWeight, fkQueueREDEnable, 
				fkQueueMappedCoS }
			STATUS current
			DESCRIPTION 
				"Description."
			::= { fkQueueNotification 1 }

		
		-- 1.3.6.1.4.1.10428 9 1.101.10.5.3.2
		fkQueueQuantumChanged NOTIFICATION-TYPE
			OBJECTS { fkQueueControlRequest, fkQueueControlTimeStamp, fkQueueControlReqResult, fkQueueControlQuantum }
			STATUS current
			DESCRIPTION 
				"Description."
			::= { fkQueueNotification 2 }

		
		-- 1.3.6.1.4.1.10428 9 1.101.10.6
		fkCounter OBJECT IDENTIFIER ::= { fkQoS 6 }

		
		-- 1.3.6.1.4.1.10428 9 1.101.10.6.1
		fkCounterTable OBJECT-TYPE
			SYNTAX SEQUENCE OF FkCounterEntry
			MAX-ACCESS not-accessible
			STATUS current
			DESCRIPTION
				"Description."
			::= { fkCounter 1 }

		
		-- 1.3.6.1.4.1.10428 9 1.101.10.6.1.1
		fkCounterEntry OBJECT-TYPE
			SYNTAX FkCounterEntry
			MAX-ACCESS not-accessible
			STATUS current
			DESCRIPTION
				"Description."
			INDEX { fkCounterIndex }
			::= { fkCounterTable 1 }

		
		FkCounterEntry ::=
			SEQUENCE { 
				fkCounterIndex
					INTEGER,
				fkCounterPackets
					Unsigned32
			 }

		-- 1.3.6.1.4.1.10428 9 1.101.10.6.1.1.1
		fkCounterIndex OBJECT-TYPE
			SYNTAX INTEGER (1..255)
			MAX-ACCESS read-only
			STATUS current
			DESCRIPTION
				"The Counter Index"
			::= { fkCounterEntry 1 }

		
		-- 1.3.6.1.4.1.10428 9 1.101.10.6.1.1.2
		fkCounterPackets OBJECT-TYPE
			SYNTAX Unsigned32
			MAX-ACCESS read-only
			STATUS current
			DESCRIPTION
				"Number of packets"
			::= { fkCounterEntry 2 }

		
		-- 1.3.6.1.4.1.10428 9 1.101.10.6.2
		fkCounterControl OBJECT IDENTIFIER ::= { fkCounter 2 }

		
		-- 1.3.6.1.4.1.10428 9 1.101.10.6.2.1
		fkCounterControlRequest OBJECT-TYPE
			SYNTAX INTEGER { clearCounter(1) }
			MAX-ACCESS read-write
			STATUS current
			DESCRIPTION
				"Description."
			::= { fkCounterControl 1 }

		
		-- 1.3.6.1.4.1.10428 9 1.101.10.6.2.2
		fkCounterControlStatus OBJECT-TYPE
			SYNTAX FkControlStatusType
			MAX-ACCESS read-only
			STATUS current
			DESCRIPTION
				"Description."
			::= { fkCounterControl 2 }

		
		-- 1.3.6.1.4.1.10428 9 1.101.10.6.2.3
		fkCounterControlTimer OBJECT-TYPE
			SYNTAX Gauge32
			MAX-ACCESS read-write
			STATUS current
			DESCRIPTION
				"Description."
			::= { fkCounterControl 3 }

		
		-- 1.3.6.1.4.1.10428 9 1.101.10.6.2.4
		fkCounterControlTimeStamp OBJECT-TYPE
			SYNTAX TimeTicks
			MAX-ACCESS read-only
			STATUS current
			DESCRIPTION
				"Description."
			::= { fkCounterControl 4 }

		
		-- 1.3.6.1.4.1.10428 9 1.101.10.6.2.5
		fkCounterControlReqResult OBJECT-TYPE
			SYNTAX FkControlRequestResultType
			MAX-ACCESS read-only
			STATUS current
			DESCRIPTION
				"Description."
			::= { fkCounterControl 5 }

		
		-- 1.3.6.1.4.1.10428 9 1.101.10.6.2.6
		fkCounterControlIndex OBJECT-TYPE
			SYNTAX Unsigned32 (1..32)
			MAX-ACCESS read-write
			STATUS current
			DESCRIPTION
				"Description."
			::= { fkCounterControl 6 }

		
		-- 1.3.6.1.4.1.10428 9 1.101.10.6.3
		fkCounterNotification OBJECT IDENTIFIER ::= { fkCounter 3 }

		
		-- 1.3.6.1.4.1.10428 9 1.101.10.6.3.1
		fkCounterCleared NOTIFICATION-TYPE
			OBJECTS { fkCounterControlRequest, fkCounterControlTimeStamp, fkCounterControlReqResult, fkCounterControlIndex }
			STATUS current
			DESCRIPTION 
				"Description."
			::= { fkCounterNotification 1 }

		
		-- 1.3.6.1.4.1.10428 9 1.101.10.7
		fkColorMarking OBJECT IDENTIFIER ::= { fkQoS 7 }

		
		-- 1.3.6.1.4.1.10428 9 1.101.10.7.1
		fkColorMarkingTable OBJECT-TYPE
			SYNTAX SEQUENCE OF FkColorMarkingEntry
			MAX-ACCESS not-accessible
			STATUS current
			DESCRIPTION
				"Description."
			::= { fkColorMarking 1 }

		
		-- 1.3.6.1.4.1.10428 9 1.101.10.7.1.1
		fkColorMarkingEntry OBJECT-TYPE
			SYNTAX FkColorMarkingEntry
			MAX-ACCESS not-accessible
			STATUS current
			DESCRIPTION
				"Description."
			INDEX { fkColorMarkingIndex }
			::= { fkColorMarkingTable 1 }

		
		FkColorMarkingEntry ::=
			SEQUENCE { 
				fkColorMarkingIndex
					INTEGER,
				fkColorMarkingType
					INTEGER,
				fkColorMarkingMode
					INTEGER,
				fkColorMarkingAwareMode
					INTEGER,
				fkColorMarkingCIR
					Integer32,
				fkColorMarkingCBS
					Integer32,
				fkColorMarkingPIR
					Integer32,
				fkColorMarkingPBS
					Integer32,
				fkColorMarkingEBS
					Integer32,
				fkColorMarkingRedAction
					BITS,
				fkColorMarkingYellowAction
					BITS,
				fkColorMarkingGreenAction
					BITS,
				fkColorMarkingRedDscp
					Integer32,
				fkColorMarkingYellowDscp
					Integer32,
				fkColorMarkingGreenDscp
					Integer32,
				fkColorMarkingUseCount
					Integer32
			 }

		-- 1.3.6.1.4.1.10428 9 1.101.10.7.1.1.1
		fkColorMarkingIndex OBJECT-TYPE
			SYNTAX INTEGER (1..2048)
			MAX-ACCESS read-only
			STATUS current
			DESCRIPTION
				"Color marking table index."
			::= { fkColorMarkingEntry 1 }

		
		-- 1.3.6.1.4.1.10428 9 1.101.10.7.1.1.2
		fkColorMarkingType OBJECT-TYPE
			SYNTAX INTEGER
				{
				srTCM(0),
				trTCM(1)
				}
			UNITS "Enum"
			MAX-ACCESS read-only
			STATUS current
			DESCRIPTION
				"Color marking type.
				srTCM = Single Rate Three Color Marking.
				trTCM = Two Rate Three Color Marking.
				"
			DEFVAL { 0 }
			::= { fkColorMarkingEntry 2 }

		
		-- 1.3.6.1.4.1.10428 9 1.101.10.7.1.1.3
		fkColorMarkingMode OBJECT-TYPE
			SYNTAX INTEGER
				{
				blind(0),
				aware(1)
				}
			UNITS "Enum"
			MAX-ACCESS read-only
			STATUS current
			DESCRIPTION
				"Color marking mode."
			DEFVAL { 0 }
			::= { fkColorMarkingEntry 3 }

		
		-- 1.3.6.1.4.1.10428 9 1.101.10.7.1.1.4
		fkColorMarkingAwareMode OBJECT-TYPE
			SYNTAX INTEGER
				{
				unprotected(1),
				protected(2)
				}
			UNITS "Enum"
			MAX-ACCESS read-only
			STATUS current
			DESCRIPTION
				"Color marking aware mode.
				Used only when fkColorMarkingMode is aware."
			DEFVAL { 1 }
			::= { fkColorMarkingEntry 4 }

		
		-- 1.3.6.1.4.1.10428 9 1.101.10.7.1.1.5
		fkColorMarkingCIR OBJECT-TYPE
			SYNTAX Integer32 (1..1000000)
			UNITS "Integer"
			MAX-ACCESS read-only
			STATUS current
			DESCRIPTION
				"Committed Information Rate.
				The value is in unit for 64 kbps.
				"
			DEFVAL { 0 }
			::= { fkColorMarkingEntry 5 }

		
		-- 1.3.6.1.4.1.10428 9 1.101.10.7.1.1.6
		fkColorMarkingCBS OBJECT-TYPE
			SYNTAX Integer32 (1..4000)
			UNITS "Integer"
			MAX-ACCESS read-only
			STATUS current
			DESCRIPTION
				"Committed Burst Size.
				The value is in unit for square of 2 bits.
				"
			DEFVAL { 0 }
			::= { fkColorMarkingEntry 6 }

		
		-- 1.3.6.1.4.1.10428 9 1.101.10.7.1.1.7
		fkColorMarkingPIR OBJECT-TYPE
			SYNTAX Integer32 (1..1000000)
			UNITS "Integer "
			MAX-ACCESS read-only
			STATUS current
			DESCRIPTION
				"Peak Information Rate. 
				*) Used only when fkColorMarkingMode is Aware.
				The value is in unit for 64 kbps.
				."
			DEFVAL { 0 }
			::= { fkColorMarkingEntry 7 }

		
		-- 1.3.6.1.4.1.10428 9 1.101.10.7.1.1.8
		fkColorMarkingPBS OBJECT-TYPE
			SYNTAX Integer32 (1..4000)
			UNITS "Integer "
			MAX-ACCESS read-only
			STATUS current
			DESCRIPTION
				"Peak Burst Size. 
				*) Used only when fkColorMarkingMode is Aware.
				The value is in unit for square of 2 bits.
				"
			DEFVAL { 0 }
			::= { fkColorMarkingEntry 8 }

		
		-- 1.3.6.1.4.1.10428 9 1.101.10.7.1.1.9
		fkColorMarkingEBS OBJECT-TYPE
			SYNTAX Integer32 (1..4000)
			UNITS "Integer "
			MAX-ACCESS read-only
			STATUS current
			DESCRIPTION
				"Excess Burst Size. 
				*) Used only when fkColorMarkingMode is Blind.
				The value is in unit for square of 2 bits.
				"
			DEFVAL { 0 }
			::= { fkColorMarkingEntry 9 }

		
		-- 1.3.6.1.4.1.10428 9 1.101.10.7.1.1.10
		fkColorMarkingRedAction OBJECT-TYPE
			SYNTAX BITS
				{
				reserve0(0),
				reserve1(1),
				reserve2(2),
				reserve3(3),
				reserve4(4),
				dropProcedence(5),
				marking(6),
				drop(7),
				dropPrecedenceGreen(8),
				dropPrecedenceYellow(9),
				dropPrecedenceRed(10)
				}
			UNITS "bits"
			MAX-ACCESS read-only
			STATUS current
			DESCRIPTION
				"The action to be apply when incoming packet is colored in red."
			DEFVAL { { 0 } }
			::= { fkColorMarkingEntry 10 }

		
		-- 1.3.6.1.4.1.10428 9 1.101.10.7.1.1.11
		fkColorMarkingYellowAction OBJECT-TYPE
			SYNTAX BITS
				{
				reserve0(0),
				reserve1(1),
				reserve2(2),
				reserve3(3),
				reserve4(4),
				dropProcedence(5),
				marking(6),
				drop(7),
				dropPrecedenceGreen(8),
				dropPrecedenceYellow(9),
				dropPrecedenceRed(10)
				}
			UNITS "bits"
			MAX-ACCESS read-only
			STATUS current
			DESCRIPTION
				"The action to be apply when incoming packet is colored in yellow."
			DEFVAL { { 0 } }
			::= { fkColorMarkingEntry 11 }

		
		-- 1.3.6.1.4.1.10428 9 1.101.10.7.1.1.12
		fkColorMarkingGreenAction OBJECT-TYPE
			SYNTAX BITS
				{
				reserve0(0),
				reserve1(1),
				reserve2(2),
				reserve3(3),
				reserve4(4),
				dropProcedence(5),
				marking(6),
				drop(7),
				dropPrecedenceGreen(8),
				dropPrecedenceYellow(9),
				dropPrecedenceRed(10)
				}
			UNITS "bits"
			MAX-ACCESS read-only
			STATUS current
			DESCRIPTION
				"The action to be apply when incoming packet is colored in green. (not supported)"
			DEFVAL { { 6 } }
			::= { fkColorMarkingEntry 12 }

		
		-- 1.3.6.1.4.1.10428 9 1.101.10.7.1.1.13
		fkColorMarkingRedDscp OBJECT-TYPE
			SYNTAX Integer32 (0..63)
			UNITS "Integer "
			MAX-ACCESS read-only
			STATUS current
			DESCRIPTION
				"The dscp value to be apply when incoming packet is colored in red."
			DEFVAL { 30 }
			::= { fkColorMarkingEntry 13 }

		
		-- 1.3.6.1.4.1.10428 9 1.101.10.7.1.1.14
		fkColorMarkingYellowDscp OBJECT-TYPE
			SYNTAX Integer32 (0..63)
			UNITS "Integer "
			MAX-ACCESS read-only
			STATUS current
			DESCRIPTION
				"The dscp value to be apply when incoming packet is colored in yellow."
			DEFVAL { 28 }
			::= { fkColorMarkingEntry 14 }

		
		-- 1.3.6.1.4.1.10428 9 1.101.10.7.1.1.15
		fkColorMarkingGreenDscp OBJECT-TYPE
			SYNTAX Integer32 (0..63)
			UNITS "Integer "
			MAX-ACCESS read-only
			STATUS current
			DESCRIPTION
				"The dscp value to be apply when incoming packet is colored in green. (not supported)"
			DEFVAL { 26 }
			::= { fkColorMarkingEntry 15 }

		
		-- 1.3.6.1.4.1.10428 9 1.101.10.7.1.1.16
		fkColorMarkingUseCount OBJECT-TYPE
			SYNTAX Integer32
			MAX-ACCESS read-only
			STATUS current
			DESCRIPTION
				"The number of rules used this color marking profile."
			DEFVAL { 0 }
			::= { fkColorMarkingEntry 16 }

		
		-- 1.3.6.1.4.1.10428 9 1.101.10.7.2
		fkColorMarkingControl OBJECT IDENTIFIER ::= { fkColorMarking 2 }

		
		-- 1.3.6.1.4.1.10428 9 1.101.10.7.2.1
		fkColorMarkingControlRequest OBJECT-TYPE
			SYNTAX INTEGER { setColorMarkingProfile(1) }
			MAX-ACCESS read-write
			STATUS current
			DESCRIPTION
				"Description."
			::= { fkColorMarkingControl 1 }

		
		-- 1.3.6.1.4.1.10428 9 1.101.10.7.2.2
		fkColorMarkingControlStatus OBJECT-TYPE
			SYNTAX FkControlStatusType
			MAX-ACCESS read-write
			STATUS current
			DESCRIPTION
				"Description."
			::= { fkColorMarkingControl 2 }

		
		-- 1.3.6.1.4.1.10428 9 1.101.10.7.2.3
		fkColorMarkingControlTimer OBJECT-TYPE
			SYNTAX Gauge32
			MAX-ACCESS read-write
			STATUS current
			DESCRIPTION
				"Description."
			::= { fkColorMarkingControl 3 }

		
		-- 1.3.6.1.4.1.10428 9 1.101.10.7.2.4
		fkColorMarkingControlTimeStamp OBJECT-TYPE
			SYNTAX TimeTicks
			MAX-ACCESS read-only
			STATUS current
			DESCRIPTION
				"Description."
			::= { fkColorMarkingControl 4 }

		
		-- 1.3.6.1.4.1.10428 9 1.101.10.7.2.5
		fkColorMarkingControlReqResult OBJECT-TYPE
			SYNTAX FkControlRequestResultType
			MAX-ACCESS read-write
			STATUS current
			DESCRIPTION
				"Description."
			::= { fkColorMarkingControl 5 }

		
		-- 1.3.6.1.4.1.10428 9 1.101.10.7.2.6
		fkColorMarkingControlIndex OBJECT-TYPE
			SYNTAX Integer32 (1..2048)
			UNITS "index"
			MAX-ACCESS read-write
			STATUS current
			DESCRIPTION
				"Color marking table index"
			DEFVAL { 1 }
			::= { fkColorMarkingControl 6 }

		
		-- 1.3.6.1.4.1.10428 9 1.101.10.7.2.7
		fkColorMarkingControlType OBJECT-TYPE
			SYNTAX INTEGER
				{
				srTCM(0),
				trTCM(1)
				}
			UNITS "enum"
			MAX-ACCESS read-write
			STATUS current
			DESCRIPTION
				"Color marking type.
				srTCM = Single Rate Three Color Marking.
				trTCM = Two Rate Three Color Marking.
				"
			DEFVAL { 0 }
			::= { fkColorMarkingControl 7 }

		
		-- 1.3.6.1.4.1.10428 9 1.101.10.7.2.8
		fkColorMarkingControlMode OBJECT-TYPE
			SYNTAX INTEGER
				{
				blind(0),
				aware(1)
				}
			UNITS "enum"
			MAX-ACCESS read-write
			STATUS current
			DESCRIPTION
				"Color marking mode"
			DEFVAL { 0 }
			::= { fkColorMarkingControl 8 }

		
		-- 1.3.6.1.4.1.10428 9 1.101.10.7.2.9
		fkColorMarkingControlAwareMode OBJECT-TYPE
			SYNTAX INTEGER
				{
				unprotected(1),
				protected(2)
				}
			UNITS "enum"
			MAX-ACCESS read-write
			STATUS current
			DESCRIPTION
				"Color marking aware mode.
				Used only when fkColorMarkingControlMode is aware."
			DEFVAL { 1 }
			::= { fkColorMarkingControl 9 }

		
		-- 1.3.6.1.4.1.10428 9 1.101.10.7.2.10
		fkColorMarkingControlCIR OBJECT-TYPE
			SYNTAX Integer32 (1..1000000)
			UNITS "Integer"
			MAX-ACCESS read-write
			STATUS current
			DESCRIPTION
				"Committed Information Rate.
				The value is in unit for 64 kbps
				"
			DEFVAL { 0 }
			::= { fkColorMarkingControl 10 }

		
		-- 1.3.6.1.4.1.10428 9 1.101.10.7.2.11
		fkColorMarkingControlCBS OBJECT-TYPE
			SYNTAX Integer32 (1..4000)
			UNITS "Integer "
			MAX-ACCESS read-write
			STATUS current
			DESCRIPTION
				"Committed Burst Size.
				The value is in unit for square of 2 bits.
				"
			DEFVAL { 0 }
			::= { fkColorMarkingControl 11 }

		
		-- 1.3.6.1.4.1.10428 9 1.101.10.7.2.12
		fkColorMarkingControlPIR OBJECT-TYPE
			SYNTAX Integer32 (1..1000000)
			UNITS "Integer "
			MAX-ACCESS read-write
			STATUS current
			DESCRIPTION
				"Peak Information Rate. 
				*) Used only when fkColorMarkingMode is Aware.
				The value is in unit for 64 kbps.
				"
			DEFVAL { 0 }
			::= { fkColorMarkingControl 12 }

		
		-- 1.3.6.1.4.1.10428 9 1.101.10.7.2.13
		fkColorMarkingControlPBS OBJECT-TYPE
			SYNTAX Integer32 (1..4000)
			UNITS "Integer "
			MAX-ACCESS read-write
			STATUS current
			DESCRIPTION
				"Peak Burst Size. 
				*) Used only when fkColorMarkingMode is Aware.
				The value is in unit for square of 2 bits.
				"
			DEFVAL { 0 }
			::= { fkColorMarkingControl 13 }

		
		-- 1.3.6.1.4.1.10428 9 1.101.10.7.2.14
		fkColorMarkingControlEBS OBJECT-TYPE
			SYNTAX Integer32 (1..4000)
			UNITS "Integer "
			MAX-ACCESS read-write
			STATUS current
			DESCRIPTION
				"Excess Burst Size. 
				*) Used only when fkColorMarkingMode is Blind.
				The value is in unit for square of 2 bits.
				"
			DEFVAL { 0 }
			::= { fkColorMarkingControl 14 }

		
		-- 1.3.6.1.4.1.10428 9 1.101.10.7.2.15
		fkColorMarkingControlRedAction OBJECT-TYPE
			SYNTAX BITS
				{
				reserve0(0),
				reserve1(1),
				reserve2(2),
				reserve3(3),
				reserve4(4),
				dropProcedence(5),
				marking(6),
				drop(7),
				dropPrecedenceGreen(8),
				dropPrecedenceYellow(9),
				dropPrecedenceRed(10)
				}
			UNITS "bits"
			MAX-ACCESS read-write
			STATUS current
			DESCRIPTION
				"The action to be apply when incoming packet is colored in red."
			DEFVAL { { 0 } }
			::= { fkColorMarkingControl 15 }

		
		-- 1.3.6.1.4.1.10428 9 1.101.10.7.2.16
		fkColorMarkingControlYellowAction OBJECT-TYPE
			SYNTAX BITS
				{
				reserve0(0),
				reserve1(1),
				reserve2(2),
				reserve3(3),
				reserve4(4),
				dropProcedence(5),
				marking(6),
				drop(7),
				dropPrecedenceGreen(8),
				dropPrecedenceYellow(9),
				dropPrecedenceRed(10)
				}
			UNITS "bits"
			MAX-ACCESS read-write
			STATUS current
			DESCRIPTION
				"The action to be apply when incoming packet is colored in yellow."
			DEFVAL { { 0 } }
			::= { fkColorMarkingControl 16 }

		
		-- 1.3.6.1.4.1.10428 9 1.101.10.7.2.17
		fkColorMarkingControlGreenAction OBJECT-TYPE
			SYNTAX BITS
				{
				reserve0(0),
				reserve1(1),
				reserve2(2),
				reserve3(3),
				reserve4(4),
				dropProcedence(5),
				marking(6),
				drop(7),
				dropPrecedenceGreen(8),
				dropPrecedenceYellow(9),
				dropPrecedenceRed(10)
				}
			UNITS "bits"
			MAX-ACCESS read-write
			STATUS current
			DESCRIPTION
				"The action to be apply when incoming packet is colored in green. (not supported)"
			DEFVAL { { 6 } }
			::= { fkColorMarkingControl 17 }

		
		-- 1.3.6.1.4.1.10428 9 1.101.10.7.2.18
		fkColorMarkingControlRedDscp OBJECT-TYPE
			SYNTAX Integer32 (0..63)
			UNITS "Integer"
			MAX-ACCESS read-write
			STATUS current
			DESCRIPTION
				"The dscp value to be apply when incoming packet is colored in red."
			DEFVAL { 30 }
			::= { fkColorMarkingControl 18 }

		
		-- 1.3.6.1.4.1.10428 9 1.101.10.7.2.19
		fkColorMarkingControlYellowDscp OBJECT-TYPE
			SYNTAX Integer32 (0..63)
			UNITS "Integer "
			MAX-ACCESS read-write
			STATUS current
			DESCRIPTION
				"The dscp value to be apply when incoming packet is colored in yellow."
			DEFVAL { 28 }
			::= { fkColorMarkingControl 19 }

		
		-- 1.3.6.1.4.1.10428 9 1.101.10.7.2.20
		fkColorMarkingControlGreenDscp OBJECT-TYPE
			SYNTAX Integer32 (0..63)
			UNITS "Integer "
			MAX-ACCESS read-write
			STATUS current
			DESCRIPTION
				"The dscp value to be apply when incoming packet is colored in green. (not supported)"
			DEFVAL { 26 }
			::= { fkColorMarkingControl 20 }

		
		-- 1.3.6.1.4.1.10428 9 1.101.10.7.3
		fkColorMarkingNotification OBJECT IDENTIFIER ::= { fkColorMarking 3 }

		
		-- 1.3.6.1.4.1.10428 9 1.101.10.7.3.1
		fkColorMarkingProfileChanged NOTIFICATION-TYPE
			OBJECTS { fkColorMarkingControlRequest, fkColorMarkingControlReqResult, fkColorMarkingControlTimeStamp, fkColorMarkingType, fkColorMarkingMode, 
				fkColorMarkingAwareMode, fkColorMarkingCIR, fkColorMarkingCBS, fkColorMarkingPIR, fkColorMarkingPBS, 
				fkColorMarkingEBS, fkColorMarkingRedAction, fkColorMarkingYellowAction, fkColorMarkingGreenAction, fkColorMarkingRedDscp, 
				fkColorMarkingYellowDscp, fkColorMarkingGreenDscp }
			STATUS current
			DESCRIPTION 
				"Description."
			::= { fkColorMarkingNotification 1 }

		
		-- 1.3.6.1.4.1.10428 9 1.101.10.8
		fkQoSGroup OBJECT-GROUP
			OBJECTS { fkQosUserFlowNum, fkQosTrafficProfileNum, fkQosCounterNum, fkQosQueueNum, fkTrafficProfileIndex, 
				fkTrafficProfileMinBandwidth, fkTrafficProfileMaxBandwidth, fkTrafficProfileMaxBurstSize, fkTrafficProfileUseCount, fkUserFlowName, 
				fkUserFlowIngressPorts, fkUserFlowEgressPorts, fkUserFlowEthernetType, fkUserFlowSrcMacAddr, fkUserFlowDstMacAddr, 
				fkUserFlowVlan, fkUserFlow8021p, fkUserFlowSrcIpAddr, fkUserFlowSrcPrefixLength, fkUserFlowDstIpAddr, 
				fkUserFlowDstPrefixLength, fkUserFlowIpPktPriorityType, fkUserFlowIpPktPriority, fkUserFlowProtocolType, fkUserFlowTcpFlag, 
				fkUserFlowSrcL4Port, fkUserFlowDstL4Port, fkUserFlowPktLen, fkUserFlowValidFlags, fkUserFlowMatchFlags, 
				fkUserFlowPriority, fkUserFlowMatchCounterId, fkUserFlowMatchTrafficProfileId, fkUserFlowMatchQueue, fkUserFlowMatchIpPktPriorityType, 
				fkUserFlowMatchIpPktPriority, fkUserFlowMatchRedirPort, fkUserFlowMatchVid, fkUserFlowMatchDstMac, fkUserFlowMatchPortMap, 
				fkUserFlowMatchEgressType, fkUserFlowMatchAction, fkUserFlowNomatchCounterId, fkUserFlowNomatchTrafficProfileId, fkUserFlowNomatchQueue, 
				fkUserFlowNomatchIpPktPriorityType, fkUserFlowNomatchIpPktPriority, fkUserFlowNomatchRedirPort, fkUserFlowNomatchVid, fkUserFlowNomatchAction, 
				fkUserFlowMatchColorMarkingId, fkUserFlowNomatchColorMarkingId, fkPortSchedulInterfaceIndex, fkPortScheduleMode, fkQueueId, 
				fkQueueREDEnable, fkQueueMappedCoS, fkQueueWREDMinThreshold, fkQueueWREDMaxThreshold, fkQueueWREDProbMax, 
				fkQueueMinBandwidth, fkQueueMaxBandwidth, fkQueueWeight, fkQueueMaxLatency, fkQueueMaxPackets, 
				fkCounterIndex, fkCounterPackets, fkColorMarkingIndex, fkColorMarkingType, fkColorMarkingMode, 
				fkColorMarkingAwareMode, fkColorMarkingCIR, fkColorMarkingCBS, fkColorMarkingPIR, fkColorMarkingPBS, 
				fkColorMarkingEBS, fkColorMarkingRedAction, fkColorMarkingYellowAction, fkColorMarkingGreenAction, fkColorMarkingRedDscp, 
				fkColorMarkingYellowDscp, fkColorMarkingGreenDscp, fkQosRuleMode, fkQoSBaseControlRequest, fkQoSBaseControlStatus, 
				fkQoSBaseControlTimer, fkQoSBaseControlTimeStamp, fkQoSBaseControlReqResult, fkQoSBaseControlRuleMode, fkTrafficProfileControlRequest, 
				fkTrafficProfileControlStatus, fkTrafficProfileControlTimer, fkTrafficProfileControlTimeStamp, fkTrafficProfileControlReqResult, fkTrafficProfileControlIndex, 
				fkTrafficProfileControlMinBandwidth, fkTrafficProfileControlMaxBandwidth, fkTrafficProfileControlMaxBurstSize, fkUserFlowMatchRoutePrimary, fkUserFlowMatchRouteSecondary, 
				fkUserFlowControlRequest, fkUserFlowControlStatus, fkUserFlowControlTimer, fkUserFlowControlTimeStamp, fkUserFlowControlReqResult, 
				fkUserFlowControlName, fkUserFlowControlIngressPorts, fkUserFlowControlEgressPorts, fkUserFlowControlEthernetType, fkUserFlowControlSrcMacAddr, 
				fkUserFlowControlDstMacAddr, fkUserFlowControlVlan, fkUserFlowControl8021p, fkUserFlowControlSrcIpAddr, fkUserFlowControlSrcPrefixLength, 
				fkUserFlowControlDstIpAddr, fkUserFlowControlDstPrefixLength, fkUserFlowControlIpPktPriorityType, fkUserFlowControlIpPktPriority, fkUserFlowControlProtocolType, 
				fkUserFlowControlTcpFlag, fkUserFlowControlSrcL4Port, fkUserFlowControlDstL4Port, fkUserFlowControlPktLen, fkUserFlowControlValidFlag, 
				fkUserFlowControlMatchFlag, fkUserFlowControlPriority, fkUserFlowControlMatchCounterId, fkUserFlowControlMatchTrafficProfileId, fkUserFlowControlMatchQueue, 
				fkUserFlowControlMatchIpPktPriorityType, fkUserFlowControlMatchIpPktPriority, fkUserFlowControlMatchRedirPort, fkUserFlowControlMatchVid, fkUserFlowControlMatchDstMac, 
				fkUserFlowControlMatchPortMap, fkUserFlowControlMatchEgressType, fkUserFlowControlMatchAction, fkUserFlowControlNomatchCounterId, fkUserFlowControlNomatchTrafficProfileId, 
				fkUserFlowControlNomatchQueue, fkUserFlowControlNomatchIpPktPriorityType, fkUserFlowControlNomatchIpPktPriority, fkUserFlowControlNomatchRedirPort, fkUserFlowControlNomatchVid, 
				fkUserFlowControlNomatchAction, fkUserFlowControlMatchColorMarkingId, fkUserFlowControlNomatchColorMarkingId, fkUserFlowControlInnerVlan, fkUserFlowControlInner8021p, 
				fkUserFlowControlMatchRoutePrimary, fkUserFlowControlMatchRouteSecondary, fkPortScheduleControlRequest, fkScheduleControlStatus, fkPortScheduleControlTimer, 
				fkPortScheduleControlTimeStamp, fkPortScheduleControlReqResult, fkPortScheduleControlInterfaceIndex, fkPortScheduleControlMode, fkQueueQuantum, 
				fkQueueControlRequest, fkQueueControlStatus, fkQueueControlTimer, fkQueueControlTimeStamp, fkQueueControlReqResult, 
				fkQueueControlInterfaceIndex, fkQueueControlId, fkQueueControlREDEnable, fkQueueControlMappedCoS, fkQueueControlWREDMinThreshold, 
				fkQueueControlWREDMaxThreshold, fkQueueControlWREDProbMax, fkQueueControlMinBandwidth, fkQueueControlMaxBandwidth, fkQueueControlWeight, 
				fkQueueControlMaxLatency, fkQueueControlMaxPackets, fkQueueControlQuantum, fkCounterControlRequest, fkCounterControlStatus, 
				fkCounterControlTimer, fkCounterControlTimeStamp, fkCounterControlReqResult, fkCounterControlIndex, fkColorMarkingControlRequest, 
				fkColorMarkingControlStatus, fkColorMarkingControlTimer, fkColorMarkingControlTimeStamp, fkColorMarkingControlReqResult, fkColorMarkingControlIndex, 
				fkColorMarkingControlType, fkColorMarkingControlMode, fkColorMarkingControlAwareMode, fkColorMarkingControlCIR, fkColorMarkingControlCBS, 
				fkColorMarkingControlPIR, fkColorMarkingControlPBS, fkColorMarkingControlEBS, fkColorMarkingControlRedAction, fkColorMarkingControlYellowAction, 
				fkColorMarkingControlGreenAction, fkColorMarkingControlRedDscp, fkColorMarkingControlYellowDscp, fkColorMarkingControlGreenDscp, fkQueueUsedPkts, 
				fkQueueUsedBytes, fkColorMarkingUseCount, fkQosColorMarkingProfileNum, fkUserFlowInnerVlan, fkUserFlowInner8021p
				 }
			STATUS current
			DESCRIPTION 
				"Description."
			::= { fkQoS 8 }

		
		-- 1.3.6.1.4.1.10428 9 1.101.10.9
		fkQoSControlGroup OBJECT-GROUP
			OBJECTS { fkTrafficProfileControlRequest, fkTrafficProfileControlStatus, fkTrafficProfileControlTimer, fkTrafficProfileControlTimeStamp, fkTrafficProfileControlReqResult, 
				fkTrafficProfileControlIndex, fkTrafficProfileControlMinBandwidth, fkTrafficProfileControlMaxBandwidth, fkTrafficProfileControlMaxBurstSize, fkUserFlowControlRequest, 
				fkUserFlowControlStatus, fkUserFlowControlTimer, fkUserFlowControlTimeStamp, fkUserFlowControlReqResult, fkUserFlowControlName, 
				fkUserFlowControlIngressPorts, fkUserFlowControlEgressPorts, fkUserFlowControlEthernetType, fkUserFlowControlSrcMacAddr, fkUserFlowControlDstMacAddr, 
				fkUserFlowControlVlan, fkUserFlowControl8021p, fkUserFlowControlSrcIpAddr, fkUserFlowControlSrcPrefixLength, fkUserFlowControlDstIpAddr, 
				fkUserFlowControlDstPrefixLength, fkUserFlowControlIpPktPriorityType, fkUserFlowControlIpPktPriority, fkUserFlowControlProtocolType, fkUserFlowControlTcpFlag, 
				fkUserFlowControlSrcL4Port, fkUserFlowControlDstL4Port, fkUserFlowControlPktLen, fkUserFlowControlValidFlag, fkUserFlowControlMatchFlag, 
				fkUserFlowControlPriority, fkUserFlowControlMatchCounterId, fkUserFlowControlMatchTrafficProfileId, fkUserFlowControlMatchQueue, fkUserFlowControlMatchIpPktPriorityType, 
				fkUserFlowControlMatchIpPktPriority, fkUserFlowControlMatchRedirPort, fkUserFlowControlMatchVid, fkUserFlowControlMatchDstMac, fkUserFlowControlMatchPortMap, 
				fkUserFlowControlMatchEgressType, fkUserFlowControlMatchAction, fkUserFlowControlNomatchCounterId, fkUserFlowControlNomatchTrafficProfileId, fkUserFlowControlNomatchQueue, 
				fkUserFlowControlNomatchIpPktPriorityType, fkUserFlowControlNomatchIpPktPriority, fkUserFlowControlNomatchRedirPort, fkUserFlowControlNomatchVid, fkUserFlowControlNomatchAction, 
				fkUserFlowControlMatchColorMarkingId, fkUserFlowControlNomatchColorMarkingId, fkQueueControlRequest, fkQueueControlStatus, fkQueueControlTimer, 
				fkQueueControlTimeStamp, fkQueueControlReqResult, fkQueueControlInterfaceIndex, fkQueueControlId, fkQueueControlREDEnable, 
				fkQueueControlMappedCoS, fkQueueControlWREDMinThreshold, fkQueueControlWREDMaxThreshold, fkQueueControlWREDProbMax, fkQueueControlMinBandwidth, 
				fkQueueControlMaxBandwidth, fkQueueControlWeight, fkQueueControlMaxLatency, fkUserFlowControlInnerVlan, fkUserFlowControlInner8021p, 
				fkQosUserFlowNum, fkQosTrafficProfileNum, fkQosCounterNum, fkQosQueueNum, fkQosColorMarkingProfileNum, 
				fkQosRuleMode, fkQoSBaseControlRequest, fkQoSBaseControlStatus, fkQoSBaseControlTimer, fkQoSBaseControlTimeStamp, 
				fkQoSBaseControlReqResult, fkQoSBaseControlRuleMode, fkTrafficProfileIndex, fkTrafficProfileMinBandwidth, fkTrafficProfileMaxBandwidth, 
				fkTrafficProfileMaxBurstSize, fkTrafficProfileUseCount, fkUserFlowName, fkUserFlowIngressPorts, fkUserFlowEgressPorts, 
				fkUserFlowEthernetType, fkUserFlowSrcMacAddr, fkUserFlowDstMacAddr, fkUserFlowVlan, fkUserFlow8021p, 
				fkUserFlowSrcIpAddr, fkUserFlowSrcPrefixLength, fkUserFlowDstIpAddr, fkUserFlowDstPrefixLength, fkUserFlowIpPktPriorityType, 
				fkUserFlowIpPktPriority, fkUserFlowProtocolType, fkUserFlowTcpFlag, fkUserFlowSrcL4Port, fkUserFlowDstL4Port, 
				fkUserFlowPktLen, fkUserFlowValidFlags, fkUserFlowMatchFlags, fkUserFlowPriority, fkUserFlowMatchCounterId, 
				fkUserFlowMatchTrafficProfileId, fkUserFlowMatchQueue, fkUserFlowMatchIpPktPriorityType, fkUserFlowMatchIpPktPriority, fkUserFlowMatchRedirPort, 
				fkUserFlowMatchVid, fkUserFlowMatchDstMac, fkUserFlowMatchPortMap, fkUserFlowMatchEgressType, fkUserFlowMatchAction, 
				fkUserFlowNomatchCounterId, fkUserFlowNomatchTrafficProfileId, fkUserFlowNomatchQueue, fkUserFlowNomatchIpPktPriorityType, fkUserFlowNomatchIpPktPriority, 
				fkUserFlowNomatchRedirPort, fkUserFlowNomatchVid, fkUserFlowNomatchAction, fkUserFlowMatchColorMarkingId, fkUserFlowNomatchColorMarkingId, 
				fkUserFlowInnerVlan, fkUserFlowInner8021p, fkUserFlowMatchRoutePrimary, fkUserFlowMatchRouteSecondary, fkUserFlowControlMatchRoutePrimary, 
				fkUserFlowControlMatchRouteSecondary, fkPortSchedulInterfaceIndex, fkPortScheduleMode, fkQueueId, fkQueueREDEnable, 
				fkQueueMappedCoS, fkQueueWREDMinThreshold, fkQueueWREDMaxThreshold, fkQueueWREDProbMax, fkQueueMinBandwidth, 
				fkQueueMaxBandwidth, fkQueueWeight, fkQueueMaxLatency, fkQueueMaxPackets, fkQueueQuantum, 
				fkQueueControlQuantum, fkCounterIndex, fkCounterPackets, fkColorMarkingIndex, fkColorMarkingType, 
				fkColorMarkingMode, fkColorMarkingAwareMode, fkColorMarkingCIR, fkColorMarkingCBS, fkColorMarkingPIR, 
				fkColorMarkingPBS, fkColorMarkingEBS, fkColorMarkingRedAction, fkColorMarkingYellowAction, fkColorMarkingGreenAction, 
				fkColorMarkingRedDscp, fkColorMarkingYellowDscp, fkColorMarkingGreenDscp, fkColorMarkingUseCount, fkQueueControlMaxPackets, 
				fkPortScheduleControlRequest, fkScheduleControlStatus, fkPortScheduleControlTimer, fkPortScheduleControlTimeStamp, fkPortScheduleControlReqResult, 
				fkPortScheduleControlInterfaceIndex, fkPortScheduleControlMode, fkCounterControlRequest, fkCounterControlStatus, fkCounterControlTimer, 
				fkCounterControlTimeStamp, fkCounterControlReqResult, fkCounterControlIndex, fkColorMarkingControlRequest, fkColorMarkingControlStatus, 
				fkColorMarkingControlTimer, fkColorMarkingControlTimeStamp, fkColorMarkingControlReqResult, fkColorMarkingControlIndex, fkColorMarkingControlType, 
				fkColorMarkingControlMode, fkColorMarkingControlAwareMode, fkColorMarkingControlCIR, fkColorMarkingControlCBS, fkColorMarkingControlPIR, 
				fkColorMarkingControlPBS, fkColorMarkingControlEBS, fkColorMarkingControlRedAction, fkColorMarkingControlYellowAction, fkColorMarkingControlGreenAction, 
				fkColorMarkingControlRedDscp, fkColorMarkingControlYellowDscp, fkColorMarkingControlGreenDscp }
			STATUS current
			DESCRIPTION 
				"Description."
			::= { fkQoS 9 }

		
		-- 1.3.6.1.4.1.10428 9 1.101.10.11
		fkQoSNotificationGroup NOTIFICATION-GROUP
			NOTIFICATIONS { fkTrafficProfileChanged, fkUserFlowCreated, fkUserFlowDestroyed, fkUserFlowClassifierProfileChanged, fkUserFlowMatchActionProfileChanged, 
				fkUserFlowNomatchActionProfileChanged, fkPortScheduleModeChanged, fkQueueProfileChanged, fkCounterCleared, fkColorMarkingProfileChanged, 
				fkQoSBaseRuleModeChanged, fkQueueQuantumChanged }
			STATUS current
			DESCRIPTION 
				"Description."
			::= { fkQoS 11 }

		
	
	END

--
-- fk-qos-mib.mib
--
