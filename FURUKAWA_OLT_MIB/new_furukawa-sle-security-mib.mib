--
-- fk-security-mib.mib
-- MIB generated by MG-SOFT Visual MIB Builder Version 6.0  Build 88
-- Thursday, March 21, 2013 at 10:35:16
--

	FK-SECURITY-MIB DEFINITIONS ::= BEGIN
 
		IMPORTS
			fkMgmt			
				FROM FKOLTG1040-SMI			
			InterfaceIndex			
				FROM IF-MIB			
			FkControlStatusType, FkControlRequestResultType			
				FROM FK-TC-MIB			
			OBJECT-GROUP, NOTIFICATION-GROUP			
				FROM SNMPv2-CONF			
			TimeTicks, IpAddress, Integer32, Unsigned32, Gauge32, 
			Counter32, OBJECT-TYPE, MODULE-IDENTITY, NOTIFICATION-TYPE			
				FROM SNMPv2-SMI			
			DateAndTime, TimeStamp, MacAddress			
				FROM SNMPv2-TC;
	
	
		-- 1.3.6.1.4.1.10428 9 1.101.7
		fkSecurity MODULE-IDENTITY 
			LAST-UPDATED "200412100929Z"		-- December 10, 2004 at 09:29 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 7 }

		
	
	
--
-- Node definitions
--
	
		-- 1.3.6.1.4.1.10428 9 1.101.7.1
		fkSecurityBase OBJECT IDENTIFIER ::= { fkSecurity 1 }

		
		-- 1.3.6.1.4.1.10428 9 1.101.7.1.1
		fkSecurityBaseInfo OBJECT IDENTIFIER ::= { fkSecurityBase 1 }

		
		-- 1.3.6.1.4.1.10428 9 1.101.7.1.1.1
		fkSecurityRadiusRetransmissions OBJECT-TYPE
			SYNTAX Integer32
			MAX-ACCESS read-only
			STATUS current
			DESCRIPTION
				"Description"
			::= { fkSecurityBaseInfo 1 }

		
		-- 1.3.6.1.4.1.10428 9 1.101.7.1.1.2
		fkSecurityRadiusTimeouts OBJECT-TYPE
			SYNTAX Integer32
			MAX-ACCESS read-only
			STATUS current
			DESCRIPTION
				"Description"
			::= { fkSecurityBaseInfo 2 }

		
		-- 1.3.6.1.4.1.10428 9 1.101.7.1.1.3
		fkSecurityRadiusInterfaceName OBJECT-TYPE
			SYNTAX OCTET STRING (SIZE (0..255))
			MAX-ACCESS read-only
			STATUS current
			DESCRIPTION
				"Description"
			::= { fkSecurityBaseInfo 3 }

		
		-- 1.3.6.1.4.1.10428 9 1.101.7.1.1.4
		fkSecurityRadiusInterfaceAddress OBJECT-TYPE
			SYNTAX IpAddress
			MAX-ACCESS read-only
			STATUS current
			DESCRIPTION
				"Description"
			::= { fkSecurityBaseInfo 4 }

		
		-- 1.3.6.1.4.1.10428 9 1.101.7.1.1.5
		fkSecurityTacacsInterfaceName OBJECT-TYPE
			SYNTAX OCTET STRING (SIZE (0..255))
			MAX-ACCESS read-only
			STATUS current
			DESCRIPTION
				"Description"
			::= { fkSecurityBaseInfo 5 }

		
		-- 1.3.6.1.4.1.10428 9 1.101.7.1.1.6
		fkSecurityTacacsInterfaceAddress OBJECT-TYPE
			SYNTAX IpAddress
			MAX-ACCESS read-only
			STATUS current
			DESCRIPTION
				"Description"
			::= { fkSecurityBaseInfo 6 }

		
		-- 1.3.6.1.4.1.10428 9 1.101.7.1.1.7
		fkSecurityTacacsPort OBJECT-TYPE
			SYNTAX Integer32 (0..65535)
			MAX-ACCESS read-only
			STATUS current
			DESCRIPTION
				"Description"
			::= { fkSecurityBaseInfo 7 }

		
		-- 1.3.6.1.4.1.10428 9 1.101.7.1.1.8
		fkSecurityTacacsAuthType OBJECT-TYPE
			SYNTAX INTEGER
				{
				ascii(0),
				pap(1),
				chap(2)
				}
			MAX-ACCESS read-only
			STATUS current
			DESCRIPTION
				"Description"
			DEFVAL { ascii }
			::= { fkSecurityBaseInfo 8 }

		
		-- 1.3.6.1.4.1.10428 9 1.101.7.1.1.9
		fkSecurityTacacsTimeouts OBJECT-TYPE
			SYNTAX Integer32
			MAX-ACCESS read-only
			STATUS current
			DESCRIPTION
				"Description"
			::= { fkSecurityBaseInfo 9 }

		
		-- 1.3.6.1.4.1.10428 9 1.101.7.1.1.10
		fkSecurityTacacsPriorityLevel OBJECT-TYPE
			SYNTAX INTEGER
				{
				max(0),
				min(1),
				root(2),
				user(3)
				}
			MAX-ACCESS read-only
			STATUS current
			DESCRIPTION
				"Description"
			DEFVAL { min }
			::= { fkSecurityBaseInfo 10 }

		
		-- 1.3.6.1.4.1.10428 9 1.101.7.1.1.11
		fkSecurityDot1xActivity OBJECT-TYPE
			SYNTAX INTEGER
				{
				disable(0),
				enable(1)
				}
			MAX-ACCESS read-only
			STATUS current
			DESCRIPTION
				"Description"
			::= { fkSecurityBaseInfo 11 }

		
		-- 1.3.6.1.4.1.10428 9 1.101.7.1.1.12
		fkSecurityLoginLimits OBJECT-TYPE
			SYNTAX Integer32
			MAX-ACCESS read-only
			STATUS current
			DESCRIPTION
				"The limit number of use login."
			::= { fkSecurityBaseInfo 12 }

		
		-- 1.3.6.1.4.1.10428 9 1.101.7.1.2
		fkSecurityBaseControl OBJECT IDENTIFIER ::= { fkSecurityBase 2 }

		
		-- 1.3.6.1.4.1.10428 9 1.101.7.1.2.1
		fkSecurityControlRequest OBJECT-TYPE
			SYNTAX INTEGER
				{
				setSecurityBaseRadiusProfile(1),
				setSecurityBaseTacacsProfile(2),
				setSecurityBaseDot1xActivity(3),
				setSecurityBaseLoginLimits(4)
				}
			MAX-ACCESS read-write
			STATUS current
			DESCRIPTION
				"Description"
			::= { fkSecurityBaseControl 1 }

		
		-- 1.3.6.1.4.1.10428 9 1.101.7.1.2.2
		fkSecurityControlStatus OBJECT-TYPE
			SYNTAX FkControlStatusType
			MAX-ACCESS read-only
			STATUS current
			DESCRIPTION
				"Description"
			::= { fkSecurityBaseControl 2 }

		
		-- 1.3.6.1.4.1.10428 9 1.101.7.1.2.3
		fkSecurityControlTimer OBJECT-TYPE
			SYNTAX Gauge32
			MAX-ACCESS read-write
			STATUS current
			DESCRIPTION
				"Description"
			::= { fkSecurityBaseControl 3 }

		
		-- 1.3.6.1.4.1.10428 9 1.101.7.1.2.4
		fkSecurityControlTimeStamp OBJECT-TYPE
			SYNTAX TimeStamp
			MAX-ACCESS read-only
			STATUS current
			DESCRIPTION
				"Description"
			::= { fkSecurityBaseControl 4 }

		
		-- 1.3.6.1.4.1.10428 9 1.101.7.1.2.5
		fkSecurityControlReqResult OBJECT-TYPE
			SYNTAX FkControlRequestResultType
			MAX-ACCESS read-only
			STATUS current
			DESCRIPTION
				"Description"
			::= { fkSecurityBaseControl 5 }

		
		-- 1.3.6.1.4.1.10428 9 1.101.7.1.2.6
		fkSecurityControlRadiusRetransmissions OBJECT-TYPE
			SYNTAX Integer32
			MAX-ACCESS read-write
			STATUS current
			DESCRIPTION
				"Description"
			::= { fkSecurityBaseControl 6 }

		
		-- 1.3.6.1.4.1.10428 9 1.101.7.1.2.7
		fkSecurityControlRadiusTimeouts OBJECT-TYPE
			SYNTAX Integer32
			MAX-ACCESS read-write
			STATUS current
			DESCRIPTION
				"Description"
			::= { fkSecurityBaseControl 7 }

		
		-- 1.3.6.1.4.1.10428 9 1.101.7.1.2.8
		fkSecurityControlRadiusInterfaceName OBJECT-TYPE
			SYNTAX OCTET STRING (SIZE (0..255))
			MAX-ACCESS read-write
			STATUS current
			DESCRIPTION
				"Description"
			::= { fkSecurityBaseControl 8 }

		
		-- 1.3.6.1.4.1.10428 9 1.101.7.1.2.9
		fkSecurityControlRadiusInterfaceAddress OBJECT-TYPE
			SYNTAX IpAddress
			MAX-ACCESS read-write
			STATUS current
			DESCRIPTION
				"Description"
			::= { fkSecurityBaseControl 9 }

		
		-- 1.3.6.1.4.1.10428 9 1.101.7.1.2.10
		fkSecurityControlTacacsInterfaceName OBJECT-TYPE
			SYNTAX OCTET STRING (SIZE (0..255))
			MAX-ACCESS read-write
			STATUS current
			DESCRIPTION
				"Description"
			::= { fkSecurityBaseControl 10 }

		
		-- 1.3.6.1.4.1.10428 9 1.101.7.1.2.11
		fkSecurityControlTacacsInterfaceAddress OBJECT-TYPE
			SYNTAX IpAddress
			MAX-ACCESS read-write
			STATUS current
			DESCRIPTION
				"Description"
			::= { fkSecurityBaseControl 11 }

		
		-- 1.3.6.1.4.1.10428 9 1.101.7.1.2.12
		fkSecurityControlTacacsPort OBJECT-TYPE
			SYNTAX Integer32 (0..65535)
			MAX-ACCESS read-write
			STATUS current
			DESCRIPTION
				"Description"
			::= { fkSecurityBaseControl 12 }

		
		-- 1.3.6.1.4.1.10428 9 1.101.7.1.2.13
		fkSecurityControlTacacsAuthType OBJECT-TYPE
			SYNTAX INTEGER
				{
				ascii(0),
				pap(1),
				chap(2)
				}
			MAX-ACCESS read-write
			STATUS current
			DESCRIPTION
				"Description"
			DEFVAL { ascii }
			::= { fkSecurityBaseControl 13 }

		
		-- 1.3.6.1.4.1.10428 9 1.101.7.1.2.14
		fkSecurityControlTacacsTimeouts OBJECT-TYPE
			SYNTAX Integer32
			MAX-ACCESS read-write
			STATUS current
			DESCRIPTION
				"Description"
			::= { fkSecurityBaseControl 14 }

		
		-- 1.3.6.1.4.1.10428 9 1.101.7.1.2.15
		fkSecurityControlTacacsPriorityLevel OBJECT-TYPE
			SYNTAX INTEGER
				{
				max(0),
				min(1),
				root(2),
				user(3)
				}
			MAX-ACCESS read-write
			STATUS current
			DESCRIPTION
				"Description"
			DEFVAL { min }
			::= { fkSecurityBaseControl 15 }

		
		-- 1.3.6.1.4.1.10428 9 1.101.7.1.2.16
		fkSecurityControlDot1xActivity OBJECT-TYPE
			SYNTAX INTEGER
				{
				disable(0),
				enable(1)
				}
			MAX-ACCESS read-write
			STATUS current
			DESCRIPTION
				"Description"
			::= { fkSecurityBaseControl 16 }

		
		-- 1.3.6.1.4.1.10428 9 1.101.7.1.2.17
		fkSecurityControlLoginLimits OBJECT-TYPE
			SYNTAX Integer32
			MAX-ACCESS read-write
			STATUS current
			DESCRIPTION
				"The limit number of use login."
			::= { fkSecurityBaseControl 17 }

		
		-- 1.3.6.1.4.1.10428 9 1.101.7.1.3
		fkSecurityBaseNotification OBJECT IDENTIFIER ::= { fkSecurityBase 3 }

		
		-- 1.3.6.1.4.1.10428 9 1.101.7.1.3.1
		fkSecurityRadiusProfileChanged NOTIFICATION-TYPE
			OBJECTS { fkSecurityRadiusRetransmissions, fkSecurityRadiusTimeouts, fkSecurityRadiusInterfaceName, fkSecurityRadiusInterfaceAddress, fkSecurityControlRequest, 
				fkSecurityControlTimeStamp, fkSecurityControlReqResult }
			STATUS current
			DESCRIPTION 
				"Description"
			::= { fkSecurityBaseNotification 1 }

		
		-- 1.3.6.1.4.1.10428 9 1.101.7.1.3.2
		fkSecurityTacacsProfileChanged NOTIFICATION-TYPE
			OBJECTS { fkSecurityTacacsInterfaceName, fkSecurityTacacsInterfaceAddress, fkSecurityTacacsPort, fkSecurityTacacsAuthType, fkSecurityTacacsTimeouts, 
				fkSecurityTacacsPriorityLevel, fkSecurityControlStatus, fkSecurityControlTimeStamp, fkSecurityControlReqResult }
			STATUS current
			DESCRIPTION 
				"Description"
			::= { fkSecurityBaseNotification 2 }

		
		-- 1.3.6.1.4.1.10428 9 1.101.7.1.3.3
		fkSecurityDot1xActivityChanged NOTIFICATION-TYPE
			OBJECTS { fkSecurityDot1xActivity, fkSecurityControlRequest, fkSecurityControlTimeStamp, fkSecurityControlReqResult }
			STATUS current
			DESCRIPTION 
				"Description"
			::= { fkSecurityBaseNotification 3 }

		
		-- 1.3.6.1.4.1.10428 9 1.101.7.1.3.4
		fkSecurityBaseLoginLimitsChanged NOTIFICATION-TYPE
			OBJECTS { fkSecurityControlRequest, fkSecurityControlTimeStamp, fkSecurityControlReqResult, fkSecurityControlLoginLimits }
			STATUS current
			DESCRIPTION 
				"Description."
			::= { fkSecurityBaseNotification 4 }

		
		-- 1.3.6.1.4.1.10428 9 1.101.7.2
		fkAAA OBJECT IDENTIFIER ::= { fkSecurity 2 }

		
		-- 1.3.6.1.4.1.10428 9 1.101.7.2.1
		fkAaaTable OBJECT-TYPE
			SYNTAX SEQUENCE OF FkAaaEntry
			MAX-ACCESS not-accessible
			STATUS current
			DESCRIPTION
				"Description."
			::= { fkAAA 1 }

		
		-- 1.3.6.1.4.1.10428 9 1.101.7.2.1.1
		fkAaaEntry OBJECT-TYPE
			SYNTAX FkAaaEntry
			MAX-ACCESS not-accessible
			STATUS current
			DESCRIPTION
				"Description."
			INDEX { fkAaaSession, fkAaaAuthen }
			::= { fkAaaTable 1 }

		
		FkAaaEntry ::=
			SEQUENCE { 
				fkAaaSession
					INTEGER,
				fkAaaAuthen
					INTEGER,
				fkAaaEnable
					INTEGER,
				fkAaaPrimarySequence
					INTEGER
			 }

		-- 1.3.6.1.4.1.10428 9 1.101.7.2.1.1.1
		fkAaaSession OBJECT-TYPE
			SYNTAX INTEGER
				{
				console(1),
				remote(2)
				}
			MAX-ACCESS read-only
			STATUS current
			DESCRIPTION
				"Location of authentication."
			::= { fkAaaEntry 1 }

		
		-- 1.3.6.1.4.1.10428 9 1.101.7.2.1.1.2
		fkAaaAuthen OBJECT-TYPE
			SYNTAX INTEGER
				{
				host(1),
				radius(2),
				tacacs(3)
				}
			MAX-ACCESS read-only
			STATUS current
			DESCRIPTION
				"The kind of authentication."
			::= { fkAaaEntry 2 }

		
		-- 1.3.6.1.4.1.10428 9 1.101.7.2.1.1.3
		fkAaaEnable OBJECT-TYPE
			SYNTAX INTEGER
				{
				disable(0),
				enable(1)
				}
			MAX-ACCESS read-only
			STATUS current
			DESCRIPTION
				"Enable or disable the corresponding authen method."
			::= { fkAaaEntry 3 }

		
		-- 1.3.6.1.4.1.10428 9 1.101.7.2.1.1.4
		fkAaaPrimarySequence OBJECT-TYPE
			SYNTAX INTEGER (1..3)
			MAX-ACCESS read-only
			STATUS current
			DESCRIPTION
				"The primary priority of the corresponding authen method"
			::= { fkAaaEntry 4 }

		
		-- 1.3.6.1.4.1.10428 9 1.101.7.2.2
		fkAaaControl OBJECT IDENTIFIER ::= { fkAAA 2 }

		
		-- 1.3.6.1.4.1.10428 9 1.101.7.2.2.1
		fkAaaControlRequest OBJECT-TYPE
			SYNTAX INTEGER { setAaaProfile(1) }
			MAX-ACCESS read-write
			STATUS current
			DESCRIPTION
				"Description"
			::= { fkAaaControl 1 }

		
		-- 1.3.6.1.4.1.10428 9 1.101.7.2.2.2
		fkAaaControlStatus OBJECT-TYPE
			SYNTAX FkControlStatusType
			MAX-ACCESS read-only
			STATUS current
			DESCRIPTION
				"Describes the status of a user command group, 
				used for block commands while a command execution in process."
			::= { fkAaaControl 2 }

		
		-- 1.3.6.1.4.1.10428 9 1.101.7.2.2.3
		fkAaaControlTimer OBJECT-TYPE
			SYNTAX Gauge32
			MAX-ACCESS read-write
			STATUS current
			DESCRIPTION
				"Maximum command duration time in case of long running."
			::= { fkAaaControl 3 }

		
		-- 1.3.6.1.4.1.10428 9 1.101.7.2.2.4
		fkAaaControlTimeStamp OBJECT-TYPE
			SYNTAX TimeStamp
			MAX-ACCESS read-only
			STATUS current
			DESCRIPTION
				"Time stamp attribute set at end of command."
			::= { fkAaaControl 4 }

		
		-- 1.3.6.1.4.1.10428 9 1.101.7.2.2.5
		fkAaaControlReqResult OBJECT-TYPE
			SYNTAX FkControlRequestResultType
			MAX-ACCESS read-only
			STATUS current
			DESCRIPTION
				"Command result attribute."
			::= { fkAaaControl 5 }

		
		-- 1.3.6.1.4.1.10428 9 1.101.7.2.2.6
		fkAaaControlSession OBJECT-TYPE
			SYNTAX INTEGER
				{
				console(1),
				remote(2)
				}
			MAX-ACCESS read-write
			STATUS current
			DESCRIPTION
				"Location of authentication."
			::= { fkAaaControl 6 }

		
		-- 1.3.6.1.4.1.10428 9 1.101.7.2.2.7
		fkAaaControlAuthen OBJECT-TYPE
			SYNTAX INTEGER
				{
				host(1),
				radius(2),
				tacacs(3)
				}
			MAX-ACCESS read-write
			STATUS current
			DESCRIPTION
				"The kind of authentication."
			::= { fkAaaControl 7 }

		
		-- 1.3.6.1.4.1.10428 9 1.101.7.2.2.8
		fkAaaControlEnable OBJECT-TYPE
			SYNTAX INTEGER
				{
				disable(0),
				enable(1)
				}
			MAX-ACCESS read-write
			STATUS current
			DESCRIPTION
				"Enable or disable the corresponding authen method."
			::= { fkAaaControl 8 }

		
		-- 1.3.6.1.4.1.10428 9 1.101.7.2.2.9
		fkAaaControlPrimaryFlag OBJECT-TYPE
			SYNTAX INTEGER
				{
				disable(0),
				enable(1)
				}
			MAX-ACCESS read-write
			STATUS current
			DESCRIPTION
				"The primary validation flag of the corresponding authen method"
			::= { fkAaaControl 9 }

		
		-- 1.3.6.1.4.1.10428 9 1.101.7.2.3
		fkAaaNotification OBJECT IDENTIFIER ::= { fkAAA 3 }

		
		-- 1.3.6.1.4.1.10428 9 1.101.7.2.3.1
		fkAaaProfileChanged NOTIFICATION-TYPE
			OBJECTS { fkAaaControlRequest, fkAaaControlTimeStamp, fkAaaControlReqResult, fkAaaEnable, fkAaaPrimarySequence
				 }
			STATUS current
			DESCRIPTION 
				"Description
				"
			::= { fkAaaNotification 1 }

		
		-- 1.3.6.1.4.1.10428 9 1.101.7.3
		fkRadiusServer OBJECT IDENTIFIER ::= { fkSecurity 3 }

		
		-- 1.3.6.1.4.1.10428 9 1.101.7.3.1
		fkRadiusServerTable OBJECT-TYPE
			SYNTAX SEQUENCE OF FkRadiusServerEntry
			MAX-ACCESS not-accessible
			STATUS current
			DESCRIPTION
				"Description."
			::= { fkRadiusServer 1 }

		
		-- 1.3.6.1.4.1.10428 9 1.101.7.3.1.1
		fkRadiusServerEntry OBJECT-TYPE
			SYNTAX FkRadiusServerEntry
			MAX-ACCESS not-accessible
			STATUS current
			DESCRIPTION
				"Description."
			INDEX { fkRadiusServerAddress }
			::= { fkRadiusServerTable 1 }

		
		FkRadiusServerEntry ::=
			SEQUENCE { 
				fkRadiusServerAddress
					IpAddress,
				fkRadiusServerClientKey
					OCTET STRING,
				fkRadiusServerAuthPort
					INTEGER,
				fkRadiusServerAccPort
					INTEGER,
				fkRadiusServerMode
					BITS
			 }

		-- 1.3.6.1.4.1.10428 9 1.101.7.3.1.1.1
		fkRadiusServerAddress OBJECT-TYPE
			SYNTAX IpAddress
			MAX-ACCESS read-only
			STATUS current
			DESCRIPTION
				"The IP address of the RADIUS server referred 
				to in this table entry."
			::= { fkRadiusServerEntry 1 }

		
		-- 1.3.6.1.4.1.10428 9 1.101.7.3.1.1.2
		fkRadiusServerClientKey OBJECT-TYPE
			SYNTAX OCTET STRING (SIZE (0..255))
			MAX-ACCESS read-only
			STATUS current
			DESCRIPTION
				"The key to be used in communication between the 
				device and the Radius server."
			::= { fkRadiusServerEntry 2 }

		
		-- 1.3.6.1.4.1.10428 9 1.101.7.3.1.1.3
		fkRadiusServerAuthPort OBJECT-TYPE
			SYNTAX INTEGER (0..65535)
			MAX-ACCESS read-only
			STATUS current
			DESCRIPTION
				"The UDP port the client is using to send requests to this server for authentication."
			::= { fkRadiusServerEntry 3 }

		
		-- 1.3.6.1.4.1.10428 9 1.101.7.3.1.1.4
		fkRadiusServerAccPort OBJECT-TYPE
			SYNTAX INTEGER (0..65535)
			MAX-ACCESS read-only
			STATUS current
			DESCRIPTION
				"The UDP port the client is using to send requests to this server for accounting."
			::= { fkRadiusServerEntry 4 }

		
		-- 1.3.6.1.4.1.10428 9 1.101.7.3.1.1.5
		fkRadiusServerMode OBJECT-TYPE
			SYNTAX BITS
				{
				aaa(0),
				dot1x(1)
				}
			MAX-ACCESS read-only
			STATUS current
			DESCRIPTION
				"Radius Server operation mode: if set bit 0, is used 
				in login, and if set bit 1, is used in 802.1X (dot1x)."
			::= { fkRadiusServerEntry 5 }

		
		-- 1.3.6.1.4.1.10428 9 1.101.7.3.2
		fkRadiusServerControl OBJECT IDENTIFIER ::= { fkRadiusServer 2 }

		
		-- 1.3.6.1.4.1.10428 9 1.101.7.3.2.1
		fkRadiusServerControlRequest OBJECT-TYPE
			SYNTAX INTEGER
				{
				createRadiusServer(1),
				destroyRadiusServer(2),
				setRadiusServerProfile(3)
				}
			MAX-ACCESS read-write
			STATUS current
			DESCRIPTION
				"The MIB object for the user command."
			::= { fkRadiusServerControl 1 }

		
		-- 1.3.6.1.4.1.10428 9 1.101.7.3.2.2
		fkRadiusServerControlStatus OBJECT-TYPE
			SYNTAX FkControlStatusType
			MAX-ACCESS read-only
			STATUS current
			DESCRIPTION
				"Describes the status of a user command group, 
				used for block commands while a command execution in process."
			::= { fkRadiusServerControl 2 }

		
		-- 1.3.6.1.4.1.10428 9 1.101.7.3.2.3
		fkRadiusServerControlTimer OBJECT-TYPE
			SYNTAX Gauge32
			MAX-ACCESS read-write
			STATUS current
			DESCRIPTION
				"Maximum command duration time in case of long running"
			::= { fkRadiusServerControl 3 }

		
		-- 1.3.6.1.4.1.10428 9 1.101.7.3.2.4
		fkRadiusServerControlTimeStamp OBJECT-TYPE
			SYNTAX TimeStamp
			MAX-ACCESS read-only
			STATUS current
			DESCRIPTION
				"Time stamp attribute set at end of command."
			::= { fkRadiusServerControl 4 }

		
		-- 1.3.6.1.4.1.10428 9 1.101.7.3.2.5
		fkRadiusServerControlReqResult OBJECT-TYPE
			SYNTAX FkControlRequestResultType
			MAX-ACCESS read-only
			STATUS current
			DESCRIPTION
				"Command result attribute."
			::= { fkRadiusServerControl 5 }

		
		-- 1.3.6.1.4.1.10428 9 1.101.7.3.2.6
		fkRadiusServerControlAddress OBJECT-TYPE
			SYNTAX IpAddress
			MAX-ACCESS read-write
			STATUS current
			DESCRIPTION
				"The IP address of the RADIUS server referred to 
				in this table entry."
			::= { fkRadiusServerControl 6 }

		
		-- 1.3.6.1.4.1.10428 9 1.101.7.3.2.7
		fkRadiusServerControlClientKey OBJECT-TYPE
			SYNTAX OCTET STRING (SIZE (0..255))
			MAX-ACCESS read-write
			STATUS current
			DESCRIPTION
				"The key to be used in communication between 
				the device and the Radius server."
			::= { fkRadiusServerControl 7 }

		
		-- 1.3.6.1.4.1.10428 9 1.101.7.3.2.8
		fkRadiusServerControlAuthPort OBJECT-TYPE
			SYNTAX Integer32 (0..65535)
			MAX-ACCESS read-write
			STATUS current
			DESCRIPTION
				"The service port  number for communication with server."
			::= { fkRadiusServerControl 8 }

		
		-- 1.3.6.1.4.1.10428 9 1.101.7.3.2.9
		fkRadiusServerControlAccPort OBJECT-TYPE
			SYNTAX Integer32 (0..65535)
			MAX-ACCESS read-write
			STATUS current
			DESCRIPTION
				"The service port  number for communication with server."
			::= { fkRadiusServerControl 9 }

		
		-- 1.3.6.1.4.1.10428 9 1.101.7.3.2.10
		fkRadiusServerControlMode OBJECT-TYPE
			SYNTAX BITS
				{
				aaa(0),
				dot1x(1)
				}
			MAX-ACCESS read-write
			STATUS current
			DESCRIPTION
				"Description."
			::= { fkRadiusServerControl 10 }
-- Radius Server operation mode: if set bit 0, is used 
-- in login, and if set bit 1, is used in 802.1X (dot1x).
		
		-- 1.3.6.1.4.1.10428 9 1.101.7.3.3
		fkRadiusServerNotification OBJECT IDENTIFIER ::= { fkRadiusServer 3 }

		
		-- 1.3.6.1.4.1.10428 9 1.101.7.3.3.1
		fkRadiusServerCreated NOTIFICATION-TYPE
			OBJECTS { fkRadiusServerControlRequest, fkRadiusServerControlTimeStamp, fkRadiusServerControlReqResult, fkRadiusServerClientKey, fkRadiusServerAccPort, 
				fkRadiusServerAuthPort, fkRadiusServerMode }
			STATUS current
			DESCRIPTION 
				"Description"
			::= { fkRadiusServerNotification 1 }

		
		-- 1.3.6.1.4.1.10428 9 1.101.7.3.3.2
		fkRadiusServerDestroyed NOTIFICATION-TYPE
			OBJECTS { fkRadiusServerControlRequest, fkRadiusServerControlTimeStamp, fkRadiusServerControlReqResult, fkRadiusServerControlAddress }
			STATUS current
			DESCRIPTION 
				"Description"
			::= { fkRadiusServerNotification 2 }

		
		-- 1.3.6.1.4.1.10428 9 1.101.7.3.3.3
		fkRadiusServerProfileChanged NOTIFICATION-TYPE
			OBJECTS { fkRadiusServerControlRequest, fkRadiusServerControlTimeStamp, fkRadiusServerControlReqResult, fkRadiusServerClientKey, fkRadiusServerAuthPort, 
				fkRadiusServerAccPort, fkRadiusServerMode }
			STATUS current
			DESCRIPTION 
				"Description"
			::= { fkRadiusServerNotification 3 }

		
		-- 1.3.6.1.4.1.10428 9 1.101.7.4
		fkTacacsServer OBJECT IDENTIFIER ::= { fkSecurity 4 }

		
		-- 1.3.6.1.4.1.10428 9 1.101.7.4.1
		fkTacacsServerTable OBJECT-TYPE
			SYNTAX SEQUENCE OF FkTacacsServerEntry
			MAX-ACCESS not-accessible
			STATUS current
			DESCRIPTION
				"Description."
			::= { fkTacacsServer 1 }

		
		-- 1.3.6.1.4.1.10428 9 1.101.7.4.1.1
		fkTacacsServerEntry OBJECT-TYPE
			SYNTAX FkTacacsServerEntry
			MAX-ACCESS not-accessible
			STATUS current
			DESCRIPTION
				"Description."
			INDEX { fkTacacsServerAddress }
			::= { fkTacacsServerTable 1 }

		
		FkTacacsServerEntry ::=
			SEQUENCE { 
				fkTacacsServerAddress
					IpAddress,
				fkTacacsServerClientKey
					OCTET STRING
			 }

		-- 1.3.6.1.4.1.10428 9 1.101.7.4.1.1.1
		fkTacacsServerAddress OBJECT-TYPE
			SYNTAX IpAddress
			MAX-ACCESS read-only
			STATUS current
			DESCRIPTION
				"The IP address of the TACACS accounting server 
				referred to in this table entry."
			::= { fkTacacsServerEntry 1 }

		
		-- 1.3.6.1.4.1.10428 9 1.101.7.4.1.1.2
		fkTacacsServerClientKey OBJECT-TYPE
			SYNTAX OCTET STRING (SIZE (0..255))
			MAX-ACCESS read-only
			STATUS current
			DESCRIPTION
				"The key to be used in communication between the 
				device and the Tacacs server."
			::= { fkTacacsServerEntry 2 }

		
		-- 1.3.6.1.4.1.10428 9 1.101.7.4.2
		fkTacacsServerControl OBJECT IDENTIFIER ::= { fkTacacsServer 2 }

		
		-- 1.3.6.1.4.1.10428 9 1.101.7.4.2.1
		fkTacacsServerControlRequest OBJECT-TYPE
			SYNTAX INTEGER
				{
				createTacacsServer(1),
				destroyTacacsServer(2),
				setTacacsServerClientKey(3)
				}
			MAX-ACCESS read-write
			STATUS current
			DESCRIPTION
				"The MIB object for the user command."
			::= { fkTacacsServerControl 1 }

		
		-- 1.3.6.1.4.1.10428 9 1.101.7.4.2.2
		fkTacacsServerControlStatus OBJECT-TYPE
			SYNTAX FkControlStatusType
			MAX-ACCESS read-only
			STATUS current
			DESCRIPTION
				"Describes the status of a user command group, used 
				for block commands while a command execution in process."
			::= { fkTacacsServerControl 2 }

		
		-- 1.3.6.1.4.1.10428 9 1.101.7.4.2.3
		fkTacacsServerControlTimer OBJECT-TYPE
			SYNTAX Gauge32
			MAX-ACCESS read-write
			STATUS current
			DESCRIPTION
				"Maximum command duration time in case of long running."
			::= { fkTacacsServerControl 3 }

		
		-- 1.3.6.1.4.1.10428 9 1.101.7.4.2.4
		fkTacacsServerControlTimeStamp OBJECT-TYPE
			SYNTAX TimeStamp
			MAX-ACCESS read-only
			STATUS current
			DESCRIPTION
				"Time stamp attribute set at end of command."
			::= { fkTacacsServerControl 4 }

		
		-- 1.3.6.1.4.1.10428 9 1.101.7.4.2.5
		fkTacacsServerControlReqResult OBJECT-TYPE
			SYNTAX FkControlRequestResultType
			MAX-ACCESS read-only
			STATUS current
			DESCRIPTION
				"Command result attribute."
			::= { fkTacacsServerControl 5 }

		
		-- 1.3.6.1.4.1.10428 9 1.101.7.4.2.6
		fkTacacsServerControlAddress OBJECT-TYPE
			SYNTAX IpAddress
			MAX-ACCESS read-write
			STATUS current
			DESCRIPTION
				"The IP address of the TACACS accounting server 
				referred to in this table entry."
			::= { fkTacacsServerControl 6 }

		
		-- 1.3.6.1.4.1.10428 9 1.101.7.4.2.7
		fkTacacsServerControlClientKey OBJECT-TYPE
			SYNTAX OCTET STRING (SIZE (0..255))
			MAX-ACCESS read-write
			STATUS current
			DESCRIPTION
				"The key to be used in communication between the 
				device and the Tacacs server."
			::= { fkTacacsServerControl 7 }

		
		-- 1.3.6.1.4.1.10428 9 1.101.7.4.3
		fkTacacsServerNotification OBJECT IDENTIFIER ::= { fkTacacsServer 3 }

		
		-- 1.3.6.1.4.1.10428 9 1.101.7.4.3.1
		fkTacacsServerCreated NOTIFICATION-TYPE
			OBJECTS { fkTacacsServerControlRequest, fkTacacsServerControlTimeStamp, fkTacacsServerControlReqResult, fkTacacsServerClientKey }
			STATUS current
			DESCRIPTION 
				"Description"
			::= { fkTacacsServerNotification 1 }

		
		-- 1.3.6.1.4.1.10428 9 1.101.7.4.3.2
		fkTacacsServerDestroyed NOTIFICATION-TYPE
			OBJECTS { fkTacacsServerControlRequest, fkTacacsServerControlTimeStamp, fkTacacsServerControlReqResult, fkTacacsServerControlAddress }
			STATUS current
			DESCRIPTION 
				"DescriptionDescription"
			::= { fkTacacsServerNotification 2 }

		
		-- 1.3.6.1.4.1.10428 9 1.101.7.4.3.3
		fkTacacsServerClientKeyChanged NOTIFICATION-TYPE
			OBJECTS { fkTacacsServerControlRequest, fkTacacsServerControlTimeStamp, fkTacacsServerControlReqResult, fkTacacsServerClientKey }
			STATUS current
			DESCRIPTION 
				"Description"
			::= { fkTacacsServerNotification 3 }

		
		-- 1.3.6.1.4.1.10428 9 1.101.7.5
		fkAcl OBJECT IDENTIFIER ::= { fkSecurity 5 }

		
		-- 1.3.6.1.4.1.10428 9 1.101.7.5.1
		fkAclTable OBJECT-TYPE
			SYNTAX SEQUENCE OF FkAclEntry
			MAX-ACCESS not-accessible
			STATUS current
			DESCRIPTION
				"Description"
			::= { fkAcl 1 }

		
		-- 1.3.6.1.4.1.10428 9 1.101.7.5.1.1
		fkAclEntry OBJECT-TYPE
			SYNTAX FkAclEntry
			MAX-ACCESS not-accessible
			STATUS current
			DESCRIPTION
				"Description."
			INDEX { fkAclName }
			::= { fkAclTable 1 }

		
		FkAclEntry ::=
			SEQUENCE { 
				fkAclName
					OCTET STRING,
				fkAclSrcIpAddr
					IpAddress,
				fkAclSrcPrefixLength
					Integer32,
				fkAclDstIpAddr
					IpAddress,
				fkAclDstPrefixLength
					Integer32,
				fkAclDscp
					Integer32,
				fkAclProtocolType
					Integer32,
				fkAclTcpFlag
					BITS,
				fkAclSrcL4Port
					Integer32,
				fkAclDstL4Port
					Integer32,
				fkAclPktLen
					Integer32,
				fkAclValidFlags
					BITS,
				fkAclMatchFlags
					BITS,
				fkAclMatchAction
					INTEGER,
				fkAclNomatchAction
					INTEGER,
				fkAclPriority
					INTEGER
			 }

		-- 1.3.6.1.4.1.10428 9 1.101.7.5.1.1.1
		fkAclName OBJECT-TYPE
			SYNTAX OCTET STRING (SIZE (0..63))
			MAX-ACCESS read-only
			STATUS current
			DESCRIPTION
				"Description"
			::= { fkAclEntry 1 }

		
		-- 1.3.6.1.4.1.10428 9 1.101.7.5.1.1.2
		fkAclSrcIpAddr OBJECT-TYPE
			SYNTAX IpAddress
			MAX-ACCESS read-only
			STATUS current
			DESCRIPTION
				"Description"
			::= { fkAclEntry 2 }

		
		-- 1.3.6.1.4.1.10428 9 1.101.7.5.1.1.3
		fkAclSrcPrefixLength OBJECT-TYPE
			SYNTAX Integer32 (0..31)
			MAX-ACCESS read-only
			STATUS current
			DESCRIPTION
				"Description"
			::= { fkAclEntry 3 }

		
		-- 1.3.6.1.4.1.10428 9 1.101.7.5.1.1.4
		fkAclDstIpAddr OBJECT-TYPE
			SYNTAX IpAddress
			MAX-ACCESS read-only
			STATUS current
			DESCRIPTION
				"Description"
			::= { fkAclEntry 4 }

		
		-- 1.3.6.1.4.1.10428 9 1.101.7.5.1.1.5
		fkAclDstPrefixLength OBJECT-TYPE
			SYNTAX Integer32 (0..31)
			MAX-ACCESS read-only
			STATUS current
			DESCRIPTION
				"Description"
			::= { fkAclEntry 5 }

		
		-- 1.3.6.1.4.1.10428 9 1.101.7.5.1.1.6
		fkAclDscp OBJECT-TYPE
			SYNTAX Integer32
			MAX-ACCESS read-only
			STATUS current
			DESCRIPTION
				"Description"
			DEFVAL { -1 }
			::= { fkAclEntry 6 }

		
		-- 1.3.6.1.4.1.10428 9 1.101.7.5.1.1.7
		fkAclProtocolType OBJECT-TYPE
			SYNTAX Integer32 (1..255)
			MAX-ACCESS read-only
			STATUS current
			DESCRIPTION
				"Description"
			::= { fkAclEntry 7 }

		
		-- 1.3.6.1.4.1.10428 9 1.101.7.5.1.1.8
		fkAclTcpFlag OBJECT-TYPE
			SYNTAX BITS
				{
				reserv(0),
				reserv1(1),
				urg(2),
				ack(3),
				psh(4),
				rst(5),
				syn(6),
				fin(7)
				}
			MAX-ACCESS read-only
			STATUS current
			DESCRIPTION
				"Description"
			::= { fkAclEntry 8 }

		
		-- 1.3.6.1.4.1.10428 9 1.101.7.5.1.1.9
		fkAclSrcL4Port OBJECT-TYPE
			SYNTAX Integer32 (1..65535)
			MAX-ACCESS read-only
			STATUS current
			DESCRIPTION
				"Description"
			::= { fkAclEntry 9 }

		
		-- 1.3.6.1.4.1.10428 9 1.101.7.5.1.1.10
		fkAclDstL4Port OBJECT-TYPE
			SYNTAX Integer32 (1..65535)
			MAX-ACCESS read-only
			STATUS current
			DESCRIPTION
				"Description"
			::= { fkAclEntry 10 }

		
		-- 1.3.6.1.4.1.10428 9 1.101.7.5.1.1.11
		fkAclPktLen OBJECT-TYPE
			SYNTAX Integer32 (21..65535)
			MAX-ACCESS read-only
			STATUS current
			DESCRIPTION
				"Description"
			::= { fkAclEntry 11 }

		
		-- 1.3.6.1.4.1.10428 9 1.101.7.5.1.1.12
		fkAclValidFlags OBJECT-TYPE
			SYNTAX BITS
				{
				aclSrcIpAddress(0),
				aclSrcPrefixLegth(1),
				aclDstIpAddress(2),
				aclDstPrefixLegth(3),
				aclDscp(4),
				aclProtocolType(5),
				aclTcpFlags(6),
				aclSrcL4Port(7),
				aclDstL4Port(8),
				aclPacketLength(9)
				}
			MAX-ACCESS read-only
			STATUS current
			DESCRIPTION
				"Description"
			::= { fkAclEntry 12 }

		
		-- 1.3.6.1.4.1.10428 9 1.101.7.5.1.1.13
		fkAclMatchFlags OBJECT-TYPE
			SYNTAX BITS
				{
				aclSrcIpAddress(0),
				aclSrcPrefixLegth(1),
				aclDstIpAddress(2),
				aclDstPrefixLength(3),
				aclDscp(4),
				aclProtocolType(5),
				aclTcpFlag(6),
				aclSrcL4Port(7),
				aclDstL4Port(8),
				aclPacketLength(9)
				}
			MAX-ACCESS read-only
			STATUS current
			DESCRIPTION
				"Description"
			::= { fkAclEntry 13 }

		
		-- 1.3.6.1.4.1.10428 9 1.101.7.5.1.1.14
		fkAclMatchAction OBJECT-TYPE
			SYNTAX INTEGER
				{
				permit(1),
				deny(2)
				}
			MAX-ACCESS read-only
			STATUS current
			DESCRIPTION
				"Description"
			::= { fkAclEntry 14 }

		
		-- 1.3.6.1.4.1.10428 9 1.101.7.5.1.1.15
		fkAclNomatchAction OBJECT-TYPE
			SYNTAX INTEGER
				{
				permit(1),
				deny(2)
				}
			MAX-ACCESS read-only
			STATUS current
			DESCRIPTION
				"DescriptionDescription"
			::= { fkAclEntry 15 }

		
		-- 1.3.6.1.4.1.10428 9 1.101.7.5.1.1.16
		fkAclPriority OBJECT-TYPE
			SYNTAX INTEGER
				{
				low(1),
				medium(2),
				high(3),
				highest(4)
				}
			MAX-ACCESS read-only
			STATUS current
			DESCRIPTION
				"Description"
			::= { fkAclEntry 16 }

		
		-- 1.3.6.1.4.1.10428 9 1.101.7.5.2
		fkAclControl OBJECT IDENTIFIER ::= { fkAcl 2 }

		
		-- 1.3.6.1.4.1.10428 9 1.101.7.5.2.1
		fkAclControlRequest OBJECT-TYPE
			SYNTAX INTEGER
				{
				createAclRule(1),
				destroyAclRule(2),
				setAclClassifierProfile(3),
				setAclMatchAction(10),
				setAclNomatchAction(11)
				}
			MAX-ACCESS read-write
			STATUS current
			DESCRIPTION
				"DescriptionDescription"
			::= { fkAclControl 1 }

		
		-- 1.3.6.1.4.1.10428 9 1.101.7.5.2.2
		fkAclControlStatus OBJECT-TYPE
			SYNTAX FkControlStatusType
			MAX-ACCESS read-only
			STATUS current
			DESCRIPTION
				"Description"
			::= { fkAclControl 2 }

		
		-- 1.3.6.1.4.1.10428 9 1.101.7.5.2.3
		fkAclControlTimer OBJECT-TYPE
			SYNTAX Gauge32
			MAX-ACCESS read-write
			STATUS current
			DESCRIPTION
				"Description"
			::= { fkAclControl 3 }

		
		-- 1.3.6.1.4.1.10428 9 1.101.7.5.2.4
		fkAclControlTimeStamp OBJECT-TYPE
			SYNTAX TimeStamp
			MAX-ACCESS read-only
			STATUS current
			DESCRIPTION
				"Description"
			::= { fkAclControl 4 }

		
		-- 1.3.6.1.4.1.10428 9 1.101.7.5.2.5
		fkAclControlReqResult OBJECT-TYPE
			SYNTAX FkControlRequestResultType
			MAX-ACCESS read-only
			STATUS current
			DESCRIPTION
				"Description"
			::= { fkAclControl 5 }

		
		-- 1.3.6.1.4.1.10428 9 1.101.7.5.2.6
		fkAclControlName OBJECT-TYPE
			SYNTAX OCTET STRING (SIZE (0..63))
			MAX-ACCESS read-write
			STATUS current
			DESCRIPTION
				"Description"
			::= { fkAclControl 6 }

		
		-- 1.3.6.1.4.1.10428 9 1.101.7.5.2.7
		fkAclControlSrcIpAddr OBJECT-TYPE
			SYNTAX IpAddress
			MAX-ACCESS read-write
			STATUS current
			DESCRIPTION
				"Description"
			::= { fkAclControl 7 }

		
		-- 1.3.6.1.4.1.10428 9 1.101.7.5.2.8
		fkAclControlSrcPrefixLength OBJECT-TYPE
			SYNTAX Integer32 (0..31)
			MAX-ACCESS read-write
			STATUS current
			DESCRIPTION
				"Description"
			::= { fkAclControl 8 }

		
		-- 1.3.6.1.4.1.10428 9 1.101.7.5.2.9
		fkAclControlDstIpAddr OBJECT-TYPE
			SYNTAX IpAddress
			MAX-ACCESS read-write
			STATUS current
			DESCRIPTION
				"DescriptionDescription"
			::= { fkAclControl 9 }

		
		-- 1.3.6.1.4.1.10428 9 1.101.7.5.2.10
		fkAclControlDstPrefixLength OBJECT-TYPE
			SYNTAX Integer32 (0..31)
			MAX-ACCESS read-write
			STATUS current
			DESCRIPTION
				"Description"
			::= { fkAclControl 10 }

		
		-- 1.3.6.1.4.1.10428 9 1.101.7.5.2.11
		fkAclControlDscp OBJECT-TYPE
			SYNTAX Integer32
			MAX-ACCESS read-write
			STATUS current
			DESCRIPTION
				"Description"
			DEFVAL { -1 }
			::= { fkAclControl 11 }

		
		-- 1.3.6.1.4.1.10428 9 1.101.7.5.2.12
		fkAclControlProtocolType OBJECT-TYPE
			SYNTAX Integer32 (1..255)
			MAX-ACCESS read-write
			STATUS current
			DESCRIPTION
				"Description"
			::= { fkAclControl 12 }

		
		-- 1.3.6.1.4.1.10428 9 1.101.7.5.2.13
		fkAclControlTcpFlag OBJECT-TYPE
			SYNTAX BITS
				{
				reserv(0),
				reserv1(1),
				urg(2),
				ack(3),
				psh(4),
				rst(5),
				syn(6),
				fin(7)
				}
			MAX-ACCESS read-write
			STATUS current
			DESCRIPTION
				"Description"
			::= { fkAclControl 13 }

		
		-- 1.3.6.1.4.1.10428 9 1.101.7.5.2.14
		fkAclControlSrcL4Port OBJECT-TYPE
			SYNTAX Integer32 (0..65535)
			MAX-ACCESS read-write
			STATUS current
			DESCRIPTION
				"Description"
			::= { fkAclControl 14 }

		
		-- 1.3.6.1.4.1.10428 9 1.101.7.5.2.15
		fkAclControlDstL4Port OBJECT-TYPE
			SYNTAX Integer32 (0..65535)
			MAX-ACCESS read-write
			STATUS current
			DESCRIPTION
				"Description"
			::= { fkAclControl 15 }

		
		-- 1.3.6.1.4.1.10428 9 1.101.7.5.2.16
		fkAclControlPktLen OBJECT-TYPE
			SYNTAX Integer32 (21..65535)
			MAX-ACCESS read-write
			STATUS current
			DESCRIPTION
				"Description"
			::= { fkAclControl 16 }

		
		-- 1.3.6.1.4.1.10428 9 1.101.7.5.2.17
		fkAclControlValidFlags OBJECT-TYPE
			SYNTAX BITS
				{
				aclSrcIpAddress(0),
				aclSrcPrefixLength(1),
				aclDstIpAddress(2),
				aclDstPrefixLength(3),
				aclDscp(4),
				aclProtocolType(5),
				aclTcpFlag(6),
				aclSrcL4Port(7),
				aclDstL4Port(8),
				aclPacketLength(9)
				}
			MAX-ACCESS read-write
			STATUS current
			DESCRIPTION
				"Description"
			::= { fkAclControl 17 }

		
		-- 1.3.6.1.4.1.10428 9 1.101.7.5.2.18
		fkAclControlMatchFlags OBJECT-TYPE
			SYNTAX BITS
				{
				aclSrcIpAddress(0),
				aclSrcPrefixLength(1),
				aclDstIpAddress(2),
				aclDstPrefixLength(3),
				aclDscp(4),
				aclProtocolType(5),
				aclTcpFlag(6),
				aclSrcL4Port(7),
				aclDstL4Port(8),
				aclPacketLength(9)
				}
			MAX-ACCESS read-write
			STATUS current
			DESCRIPTION
				"Description"
			::= { fkAclControl 18 }

		
		-- 1.3.6.1.4.1.10428 9 1.101.7.5.2.19
		fkAclControlMatchAction OBJECT-TYPE
			SYNTAX INTEGER
				{
				none(0),
				permit(1),
				deny(2)
				}
			MAX-ACCESS read-write
			STATUS current
			DESCRIPTION
				"Description"
			::= { fkAclControl 19 }

		
		-- 1.3.6.1.4.1.10428 9 1.101.7.5.2.20
		fkAclControlNomatchAction OBJECT-TYPE
			SYNTAX INTEGER
				{
				none(0),
				permit(1),
				deny(2)
				}
			MAX-ACCESS read-write
			STATUS current
			DESCRIPTION
				"Description"
			::= { fkAclControl 20 }

		
		-- 1.3.6.1.4.1.10428 9 1.101.7.5.2.21
		fkAclControlPriority OBJECT-TYPE
			SYNTAX INTEGER
				{
				low(1),
				medium(2),
				high(3),
				highest(4)
				}
			MAX-ACCESS read-write
			STATUS current
			DESCRIPTION
				"Description"
			::= { fkAclControl 21 }

		
		-- 1.3.6.1.4.1.10428 9 1.101.7.5.3
		fkAclNotification OBJECT IDENTIFIER ::= { fkAcl 3 }

		
		-- 1.3.6.1.4.1.10428 9 1.101.7.5.3.1
		fkAclCreated NOTIFICATION-TYPE
			OBJECTS { fkAclControlRequest, fkAclControlTimeStamp, fkAclControlReqResult, fkAclSrcIpAddr, fkAclSrcPrefixLength, 
				fkAclDstIpAddr, fkAclDstPrefixLength, fkAclDscp, fkAclProtocolType, fkAclTcpFlag, 
				fkAclSrcL4Port, fkAclDstL4Port, fkAclPktLen, fkAclValidFlags, fkAclMatchFlags, 
				fkAclMatchAction, fkAclNomatchAction, fkAclPriority }
			STATUS current
			DESCRIPTION 
				"Description"
			::= { fkAclNotification 1 }

		
		-- 1.3.6.1.4.1.10428 9 1.101.7.5.3.2
		fkAclDestroyed NOTIFICATION-TYPE
			OBJECTS { fkAclControlRequest, fkAclControlTimeStamp, fkAclControlReqResult, fkAclControlName }
			STATUS current
			DESCRIPTION 
				"Description"
			::= { fkAclNotification 2 }

		
		-- 1.3.6.1.4.1.10428 9 1.101.7.5.3.3
		fkAclClassifierProfileChanged NOTIFICATION-TYPE
			OBJECTS { fkAclControlRequest, fkAclControlTimeStamp, fkAclControlReqResult, fkAclSrcIpAddr, fkAclSrcPrefixLength, 
				fkAclDstIpAddr, fkAclDstPrefixLength, fkAclDscp, fkAclProtocolType, fkAclTcpFlag, 
				fkAclSrcL4Port, fkAclDstL4Port, fkAclPktLen, fkAclValidFlags, fkAclMatchFlags
				 }
			STATUS current
			DESCRIPTION 
				"Description"
			::= { fkAclNotification 3 }

		
		-- 1.3.6.1.4.1.10428 9 1.101.7.5.3.4
		fkAclMatchActionChanged NOTIFICATION-TYPE
			OBJECTS { fkAclControlRequest, fkAclControlTimeStamp, fkAclControlReqResult, fkAclMatchAction }
			STATUS current
			DESCRIPTION 
				"Description"
			::= { fkAclNotification 4 }

		
		-- 1.3.6.1.4.1.10428 9 1.101.7.5.3.5
		fkAclNomatchActionChanged NOTIFICATION-TYPE
			OBJECTS { fkAclControlRequest, fkAclControlTimeStamp, fkAclControlReqResult, fkAclNomatchAction }
			STATUS current
			DESCRIPTION 
				"Description"
			::= { fkAclNotification 5 }

		
		-- 1.3.6.1.4.1.10428 9 1.101.7.6
		fkDot1xPort OBJECT IDENTIFIER ::= { fkSecurity 6 }

		
		-- 1.3.6.1.4.1.10428 9 1.101.7.6.1
		fkDot1xPortTable OBJECT-TYPE
			SYNTAX SEQUENCE OF FkDot1xPortEntry
			MAX-ACCESS not-accessible
			STATUS current
			DESCRIPTION
				"The table that contains the configuration objects 
				for the Authenticator PAE associated with each port."
			::= { fkDot1xPort 1 }

		
		-- 1.3.6.1.4.1.10428 9 1.101.7.6.1.1
		fkDot1xPortEntry OBJECT-TYPE
			SYNTAX FkDot1xPortEntry
			MAX-ACCESS not-accessible
			STATUS current
			DESCRIPTION
				"The configuration information for an Authenticator PAE."
			INDEX { fkDot1xPortIndex }
			::= { fkDot1xPortTable 1 }

		
		FkDot1xPortEntry ::=
			SEQUENCE { 
				fkDot1xPortIndex
					InterfaceIndex,
				fkDot1xPortEnable
					INTEGER,
				fkDot1xPortMode
					INTEGER,
				fkDot1xPortReauthEnable
					INTEGER,
				fkDot1xPortQuietPeriod
					Integer32,
				fkDot1xPortReauthPeriod
					Integer32,
				fkDot1xPortAuthSuccess
					INTEGER
			 }

		-- 1.3.6.1.4.1.10428 9 1.101.7.6.1.1.1
		fkDot1xPortIndex OBJECT-TYPE
			SYNTAX InterfaceIndex
			MAX-ACCESS read-only
			STATUS current
			DESCRIPTION
				"The port number associated with this port."
			::= { fkDot1xPortEntry 1 }

		
		-- 1.3.6.1.4.1.10428 9 1.101.7.6.1.1.2
		fkDot1xPortEnable OBJECT-TYPE
			SYNTAX INTEGER
				{
				disable(1),
				portEnable(2),
				macEnable(3)
				}
			MAX-ACCESS read-only
			STATUS current
			DESCRIPTION
				"The administrativ state for each port."
			::= { fkDot1xPortEntry 2 }

		
		-- 1.3.6.1.4.1.10428 9 1.101.7.6.1.1.3
		fkDot1xPortMode OBJECT-TYPE
			SYNTAX INTEGER
				{
				default(-1),
				none(0),
				auto(1),
				forceAuthorized(2),
				forceUnauthorized(3)
				}
			MAX-ACCESS read-only
			STATUS current
			DESCRIPTION
				"The control values of the Authenticator PAE controlled."
			::= { fkDot1xPortEntry 3 }

		
		-- 1.3.6.1.4.1.10428 9 1.101.7.6.1.1.4
		fkDot1xPortReauthEnable OBJECT-TYPE
			SYNTAX INTEGER
				{
				disable(0),
				enable(1)
				}
			MAX-ACCESS read-only
			STATUS current
			DESCRIPTION
				"The reauthentication control for this port."
			::= { fkDot1xPortEntry 4 }

		
		-- 1.3.6.1.4.1.10428 9 1.101.7.6.1.1.5
		fkDot1xPortQuietPeriod OBJECT-TYPE
			SYNTAX Integer32 (1..65535)
			MAX-ACCESS read-only
			STATUS current
			DESCRIPTION
				"The value, in seconds, of the quietPeriod constant
				currently in use by the Authenticator PAE state machine."
			::= { fkDot1xPortEntry 5 }

		
		-- 1.3.6.1.4.1.10428 9 1.101.7.6.1.1.6
		fkDot1xPortReauthPeriod OBJECT-TYPE
			SYNTAX Integer32 (1..65535)
			MAX-ACCESS read-only
			STATUS current
			DESCRIPTION
				"The value, in seconds, of the txPeriod constant
				currently in use by the Authenticator PAE state machine."
			::= { fkDot1xPortEntry 6 }

		
		-- 1.3.6.1.4.1.10428 9 1.101.7.6.1.1.7
		fkDot1xPortAuthSuccess OBJECT-TYPE
			SYNTAX INTEGER
				{
				fail(1),
				success(2)
				}
			MAX-ACCESS read-only
			STATUS current
			DESCRIPTION
				"The value result to authentication of the supplicator."
			::= { fkDot1xPortEntry 7 }

		
		-- 1.3.6.1.4.1.10428 9 1.101.7.6.2
		fkDot1xPortControl OBJECT IDENTIFIER ::= { fkDot1xPort 2 }

		
		-- 1.3.6.1.4.1.10428 9 1.101.7.6.2.1
		fkDot1xPortControlRequest OBJECT-TYPE
			SYNTAX INTEGER
				{
				setDot1xPortProfile(1),
				setDot1xPortReauthenticate(2),
				setDot1xPortInittialize(3)
				}
			MAX-ACCESS read-write
			STATUS current
			DESCRIPTION
				"The MIB object for the dot1x command.A SetRequest 
				on this attribute starts a command execution 
				process in the netElement."
			::= { fkDot1xPortControl 1 }

		
		-- 1.3.6.1.4.1.10428 9 1.101.7.6.2.2
		fkDot1xPortControlStatus OBJECT-TYPE
			SYNTAX FkControlStatusType
			MAX-ACCESS read-only
			STATUS current
			DESCRIPTION
				"Describes the status of a user command group, used
				for block commands while a command execution in process"
			::= { fkDot1xPortControl 2 }

		
		-- 1.3.6.1.4.1.10428 9 1.101.7.6.2.3
		fkDot1xPortControlTimer OBJECT-TYPE
			SYNTAX Gauge32
			MAX-ACCESS read-write
			STATUS current
			DESCRIPTION
				"Maximum command duration time in case of long running."
			::= { fkDot1xPortControl 3 }

		
		-- 1.3.6.1.4.1.10428 9 1.101.7.6.2.4
		fkDot1xPortControlTimeStamp OBJECT-TYPE
			SYNTAX TimeStamp
			MAX-ACCESS read-only
			STATUS current
			DESCRIPTION
				"Time stamp attribute set at end of command."
			::= { fkDot1xPortControl 4 }

		
		-- 1.3.6.1.4.1.10428 9 1.101.7.6.2.5
		fkDot1xPortControlReqResult OBJECT-TYPE
			SYNTAX FkControlRequestResultType
			MAX-ACCESS read-only
			STATUS current
			DESCRIPTION
				"Command result attribute."
			::= { fkDot1xPortControl 5 }

		
		-- 1.3.6.1.4.1.10428 9 1.101.7.6.2.6
		fkDot1xPortControlIndex OBJECT-TYPE
			SYNTAX Integer32
			MAX-ACCESS read-write
			STATUS current
			DESCRIPTION
				"The port number associated with this port."
			::= { fkDot1xPortControl 6 }

		
		-- 1.3.6.1.4.1.10428 9 1.101.7.6.2.7
		fkDot1xPortControlEnable OBJECT-TYPE
			SYNTAX INTEGER
				{
				default(-1),
				disable(1),
				portEnable(2),
				macEnable(3)
				}
			MAX-ACCESS read-write
			STATUS current
			DESCRIPTION
				"The administrativ state for each port."
			::= { fkDot1xPortControl 7 }

		
		-- 1.3.6.1.4.1.10428 9 1.101.7.6.2.8
		fkDot1xPortControlMode OBJECT-TYPE
			SYNTAX INTEGER
				{
				default(-1),
				none(0),
				auto(1),
				forceAuthorized(2),
				forceUnauthorized(3)
				}
			MAX-ACCESS read-write
			STATUS current
			DESCRIPTION
				"The control values of the Authenticator PAE controlled."
			::= { fkDot1xPortControl 8 }

		
		-- 1.3.6.1.4.1.10428 9 1.101.7.6.2.9
		fkDot1xPortControlReauthEnable OBJECT-TYPE
			SYNTAX INTEGER
				{
				default(-1),
				disable(0),
				enable(1)
				}
			MAX-ACCESS read-write
			STATUS current
			DESCRIPTION
				"The reauthentication control for this port. Setting
				this attribute TRUE causes the Authenticator PAE state
				machine for the Port to reauthenticate the Supplicant.
				Setting this attribute FALSE has no effect."
			::= { fkDot1xPortControl 9 }

		
		-- 1.3.6.1.4.1.10428 9 1.101.7.6.2.10
		fkDot1xPortControlQuietPeriod OBJECT-TYPE
			SYNTAX Integer32 (-1 | 1..65535)
			MAX-ACCESS read-write
			STATUS current
			DESCRIPTION
				"The value, in seconds, of the quietPeriod constant
				currently in use by the Authenticator PAE state machine."
			::= { fkDot1xPortControl 10 }

		
		-- 1.3.6.1.4.1.10428 9 1.101.7.6.2.11
		fkDot1xPortControlReauthPeriod OBJECT-TYPE
			SYNTAX Integer32 (-1 | 1..65535)
			MAX-ACCESS read-write
			STATUS current
			DESCRIPTION
				"The value, in seconds, of the txPeriod constant
				currently in use by the Authenticator PAE state machine.
				(0~4294967295 for V5812G. 0 is initialization at 3600.)"
			::= { fkDot1xPortControl 11 }

		
		-- 1.3.6.1.4.1.10428 9 1.101.7.6.3
		fkDot1xPortNotification OBJECT IDENTIFIER ::= { fkDot1xPort 3 }

		
		-- 1.3.6.1.4.1.10428 9 1.101.7.6.3.1
		fkDot1xPortProfileChanged NOTIFICATION-TYPE
			OBJECTS { fkDot1xPortControlRequest, fkDot1xPortControlReqResult, fkDot1xPortControlTimeStamp, fkDot1xPortEnable, fkDot1xPortMode, 
				fkDot1xPortReauthEnable, fkDot1xPortQuietPeriod, fkDot1xPortReauthPeriod }
			STATUS current
			DESCRIPTION 
				"The trap for CLI command."
			::= { fkDot1xPortNotification 1 }

		
		-- 1.3.6.1.4.1.10428 9 1.101.7.6.3.2
		fkDot1xPortAuthSuccessChanged NOTIFICATION-TYPE
			OBJECTS { fkDot1xPortControlRequest, fkDot1xPortControlTimeStamp, fkDot1xPortControlReqResult, fkDot1xPortAuthSuccess }
			STATUS current
			DESCRIPTION 
				"The trap for authentication result."
			::= { fkDot1xPortNotification 2 }

		
		-- 1.3.6.1.4.1.10428 9 1.101.7.7
		fkDot1xStatistics OBJECT IDENTIFIER ::= { fkSecurity 7 }

		
		-- 1.3.6.1.4.1.10428 9 1.101.7.7.1
		fkDot1xStatisticsTable OBJECT-TYPE
			SYNTAX SEQUENCE OF FkDot1xStatisticsEntry
			MAX-ACCESS not-accessible
			STATUS current
			DESCRIPTION
				"Description."
			::= { fkDot1xStatistics 1 }

		
		-- 1.3.6.1.4.1.10428 9 1.101.7.7.1.1
		fkDot1xStatisticsEntry OBJECT-TYPE
			SYNTAX FkDot1xStatisticsEntry
			MAX-ACCESS not-accessible
			STATUS current
			DESCRIPTION
				"Description."
			INDEX { fkDot1xStatsPortIndex }
			::= { fkDot1xStatisticsTable 1 }

		
		FkDot1xStatisticsEntry ::=
			SEQUENCE { 
				fkDot1xStatsPortIndex
					INTEGER,
				fkDot1xStatsEapolFramesRx
					Counter32,
				fkDot1xStatsEapolFramesTx
					Counter32,
				fkDot1xStatsEapolStartFramesRx
					Counter32,
				fkDot1xStatsEapolLogoffFramesRx
					Counter32,
				fkDot1xStatsEapolRespIdFramesRx
					Counter32,
				fkDot1xStatsEapolRespFramesRx
					Counter32,
				fkDot1xStatsEapolReqIdFramesTx
					Counter32,
				fkDot1xStatsEapolReqFramesTx
					Integer32,
				fkDot1xStatsInvalidEapolFramesRx
					Counter32,
				fkDot1xStatsEapLengthErrorFramesRx
					Counter32,
				fkDot1xStatsLastEapolFrameVersion
					Counter32,
				fkDot1xStatsLastEapolFrameSource
					MacAddress
			 }

		-- 1.3.6.1.4.1.10428 9 1.101.7.7.1.1.1
		fkDot1xStatsPortIndex OBJECT-TYPE
			SYNTAX INTEGER (1..255)
			MAX-ACCESS read-only
			STATUS current
			DESCRIPTION
				"Description"
			::= { fkDot1xStatisticsEntry 1 }

		
		-- 1.3.6.1.4.1.10428 9 1.101.7.7.1.1.2
		fkDot1xStatsEapolFramesRx OBJECT-TYPE
			SYNTAX Counter32
			MAX-ACCESS read-only
			STATUS current
			DESCRIPTION
				"Description"
			::= { fkDot1xStatisticsEntry 2 }

		
		-- 1.3.6.1.4.1.10428 9 1.101.7.7.1.1.3
		fkDot1xStatsEapolFramesTx OBJECT-TYPE
			SYNTAX Counter32
			MAX-ACCESS read-only
			STATUS current
			DESCRIPTION
				"Description"
			::= { fkDot1xStatisticsEntry 3 }

		
		-- 1.3.6.1.4.1.10428 9 1.101.7.7.1.1.4
		fkDot1xStatsEapolStartFramesRx OBJECT-TYPE
			SYNTAX Counter32
			MAX-ACCESS read-only
			STATUS current
			DESCRIPTION
				"Description"
			::= { fkDot1xStatisticsEntry 4 }

		
		-- 1.3.6.1.4.1.10428 9 1.101.7.7.1.1.5
		fkDot1xStatsEapolLogoffFramesRx OBJECT-TYPE
			SYNTAX Counter32
			MAX-ACCESS read-only
			STATUS current
			DESCRIPTION
				"Description"
			::= { fkDot1xStatisticsEntry 5 }

		
		-- 1.3.6.1.4.1.10428 9 1.101.7.7.1.1.6
		fkDot1xStatsEapolRespIdFramesRx OBJECT-TYPE
			SYNTAX Counter32
			MAX-ACCESS read-only
			STATUS current
			DESCRIPTION
				"Description"
			::= { fkDot1xStatisticsEntry 6 }

		
		-- 1.3.6.1.4.1.10428 9 1.101.7.7.1.1.7
		fkDot1xStatsEapolRespFramesRx OBJECT-TYPE
			SYNTAX Counter32
			MAX-ACCESS read-only
			STATUS current
			DESCRIPTION
				"Description"
			::= { fkDot1xStatisticsEntry 7 }

		
		-- 1.3.6.1.4.1.10428 9 1.101.7.7.1.1.8
		fkDot1xStatsEapolReqIdFramesTx OBJECT-TYPE
			SYNTAX Counter32
			MAX-ACCESS read-only
			STATUS current
			DESCRIPTION
				"Description"
			::= { fkDot1xStatisticsEntry 8 }

		
		-- 1.3.6.1.4.1.10428 9 1.101.7.7.1.1.9
		fkDot1xStatsEapolReqFramesTx OBJECT-TYPE
			SYNTAX Integer32
			MAX-ACCESS read-only
			STATUS current
			DESCRIPTION
				"Description"
			::= { fkDot1xStatisticsEntry 9 }

		
		-- 1.3.6.1.4.1.10428 9 1.101.7.7.1.1.10
		fkDot1xStatsInvalidEapolFramesRx OBJECT-TYPE
			SYNTAX Counter32
			MAX-ACCESS read-only
			STATUS current
			DESCRIPTION
				"Description"
			::= { fkDot1xStatisticsEntry 10 }

		
		-- 1.3.6.1.4.1.10428 9 1.101.7.7.1.1.11
		fkDot1xStatsEapLengthErrorFramesRx OBJECT-TYPE
			SYNTAX Counter32
			MAX-ACCESS read-only
			STATUS current
			DESCRIPTION
				"Description"
			::= { fkDot1xStatisticsEntry 11 }

		
		-- 1.3.6.1.4.1.10428 9 1.101.7.7.1.1.12
		fkDot1xStatsLastEapolFrameVersion OBJECT-TYPE
			SYNTAX Counter32
			MAX-ACCESS read-only
			STATUS current
			DESCRIPTION
				"Description"
			::= { fkDot1xStatisticsEntry 12 }

		
		-- 1.3.6.1.4.1.10428 9 1.101.7.7.1.1.13
		fkDot1xStatsLastEapolFrameSource OBJECT-TYPE
			SYNTAX MacAddress
			MAX-ACCESS read-only
			STATUS current
			DESCRIPTION
				"Description"
			::= { fkDot1xStatisticsEntry 13 }

		
		-- 1.3.6.1.4.1.10428 9 1.101.7.7.2
		fkDot1xStatisticsControl OBJECT IDENTIFIER ::= { fkDot1xStatistics 2 }

		
		-- 1.3.6.1.4.1.10428 9 1.101.7.7.2.1
		fkDot1xStatsControlRequest OBJECT-TYPE
			SYNTAX INTEGER { clearDot1xStatistics(1) }
			MAX-ACCESS read-write
			STATUS current
			DESCRIPTION
				"Description"
			::= { fkDot1xStatisticsControl 1 }

		
		-- 1.3.6.1.4.1.10428 9 1.101.7.7.2.2
		fkDot1xStatsControlStatus OBJECT-TYPE
			SYNTAX FkControlStatusType
			MAX-ACCESS read-only
			STATUS current
			DESCRIPTION
				"Description"
			::= { fkDot1xStatisticsControl 2 }

		
		-- 1.3.6.1.4.1.10428 9 1.101.7.7.2.3
		fkDot1xStatsControlTimer OBJECT-TYPE
			SYNTAX Gauge32
			MAX-ACCESS read-write
			STATUS current
			DESCRIPTION
				"Description"
			::= { fkDot1xStatisticsControl 3 }

		
		-- 1.3.6.1.4.1.10428 9 1.101.7.7.2.4
		fkDot1xStatsControlTimeStamp OBJECT-TYPE
			SYNTAX TimeTicks
			MAX-ACCESS read-only
			STATUS current
			DESCRIPTION
				"Description"
			::= { fkDot1xStatisticsControl 4 }

		
		-- 1.3.6.1.4.1.10428 9 1.101.7.7.2.5
		fkDot1xStatsControlReqResult OBJECT-TYPE
			SYNTAX FkControlRequestResultType
			MAX-ACCESS read-only
			STATUS current
			DESCRIPTION
				"Description"
			::= { fkDot1xStatisticsControl 5 }

		
		-- 1.3.6.1.4.1.10428 9 1.101.7.7.2.6
		fkDot1xStatsControlPortIndex OBJECT-TYPE
			SYNTAX Unsigned32 (1..255)
			MAX-ACCESS read-write
			STATUS current
			DESCRIPTION
				"Description"
			::= { fkDot1xStatisticsControl 6 }

		
		-- 1.3.6.1.4.1.10428 9 1.101.7.7.3
		fkDot1xStatisticsNotification OBJECT IDENTIFIER ::= { fkDot1xStatistics 3 }

		
		-- 1.3.6.1.4.1.10428 9 1.101.7.7.3.1
		fkDot1xStatisticsCleared NOTIFICATION-TYPE
			OBJECTS { fkDot1xStatsControlRequest, fkDot1xStatsControlTimeStamp, fkDot1xStatsControlReqResult, fkDot1xStatsControlPortIndex }
			STATUS current
			DESCRIPTION 
				"Description"
			::= { fkDot1xStatisticsNotification 1 }

		
		-- 1.3.6.1.4.1.10428 9 1.101.7.8
		fkArpInspection OBJECT IDENTIFIER ::= { fkSecurity 8 }

		
		-- 1.3.6.1.4.1.10428 9 1.101.7.8.1
		fkArpInspectBase OBJECT IDENTIFIER ::= { fkArpInspection 1 }

		
		-- 1.3.6.1.4.1.10428 9 1.101.7.8.1.1
		fkArpInspectBaseInfo OBJECT IDENTIFIER ::= { fkArpInspectBase 1 }

		
		-- 1.3.6.1.4.1.10428 9 1.101.7.8.1.1.1
		fkArpInspectValidateSrcMac OBJECT-TYPE
			SYNTAX INTEGER
				{
				disable(0),
				enable(1)
				}
			MAX-ACCESS read-only
			STATUS current
			DESCRIPTION
				"Validate Source Mac"
			::= { fkArpInspectBaseInfo 1 }

		
		-- 1.3.6.1.4.1.10428 9 1.101.7.8.1.1.2
		fkArpInspectValidateDstMac OBJECT-TYPE
			SYNTAX INTEGER
				{
				disable(0),
				enable(1)
				}
			MAX-ACCESS read-only
			STATUS current
			DESCRIPTION
				"Validate Destination Mac"
			::= { fkArpInspectBaseInfo 2 }

		
		-- 1.3.6.1.4.1.10428 9 1.101.7.8.1.1.3
		fkArpInspectValidateIpAddr OBJECT-TYPE
			SYNTAX INTEGER
				{
				disable(0),
				enable(1)
				}
			MAX-ACCESS read-only
			STATUS current
			DESCRIPTION
				"Validate IP Address"
			::= { fkArpInspectBaseInfo 3 }

		
		-- 1.3.6.1.4.1.10428 9 1.101.7.8.1.1.4
		fkArpInspectLogBufferSize OBJECT-TYPE
			SYNTAX Integer32 (0..1024)
			MAX-ACCESS read-only
			STATUS current
			DESCRIPTION
				"Description."
			::= { fkArpInspectBaseInfo 4 }

		
		-- 1.3.6.1.4.1.10428 9 1.101.7.8.1.1.5
		fkArpInspectLogEntry OBJECT-TYPE
			SYNTAX Integer32 (0..1024)
			MAX-ACCESS read-only
			STATUS current
			DESCRIPTION
				"Description."
			::= { fkArpInspectBaseInfo 5 }

		
		-- 1.3.6.1.4.1.10428 9 1.101.7.8.1.1.6
		fkArpInspectLogInterval OBJECT-TYPE
			SYNTAX Integer32 (0..86400)
			MAX-ACCESS read-only
			STATUS current
			DESCRIPTION
				"Description."
			::= { fkArpInspectBaseInfo 6 }

		
		-- 1.3.6.1.4.1.10428 9 1.101.7.8.1.2
		fkArpInspectBaseControl OBJECT IDENTIFIER ::= { fkArpInspectBase 2 }

		
		-- 1.3.6.1.4.1.10428 9 1.101.7.8.1.2.1
		fkArpInspectControlRequest OBJECT-TYPE
			SYNTAX INTEGER
				{
				setArpInspectValidateProfile(1),
				setArpInspectLogBufferSize(2),
				setArpInspectLogRate(3)
				}
			MAX-ACCESS read-write
			STATUS current
			DESCRIPTION
				"Description"
			::= { fkArpInspectBaseControl 1 }

		
		-- 1.3.6.1.4.1.10428 9 1.101.7.8.1.2.2
		fkArpInspectControlStatus OBJECT-TYPE
			SYNTAX FkControlStatusType
			MAX-ACCESS read-only
			STATUS current
			DESCRIPTION
				"Description"
			::= { fkArpInspectBaseControl 2 }

		
		-- 1.3.6.1.4.1.10428 9 1.101.7.8.1.2.3
		fkArpInspectControlTimer OBJECT-TYPE
			SYNTAX Gauge32
			MAX-ACCESS read-write
			STATUS current
			DESCRIPTION
				"Description"
			::= { fkArpInspectBaseControl 3 }

		
		-- 1.3.6.1.4.1.10428 9 1.101.7.8.1.2.4
		fkArpInspectControlTimeStamp OBJECT-TYPE
			SYNTAX TimeTicks
			MAX-ACCESS read-only
			STATUS current
			DESCRIPTION
				"Description"
			::= { fkArpInspectBaseControl 4 }

		
		-- 1.3.6.1.4.1.10428 9 1.101.7.8.1.2.5
		fkArpInspectControlReqResult OBJECT-TYPE
			SYNTAX FkControlRequestResultType
			MAX-ACCESS read-only
			STATUS current
			DESCRIPTION
				"Result of the last command."
			::= { fkArpInspectBaseControl 5 }

		
		-- 1.3.6.1.4.1.10428 9 1.101.7.8.1.2.6
		fkArpInspectControlValidateSrcMac OBJECT-TYPE
			SYNTAX INTEGER
				{
				disable(0),
				enable(1)
				}
			MAX-ACCESS read-write
			STATUS current
			DESCRIPTION
				"Description."
			::= { fkArpInspectBaseControl 6 }

		
		-- 1.3.6.1.4.1.10428 9 1.101.7.8.1.2.7
		fkArpInspectControlValidateDstMac OBJECT-TYPE
			SYNTAX INTEGER
				{
				disable(0),
				enable(1)
				}
			MAX-ACCESS read-write
			STATUS current
			DESCRIPTION
				"Description."
			::= { fkArpInspectBaseControl 7 }

		
		-- 1.3.6.1.4.1.10428 9 1.101.7.8.1.2.8
		fkArpInspectControlValidateIpAddr OBJECT-TYPE
			SYNTAX INTEGER
				{
				disable(0),
				enable(1)
				}
			MAX-ACCESS read-write
			STATUS current
			DESCRIPTION
				"Description."
			::= { fkArpInspectBaseControl 8 }

		
		-- 1.3.6.1.4.1.10428 9 1.101.7.8.1.2.9
		fkArpInspectControlLogBufferSize OBJECT-TYPE
			SYNTAX Integer32 (0..1024)
			MAX-ACCESS read-write
			STATUS current
			DESCRIPTION
				"Description."
			::= { fkArpInspectBaseControl 9 }

		
		-- 1.3.6.1.4.1.10428 9 1.101.7.8.1.2.10
		fkArpInspectControlLogEntry OBJECT-TYPE
			SYNTAX Integer32 (0..1024)
			MAX-ACCESS read-write
			STATUS current
			DESCRIPTION
				"Description."
			::= { fkArpInspectBaseControl 10 }

		
		-- 1.3.6.1.4.1.10428 9 1.101.7.8.1.2.11
		fkArpInspectControlLogInterval OBJECT-TYPE
			SYNTAX Integer32 (0..86400)
			MAX-ACCESS read-write
			STATUS current
			DESCRIPTION
				"Description."
			::= { fkArpInspectBaseControl 11 }

		
		-- 1.3.6.1.4.1.10428 9 1.101.7.8.1.3
		fkArpInspectBaseNotifications OBJECT IDENTIFIER ::= { fkArpInspectBase 3 }

		
		-- 1.3.6.1.4.1.10428 9 1.101.7.8.1.3.1
		fkArpInspectValidateChanged NOTIFICATION-TYPE
			OBJECTS { fkArpInspectControlRequest, fkArpInspectControlTimeStamp, fkArpInspectControlReqResult, fkArpInspectControlValidateSrcMac, fkArpInspectControlValidateDstMac, 
				fkArpInspectControlValidateIpAddr }
			STATUS current
			DESCRIPTION 
				"fkArpInspectValidateControl"
			::= { fkArpInspectBaseNotifications 1 }

		
		-- 1.3.6.1.4.1.10428 9 1.101.7.8.1.3.2
		fkArpInspectLogBufferSizeChanged NOTIFICATION-TYPE
			OBJECTS { fkArpInspectControlRequest, fkArpInspectControlTimeStamp, fkArpInspectControlReqResult, fkArpInspectControlLogBufferSize }
			STATUS current
			DESCRIPTION 
				"Description."
			::= { fkArpInspectBaseNotifications 2 }

		
		-- 1.3.6.1.4.1.10428 9 1.101.7.8.1.3.3
		fkArpInspectLogRateChanged NOTIFICATION-TYPE
			OBJECTS { fkArpInspectControlRequest, fkArpInspectControlTimeStamp, fkArpInspectControlReqResult, fkArpInspectControlLogEntry, fkArpInspectControlLogInterval
				 }
			STATUS current
			DESCRIPTION 
				"Description."
			::= { fkArpInspectBaseNotifications 3 }

		
		-- 1.3.6.1.4.1.10428 9 1.101.7.8.2
		fkArpACL OBJECT IDENTIFIER ::= { fkArpInspection 2 }

		
		-- 1.3.6.1.4.1.10428 9 1.101.7.8.2.1
		fkArpAclTable OBJECT-TYPE
			SYNTAX SEQUENCE OF FkArpAclEntry
			MAX-ACCESS not-accessible
			STATUS current
			DESCRIPTION
				"Description."
			::= { fkArpACL 1 }

		
		-- 1.3.6.1.4.1.10428 9 1.101.7.8.2.1.1
		fkArpAclEntry OBJECT-TYPE
			SYNTAX FkArpAclEntry
			MAX-ACCESS not-accessible
			STATUS current
			DESCRIPTION
				"Description."
			INDEX { fkArpAclIndex }
			::= { fkArpAclTable 1 }

		
		FkArpAclEntry ::=
			SEQUENCE { 
				fkArpAclIndex
					INTEGER,
				fkArpAclName
					OCTET STRING,
				fkArpAclNumEntries
					INTEGER
			 }

		-- 1.3.6.1.4.1.10428 9 1.101.7.8.2.1.1.1
		fkArpAclIndex OBJECT-TYPE
			SYNTAX INTEGER (1..2147483647)
			MAX-ACCESS read-only
			STATUS current
			DESCRIPTION
				"Description."
			::= { fkArpAclEntry 1 }

		
		-- 1.3.6.1.4.1.10428 9 1.101.7.8.2.1.1.2
		fkArpAclName OBJECT-TYPE
			SYNTAX OCTET STRING (SIZE (1..255))
			MAX-ACCESS read-only
			STATUS current
			DESCRIPTION
				"Description."
			::= { fkArpAclEntry 2 }

		
		-- 1.3.6.1.4.1.10428 9 1.101.7.8.2.1.1.3
		fkArpAclNumEntries OBJECT-TYPE
			SYNTAX INTEGER (1..2147483647)
			MAX-ACCESS read-only
			STATUS current
			DESCRIPTION
				"Number of Entries"
			::= { fkArpAclEntry 3 }

		
		-- 1.3.6.1.4.1.10428 9 1.101.7.8.2.2
		fkArpAclControl OBJECT IDENTIFIER ::= { fkArpACL 2 }

		
		-- 1.3.6.1.4.1.10428 9 1.101.7.8.2.2.1
		fkArpAclControlRequest OBJECT-TYPE
			SYNTAX INTEGER
				{
				createArpAcl(1),
				destroyArpAcl(2)
				}
			MAX-ACCESS read-write
			STATUS current
			DESCRIPTION
				"Description"
			::= { fkArpAclControl 1 }

		
		-- 1.3.6.1.4.1.10428 9 1.101.7.8.2.2.2
		fkArpAclControlStatus OBJECT-TYPE
			SYNTAX FkControlStatusType
			MAX-ACCESS read-only
			STATUS current
			DESCRIPTION
				"Description"
			::= { fkArpAclControl 2 }

		
		-- 1.3.6.1.4.1.10428 9 1.101.7.8.2.2.3
		fkArpAclControlTimer OBJECT-TYPE
			SYNTAX Gauge32
			MAX-ACCESS read-write
			STATUS current
			DESCRIPTION
				"Description"
			::= { fkArpAclControl 3 }

		
		-- 1.3.6.1.4.1.10428 9 1.101.7.8.2.2.4
		fkArpAclControlTimeStamp OBJECT-TYPE
			SYNTAX TimeTicks
			MAX-ACCESS read-only
			STATUS current
			DESCRIPTION
				"Description"
			::= { fkArpAclControl 4 }

		
		-- 1.3.6.1.4.1.10428 9 1.101.7.8.2.2.5
		fkArpAclControlReqResult OBJECT-TYPE
			SYNTAX FkControlRequestResultType
			MAX-ACCESS read-only
			STATUS current
			DESCRIPTION
				"Result of the last command."
			::= { fkArpAclControl 5 }

		
		-- 1.3.6.1.4.1.10428 9 1.101.7.8.2.2.6
		fkArpAclControlIndex OBJECT-TYPE
			SYNTAX Integer32
			MAX-ACCESS read-write
			STATUS current
			DESCRIPTION
				"Description."
			::= { fkArpAclControl 6 }

		
		-- 1.3.6.1.4.1.10428 9 1.101.7.8.2.2.7
		fkArpAclControlName OBJECT-TYPE
			SYNTAX OCTET STRING (SIZE (1..255))
			MAX-ACCESS read-write
			STATUS current
			DESCRIPTION
				"The name of acl."
			::= { fkArpAclControl 7 }

		
		-- 1.3.6.1.4.1.10428 9 1.101.7.8.2.3
		fkArpAclNotifications OBJECT IDENTIFIER ::= { fkArpACL 3 }

		
		-- 1.3.6.1.4.1.10428 9 1.101.7.8.2.3.1
		fkArpAclCreated NOTIFICATION-TYPE
			OBJECTS { fkArpAclControlRequest, fkArpAclControlTimeStamp, fkArpAclControlReqResult, fkArpAclName }
			STATUS current
			DESCRIPTION 
				"fkArpInspectValidateControl"
			::= { fkArpAclNotifications 1 }

		
		-- 1.3.6.1.4.1.10428 9 1.101.7.8.2.3.2
		fkArpAclDestroyed NOTIFICATION-TYPE
			OBJECTS { fkArpAclControlRequest, fkArpAclControlTimeStamp, fkArpAclControlReqResult, fkArpAclControlIndex }
			STATUS current
			DESCRIPTION 
				"fkArpInspectValidateControl"
			::= { fkArpAclNotifications 2 }

		
		-- 1.3.6.1.4.1.10428 9 1.101.7.8.3
		fkArpACLRule OBJECT IDENTIFIER ::= { fkArpInspection 3 }

		
		-- 1.3.6.1.4.1.10428 9 1.101.7.8.3.1
		fkArpAclRuleTable OBJECT-TYPE
			SYNTAX SEQUENCE OF FkArpAclRuleEntry
			MAX-ACCESS not-accessible
			STATUS current
			DESCRIPTION
				"Description."
			::= { fkArpACLRule 1 }

		
		-- 1.3.6.1.4.1.10428 9 1.101.7.8.3.1.1
		fkArpAclRuleEntry OBJECT-TYPE
			SYNTAX FkArpAclRuleEntry
			MAX-ACCESS not-accessible
			STATUS current
			DESCRIPTION
				"Description."
			INDEX { fkArpAclRuleAclIndex, fkArpAclRuleIndex }
			::= { fkArpAclRuleTable 1 }

		
		FkArpAclRuleEntry ::=
			SEQUENCE { 
				fkArpAclRuleAclIndex
					Integer32,
				fkArpAclRuleIndex
					Integer32,
				fkArpAclRuleAction
					INTEGER,
				fkArpAclRuleType
					INTEGER,
				fkArpAclRuleRangeStartIP
					IpAddress,
				fkArpAclRuleRangeEndIP
					IpAddress,
				fkArpAclRuleIPAddress
					IpAddress,
				fkArpAclRuleIPMask
					Integer32,
				fkArpAclRuleMacAddr
					MacAddress,
				fkArpAclRuleMacType
					INTEGER
			 }

		-- 1.3.6.1.4.1.10428 9 1.101.7.8.3.1.1.1
		fkArpAclRuleAclIndex OBJECT-TYPE
			SYNTAX Integer32 (1..2147483647)
			MAX-ACCESS read-only
			STATUS current
			DESCRIPTION
				"Description."
			::= { fkArpAclRuleEntry 1 }

		
		-- 1.3.6.1.4.1.10428 9 1.101.7.8.3.1.1.2
		fkArpAclRuleIndex OBJECT-TYPE
			SYNTAX Integer32 (1..2147483647)
			MAX-ACCESS read-only
			STATUS current
			DESCRIPTION
				"ACL entry Index"
			::= { fkArpAclRuleEntry 2 }

		
		-- 1.3.6.1.4.1.10428 9 1.101.7.8.3.1.1.3
		fkArpAclRuleAction OBJECT-TYPE
			SYNTAX INTEGER
				{
				deny(0),
				permit(1)
				}
			MAX-ACCESS read-only
			STATUS current
			DESCRIPTION
				"The permit/deny control used per entry"
			::= { fkArpAclRuleEntry 3 }

		
		-- 1.3.6.1.4.1.10428 9 1.101.7.8.3.1.1.4
		fkArpAclRuleType OBJECT-TYPE
			SYNTAX INTEGER
				{
				subnet(0),
				range(1),
				dhcpSnooping(2)
				}
			MAX-ACCESS read-only
			STATUS current
			DESCRIPTION
				"Specify IP address is host or range."
			::= { fkArpAclRuleEntry 4 }

		
		-- 1.3.6.1.4.1.10428 9 1.101.7.8.3.1.1.5
		fkArpAclRuleRangeStartIP OBJECT-TYPE
			SYNTAX IpAddress
			MAX-ACCESS read-only
			STATUS current
			DESCRIPTION
				"Valid if fkArpAclEntryRange is 1,Otherwise this value is invalid."
			::= { fkArpAclRuleEntry 5 }

		
		-- 1.3.6.1.4.1.10428 9 1.101.7.8.3.1.1.6
		fkArpAclRuleRangeEndIP OBJECT-TYPE
			SYNTAX IpAddress
			MAX-ACCESS read-only
			STATUS current
			DESCRIPTION
				"Valid if fkArpAclEntryRange is 1,Otherwise this value is invalid."
			::= { fkArpAclRuleEntry 6 }

		
		-- 1.3.6.1.4.1.10428 9 1.101.7.8.3.1.1.7
		fkArpAclRuleIPAddress OBJECT-TYPE
			SYNTAX IpAddress
			MAX-ACCESS read-only
			STATUS current
			DESCRIPTION
				"IP Address.Valid if fkArpAclEntryRange is 0."
			::= { fkArpAclRuleEntry 7 }

		
		-- 1.3.6.1.4.1.10428 9 1.101.7.8.3.1.1.8
		fkArpAclRuleIPMask OBJECT-TYPE
			SYNTAX Integer32 (1..32)
			MAX-ACCESS read-only
			STATUS current
			DESCRIPTION
				"SubnetMask.Valid if fkArpAclEntryRange is 0."
			::= { fkArpAclRuleEntry 8 }

		
		-- 1.3.6.1.4.1.10428 9 1.101.7.8.3.1.1.9
		fkArpAclRuleMacAddr OBJECT-TYPE
			SYNTAX MacAddress
			MAX-ACCESS read-only
			STATUS current
			DESCRIPTION
				"Mac Address. If  fkArpAclEntryMacType is 0 , this value is invalid."
			::= { fkArpAclRuleEntry 9 }

		
		-- 1.3.6.1.4.1.10428 9 1.101.7.8.3.1.1.10
		fkArpAclRuleMacType OBJECT-TYPE
			SYNTAX INTEGER
				{
				any(0),
				host(1)
				}
			MAX-ACCESS read-only
			STATUS current
			DESCRIPTION
				"Description."
			::= { fkArpAclRuleEntry 10 }

		
		-- 1.3.6.1.4.1.10428 9 1.101.7.8.3.2
		fkArpAclRuleControl OBJECT IDENTIFIER ::= { fkArpACLRule 2 }

		
		-- 1.3.6.1.4.1.10428 9 1.101.7.8.3.2.1
		fkArpAclRuleControlRequest OBJECT-TYPE
			SYNTAX INTEGER
				{
				createArpAclRule(1),
				destroyArpAclRule(2)
				}
			MAX-ACCESS read-write
			STATUS current
			DESCRIPTION
				"Description"
			::= { fkArpAclRuleControl 1 }

		
		-- 1.3.6.1.4.1.10428 9 1.101.7.8.3.2.2
		fkArpAclRuleControlStatus OBJECT-TYPE
			SYNTAX FkControlStatusType
			MAX-ACCESS read-only
			STATUS current
			DESCRIPTION
				"Description"
			::= { fkArpAclRuleControl 2 }

		
		-- 1.3.6.1.4.1.10428 9 1.101.7.8.3.2.3
		fkArpAclRuleControlTimer OBJECT-TYPE
			SYNTAX Gauge32
			MAX-ACCESS read-write
			STATUS current
			DESCRIPTION
				"Description"
			::= { fkArpAclRuleControl 3 }

		
		-- 1.3.6.1.4.1.10428 9 1.101.7.8.3.2.4
		fkArpAclRuleControlTimeStamp OBJECT-TYPE
			SYNTAX TimeTicks
			MAX-ACCESS read-only
			STATUS current
			DESCRIPTION
				"Description"
			::= { fkArpAclRuleControl 4 }

		
		-- 1.3.6.1.4.1.10428 9 1.101.7.8.3.2.5
		fkArpAclRuleControlReqResult OBJECT-TYPE
			SYNTAX FkControlRequestResultType
			MAX-ACCESS read-only
			STATUS current
			DESCRIPTION
				"Result of the last command."
			::= { fkArpAclRuleControl 5 }

		
		-- 1.3.6.1.4.1.10428 9 1.101.7.8.3.2.6
		fkArpAclRuleControlAclIndex OBJECT-TYPE
			SYNTAX Integer32
			MAX-ACCESS read-write
			STATUS current
			DESCRIPTION
				"The name of acl."
			::= { fkArpAclRuleControl 6 }

		
		-- 1.3.6.1.4.1.10428 9 1.101.7.8.3.2.7
		fkArpAclRuleControlIndex OBJECT-TYPE
			SYNTAX Integer32
			MAX-ACCESS read-write
			STATUS current
			DESCRIPTION
				"The entry index within ACL"
			::= { fkArpAclRuleControl 7 }

		
		-- 1.3.6.1.4.1.10428 9 1.101.7.8.3.2.8
		fkArpAclRuleControlAction OBJECT-TYPE
			SYNTAX INTEGER
				{
				deny(0),
				permit(1)
				}
			MAX-ACCESS read-write
			STATUS current
			DESCRIPTION
				"The permit/deny control used per entry"
			::= { fkArpAclRuleControl 8 }

		
		-- 1.3.6.1.4.1.10428 9 1.101.7.8.3.2.9
		fkArpAclRuleControlType OBJECT-TYPE
			SYNTAX INTEGER
				{
				subnet(0),
				range(1),
				dhcpSnooping(2)
				}
			MAX-ACCESS read-write
			STATUS current
			DESCRIPTION
				"If  type of entry is 1, fkArpAclEntryControlType must be 0.
				"
			::= { fkArpAclRuleControl 9 }

		
		-- 1.3.6.1.4.1.10428 9 1.101.7.8.3.2.10
		fkArpAclRuleControlRangeStartIP OBJECT-TYPE
			SYNTAX IpAddress
			MAX-ACCESS read-write
			STATUS current
			DESCRIPTION
				"Description"
			::= { fkArpAclRuleControl 10 }

		
		-- 1.3.6.1.4.1.10428 9 1.101.7.8.3.2.11
		fkArpAclRuleControlRangeEndIP OBJECT-TYPE
			SYNTAX IpAddress
			MAX-ACCESS read-write
			STATUS current
			DESCRIPTION
				"Description"
			::= { fkArpAclRuleControl 11 }

		
		-- 1.3.6.1.4.1.10428 9 1.101.7.8.3.2.12
		fkArpAclRuleControlIPAddress OBJECT-TYPE
			SYNTAX IpAddress
			MAX-ACCESS read-write
			STATUS current
			DESCRIPTION
				"Description"
			::= { fkArpAclRuleControl 12 }

		
		-- 1.3.6.1.4.1.10428 9 1.101.7.8.3.2.13
		fkArpAclRuleControlIPMask OBJECT-TYPE
			SYNTAX INTEGER (1..32)
			MAX-ACCESS read-write
			STATUS current
			DESCRIPTION
				"Description"
			::= { fkArpAclRuleControl 13 }

		
		-- 1.3.6.1.4.1.10428 9 1.101.7.8.3.2.14
		fkArpAclRuleControlMacAddr OBJECT-TYPE
			SYNTAX MacAddress
			MAX-ACCESS read-write
			STATUS current
			DESCRIPTION
				"Description"
			::= { fkArpAclRuleControl 14 }

		
		-- 1.3.6.1.4.1.10428 9 1.101.7.8.3.2.15
		fkArpAclRuleControlMacType OBJECT-TYPE
			SYNTAX INTEGER
				{
				any(0),
				host(1)
				}
			MAX-ACCESS read-write
			STATUS current
			DESCRIPTION
				"Description"
			::= { fkArpAclRuleControl 15 }

		
		-- 1.3.6.1.4.1.10428 9 1.101.7.8.3.3
		fkArpAclRuleNotifications OBJECT IDENTIFIER ::= { fkArpACLRule 3 }

		
		-- 1.3.6.1.4.1.10428 9 1.101.7.8.3.3.1
		fkArpAclRuleCreated NOTIFICATION-TYPE
			OBJECTS { fkArpAclRuleControlRequest, fkArpAclRuleControlTimeStamp, fkArpAclRuleControlReqResult, fkArpAclRuleAction, fkArpAclRuleType, 
				fkArpAclRuleRangeStartIP, fkArpAclRuleRangeEndIP, fkArpAclRuleIPAddress, fkArpAclRuleIPMask, fkArpAclRuleMacAddr, 
				fkArpAclRuleMacType }
			STATUS current
			DESCRIPTION 
				"createArpAclEntry"
			::= { fkArpAclRuleNotifications 1 }

		
		-- 1.3.6.1.4.1.10428 9 1.101.7.8.3.3.2
		fkArpAclRuleDestroyed NOTIFICATION-TYPE
			OBJECTS { fkArpAclRuleControlRequest, fkArpAclRuleControlTimeStamp, fkArpAclRuleControlReqResult, fkArpAclRuleControlAclIndex, fkArpAclRuleControlIndex
				 }
			STATUS current
			DESCRIPTION 
				"destroyArpAclEntry"
			::= { fkArpAclRuleNotifications 2 }

		
		-- 1.3.6.1.4.1.10428 9 1.101.7.8.4
		fkArpInspectVlan OBJECT IDENTIFIER ::= { fkArpInspection 4 }

		
		-- 1.3.6.1.4.1.10428 9 1.101.7.8.4.1
		fkArpInspectVlanTable OBJECT-TYPE
			SYNTAX SEQUENCE OF FkArpInspectVlanEntry
			MAX-ACCESS not-accessible
			STATUS current
			DESCRIPTION
				"Description."
			::= { fkArpInspectVlan 1 }

		
		-- 1.3.6.1.4.1.10428 9 1.101.7.8.4.1.1
		fkArpInspectVlanEntry OBJECT-TYPE
			SYNTAX FkArpInspectVlanEntry
			MAX-ACCESS not-accessible
			STATUS current
			DESCRIPTION
				"Description."
			INDEX { fkArpInspectVlanIndex }
			::= { fkArpInspectVlanTable 1 }

		
		FkArpInspectVlanEntry ::=
			SEQUENCE { 
				fkArpInspectVlanIndex
					Integer32,
				fkArpInspectVlanEnable
					INTEGER,
				fkArpInspectVlanFilterAcl
					Integer32,
				fkArpInspectVlanFwdPktCnt
					Integer32,
				fkArpInspectVlanDropPktCnt
					Integer32,
				fkArpInspectVlanAclPermits
					Integer32,
				fkArpInspectVlanAclDrops
					Integer32,
				fkArpInspectVlanSrcMacFailurs
					Integer32,
				fkArpInspectVlanDstMacFailurs
					Integer32,
				fkArpInspectVlanIpAddrFailurs
					Integer32,
				fkArpInspectVlanFilterAclName
					OCTET STRING
			 }

		-- 1.3.6.1.4.1.10428 9 1.101.7.8.4.1.1.1
		fkArpInspectVlanIndex OBJECT-TYPE
			SYNTAX Integer32 (1..4094)
			MAX-ACCESS read-only
			STATUS current
			DESCRIPTION
				"The index of vlan."
			::= { fkArpInspectVlanEntry 1 }

		
		-- 1.3.6.1.4.1.10428 9 1.101.7.8.4.1.1.2
		fkArpInspectVlanEnable OBJECT-TYPE
			SYNTAX INTEGER
				{
				disable(0),
				enable(1)
				}
			MAX-ACCESS read-only
			STATUS current
			DESCRIPTION
				"The enable/disable control used per vlan."
			::= { fkArpInspectVlanEntry 2 }

		
		-- 1.3.6.1.4.1.10428 9 1.101.7.8.4.1.1.3
		fkArpInspectVlanFilterAcl OBJECT-TYPE
			SYNTAX Integer32
			MAX-ACCESS read-only
			STATUS current
			DESCRIPTION
				"Description."
			::= { fkArpInspectVlanEntry 3 }

		
		-- 1.3.6.1.4.1.10428 9 1.101.7.8.4.1.1.4
		fkArpInspectVlanFwdPktCnt OBJECT-TYPE
			SYNTAX Integer32
			MAX-ACCESS read-only
			STATUS current
			DESCRIPTION
				"Forwarded arp packet count."
			::= { fkArpInspectVlanEntry 4 }

		
		-- 1.3.6.1.4.1.10428 9 1.101.7.8.4.1.1.5
		fkArpInspectVlanDropPktCnt OBJECT-TYPE
			SYNTAX Integer32
			MAX-ACCESS read-only
			STATUS current
			DESCRIPTION
				"Droped arp packet count."
			::= { fkArpInspectVlanEntry 5 }

		
		-- 1.3.6.1.4.1.10428 9 1.101.7.8.4.1.1.6
		fkArpInspectVlanAclPermits OBJECT-TYPE
			SYNTAX Integer32
			MAX-ACCESS read-only
			STATUS current
			DESCRIPTION
				"Description."
			::= { fkArpInspectVlanEntry 6 }

		
		-- 1.3.6.1.4.1.10428 9 1.101.7.8.4.1.1.7
		fkArpInspectVlanAclDrops OBJECT-TYPE
			SYNTAX Integer32
			MAX-ACCESS read-only
			STATUS current
			DESCRIPTION
				"Description."
			::= { fkArpInspectVlanEntry 7 }

		
		-- 1.3.6.1.4.1.10428 9 1.101.7.8.4.1.1.8
		fkArpInspectVlanSrcMacFailurs OBJECT-TYPE
			SYNTAX Integer32
			MAX-ACCESS read-only
			STATUS current
			DESCRIPTION
				"Description."
			::= { fkArpInspectVlanEntry 8 }

		
		-- 1.3.6.1.4.1.10428 9 1.101.7.8.4.1.1.9
		fkArpInspectVlanDstMacFailurs OBJECT-TYPE
			SYNTAX Integer32
			MAX-ACCESS read-only
			STATUS current
			DESCRIPTION
				"Description."
			::= { fkArpInspectVlanEntry 9 }

		
		-- 1.3.6.1.4.1.10428 9 1.101.7.8.4.1.1.10
		fkArpInspectVlanIpAddrFailurs OBJECT-TYPE
			SYNTAX Integer32
			MAX-ACCESS read-only
			STATUS current
			DESCRIPTION
				"Description."
			::= { fkArpInspectVlanEntry 10 }

		
		-- 1.3.6.1.4.1.10428 9 1.101.7.8.4.1.1.11
		fkArpInspectVlanFilterAclName OBJECT-TYPE
			SYNTAX OCTET STRING (SIZE (1..255))
			MAX-ACCESS read-only
			STATUS current
			DESCRIPTION
				"Description."
			::= { fkArpInspectVlanEntry 11 }

		
		-- 1.3.6.1.4.1.10428 9 1.101.7.8.4.2
		fkArpInspectVlanControl OBJECT IDENTIFIER ::= { fkArpInspectVlan 2 }

		
		-- 1.3.6.1.4.1.10428 9 1.101.7.8.4.2.1
		fkArpInspectVlanControlRequest OBJECT-TYPE
			SYNTAX INTEGER
				{
				setArpInspectVlanProfile(1),
				clearArpInspectVlanStatistics(2)
				}
			MAX-ACCESS read-write
			STATUS current
			DESCRIPTION
				"Description"
			::= { fkArpInspectVlanControl 1 }

		
		-- 1.3.6.1.4.1.10428 9 1.101.7.8.4.2.2
		fkArpInspectVlanControlStatus OBJECT-TYPE
			SYNTAX FkControlStatusType
			MAX-ACCESS read-only
			STATUS current
			DESCRIPTION
				"Description"
			::= { fkArpInspectVlanControl 2 }

		
		-- 1.3.6.1.4.1.10428 9 1.101.7.8.4.2.3
		fkArpInspectVlanControlTimer OBJECT-TYPE
			SYNTAX Gauge32
			MAX-ACCESS read-write
			STATUS current
			DESCRIPTION
				"Description"
			::= { fkArpInspectVlanControl 3 }

		
		-- 1.3.6.1.4.1.10428 9 1.101.7.8.4.2.4
		fkArpInspectVlanControlTimeStamp OBJECT-TYPE
			SYNTAX TimeTicks
			MAX-ACCESS read-only
			STATUS current
			DESCRIPTION
				"Description"
			::= { fkArpInspectVlanControl 4 }

		
		-- 1.3.6.1.4.1.10428 9 1.101.7.8.4.2.5
		fkArpInspectVlanControlReqResult OBJECT-TYPE
			SYNTAX FkControlRequestResultType
			MAX-ACCESS read-only
			STATUS current
			DESCRIPTION
				"Result of the last command."
			::= { fkArpInspectVlanControl 5 }

		
		-- 1.3.6.1.4.1.10428 9 1.101.7.8.4.2.6
		fkArpInspectVlanControlIndex OBJECT-TYPE
			SYNTAX INTEGER (1..4094)
			MAX-ACCESS read-write
			STATUS current
			DESCRIPTION
				"The index of vlan."
			::= { fkArpInspectVlanControl 6 }

		
		-- 1.3.6.1.4.1.10428 9 1.101.7.8.4.2.7
		fkArpInspectVlanControlEnable OBJECT-TYPE
			SYNTAX INTEGER
				{
				disable(0),
				enable(1)
				}
			MAX-ACCESS read-write
			STATUS current
			DESCRIPTION
				"The enable/disable control used per vlan."
			::= { fkArpInspectVlanControl 7 }

		
		-- 1.3.6.1.4.1.10428 9 1.101.7.8.4.2.8
		fkArpInspectVlanControlFilterAcl OBJECT-TYPE
			SYNTAX Integer32
			MAX-ACCESS read-write
			STATUS current
			DESCRIPTION
				"The ARP Access-list Name to be applied to vlan"
			::= { fkArpInspectVlanControl 8 }

		
		-- 1.3.6.1.4.1.10428 9 1.101.7.8.4.3
		fkArpInspectVlanNotifications OBJECT IDENTIFIER ::= { fkArpInspectVlan 3 }

		
		-- 1.3.6.1.4.1.10428 9 1.101.7.8.4.3.1
		fkArpInspectVlanChanged NOTIFICATION-TYPE
			OBJECTS { fkArpInspectVlanControlRequest, fkArpInspectVlanControlTimeStamp, fkArpInspectVlanControlReqResult, fkArpInspectVlanEnable, fkArpInspectVlanFilterAcl
				 }
			STATUS current
			DESCRIPTION 
				"setArpInspectVlanProfile"
			::= { fkArpInspectVlanNotifications 1 }

		
		-- 1.3.6.1.4.1.10428 9 1.101.7.8.5
		fkArpInspectPort OBJECT IDENTIFIER ::= { fkArpInspection 5 }

		
		-- 1.3.6.1.4.1.10428 9 1.101.7.8.5.1
		fkArpInspectPortTable OBJECT-TYPE
			SYNTAX SEQUENCE OF FkArpInspectPortEntry
			MAX-ACCESS not-accessible
			STATUS current
			DESCRIPTION
				"Description."
			::= { fkArpInspectPort 1 }

		
		-- 1.3.6.1.4.1.10428 9 1.101.7.8.5.1.1
		fkArpInspectPortEntry OBJECT-TYPE
			SYNTAX FkArpInspectPortEntry
			MAX-ACCESS not-accessible
			STATUS current
			DESCRIPTION
				"Description."
			INDEX { fkArpInspectPortIndex }
			::= { fkArpInspectPortTable 1 }

		
		FkArpInspectPortEntry ::=
			SEQUENCE { 
				fkArpInspectPortIndex
					Integer32,
				fkArpInspectPortTrust
					INTEGER
			 }

		-- 1.3.6.1.4.1.10428 9 1.101.7.8.5.1.1.1
		fkArpInspectPortIndex OBJECT-TYPE
			SYNTAX Integer32 (1..255)
			MAX-ACCESS read-only
			STATUS current
			DESCRIPTION
				"The index of port."
			::= { fkArpInspectPortEntry 1 }

		
		-- 1.3.6.1.4.1.10428 9 1.101.7.8.5.1.1.2
		fkArpInspectPortTrust OBJECT-TYPE
			SYNTAX INTEGER
				{
				untrust(0),
				trust(1)
				}
			MAX-ACCESS read-only
			STATUS current
			DESCRIPTION
				"The trust/untrust control used per port."
			::= { fkArpInspectPortEntry 2 }

		
		-- 1.3.6.1.4.1.10428 9 1.101.7.8.5.2
		fkArpInspectPortControl OBJECT IDENTIFIER ::= { fkArpInspectPort 2 }

		
		-- 1.3.6.1.4.1.10428 9 1.101.7.8.5.2.1
		fkArpInspectPortControlRequest OBJECT-TYPE
			SYNTAX INTEGER { setArpInspectTrustPort(1) }
			MAX-ACCESS read-write
			STATUS current
			DESCRIPTION
				"Description"
			::= { fkArpInspectPortControl 1 }

		
		-- 1.3.6.1.4.1.10428 9 1.101.7.8.5.2.2
		fkArpInspectPortControlStatus OBJECT-TYPE
			SYNTAX FkControlStatusType
			MAX-ACCESS read-only
			STATUS current
			DESCRIPTION
				"Description"
			::= { fkArpInspectPortControl 2 }

		
		-- 1.3.6.1.4.1.10428 9 1.101.7.8.5.2.3
		fkArpInspectPortControlTimer OBJECT-TYPE
			SYNTAX Gauge32
			MAX-ACCESS read-write
			STATUS current
			DESCRIPTION
				"Description"
			::= { fkArpInspectPortControl 3 }

		
		-- 1.3.6.1.4.1.10428 9 1.101.7.8.5.2.4
		fkArpInspectPortControlTimeStamp OBJECT-TYPE
			SYNTAX TimeTicks
			MAX-ACCESS read-only
			STATUS current
			DESCRIPTION
				"Description"
			::= { fkArpInspectPortControl 4 }

		
		-- 1.3.6.1.4.1.10428 9 1.101.7.8.5.2.5
		fkArpInspectPortControlReqResult OBJECT-TYPE
			SYNTAX FkControlRequestResultType
			MAX-ACCESS read-only
			STATUS current
			DESCRIPTION
				"Result of the last command."
			::= { fkArpInspectPortControl 5 }

		
		-- 1.3.6.1.4.1.10428 9 1.101.7.8.5.2.6
		fkArpInspectPortControlIndex OBJECT-TYPE
			SYNTAX INTEGER (1..255)
			MAX-ACCESS read-write
			STATUS current
			DESCRIPTION
				"The index of port."
			::= { fkArpInspectPortControl 6 }

		
		-- 1.3.6.1.4.1.10428 9 1.101.7.8.5.2.7
		fkArpInspectPortControlTrust OBJECT-TYPE
			SYNTAX INTEGER
				{
				untrust(0),
				trust(1)
				}
			MAX-ACCESS read-write
			STATUS current
			DESCRIPTION
				"The enable/disable control used per port"
			::= { fkArpInspectPortControl 7 }

		
		-- 1.3.6.1.4.1.10428 9 1.101.7.8.5.3
		fkArpInspectPortNotifications OBJECT IDENTIFIER ::= { fkArpInspectPort 3 }

		
		-- 1.3.6.1.4.1.10428 9 1.101.7.8.5.3.1
		fkArpInspectPortChanged NOTIFICATION-TYPE
			OBJECTS { fkArpInspectPortControlRequest, fkArpInspectPortControlTimeStamp, fkArpInspectPortControlTrust, fkArpInspectPortControlReqResult }
			STATUS current
			DESCRIPTION 
				"setArpInspectTrustPort"
			::= { fkArpInspectPortNotifications 1 }

		
		-- 1.3.6.1.4.1.10428 9 1.101.7.8.6
		fkArpInspectInvalidLog OBJECT IDENTIFIER ::= { fkArpInspection 6 }

		
		-- 1.3.6.1.4.1.10428 9 1.101.7.8.6.1
		fkArpInspectInvalidLogTable OBJECT-TYPE
			SYNTAX SEQUENCE OF FkArpInspectInvalidLogEntry
			MAX-ACCESS not-accessible
			STATUS current
			DESCRIPTION
				"Description."
			::= { fkArpInspectInvalidLog 1 }

		
		-- 1.3.6.1.4.1.10428 9 1.101.7.8.6.1.1
		fkArpInspectInvalidLogEntry OBJECT-TYPE
			SYNTAX FkArpInspectInvalidLogEntry
			MAX-ACCESS not-accessible
			STATUS current
			DESCRIPTION
				"Description."
			INDEX { fkArpInspectInvalidLogId }
			::= { fkArpInspectInvalidLogTable 1 }

		
		FkArpInspectInvalidLogEntry ::=
			SEQUENCE { 
				fkArpInspectInvalidLogId
					INTEGER,
				fkArpInspectInvalidLogReason
					INTEGER,
				fkArpInspectInvalidLogSamePktCnt
					Counter32,
				fkArpInspectInvalidLogOpcode
					INTEGER,
				fkArpInspectInvalidLogPortNumber
					INTEGER,
				fkArpInspectInvalidLogVlanId
					INTEGER,
				fkArpInspectInvalidLogSrcMacAddr
					OCTET STRING,
				fkArpInspectInvalidLogSrcIpAddr
					IpAddress,
				fkArpInspectInvalidLogDstMacAddr
					OCTET STRING,
				fkArpInspectInvalidLogDstIpAddr
					IpAddress,
				fkArpInspectInvalidLogLastRecvTime
					OCTET STRING
			 }

		-- 1.3.6.1.4.1.10428 9 1.101.7.8.6.1.1.1
		fkArpInspectInvalidLogId OBJECT-TYPE
			SYNTAX INTEGER (0..65535)
			MAX-ACCESS read-only
			STATUS current
			DESCRIPTION
				"ARP inspection invalid index."
			::= { fkArpInspectInvalidLogEntry 1 }

		
		-- 1.3.6.1.4.1.10428 9 1.101.7.8.6.1.1.2
		fkArpInspectInvalidLogReason OBJECT-TYPE
			SYNTAX INTEGER
				{
				aliReasonNone(0),
				aliReasonDhcpPermit(1),
				aliReasonDhcpDeny(2),
				aliReasonAclPermit(3),
				aliReasonAclDeny(4),
				aliReasonValidSrcfail(5),
				aliReasonValidDstfail(6),
				aliReasonValidIpfail(7)
				}
			MAX-ACCESS read-only
			STATUS current
			DESCRIPTION
				"ARP inspection invalid reason."
			::= { fkArpInspectInvalidLogEntry 2 }

		
		-- 1.3.6.1.4.1.10428 9 1.101.7.8.6.1.1.3
		fkArpInspectInvalidLogSamePktCnt OBJECT-TYPE
			SYNTAX Counter32
			MAX-ACCESS read-only
			STATUS current
			DESCRIPTION
				"ARP inspection invalid same packet counters."
			::= { fkArpInspectInvalidLogEntry 3 }

		
		-- 1.3.6.1.4.1.10428 9 1.101.7.8.6.1.1.4
		fkArpInspectInvalidLogOpcode OBJECT-TYPE
			SYNTAX INTEGER
				{
				arpopRequest(1),
				arpopReply(2)
				}
			MAX-ACCESS read-only
			STATUS current
			DESCRIPTION
				"ARP protocol opcodes."
			::= { fkArpInspectInvalidLogEntry 4 }

		
		-- 1.3.6.1.4.1.10428 9 1.101.7.8.6.1.1.5
		fkArpInspectInvalidLogPortNumber OBJECT-TYPE
			SYNTAX INTEGER
			MAX-ACCESS read-only
			STATUS current
			DESCRIPTION
				"ARP inspection invalid port number."
			::= { fkArpInspectInvalidLogEntry 5 }

		
		-- 1.3.6.1.4.1.10428 9 1.101.7.8.6.1.1.6
		fkArpInspectInvalidLogVlanId OBJECT-TYPE
			SYNTAX INTEGER
			MAX-ACCESS read-only
			STATUS current
			DESCRIPTION
				"ARP inspection invalid vlan id."
			::= { fkArpInspectInvalidLogEntry 6 }

		
		-- 1.3.6.1.4.1.10428 9 1.101.7.8.6.1.1.7
		fkArpInspectInvalidLogSrcMacAddr OBJECT-TYPE
			SYNTAX OCTET STRING (SIZE (0..6))
			MAX-ACCESS read-only
			STATUS current
			DESCRIPTION
				"ARP inspection invalid source mac address."
			::= { fkArpInspectInvalidLogEntry 7 }

		
		-- 1.3.6.1.4.1.10428 9 1.101.7.8.6.1.1.8
		fkArpInspectInvalidLogSrcIpAddr OBJECT-TYPE
			SYNTAX IpAddress
			MAX-ACCESS read-only
			STATUS current
			DESCRIPTION
				"ARP inspection invalid source IP address."
			::= { fkArpInspectInvalidLogEntry 8 }

		
		-- 1.3.6.1.4.1.10428 9 1.101.7.8.6.1.1.9
		fkArpInspectInvalidLogDstMacAddr OBJECT-TYPE
			SYNTAX OCTET STRING (SIZE (0..6))
			MAX-ACCESS read-only
			STATUS current
			DESCRIPTION
				"ARP inspection invalid destination mac address."
			::= { fkArpInspectInvalidLogEntry 9 }

		
		-- 1.3.6.1.4.1.10428 9 1.101.7.8.6.1.1.10
		fkArpInspectInvalidLogDstIpAddr OBJECT-TYPE
			SYNTAX IpAddress
			MAX-ACCESS read-only
			STATUS current
			DESCRIPTION
				"ARP inspection invalid destination IP address."
			::= { fkArpInspectInvalidLogEntry 10 }

		
		-- 1.3.6.1.4.1.10428 9 1.101.7.8.6.1.1.11
		fkArpInspectInvalidLogLastRecvTime OBJECT-TYPE
			SYNTAX OCTET STRING
			MAX-ACCESS read-only
			STATUS current
			DESCRIPTION
				"ARP inspection invalid packet last received time."
			::= { fkArpInspectInvalidLogEntry 11 }

		
		-- 1.3.6.1.4.1.10428 9 1.101.7.9
		fkSecurityAttack OBJECT IDENTIFIER ::= { fkSecurity 9 }

		
-- by rule id.
		-- 1.3.6.1.4.1.10428 9 1.101.7.9.1
		fkSecurityAttackBasic OBJECT IDENTIFIER ::= { fkSecurityAttack 1 }

		
		-- 1.3.6.1.4.1.10428 9 1.101.7.9.1.1
		fkSecurityAttackBasicBase OBJECT IDENTIFIER ::= { fkSecurityAttackBasic 1 }

		
		-- 1.3.6.1.4.1.10428 9 1.101.7.9.1.1.1
		fkSecurityAttackBasicBaseInfo OBJECT IDENTIFIER ::= { fkSecurityAttackBasicBase 1 }

		
		-- 1.3.6.1.4.1.10428 9 1.101.7.9.1.1.1.1
		fkSecurityAttackBasicBaseInfoGlobalStatus OBJECT-TYPE
			SYNTAX INTEGER
				{
				disable(0),
				enable(1)
				}
			MAX-ACCESS read-only
			STATUS current
			DESCRIPTION
				"The port attack global status."
			::= { fkSecurityAttackBasicBaseInfo 1 }

		
		-- 1.3.6.1.4.1.10428 9 1.101.7.9.1.1.1.2
		fkSecurityAttackBasicBaseDosStatus OBJECT-TYPE
			SYNTAX INTEGER
				{
				disable(0),
				enable(1)
				}
			MAX-ACCESS read-only
			STATUS current
			DESCRIPTION
				"The DOS status."
			::= { fkSecurityAttackBasicBaseInfo 2 }

		
		-- 1.3.6.1.4.1.10428 9 1.101.7.9.1.1.1.3
		fkSecurityAttackBasicBaseScanStatus OBJECT-TYPE
			SYNTAX INTEGER
				{
				disable(0),
				enable(1)
				}
			MAX-ACCESS read-only
			STATUS current
			DESCRIPTION
				"The Scan status."
			::= { fkSecurityAttackBasicBaseInfo 3 }

		
		-- 1.3.6.1.4.1.10428 9 1.101.7.9.1.1.1.4
		fkSecurityAttackBasicBaseCollectInterval OBJECT-TYPE
			SYNTAX Integer32
			MAX-ACCESS read-only
			STATUS current
			DESCRIPTION
				"The sampling interval"
			::= { fkSecurityAttackBasicBaseInfo 4 }

		
		-- 1.3.6.1.4.1.10428 9 1.101.7.9.1.1.2
		fkSecurityAttackBasicBaseControl OBJECT IDENTIFIER ::= { fkSecurityAttackBasicBase 2 }

		
		-- 1.3.6.1.4.1.10428 9 1.101.7.9.1.1.2.1
		fkSecurityAttackBasicBaseControlRequest OBJECT-TYPE
			SYNTAX INTEGER
				{
				setSecurityAttackGlobalStatus(1),
				setSecurityAttackDosStatus(2),
				setSecurityAttackScanStatus(3),
				setSecurityAttackCollectInterval(4),
				setSecurityAttackAllConfig(5)
				}
			MAX-ACCESS read-write
			STATUS current
			DESCRIPTION
				"Description"
			::= { fkSecurityAttackBasicBaseControl 1 }

		
		-- 1.3.6.1.4.1.10428 9 1.101.7.9.1.1.2.2
		fkSecurityAttackBasicBaseControlStatus OBJECT-TYPE
			SYNTAX FkControlStatusType
			MAX-ACCESS read-only
			STATUS current
			DESCRIPTION
				"Description"
			::= { fkSecurityAttackBasicBaseControl 2 }

		
		-- 1.3.6.1.4.1.10428 9 1.101.7.9.1.1.2.3
		fkSecurityAttackBasicBaseControlTimer OBJECT-TYPE
			SYNTAX Gauge32
			MAX-ACCESS read-write
			STATUS current
			DESCRIPTION
				"Description"
			::= { fkSecurityAttackBasicBaseControl 3 }

		
		-- 1.3.6.1.4.1.10428 9 1.101.7.9.1.1.2.4
		fkSecurityAttackBasicBaseControlTimeStamp OBJECT-TYPE
			SYNTAX TimeTicks
			MAX-ACCESS read-only
			STATUS current
			DESCRIPTION
				"Description"
			::= { fkSecurityAttackBasicBaseControl 4 }

		
		-- 1.3.6.1.4.1.10428 9 1.101.7.9.1.1.2.5
		fkSecurityAttackBasicBaseControlReqResult OBJECT-TYPE
			SYNTAX FkControlRequestResultType
			MAX-ACCESS read-only
			STATUS current
			DESCRIPTION
				"Result of the last command."
			::= { fkSecurityAttackBasicBaseControl 5 }

		
		-- 1.3.6.1.4.1.10428 9 1.101.7.9.1.1.2.6
		fkSecurityAttackBasicBaseControlGlobalStatus OBJECT-TYPE
			SYNTAX INTEGER
				{
				disable(0),
				enable(1)
				}
			MAX-ACCESS read-write
			STATUS current
			DESCRIPTION
				"The port attack global status."
			::= { fkSecurityAttackBasicBaseControl 6 }

		
		-- 1.3.6.1.4.1.10428 9 1.101.7.9.1.1.2.7
		fkSecurityAttackBasicBaseControlDosStatus OBJECT-TYPE
			SYNTAX INTEGER
				{
				disable(0),
				enable(1)
				}
			MAX-ACCESS read-write
			STATUS current
			DESCRIPTION
				"The DOS status."
			::= { fkSecurityAttackBasicBaseControl 7 }

		
		-- 1.3.6.1.4.1.10428 9 1.101.7.9.1.1.2.8
		fkSecurityAttackBasicBaseControlScanStatus OBJECT-TYPE
			SYNTAX INTEGER
				{
				disable(0),
				enable(1)
				}
			MAX-ACCESS read-write
			STATUS current
			DESCRIPTION
				"The Scan status."
			::= { fkSecurityAttackBasicBaseControl 8 }

		
		-- 1.3.6.1.4.1.10428 9 1.101.7.9.1.1.2.9
		fkSecurityAttackBasicBaseControlCollectInterval OBJECT-TYPE
			SYNTAX Integer32
			MAX-ACCESS read-write
			STATUS current
			DESCRIPTION
				"The sampling interval"
			::= { fkSecurityAttackBasicBaseControl 9 }

		
		-- 1.3.6.1.4.1.10428 9 1.101.7.9.1.1.3
		fkSecurityAttackBasicBaseNotification OBJECT IDENTIFIER ::= { fkSecurityAttackBasicBase 3 }

		
		-- 1.3.6.1.4.1.10428 9 1.101.7.9.1.1.3.1
		fkSecurityAttackBasicBaseGlobalStatusChanged NOTIFICATION-TYPE
			OBJECTS { fkSecurityAttackBasicBaseControlRequest, fkSecurityAttackBasicBaseControlTimeStamp, fkSecurityAttackBasicBaseControlReqResult, fkSecurityAttackBasicBaseControlGlobalStatus }
			STATUS current
			DESCRIPTION 
				"setSecurityAttackGlobalStatus"
			::= { fkSecurityAttackBasicBaseNotification 1 }

		
		-- 1.3.6.1.4.1.10428 9 1.101.7.9.1.1.3.2
		fkSecurityAttackBasicBaseDosStatusChanged NOTIFICATION-TYPE
			OBJECTS { fkSecurityAttackBasicBaseControlRequest, fkSecurityAttackBasicBaseControlTimeStamp, fkSecurityAttackBasicBaseControlReqResult, fkSecurityAttackBasicBaseControlDosStatus }
			STATUS current
			DESCRIPTION 
				"setSecurityAttackDosStatus"
			::= { fkSecurityAttackBasicBaseNotification 2 }

		
		-- 1.3.6.1.4.1.10428 9 1.101.7.9.1.1.3.3
		fkSecurityAttackBasicBaseScanStatusChanged NOTIFICATION-TYPE
			OBJECTS { fkSecurityAttackBasicBaseControlRequest, fkSecurityAttackBasicBaseControlTimeStamp, fkSecurityAttackBasicBaseControlReqResult, fkSecurityAttackBasicBaseControlScanStatus }
			STATUS current
			DESCRIPTION 
				"setSecurityAttackScanStatus"
			::= { fkSecurityAttackBasicBaseNotification 3 }

		
		-- 1.3.6.1.4.1.10428 9 1.101.7.9.1.1.3.4
		fkSecurityAttackBasicBaseCollectIntervalChanged NOTIFICATION-TYPE
			OBJECTS { fkSecurityAttackBasicBaseControlRequest, fkSecurityAttackBasicBaseControlTimeStamp, fkSecurityAttackBasicBaseControlReqResult, fkSecurityAttackBasicBaseControlCollectInterval }
			STATUS current
			DESCRIPTION 
				"setSecurityAttackCollectInterval"
			::= { fkSecurityAttackBasicBaseNotification 4 }

		
		-- 1.3.6.1.4.1.10428 9 1.101.7.9.1.1.3.5
		fkSecurityAttackBasicBaseAllConfigChanged NOTIFICATION-TYPE
			OBJECTS { fkSecurityAttackBasicBaseControlRequest, fkSecurityAttackBasicBaseControlTimeStamp, fkSecurityAttackBasicBaseControlReqResult, fkSecurityAttackBasicBaseControlGlobalStatus, fkSecurityAttackBasicBaseControlDosStatus, 
				fkSecurityAttackBasicBaseControlScanStatus, fkSecurityAttackBasicBaseControlCollectInterval }
			STATUS current
			DESCRIPTION 
				"setSecurityAttackAllConfig"
			::= { fkSecurityAttackBasicBaseNotification 5 }

		
		-- 1.3.6.1.4.1.10428 9 1.101.7.9.1.2
		fkSecurityAttackBasicPolicy OBJECT IDENTIFIER ::= { fkSecurityAttackBasic 2 }

		
		-- 1.3.6.1.4.1.10428 9 1.101.7.9.1.2.1
		fkSecurityAttackBasicPolicyInfo OBJECT IDENTIFIER ::= { fkSecurityAttackBasicPolicy 1 }

		
		-- 1.3.6.1.4.1.10428 9 1.101.7.9.1.2.1.1
		fkSecurityAttackBasicPolicyAttackType OBJECT-TYPE
			SYNTAX BITS
				{
				none(0),
				tcpDosAttack(1),
				udpDosAttack(2),
				icmpDosAttack(3),
				hostScan(4),
				portScan(5)
				}
			MAX-ACCESS read-only
			STATUS current
			DESCRIPTION
				"The port attack type."
			::= { fkSecurityAttackBasicPolicyInfo 1 }

		
		-- 1.3.6.1.4.1.10428 9 1.101.7.9.1.2.1.2
		fkSecurityAttackBasicPolicyBlockTime OBJECT-TYPE
			SYNTAX OCTET STRING
			MAX-ACCESS read-only
			STATUS current
			DESCRIPTION
				"The block time of port attack. (10-86400 sec)"
			::= { fkSecurityAttackBasicPolicyInfo 2 }

		
		-- 1.3.6.1.4.1.10428 9 1.101.7.9.1.2.1.3
		fkSecurityAttackBasicPolicyThresholdCount OBJECT-TYPE
			SYNTAX OCTET STRING
			MAX-ACCESS read-only
			STATUS current
			DESCRIPTION
				"Description."
			::= { fkSecurityAttackBasicPolicyInfo 3 }

		
		-- 1.3.6.1.4.1.10428 9 1.101.7.9.1.2.1.4
		fkSecurityAttackBasicPolicyCollectPorts OBJECT-TYPE
			SYNTAX OCTET STRING
			MAX-ACCESS read-only
			STATUS current
			DESCRIPTION
				"The Collect ports."
			::= { fkSecurityAttackBasicPolicyInfo 4 }

		
		-- 1.3.6.1.4.1.10428 9 1.101.7.9.1.2.2
		fkSecurityAttackBasicPolicyControl OBJECT IDENTIFIER ::= { fkSecurityAttackBasicPolicy 2 }

		
		-- 1.3.6.1.4.1.10428 9 1.101.7.9.1.2.2.1
		fkSecurityAttackBasicPolicyControlRequest OBJECT-TYPE
			SYNTAX INTEGER
				{
				setSecurityAttackBasicPolicyBlockTime(1),
				setSecurityAttackBasicPolicyThresholdCount(2),
				setSecurityAttackBasicPolicyCollectPorts(3),
				setSecurityAttackBasicPolicyAllConfig(4)
				}
			MAX-ACCESS read-write
			STATUS current
			DESCRIPTION
				"Decsription"
			::= { fkSecurityAttackBasicPolicyControl 1 }

		
		-- 1.3.6.1.4.1.10428 9 1.101.7.9.1.2.2.2
		fkSecurityAttackBasicPolicyControlStatus OBJECT-TYPE
			SYNTAX FkControlStatusType
			MAX-ACCESS read-only
			STATUS current
			DESCRIPTION
				"Description"
			::= { fkSecurityAttackBasicPolicyControl 2 }

		
		-- 1.3.6.1.4.1.10428 9 1.101.7.9.1.2.2.3
		fkSecurityAttackBasicPolicyControlTimer OBJECT-TYPE
			SYNTAX Gauge32
			MAX-ACCESS read-write
			STATUS current
			DESCRIPTION
				"Description"
			::= { fkSecurityAttackBasicPolicyControl 3 }

		
		-- 1.3.6.1.4.1.10428 9 1.101.7.9.1.2.2.4
		fkSecurityAttackBasicPolicyControlTimeStamp OBJECT-TYPE
			SYNTAX TimeTicks
			MAX-ACCESS read-only
			STATUS current
			DESCRIPTION
				"Description"
			::= { fkSecurityAttackBasicPolicyControl 4 }

		
		-- 1.3.6.1.4.1.10428 9 1.101.7.9.1.2.2.5
		fkSecurityAttackBasicPolicyControlReqResult OBJECT-TYPE
			SYNTAX FkControlRequestResultType
			MAX-ACCESS read-only
			STATUS current
			DESCRIPTION
				"Result of the last command."
			::= { fkSecurityAttackBasicPolicyControl 5 }

		
		-- 1.3.6.1.4.1.10428 9 1.101.7.9.1.2.2.6
		fkSecurityAttackBasicPolicyControlAttackType OBJECT-TYPE
			SYNTAX BITS
				{
				none(0),
				tcpDosAttack(1),
				udpDosAttack(2),
				icmpDosAttack(3),
				hostScan(4),
				portScan(5)
				}
			MAX-ACCESS read-write
			STATUS current
			DESCRIPTION
				"The port attack type."
			::= { fkSecurityAttackBasicPolicyControl 6 }

		
		-- 1.3.6.1.4.1.10428 9 1.101.7.9.1.2.2.7
		fkSecurityAttackBasicPolicyControlBlockTime OBJECT-TYPE
			SYNTAX OCTET STRING
			MAX-ACCESS read-write
			STATUS current
			DESCRIPTION
				"The block time of port attack. (10-86400 sec)"
			::= { fkSecurityAttackBasicPolicyControl 7 }

		
		-- 1.3.6.1.4.1.10428 9 1.101.7.9.1.2.2.8
		fkSecurityAttackBasicPolicyControlThresholdCount OBJECT-TYPE
			SYNTAX OCTET STRING
			MAX-ACCESS read-write
			STATUS current
			DESCRIPTION
				"Description."
			::= { fkSecurityAttackBasicPolicyControl 8 }

		
		-- 1.3.6.1.4.1.10428 9 1.101.7.9.1.2.2.9
		fkSecurityAttackBasicPolicyControlCollectPorts OBJECT-TYPE
			SYNTAX OCTET STRING
			MAX-ACCESS read-write
			STATUS current
			DESCRIPTION
				"The Collect ports."
			::= { fkSecurityAttackBasicPolicyControl 9 }

		
		-- 1.3.6.1.4.1.10428 9 1.101.7.9.1.2.3
		fkSecurityAttackBasicPolicyNotification OBJECT IDENTIFIER ::= { fkSecurityAttackBasicPolicy 3 }

		
		-- 1.3.6.1.4.1.10428 9 1.101.7.9.1.2.3.1
		fkSecurityAttackBasicPolicyBlockTimeChanged NOTIFICATION-TYPE
			OBJECTS { fkSecurityAttackBasicPolicyControlRequest, fkSecurityAttackBasicPolicyControlTimeStamp, fkSecurityAttackBasicPolicyControlReqResult, fkSecurityAttackBasicPolicyControlAttackType, fkSecurityAttackBasicPolicyControlBlockTime
				 }
			STATUS current
			DESCRIPTION 
				"setSecurityAttackBasicPolicyBlockTime"
			::= { fkSecurityAttackBasicPolicyNotification 1 }

		
		-- 1.3.6.1.4.1.10428 9 1.101.7.9.1.2.3.2
		fkSecurityAttackBasicPolicyThresholdCountChanged NOTIFICATION-TYPE
			OBJECTS { fkSecurityAttackBasicPolicyControlRequest, fkSecurityAttackBasicPolicyControlTimeStamp, fkSecurityAttackBasicPolicyControlReqResult, fkSecurityAttackBasicPolicyControlAttackType, fkSecurityAttackBasicPolicyControlThresholdCount
				 }
			STATUS current
			DESCRIPTION 
				"setSecurityAttackBasicPolicyThresholdCount"
			::= { fkSecurityAttackBasicPolicyNotification 2 }

		
		-- 1.3.6.1.4.1.10428 9 1.101.7.9.1.2.3.3
		fkSecurityAttackBasicPolicyCollectPortsChanged NOTIFICATION-TYPE
			OBJECTS { fkSecurityAttackBasicPolicyControlRequest, fkSecurityAttackBasicPolicyControlTimeStamp, fkSecurityAttackBasicPolicyControlReqResult, fkSecurityAttackBasicPolicyControlCollectPorts }
			STATUS current
			DESCRIPTION 
				"setSecurityAttackBasicPolicyCollectPorts"
			::= { fkSecurityAttackBasicPolicyNotification 3 }

		
		-- 1.3.6.1.4.1.10428 9 1.101.7.9.1.2.3.4
		setSecurityAttackBasicPolicyAllConfigChanged NOTIFICATION-TYPE
			OBJECTS { fkSecurityAttackBasicPolicyControlRequest, fkSecurityAttackBasicPolicyControlTimeStamp, fkSecurityAttackBasicPolicyControlReqResult, fkSecurityAttackBasicPolicyControlAttackType, fkSecurityAttackBasicPolicyControlBlockTime, 
				fkSecurityAttackBasicPolicyControlThresholdCount, fkSecurityAttackBasicPolicyControlCollectPorts }
			STATUS current
			DESCRIPTION 
				"Description."
			::= { fkSecurityAttackBasicPolicyNotification 4 }

		
		-- 1.3.6.1.4.1.10428 9 1.101.7.9.1.3
		fkSecurityAttackBasicExceptList OBJECT IDENTIFIER ::= { fkSecurityAttackBasic 3 }

		
		-- 1.3.6.1.4.1.10428 9 1.101.7.9.1.3.1
		fkSecurityAttackBasicExceptListTable OBJECT-TYPE
			SYNTAX SEQUENCE OF FkSecurityAttackBasicExceptListEntry
			MAX-ACCESS not-accessible
			STATUS current
			DESCRIPTION
				"Description."
			::= { fkSecurityAttackBasicExceptList 1 }

		
		-- 1.3.6.1.4.1.10428 9 1.101.7.9.1.3.1.1
		fkSecurityAttackBasicExceptListEntry OBJECT-TYPE
			SYNTAX FkSecurityAttackBasicExceptListEntry
			MAX-ACCESS not-accessible
			STATUS current
			DESCRIPTION
				"Description."
			INDEX { fkSecurityAttackBasicExceptListIndex }
			::= { fkSecurityAttackBasicExceptListTable 1 }

		
		FkSecurityAttackBasicExceptListEntry ::=
			SEQUENCE { 
				fkSecurityAttackBasicExceptListIndex
					Integer32,
				fkSecurityAttackBasicExceptListProtocolType
					INTEGER,
				fkSecurityAttackBasicExceptListSourceIpAddress
					IpAddress,
				fkSecurityAttackBasicExceptListDestinationIpAddress
					IpAddress,
				fkSecurityAttackBasicExceptListIngressPort
					Integer32
			 }

		-- 1.3.6.1.4.1.10428 9 1.101.7.9.1.3.1.1.1
		fkSecurityAttackBasicExceptListIndex OBJECT-TYPE
			SYNTAX Integer32 (1..65535)
			MAX-ACCESS read-only
			STATUS current
			DESCRIPTION
				"The Rule index."
			::= { fkSecurityAttackBasicExceptListEntry 1 }

		
		-- 1.3.6.1.4.1.10428 9 1.101.7.9.1.3.1.1.2
		fkSecurityAttackBasicExceptListProtocolType OBJECT-TYPE
			SYNTAX INTEGER
				{
				any(0),
				tcp(1),
				udp(2),
				icmp(3)
				}
			MAX-ACCESS read-only
			STATUS current
			DESCRIPTION
				"The protocol type"
			::= { fkSecurityAttackBasicExceptListEntry 2 }

		
		-- 1.3.6.1.4.1.10428 9 1.101.7.9.1.3.1.1.3
		fkSecurityAttackBasicExceptListSourceIpAddress OBJECT-TYPE
			SYNTAX IpAddress
			MAX-ACCESS read-only
			STATUS current
			DESCRIPTION
				"The source IP address "
			::= { fkSecurityAttackBasicExceptListEntry 3 }

		
		-- 1.3.6.1.4.1.10428 9 1.101.7.9.1.3.1.1.4
		fkSecurityAttackBasicExceptListDestinationIpAddress OBJECT-TYPE
			SYNTAX IpAddress
			MAX-ACCESS read-only
			STATUS current
			DESCRIPTION
				"The destination IP address "
			::= { fkSecurityAttackBasicExceptListEntry 4 }

		
		-- 1.3.6.1.4.1.10428 9 1.101.7.9.1.3.1.1.5
		fkSecurityAttackBasicExceptListIngressPort OBJECT-TYPE
			SYNTAX Integer32 (1..65535)
			MAX-ACCESS read-only
			STATUS current
			DESCRIPTION
				"The ingress port"
			::= { fkSecurityAttackBasicExceptListEntry 5 }

		
		-- 1.3.6.1.4.1.10428 9 1.101.7.9.1.3.2
		fkSecurityAttackBasicExceptListControl OBJECT IDENTIFIER ::= { fkSecurityAttackBasicExceptList 2 }

		
		-- 1.3.6.1.4.1.10428 9 1.101.7.9.1.3.2.1
		fkSecurityAttackBasicExceptListControlRequest OBJECT-TYPE
			SYNTAX INTEGER
				{
				createSecurityAttackBasicExceptList(1),
				modifySecurityAttackBasicExceptList(2),
				delSecurityAttackBasicExceptList(3)
				}
			MAX-ACCESS read-write
			STATUS current
			DESCRIPTION
				"Description"
			::= { fkSecurityAttackBasicExceptListControl 1 }

		
		-- 1.3.6.1.4.1.10428 9 1.101.7.9.1.3.2.2
		fkSecurityAttackBasicExceptListControlStatus OBJECT-TYPE
			SYNTAX FkControlStatusType
			MAX-ACCESS read-only
			STATUS current
			DESCRIPTION
				"Description"
			::= { fkSecurityAttackBasicExceptListControl 2 }

		
		-- 1.3.6.1.4.1.10428 9 1.101.7.9.1.3.2.3
		fkSecurityAttackBasicExceptListControlTimer OBJECT-TYPE
			SYNTAX Gauge32
			MAX-ACCESS read-write
			STATUS current
			DESCRIPTION
				"Description"
			::= { fkSecurityAttackBasicExceptListControl 3 }

		
		-- 1.3.6.1.4.1.10428 9 1.101.7.9.1.3.2.4
		fkSecurityAttackBasicExceptListControlTimeStamp OBJECT-TYPE
			SYNTAX TimeTicks
			MAX-ACCESS read-only
			STATUS current
			DESCRIPTION
				"Description"
			::= { fkSecurityAttackBasicExceptListControl 4 }

		
		-- 1.3.6.1.4.1.10428 9 1.101.7.9.1.3.2.5
		fkSecurityAttackBasicExceptListControlReqResult OBJECT-TYPE
			SYNTAX FkControlRequestResultType
			MAX-ACCESS read-only
			STATUS current
			DESCRIPTION
				"Result of the last command."
			::= { fkSecurityAttackBasicExceptListControl 5 }

		
		-- 1.3.6.1.4.1.10428 9 1.101.7.9.1.3.2.6
		fkSecurityAttackBasicExceptListControlRuleIndex OBJECT-TYPE
			SYNTAX Integer32
			MAX-ACCESS read-write
			STATUS current
			DESCRIPTION
				"The rule index of except list. It’s specific nuber per each rule."
			::= { fkSecurityAttackBasicExceptListControl 6 }

		
		-- 1.3.6.1.4.1.10428 9 1.101.7.9.1.3.2.7
		fkSecurityAttackBasicExceptListControlProtocolType OBJECT-TYPE
			SYNTAX INTEGER
				{
				any(0),
				tcp(1),
				udp(2),
				icmp(3)
				}
			MAX-ACCESS read-write
			STATUS current
			DESCRIPTION
				"The port attack block time (default:300 sec)"
			::= { fkSecurityAttackBasicExceptListControl 7 }

		
		-- 1.3.6.1.4.1.10428 9 1.101.7.9.1.3.2.8
		fkSecurityAttackBasicExceptListControlSourceIpAddress OBJECT-TYPE
			SYNTAX IpAddress
			MAX-ACCESS read-write
			STATUS current
			DESCRIPTION
				"Description."
			::= { fkSecurityAttackBasicExceptListControl 8 }

		
		-- 1.3.6.1.4.1.10428 9 1.101.7.9.1.3.2.9
		fkSecurityAttackBasicExceptListControlDestinationIpAddress OBJECT-TYPE
			SYNTAX IpAddress
			MAX-ACCESS read-write
			STATUS current
			DESCRIPTION
				"Description."
			::= { fkSecurityAttackBasicExceptListControl 9 }

		
		-- 1.3.6.1.4.1.10428 9 1.101.7.9.1.3.2.10
		fkSecurityAttackBasicExceptListControlIngressPort OBJECT-TYPE
			SYNTAX Integer32
			MAX-ACCESS read-write
			STATUS current
			DESCRIPTION
				"The ingress port"
			::= { fkSecurityAttackBasicExceptListControl 10 }

		
		-- 1.3.6.1.4.1.10428 9 1.101.7.9.1.3.3
		fkSecurityAttackBasicExceptListNotification OBJECT IDENTIFIER ::= { fkSecurityAttackBasicExceptList 3 }

		
		-- 1.3.6.1.4.1.10428 9 1.101.7.9.1.3.3.1
		fkSecurityAttackBasicExceptListCreated NOTIFICATION-TYPE
			OBJECTS { fkSecurityAttackBasicExceptListControlRequest, fkSecurityAttackBasicExceptListControlTimeStamp, fkSecurityAttackBasicExceptListControlReqResult, fkSecurityAttackBasicExceptListControlProtocolType, fkSecurityAttackBasicExceptListControlSourceIpAddress, 
				fkSecurityAttackBasicExceptListControlDestinationIpAddress, fkSecurityAttackBasicExceptListControlIngressPort }
			STATUS current
			DESCRIPTION 
				"createSecurityAttackBasicExceptList"
			::= { fkSecurityAttackBasicExceptListNotification 1 }

		
		-- 1.3.6.1.4.1.10428 9 1.101.7.9.1.3.3.2
		fkSecurityAttackBasicExceptListChanged NOTIFICATION-TYPE
			OBJECTS { fkSecurityAttackBasicExceptListControlRequest, fkSecurityAttackBasicExceptListControlTimeStamp, fkSecurityAttackBasicExceptListControlReqResult, fkSecurityAttackBasicExceptListControlRuleIndex, fkSecurityAttackBasicExceptListControlProtocolType, 
				fkSecurityAttackBasicExceptListControlSourceIpAddress, fkSecurityAttackBasicExceptListControlDestinationIpAddress, fkSecurityAttackBasicExceptListControlIngressPort }
			STATUS current
			DESCRIPTION 
				"modifySecurityAttackBasicExceptList"
			::= { fkSecurityAttackBasicExceptListNotification 2 }

		
		-- 1.3.6.1.4.1.10428 9 1.101.7.9.1.3.3.3
		fkSecurityAttackBasicExceptListDeleted NOTIFICATION-TYPE
			OBJECTS { fkSecurityAttackBasicExceptListControlRequest, fkSecurityAttackBasicExceptListControlTimeStamp, fkSecurityAttackBasicExceptListControlReqResult, fkSecurityAttackBasicExceptListControlRuleIndex }
			STATUS current
			DESCRIPTION 
				"delSecurityAttackBasicExceptList"
			::= { fkSecurityAttackBasicExceptListNotification 3 }

		
		-- 1.3.6.1.4.1.10428 9 1.101.7.9.1.4
		fkSecurityAttackBasicBlackList OBJECT IDENTIFIER ::= { fkSecurityAttackBasic 4 }

		
		-- 1.3.6.1.4.1.10428 9 1.101.7.9.1.4.1
		fkSecurityAttackBasicBlackListTable OBJECT-TYPE
			SYNTAX SEQUENCE OF FkSecurityAttackBasicBlackListEntry
			MAX-ACCESS not-accessible
			STATUS current
			DESCRIPTION
				"Description."
			::= { fkSecurityAttackBasicBlackList 1 }

		
		-- 1.3.6.1.4.1.10428 9 1.101.7.9.1.4.1.1
		fkSecurityAttackBasicBlackListEntry OBJECT-TYPE
			SYNTAX FkSecurityAttackBasicBlackListEntry
			MAX-ACCESS not-accessible
			STATUS current
			DESCRIPTION
				"Description."
			INDEX { fkSecurityAttackBasicExceptListIndex }
			::= { fkSecurityAttackBasicBlackListTable 1 }

		
		FkSecurityAttackBasicBlackListEntry ::=
			SEQUENCE { 
				fkSecurityAttackBasicBlackListIndex
					Integer32,
				fkSecurityAttackBasicBlackListProtocolType
					INTEGER,
				fkSecurityAttackBasicBlackListSourceIpAddress
					IpAddress,
				fkSecurityAttackBasicBlackListDestinationIpAddress
					IpAddress,
				fkSecurityAttackBasicBlackListBlockingStatus
					INTEGER,
				fkSecurityAttackBasicBlackListIgressPort
					Integer32
			 }

		-- 1.3.6.1.4.1.10428 9 1.101.7.9.1.4.1.1.1
		fkSecurityAttackBasicBlackListIndex OBJECT-TYPE
			SYNTAX Integer32 (1..65535)
			MAX-ACCESS read-only
			STATUS current
			DESCRIPTION
				"The Rule index."
			::= { fkSecurityAttackBasicBlackListEntry 1 }

		
		-- 1.3.6.1.4.1.10428 9 1.101.7.9.1.4.1.1.2
		fkSecurityAttackBasicBlackListProtocolType OBJECT-TYPE
			SYNTAX INTEGER
				{
				any(0),
				tcp(1),
				udp(2),
				icmp(3)
				}
			MAX-ACCESS read-only
			STATUS current
			DESCRIPTION
				"The protocol type"
			::= { fkSecurityAttackBasicBlackListEntry 2 }

		
		-- 1.3.6.1.4.1.10428 9 1.101.7.9.1.4.1.1.3
		fkSecurityAttackBasicBlackListSourceIpAddress OBJECT-TYPE
			SYNTAX IpAddress
			MAX-ACCESS read-only
			STATUS current
			DESCRIPTION
				"The source IP address "
			::= { fkSecurityAttackBasicBlackListEntry 3 }

		
		-- 1.3.6.1.4.1.10428 9 1.101.7.9.1.4.1.1.4
		fkSecurityAttackBasicBlackListDestinationIpAddress OBJECT-TYPE
			SYNTAX IpAddress
			MAX-ACCESS read-only
			STATUS current
			DESCRIPTION
				"The destination IP address "
			::= { fkSecurityAttackBasicBlackListEntry 4 }

		
		-- 1.3.6.1.4.1.10428 9 1.101.7.9.1.4.1.1.5
		fkSecurityAttackBasicBlackListBlockingStatus OBJECT-TYPE
			SYNTAX INTEGER
				{
				disable(0),
				enable(1)
				}
			MAX-ACCESS read-only
			STATUS current
			DESCRIPTION
				"The blocking status."
			::= { fkSecurityAttackBasicBlackListEntry 5 }

		
		-- 1.3.6.1.4.1.10428 9 1.101.7.9.1.4.1.1.6
		fkSecurityAttackBasicBlackListIgressPort OBJECT-TYPE
			SYNTAX Integer32
			MAX-ACCESS read-only
			STATUS current
			DESCRIPTION
				"The engress port
				"
			::= { fkSecurityAttackBasicBlackListEntry 6 }

		
		-- 1.3.6.1.4.1.10428 9 1.101.7.9.1.4.2
		fkSecurityAttackBasicBlackListControl OBJECT IDENTIFIER ::= { fkSecurityAttackBasicBlackList 2 }

		
		-- 1.3.6.1.4.1.10428 9 1.101.7.9.1.4.2.1
		fkSecurityAttackBasicBlackListControlRequest OBJECT-TYPE
			SYNTAX INTEGER
				{
				createSecurityAttackBasicBlackList(1),
				delSecurityAttackBasicBlackList(2)
				}
			MAX-ACCESS read-write
			STATUS current
			DESCRIPTION
				"Description"
			::= { fkSecurityAttackBasicBlackListControl 1 }

		
		-- 1.3.6.1.4.1.10428 9 1.101.7.9.1.4.2.2
		fkSecurityAttackBasicBlackListControlStatus OBJECT-TYPE
			SYNTAX FkControlStatusType
			MAX-ACCESS read-only
			STATUS current
			DESCRIPTION
				"Description"
			::= { fkSecurityAttackBasicBlackListControl 2 }

		
		-- 1.3.6.1.4.1.10428 9 1.101.7.9.1.4.2.3
		fkSecurityAttackBasicBlackListControlTimer OBJECT-TYPE
			SYNTAX Gauge32
			MAX-ACCESS read-write
			STATUS current
			DESCRIPTION
				"Description"
			::= { fkSecurityAttackBasicBlackListControl 3 }

		
		-- 1.3.6.1.4.1.10428 9 1.101.7.9.1.4.2.4
		fkSecurityAttackBasicBlackListControlTimeStamp OBJECT-TYPE
			SYNTAX TimeTicks
			MAX-ACCESS read-only
			STATUS current
			DESCRIPTION
				"Description"
			::= { fkSecurityAttackBasicBlackListControl 4 }

		
		-- 1.3.6.1.4.1.10428 9 1.101.7.9.1.4.2.5
		fkSecurityAttackBasicBlackListControlReqResult OBJECT-TYPE
			SYNTAX FkControlRequestResultType
			MAX-ACCESS read-only
			STATUS current
			DESCRIPTION
				"Result of the last command."
			::= { fkSecurityAttackBasicBlackListControl 5 }

		
		-- 1.3.6.1.4.1.10428 9 1.101.7.9.1.4.2.6
		fkSecurityAttackBasicBlackListControlRuleIndex OBJECT-TYPE
			SYNTAX Integer32
			MAX-ACCESS read-write
			STATUS current
			DESCRIPTION
				"The rule index of except list. It’s specific nuber per each rule."
			::= { fkSecurityAttackBasicBlackListControl 6 }

		
		-- 1.3.6.1.4.1.10428 9 1.101.7.9.1.4.2.7
		fkSecurityAttackBasicBlackListControlProtocolType OBJECT-TYPE
			SYNTAX INTEGER
				{
				any(0),
				tcp(1),
				udp(2),
				icmp(3)
				}
			MAX-ACCESS read-write
			STATUS current
			DESCRIPTION
				"The port attack block time (default:300 sec)"
			::= { fkSecurityAttackBasicBlackListControl 7 }

		
		-- 1.3.6.1.4.1.10428 9 1.101.7.9.1.4.2.8
		fkSecurityAttackBasicBlackListControlSourceIpAddress OBJECT-TYPE
			SYNTAX IpAddress
			MAX-ACCESS read-write
			STATUS current
			DESCRIPTION
				"Description."
			::= { fkSecurityAttackBasicBlackListControl 8 }

		
		-- 1.3.6.1.4.1.10428 9 1.101.7.9.1.4.2.9
		fkSecurityAttackBasicBlackListControlDestinationIpAddress OBJECT-TYPE
			SYNTAX IpAddress
			MAX-ACCESS read-write
			STATUS current
			DESCRIPTION
				"Description."
			::= { fkSecurityAttackBasicBlackListControl 9 }

		
--  1.3.6.1.4.1.10428 9 1.101.7.9.1.4.2.10
		-- 1.3.6.1.4.1.10428 9 1.101.7.9.1.4.2.10
		fkSecurityAttackBasicBlackListControlIngressPort OBJECT-TYPE
			SYNTAX Integer32
			MAX-ACCESS read-write
			STATUS current
			DESCRIPTION
				"The engress port"
			::= { fkSecurityAttackBasicBlackListControl 10 }

		
		-- 1.3.6.1.4.1.10428 9 1.101.7.9.1.4.3
		fkSecurityAttackBasicBlackListNotification OBJECT IDENTIFIER ::= { fkSecurityAttackBasicBlackList 3 }

		
		-- 1.3.6.1.4.1.10428 9 1.101.7.9.1.4.3.1
		fkSecurityAttackBasicBlackListCreated NOTIFICATION-TYPE
			OBJECTS { fkSecurityAttackBasicBlackListControlRequest, fkSecurityAttackBasicBlackListControlTimeStamp, fkSecurityAttackBasicBlackListControlReqResult, fkSecurityAttackBasicBlackListControlRuleIndex, fkSecurityAttackBasicBlackListControlProtocolType, 
				fkSecurityAttackBasicBlackListControlSourceIpAddress, fkSecurityAttackBasicBlackListControlDestinationIpAddress, fkSecurityAttackBasicBlackListControlIngressPort }
			STATUS current
			DESCRIPTION 
				"createSecurityAttackBasicBlackList"
			::= { fkSecurityAttackBasicBlackListNotification 1 }

		
		-- 1.3.6.1.4.1.10428 9 1.101.7.9.1.4.3.2
		fkSecurityAttackBasicBlackListDeleted NOTIFICATION-TYPE
			OBJECTS { fkSecurityAttackBasicBlackListControlRequest, fkSecurityAttackBasicBlackListControlTimeStamp, fkSecurityAttackBasicBlackListControlReqResult, fkSecurityAttackBasicBlackListControlRuleIndex }
			STATUS current
			DESCRIPTION 
				"setSecurityAttackBasicBlackList"
			::= { fkSecurityAttackBasicBlackListNotification 2 }

		
		-- 1.3.6.1.4.1.10428 9 1.101.7.9.1.5
		fkSecurityAttackBasicBlockedList OBJECT IDENTIFIER ::= { fkSecurityAttackBasic 5 }

		
		-- 1.3.6.1.4.1.10428 9 1.101.7.9.1.5.1
		fkSecurityAttackBasicBlockedListTable OBJECT-TYPE
			SYNTAX SEQUENCE OF FkSecurityAttackBasicBlockedListEntry
			MAX-ACCESS not-accessible
			STATUS current
			DESCRIPTION
				"Description."
			::= { fkSecurityAttackBasicBlockedList 1 }

		
		-- 1.3.6.1.4.1.10428 9 1.101.7.9.1.5.1.1
		fkSecurityAttackBasicBlockedListEntry OBJECT-TYPE
			SYNTAX FkSecurityAttackBasicBlockedListEntry
			MAX-ACCESS not-accessible
			STATUS current
			DESCRIPTION
				"Description."
			INDEX { fkSecurityAttackBasicBlockedListIndex }
			::= { fkSecurityAttackBasicBlockedListTable 1 }

		
		FkSecurityAttackBasicBlockedListEntry ::=
			SEQUENCE { 
				fkSecurityAttackBasicBlockedListIndex
					Integer32,
				fkSecurityAttackBasicBlockedListAttackType
					INTEGER,
				fkSecurityAttackBasicBlockedListStartTime
					OCTET STRING,
				fkSecurityAttackBasicBlockedListEndTime
					OCTET STRING,
				fkSecurityAttackBasicBlockedListAttackSourceIp
					IpAddress,
				fkSecurityAttackBasicBlockedListAttackDestinationIp
					IpAddress,
				fkSecurityAttackBasicBlockedListProtocol
					INTEGER,
				fkSecurityAttackBasicBlockedListAttackPktCount
					Counter32,
				fkSecurityAttackBasicBlockedListAttackBlockTime
					Integer32,
				fkSecurityAttackBasicBlockedListBlackListIndex
					Integer32,
				fkSecurityAttackBasicBlockedListIgressPort
					Integer32
			 }

		-- 1.3.6.1.4.1.10428 9 1.101.7.9.1.5.1.1.1
		fkSecurityAttackBasicBlockedListIndex OBJECT-TYPE
			SYNTAX Integer32 (1..65535)
			MAX-ACCESS read-only
			STATUS current
			DESCRIPTION
				"The Rule index."
			::= { fkSecurityAttackBasicBlockedListEntry 1 }

		
		-- 1.3.6.1.4.1.10428 9 1.101.7.9.1.5.1.1.2
		fkSecurityAttackBasicBlockedListAttackType OBJECT-TYPE
			SYNTAX INTEGER
				{
				none(0),
				tcpDosAttack(1),
				udpDosAttack(2),
				icmpDosAttack(3),
				hostScan(4),
				portScan(5),
				staticAttack(6)
				}
			MAX-ACCESS read-only
			STATUS current
			DESCRIPTION
				"The port attack type"
			::= { fkSecurityAttackBasicBlockedListEntry 2 }

		
		-- 1.3.6.1.4.1.10428 9 1.101.7.9.1.5.1.1.3
		fkSecurityAttackBasicBlockedListStartTime OBJECT-TYPE
			SYNTAX OCTET STRING
			MAX-ACCESS read-only
			STATUS current
			DESCRIPTION
				"The start time."
			::= { fkSecurityAttackBasicBlockedListEntry 3 }

		
		-- 1.3.6.1.4.1.10428 9 1.101.7.9.1.5.1.1.4
		fkSecurityAttackBasicBlockedListEndTime OBJECT-TYPE
			SYNTAX OCTET STRING
			MAX-ACCESS read-only
			STATUS current
			DESCRIPTION
				"The End Time"
			::= { fkSecurityAttackBasicBlockedListEntry 4 }

		
		-- 1.3.6.1.4.1.10428 9 1.101.7.9.1.5.1.1.5
		fkSecurityAttackBasicBlockedListAttackSourceIp OBJECT-TYPE
			SYNTAX IpAddress
			MAX-ACCESS read-only
			STATUS current
			DESCRIPTION
				"The attack source ip address"
			::= { fkSecurityAttackBasicBlockedListEntry 5 }

		
		-- 1.3.6.1.4.1.10428 9 1.101.7.9.1.5.1.1.6
		fkSecurityAttackBasicBlockedListAttackDestinationIp OBJECT-TYPE
			SYNTAX IpAddress
			MAX-ACCESS read-only
			STATUS current
			DESCRIPTION
				"The attack Destination ip address"
			::= { fkSecurityAttackBasicBlockedListEntry 6 }

		
		-- 1.3.6.1.4.1.10428 9 1.101.7.9.1.5.1.1.7
		fkSecurityAttackBasicBlockedListProtocol OBJECT-TYPE
			SYNTAX INTEGER
				{
				any(0),
				tcp(1),
				udp(2),
				icmp(3),
				arp(4)
				}
			MAX-ACCESS read-only
			STATUS current
			DESCRIPTION
				"The protocol type."
			::= { fkSecurityAttackBasicBlockedListEntry 7 }

		
		-- 1.3.6.1.4.1.10428 9 1.101.7.9.1.5.1.1.8
		fkSecurityAttackBasicBlockedListAttackPktCount OBJECT-TYPE
			SYNTAX Counter32
			MAX-ACCESS read-only
			STATUS current
			DESCRIPTION
				"The attack packet per second."
			::= { fkSecurityAttackBasicBlockedListEntry 8 }

		
		-- 1.3.6.1.4.1.10428 9 1.101.7.9.1.5.1.1.9
		fkSecurityAttackBasicBlockedListAttackBlockTime OBJECT-TYPE
			SYNTAX Integer32 (10..86400)
			MAX-ACCESS read-only
			STATUS current
			DESCRIPTION
				"The attack block time."
			::= { fkSecurityAttackBasicBlockedListEntry 9 }

		
		-- 1.3.6.1.4.1.10428 9 1.101.7.9.1.5.1.1.10
		fkSecurityAttackBasicBlockedListBlackListIndex OBJECT-TYPE
			SYNTAX Integer32
			MAX-ACCESS read-only
			STATUS current
			DESCRIPTION
				"The Black list index."
			::= { fkSecurityAttackBasicBlockedListEntry 10 }

		
		-- 1.3.6.1.4.1.10428 9 1.101.7.9.1.5.1.1.11
		fkSecurityAttackBasicBlockedListIgressPort OBJECT-TYPE
			SYNTAX Integer32
			MAX-ACCESS read-only
			STATUS current
			DESCRIPTION
				"The engress port
				"
			::= { fkSecurityAttackBasicBlockedListEntry 11 }

		
		-- 1.3.6.1.4.1.10428 9 1.101.7.9.1.5.2
		fkSecurityAttackBasicBlockedListControl OBJECT IDENTIFIER ::= { fkSecurityAttackBasicBlockedList 2 }

		
		-- 1.3.6.1.4.1.10428 9 1.101.7.9.1.5.2.1
		fkSecurityAttackBasicBlockedListControlRequest OBJECT-TYPE
			SYNTAX INTEGER
				{
				setSecurityAttackBasicBlockTime(1),
				delSecurityAttackBasicBlockList(2)
				}
			MAX-ACCESS read-write
			STATUS current
			DESCRIPTION
				"Description"
			::= { fkSecurityAttackBasicBlockedListControl 1 }

		
		-- 1.3.6.1.4.1.10428 9 1.101.7.9.1.5.2.2
		fkSecurityAttackBasicBlockedListControlStatus OBJECT-TYPE
			SYNTAX FkControlStatusType
			MAX-ACCESS read-only
			STATUS current
			DESCRIPTION
				"Description"
			::= { fkSecurityAttackBasicBlockedListControl 2 }

		
		-- 1.3.6.1.4.1.10428 9 1.101.7.9.1.5.2.3
		fkSecurityAttackBasicBlockedListControlTimer OBJECT-TYPE
			SYNTAX Gauge32
			MAX-ACCESS read-write
			STATUS current
			DESCRIPTION
				"Description"
			::= { fkSecurityAttackBasicBlockedListControl 3 }

		
		-- 1.3.6.1.4.1.10428 9 1.101.7.9.1.5.2.4
		fkSecurityAttackBasicBlockedListControlTimeStamp OBJECT-TYPE
			SYNTAX TimeTicks
			MAX-ACCESS read-only
			STATUS current
			DESCRIPTION
				"Description"
			::= { fkSecurityAttackBasicBlockedListControl 4 }

		
		-- 1.3.6.1.4.1.10428 9 1.101.7.9.1.5.2.5
		fkSecurityAttackBasicBlockedListControlReqResult OBJECT-TYPE
			SYNTAX FkControlRequestResultType
			MAX-ACCESS read-only
			STATUS current
			DESCRIPTION
				"Result of the last command."
			::= { fkSecurityAttackBasicBlockedListControl 5 }

		
		-- 1.3.6.1.4.1.10428 9 1.101.7.9.1.5.2.6
		fkSecurityAttackBasicBlockedListControlRuleIndex OBJECT-TYPE
			SYNTAX Integer32
			MAX-ACCESS read-write
			STATUS current
			DESCRIPTION
				"The Rule index of blocked list. It’s specific nuber per each rule."
			::= { fkSecurityAttackBasicBlockedListControl 6 }

		
		-- 1.3.6.1.4.1.10428 9 1.101.7.9.1.5.2.7
		fkSecurityAttackBasicBlockedListControlBlockTime OBJECT-TYPE
			SYNTAX Integer32 (10..86400)
			MAX-ACCESS read-write
			STATUS current
			DESCRIPTION
				"The port attack block time "
			::= { fkSecurityAttackBasicBlockedListControl 7 }

		
		-- 1.3.6.1.4.1.10428 9 1.101.7.9.1.5.3
		fkSecurityAttackBasicBlockedListNotification OBJECT IDENTIFIER ::= { fkSecurityAttackBasicBlockedList 3 }

		
		-- 1.3.6.1.4.1.10428 9 1.101.7.9.1.5.3.1
		fkSecurityAttackBasicBlockedListBlockTimeChanged NOTIFICATION-TYPE
			OBJECTS { fkSecurityAttackBasicBlockedListControlRequest, fkSecurityAttackBasicBlockedListControlTimeStamp, fkSecurityAttackBasicBlockedListControlReqResult, fkSecurityAttackBasicBlockedListControlRuleIndex, fkSecurityAttackBasicBlockedListControlBlockTime }
			STATUS current
			DESCRIPTION 
				"setSecurityAttackBasicBlockTime"
			::= { fkSecurityAttackBasicBlockedListNotification 1 }

		
		-- 1.3.6.1.4.1.10428 9 1.101.7.9.1.5.3.2
		fkSecurityAttackBasicBlockedListDeleted NOTIFICATION-TYPE
			OBJECTS { fkSecurityAttackBasicBlockedListControlRequest, fkSecurityAttackBasicBlockedListControlTimeStamp, fkSecurityAttackBasicBlockedListControlReqResult, fkSecurityAttackBasicBlockedListControlRuleIndex }
			STATUS current
			DESCRIPTION 
				"delSecurityAttackBasicBlockList"
			::= { fkSecurityAttackBasicBlockedListNotification 2 }

		
-- by port index.
		-- 1.3.6.1.4.1.10428 9 1.101.7.9.2
		fkSecurityAttackExpansion OBJECT IDENTIFIER ::= { fkSecurityAttack 2 }

		
		-- 1.3.6.1.4.1.10428 9 1.101.7.9.2.1
		fkSecurityAttackExpansionBase OBJECT IDENTIFIER ::= { fkSecurityAttackExpansion 1 }

		
		-- 1.3.6.1.4.1.10428 9 1.101.7.9.2.1.1
		fkSecurityAttackExpansionBaseInfo OBJECT IDENTIFIER ::= { fkSecurityAttackExpansionBase 1 }

		
		-- 1.3.6.1.4.1.10428 9 1.101.7.9.2.1.1.1
		fkSecurityAttackExpansionBaseGlobalStatus OBJECT-TYPE
			SYNTAX INTEGER
				{
				disable(0),
				enable(1)
				}
			MAX-ACCESS read-only
			STATUS current
			DESCRIPTION
				"The port attack global status."
			::= { fkSecurityAttackExpansionBaseInfo 1 }

		
		-- 1.3.6.1.4.1.10428 9 1.101.7.9.2.1.2
		fkSecurityAttackExpansionBaseControl OBJECT IDENTIFIER ::= { fkSecurityAttackExpansionBase 2 }

		
		-- 1.3.6.1.4.1.10428 9 1.101.7.9.2.1.2.1
		fkSecurityAttackExpansionBaseControlRequest OBJECT-TYPE
			SYNTAX INTEGER { setSecurityAttackExpansionGlobalStatus(1) }
			MAX-ACCESS read-write
			STATUS current
			DESCRIPTION
				"Description"
			::= { fkSecurityAttackExpansionBaseControl 1 }

		
		-- 1.3.6.1.4.1.10428 9 1.101.7.9.2.1.2.2
		fkSecurityAttackExpansionBaseControlStatus OBJECT-TYPE
			SYNTAX FkControlStatusType
			MAX-ACCESS read-only
			STATUS current
			DESCRIPTION
				"Description"
			::= { fkSecurityAttackExpansionBaseControl 2 }

		
		-- 1.3.6.1.4.1.10428 9 1.101.7.9.2.1.2.3
		fkSecurityAttackExpansionBaseControlTimer OBJECT-TYPE
			SYNTAX Gauge32
			MAX-ACCESS read-write
			STATUS current
			DESCRIPTION
				"Description"
			::= { fkSecurityAttackExpansionBaseControl 3 }

		
		-- 1.3.6.1.4.1.10428 9 1.101.7.9.2.1.2.4
		fkSecurityAttackExpansionBaseControlTimeStamp OBJECT-TYPE
			SYNTAX TimeTicks
			MAX-ACCESS read-only
			STATUS current
			DESCRIPTION
				"Description"
			::= { fkSecurityAttackExpansionBaseControl 4 }

		
		-- 1.3.6.1.4.1.10428 9 1.101.7.9.2.1.2.5
		fkSecurityAttackExpansionBaseControlReqResult OBJECT-TYPE
			SYNTAX FkControlRequestResultType
			MAX-ACCESS read-only
			STATUS current
			DESCRIPTION
				"Result of the last command."
			::= { fkSecurityAttackExpansionBaseControl 5 }

		
		-- 1.3.6.1.4.1.10428 9 1.101.7.9.2.1.2.6
		fkSecurityAttackExpansionBaseControlGlobalStatus OBJECT-TYPE
			SYNTAX INTEGER
				{
				disable(0),
				enable(1)
				}
			MAX-ACCESS read-write
			STATUS current
			DESCRIPTION
				"The port attack global status."
			::= { fkSecurityAttackExpansionBaseControl 6 }

		
		-- 1.3.6.1.4.1.10428 9 1.101.7.9.2.1.3
		fkSecurityAttackExpansionBaseNotification OBJECT IDENTIFIER ::= { fkSecurityAttackExpansionBase 3 }

		
		-- 1.3.6.1.4.1.10428 9 1.101.7.9.2.1.3.1
		fkSecurityAttackExpansionBaseGlobalStatusChanged NOTIFICATION-TYPE
			OBJECTS { fkSecurityAttackExpansionBaseControlRequest, fkSecurityAttackExpansionBaseControlTimeStamp, fkSecurityAttackExpansionBaseControlReqResult, fkSecurityAttackExpansionBaseControlGlobalStatus }
			STATUS current
			DESCRIPTION 
				"setSecurityAttackExpansionGlobalStatus"
			::= { fkSecurityAttackExpansionBaseNotification 1 }

		
		-- 1.3.6.1.4.1.10428 9 1.101.7.9.2.2
		fkSecurityAttackExpansionPolicy OBJECT IDENTIFIER ::= { fkSecurityAttackExpansion 2 }

		
		-- 1.3.6.1.4.1.10428 9 1.101.7.9.2.2.1
		fkSecurityAttackExpansionPolicyTable OBJECT-TYPE
			SYNTAX SEQUENCE OF FkSecurityAttackExpansionPolicyEntry
			MAX-ACCESS not-accessible
			STATUS current
			DESCRIPTION
				"Description."
			::= { fkSecurityAttackExpansionPolicy 1 }

		
		-- 1.3.6.1.4.1.10428 9 1.101.7.9.2.2.1.1
		fkSecurityAttackExpansionPolicyEntry OBJECT-TYPE
			SYNTAX FkSecurityAttackExpansionPolicyEntry
			MAX-ACCESS not-accessible
			STATUS current
			DESCRIPTION
				"Description."
			INDEX { fkSecurityAttackExpansionPolicyPortIndex }
			::= { fkSecurityAttackExpansionPolicyTable 1 }

		
		FkSecurityAttackExpansionPolicyEntry ::=
			SEQUENCE { 
				fkSecurityAttackExpansionPolicyPortIndex
					Integer32,
				fkSecurityAttackExpansionPolicyStatus
					INTEGER,
				fkSecurityAttackExpansionPolicyAttackType
					BITS,
				fkSecurityAttackExpansionPolicyBlockTime
					OCTET STRING
			 }

		-- 1.3.6.1.4.1.10428 9 1.101.7.9.2.2.1.1.1
		fkSecurityAttackExpansionPolicyPortIndex OBJECT-TYPE
			SYNTAX Integer32 (1..65535)
			MAX-ACCESS read-only
			STATUS current
			DESCRIPTION
				"The Port Index."
			::= { fkSecurityAttackExpansionPolicyEntry 1 }

		
		-- 1.3.6.1.4.1.10428 9 1.101.7.9.2.2.1.1.2
		fkSecurityAttackExpansionPolicyStatus OBJECT-TYPE
			SYNTAX INTEGER
				{
				disable(0),
				enable(1)
				}
			MAX-ACCESS read-write
			STATUS current
			DESCRIPTION
				"The Port attack feature status(This OID is only for GET)."
			::= { fkSecurityAttackExpansionPolicyEntry 2 }

		
		-- 1.3.6.1.4.1.10428 9 1.101.7.9.2.2.1.1.3
		fkSecurityAttackExpansionPolicyAttackType OBJECT-TYPE
			SYNTAX BITS
				{
				none(0),
				tcpDosAttack(1),
				tcpPortFlooding(2),
				tcpHostRandomFlooding(3),
				tcpHostScanning(4),
				ipSppfing(5),
				udpDosAttack(6),
				udpPortFlooding(7),
				udpHostRandomFlooding(8),
				udpHostScanning(9),
				udpIPSppfing(10),
				icmpDosAttack(11),
				icmpIPSppfing(12),
				icmpHostScanning(13),
				arpMacFlooding(14),
				arpSpoofing(15),
				decoySnare(16),
				hostScan(17),
				portScan(18),
				tcpPortScanning(19),
				udpPortScanning(20),
				staticAttack(21)
				}
			MAX-ACCESS read-only
			STATUS current
			DESCRIPTION
				"The policy status of port attack type."
			::= { fkSecurityAttackExpansionPolicyEntry 3 }

		
		-- 1.3.6.1.4.1.10428 9 1.101.7.9.2.2.1.1.4
		fkSecurityAttackExpansionPolicyBlockTime OBJECT-TYPE
			SYNTAX OCTET STRING
			MAX-ACCESS read-only
			STATUS current
			DESCRIPTION
				"The block time of port attack. (10-86400 sec)"
			::= { fkSecurityAttackExpansionPolicyEntry 4 }

		
		-- 1.3.6.1.4.1.10428 9 1.101.7.9.2.2.2
		fkSecurityAttackExpansionPolicyControl OBJECT IDENTIFIER ::= { fkSecurityAttackExpansionPolicy 2 }

		
		-- 1.3.6.1.4.1.10428 9 1.101.7.9.2.2.2.1
		fkSecurityAttackExpansionPolicyControlRequest OBJECT-TYPE
			SYNTAX INTEGER { setSecurityAttackExpansionPolicy(1) }
			MAX-ACCESS read-write
			STATUS current
			DESCRIPTION
				"Description"
			::= { fkSecurityAttackExpansionPolicyControl 1 }

		
		-- 1.3.6.1.4.1.10428 9 1.101.7.9.2.2.2.2
		fkSecurityAttackExpansionPolicyControlStatus OBJECT-TYPE
			SYNTAX FkControlStatusType
			MAX-ACCESS read-only
			STATUS current
			DESCRIPTION
				"Description"
			::= { fkSecurityAttackExpansionPolicyControl 2 }

		
		-- 1.3.6.1.4.1.10428 9 1.101.7.9.2.2.2.3
		fkSecurityAttackExpansionPolicyControlTimer OBJECT-TYPE
			SYNTAX Gauge32
			MAX-ACCESS read-write
			STATUS current
			DESCRIPTION
				"Description"
			::= { fkSecurityAttackExpansionPolicyControl 3 }

		
		-- 1.3.6.1.4.1.10428 9 1.101.7.9.2.2.2.4
		fkSecurityAttackExpansionPolicyControlTimeStamp OBJECT-TYPE
			SYNTAX TimeTicks
			MAX-ACCESS read-only
			STATUS current
			DESCRIPTION
				"Description"
			::= { fkSecurityAttackExpansionPolicyControl 4 }

		
		-- 1.3.6.1.4.1.10428 9 1.101.7.9.2.2.2.5
		fkSecurityAttackExpansionPolicyControlReqResult OBJECT-TYPE
			SYNTAX FkControlRequestResultType
			MAX-ACCESS read-only
			STATUS current
			DESCRIPTION
				"Result of the last command."
			::= { fkSecurityAttackExpansionPolicyControl 5 }

		
		-- 1.3.6.1.4.1.10428 9 1.101.7.9.2.2.2.6
		fkSecurityAttackExpansionPolicyControlPortIndex OBJECT-TYPE
			SYNTAX Integer32
			MAX-ACCESS read-write
			STATUS current
			DESCRIPTION
				"The port index."
			::= { fkSecurityAttackExpansionPolicyControl 6 }

		
		-- 1.3.6.1.4.1.10428 9 1.101.7.9.2.2.2.7
		fkSecurityAttackExpansionPolicyControlAttackType OBJECT-TYPE
			SYNTAX BITS
				{
				none(0),
				tcpDosAttack(1),
				tcpPortFlooding(2),
				tcpHostRandomFlooding(3),
				tcpHostScanning(4),
				ipSppfing(5),
				udpDosAttack(6),
				udpPortFlooding(7),
				udpHostRandomFlooding(8),
				udpHostScanning(9),
				udpIPSppfing(10),
				icmpDosAttack(11),
				icmpIPSppfing(12),
				icmpHostScanning(13),
				arpMacFlooding(14),
				arpSpoofing(15),
				decoySnare(16),
				hostScan(17),
				portScan(18),
				tcpPortScanning(19),
				udpPortScanning(20),
				staticAttack(21)
				}
			MAX-ACCESS read-write
			STATUS current
			DESCRIPTION
				"The port attack type."
			::= { fkSecurityAttackExpansionPolicyControl 7 }

		
		-- 1.3.6.1.4.1.10428 9 1.101.7.9.2.2.2.8
		fkSecurityAttackExpansionPolicyControlBlockTime OBJECT-TYPE
			SYNTAX OCTET STRING
			MAX-ACCESS read-write
			STATUS current
			DESCRIPTION
				"The block time of port attack. (10-86400 sec)"
			::= { fkSecurityAttackExpansionPolicyControl 8 }

		
		-- 1.3.6.1.4.1.10428 9 1.101.7.9.2.2.3
		fkSecurityAttackExpansionPolicyNotification OBJECT IDENTIFIER ::= { fkSecurityAttackExpansionPolicy 3 }

		
		-- 1.3.6.1.4.1.10428 9 1.101.7.9.2.2.3.1
		fkSecurityAttackExpansionPolicyChanged NOTIFICATION-TYPE
			OBJECTS { fkSecurityAttackExpansionPolicyControlRequest, fkSecurityAttackExpansionPolicyControlTimeStamp, fkSecurityAttackExpansionPolicyControlReqResult, fkSecurityAttackExpansionPolicyControlPortIndex, fkSecurityAttackExpansionPolicyControlAttackType, 
				fkSecurityAttackExpansionPolicyControlBlockTime }
			STATUS current
			DESCRIPTION 
				"setSecurityAttackExpansionPolicy"
			::= { fkSecurityAttackExpansionPolicyNotification 1 }

		
		-- 1.3.6.1.4.1.10428 9 1.101.7.9.2.3
		fkSecurityAttackExpansionExceptList OBJECT IDENTIFIER ::= { fkSecurityAttackExpansion 3 }

		
		-- 1.3.6.1.4.1.10428 9 1.101.7.9.2.3.1
		fkSecurityAttackExpansionExceptListTable OBJECT-TYPE
			SYNTAX SEQUENCE OF FkSecurityAttackExpansionExceptListEntry
			MAX-ACCESS not-accessible
			STATUS current
			DESCRIPTION
				"Description."
			::= { fkSecurityAttackExpansionExceptList 1 }

		
		-- 1.3.6.1.4.1.10428 9 1.101.7.9.2.3.1.1
		fkSecurityAttackExpansionExceptListEntry OBJECT-TYPE
			SYNTAX FkSecurityAttackExpansionExceptListEntry
			MAX-ACCESS not-accessible
			STATUS current
			DESCRIPTION
				"Description."
			INDEX { fkSecurityAttackExpansionExceptListPortIndex, fkSecurityAttackExpansionExceptListIndex }
			::= { fkSecurityAttackExpansionExceptListTable 1 }

		
		FkSecurityAttackExpansionExceptListEntry ::=
			SEQUENCE { 
				fkSecurityAttackExpansionExceptListPortIndex
					Integer32,
				fkSecurityAttackExpansionExceptListIndex
					Integer32,
				fkSecurityAttackExpansionExceptListRuleIndex
					Integer32,
				fkSecurityAttackExpansionExceptListProtocolType
					INTEGER,
				fkSecurityAttackExpansionExceptListSourceType
					INTEGER,
				fkSecurityAttackExpansionExceptListSourceIpAddress
					IpAddress,
				fkSecurityAttackExpansionExceptListSourceIpMask
					Integer32,
				fkSecurityAttackExpansionExceptListSourceMac
					OCTET STRING,
				fkSecurityAttackExpansionExceptListSourcePortType
					INTEGER,
				fkSecurityAttackExpansionExceptListSourcePortFrom
					Integer32,
				fkSecurityAttackExpansionExceptListSourcePortTo
					Integer32,
				fkSecurityAttackExpansionExceptListDestinationType
					INTEGER,
				fkSecurityAttackExpansionExceptListDestinationIpAddress
					IpAddress,
				fkSecurityAttackExpansionExceptListDestinationIpMask
					Integer32,
				fkSecurityAttackExpansionExceptListDestinationMac
					OCTET STRING,
				fkSecurityAttackExpansionExceptListDestinationPortType
					INTEGER,
				fkSecurityAttackExpansionExceptListDestinationPortFrom
					Integer32,
				fkSecurityAttackExpansionExceptListDestinationPortTo
					Integer32
			 }

		-- 1.3.6.1.4.1.10428 9 1.101.7.9.2.3.1.1.1
		fkSecurityAttackExpansionExceptListPortIndex OBJECT-TYPE
			SYNTAX Integer32 (1..65535)
			MAX-ACCESS read-only
			STATUS current
			DESCRIPTION
				"The port index."
			::= { fkSecurityAttackExpansionExceptListEntry 1 }

		
		-- 1.3.6.1.4.1.10428 9 1.101.7.9.2.3.1.1.2
		fkSecurityAttackExpansionExceptListIndex OBJECT-TYPE
			SYNTAX Integer32 (1..65535)
			MAX-ACCESS read-only
			STATUS current
			DESCRIPTION
				"The except list index."
			::= { fkSecurityAttackExpansionExceptListEntry 2 }

		
		-- 1.3.6.1.4.1.10428 9 1.101.7.9.2.3.1.1.3
		fkSecurityAttackExpansionExceptListRuleIndex OBJECT-TYPE
			SYNTAX Integer32
			MAX-ACCESS read-only
			STATUS current
			DESCRIPTION
				"The rule index. It’s specific nuber per each rule."
			::= { fkSecurityAttackExpansionExceptListEntry 3 }

		
		-- 1.3.6.1.4.1.10428 9 1.101.7.9.2.3.1.1.4
		fkSecurityAttackExpansionExceptListProtocolType OBJECT-TYPE
			SYNTAX INTEGER
				{
				any(0),
				tcp(1),
				udp(2),
				icmp(3),
				arp(4)
				}
			MAX-ACCESS read-only
			STATUS current
			DESCRIPTION
				"The protocol type"
			::= { fkSecurityAttackExpansionExceptListEntry 4 }

		
		-- 1.3.6.1.4.1.10428 9 1.101.7.9.2.3.1.1.5
		fkSecurityAttackExpansionExceptListSourceType OBJECT-TYPE
			SYNTAX INTEGER
				{
				any(0),
				ip(1),
				mac(2)
				}
			MAX-ACCESS read-only
			STATUS current
			DESCRIPTION
				"The Source Type."
			::= { fkSecurityAttackExpansionExceptListEntry 5 }

		
		-- 1.3.6.1.4.1.10428 9 1.101.7.9.2.3.1.1.6
		fkSecurityAttackExpansionExceptListSourceIpAddress OBJECT-TYPE
			SYNTAX IpAddress
			MAX-ACCESS read-only
			STATUS current
			DESCRIPTION
				"The source IP address "
			::= { fkSecurityAttackExpansionExceptListEntry 6 }

		
		-- 1.3.6.1.4.1.10428 9 1.101.7.9.2.3.1.1.7
		fkSecurityAttackExpansionExceptListSourceIpMask OBJECT-TYPE
			SYNTAX Integer32
			MAX-ACCESS read-only
			STATUS current
			DESCRIPTION
				"The source IP address mask"
			::= { fkSecurityAttackExpansionExceptListEntry 7 }

		
		-- 1.3.6.1.4.1.10428 9 1.101.7.9.2.3.1.1.8
		fkSecurityAttackExpansionExceptListSourceMac OBJECT-TYPE
			SYNTAX OCTET STRING
			MAX-ACCESS read-only
			STATUS current
			DESCRIPTION
				"The source MAC address."
			::= { fkSecurityAttackExpansionExceptListEntry 8 }

		
		-- 1.3.6.1.4.1.10428 9 1.101.7.9.2.3.1.1.9
		fkSecurityAttackExpansionExceptListSourcePortType OBJECT-TYPE
			SYNTAX INTEGER
				{
				any(0),
				equal(1),
				range(2)
				}
			MAX-ACCESS read-only
			STATUS current
			DESCRIPTION
				"The source port type."
			::= { fkSecurityAttackExpansionExceptListEntry 9 }

		
		-- 1.3.6.1.4.1.10428 9 1.101.7.9.2.3.1.1.10
		fkSecurityAttackExpansionExceptListSourcePortFrom OBJECT-TYPE
			SYNTAX Integer32
			MAX-ACCESS read-only
			STATUS current
			DESCRIPTION
				"SourcePort Type is Any then 0
				Equal then portNo
				Range then From PortNo"
			::= { fkSecurityAttackExpansionExceptListEntry 10 }

		
		-- 1.3.6.1.4.1.10428 9 1.101.7.9.2.3.1.1.11
		fkSecurityAttackExpansionExceptListSourcePortTo OBJECT-TYPE
			SYNTAX Integer32
			MAX-ACCESS read-only
			STATUS current
			DESCRIPTION
				"SourcePort Type is Any then 0
				Equal then portNo
				Range then From PortNo"
			::= { fkSecurityAttackExpansionExceptListEntry 11 }

		
		-- 1.3.6.1.4.1.10428 9 1.101.7.9.2.3.1.1.12
		fkSecurityAttackExpansionExceptListDestinationType OBJECT-TYPE
			SYNTAX INTEGER
				{
				any(0),
				ip(1),
				mac(2)
				}
			MAX-ACCESS read-only
			STATUS current
			DESCRIPTION
				"The destination Type."
			::= { fkSecurityAttackExpansionExceptListEntry 12 }

		
		-- 1.3.6.1.4.1.10428 9 1.101.7.9.2.3.1.1.13
		fkSecurityAttackExpansionExceptListDestinationIpAddress OBJECT-TYPE
			SYNTAX IpAddress
			MAX-ACCESS read-only
			STATUS current
			DESCRIPTION
				"The destination IP address "
			::= { fkSecurityAttackExpansionExceptListEntry 13 }

		
		-- 1.3.6.1.4.1.10428 9 1.101.7.9.2.3.1.1.14
		fkSecurityAttackExpansionExceptListDestinationIpMask OBJECT-TYPE
			SYNTAX Integer32
			MAX-ACCESS read-only
			STATUS current
			DESCRIPTION
				"The destination IP address mask"
			::= { fkSecurityAttackExpansionExceptListEntry 14 }

		
		-- 1.3.6.1.4.1.10428 9 1.101.7.9.2.3.1.1.15
		fkSecurityAttackExpansionExceptListDestinationMac OBJECT-TYPE
			SYNTAX OCTET STRING
			MAX-ACCESS read-only
			STATUS current
			DESCRIPTION
				"The source MAC address."
			::= { fkSecurityAttackExpansionExceptListEntry 15 }

		
		-- 1.3.6.1.4.1.10428 9 1.101.7.9.2.3.1.1.16
		fkSecurityAttackExpansionExceptListDestinationPortType OBJECT-TYPE
			SYNTAX INTEGER
				{
				any(0),
				equal(1),
				range(2)
				}
			MAX-ACCESS read-only
			STATUS current
			DESCRIPTION
				"The destination port type."
			::= { fkSecurityAttackExpansionExceptListEntry 16 }

		
		-- 1.3.6.1.4.1.10428 9 1.101.7.9.2.3.1.1.17
		fkSecurityAttackExpansionExceptListDestinationPortFrom OBJECT-TYPE
			SYNTAX Integer32
			MAX-ACCESS read-only
			STATUS current
			DESCRIPTION
				"Destination Port Type is Any then 0
				Equal then portNo
				Range then From PortNo
				"
			::= { fkSecurityAttackExpansionExceptListEntry 17 }

		
		-- 1.3.6.1.4.1.10428 9 1.101.7.9.2.3.1.1.18
		fkSecurityAttackExpansionExceptListDestinationPortTo OBJECT-TYPE
			SYNTAX Integer32
			MAX-ACCESS read-only
			STATUS current
			DESCRIPTION
				"Destination Port Type is Any then 0
				Equal then portNo
				Range then From PortNo
				"
			::= { fkSecurityAttackExpansionExceptListEntry 18 }

		
		-- 1.3.6.1.4.1.10428 9 1.101.7.9.2.3.2
		fkSecurityAttackExpansionExceptListControl OBJECT IDENTIFIER ::= { fkSecurityAttackExpansionExceptList 2 }

		
		-- 1.3.6.1.4.1.10428 9 1.101.7.9.2.3.2.1
		fkSecurityAttackExpansionExceptListControlRequest OBJECT-TYPE
			SYNTAX INTEGER
				{
				createSecurityAttackExpansionExceptList(1),
				modifyPortAttackExpansionExceptList(2),
				delPortAttackExpansionExceptList(3)
				}
			MAX-ACCESS read-write
			STATUS current
			DESCRIPTION
				"Description"
			::= { fkSecurityAttackExpansionExceptListControl 1 }

		
		-- 1.3.6.1.4.1.10428 9 1.101.7.9.2.3.2.2
		fkSecurityAttackExpansionExceptListControlStatus OBJECT-TYPE
			SYNTAX FkControlStatusType
			MAX-ACCESS read-only
			STATUS current
			DESCRIPTION
				"Description"
			::= { fkSecurityAttackExpansionExceptListControl 2 }

		
		-- 1.3.6.1.4.1.10428 9 1.101.7.9.2.3.2.3
		fkSecurityAttackExpansionExceptListControlTimer OBJECT-TYPE
			SYNTAX Gauge32
			MAX-ACCESS read-write
			STATUS current
			DESCRIPTION
				"Description"
			::= { fkSecurityAttackExpansionExceptListControl 3 }

		
		-- 1.3.6.1.4.1.10428 9 1.101.7.9.2.3.2.4
		fkSecurityAttackExpansionExceptListControlTimeStamp OBJECT-TYPE
			SYNTAX TimeTicks
			MAX-ACCESS read-only
			STATUS current
			DESCRIPTION
				"Description"
			::= { fkSecurityAttackExpansionExceptListControl 4 }

		
		-- 1.3.6.1.4.1.10428 9 1.101.7.9.2.3.2.5
		fkSecurityAttackExpansionExceptListControlReqResult OBJECT-TYPE
			SYNTAX FkControlRequestResultType
			MAX-ACCESS read-only
			STATUS current
			DESCRIPTION
				"Result of the last command."
			::= { fkSecurityAttackExpansionExceptListControl 5 }

		
		-- 1.3.6.1.4.1.10428 9 1.101.7.9.2.3.2.6
		fkSecurityAttackExpansionExceptListControlPortIndex OBJECT-TYPE
			SYNTAX Integer32
			MAX-ACCESS read-write
			STATUS current
			DESCRIPTION
				"The port index."
			::= { fkSecurityAttackExpansionExceptListControl 6 }

		
		-- 1.3.6.1.4.1.10428 9 1.101.7.9.2.3.2.7
		fkSecurityAttackExpansionExceptListControlRuleIndex OBJECT-TYPE
			SYNTAX Integer32
			MAX-ACCESS read-write
			STATUS current
			DESCRIPTION
				"The rule index of except list. It’s specific nuber per each rule."
			::= { fkSecurityAttackExpansionExceptListControl 7 }

		
		-- 1.3.6.1.4.1.10428 9 1.101.7.9.2.3.2.8
		fkSecurityAttackExpansionExceptListControlProtocolType OBJECT-TYPE
			SYNTAX INTEGER
				{
				any(0),
				tcp(1),
				udp(2),
				icmp(3),
				arp(4)
				}
			MAX-ACCESS read-write
			STATUS current
			DESCRIPTION
				"The port attack block time (default:300 sec)"
			::= { fkSecurityAttackExpansionExceptListControl 8 }

		
		-- 1.3.6.1.4.1.10428 9 1.101.7.9.2.3.2.9
		fkSecurityAttackExpansionExceptListControlSourceType OBJECT-TYPE
			SYNTAX INTEGER
				{
				any(0),
				ip(1),
				mac(2)
				}
			MAX-ACCESS read-write
			STATUS current
			DESCRIPTION
				"Description."
			::= { fkSecurityAttackExpansionExceptListControl 9 }

		
		-- 1.3.6.1.4.1.10428 9 1.101.7.9.2.3.2.10
		fkSecurityAttackExpansionExceptListControlSourceIpAddress OBJECT-TYPE
			SYNTAX IpAddress
			MAX-ACCESS read-write
			STATUS current
			DESCRIPTION
				"Description."
			::= { fkSecurityAttackExpansionExceptListControl 10 }

		
		-- 1.3.6.1.4.1.10428 9 1.101.7.9.2.3.2.11
		fkSecurityAttackExpansionExceptListControlSourceIpMask OBJECT-TYPE
			SYNTAX Integer32
			MAX-ACCESS read-write
			STATUS current
			DESCRIPTION
				"Description."
			::= { fkSecurityAttackExpansionExceptListControl 11 }

		
		-- 1.3.6.1.4.1.10428 9 1.101.7.9.2.3.2.12
		fkSecurityAttackExpansionExceptListControlSourceMac OBJECT-TYPE
			SYNTAX OCTET STRING
			MAX-ACCESS read-write
			STATUS current
			DESCRIPTION
				"The source MAC address."
			::= { fkSecurityAttackExpansionExceptListControl 12 }

		
		-- 1.3.6.1.4.1.10428 9 1.101.7.9.2.3.2.13
		fkSecurityAttackExpansionExceptListControlSourcePortType OBJECT-TYPE
			SYNTAX INTEGER
				{
				any(0),
				equal(1),
				range(2)
				}
			MAX-ACCESS read-write
			STATUS current
			DESCRIPTION
				"The destination port type."
			::= { fkSecurityAttackExpansionExceptListControl 13 }

		
		-- 1.3.6.1.4.1.10428 9 1.101.7.9.2.3.2.14
		fkSecurityAttackExpansionExceptListControlSourcePortFrom OBJECT-TYPE
			SYNTAX Integer32
			MAX-ACCESS read-write
			STATUS current
			DESCRIPTION
				"Src Port Type is Any then 0
				Equal then portNo
				Range then From PortNo"
			::= { fkSecurityAttackExpansionExceptListControl 14 }

		
		-- 1.3.6.1.4.1.10428 9 1.101.7.9.2.3.2.15
		fkSecurityAttackExpansionExceptListControlSourcePortTo OBJECT-TYPE
			SYNTAX Integer32
			MAX-ACCESS read-write
			STATUS current
			DESCRIPTION
				"Src Port Type is Any then 0
				Equal then portNo
				Range then From PortNo"
			::= { fkSecurityAttackExpansionExceptListControl 15 }

		
		-- 1.3.6.1.4.1.10428 9 1.101.7.9.2.3.2.16
		fkSecurityAttackExpansionExceptListControlDestinationType OBJECT-TYPE
			SYNTAX INTEGER
				{
				any(0),
				ip(1),
				mac(2)
				}
			MAX-ACCESS read-write
			STATUS current
			DESCRIPTION
				"Description."
			::= { fkSecurityAttackExpansionExceptListControl 16 }

		
		-- 1.3.6.1.4.1.10428 9 1.101.7.9.2.3.2.17
		fkSecurityAttackExpansionExceptListControlDestinationIpAddress OBJECT-TYPE
			SYNTAX IpAddress
			MAX-ACCESS read-write
			STATUS current
			DESCRIPTION
				"Description."
			::= { fkSecurityAttackExpansionExceptListControl 17 }

		
		-- 1.3.6.1.4.1.10428 9 1.101.7.9.2.3.2.18
		fkSecurityAttackExpansionExceptListControlDestinationIpMask OBJECT-TYPE
			SYNTAX Integer32
			MAX-ACCESS read-write
			STATUS current
			DESCRIPTION
				"Description."
			::= { fkSecurityAttackExpansionExceptListControl 18 }

		
		-- 1.3.6.1.4.1.10428 9 1.101.7.9.2.3.2.19
		fkSecurityAttackExpansionExceptListControlDestinationMac OBJECT-TYPE
			SYNTAX Integer32
			MAX-ACCESS read-write
			STATUS current
			DESCRIPTION
				"The source MAC address."
			::= { fkSecurityAttackExpansionExceptListControl 19 }

		
		-- 1.3.6.1.4.1.10428 9 1.101.7.9.2.3.2.20
		fkSecurityAttackExpansionExceptListControlDestinationPortType OBJECT-TYPE
			SYNTAX INTEGER
				{
				any(0),
				equal(1),
				range(2)
				}
			MAX-ACCESS read-write
			STATUS current
			DESCRIPTION
				"The destination port type."
			::= { fkSecurityAttackExpansionExceptListControl 20 }

		
		-- 1.3.6.1.4.1.10428 9 1.101.7.9.2.3.2.21
		fkSecurityAttackExpansionExceptListControlDestinationPortFrom OBJECT-TYPE
			SYNTAX Integer32
			MAX-ACCESS read-write
			STATUS current
			DESCRIPTION
				"Src Port Type is Any then 0
				Equal then portNo
				Range then From PortNo"
			::= { fkSecurityAttackExpansionExceptListControl 21 }

		
		-- 1.3.6.1.4.1.10428 9 1.101.7.9.2.3.2.22
		fkSecurityAttackExpansionExceptListControlDestinationPortTo OBJECT-TYPE
			SYNTAX Integer32
			MAX-ACCESS read-write
			STATUS current
			DESCRIPTION
				"Src Port Type is Any then 0
				Equal then portNo
				Range then From PortNo"
			::= { fkSecurityAttackExpansionExceptListControl 22 }

		
		-- 1.3.6.1.4.1.10428 9 1.101.7.9.2.3.3
		fkSecurityAttackExpansionExceptListNotification OBJECT IDENTIFIER ::= { fkSecurityAttackExpansionExceptList 3 }

		
		-- 1.3.6.1.4.1.10428 9 1.101.7.9.2.3.3.1
		fkSecurityAttackExpansionExceptListCreated NOTIFICATION-TYPE
			OBJECTS { fkSecurityAttackExpansionExceptListControlRequest, fkSecurityAttackExpansionExceptListControlTimeStamp, fkSecurityAttackExpansionExceptListControlReqResult, fkSecurityAttackExpansionExceptListControlPortIndex, fkSecurityAttackExpansionExceptListControlProtocolType, 
				fkSecurityAttackExpansionExceptListControlSourceType, fkSecurityAttackExpansionExceptListControlSourceIpAddress, fkSecurityAttackExpansionExceptListControlSourceIpMask, fkSecurityAttackExpansionExceptListControlSourceMac, fkSecurityAttackExpansionExceptListControlSourcePortType, 
				fkSecurityAttackExpansionExceptListControlSourcePortFrom, fkSecurityAttackExpansionExceptListControlSourcePortTo, fkSecurityAttackExpansionExceptListControlDestinationType, fkSecurityAttackExpansionExceptListControlDestinationIpAddress, fkSecurityAttackExpansionExceptListControlDestinationIpMask, 
				fkSecurityAttackExpansionExceptListControlDestinationMac, fkSecurityAttackExpansionExceptListControlDestinationPortType, fkSecurityAttackExpansionExceptListControlDestinationPortFrom, fkSecurityAttackExpansionExceptListControlDestinationPortTo }
			STATUS current
			DESCRIPTION 
				"createPortAttackExpansionExceptList"
			::= { fkSecurityAttackExpansionExceptListNotification 1 }

		
		-- 1.3.6.1.4.1.10428 9 1.101.7.9.2.3.3.2
		fkSecurityAttackExpansionExceptListChanged NOTIFICATION-TYPE
			OBJECTS { fkSecurityAttackExpansionExceptListControlRequest, fkSecurityAttackExpansionExceptListControlTimeStamp, fkSecurityAttackExpansionExceptListControlReqResult, fkSecurityAttackExpansionExceptListControlRuleIndex, fkSecurityAttackExpansionExceptListControlProtocolType, 
				fkSecurityAttackExpansionExceptListControlSourceType, fkSecurityAttackExpansionExceptListControlSourceIpAddress, fkSecurityAttackExpansionExceptListControlSourceIpMask, fkSecurityAttackExpansionExceptListControlSourceMac, fkSecurityAttackExpansionExceptListControlSourcePortType, 
				fkSecurityAttackExpansionExceptListControlSourcePortFrom, fkSecurityAttackExpansionExceptListControlSourcePortTo, fkSecurityAttackExpansionExceptListControlDestinationType, fkSecurityAttackExpansionExceptListControlDestinationIpAddress, fkSecurityAttackExpansionExceptListControlDestinationIpMask, 
				fkSecurityAttackExpansionExceptListControlDestinationMac, fkSecurityAttackExpansionExceptListControlDestinationPortType, fkSecurityAttackExpansionExceptListControlDestinationPortFrom, fkSecurityAttackExpansionExceptListControlDestinationPortTo }
			STATUS current
			DESCRIPTION 
				"modifyPortAttackExpansionExceptList"
			::= { fkSecurityAttackExpansionExceptListNotification 2 }

		
		-- 1.3.6.1.4.1.10428 9 1.101.7.9.2.3.3.3
		fkSecurityAttackExpansionExceptListDeleted NOTIFICATION-TYPE
			OBJECTS { fkSecurityAttackExpansionExceptListControlRequest, fkSecurityAttackExpansionExceptListControlTimeStamp, fkSecurityAttackExpansionExceptListControlReqResult, fkSecurityAttackExpansionExceptListControlRuleIndex }
			STATUS current
			DESCRIPTION 
				"delPortAttackExpansionExceptList"
			::= { fkSecurityAttackExpansionExceptListNotification 3 }

		
		-- 1.3.6.1.4.1.10428 9 1.101.7.9.2.4
		fkSecurityAttackExpansionBlockedList OBJECT IDENTIFIER ::= { fkSecurityAttackExpansion 4 }

		
		-- 1.3.6.1.4.1.10428 9 1.101.7.9.2.4.1
		fkSecurityAttackExpansionBlockedListTable OBJECT-TYPE
			SYNTAX SEQUENCE OF FkSecurityAttackExpansionBlockedListEntry
			MAX-ACCESS not-accessible
			STATUS current
			DESCRIPTION
				"Description."
			::= { fkSecurityAttackExpansionBlockedList 1 }

		
		-- 1.3.6.1.4.1.10428 9 1.101.7.9.2.4.1.1
		fkSecurityAttackExpansionBlockedListEntry OBJECT-TYPE
			SYNTAX FkSecurityAttackExpansionBlockedListEntry
			MAX-ACCESS not-accessible
			STATUS current
			DESCRIPTION
				"Description."
			INDEX { fkSecurityAttackExpansionBlockedListPortIndex, fkSecurityAttackExpansionBlockedListIndex }
			::= { fkSecurityAttackExpansionBlockedListTable 1 }

		
		FkSecurityAttackExpansionBlockedListEntry ::=
			SEQUENCE { 
				fkSecurityAttackExpansionBlockedListPortIndex
					Integer32,
				fkSecurityAttackExpansionBlockedListIndex
					Integer32,
				fkSecurityAttackExpansionBlockedListRuleIndex
					Integer32,
				fkSecurityAttackExpansionBlockedListAttackType
					INTEGER,
				fkSecurityAttackExpansionBlockedListAttackBlockType
					BITS,
				fkSecurityAttackExpansionBlockedListStartTime
					OCTET STRING,
				fkSecurityAttackExpansionBlockedListEndTime
					OCTET STRING,
				fkSecurityAttackExpansionBlockedListAttackSourceIp
					IpAddress,
				fkSecurityAttackExpansionBlockedListSourceMac
					OCTET STRING,
				fkSecurityAttackExpansionBlockedListAttackDestinationIp
					IpAddress,
				fkSecurityAttackExpansionBlockedListProtocol
					INTEGER,
				fkSecurityAttackExpansionBlockedListSourcePort
					Integer32,
				fkSecurityAttackExpansionBlockedListDestinationPort
					Integer32,
				fkSecurityAttackExpansionBlockedListAttackPktCount
					Counter32,
				fkSecurityAttackExpansionBlockedListAttackBlockTime
					Integer32
			 }

		-- 1.3.6.1.4.1.10428 9 1.101.7.9.2.4.1.1.1
		fkSecurityAttackExpansionBlockedListPortIndex OBJECT-TYPE
			SYNTAX Integer32 (1..65535)
			MAX-ACCESS read-only
			STATUS current
			DESCRIPTION
				"Description."
			::= { fkSecurityAttackExpansionBlockedListEntry 1 }

		
		-- 1.3.6.1.4.1.10428 9 1.101.7.9.2.4.1.1.2
		fkSecurityAttackExpansionBlockedListIndex OBJECT-TYPE
			SYNTAX Integer32 (1..65535)
			MAX-ACCESS read-only
			STATUS current
			DESCRIPTION
				"The blocked list index."
			::= { fkSecurityAttackExpansionBlockedListEntry 2 }

		
		-- 1.3.6.1.4.1.10428 9 1.101.7.9.2.4.1.1.3
		fkSecurityAttackExpansionBlockedListRuleIndex OBJECT-TYPE
			SYNTAX Integer32
			MAX-ACCESS read-only
			STATUS current
			DESCRIPTION
				"The Rule index of blocked list. It’s specific nuber per each rule."
			::= { fkSecurityAttackExpansionBlockedListEntry 3 }

		
		-- 1.3.6.1.4.1.10428 9 1.101.7.9.2.4.1.1.4
		fkSecurityAttackExpansionBlockedListAttackType OBJECT-TYPE
			SYNTAX INTEGER
				{
				none(0),
				tcpDosAttack(1),
				tcpPortFlooding(2),
				tcpHostRandomFlooding(3),
				tcpHostScanning(4),
				ipSppfing(5),
				udpDosAttack(6),
				udpPortFlooding(7),
				udpHostRandomFlooding(8),
				udpHostScanning(9),
				udpIPSppfing(10),
				icmpDosAttack(11),
				icmpIPSppfing(12),
				icmpHostScanning(13),
				arpMacFlooding(14),
				arpSpoofing(15),
				decoySnare(16),
				hostScan(17),
				portScan(18),
				tcpPortScanning(19),
				udpPortScanning(20),
				staticAttack(21)
				}
			MAX-ACCESS read-only
			STATUS current
			DESCRIPTION
				"The port attack type"
			::= { fkSecurityAttackExpansionBlockedListEntry 4 }

		
		-- 1.3.6.1.4.1.10428 9 1.101.7.9.2.4.1.1.5
		fkSecurityAttackExpansionBlockedListAttackBlockType OBJECT-TYPE
			SYNTAX BITS
				{
				none(0),
				sourceIp(1),
				sourceMac(2),
				sourcePort(3),
				destinationIp(4),
				destinationPort(5)
				}
			MAX-ACCESS read-only
			STATUS current
			DESCRIPTION
				"The attack block type."
			::= { fkSecurityAttackExpansionBlockedListEntry 5 }

		
		-- 1.3.6.1.4.1.10428 9 1.101.7.9.2.4.1.1.6
		fkSecurityAttackExpansionBlockedListStartTime OBJECT-TYPE
			SYNTAX OCTET STRING
			MAX-ACCESS read-only
			STATUS current
			DESCRIPTION
				"The start time."
			::= { fkSecurityAttackExpansionBlockedListEntry 6 }

		
		-- 1.3.6.1.4.1.10428 9 1.101.7.9.2.4.1.1.7
		fkSecurityAttackExpansionBlockedListEndTime OBJECT-TYPE
			SYNTAX OCTET STRING
			MAX-ACCESS read-only
			STATUS current
			DESCRIPTION
				"The End Time"
			::= { fkSecurityAttackExpansionBlockedListEntry 7 }

		
		-- 1.3.6.1.4.1.10428 9 1.101.7.9.2.4.1.1.8
		fkSecurityAttackExpansionBlockedListAttackSourceIp OBJECT-TYPE
			SYNTAX IpAddress
			MAX-ACCESS read-only
			STATUS current
			DESCRIPTION
				"The attack source ip address"
			::= { fkSecurityAttackExpansionBlockedListEntry 8 }

		
		-- 1.3.6.1.4.1.10428 9 1.101.7.9.2.4.1.1.9
		fkSecurityAttackExpansionBlockedListSourceMac OBJECT-TYPE
			SYNTAX OCTET STRING
			MAX-ACCESS read-only
			STATUS current
			DESCRIPTION
				"The attack source MAC address"
			::= { fkSecurityAttackExpansionBlockedListEntry 9 }

		
		-- 1.3.6.1.4.1.10428 9 1.101.7.9.2.4.1.1.10
		fkSecurityAttackExpansionBlockedListAttackDestinationIp OBJECT-TYPE
			SYNTAX IpAddress
			MAX-ACCESS read-only
			STATUS current
			DESCRIPTION
				"The attack Destination ip address"
			::= { fkSecurityAttackExpansionBlockedListEntry 10 }

		
		-- 1.3.6.1.4.1.10428 9 1.101.7.9.2.4.1.1.11
		fkSecurityAttackExpansionBlockedListProtocol OBJECT-TYPE
			SYNTAX INTEGER
				{
				any(0),
				tcp(1),
				udp(2),
				icmp(3),
				arp(4)
				}
			MAX-ACCESS read-only
			STATUS current
			DESCRIPTION
				"The protocol type."
			::= { fkSecurityAttackExpansionBlockedListEntry 11 }

		
		-- 1.3.6.1.4.1.10428 9 1.101.7.9.2.4.1.1.12
		fkSecurityAttackExpansionBlockedListSourcePort OBJECT-TYPE
			SYNTAX Integer32 (0..65535)
			MAX-ACCESS read-only
			STATUS current
			DESCRIPTION
				"The source port (0: any)"
			::= { fkSecurityAttackExpansionBlockedListEntry 12 }

		
		-- 1.3.6.1.4.1.10428 9 1.101.7.9.2.4.1.1.13
		fkSecurityAttackExpansionBlockedListDestinationPort OBJECT-TYPE
			SYNTAX Integer32 (0..65535)
			MAX-ACCESS read-only
			STATUS current
			DESCRIPTION
				"The destination port (0: any)"
			::= { fkSecurityAttackExpansionBlockedListEntry 13 }

		
		-- 1.3.6.1.4.1.10428 9 1.101.7.9.2.4.1.1.14
		fkSecurityAttackExpansionBlockedListAttackPktCount OBJECT-TYPE
			SYNTAX Counter32
			MAX-ACCESS read-only
			STATUS current
			DESCRIPTION
				"The attack packet per second."
			::= { fkSecurityAttackExpansionBlockedListEntry 14 }

		
		-- 1.3.6.1.4.1.10428 9 1.101.7.9.2.4.1.1.15
		fkSecurityAttackExpansionBlockedListAttackBlockTime OBJECT-TYPE
			SYNTAX Integer32 (-1 | 10..86400)
			MAX-ACCESS read-only
			STATUS current
			DESCRIPTION
				"The attack block time."
			::= { fkSecurityAttackExpansionBlockedListEntry 15 }

		
		-- 1.3.6.1.4.1.10428 9 1.101.7.9.2.4.2
		fkSecurityAttackExpansionBlockedListControl OBJECT IDENTIFIER ::= { fkSecurityAttackExpansionBlockedList 2 }

		
		-- 1.3.6.1.4.1.10428 9 1.101.7.9.2.4.2.1
		fkSecurityAttackExpansionBlockedListControlRequest OBJECT-TYPE
			SYNTAX INTEGER { setPortAttackExpansionBlockTime(1) }
			MAX-ACCESS read-write
			STATUS current
			DESCRIPTION
				"Description"
			::= { fkSecurityAttackExpansionBlockedListControl 1 }

		
		-- 1.3.6.1.4.1.10428 9 1.101.7.9.2.4.2.2
		fkSecurityAttackExpansionBlockedListControlStatus OBJECT-TYPE
			SYNTAX FkControlStatusType
			MAX-ACCESS read-only
			STATUS current
			DESCRIPTION
				"Description"
			::= { fkSecurityAttackExpansionBlockedListControl 2 }

		
		-- 1.3.6.1.4.1.10428 9 1.101.7.9.2.4.2.3
		fkSecurityAttackExpansionBlockedListControlTimer OBJECT-TYPE
			SYNTAX Gauge32
			MAX-ACCESS read-write
			STATUS current
			DESCRIPTION
				"Description"
			::= { fkSecurityAttackExpansionBlockedListControl 3 }

		
		-- 1.3.6.1.4.1.10428 9 1.101.7.9.2.4.2.4
		fkSecurityAttackExpansionBlockedListControlTimeStamp OBJECT-TYPE
			SYNTAX TimeTicks
			MAX-ACCESS read-only
			STATUS current
			DESCRIPTION
				"Description"
			::= { fkSecurityAttackExpansionBlockedListControl 4 }

		
		-- 1.3.6.1.4.1.10428 9 1.101.7.9.2.4.2.5
		fkSecurityAttackExpansionBlockedListControlReqResult OBJECT-TYPE
			SYNTAX FkControlRequestResultType
			MAX-ACCESS read-only
			STATUS current
			DESCRIPTION
				"Result of the last command."
			::= { fkSecurityAttackExpansionBlockedListControl 5 }

		
		-- 1.3.6.1.4.1.10428 9 1.101.7.9.2.4.2.6
		fkSecurityAttackExpansionBlockedListControlRuleIndex OBJECT-TYPE
			SYNTAX Integer32
			MAX-ACCESS read-write
			STATUS current
			DESCRIPTION
				"The Rule index of blocked list. It’s specific nuber per each rule."
			::= { fkSecurityAttackExpansionBlockedListControl 6 }

		
		-- 1.3.6.1.4.1.10428 9 1.101.7.9.2.4.2.7
		fkSecurityAttackExpansionBlockedListControlBlockTime OBJECT-TYPE
			SYNTAX Integer32 (-1 | 10..86400)
			MAX-ACCESS read-write
			STATUS current
			DESCRIPTION
				"The port attack block time "
			::= { fkSecurityAttackExpansionBlockedListControl 7 }

		
		-- 1.3.6.1.4.1.10428 9 1.101.7.9.2.4.3
		fkSecurityAttackExpansionBlockedListNotification OBJECT IDENTIFIER ::= { fkSecurityAttackExpansionBlockedList 3 }

		
		-- 1.3.6.1.4.1.10428 9 1.101.7.9.2.4.3.1
		fkSecurityAttackExpansionBlockedListBlockTimeChanged NOTIFICATION-TYPE
			OBJECTS { fkSecurityAttackExpansionBlockedListControlRequest, fkSecurityAttackExpansionBlockedListControlTimeStamp, fkSecurityAttackExpansionBlockedListControlReqResult, fkSecurityAttackExpansionBlockedListControlRuleIndex, fkSecurityAttackExpansionBlockedListControlBlockTime
				 }
			STATUS current
			DESCRIPTION 
				"setPortAttackExpansionBlockTime"
			::= { fkSecurityAttackExpansionBlockedListNotification 1 }

		
		-- 1.3.6.1.4.1.10428 9 1.101.7.10
		fkSecurityGroup OBJECT-GROUP
			OBJECTS { fkSecurityRadiusRetransmissions, fkSecurityRadiusTimeouts, fkSecurityRadiusInterfaceName, fkSecurityRadiusInterfaceAddress, fkSecurityTacacsInterfaceName, 
				fkSecurityTacacsInterfaceAddress, fkSecurityTacacsPort, fkSecurityTacacsAuthType, fkSecurityTacacsTimeouts, fkSecurityTacacsPriorityLevel, 
				fkSecurityDot1xActivity, fkSecurityLoginLimits, fkSecurityControlRequest, fkSecurityControlStatus, fkSecurityControlTimer, 
				fkSecurityControlTimeStamp, fkSecurityControlReqResult, fkSecurityControlRadiusRetransmissions, fkSecurityControlRadiusTimeouts, fkSecurityControlRadiusInterfaceName, 
				fkSecurityControlRadiusInterfaceAddress, fkSecurityControlTacacsInterfaceName, fkSecurityControlTacacsInterfaceAddress, fkSecurityControlTacacsPort, fkSecurityControlTacacsAuthType, 
				fkSecurityControlTacacsTimeouts, fkSecurityControlTacacsPriorityLevel, fkSecurityControlDot1xActivity, fkSecurityControlLoginLimits, fkAaaSession, 
				fkAaaAuthen, fkAaaEnable, fkAaaPrimarySequence, fkAaaControlRequest, fkAaaControlStatus, 
				fkAaaControlTimer, fkAaaControlTimeStamp, fkAaaControlReqResult, fkAaaControlSession, fkAaaControlAuthen, 
				fkAaaControlEnable, fkAaaControlPrimaryFlag, fkRadiusServerAddress, fkRadiusServerClientKey, fkRadiusServerAuthPort, 
				fkRadiusServerAccPort, fkRadiusServerMode, fkRadiusServerControlRequest, fkRadiusServerControlStatus, fkRadiusServerControlTimer, 
				fkRadiusServerControlTimeStamp, fkRadiusServerControlReqResult, fkRadiusServerControlAddress, fkRadiusServerControlClientKey, fkRadiusServerControlAuthPort, 
				fkRadiusServerControlAccPort, fkRadiusServerControlMode, fkTacacsServerAddress, fkTacacsServerClientKey, fkTacacsServerControlRequest, 
				fkTacacsServerControlStatus, fkTacacsServerControlTimer, fkTacacsServerControlTimeStamp, fkTacacsServerControlReqResult, fkTacacsServerControlAddress, 
				fkTacacsServerControlClientKey, fkAclName, fkAclSrcIpAddr, fkAclSrcPrefixLength, fkAclDstIpAddr, 
				fkAclDstPrefixLength, fkAclDscp, fkAclProtocolType, fkAclTcpFlag, fkAclSrcL4Port, 
				fkAclDstL4Port, fkAclPktLen, fkAclValidFlags, fkAclMatchFlags, fkAclMatchAction, 
				fkAclNomatchAction, fkAclPriority, fkAclControlRequest, fkAclControlStatus, fkAclControlTimer, 
				fkAclControlTimeStamp, fkAclControlReqResult, fkAclControlName, fkAclControlSrcIpAddr, fkAclControlSrcPrefixLength, 
				fkAclControlDstIpAddr, fkAclControlDstPrefixLength, fkAclControlDscp, fkAclControlProtocolType, fkAclControlTcpFlag, 
				fkAclControlSrcL4Port, fkAclControlDstL4Port, fkAclControlPktLen, fkAclControlValidFlags, fkAclControlMatchFlags, 
				fkAclControlMatchAction, fkAclControlNomatchAction, fkAclControlPriority, fkDot1xPortIndex, fkDot1xPortEnable, 
				fkDot1xPortMode, fkDot1xPortReauthEnable, fkDot1xPortQuietPeriod, fkDot1xPortReauthPeriod, fkDot1xPortAuthSuccess, 
				fkDot1xPortControlRequest, fkDot1xPortControlStatus, fkDot1xPortControlTimer, fkDot1xPortControlTimeStamp, fkDot1xPortControlReqResult, 
				fkDot1xPortControlIndex, fkDot1xPortControlEnable, fkDot1xPortControlMode, fkDot1xPortControlReauthEnable, fkDot1xPortControlQuietPeriod, 
				fkDot1xPortControlReauthPeriod, fkDot1xStatsPortIndex, fkDot1xStatsEapolFramesRx, fkDot1xStatsEapolFramesTx, fkDot1xStatsEapolStartFramesRx, 
				fkDot1xStatsEapolLogoffFramesRx, fkDot1xStatsEapolRespIdFramesRx, fkDot1xStatsEapolRespFramesRx, fkDot1xStatsEapolReqIdFramesTx, fkDot1xStatsEapolReqFramesTx, 
				fkDot1xStatsInvalidEapolFramesRx, fkDot1xStatsEapLengthErrorFramesRx, fkDot1xStatsLastEapolFrameVersion, fkDot1xStatsLastEapolFrameSource, fkDot1xStatsControlRequest, 
				fkDot1xStatsControlStatus, fkDot1xStatsControlTimer, fkDot1xStatsControlTimeStamp, fkDot1xStatsControlReqResult, fkDot1xStatsControlPortIndex, 
				fkArpInspectValidateSrcMac, fkArpInspectValidateDstMac, fkArpInspectValidateIpAddr, fkArpInspectLogBufferSize, fkArpInspectLogEntry, 
				fkArpInspectLogInterval, fkArpInspectControlRequest, fkArpInspectControlStatus, fkArpInspectControlTimer, fkArpInspectControlTimeStamp, 
				fkArpInspectControlReqResult, fkArpInspectControlValidateSrcMac, fkArpInspectControlValidateDstMac, fkArpInspectControlValidateIpAddr, fkArpInspectControlLogBufferSize, 
				fkArpInspectControlLogEntry, fkArpInspectControlLogInterval, fkArpAclIndex, fkArpAclName, fkArpAclNumEntries, 
				fkArpAclControlRequest, fkArpAclControlStatus, fkArpAclControlTimer, fkArpAclControlTimeStamp, fkArpAclControlReqResult, 
				fkArpAclControlIndex, fkArpAclControlName, fkArpAclRuleAclIndex, fkArpAclRuleIndex, fkArpAclRuleAction, 
				fkArpAclRuleType, fkArpAclRuleRangeStartIP, fkArpAclRuleRangeEndIP, fkArpAclRuleIPAddress, fkArpAclRuleIPMask, 
				fkArpAclRuleMacAddr, fkArpAclRuleMacType, fkArpAclRuleControlRequest, fkArpAclRuleControlStatus, fkArpAclRuleControlTimer, 
				fkArpAclRuleControlTimeStamp, fkArpAclRuleControlReqResult, fkArpAclRuleControlAclIndex, fkArpAclRuleControlIndex, fkArpAclRuleControlAction, 
				fkArpAclRuleControlType, fkArpAclRuleControlRangeStartIP, fkArpAclRuleControlRangeEndIP, fkArpAclRuleControlIPAddress, fkArpAclRuleControlIPMask, 
				fkArpAclRuleControlMacAddr, fkArpAclRuleControlMacType, fkArpInspectVlanIndex, fkArpInspectVlanEnable, fkArpInspectVlanFilterAcl, 
				fkArpInspectVlanFwdPktCnt, fkArpInspectVlanDropPktCnt, fkArpInspectVlanAclPermits, fkArpInspectVlanAclDrops, fkArpInspectVlanSrcMacFailurs, 
				fkArpInspectVlanDstMacFailurs, fkArpInspectVlanIpAddrFailurs, fkArpInspectVlanFilterAclName, fkArpInspectVlanControlRequest, fkArpInspectVlanControlStatus, 
				fkArpInspectVlanControlTimer, fkArpInspectVlanControlTimeStamp, fkArpInspectVlanControlReqResult, fkArpInspectVlanControlIndex, fkArpInspectVlanControlEnable, 
				fkArpInspectVlanControlFilterAcl, fkArpInspectPortIndex, fkArpInspectPortTrust, fkArpInspectPortControlRequest, fkArpInspectPortControlStatus, 
				fkArpInspectPortControlTimer, fkArpInspectPortControlTimeStamp, fkArpInspectPortControlReqResult, fkArpInspectPortControlIndex, fkArpInspectPortControlTrust, 
				fkArpInspectInvalidLogId, fkArpInspectInvalidLogReason, fkArpInspectInvalidLogSamePktCnt, fkArpInspectInvalidLogOpcode, fkArpInspectInvalidLogPortNumber, 
				fkArpInspectInvalidLogVlanId, fkArpInspectInvalidLogSrcMacAddr, fkArpInspectInvalidLogSrcIpAddr, fkArpInspectInvalidLogDstMacAddr, fkArpInspectInvalidLogDstIpAddr, 
				fkArpInspectInvalidLogLastRecvTime, fkSecurityAttackBasicBaseInfoGlobalStatus, fkSecurityAttackBasicBaseControlRequest, fkSecurityAttackBasicBaseControlStatus, fkSecurityAttackBasicBaseControlTimer, 
				fkSecurityAttackBasicBaseControlTimeStamp, fkSecurityAttackBasicBaseControlReqResult, fkSecurityAttackBasicBaseControlGlobalStatus, fkSecurityAttackBasicPolicyBlockTime, fkSecurityAttackBasicPolicyControlRequest, 
				fkSecurityAttackBasicPolicyControlStatus, fkSecurityAttackBasicPolicyControlTimer, fkSecurityAttackBasicPolicyControlTimeStamp, fkSecurityAttackBasicPolicyControlReqResult, fkSecurityAttackBasicPolicyControlAttackType, 
				fkSecurityAttackBasicPolicyControlBlockTime, fkSecurityAttackBasicExceptListIndex, fkSecurityAttackBasicExceptListProtocolType, fkSecurityAttackBasicExceptListSourceIpAddress, fkSecurityAttackBasicExceptListDestinationIpAddress, 
				fkSecurityAttackBasicExceptListControlRequest, fkSecurityAttackBasicExceptListControlStatus, fkSecurityAttackBasicExceptListControlTimer, fkSecurityAttackBasicExceptListControlTimeStamp, fkSecurityAttackBasicExceptListControlReqResult, 
				fkSecurityAttackBasicExceptListControlRuleIndex, fkSecurityAttackBasicExceptListControlProtocolType, fkSecurityAttackBasicExceptListControlSourceIpAddress, fkSecurityAttackBasicExceptListControlDestinationIpAddress, fkSecurityAttackBasicBlockedListIndex, 
				fkSecurityAttackBasicBlockedListAttackType, fkSecurityAttackBasicBlockedListStartTime, fkSecurityAttackBasicBlockedListEndTime, fkSecurityAttackBasicBlockedListAttackSourceIp, fkSecurityAttackBasicBlockedListAttackDestinationIp, 
				fkSecurityAttackBasicBlockedListProtocol, fkSecurityAttackBasicBlockedListAttackPktCount, fkSecurityAttackBasicBlockedListAttackBlockTime, fkSecurityAttackBasicBlockedListControlRequest, fkSecurityAttackBasicBlockedListControlStatus, 
				fkSecurityAttackBasicBlockedListControlTimer, fkSecurityAttackBasicBlockedListControlTimeStamp, fkSecurityAttackBasicBlockedListControlReqResult, fkSecurityAttackBasicBlockedListControlRuleIndex, fkSecurityAttackBasicBlockedListControlBlockTime, 
				fkSecurityAttackExpansionBaseGlobalStatus, fkSecurityAttackExpansionBaseControlRequest, fkSecurityAttackExpansionBaseControlStatus, fkSecurityAttackExpansionBaseControlTimer, fkSecurityAttackExpansionBaseControlTimeStamp, 
				fkSecurityAttackExpansionBaseControlReqResult, fkSecurityAttackExpansionBaseControlGlobalStatus, fkSecurityAttackExpansionPolicyPortIndex, fkSecurityAttackExpansionPolicyStatus, fkSecurityAttackExpansionPolicyAttackType, 
				fkSecurityAttackExpansionPolicyBlockTime, fkSecurityAttackExpansionPolicyControlRequest, fkSecurityAttackExpansionPolicyControlStatus, fkSecurityAttackExpansionPolicyControlTimer, fkSecurityAttackExpansionPolicyControlTimeStamp, 
				fkSecurityAttackExpansionPolicyControlReqResult, fkSecurityAttackExpansionPolicyControlPortIndex, fkSecurityAttackExpansionPolicyControlAttackType, fkSecurityAttackExpansionPolicyControlBlockTime, fkSecurityAttackExpansionExceptListPortIndex, 
				fkSecurityAttackExpansionExceptListIndex, fkSecurityAttackExpansionExceptListRuleIndex, fkSecurityAttackExpansionExceptListProtocolType, fkSecurityAttackExpansionExceptListSourceType, fkSecurityAttackExpansionExceptListSourceIpAddress, 
				fkSecurityAttackExpansionExceptListSourceIpMask, fkSecurityAttackExpansionExceptListSourceMac, fkSecurityAttackExpansionExceptListSourcePortType, fkSecurityAttackExpansionExceptListSourcePortFrom, fkSecurityAttackExpansionExceptListSourcePortTo, 
				fkSecurityAttackExpansionExceptListDestinationType, fkSecurityAttackExpansionExceptListDestinationIpAddress, fkSecurityAttackExpansionExceptListDestinationIpMask, fkSecurityAttackExpansionExceptListDestinationMac, fkSecurityAttackExpansionExceptListDestinationPortType, 
				fkSecurityAttackExpansionExceptListDestinationPortFrom, fkSecurityAttackExpansionExceptListDestinationPortTo, fkSecurityAttackExpansionExceptListControlRequest, fkSecurityAttackExpansionExceptListControlStatus, fkSecurityAttackExpansionExceptListControlTimer, 
				fkSecurityAttackExpansionExceptListControlTimeStamp, fkSecurityAttackExpansionExceptListControlReqResult, fkSecurityAttackExpansionExceptListControlPortIndex, fkSecurityAttackExpansionExceptListControlRuleIndex, fkSecurityAttackExpansionExceptListControlProtocolType, 
				fkSecurityAttackExpansionExceptListControlSourceType, fkSecurityAttackExpansionExceptListControlSourceIpAddress, fkSecurityAttackExpansionExceptListControlSourceIpMask, fkSecurityAttackExpansionExceptListControlSourceMac, fkSecurityAttackExpansionExceptListControlSourcePortType, 
				fkSecurityAttackExpansionExceptListControlSourcePortFrom, fkSecurityAttackExpansionExceptListControlSourcePortTo, fkSecurityAttackExpansionExceptListControlDestinationType, fkSecurityAttackExpansionExceptListControlDestinationIpAddress, fkSecurityAttackExpansionExceptListControlDestinationIpMask, 
				fkSecurityAttackExpansionExceptListControlDestinationMac, fkSecurityAttackExpansionExceptListControlDestinationPortType, fkSecurityAttackExpansionExceptListControlDestinationPortFrom, fkSecurityAttackExpansionExceptListControlDestinationPortTo, fkSecurityAttackExpansionBlockedListPortIndex, 
				fkSecurityAttackExpansionBlockedListIndex, fkSecurityAttackExpansionBlockedListRuleIndex, fkSecurityAttackExpansionBlockedListAttackType, fkSecurityAttackExpansionBlockedListAttackBlockType, fkSecurityAttackExpansionBlockedListStartTime, 
				fkSecurityAttackExpansionBlockedListEndTime, fkSecurityAttackExpansionBlockedListAttackSourceIp, fkSecurityAttackExpansionBlockedListSourceMac, fkSecurityAttackExpansionBlockedListAttackDestinationIp, fkSecurityAttackExpansionBlockedListProtocol, 
				fkSecurityAttackExpansionBlockedListSourcePort, fkSecurityAttackExpansionBlockedListDestinationPort, fkSecurityAttackExpansionBlockedListAttackPktCount, fkSecurityAttackExpansionBlockedListAttackBlockTime, fkSecurityAttackExpansionBlockedListControlRequest, 
				fkSecurityAttackExpansionBlockedListControlStatus, fkSecurityAttackExpansionBlockedListControlTimer, fkSecurityAttackExpansionBlockedListControlTimeStamp, fkSecurityAttackExpansionBlockedListControlReqResult, fkSecurityAttackExpansionBlockedListControlRuleIndex, 
				fkSecurityAttackExpansionBlockedListControlBlockTime, fkSecurityAttackBasicBaseDosStatus, fkSecurityAttackBasicBaseScanStatus, fkSecurityAttackBasicBaseCollectInterval, fkSecurityAttackBasicBaseControlDosStatus, 
				fkSecurityAttackBasicBaseControlScanStatus, fkSecurityAttackBasicBaseControlCollectInterval, fkSecurityAttackBasicPolicyAttackType, fkSecurityAttackBasicPolicyThresholdCount, fkSecurityAttackBasicPolicyControlThresholdCount, 
				fkSecurityAttackBasicBlackListIndex, fkSecurityAttackBasicBlackListProtocolType, fkSecurityAttackBasicBlackListSourceIpAddress, fkSecurityAttackBasicBlackListDestinationIpAddress, fkSecurityAttackBasicBlackListBlockingStatus, 
				fkSecurityAttackBasicBlackListControlRequest, fkSecurityAttackBasicBlackListControlStatus, fkSecurityAttackBasicBlackListControlTimer, fkSecurityAttackBasicBlackListControlTimeStamp, fkSecurityAttackBasicBlackListControlReqResult, 
				fkSecurityAttackBasicBlackListControlRuleIndex, fkSecurityAttackBasicBlackListControlProtocolType, fkSecurityAttackBasicBlackListControlSourceIpAddress, fkSecurityAttackBasicBlackListControlDestinationIpAddress, fkSecurityAttackBasicPolicyCollectPorts, 
				fkSecurityAttackBasicPolicyControlCollectPorts, fkSecurityAttackBasicExceptListIngressPort, fkSecurityAttackBasicExceptListControlIngressPort, fkSecurityAttackBasicBlackListIgressPort, fkSecurityAttackBasicBlackListControlIngressPort, 
				fkSecurityAttackBasicBlockedListBlackListIndex, fkSecurityAttackBasicBlockedListIgressPort }
			STATUS current
			DESCRIPTION 
				"Description."
			::= { fkSecurity 10 }

		
		-- 1.3.6.1.4.1.10428 9 1.101.7.11
		fkSecurityNotificationGroup NOTIFICATION-GROUP
			NOTIFICATIONS { fkArpAclCreated, fkArpAclDestroyed, fkArpInspectVlanChanged, fkArpInspectLogBufferSizeChanged, fkArpInspectLogRateChanged, 
				fkSecurityBaseLoginLimitsChanged, fkArpInspectPortChanged, fkSecurityRadiusProfileChanged, fkSecurityTacacsProfileChanged, fkSecurityDot1xActivityChanged, 
				fkAaaProfileChanged, fkRadiusServerCreated, fkRadiusServerDestroyed, fkRadiusServerProfileChanged, fkTacacsServerCreated, 
				fkTacacsServerDestroyed, fkTacacsServerClientKeyChanged, fkAclCreated, fkAclDestroyed, fkAclClassifierProfileChanged, 
				fkAclMatchActionChanged, fkAclNomatchActionChanged, fkDot1xPortProfileChanged, fkDot1xPortAuthSuccessChanged, fkDot1xStatisticsCleared, 
				fkArpInspectValidateChanged, fkArpAclRuleCreated, fkArpAclRuleDestroyed, fkSecurityAttackBasicBaseGlobalStatusChanged, fkSecurityAttackBasicExceptListCreated, 
				fkSecurityAttackBasicExceptListChanged, fkSecurityAttackBasicExceptListDeleted, fkSecurityAttackExpansionBaseGlobalStatusChanged, fkSecurityAttackExpansionPolicyChanged, fkSecurityAttackExpansionExceptListCreated, 
				fkSecurityAttackExpansionExceptListChanged, fkSecurityAttackExpansionExceptListDeleted, fkSecurityAttackExpansionBlockedListBlockTimeChanged, fkSecurityAttackBasicBaseDosStatusChanged, fkSecurityAttackBasicBaseScanStatusChanged, 
				fkSecurityAttackBasicBaseCollectIntervalChanged, fkSecurityAttackBasicPolicyThresholdCountChanged, fkSecurityAttackBasicBlackListDeleted, fkSecurityAttackBasicBlockedListBlockTimeChanged, fkSecurityAttackBasicPolicyBlockTimeChanged, 
				fkSecurityAttackBasicPolicyCollectPortsChanged, fkSecurityAttackBasicBlockedListDeleted, fkSecurityAttackBasicBaseAllConfigChanged, setSecurityAttackBasicPolicyAllConfigChanged, fkSecurityAttackBasicBlackListCreated
				 }
			STATUS current
			DESCRIPTION 
				"Description."
			::= { fkSecurity 11 }

		
	
	END

--
-- fk-security-mib.mib
--
