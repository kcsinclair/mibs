-- *****************************************************************
-- FKOLTG1040-TC.my:  Fkoltg1040 MIB Textual Conventions
-- 
-- *****************************************************************
--

FKOLTG1040-TC DEFINITIONS ::= BEGIN

IMPORTS
    TEXTUAL-CONVENTION
        FROM SNMPv2-TC
    MODULE-IDENTITY,
    Gauge32,
    Integer32, Unsigned32
        FROM SNMPv2-SMI
    fkoltg1040Modules
        FROM FKOLTG1040-SMI;

fkoltg1040TextualConventions MODULE-IDENTITY
    LAST-UPDATED    "200101180000Z"
                        ORGANIZATION 
                                "Furukawa Industrial S.A."
                        CONTACT-INFO 
                                "Furukawa Industrial S.A. Produtos Eletricos
        Rua Hasdrubal Bellegard, 820 - CIC
        CEP 81460-120 - Curitiba - Parana - Brasil
        CSC 0800-41-2100
        E-mail: fisa@furukawa.com.br"
                        DESCRIPTION 
                                "The MIB module for Furukawa GPON OLT FK-OLT-G1040."
    ::= { fkoltg1040Modules 1 }

SubnetConfRangeIndex ::= TEXTUAL-CONVENTION
    STATUS      current
    DESCRIPTION
        "The value of this object identifies the range of the subnet"
    SYNTAX      INTEGER
    
SubnetConfIndex ::= TEXTUAL-CONVENTION
    STATUS      current
    DESCRIPTION
        "The value of this object identifies the subnet"
    SYNTAX      INTEGER 
    
Fkoltg1040NetworkProtocol ::= TEXTUAL-CONVENTION
    STATUS    current
    DESCRIPTION
        "Represents the different types of network layer protocols."
    -- internal note: enumerations must match those in address.h
    SYNTAX    INTEGER {
        ip (1),
        decnet (2),
        pup (3),
        chaos (4),
        xns (5),
        x121 (6),
        appletalk (7),
        clns (8),
        lat (9),
        vines (10),
        cons (11),
        apollo (12),
        stun (13),
        novell (14),
        qllc (15),
        snapshot (16),
        atmIlmi (17),
        bstun (18),
        x25pvc (19),
        unknown (65535)
    }

Fkoltg1040NetworkAddress ::= TEXTUAL-CONVENTION
    DISPLAY-HINT    "1x:"
    STATUS        current
    DESCRIPTION
        "Represents a network layer address.  The length and format of
        the address is protocol dependent as follows:
        ip        4 octets
        decnet    2 octets
        pup       obsolete
        chaos     2 octets
        xns       10 octets
                  first 4 octets are the net number
                  last 6 octets are the host number
        x121    
        appletalk 3 octets
                  first 2 octets are the net number
                  last octet is the host number
        clns
        lat
        vines     6 octets
                  first 4 octets are the net number
                  last 2 octets are the host number
        cons
        apollo    10 octets
                  first 4 octets are the net number
                  last 6 octets are the host number
        stun      8 octets
        novell    10 octets
                  first 4 octets are the net number
                  last 6 octets are the host number
        qllc      6 octets
        bstun     1 octet - bi-sync serial tunnel 
        snapshot  1 octet
        atmIlmi   4 octets
        x25 pvc   2 octets (12 bits)
        "
    SYNTAX    OCTET STRING

InterfaceIndexOrZero ::= TEXTUAL-CONVENTION
    DISPLAY-HINT "d"
    STATUS    current
    DESCRIPTION
        "Either the value 0, or the ifIndex value of an
        interface in the ifTable."
    SYNTAX    Integer32 (0..2147483647)

SAPType ::= TEXTUAL-CONVENTION
    DISPLAY-HINT "d"
    STATUS    current
    DESCRIPTION
        "Service Access Point - is a term that denotes the means
        by which a user entity in layer n+1 accesses a service
        of a provider entity in layer n."
    SYNTAX    Integer32 (0..254)

CountryCode ::= TEXTUAL-CONVENTION
    DISPLAY-HINT "2a"
    STATUS    current
    DESCRIPTION
        "Represents a case-insensitive 2-letter country code taken 
        from ISO-3166. Unrecognized countries are represented as 
        empty string."
    SYNTAX    OCTET STRING (SIZE (0 | 2))
 
EntPhysicalIndexOrZero ::= TEXTUAL-CONVENTION
    STATUS    current
    DESCRIPTION
        "This textual convention is an extension of entPhysicalIndex.
        If non-zero, the object is an entPhysicalIndex. If zero, no
        appropriate entPhysicalIndex exists. Any additional semantics
        are object specific."
    SYNTAX    Integer32 (0..2147483647)

Fkoltg1040RowOperStatus ::= TEXTUAL-CONVENTION
    STATUS    current
    DESCRIPTION
        "Represents the operational status of an table entry.
        This textual convention allows explicitly representing
        the states of rows dependent on rows in other tables.

        active(1) -
            Indicates this entry's RowStatus is active
            and the RowStatus for each dependency is active.

        activeDependencies(2) -
            Indicates that the RowStatus for each dependency
            is active, but the entry's RowStatus is not active.

        inactiveDependency(3) -
            Indicates that the RowStatus for at least one
            dependency is not active.

        missingDependency(4) -
            Indicates that at least one dependency does
            not exist in it's table.
        "
    SYNTAX    INTEGER {
        active(1),
        activeDependencies(2),
        inactiveDependency(3),
        missingDependency(4)
    }

Fkoltg1040Port ::= TEXTUAL-CONVENTION
    STATUS    current
    DESCRIPTION
        "The TCP or UDP port number range."
    REFERENCE
        "Transmission Control Protocol. J. Postel. RFC793,
        User Datagram Protocol. J. Postel. RFC768"
    SYNTAX Integer32 ( 0..65535 )

Fkoltg1040IpProtocol ::= TEXTUAL-CONVENTION
    STATUS    current
    DESCRIPTION
        "IP protocol number range."
    REFERENCE
        "Internet Protocol. J. Postel. RFC791"
    SYNTAX Integer32 ( 0..255 ) 



Fkoltg1040LocationClass ::= TEXTUAL-CONVENTION
    STATUS    current
    DESCRIPTION
        "An enumerated value which provides an indication of
        the general location type of a particular physical and/or
        logical interface.
        chassis - a system framework for mounting one or more 
                  shelves/slots/cards.
        shelf - a cabinet that holds one or more slots.
        slot -  card or subSlot holder.
        subSlot - daughter-card holder.
        port - a physical port (e.g., a DS1 or DS3 physical port).
        subPort - a logical port on a physical port (e.g., a DS1 
                  subPort on a DS3 physical port).
        channel - a logical interface (e.g., a DS0 channel, signalling
                  channel, ATM port, other virtual interfaces).
        subChannel - a sub-channel on a logical interface.
        "
    SYNTAX    INTEGER  {
        chassis(1),
        shelf(2),
        slot(3),
        subSlot(4),
        port(5),
        subPort(6),
        channel(7),
        subChannel(8)
    }

Fkoltg1040LocationSpecifier ::= TEXTUAL-CONVENTION
    STATUS    current
    DESCRIPTION
        "Use this TC to define objects that indicate the
        physical entity and/or logical interface location 
        of a managed entity on a managed device. In SNMP, a 
        standard mechanism for indicating the physical location
        of entities is via the ENTITY-MIB. However, that approach
        is not satisfactory in some cases because:

        1. The entity requiring a location-based naming may be 
           associated with an entity which can not be represented 
           as a physical entity in the ENTITY-MIB,
        2. NMS applications may desire a more direct 
           name/representation of a physical entity than is 
           available via the ENTITY-MIB, e.g., a physical entity
           which is named via a hierarchy of levels in the ENTITY-MIB.

        The value of an object defined using this TC is an ASCII 
        string consisting of zero or more elements separated by 
        commas. Each element is of the form <tag> = <value>. 

        An example of this syntax is 'slot=5,port=3'.

        The syntax of the string is formally specified using
        ABNF notation (with one exception, noted below), as
        follows:                 

        location-specifier =  elem *(',' elem) 
                       ; subject to 
                       ; size restriction specified in the SYNTAX
                       ; clause below

        elem    =   loctype '=' number

        number  = %x00-FFFFFFFF / %d0-4294967295

        loctype = 1*32VCHAR 

        It is recommended that loctype use one of the enumerated
        labels defined for Fkoltg1040LocationClass.

        (NOTE: To conform to ABNF notation as defined in RFC2234, 
         substitute the single-quote symbol with a double-quote 
         symbol in the above rules.)

        A zero length of Fkoltg1040LocationSpecifier is object-specific
        and must be defined as part of the description of any object
        which uses this syntax.
        "
    REFERENCE 
        "RFC2234, Augmented BNF for syntax specifications: ABNF"

    SYNTAX    OCTET STRING (SIZE (0..255)) 

Fkoltg1040InetAddressMask ::= TEXTUAL-CONVENTION
    STATUS       current
    DESCRIPTION
        "Denotes a generic Internet subnet address mask.
        The Internet subnet address mask is represented as the
        number of contiguous 1-bit from MSB (most significant bit)
        of the Internet subnet address mask.
        A Fkoltg1040InetAddressMask value is always interpreted within
        the context of an InetAddressType value. The 
        InetAddressType only object or InetAddressType with
        InetAddress objects which define the context must be
        registered immediately before the object which uses the
        Fkoltg1040InetAddressMask textual convention.  In other words,
        the object identifiers for the InetAddressType object and
        the Fkoltg1040InetAddressMask object MUST have the same length
        and the last sub-identifier of the InetAddressType object
        MUST be 1 less than the last sub-identifier of the 
        Fkoltg1040InetAddressMask object and MUST be 2 less than the
        last sub-identifier of the Fkoltg1040InetAddressMask object if
        an InetAddress object is defined between InetAddressType
        and Fkoltg1040InetAddressMask objects.
        The maximum value of the Fkoltg1040InetAddressMask TC is 32 for
        the value 'ipv4(1)' in InetAddressType object and 128 for
        the value 'ipv6(2)' in InetAddressType object.
        The value zero is object-specific and must therefore be
        defined as part of the description of any object which
        uses this syntax.  Examples of the usage of zero might
        include situations where Internet subnet mask was unknown,
        or when none subnet masks need to be referenced." 

    REFERENCE
        "RFC2851, Textual Conventions for Internet Network Addresses."

    SYNTAX      Unsigned32   (0..128)

Fkoltg1040AbsZeroBasedCounter32 ::= TEXTUAL-CONVENTION
    STATUS       current
    DESCRIPTION
        "This TC describes an object which counts events with the
        following semantics: objects of this type will be set to
        zero(0) on creation and will thereafter count appropriate
        events, it locks at the maximum value of 4,294,967,295 if
        the counter overflows.
        This TC may be used only in situations where wrapping is
        not possible or extremely unlikely situation."
    SYNTAX      Gauge32

Fkoltg1040SnapShotAbsCounter32 ::= TEXTUAL-CONVENTION
    STATUS       current
    DESCRIPTION
        "This TC describes an object which stores a snap-shot value
        with the following semantics: objects of this type will
        take a snap-shot value from their associated
        Fkoltg1040AbsZeroBasedCounter32 type objects on creation."
    SYNTAX      Unsigned32 

Fkoltg1040AlarmSeverity ::= TEXTUAL-CONVENTION
    STATUS      current
    DESCRIPTION
        "Represents the perceived alarm severity associated
        with a service or safety affecting condition and/or
        event.  These are based on ITU severities, except
        that info(7) is added.

            cleared(1) -
                Indicates a previous alarm condition has been
                cleared.  It is not required (unless specifically
                stated elsewhere on a case by case basis) that an
                alarm condition that has been cleared will produce
                a notification or other event containing an
                alarm severity with this value.

            indeterminate(2) -
                Indicates that the severity level cannot be
                determined. 

            critical(3) -
                Indicates that a service or safety affecting
                condition has occurred and an immediate
                corrective action is required.

            major(4) -
                Indicates that a service affecting condition has
                occurred and an urgent corrective action is
                required.

            minor(5) -
                Indicates the existence of a non-service affecting
                condition and that corrective action should be
                taken in order to prevent a more serious (for
                example, service or safety affecting) condition.

            warning(6) -
                Indicates the detection of a potential or impending
                service or safety affecting condition, before any
                significant effects have been felt.

            info(7) -
                Indicates an alarm condition that does not
                meet any other severity definition.  This can
                include important, but non-urgent, notices or
                informational events.
         "
    REFERENCE
         "ITU-X.733"
    SYNTAX INTEGER {
         cleared(1),
         indeterminate(2),
         critical(3),
         major(4),
         minor(5),
         warning(6),
         info(7)
    }

ModuleIndex ::= TEXTUAL-CONVENTION
    STATUS  current
    DESCRIPTION
       "The value of this object identifies the
       module for which this entry contains
       management information.  The value of this
       object for a particular module has the same
       value as the moduleIndex object."
   SYNTAX Integer32

PortIndex ::= TEXTUAL-CONVENTION
    STATUS  current
    DESCRIPTION
       "The value of this object identifies the
       port for which this entry contains
       management information.  The value of this
       object for a particular module has the same
       value as the portIndex object."
   SYNTAX Integer32

   MacAddressMask ::= TEXTUAL-CONVENTION
    STATUS current
    DESCRIPTION 
        "Represents Mac address Mask.
        "
    SYNTAX OCTET STRING (SIZE (6))
    
           
EnableFlag ::= TEXTUAL-CONVENTION
    STATUS current
    DESCRIPTION 
            "Description."
    SYNTAX INTEGER
    {
    enable(1),
    disable(2)
    }
                    
                    
DsQosQueueNumber        ::= TEXTUAL-CONVENTION
        STATUS  current
        DESCRIPTION     "."
        SYNTAX  Integer32(0..3)

DsQosCosNumber  ::= TEXTUAL-CONVENTION
    STATUS      current
    DESCRIPTION "."
    SYNTAX      Integer32(0..7)

DsQosTosNumber  ::= TEXTUAL-CONVENTION
    STATUS      current
    DESCRIPTION "."
    SYNTAX      Integer32(0..63)

DsQosDscpNumber ::= TEXTUAL-CONVENTION
    STATUS      current
    DESCRIPTION "."
    SYNTAX      Integer32(0..63)
        
DsIgmpVersion ::= TEXTUAL-CONVENTION
    STATUS current
    DESCRIPTION 
            "A value that represents the version of IGMP:
            
            version1(1)     : Version 1 of IGMP
            version2(2)     : Version 2 of IGMP
            version3(3)     : Version 3 of IGMP."
    SYNTAX INTEGER
            {
            version1(1),
            version2(2),
            version3(3)
            }

DsIgmpFilterMode ::= TEXTUAL-CONVENTION
                        STATUS current
                        DESCRIPTION 
                                "."
                        SYNTAX INTEGER
                                {
                                includeAllow(1),
                                includeBlock(2),
                                excludeAllow(3),
                                excludeBlock(4)
                                }
                                
                                
PortList ::= TEXTUAL-CONVENTION
    STATUS      current
    DESCRIPTION
        "Each octet within this value specifies a set of eight
        ports, with the first octet specifying ports 1 through
        8, the second octet specifying ports 9 through 16, etc.
        Within each octet, the most significant bit represents
        the lowest numbered port, and the least significant bit
        represents the highest numbered port.  Thus, each port
        of the bridge is represented by a single bit within the
        value of this object.  If that bit has a value of '1'
        then that port is included in the set of ports; the port
        is not included if its bit has a value of '0'."
    SYNTAX      OCTET STRING

VlanIndex ::= TEXTUAL-CONVENTION
    STATUS      current
    DESCRIPTION
        "A value used to index per-VLAN tables: values of 0 and
        4095 are not permitted; if the value is between 1 and
        4094 inclusive, it represents an IEEE 802.1Q VLAN-ID with
        global scope within a given bridged domain (see VlanId
        textual convention).  If the value is greater than 4095
        then it represents a VLAN with scope local to the
        particular agent, i.e. one without a global VLAN-ID
        assigned to it. Such VLANs are outside the scope of
        IEEE 802.1Q but it is convenient to be able to manage them
        in the same way using this MIB."
    SYNTAX      Unsigned32

VlanId ::= TEXTUAL-CONVENTION
    STATUS      current
    DESCRIPTION
        "A 12-bit VLAN ID used in the VLAN Tag header."
    SYNTAX      INTEGER (1..4094)
    
DsIgmpMode ::= TEXTUAL-CONVENTION
                        STATUS current
                        DESCRIPTION 
                                "A value that represents a working mode of IGMP protocol in a
                                device.
                                
                                auto(1)    : The system decides the working mode by itself.
                                
                                igmpOnly(2): Working on IGMP mode only.
                                
                                igmpCgmp(3): Working on both IGMP and CGMP modes."
                        SYNTAX INTEGER
                                {
                                auto(1),
                                igmpOnly(2),
                                igmpCgmp(3)
                                }


MediaGatewayId ::= TEXTUAL-CONVENTION 
         STATUS      current 
         DESCRIPTION  
          "Possible Media Gateway Id that can be used to identify 
           any media gateway uniquely" 
         SYNTAX      INTEGER (1..2147483647)
         
                         FkControlStatusType ::= TEXTUAL-CONVENTION
                        STATUS current
                        DESCRIPTION 
                                "The control status of an entity."
                        SYNTAX INTEGER
                                {
                                requestIdle(1),
                                requestBusy(2),
                                requestPassed(3),
                                requestFailed(4)
                                }

                FkControlRequestResultType ::= TEXTUAL-CONVENTION
                        STATUS current
                        DESCRIPTION 
                                "The request result."
                        SYNTAX INTEGER

                FkPermissionType ::= TEXTUAL-CONVENTION
                        STATUS current
                        DESCRIPTION 
                                "Description."
                        SYNTAX INTEGER
                                {
                                deny(0),
                                permit(1)
                                }

                FkTrafficType ::= TEXTUAL-CONVENTION
                        STATUS current
                        DESCRIPTION 
                                "Description."
                        SYNTAX INTEGER
                                {
                                broadcast(1),
                                multicast(2),
                                dlf(3)
                                }

                FkScopeType ::= TEXTUAL-CONVENTION
                        STATUS current
                        DESCRIPTION 
                                "Description."
                        SYNTAX INTEGER
                                {
                                port(1),
                                vlan(2)
                                }

                FkOperStateType ::= TEXTUAL-CONVENTION
                        STATUS current
                        DESCRIPTION 
                                "Description."
                        SYNTAX INTEGER
                                {
                                enabled(1),
                                disabled(2)
                                }

                FkAdminStateType ::= TEXTUAL-CONVENTION
                        STATUS current
                        DESCRIPTION 
                                "Description."
                        SYNTAX INTEGER
                                {
                                unlocked(1),
                                locked(2)
                                }

                FkCardType ::= TEXTUAL-CONVENTION
                        STATUS current
                        DESCRIPTION 
                                "Type for card type."
                        SYNTAX  OCTET STRING (SIZE (0..20))
                        
        
        FkSystemFileIndexType ::= TEXTUAL-CONVENTION
                        STATUS current
                        DESCRIPTION 
                                " Sytem file index type."
                        SYNTAX  INTEGER (1..8)
                        
        MacAddress ::= TEXTUAL-CONVENTION
            STATUS current
	DESCRIPTION 
                                ""
            SYNTAX OCTET STRING (SIZE (6))
            
        BridgeId ::= TEXTUAL-CONVENTION
            STATUS current
DESCRIPTION 
                                ""
            SYNTAX OCTET STRING (SIZE (8))
            
        Timeout ::= TEXTUAL-CONVENTION
                        STATUS current
DESCRIPTION 
                                ""
                        SYNTAX  INTEGER

END
