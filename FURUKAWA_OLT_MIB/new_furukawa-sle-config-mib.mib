--
-- FK-CONFIG-MIB.my
-- 

	FK-CONFIG-MIB DEFINITIONS ::= BEGIN
 
		IMPORTS
			fkoltg1040			
				FROM FKOLTG1040-SMI			
			OBJECT-GROUP			
				FROM SNMPv2-CONF			
			OBJECT-TYPE, MODULE-IDENTITY, OBJECT-IDENTITY			
				FROM SNMPv2-SMI;
	
	
		-- 1.3.6.1.4.1.10428 9 1.100.1
		fkMibConfig MODULE-IDENTITY 
			LAST-UPDATED "200510281731Z"		-- October 28, 2005 at 17:31 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkConfigMgmt 1 }

		
	
--
-- Type definitions
--
	
		FkVersionType ::= INTEGER
			{
			undef(0),
			one(1),
			two(2),
			three(3),
			four(4),
			five(5),
			six(6),
			seven(7)
			}

	
--
-- Node definitions
--
	
		-- 1.3.6.1.4.1.10428 9 1.100
		fkConfigMgmt OBJECT-IDENTITY
			STATUS current
			DESCRIPTION 
				"fkConfig"
			::= { fkoltg1040 100 }

		
		-- 1.3.6.1.4.1.10428 9 1.100.1.1
		fkMibConfInfo OBJECT IDENTIFIER ::= { fkMibConfig 1 }

		
		-- 1.3.6.1.4.1.10428 9 1.100.1.1.1
		fkMibConfInfoTable OBJECT-TYPE
			SYNTAX SEQUENCE OF FkMibConfInfoEntry
			MAX-ACCESS not-accessible
			STATUS current
			DESCRIPTION
				"FK MIB Configuring Information Table"
			::= { fkMibConfInfo 1 }

		
		-- 1.3.6.1.4.1.10428 9 1.100.2.1.1.1
		fkMibConfInfoEntry OBJECT-TYPE
			SYNTAX FkMibConfInfoEntry
			MAX-ACCESS not-accessible
			STATUS current
			DESCRIPTION
				"FK MIB Configuring Information Table Entries"
			INDEX { fkMibConfIndex }
			::= { fkMibConfInfoTable 1 }

		
		FkMibConfInfoEntry ::=
			SEQUENCE { 
				fkMibConfIndex
					INTEGER,
				fkMibConfVersion
					FkVersionType,
				fkMibConfDescription
					OCTET STRING,
				fkMibConfDirectory
					OBJECT IDENTIFIER
			 }

		-- 1.3.6.1.4.1.10428 9 1.100.2.1.1.1.1
		fkMibConfIndex OBJECT-TYPE
			SYNTAX INTEGER
				{
				systemManagement(1),
				device(2),
				bridge(3),
				faultManagement(4),
				performanceManagement(5),
				dhcp(6),
				security(7),
				snmp(8),
				rmon(9),
				qos(10),
				network(11),
				multicast(12),
				dhcpSnooping(13),
				mvQos(14),
				epon(20),
				sFlow(21),
				red(22),
				debug(99)
				}
			MAX-ACCESS read-only
			STATUS current
			DESCRIPTION
				"Index of FK MIBs"
			::= { fkMibConfInfoEntry 1 }

		
		-- 1.3.6.1.4.1.10428 9 1.100.2.1.1.1.2
		fkMibConfVersion OBJECT-TYPE
			SYNTAX FkVersionType
			MAX-ACCESS read-only
			STATUS current
			DESCRIPTION
				"Version of implemented specific-MIB"
			::= { fkMibConfInfoEntry 2 }

		
		-- 1.3.6.1.4.1.10428 9 1.100.2.1.1.1.3
		fkMibConfDescription OBJECT-TYPE
			SYNTAX OCTET STRING (SIZE (0..255))
			MAX-ACCESS read-only
			STATUS current
			DESCRIPTION
				"Description of indicated MIB"
			::= { fkMibConfInfoEntry 3 }

		
		-- 1.3.6.1.4.1.10428 9 1.100.2.1.1.1.4
		fkMibConfDirectory OBJECT-TYPE
			SYNTAX OBJECT IDENTIFIER
			MAX-ACCESS read-only
			STATUS current
			DESCRIPTION
				"Object identifier of module information folder for specific-MIB"
			::= { fkMibConfInfoEntry 4 }

		
		-- 1.3.6.1.4.1.10428 9 1.100.1.2
		fkModuleInfo OBJECT IDENTIFIER ::= { fkMibConfig 2 }

		
		-- 1.3.6.1.4.1.10428 9 1.100.1.2.1
		fkSystemModuleTable OBJECT-TYPE
			SYNTAX SEQUENCE OF FkSystemModuleEntry
			MAX-ACCESS not-accessible
			STATUS current
			DESCRIPTION
				"System Maintenance Module's Table"
			::= { fkModuleInfo 1 }

		
		-- 1.3.6.1.4.1.10428 9 1.100.2.5.1.1
		fkSystemModuleEntry OBJECT-TYPE
			SYNTAX FkSystemModuleEntry
			MAX-ACCESS not-accessible
			STATUS current
			DESCRIPTION
				"System Maintenance Module's Table Entries"
			INDEX { fkSystemModuleIndex }
			::= { fkSystemModuleTable 1 }

		
		FkSystemModuleEntry ::=
			SEQUENCE { 
				fkSystemModuleIndex
					INTEGER,
				fkSystemModuleVersion
					FkVersionType,
				fkSystemModuleObjectId
					OBJECT IDENTIFIER
			 }

		-- 1.3.6.1.4.1.10428 9 1.100.2.5.1.1.1
		fkSystemModuleIndex OBJECT-TYPE
			SYNTAX INTEGER
				{
				base(1),
				login(11),
				process(12),
				backup(21),
				syslogConf(31),
				syslogHistVol(32),
				syslogHistNVol(33),
				dnsServer(41),
				ntpServer(42),
				sshRemote(43),
				autoCLI(51),
				autoCliScript(52),
				autoCliSchedule(53),
				autoCliProfile(54),
				autoCliProfileServer(55),
				autoCliOutputMemory(56),
				autoResetPing(61),
				autoResetMemoryleak(62),
				coreDump(71),
				sysService(81),
				sysUser(82),
				parameter(91),
				watchDog(101)
				}
			MAX-ACCESS read-only
			STATUS current
			DESCRIPTION
				"Index of system maintenance's modules"
			::= { fkSystemModuleEntry 1 }

		
		-- 1.3.6.1.4.1.10428 9 1.100.2.5.1.1.2
		fkSystemModuleVersion OBJECT-TYPE
			SYNTAX FkVersionType
			MAX-ACCESS read-only
			STATUS current
			DESCRIPTION
				"Version of specific-module of system maintenance"
			::= { fkSystemModuleEntry 2 }

		
		-- 1.3.6.1.4.1.10428 9 1.100.2.5.1.1.3
		fkSystemModuleObjectId OBJECT-TYPE
			SYNTAX OBJECT IDENTIFIER
			MAX-ACCESS read-only
			STATUS current
			DESCRIPTION
				"Object identifier for specific-module table or group of system maintenance"
			::= { fkSystemModuleEntry 3 }

		
		-- 1.3.6.1.4.1.10428 9 1.100.1.2.2
		fkDeviceModuleTable OBJECT-TYPE
			SYNTAX SEQUENCE OF FkDeviceModuleEntry
			MAX-ACCESS not-accessible
			STATUS current
			DESCRIPTION
				"Device Module's Table"
			::= { fkModuleInfo 2 }

		
		-- 1.3.6.1.4.1.10428 9 1.100.2.5.2.1
		fkDeviceModuleEntry OBJECT-TYPE
			SYNTAX FkDeviceModuleEntry
			MAX-ACCESS not-accessible
			STATUS current
			DESCRIPTION
				"Device Module's Table Entries"
			INDEX { fkDeviceModuleIndex }
			::= { fkDeviceModuleTable 1 }

		
		FkDeviceModuleEntry ::=
			SEQUENCE { 
				fkDeviceModuleIndex
					INTEGER,
				fkDeviceModuleVersion
					FkVersionType,
				fkDeviceModuleObjectId
					OBJECT IDENTIFIER
			 }

		-- 1.3.6.1.4.1.10428 9 1.100.2.5.2.1.1
		fkDeviceModuleIndex OBJECT-TYPE
			SYNTAX INTEGER
				{
				base(1),
				ethernetPort(11),
				power(21),
				fanModule(22),
				fanUnit(23),
				temperature(24),
				battery(31),
				door(41),
				cpu(51)
				}
			MAX-ACCESS read-only
			STATUS current
			DESCRIPTION
				"Index of device's modules"
			::= { fkDeviceModuleEntry 1 }

		
		-- 1.3.6.1.4.1.10428 9 1.100.2.5.2.1.2
		fkDeviceModuleVersion OBJECT-TYPE
			SYNTAX FkVersionType
			MAX-ACCESS read-only
			STATUS current
			DESCRIPTION
				"Version of specific-module of device"
			::= { fkDeviceModuleEntry 2 }

		
		-- 1.3.6.1.4.1.10428 9 1.100.2.5.2.1.3
		fkDeviceModuleObjectId OBJECT-TYPE
			SYNTAX OBJECT IDENTIFIER
			MAX-ACCESS read-only
			STATUS current
			DESCRIPTION
				"Object identifier for specific-module table or group of device"
			::= { fkDeviceModuleEntry 3 }

		
		-- 1.3.6.1.4.1.10428 9 1.100.1.2.3
		fkBridgeModuleTable OBJECT-TYPE
			SYNTAX SEQUENCE OF FkBridgeModuleEntry
			MAX-ACCESS not-accessible
			STATUS current
			DESCRIPTION
				"Bridge Module's Table"
			::= { fkModuleInfo 3 }

		
		-- 1.3.6.1.4.1.10428 9 1.100.2.5.3.1
		fkBridgeModuleEntry OBJECT-TYPE
			SYNTAX FkBridgeModuleEntry
			MAX-ACCESS not-accessible
			STATUS current
			DESCRIPTION
				"Bridge Module's Table Entries"
			INDEX { fkBridgeModuleIndex }
			::= { fkBridgeModuleTable 1 }

		
		FkBridgeModuleEntry ::=
			SEQUENCE { 
				fkBridgeModuleIndex
					INTEGER,
				fkBridgeModuleVersion
					FkVersionType,
				fkBridgeModuleObjectId
					OBJECT IDENTIFIER
			 }

		-- 1.3.6.1.4.1.10428 9 1.100.2.5.3.1.1
		fkBridgeModuleIndex OBJECT-TYPE
			SYNTAX INTEGER
				{
				base(1),
				bridgePort(11),
				vlan(21),
				vlanMap(22),
				subnetBasedVlan(23),
				protocolBasedVlan(24),
				fdb(31),
				mfdb(32),
				stackDevice(41),
				stp(51),
				stpInstance(52),
				stpInstancePort(53),
				lag(61),
				lagLacp(62),
				lagLacpPort(63),
				erpDomain(71),
				lldpPort(81),
				lldpRemote(82),
				lldpStatistics(83),
				igmpSnoopConf(91),
				igmpSnoopGroup(92),
				portSecurity(101),
				portSecurityFdb(102),
				floodGuard(111),
				vlanTranslation(121)
				}
			MAX-ACCESS read-only
			STATUS current
			DESCRIPTION
				"Index of bridge's modules"
			::= { fkBridgeModuleEntry 1 }

		
		-- 1.3.6.1.4.1.10428 9 1.100.2.5.3.1.2
		fkBridgeModuleVersion OBJECT-TYPE
			SYNTAX FkVersionType
			MAX-ACCESS read-only
			STATUS current
			DESCRIPTION
				"Version of specific-module of bridge"
			::= { fkBridgeModuleEntry 2 }

		
		-- 1.3.6.1.4.1.10428 9 1.100.2.5.3.1.3
		fkBridgeModuleObjectId OBJECT-TYPE
			SYNTAX OBJECT IDENTIFIER
			MAX-ACCESS read-only
			STATUS current
			DESCRIPTION
				"Object identifier for specific-module table or group of bridge"
			::= { fkBridgeModuleEntry 3 }

		
		-- 1.3.6.1.4.1.10428 9 1.100.1.2.4
		fkFaultMgmtModuleTable OBJECT-TYPE
			SYNTAX SEQUENCE OF FkFaultMgmtModuleEntry
			MAX-ACCESS not-accessible
			STATUS current
			DESCRIPTION
				"Fault Management Module's Table"
			::= { fkModuleInfo 4 }

		
		-- 1.3.6.1.4.1.10428 9 1.100.2.5.4.1
		fkFaultMgmtModuleEntry OBJECT-TYPE
			SYNTAX FkFaultMgmtModuleEntry
			MAX-ACCESS not-accessible
			STATUS current
			DESCRIPTION
				"Fault Management Module's Table Entries"
			INDEX { fkFaultMgmtModuleIndex }
			::= { fkFaultMgmtModuleTable 1 }

		
		FkFaultMgmtModuleEntry ::=
			SEQUENCE { 
				fkFaultMgmtModuleIndex
					INTEGER,
				fkFaultMgmtModuleVersion
					FkVersionType,
				fkFaultMgmtModuleObjectId
					OBJECT IDENTIFIER
			 }

		-- 1.3.6.1.4.1.10428 9 1.100.2.5.4.1.1
		fkFaultMgmtModuleIndex OBJECT-TYPE
			SYNTAX INTEGER
				{
				base(1),
				alarmSeverity(11),
				alarmReport(12),
				alarmHistory(13),
				efmOam(21),
				advaSystem(31),
				advaGeneral(32),
				advaModule(33),
				advaOptical(34),
				advaOam(35)
				}
			MAX-ACCESS read-only
			STATUS current
			DESCRIPTION
				"Index of fault management's modules"
			::= { fkFaultMgmtModuleEntry 1 }

		
		-- 1.3.6.1.4.1.10428 9 1.100.2.5.4.1.2
		fkFaultMgmtModuleVersion OBJECT-TYPE
			SYNTAX FkVersionType
			MAX-ACCESS read-only
			STATUS current
			DESCRIPTION
				"Version of specific-module of fault management"
			::= { fkFaultMgmtModuleEntry 2 }

		
		-- 1.3.6.1.4.1.10428 9 1.100.2.5.4.1.3
		fkFaultMgmtModuleObjectId OBJECT-TYPE
			SYNTAX OBJECT IDENTIFIER
			MAX-ACCESS read-only
			STATUS current
			DESCRIPTION
				"Object identifier for specific-module table or group of fault management"
			::= { fkFaultMgmtModuleEntry 3 }

		
		-- 1.3.6.1.4.1.10428 9 1.100.1.2.5
		fkPerfMgmtModuleTable OBJECT-TYPE
			SYNTAX SEQUENCE OF FkPerfMgmtModuleEntry
			MAX-ACCESS not-accessible
			STATUS current
			DESCRIPTION
				"Performance Management Module's Table"
			::= { fkModuleInfo 5 }

		
		-- 1.3.6.1.4.1.10428 9 1.100.2.5.5.1
		fkPerfMgmtModuleEntry OBJECT-TYPE
			SYNTAX FkPerfMgmtModuleEntry
			MAX-ACCESS not-accessible
			STATUS current
			DESCRIPTION
				"Performance Management Module's Table Entries"
			INDEX { fkPerfMgmtModuleIndex }
			::= { fkPerfMgmtModuleTable 1 }

		
		FkPerfMgmtModuleEntry ::=
			SEQUENCE { 
				fkPerfMgmtModuleIndex
					INTEGER,
				fkPerfMgmtModuleVersion
					FkVersionType,
				fkPerfMgmtModuleObjectId
					OBJECT IDENTIFIER
			 }

		-- 1.3.6.1.4.1.10428 9 1.100.2.5.5.1.1
		fkPerfMgmtModuleIndex OBJECT-TYPE
			SYNTAX INTEGER
				{
				base(1),
				portThreshold(11),
				portRate(12),
				portStatistics(13),
				cpuStatistics(14)
				}
			MAX-ACCESS read-only
			STATUS current
			DESCRIPTION
				"Index of performance management's modules"
			::= { fkPerfMgmtModuleEntry 1 }

		
		-- 1.3.6.1.4.1.10428 9 1.100.2.5.5.1.2
		fkPerfMgmtModuleVersion OBJECT-TYPE
			SYNTAX FkVersionType
			MAX-ACCESS read-only
			STATUS current
			DESCRIPTION
				"Version of specific-module of performance management"
			::= { fkPerfMgmtModuleEntry 2 }

		
		-- 1.3.6.1.4.1.10428 9 1.100.2.5.5.1.3
		fkPerfMgmtModuleObjectId OBJECT-TYPE
			SYNTAX OBJECT IDENTIFIER
			MAX-ACCESS read-only
			STATUS current
			DESCRIPTION
				"Object identifier for specific-module table or group of performance management"
			::= { fkPerfMgmtModuleEntry 3 }

		
		-- 1.3.6.1.4.1.10428 9 1.100.1.2.6
		fkDhcpModuleTable OBJECT-TYPE
			SYNTAX SEQUENCE OF FkDhcpModuleEntry
			MAX-ACCESS not-accessible
			STATUS current
			DESCRIPTION
				"DHCP Module's Table"
			::= { fkModuleInfo 6 }

		
		-- 1.3.6.1.4.1.10428 9 1.100.2.5.6.1
		fkDhcpModuleEntry OBJECT-TYPE
			SYNTAX FkDhcpModuleEntry
			MAX-ACCESS not-accessible
			STATUS current
			DESCRIPTION
				"DHCP Module's Table Entries"
			INDEX { fkDhcpModuleIndex }
			::= { fkDhcpModuleTable 1 }

		
		FkDhcpModuleEntry ::=
			SEQUENCE { 
				fkDhcpModuleIndex
					INTEGER,
				fkDhcpModuleVersion
					FkVersionType,
				fkDhcpModuleObjectId
					OBJECT IDENTIFIER
			 }

		-- 1.3.6.1.4.1.10428 9 1.100.2.5.6.1.1
		fkDhcpModuleIndex OBJECT-TYPE
			SYNTAX INTEGER
				{
				base(1),
				pool(11),
				network(12),
				range(13),
				fixedAddress(14),
				dnsOption(15),
				defaultGwOption(16),
				serverOptions(17),
				dhcp4Logs(18),
				dhcp4Ntp(19),
				dhcp4PE(20),
				option82Port(31),
				option82Remote(32),
				option82Circuit(33),
				option82Class(34),
				option82ClassMap(35),
				option82ClassRange(36),
				filterPort(41),
				filterAddress(42),
				illegal(43),
				packetStats(51),
				leased(52),
				packetStatsPort(53),
				snopping(61),
				snoopVlan(62),
				snoopPort(63),
				snoopBindings(64),
				relayInterface(71),
				relayHelper(72),
				clientInterface(81),
				clientOptions(82),
				dhcp4PortLease(91)
				}
			MAX-ACCESS read-only
			STATUS current
			DESCRIPTION
				"Index of DHCP's modules"
			::= { fkDhcpModuleEntry 1 }

		
		-- 1.3.6.1.4.1.10428 9 1.100.2.5.6.1.2
		fkDhcpModuleVersion OBJECT-TYPE
			SYNTAX FkVersionType
			MAX-ACCESS read-only
			STATUS current
			DESCRIPTION
				"Version of specific-module of DHCP"
			::= { fkDhcpModuleEntry 2 }

		
		-- 1.3.6.1.4.1.10428 9 1.100.2.5.6.1.3
		fkDhcpModuleObjectId OBJECT-TYPE
			SYNTAX OBJECT IDENTIFIER
			MAX-ACCESS read-only
			STATUS current
			DESCRIPTION
				"Object identifier for specific-module table or group of DHCP"
			::= { fkDhcpModuleEntry 3 }

		
		-- 1.3.6.1.4.1.10428 9 1.100.1.2.7
		fkSecurityModuleTable OBJECT-TYPE
			SYNTAX SEQUENCE OF FkSecurityModuleEntry
			MAX-ACCESS not-accessible
			STATUS current
			DESCRIPTION
				"Security Module's Table"
			::= { fkModuleInfo 7 }

		
		-- 1.3.6.1.4.1.10428 9 1.100.2.5.7.1
		fkSecurityModuleEntry OBJECT-TYPE
			SYNTAX FkSecurityModuleEntry
			MAX-ACCESS not-accessible
			STATUS current
			DESCRIPTION
				"Security Module's Table Entries"
			INDEX { fkSecurityModuleIndex }
			::= { fkSecurityModuleTable 1 }

		
		FkSecurityModuleEntry ::=
			SEQUENCE { 
				fkSecurityModuleIndex
					INTEGER,
				fkSecurityModuleVersion
					FkVersionType,
				fkSecurityModuleObjectId
					OBJECT IDENTIFIER
			 }

		-- 1.3.6.1.4.1.10428 9 1.100.2.5.7.1.1
		fkSecurityModuleIndex OBJECT-TYPE
			SYNTAX INTEGER
				{
				base(1),
				aaa(11),
				radiusServer(12),
				tacacsServer(13),
				acl(21),
				dot1xPort(31),
				dot1xStatistics(32),
				arpInspection(41)
				}
			MAX-ACCESS read-only
			STATUS current
			DESCRIPTION
				"Index of security's modules"
			::= { fkSecurityModuleEntry 1 }

		
		-- 1.3.6.1.4.1.10428 9 1.100.2.5.7.1.2
		fkSecurityModuleVersion OBJECT-TYPE
			SYNTAX FkVersionType
			MAX-ACCESS read-only
			STATUS current
			DESCRIPTION
				"Version of specific-module of security"
			::= { fkSecurityModuleEntry 2 }

		
		-- 1.3.6.1.4.1.10428 9 1.100.2.5.7.1.3
		fkSecurityModuleObjectId OBJECT-TYPE
			SYNTAX OBJECT IDENTIFIER
			MAX-ACCESS read-only
			STATUS current
			DESCRIPTION
				"Object identifier for specific-module table or group of security"
			::= { fkSecurityModuleEntry 3 }

		
		-- 1.3.6.1.4.1.10428 9 1.100.1.2.8
		fkSnmpModuleTable OBJECT-TYPE
			SYNTAX SEQUENCE OF FkSnmpModuleEntry
			MAX-ACCESS not-accessible
			STATUS current
			DESCRIPTION
				"SNMP Module's Table"
			::= { fkModuleInfo 8 }

		
		-- 1.3.6.1.4.1.10428 9 1.100.2.5.8.1
		fkSnmpModuleEntry OBJECT-TYPE
			SYNTAX FkSnmpModuleEntry
			MAX-ACCESS not-accessible
			STATUS current
			DESCRIPTION
				"SNMP Module's Table Entries"
			INDEX { fkSnmpModuleIndex }
			::= { fkSnmpModuleTable 1 }

		
		FkSnmpModuleEntry ::=
			SEQUENCE { 
				fkSnmpModuleIndex
					INTEGER,
				fkSnmpModuleVersion
					FkVersionType,
				fkSnmpModuleObjectId
					OBJECT IDENTIFIER
			 }

		-- 1.3.6.1.4.1.10428 9 1.100.2.5.8.1.1
		fkSnmpModuleIndex OBJECT-TYPE
			SYNTAX INTEGER
				{
				base(1),
				com2Sec(11),
				trapHost(12),
				community(13),
				viewTreeFamily(14),
				access(15),
				securityToGroup(16),
				user(17),
				agent(18),
				snmpSeesion(19),
				snmpTrap(20),
				snmpTrapSource(21)
				}
			MAX-ACCESS read-only
			STATUS current
			DESCRIPTION
				"Index of SNMP's modules"
			::= { fkSnmpModuleEntry 1 }

		
		-- 1.3.6.1.4.1.10428 9 1.100.2.5.8.1.2
		fkSnmpModuleVersion OBJECT-TYPE
			SYNTAX FkVersionType
			MAX-ACCESS read-only
			STATUS current
			DESCRIPTION
				"Version of specific-module of SNMP"
			::= { fkSnmpModuleEntry 2 }

		
		-- 1.3.6.1.4.1.10428 9 1.100.2.5.8.1.3
		fkSnmpModuleObjectId OBJECT-TYPE
			SYNTAX OBJECT IDENTIFIER
			MAX-ACCESS read-only
			STATUS current
			DESCRIPTION
				"Object identifier for specific-module table or group of SNMP"
			::= { fkSnmpModuleEntry 3 }

		
		-- 1.3.6.1.4.1.10428 9 1.100.1.2.9
		fkRmonModuleTable OBJECT-TYPE
			SYNTAX SEQUENCE OF FkRmonModuleEntry
			MAX-ACCESS not-accessible
			STATUS current
			DESCRIPTION
				"RMON Module's Table"
			::= { fkModuleInfo 9 }

		
		-- 1.3.6.1.4.1.10428 9 1.100.2.5.9.1
		fkRmonModuleEntry OBJECT-TYPE
			SYNTAX FkRmonModuleEntry
			MAX-ACCESS not-accessible
			STATUS current
			DESCRIPTION
				"RMON Module's Table Entries"
			INDEX { fkRmonModuleIndex }
			::= { fkRmonModuleTable 1 }

		
		FkRmonModuleEntry ::=
			SEQUENCE { 
				fkRmonModuleIndex
					INTEGER,
				fkRmonModuleVersion
					FkVersionType,
				fkRmonModuleObjectId
					OBJECT IDENTIFIER
			 }

		-- 1.3.6.1.4.1.10428 9 1.100.2.5.9.1.1
		fkRmonModuleIndex OBJECT-TYPE
			SYNTAX INTEGER
				{
				base(1),
				event(11),
				alarm(12),
				history(13),
				etherStats(21)
				}
			MAX-ACCESS read-only
			STATUS current
			DESCRIPTION
				"Index of RMON's modules"
			::= { fkRmonModuleEntry 1 }

		
		-- 1.3.6.1.4.1.10428 9 1.100.2.5.9.1.2
		fkRmonModuleVersion OBJECT-TYPE
			SYNTAX FkVersionType
			MAX-ACCESS read-only
			STATUS current
			DESCRIPTION
				"Version of specific-module of RMON"
			::= { fkRmonModuleEntry 2 }

		
		-- 1.3.6.1.4.1.10428 9 1.100.2.5.9.1.3
		fkRmonModuleObjectId OBJECT-TYPE
			SYNTAX OBJECT IDENTIFIER
			MAX-ACCESS read-only
			STATUS current
			DESCRIPTION
				"Object identifier for specific-module table or group of RMON"
			::= { fkRmonModuleEntry 3 }

		
		-- 1.3.6.1.4.1.10428 9 1.100.1.2.10
		fkQosModuleTable OBJECT-TYPE
			SYNTAX SEQUENCE OF FkQosModuleEntry
			MAX-ACCESS not-accessible
			STATUS current
			DESCRIPTION
				"QoS Module's Table"
			::= { fkModuleInfo 10 }

		
		-- 1.3.6.1.4.1.10428 9 1.100.2.5.10.1
		fkQosModuleEntry OBJECT-TYPE
			SYNTAX FkQosModuleEntry
			MAX-ACCESS not-accessible
			STATUS current
			DESCRIPTION
				"QoS Module's Table Entries"
			INDEX { fkQosModuleIndex }
			::= { fkQosModuleTable 1 }

		
		FkQosModuleEntry ::=
			SEQUENCE { 
				fkQosModuleIndex
					INTEGER,
				fkQosModuleVersion
					FkVersionType,
				fkQosModuleObjectId
					OBJECT IDENTIFIER
			 }

		-- 1.3.6.1.4.1.10428 9 1.100.2.5.10.1.1
		fkQosModuleIndex OBJECT-TYPE
			SYNTAX INTEGER
				{
				base(1),
				baseV4(2),
				baseV6(3),
				trafficeProfile(11),
				portSchedule(12),
				queue(13),
				counter(14),
				colorMarking(15),
				userflow(21),
				flow(31),
				flowClassMap(32),
				flowPolicyMap(33),
				class(41),
				classFlowMap(42),
				classPolicyMap(43),
				policer(51),
				policy(61),
				policyFCMap(62),
				remark(71),
				remarkL3(72),
				remarkL2(73),
				redProfile(81),
				portRed(82)
				}
			MAX-ACCESS read-only
			STATUS current
			DESCRIPTION
				"Index of QoS's modules"
			::= { fkQosModuleEntry 1 }

		
		-- 1.3.6.1.4.1.10428 9 1.100.2.5.10.1.2
		fkQosModuleVersion OBJECT-TYPE
			SYNTAX FkVersionType
			MAX-ACCESS read-only
			STATUS current
			DESCRIPTION
				"Version of specific-module of QoS"
			::= { fkQosModuleEntry 2 }

		
		-- 1.3.6.1.4.1.10428 9 1.100.2.5.10.1.3
		fkQosModuleObjectId OBJECT-TYPE
			SYNTAX OBJECT IDENTIFIER
			MAX-ACCESS read-only
			STATUS current
			DESCRIPTION
				"Object identifier for specific-module table or group of QoS"
			::= { fkQosModuleEntry 3 }

		
		-- 1.3.6.1.4.1.10428 9 1.100.1.2.11
		fkNetworkModuleTable OBJECT-TYPE
			SYNTAX SEQUENCE OF FkNetworkModuleEntry
			MAX-ACCESS not-accessible
			STATUS current
			DESCRIPTION
				"Network Module's Table"
			::= { fkModuleInfo 11 }

		
		-- 1.3.6.1.4.1.10428 9 1.100.2.5.11.1
		fkNetworkModuleEntry OBJECT-TYPE
			SYNTAX FkNetworkModuleEntry
			MAX-ACCESS not-accessible
			STATUS current
			DESCRIPTION
				"Network Module's Table Entries"
			INDEX { fkNetworkModuleIndex }
			::= { fkNetworkModuleTable 1 }

		
		FkNetworkModuleEntry ::=
			SEQUENCE { 
				fkNetworkModuleIndex
					INTEGER,
				fkNetworkModuleVersion
					FkVersionType,
				fkNetworkModuleObjectId
					OBJECT IDENTIFIER
			 }

		-- 1.3.6.1.4.1.10428 9 1.100.2.5.11.1.1
		fkNetworkModuleIndex OBJECT-TYPE
			SYNTAX INTEGER
				{
				base(1),
				interface(11),
				ipAddress(12),
				arp(13),
				routing(21),
				dhcpClient(31)
				}
			MAX-ACCESS read-only
			STATUS current
			DESCRIPTION
				"Index of network's modules"
			::= { fkNetworkModuleEntry 1 }

		
		-- 1.3.6.1.4.1.10428 9 1.100.2.5.11.1.2
		fkNetworkModuleVersion OBJECT-TYPE
			SYNTAX FkVersionType
			MAX-ACCESS read-only
			STATUS current
			DESCRIPTION
				"Version of specific-module of network"
			::= { fkNetworkModuleEntry 2 }

		
		-- 1.3.6.1.4.1.10428 9 1.100.2.5.11.1.3
		fkNetworkModuleObjectId OBJECT-TYPE
			SYNTAX OBJECT IDENTIFIER
			MAX-ACCESS read-only
			STATUS current
			DESCRIPTION
				"Object identifier for specific-module table or group of network"
			::= { fkNetworkModuleEntry 3 }

		
		-- 1.3.6.1.4.1.10428 9 1.100.1.2.12
		fkMulticastModuleTable OBJECT-TYPE
			SYNTAX SEQUENCE OF FkMulticastModuleEntry
			MAX-ACCESS not-accessible
			STATUS current
			DESCRIPTION
				"Multicast Module's Table"
			::= { fkModuleInfo 12 }

		
		-- 1.3.6.1.4.1.10428 9 1.100.2.5.12.1
		fkMulticastModuleEntry OBJECT-TYPE
			SYNTAX FkMulticastModuleEntry
			MAX-ACCESS not-accessible
			STATUS current
			DESCRIPTION
				"Multicast Module's Table Entries"
			INDEX { fkMulticastModuleIndex }
			::= { fkMulticastModuleTable 1 }

		
		FkMulticastModuleEntry ::=
			SEQUENCE { 
				fkMulticastModuleIndex
					INTEGER,
				fkMulticastModuleVersion
					FkVersionType,
				fkMulticastModuleObjectId
					OBJECT IDENTIFIER
			 }

		-- 1.3.6.1.4.1.10428 9 1.100.2.5.12.1.1
		fkMulticastModuleIndex OBJECT-TYPE
			SYNTAX INTEGER
				{
				base(1),
				mrouteBase(11),
				mroute(12),
				mrouteNextHop(13),
				mrouteInterface(14),
				igmpBase(21),
				igmpSsmMapping(22),
				igmpHelperVlan(31),
				igmpHelperGroup(32),
				igmpInterface(41),
				igmpCache(42),
				igmpSource(43),
				igmpGroupState(44),
				igmpSnoopVlan(51),
				igmpSnoopGroup(52),
				igmpSnoopSource(53),
				igmpSnoopReport(54),
				igmpSnoopPort(55),
				igmpSnoopPortStats(56),
				igmpProfile(61),
				igmpProfileRange(62),
				igmpFilterPort(63),
				mvrPort(71),
				mvrGroup(72),
				pimBase(81),
				pimSnoopVlan(91),
				pimAgent(101),
				igmpProxyBase(111),
				igmpProxyInterface(121)
				}
			MAX-ACCESS read-only
			STATUS current
			DESCRIPTION
				"Index of multicast's modules"
			::= { fkMulticastModuleEntry 1 }

		
		-- 1.3.6.1.4.1.10428 9 1.100.2.5.12.1.2
		fkMulticastModuleVersion OBJECT-TYPE
			SYNTAX FkVersionType
			MAX-ACCESS read-only
			STATUS current
			DESCRIPTION
				"Version of specific-module of multicast"
			::= { fkMulticastModuleEntry 2 }

		
		-- 1.3.6.1.4.1.10428 9 1.100.2.5.12.1.3
		fkMulticastModuleObjectId OBJECT-TYPE
			SYNTAX OBJECT IDENTIFIER
			MAX-ACCESS read-only
			STATUS current
			DESCRIPTION
				"Object identifier for specific-module table or group of multicast"
			::= { fkMulticastModuleEntry 3 }

		
		-- 1.3.6.1.4.1.10428 9 1.100.1.2.13
		fkDhcpSnoopModuleTable OBJECT-TYPE
			SYNTAX SEQUENCE OF FkDhcpSnoopModuleEntry
			MAX-ACCESS not-accessible
			STATUS current
			DESCRIPTION
				"DHCP Snooping Module's Table (obsolated module)"
			::= { fkModuleInfo 13 }

		
		-- 1.3.6.1.4.1.10428 9 1.100.1.2.13.1
		fkDhcpSnoopModuleEntry OBJECT-TYPE
			SYNTAX FkDhcpSnoopModuleEntry
			MAX-ACCESS not-accessible
			STATUS current
			DESCRIPTION
				"Multicast Module's Table Entries"
			INDEX { fkDhcpSnoopModuleIndex }
			::= { fkDhcpSnoopModuleTable 1 }

		
		FkDhcpSnoopModuleEntry ::=
			SEQUENCE { 
				fkDhcpSnoopModuleIndex
					INTEGER,
				fkDhcpSnoopModuleVersion
					FkVersionType,
				fkDhcpSnoopModuleObjectId
					OBJECT IDENTIFIER
			 }

		-- 1.3.6.1.4.1.10428 9 1.100.1.2.13.1.1
		fkDhcpSnoopModuleIndex OBJECT-TYPE
			SYNTAX INTEGER
				{
				base(1),
				portSrcGuardConf(11),
				portSrcGuardAddress(12)
				}
			MAX-ACCESS read-only
			STATUS current
			DESCRIPTION
				"Index of DHCP snooping's modules"
			::= { fkDhcpSnoopModuleEntry 1 }

		
		-- 1.3.6.1.4.1.10428 9 1.100.1.2.13.1.2
		fkDhcpSnoopModuleVersion OBJECT-TYPE
			SYNTAX FkVersionType
			MAX-ACCESS read-only
			STATUS current
			DESCRIPTION
				"Version of specific-module of DHCP snooping"
			::= { fkDhcpSnoopModuleEntry 2 }

		
		-- 1.3.6.1.4.1.10428 9 1.100.1.2.13.1.3
		fkDhcpSnoopModuleObjectId OBJECT-TYPE
			SYNTAX OBJECT IDENTIFIER
			MAX-ACCESS read-only
			STATUS current
			DESCRIPTION
				"Object identifier for specific-module table or group of DHCP snooping"
			::= { fkDhcpSnoopModuleEntry 3 }

		
		-- 1.3.6.1.4.1.10428 9 1.100.1.2.14
		fkMvQosModuleTable OBJECT-TYPE
			SYNTAX SEQUENCE OF FkMvQosModuleEntry
			MAX-ACCESS not-accessible
			STATUS current
			DESCRIPTION
				"MvQoS Module's Table"
			::= { fkModuleInfo 14 }

		
		-- 1.3.6.1.4.1.10428 9 1.100.1.2.14.1
		fkMvQosModuleEntry OBJECT-TYPE
			SYNTAX FkMvQosModuleEntry
			MAX-ACCESS not-accessible
			STATUS current
			DESCRIPTION
				"MvQoS Module's Table Entries"
			INDEX { fkMvQosModuleIndex }
			::= { fkMvQosModuleTable 1 }

		
		FkMvQosModuleEntry ::=
			SEQUENCE { 
				fkMvQosModuleIndex
					INTEGER,
				fkMvQosModuleVersion
					FkVersionType,
				fkMvQosModuleObjectId
					OBJECT IDENTIFIER
			 }

		-- 1.3.6.1.4.1.10428 9 1.100.1.2.14.1.1
		fkMvQosModuleIndex OBJECT-TYPE
			SYNTAX INTEGER
				{
				base(1),
				baseV4(2),
				baseV6(3),
				bridgePort2Tc(11),
				bridgeProtocol2Tc(12),
				bridgeSubnet2Tc(13),
				bridgeMac2Tc(14),
				bridgeUp2TcEnable(15),
				bridgeUp2Tc(16),
				bridgeTc2Up(17),
				bridgeUp2Dp(18),
				inLifMark(21),
				routerMark(31)
				}
			MAX-ACCESS read-only
			STATUS current
			DESCRIPTION
				"Index of MvQoS's modules.(obsolated module)"
			::= { fkMvQosModuleEntry 1 }

		
		-- 1.3.6.1.4.1.10428 9 1.100.1.2.14.1.2
		fkMvQosModuleVersion OBJECT-TYPE
			SYNTAX FkVersionType
			MAX-ACCESS read-only
			STATUS current
			DESCRIPTION
				"Version of specific-module of MvQoS."
			::= { fkMvQosModuleEntry 2 }

		
		-- 1.3.6.1.4.1.10428 9 1.100.1.2.14.1.3
		fkMvQosModuleObjectId OBJECT-TYPE
			SYNTAX OBJECT IDENTIFIER
			MAX-ACCESS read-only
			STATUS current
			DESCRIPTION
				"Object identifier for specific-module table or group of MvQoS."
			::= { fkMvQosModuleEntry 3 }

		
		-- 1.3.6.1.4.1.10428 9 1.100.1.2.20
		fkEponModuleTable OBJECT-TYPE
			SYNTAX SEQUENCE OF FkEponModuleEntry
			MAX-ACCESS not-accessible
			STATUS current
			DESCRIPTION
				"EPON Module's Table"
			::= { fkModuleInfo 20 }

		
		-- 1.3.6.1.4.1.10428 9 1.100.1.2.20.1
		fkEponModuleEntry OBJECT-TYPE
			SYNTAX FkEponModuleEntry
			MAX-ACCESS not-accessible
			STATUS current
			DESCRIPTION
				"EPON Module's Table Entries"
			INDEX { fkEponModuleIndex }
			::= { fkEponModuleTable 1 }

		
		FkEponModuleEntry ::=
			SEQUENCE { 
				fkEponModuleIndex
					INTEGER,
				fkEponModuleVersion
					FkVersionType,
				fkEponModuleObjectId
					OBJECT IDENTIFIER
			 }

		-- 1.3.6.1.4.1.10428 9 1.100.1.2.20.1.1
		fkEponModuleIndex OBJECT-TYPE
			SYNTAX INTEGER
				{
				base(1),
				olt(11),
				onu(21),
				vlan(31),
				profile(41),
				profileQueue(42),
				alarm(51),
				oltStatistics(61),
				onuStatistics(62)
				}
			MAX-ACCESS read-only
			STATUS current
			DESCRIPTION
				"Index of EPON's modules.(obsolated module)"
			::= { fkEponModuleEntry 1 }

		
		-- 1.3.6.1.4.1.10428 9 1.100.1.2.20.1.2
		fkEponModuleVersion OBJECT-TYPE
			SYNTAX FkVersionType
			MAX-ACCESS read-only
			STATUS current
			DESCRIPTION
				"Version of specific-module of EPON."
			::= { fkEponModuleEntry 2 }

		
		-- 1.3.6.1.4.1.10428 9 1.100.1.2.20.1.3
		fkEponModuleObjectId OBJECT-TYPE
			SYNTAX OBJECT IDENTIFIER
			MAX-ACCESS read-only
			STATUS current
			DESCRIPTION
				"Object identifier for specific-module table or group of EPON."
			::= { fkEponModuleEntry 3 }

		
		-- 1.3.6.1.4.1.10428 9 1.100.1.2.21
		fkSFlowModuleTable OBJECT-TYPE
			SYNTAX SEQUENCE OF FkSFlowModuleEntry
			MAX-ACCESS not-accessible
			STATUS current
			DESCRIPTION
				"sFlow Module's Table"
			::= { fkModuleInfo 21 }

		
		-- 1.3.6.1.4.1.10428 9 1.100.1.2.21.1
		fkSFlowModuleEntry OBJECT-TYPE
			SYNTAX FkSFlowModuleEntry
			MAX-ACCESS not-accessible
			STATUS current
			DESCRIPTION
				"sFlow Module's Table Entries"
			INDEX { fkSFlowModuleIndex }
			::= { fkSFlowModuleTable 1 }

		
		FkSFlowModuleEntry ::=
			SEQUENCE { 
				fkSFlowModuleIndex
					INTEGER,
				fkSFlowModuleVersion
					FkVersionType,
				fkSFlowModuleObjectId
					OBJECT IDENTIFIER
			 }

		-- 1.3.6.1.4.1.10428 9 1.100.1.2.21.1.1
		fkSFlowModuleIndex OBJECT-TYPE
			SYNTAX INTEGER
				{
				base(1),
				receiver(11),
				flowSampler(12),
				counterPoller(13)
				}
			MAX-ACCESS read-only
			STATUS current
			DESCRIPTION
				"Index of sFlow's modules.(obsolated module)"
			::= { fkSFlowModuleEntry 1 }

		
		-- 1.3.6.1.4.1.10428 9 1.100.1.2.21.1.2
		fkSFlowModuleVersion OBJECT-TYPE
			SYNTAX FkVersionType
			MAX-ACCESS read-only
			STATUS current
			DESCRIPTION
				"Version of specific-module of sFlow."
			::= { fkSFlowModuleEntry 2 }

		
		-- 1.3.6.1.4.1.10428 9 1.100.1.2.21.1.3
		fkSFlowModuleObjectId OBJECT-TYPE
			SYNTAX OBJECT IDENTIFIER
			MAX-ACCESS read-only
			STATUS current
			DESCRIPTION
				"Object identifier for specific-module table or group of sFlow."
			::= { fkSFlowModuleEntry 3 }

		
		-- 1.3.6.1.4.1.10428 9 1.100.1.2.22
		fkRedModuleTable OBJECT-TYPE
			SYNTAX SEQUENCE OF FkRedModuleEntry
			MAX-ACCESS not-accessible
			STATUS current
			DESCRIPTION
				"Description."
			::= { fkModuleInfo 22 }

		
		-- 1.3.6.1.4.1.10428 9 1.100.1.2.22.1
		fkRedModuleEntry OBJECT-TYPE
			SYNTAX FkRedModuleEntry
			MAX-ACCESS not-accessible
			STATUS current
			DESCRIPTION
				"Description."
			INDEX { fkRedModuleIndex }
			::= { fkRedModuleTable 1 }

		
		FkRedModuleEntry ::=
			SEQUENCE { 
				fkRedModuleIndex
					INTEGER,
				fkRedModuleVersion
					FkVersionType,
				fkRedModuleObjectId
					OBJECT IDENTIFIER
			 }

		-- 1.3.6.1.4.1.10428 9 1.100.1.2.22.1.1
		fkRedModuleIndex OBJECT-TYPE
			SYNTAX INTEGER { base(1) }
			MAX-ACCESS read-only
			STATUS current
			DESCRIPTION
				"Description."
			::= { fkRedModuleEntry 1 }

		
		-- 1.3.6.1.4.1.10428 9 1.100.1.2.22.1.2
		fkRedModuleVersion OBJECT-TYPE
			SYNTAX FkVersionType
			MAX-ACCESS read-only
			STATUS current
			DESCRIPTION
				"Description."
			::= { fkRedModuleEntry 2 }

		
		-- 1.3.6.1.4.1.10428 9 1.100.1.2.22.1.3
		fkRedModuleObjectId OBJECT-TYPE
			SYNTAX OBJECT IDENTIFIER
			MAX-ACCESS read-only
			STATUS current
			DESCRIPTION
				"Description."
			::= { fkRedModuleEntry 3 }

		
		-- 1.3.6.1.4.1.10428 9 1.100.1.2.99
		fkDebugModuleTable OBJECT-TYPE
			SYNTAX SEQUENCE OF FkDebugModuleEntry
			MAX-ACCESS not-accessible
			STATUS current
			DESCRIPTION
				"sFlow Module's Table"
			::= { fkModuleInfo 99 }

		
		-- 1.3.6.1.4.1.10428 9 1.100.1.2.99.1
		fkDebugModuleEntry OBJECT-TYPE
			SYNTAX FkDebugModuleEntry
			MAX-ACCESS not-accessible
			STATUS current
			DESCRIPTION
				"sFlow Module's Table Entries"
			INDEX { fkSFlowModuleIndex }
			::= { fkDebugModuleTable 1 }

		
		FkDebugModuleEntry ::=
			SEQUENCE { 
				fkDebugModuleIndex
					INTEGER,
				fkDebugModuleVersion
					FkVersionType,
				fkDebugModuleObjectId
					OBJECT IDENTIFIER
			 }

		-- 1.3.6.1.4.1.10428 9 1.100.1.2.99.1.1
		fkDebugModuleIndex OBJECT-TYPE
			SYNTAX INTEGER { debugBase(1) }
			MAX-ACCESS read-only
			STATUS current
			DESCRIPTION
				"Index of sFlow's modules.(obsolated module)"
			::= { fkDebugModuleEntry 1 }

		
		-- 1.3.6.1.4.1.10428 9 1.100.1.2.99.1.2
		fkDebugModuleVersion OBJECT-TYPE
			SYNTAX FkVersionType
			MAX-ACCESS read-only
			STATUS current
			DESCRIPTION
				"Version of specific-module of sFlow."
			::= { fkDebugModuleEntry 2 }

		
		-- 1.3.6.1.4.1.10428 9 1.100.1.2.99.1.3
		fkDebugModuleObjectId OBJECT-TYPE
			SYNTAX OBJECT IDENTIFIER
			MAX-ACCESS read-only
			STATUS current
			DESCRIPTION
				"Object identifier for specific-module table or group of sFlow."
			::= { fkDebugModuleEntry 3 }

		
		-- 1.3.6.1.4.1.10428 9 1.100.1.3
		fkMibConfGroup OBJECT-GROUP
			OBJECTS { fkMibConfIndex, fkMibConfVersion, fkMibConfDescription, fkMibConfDirectory, fkSystemModuleIndex, 
				fkSystemModuleVersion, fkSystemModuleObjectId, fkDeviceModuleIndex, fkDeviceModuleVersion, fkDeviceModuleObjectId, 
				fkBridgeModuleIndex, fkBridgeModuleVersion, fkBridgeModuleObjectId, fkFaultMgmtModuleIndex, fkFaultMgmtModuleVersion, 
				fkFaultMgmtModuleObjectId, fkPerfMgmtModuleIndex, fkPerfMgmtModuleVersion, fkPerfMgmtModuleObjectId, fkDhcpModuleIndex, 
				fkDhcpModuleVersion, fkDhcpModuleObjectId, fkSecurityModuleIndex, fkSecurityModuleVersion, fkSecurityModuleObjectId, 
				fkSnmpModuleIndex, fkSnmpModuleVersion, fkSnmpModuleObjectId, fkRmonModuleIndex, fkRmonModuleVersion, 
				fkRmonModuleObjectId, fkQosModuleIndex, fkQosModuleVersion, fkQosModuleObjectId, fkNetworkModuleIndex, 
				fkNetworkModuleVersion, fkNetworkModuleObjectId, fkMulticastModuleIndex, fkMulticastModuleVersion, fkMulticastModuleObjectId, 
				fkDhcpSnoopModuleIndex, fkDhcpSnoopModuleVersion, fkDhcpSnoopModuleObjectId, fkSFlowModuleIndex, fkSFlowModuleVersion, 
				fkDebugModuleIndex, fkDebugModuleVersion, fkDebugModuleObjectId, fkRedModuleIndex, fkRedModuleVersion, 
				fkRedModuleObjectId, fkSFlowModuleObjectId, fkMvQosModuleIndex, fkMvQosModuleVersion, fkMvQosModuleObjectId, 
				fkEponModuleIndex, fkEponModuleVersion, fkEponModuleObjectId }
			STATUS current
			DESCRIPTION 
				"Description."
			::= { fkMibConfig 3 }

		
	
	END

--
-- FK-CONFIG-MIB.my
--
