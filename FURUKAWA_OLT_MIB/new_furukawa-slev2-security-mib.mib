--
-- fkv2-security-mib.mib
-- MIB generated by MG-SOFT Visual MIB Builder Version 6.0  Build 88
-- Tuesday, December 04, 2012 at 15:17:22
--

	FKV2-Security-MIB DEFINITIONS ::= BEGIN
 
		IMPORTS
			fkV2Mgmt			
				FROM FKOLTG1040-SMI			
			FkControlStatusType, FkControlRequestResultType			
				FROM FK-TC-MIB			
			OBJECT-GROUP, NOTIFICATION-GROUP			
				FROM SNMPv2-CONF			
			TimeTicks, IpAddress, Integer32, Gauge32, Counter32, 
			Counter64, BITS, OBJECT-TYPE, MODULE-IDENTITY, NOTIFICATION-TYPE			
				FROM SNMPv2-SMI			
			TimeStamp, TEXTUAL-CONVENTION			
				FROM SNMPv2-TC;
	
	
		-- 1.3.6.1.4.1.10428 9 1.102.7
		fkV2Security MODULE-IDENTITY 
			LAST-UPDATED "200605051406Z"		-- May 05, 2006 at 14:06 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkV2Mgmt 7 }

		
	
--
-- Type definitions
--
	
		IntFlowIndex ::= INTEGER (1..1024)

		IntClassIndex ::= INTEGER (1..1024)

		IntPolicyIndex ::= INTEGER (1..1024)

		OctetName ::= OCTET STRING (SIZE (1..64))

		IntIpAddrMask ::= INTEGER (0..32)

		IntProtocolType ::= INTEGER (-1 | 0..255)

		IntL4Port ::= INTEGER (-1 | 0..65535)

		IntIcmpType ::= INTEGER (-1 | 0..255)

		IntIcmpCode ::= INTEGER (-1 | 0..255)

		IntInternetProtocolFlag ::= INTEGER
			{
			nothing(-1),
			tcp(1),
			ucp(2),
			icmp(3)
			}

		IntRulePriority ::= INTEGER
			{
			nothing(-1),
			low(1),
			medium(2),
			high(3),
			highest(4)
			}

		IntFlowClass ::= INTEGER
			{
			nothing(-1),
			flow(1),
			class(2),
			both(4)
			}

		IntInterfaceIndex ::= INTEGER (-1 | 1..512)

		IntFlowOrClass ::= INTEGER
			{
			flow(1),
			class(2)
			}

		IntPermit ::= INTEGER
			{
			deny(1),
			permit(2),
			none(3)
			}

	
--
-- Textual conventions
--
	
--
-- Node definitions
--
	
		-- 1.3.6.1.4.1.10428 9 1.102.7.1
		fkV2SecurityBase OBJECT IDENTIFIER ::= { fkV2Security 1 }

		
		-- 1.3.6.1.4.1.10428 9 1.102.7.2
		fkVSecurity4 OBJECT IDENTIFIER ::= { fkV2Security 2 }

		
		-- 1.3.6.1.4.1.10428 9 1.102.7.2.5
		fkV2SecurityACL OBJECT IDENTIFIER ::= { fkVSecurity4 5 }

		
		-- 1.3.6.1.4.1.10428 9 1.102.7.2.5.1
		fkV2Security4ACLBase OBJECT IDENTIFIER ::= { fkV2SecurityACL 1 }

		
		-- 1.3.6.1.4.1.10428 9 1.102.7.2.5.2
		fkV2Security4ACLFlow OBJECT IDENTIFIER ::= { fkV2SecurityACL 2 }

		
		-- 1.3.6.1.4.1.10428 9 1.102.7.2.5.2.1
		fkV2Security4ACLFlowInfo OBJECT IDENTIFIER ::= { fkV2Security4ACLFlow 1 }

		
		-- 1.3.6.1.4.1.10428 9 1.102.7.2.5.2.1.1
		fkV2Security4ACLFlowTable OBJECT-TYPE
			SYNTAX SEQUENCE OF FkV2Security4ACLFlowEntry
			MAX-ACCESS not-accessible
			STATUS current
			DESCRIPTION
				"ACL flow table."
			::= { fkV2Security4ACLFlowInfo 1 }

		
		-- 1.3.6.1.4.1.10428 9 1.102.7.2.5.2.1.1.1
		fkV2Security4ACLFlowEntry OBJECT-TYPE
			SYNTAX FkV2Security4ACLFlowEntry
			MAX-ACCESS not-accessible
			STATUS current
			DESCRIPTION
				"key: fkV2Security4ACLFlowIndex"
			INDEX { fkV2Security4ACLFlowIndex }
			::= { fkV2Security4ACLFlowTable 1 }

		
		FkV2Security4ACLFlowEntry ::=
			SEQUENCE { 
				fkV2Security4ACLFlowIndex
					INTEGER,
				fkV2Security4ACLFlowName
					OctetName,
				fkV2Security4ACLFlowSrcIpAddr
					IpAddress,
				fkV2Security4ACLFlowSrcIpAddrMask
					IntIpAddrMask,
				fkV2Security4ACLFlowDstIpAddr
					IpAddress,
				fkV2Security4ACLFlowDstIpAddrMask
					IntIpAddrMask,
				fkV2Security4ACLFlowProtocolType
					IntProtocolType,
				fkV2Security4ACLFlowTcpSrcStartPort
					IntL4Port,
				fkV2Security4ACLFlowTcpSrcEndPort
					IntL4Port,
				fkV2Security4ACLFlowTcpDstStartPort
					IntL4Port,
				fkV2Security4ACLFlowTcpDstEndPort
					IntL4Port,
				fkV2Security4ACLFlowTcpFlag
					BITS,
				fkV2Security4ACLFlowUdpSrcStartPort
					IntL4Port,
				fkV2Security4ACLFlowUdpSrcEndPort
					IntL4Port,
				fkV2Security4ACLFlowUdpDstStartPort
					IntL4Port,
				fkV2Security4ACLFlowUdpDstEndPort
					IntL4Port,
				fkV2Security4ACLFlowIcmpType
					IntIcmpType,
				fkV2Security4ACLFlowIcmpCode
					IntIcmpCode,
				fkV2Security4ACLFlowHdrlen
					INTEGER,
				fkV2Security4ACLFlowIpFlag
					INTEGER
			 }

		-- 1.3.6.1.4.1.10428 9 1.102.7.2.5.2.1.1.1.1
		fkV2Security4ACLFlowIndex OBJECT-TYPE
			SYNTAX INTEGER (1..1024)
			MAX-ACCESS read-only
			STATUS current
			DESCRIPTION
				"The index of flow"
			::= { fkV2Security4ACLFlowEntry 1 }

		
		-- 1.3.6.1.4.1.10428 9 1.102.7.2.5.2.1.1.1.2
		fkV2Security4ACLFlowName OBJECT-TYPE
			SYNTAX OctetName
			MAX-ACCESS read-only
			STATUS current
			DESCRIPTION
				"The name of flow"
			::= { fkV2Security4ACLFlowEntry 2 }

		
		-- 1.3.6.1.4.1.10428 9 1.102.7.2.5.2.1.1.1.3
		fkV2Security4ACLFlowSrcIpAddr OBJECT-TYPE
			SYNTAX IpAddress
			MAX-ACCESS read-only
			STATUS current
			DESCRIPTION
				"The IP address to match against the packet's source IP address.
				The value of 0.0.0.0 means any(not set)
				"
			::= { fkV2Security4ACLFlowEntry 3 }

		
		-- 1.3.6.1.4.1.10428 9 1.102.7.2.5.2.1.1.1.4
		fkV2Security4ACLFlowSrcIpAddrMask OBJECT-TYPE
			SYNTAX IntIpAddrMask
			MAX-ACCESS read-only
			STATUS current
			DESCRIPTION
				"The mask of source IP address
				The value of -1 means any(not set)
				"
			::= { fkV2Security4ACLFlowEntry 4 }

		
		-- 1.3.6.1.4.1.10428 9 1.102.7.2.5.2.1.1.1.5
		fkV2Security4ACLFlowDstIpAddr OBJECT-TYPE
			SYNTAX IpAddress
			MAX-ACCESS read-only
			STATUS current
			DESCRIPTION
				"The IP address to match against the packet's destination IP address.
				The value of 0.0.0.0 means any(not set)
				"
			::= { fkV2Security4ACLFlowEntry 5 }

		
		-- 1.3.6.1.4.1.10428 9 1.102.7.2.5.2.1.1.1.6
		fkV2Security4ACLFlowDstIpAddrMask OBJECT-TYPE
			SYNTAX IntIpAddrMask
			MAX-ACCESS read-only
			STATUS current
			DESCRIPTION
				"The mask of destination IP address
				The value of -1 means any(not set)
				"
			::= { fkV2Security4ACLFlowEntry 6 }

		
		-- 1.3.6.1.4.1.10428 9 1.102.7.2.5.2.1.1.1.7
		fkV2Security4ACLFlowProtocolType OBJECT-TYPE
			SYNTAX IntProtocolType
			MAX-ACCESS read-only
			STATUS current
			DESCRIPTION
				"The type of IP protocol
				The flat internet protocol is from fkV2QoS4FlowTcpSrcStartPort to fkV2QoS4FlowIcmpCode
				If the value is tcp(6),
				From fkV2QoS4FlowTcpSrcStartPort to fkV2QoS4FlowTcpFlag value is available
				If the value is u¿¡(17),
				From fkV2QoS4FlowUdpSrcStartPort to fkV2QoS4FlowUdpDstEndPort value is available
				If the value is icmp(1),
				The value of fkV2QoS4FlowIcmpType and fkV2QoS4FlowIcmpCode is available
				The value of -1 means any(not set)
				Otherwise, from fkV2QoS4FlowTcpSrcStartPort to fkV2QoS4FlowIcmpCode value is not available
				The value of -1 means any(not set)
				"
			::= { fkV2Security4ACLFlowEntry 7 }

		
		-- 1.3.6.1.4.1.10428 9 1.102.7.2.5.2.1.1.1.8
		fkV2Security4ACLFlowTcpSrcStartPort OBJECT-TYPE
			SYNTAX IntL4Port
			MAX-ACCESS read-only
			STATUS current
			DESCRIPTION
				"The start source port in range of source port in TCP packet
				The value of -1 means any(not set)
				"
			::= { fkV2Security4ACLFlowEntry 8 }

		
		-- 1.3.6.1.4.1.10428 9 1.102.7.2.5.2.1.1.1.9
		fkV2Security4ACLFlowTcpSrcEndPort OBJECT-TYPE
			SYNTAX IntL4Port
			MAX-ACCESS read-only
			STATUS current
			DESCRIPTION
				"The end source port in range of source port in TCP packet
				The value of -1 means any(not set)
				"
			::= { fkV2Security4ACLFlowEntry 9 }

		
		-- 1.3.6.1.4.1.10428 9 1.102.7.2.5.2.1.1.1.10
		fkV2Security4ACLFlowTcpDstStartPort OBJECT-TYPE
			SYNTAX IntL4Port
			MAX-ACCESS read-only
			STATUS current
			DESCRIPTION
				"The start destination port in range of source port in TCP packet. The value of -1 means any(not set)"
			::= { fkV2Security4ACLFlowEntry 10 }

		
		-- 1.3.6.1.4.1.10428 9 1.102.7.2.5.2.1.1.1.11
		fkV2Security4ACLFlowTcpDstEndPort OBJECT-TYPE
			SYNTAX IntL4Port
			MAX-ACCESS read-only
			STATUS current
			DESCRIPTION
				"The end destination port in range of destination port in TCP packet. The value of -1 means any(not set)"
			::= { fkV2Security4ACLFlowEntry 11 }

		
		-- 1.3.6.1.4.1.10428 9 1.102.7.2.5.2.1.1.1.12
		fkV2Security4ACLFlowTcpFlag OBJECT-TYPE
			SYNTAX BITS
				{
				reserv0(0),
				reserv1(1),
				urg(2),
				ack(3),
				psh(4),
				rst(5),
				syn(6),
				fin(7)
				}
			MAX-ACCESS read-only
			STATUS current
			DESCRIPTION
				"The flag in TCP packet"
			::= { fkV2Security4ACLFlowEntry 12 }

		
		-- 1.3.6.1.4.1.10428 9 1.102.7.2.5.2.1.1.1.13
		fkV2Security4ACLFlowUdpSrcStartPort OBJECT-TYPE
			SYNTAX IntL4Port
			MAX-ACCESS read-only
			STATUS current
			DESCRIPTION
				"The start source port in range of source port in UDP packet
				The value of -1 means any(not set)
				"
			::= { fkV2Security4ACLFlowEntry 13 }

		
		-- 1.3.6.1.4.1.10428 9 1.102.7.2.5.2.1.1.1.14
		fkV2Security4ACLFlowUdpSrcEndPort OBJECT-TYPE
			SYNTAX IntL4Port
			MAX-ACCESS read-only
			STATUS current
			DESCRIPTION
				"The end source port in range of source port in UDP packet
				The value of -1 means any(not set)
				"
			::= { fkV2Security4ACLFlowEntry 14 }

		
		-- 1.3.6.1.4.1.10428 9 1.102.7.2.5.2.1.1.1.15
		fkV2Security4ACLFlowUdpDstStartPort OBJECT-TYPE
			SYNTAX IntL4Port
			MAX-ACCESS read-only
			STATUS current
			DESCRIPTION
				"The start destination port in range of destination port in UDP packet. The value of -1 means any(not set)"
			::= { fkV2Security4ACLFlowEntry 15 }

		
		-- 1.3.6.1.4.1.10428 9 1.102.7.2.5.2.1.1.1.16
		fkV2Security4ACLFlowUdpDstEndPort OBJECT-TYPE
			SYNTAX IntL4Port
			MAX-ACCESS read-only
			STATUS current
			DESCRIPTION
				"The end destination port in range of destination port in UDP packet. The value of -1 means any(not set)"
			::= { fkV2Security4ACLFlowEntry 16 }

		
		-- 1.3.6.1.4.1.10428 9 1.102.7.2.5.2.1.1.1.17
		fkV2Security4ACLFlowIcmpType OBJECT-TYPE
			SYNTAX IntIcmpType
			MAX-ACCESS read-only
			STATUS current
			DESCRIPTION
				"The type of ICMP message
				The value of -1 means any(not set)
				"
			::= { fkV2Security4ACLFlowEntry 17 }

		
		-- 1.3.6.1.4.1.10428 9 1.102.7.2.5.2.1.1.1.18
		fkV2Security4ACLFlowIcmpCode OBJECT-TYPE
			SYNTAX IntIcmpCode
			MAX-ACCESS read-only
			STATUS current
			DESCRIPTION
				"The code of ICMP message
				The value of -1 means any(not set)
				"
			::= { fkV2Security4ACLFlowEntry 18 }

		
		-- 1.3.6.1.4.1.10428 9 1.102.7.2.5.2.1.1.1.19
		fkV2Security4ACLFlowHdrlen OBJECT-TYPE
			SYNTAX INTEGER (0 | 1..15)
			MAX-ACCESS read-only
			STATUS current
			DESCRIPTION
				"The IP header length.
				The value of 0 means any(not set)"
			::= { fkV2Security4ACLFlowEntry 19 }

		
		-- 1.3.6.1.4.1.10428 9 1.102.7.2.5.2.1.1.1.20
		fkV2Security4ACLFlowIpFlag OBJECT-TYPE
			SYNTAX INTEGER
				{
				none(0),
				srcAny(1),
				dstAny(2),
				srcDstAny(3)
				}
			MAX-ACCESS read-only
			STATUS current
			DESCRIPTION
				"The any flag of IP address."
			::= { fkV2Security4ACLFlowEntry 20 }

		
		-- 1.3.6.1.4.1.10428 9 1.102.7.2.5.2.1.2
		fkV2Security4ACLFlowControl OBJECT IDENTIFIER ::= { fkV2Security4ACLFlowInfo 2 }

		
		-- 1.3.6.1.4.1.10428 9 1.102.7.2.5.2.1.2.1
		fkV2Security4ACLFlowControlRequest OBJECT-TYPE
			SYNTAX INTEGER
				{
				createFlow(1),
				modifyFlow(2),
				destroyFlow(3),
				destroyAllFlow(4)
				}
			MAX-ACCESS read-write
			STATUS current
			DESCRIPTION
				"The request of a user command"
			::= { fkV2Security4ACLFlowControl 1 }

		
		-- 1.3.6.1.4.1.10428 9 1.102.7.2.5.2.1.2.2
		fkV2Security4ACLFlowControlStatus OBJECT-TYPE
			SYNTAX FkControlStatusType
			MAX-ACCESS read-only
			STATUS current
			DESCRIPTION
				"The status of user command"
			::= { fkV2Security4ACLFlowControl 2 }

		
		-- 1.3.6.1.4.1.10428 9 1.102.7.2.5.2.1.2.3
		fkV2Security4ACLFlowControlTimer OBJECT-TYPE
			SYNTAX Gauge32
			MAX-ACCESS read-write
			STATUS current
			DESCRIPTION
				"The maximum time for the manager for a long running user command"
			::= { fkV2Security4ACLFlowControl 3 }

		
		-- 1.3.6.1.4.1.10428 9 1.102.7.2.5.2.1.2.4
		fkV2Security4ACLFlowControlTimeStamp OBJECT-TYPE
			SYNTAX TimeTicks
			MAX-ACCESS read-only
			STATUS current
			DESCRIPTION
				"The time stamp of the last command(end of command)"
			::= { fkV2Security4ACLFlowControl 4 }

		
		-- 1.3.6.1.4.1.10428 9 1.102.7.2.5.2.1.2.5
		fkV2Security4ACLFlowControlReqResult OBJECT-TYPE
			SYNTAX FkControlRequestResultType
			MAX-ACCESS read-only
			STATUS current
			DESCRIPTION
				"The result of the last user command"
			::= { fkV2Security4ACLFlowControl 5 }

		
		-- 1.3.6.1.4.1.10428 9 1.102.7.2.5.2.1.2.6
		fkV2Security4ACLFlowControlIndex OBJECT-TYPE
			SYNTAX IntFlowIndex
			MAX-ACCESS read-write
			STATUS current
			DESCRIPTION
				"The index of flow"
			::= { fkV2Security4ACLFlowControl 6 }

		
		-- 1.3.6.1.4.1.10428 9 1.102.7.2.5.2.1.2.7
		fkV2Security4ACLFlowControlName OBJECT-TYPE
			SYNTAX OctetName
			MAX-ACCESS read-write
			STATUS current
			DESCRIPTION
				"The name of flow"
			::= { fkV2Security4ACLFlowControl 7 }

		
		-- 1.3.6.1.4.1.10428 9 1.102.7.2.5.2.1.2.8
		fkV2Security4ACLFlowControlSrcIpAddr OBJECT-TYPE
			SYNTAX IpAddress
			MAX-ACCESS read-write
			STATUS current
			DESCRIPTION
				"The IP address to match against the packet's source IP address.
				The value of 0.0.0.0 means any(not set)
				"
			::= { fkV2Security4ACLFlowControl 8 }

		
		-- 1.3.6.1.4.1.10428 9 1.102.7.2.5.2.1.2.9
		fkV2Security4ACLFlowControlSrcIpAddrMask OBJECT-TYPE
			SYNTAX IntIpAddrMask
			MAX-ACCESS read-write
			STATUS current
			DESCRIPTION
				"The mask of source IP address
				The value of -1 means any(not set)
				"
			::= { fkV2Security4ACLFlowControl 9 }

		
		-- 1.3.6.1.4.1.10428 9 1.102.7.2.5.2.1.2.10
		fkV2Security4ACLFlowControlDstIpAddr OBJECT-TYPE
			SYNTAX IpAddress
			MAX-ACCESS read-write
			STATUS current
			DESCRIPTION
				"The IP address to match against the packet's destination IP address.
				The value of 0.0.0.0 means any(not set)
				"
			::= { fkV2Security4ACLFlowControl 10 }

		
		-- 1.3.6.1.4.1.10428 9 1.102.7.2.5.2.1.2.11
		fkV2Security4ACLFlowControlDstIpAddrMask OBJECT-TYPE
			SYNTAX IntIpAddrMask
			MAX-ACCESS read-write
			STATUS current
			DESCRIPTION
				"The mask of destination IP address
				The value of -1 means any(not set)
				"
			::= { fkV2Security4ACLFlowControl 11 }

		
		-- 1.3.6.1.4.1.10428 9 1.102.7.2.5.2.1.2.12
		fkV2Security4ACLFlowControlProtocolType OBJECT-TYPE
			SYNTAX IntProtocolType
			MAX-ACCESS read-write
			STATUS current
			DESCRIPTION
				"The type of IP protocol
				The flat internet protocol is from fkV2QoS4FlowTcpSrcStartPort to fkV2QoS4FlowIcmpCode
				If the value is tcp(6),
				From fkV2QoS4FlowControlTcpSrcStartPort to fkV2QoS4FlowControlTcpFlag value is available
				If the value is u¿¡(17),
				From fkV2QoS4FlowControlUdpSrcStartPort to fkV2QoS4FlowControlUdpDstEndPort value is available
				If the value is icmp(1),
				The value of fkV2QoS4FlowControlIcmpType and fkV2QoS4FlowControlIcmpCode is available
				The value of -1 means any(not set)
				Otherwise, from fkV2QoS4FlowControlTcpSrcStartPort to fkV2QoS4FlowControlIcmpCode value is not available
				The value of -1 means any(not set)
				"
			::= { fkV2Security4ACLFlowControl 12 }

		
		-- 1.3.6.1.4.1.10428 9 1.102.7.2.5.2.1.2.13
		fkV2Security4ACLFlowControlTcpSrcStartPort OBJECT-TYPE
			SYNTAX IntL4Port
			MAX-ACCESS read-write
			STATUS current
			DESCRIPTION
				"The start source port in range of source port in TCP packet
				The value of -1 means any(not set)
				"
			::= { fkV2Security4ACLFlowControl 13 }

		
		-- 1.3.6.1.4.1.10428 9 1.102.7.2.5.2.1.2.14
		fkV2Security4ACLFlowControlTcpSrcEndPort OBJECT-TYPE
			SYNTAX IntL4Port
			MAX-ACCESS read-write
			STATUS current
			DESCRIPTION
				"The end source port in range of source port in TCP packet
				The value of -1 means any(not set)
				"
			::= { fkV2Security4ACLFlowControl 14 }

		
		-- 1.3.6.1.4.1.10428 9 1.102.7.2.5.2.1.2.15
		fkV2Security4ACLFlowControlTcpDstStartPort OBJECT-TYPE
			SYNTAX IntL4Port
			MAX-ACCESS read-write
			STATUS current
			DESCRIPTION
				"The start destination port in range of source port in TCP packet. The value of -1 means any(not set)"
			::= { fkV2Security4ACLFlowControl 15 }

		
		-- 1.3.6.1.4.1.10428 9 1.102.7.2.5.2.1.2.16
		fkV2Security4ACLFlowControlTcpDstEndPort OBJECT-TYPE
			SYNTAX IntL4Port
			MAX-ACCESS read-write
			STATUS current
			DESCRIPTION
				"The end destination port in range of destination port in TCP packet. The value of -1 means any(not set)"
			::= { fkV2Security4ACLFlowControl 16 }

		
		-- 1.3.6.1.4.1.10428 9 1.102.7.2.5.2.1.2.17
		fkV2Security4ACLFlowControlTcpFlag OBJECT-TYPE
			SYNTAX BITS
				{
				reserv0(0),
				reserv1(1),
				urg(2),
				ack(3),
				psh(4),
				rst(5),
				syn(6),
				fin(7)
				}
			MAX-ACCESS read-write
			STATUS current
			DESCRIPTION
				"The flag in TCP packet"
			::= { fkV2Security4ACLFlowControl 17 }

		
		-- 1.3.6.1.4.1.10428 9 1.102.7.2.5.2.1.2.18
		fkV2Security4ACLFlowControlUdpSrcStartPort OBJECT-TYPE
			SYNTAX IntL4Port
			MAX-ACCESS read-write
			STATUS current
			DESCRIPTION
				"The start source port in range of source port in UDP packet
				The value of -1 means any(not set)
				"
			::= { fkV2Security4ACLFlowControl 18 }

		
		-- 1.3.6.1.4.1.10428 9 1.102.7.2.5.2.1.2.19
		fkV2Security4ACLFlowControlUdpSrcEndPort OBJECT-TYPE
			SYNTAX IntL4Port
			MAX-ACCESS read-write
			STATUS current
			DESCRIPTION
				"The end source port in range of source port in UDP packet
				The value of -1 means any(not set)
				"
			::= { fkV2Security4ACLFlowControl 19 }

		
		-- 1.3.6.1.4.1.10428 9 1.102.7.2.5.2.1.2.20
		fkV2Security4ACLFlowControlUdpDstStartPort OBJECT-TYPE
			SYNTAX IntL4Port
			MAX-ACCESS read-write
			STATUS current
			DESCRIPTION
				"The start destination port in range of destination port in UDP packet. The value of -1 means any(not set)"
			::= { fkV2Security4ACLFlowControl 20 }

		
		-- 1.3.6.1.4.1.10428 9 1.102.7.2.5.2.1.2.21
		fkV2Security4ACLFlowControlUdpDstEndPort OBJECT-TYPE
			SYNTAX IntL4Port
			MAX-ACCESS read-write
			STATUS current
			DESCRIPTION
				"The end destination port in range of destination port in UDP packet. The value of -1 means any(not set)"
			::= { fkV2Security4ACLFlowControl 21 }

		
		-- 1.3.6.1.4.1.10428 9 1.102.7.2.5.2.1.2.22
		fkV2Security4ACLFlowControlIcmpType OBJECT-TYPE
			SYNTAX IntIcmpType
			MAX-ACCESS read-write
			STATUS current
			DESCRIPTION
				"The type of ICMP message
				The value of -1 means any(not set)
				"
			::= { fkV2Security4ACLFlowControl 22 }

		
		-- 1.3.6.1.4.1.10428 9 1.102.7.2.5.2.1.2.23
		fkV2Security4ACLFlowControlIcmpCode OBJECT-TYPE
			SYNTAX IntIcmpCode
			MAX-ACCESS read-write
			STATUS current
			DESCRIPTION
				"The code of ICMP message
				The value of -1 means any(not set)
				"
			::= { fkV2Security4ACLFlowControl 23 }

		
		-- 1.3.6.1.4.1.10428 9 1.102.7.2.5.2.1.2.24
		fkV2Security4ACLFlowControlHdrlen OBJECT-TYPE
			SYNTAX INTEGER (0 | 1..15)
			MAX-ACCESS read-write
			STATUS current
			DESCRIPTION
				"The IP header length
				The value of 0 means any(not set)"
			::= { fkV2Security4ACLFlowControl 24 }

		
		-- 1.3.6.1.4.1.10428 9 1.102.7.2.5.2.1.2.25
		fkV2Security4ACLFlowControlIpFlag OBJECT-TYPE
			SYNTAX INTEGER
				{
				none(0),
				srcAny(1),
				dstAny(2),
				srcDstAny(3)
				}
			MAX-ACCESS read-write
			STATUS current
			DESCRIPTION
				"The any flag of IP address."
			::= { fkV2Security4ACLFlowControl 25 }

		
		-- 1.3.6.1.4.1.10428 9 1.102.7.2.5.2.1.3
		fkV2Security4ACLFlowNotification OBJECT IDENTIFIER ::= { fkV2Security4ACLFlowInfo 3 }

		
		-- 1.3.6.1.4.1.10428 9 1.102.7.2.5.2.1.3.1
		fkACLFlowCreated NOTIFICATION-TYPE
			OBJECTS { fkV2Security4ACLFlowControlRequest, fkV2Security4ACLFlowControlTimeStamp, fkV2Security4ACLFlowIpFlag, fkV2Security4ACLFlowControlIpFlag, fkV2Security4ACLFlowControlReqResult, 
				fkV2Security4ACLFlowName, fkV2Security4ACLFlowSrcIpAddr, fkV2Security4ACLFlowSrcIpAddrMask, fkV2Security4ACLFlowDstIpAddr, fkV2Security4ACLFlowDstIpAddrMask, 
				fkV2Security4ACLFlowProtocolType, fkV2Security4ACLFlowTcpSrcStartPort, fkV2Security4ACLFlowTcpSrcEndPort, fkV2Security4ACLFlowTcpDstStartPort, fkV2Security4ACLFlowTcpDstEndPort, 
				fkV2Security4ACLFlowTcpFlag, fkV2Security4ACLFlowUdpSrcStartPort, fkV2Security4ACLFlowUdpSrcEndPort, fkV2Security4ACLFlowUdpDstStartPort, fkV2Security4ACLFlowUdpDstEndPort, 
				fkV2Security4ACLFlowIcmpType, fkV2Security4ACLFlowIcmpCode, fkV2Security4ACLFlowHdrlen }
			STATUS current
			DESCRIPTION 
				"Description."
			::= { fkV2Security4ACLFlowNotification 1 }

		
		-- 1.3.6.1.4.1.10428 9 1.102.7.2.5.2.1.3.2
		fkACLFlowChanged NOTIFICATION-TYPE
			OBJECTS { fkV2Security4ACLFlowControlRequest, fkV2Security4ACLFlowControlTimeStamp, fkV2Security4ACLFlowControlReqResult, fkV2Security4ACLFlowIpFlag, fkV2Security4ACLFlowControlIpFlag, 
				fkV2Security4ACLFlowControlIndex, fkV2Security4ACLFlowSrcIpAddr, fkV2Security4ACLFlowSrcIpAddrMask, fkV2Security4ACLFlowDstIpAddr, fkV2Security4ACLFlowDstIpAddrMask, 
				fkV2Security4ACLFlowProtocolType, fkV2Security4ACLFlowTcpSrcStartPort, fkV2Security4ACLFlowTcpSrcEndPort, fkV2Security4ACLFlowTcpDstStartPort, fkV2Security4ACLFlowTcpDstEndPort, 
				fkV2Security4ACLFlowTcpFlag, fkV2Security4ACLFlowUdpSrcStartPort, fkV2Security4ACLFlowUdpSrcEndPort, fkV2Security4ACLFlowUdpDstStartPort, fkV2Security4ACLFlowUdpDstEndPort, 
				fkV2Security4ACLFlowIcmpType, fkV2Security4ACLFlowIcmpCode, fkV2Security4ACLFlowHdrlen }
			STATUS current
			DESCRIPTION 
				"Description."
			::= { fkV2Security4ACLFlowNotification 2 }

		
		-- 1.3.6.1.4.1.10428 9 1.102.7.2.5.2.1.3.3
		fkACLFlowDestroyed NOTIFICATION-TYPE
			OBJECTS { fkV2Security4ACLFlowControlRequest, fkV2Security4ACLFlowControlTimeStamp, fkV2Security4ACLFlowControlReqResult, fkV2Security4ACLFlowControlIndex }
			STATUS current
			DESCRIPTION 
				"Description."
			::= { fkV2Security4ACLFlowNotification 3 }

		
		-- 1.3.6.1.4.1.10428 9 1.102.7.2.5.2.1.3.4
		fkACLFlowAllDestroyed NOTIFICATION-TYPE
			OBJECTS { fkV2Security4ACLFlowControlRequest, fkV2Security4ACLFlowControlTimeStamp, fkV2Security4ACLFlowControlReqResult }
			STATUS current
			DESCRIPTION 
				"Description."
			::= { fkV2Security4ACLFlowNotification 4 }

		
		-- 1.3.6.1.4.1.10428 9 1.102.7.2.5.2.2
		fkV2Security4ACLFlowClass OBJECT IDENTIFIER ::= { fkV2Security4ACLFlow 2 }

		
		-- 1.3.6.1.4.1.10428 9 1.102.7.2.5.2.2.1
		fkV2Security4ACLFlowClassTable OBJECT-TYPE
			SYNTAX SEQUENCE OF FkV2Security4ACLFlowClassEntry
			MAX-ACCESS not-accessible
			STATUS current
			DESCRIPTION
				"ACL flow class table."
			::= { fkV2Security4ACLFlowClass 1 }

		
		-- 1.3.6.1.4.1.10428 9 1.102.7.2.5.2.2.1.1
		fkV2Security4ACLFlowClassEntry OBJECT-TYPE
			SYNTAX FkV2Security4ACLFlowClassEntry
			MAX-ACCESS not-accessible
			STATUS current
			DESCRIPTION
				"key: fkV2Security4ACLFlowIndex, fkV2Security4ACLFlowClassIndex"
			INDEX { fkV2Security4ACLFlowIndex, fkV2Security4ACLFlowClassIndex }
			::= { fkV2Security4ACLFlowClassTable 1 }

		
		FkV2Security4ACLFlowClassEntry ::=
			SEQUENCE { 
				fkV2Security4ACLFlowClassIndex
					IntClassIndex,
				fkV2Security4ACLFlowClassID
					IntClassIndex,
				fkV2Security4ACLFlowClassName
					OctetName
			 }

		-- 1.3.6.1.4.1.10428 9 1.102.7.2.5.2.2.1.1.1
		fkV2Security4ACLFlowClassIndex OBJECT-TYPE
			SYNTAX IntClassIndex
			MAX-ACCESS read-only
			STATUS current
			DESCRIPTION
				"The index of the class for the flow"
			::= { fkV2Security4ACLFlowClassEntry 1 }

		
		-- 1.3.6.1.4.1.10428 9 1.102.7.2.5.2.2.1.1.2
		fkV2Security4ACLFlowClassID OBJECT-TYPE
			SYNTAX IntClassIndex
			MAX-ACCESS read-only
			STATUS current
			DESCRIPTION
				"The identifier of the class"
			::= { fkV2Security4ACLFlowClassEntry 2 }

		
		-- 1.3.6.1.4.1.10428 9 1.102.7.2.5.2.2.1.1.3
		fkV2Security4ACLFlowClassName OBJECT-TYPE
			SYNTAX OctetName
			MAX-ACCESS read-only
			STATUS current
			DESCRIPTION
				"The name of the class"
			::= { fkV2Security4ACLFlowClassEntry 3 }

		
		-- 1.3.6.1.4.1.10428 9 1.102.7.2.5.2.3
		fkV2Security4ACLFlowPolicy OBJECT IDENTIFIER ::= { fkV2Security4ACLFlow 3 }

		
		-- 1.3.6.1.4.1.10428 9 1.102.7.2.5.2.3.1
		fkV2QoS4ACLFlowPolicyTable OBJECT-TYPE
			SYNTAX SEQUENCE OF FkV2QoS4ACLFlowPolicyEntry
			MAX-ACCESS not-accessible
			STATUS current
			DESCRIPTION
				"ACL flow policy table."
			::= { fkV2Security4ACLFlowPolicy 1 }

		
		-- 1.3.6.1.4.1.10428 9 1.102.7.2.5.2.3.1.1
		fkV2QoS4ACLFlowPolicyEntry OBJECT-TYPE
			SYNTAX FkV2QoS4ACLFlowPolicyEntry
			MAX-ACCESS not-accessible
			STATUS current
			DESCRIPTION
				"key: fkV2Security4ACLFlowIndex, fkV2Security4ACLFlowPolicyIndex"
			INDEX { fkV2Security4ACLFlowIndex, fkV2Security4ACLFlowPolicyIndex }
			::= { fkV2QoS4ACLFlowPolicyTable 1 }

		
		FkV2QoS4ACLFlowPolicyEntry ::=
			SEQUENCE { 
				fkV2Security4ACLFlowPolicyIndex
					IntPolicyIndex,
				fkV2Security4ACLFlowPolicyID
					IntPolicyIndex,
				fkV2Security4ACLFlowPolicyName
					OctetName
			 }

		-- 1.3.6.1.4.1.10428 9 1.102.7.2.5.2.3.1.1.1
		fkV2Security4ACLFlowPolicyIndex OBJECT-TYPE
			SYNTAX IntPolicyIndex
			MAX-ACCESS read-only
			STATUS current
			DESCRIPTION
				"The index of the policy for the flow"
			::= { fkV2QoS4ACLFlowPolicyEntry 1 }

		
		-- 1.3.6.1.4.1.10428 9 1.102.7.2.5.2.3.1.1.2
		fkV2Security4ACLFlowPolicyID OBJECT-TYPE
			SYNTAX IntPolicyIndex
			MAX-ACCESS read-only
			STATUS current
			DESCRIPTION
				"The identifier of the policy"
			::= { fkV2QoS4ACLFlowPolicyEntry 2 }

		
		-- 1.3.6.1.4.1.10428 9 1.102.7.2.5.2.3.1.1.3
		fkV2Security4ACLFlowPolicyName OBJECT-TYPE
			SYNTAX OctetName
			MAX-ACCESS read-only
			STATUS current
			DESCRIPTION
				"The name of the policy"
			::= { fkV2QoS4ACLFlowPolicyEntry 3 }

		
		-- 1.3.6.1.4.1.10428 9 1.102.7.2.5.3
		fkV2Security4ACLClass OBJECT IDENTIFIER ::= { fkV2SecurityACL 3 }

		
		-- 1.3.6.1.4.1.10428 9 1.102.7.2.5.3.1
		fkV2Security4ACLClassInfo OBJECT IDENTIFIER ::= { fkV2Security4ACLClass 1 }

		
		-- 1.3.6.1.4.1.10428 9 1.102.7.2.5.3.1.1
		fkV2Security4ACLClassTable OBJECT-TYPE
			SYNTAX SEQUENCE OF FkV2Security4ACLClassEntry
			MAX-ACCESS not-accessible
			STATUS current
			DESCRIPTION
				"ACL class table."
			::= { fkV2Security4ACLClassInfo 1 }

		
		-- 1.3.6.1.4.1.10428 9 1.102.7.2.5.3.1.1.1
		fkV2Security4ACLClassEntry OBJECT-TYPE
			SYNTAX FkV2Security4ACLClassEntry
			MAX-ACCESS not-accessible
			STATUS current
			DESCRIPTION
				"key: fkV2Security4ACLClassIndex"
			INDEX { fkV2Security4ACLClassIndex }
			::= { fkV2Security4ACLClassTable 1 }

		
		FkV2Security4ACLClassEntry ::=
			SEQUENCE { 
				fkV2Security4ACLClassIndex
					IntClassIndex,
				fkV2Security4ACLClassName
					OctetName,
				fkV2Security4ACLClassFlowCnt
					Counter32
			 }

		-- 1.3.6.1.4.1.10428 9 1.102.7.2.5.3.1.1.1.1
		fkV2Security4ACLClassIndex OBJECT-TYPE
			SYNTAX IntClassIndex
			MAX-ACCESS read-only
			STATUS current
			DESCRIPTION
				"The index of class"
			::= { fkV2Security4ACLClassEntry 1 }

		
		-- 1.3.6.1.4.1.10428 9 1.102.7.2.5.3.1.1.1.2
		fkV2Security4ACLClassName OBJECT-TYPE
			SYNTAX OctetName
			MAX-ACCESS read-only
			STATUS current
			DESCRIPTION
				"The name of class"
			::= { fkV2Security4ACLClassEntry 2 }

		
		-- 1.3.6.1.4.1.10428 9 1.102.7.2.5.3.1.1.1.3
		fkV2Security4ACLClassFlowCnt OBJECT-TYPE
			SYNTAX Counter32
			MAX-ACCESS read-only
			STATUS current
			DESCRIPTION
				"The counter of flow in class"
			::= { fkV2Security4ACLClassEntry 3 }

		
		-- 1.3.6.1.4.1.10428 9 1.102.7.2.5.3.1.2
		fkV2Security4ACLClassControl OBJECT IDENTIFIER ::= { fkV2Security4ACLClassInfo 2 }

		
		-- 1.3.6.1.4.1.10428 9 1.102.7.2.5.3.1.2.1
		fkV2Security4ACLClassControlRequest OBJECT-TYPE
			SYNTAX INTEGER
				{
				createClass(1),
				destroyClass(2),
				destroyAllClass(3)
				}
			MAX-ACCESS read-write
			STATUS current
			DESCRIPTION
				"The request of a user command"
			::= { fkV2Security4ACLClassControl 1 }

		
		-- 1.3.6.1.4.1.10428 9 1.102.7.2.5.3.1.2.2
		fkV2Security4ACLClassControlStatus OBJECT-TYPE
			SYNTAX FkControlStatusType
			MAX-ACCESS read-only
			STATUS current
			DESCRIPTION
				"The status of user command"
			::= { fkV2Security4ACLClassControl 2 }

		
		-- 1.3.6.1.4.1.10428 9 1.102.7.2.5.3.1.2.3
		fkV2Security4ACLClassControlTimer OBJECT-TYPE
			SYNTAX Gauge32
			MAX-ACCESS read-write
			STATUS current
			DESCRIPTION
				"The maximum time for the manager for a long running user command"
			::= { fkV2Security4ACLClassControl 3 }

		
		-- 1.3.6.1.4.1.10428 9 1.102.7.2.5.3.1.2.4
		fkV2Security4ACLClassControlTimeStamp OBJECT-TYPE
			SYNTAX TimeTicks
			MAX-ACCESS read-only
			STATUS current
			DESCRIPTION
				"The time stamp of the last command(end of command)"
			::= { fkV2Security4ACLClassControl 4 }

		
		-- 1.3.6.1.4.1.10428 9 1.102.7.2.5.3.1.2.5
		fkV2Security4ACLClassControlReqResult OBJECT-TYPE
			SYNTAX FkControlRequestResultType
			MAX-ACCESS read-only
			STATUS current
			DESCRIPTION
				"The result of the last user command"
			::= { fkV2Security4ACLClassControl 5 }

		
		-- 1.3.6.1.4.1.10428 9 1.102.7.2.5.3.1.2.6
		fkV2Security4ACLClassControlIndex OBJECT-TYPE
			SYNTAX IntClassIndex
			MAX-ACCESS read-write
			STATUS current
			DESCRIPTION
				"The index of class"
			::= { fkV2Security4ACLClassControl 6 }

		
		-- 1.3.6.1.4.1.10428 9 1.102.7.2.5.3.1.2.7
		fkV2Security4ACLClassControlName OBJECT-TYPE
			SYNTAX OctetName
			MAX-ACCESS read-write
			STATUS current
			DESCRIPTION
				"The name of class"
			::= { fkV2Security4ACLClassControl 7 }

		
		-- 1.3.6.1.4.1.10428 9 1.102.7.2.5.3.1.3
		fkV2Security4ACLClassNotification OBJECT IDENTIFIER ::= { fkV2Security4ACLClassInfo 3 }

		
		-- 1.3.6.1.4.1.10428 9 1.102.7.2.5.3.1.3.1
		fkACLClassCreated NOTIFICATION-TYPE
			OBJECTS { fkV2Security4ACLClassControlRequest, fkV2Security4ACLClassControlTimeStamp, fkV2Security4ACLClassControlReqResult, fkV2Security4ACLFlowClassName }
			STATUS current
			DESCRIPTION 
				"Description."
			::= { fkV2Security4ACLClassNotification 1 }

		
		-- 1.3.6.1.4.1.10428 9 1.102.7.2.5.3.1.3.2
		fkACLClassDestroyed NOTIFICATION-TYPE
			OBJECTS { fkV2Security4ACLClassControlRequest, fkV2Security4ACLClassControlTimeStamp, fkV2Security4ACLClassControlReqResult, fkV2Security4ACLClassControlIndex }
			STATUS current
			DESCRIPTION 
				"Description."
			::= { fkV2Security4ACLClassNotification 2 }

		
		-- 1.3.6.1.4.1.10428 9 1.102.7.2.5.3.1.3.3
		fkACLClassAllDestroyed NOTIFICATION-TYPE
			OBJECTS { fkV2Security4ACLClassControlRequest, fkV2Security4ACLClassControlTimeStamp, fkV2Security4ACLClassControlReqResult }
			STATUS current
			DESCRIPTION 
				"Description."
			::= { fkV2Security4ACLClassNotification 3 }

		
		-- 1.3.6.1.4.1.10428 9 1.102.7.2.5.3.2
		fkV2Security4ACLClassFlow OBJECT IDENTIFIER ::= { fkV2Security4ACLClass 2 }

		
		-- 1.3.6.1.4.1.10428 9 1.102.7.2.5.3.2.1
		fkV2Security4ACLClassFlowTable OBJECT-TYPE
			SYNTAX SEQUENCE OF FkV2Security4ACLClassFlowEntry
			MAX-ACCESS not-accessible
			STATUS current
			DESCRIPTION
				"Description."
			::= { fkV2Security4ACLClassFlow 1 }

		
		-- 1.3.6.1.4.1.10428 9 1.102.7.2.5.3.2.1.1
		fkV2Security4ACLClassFlowEntry OBJECT-TYPE
			SYNTAX FkV2Security4ACLClassFlowEntry
			MAX-ACCESS not-accessible
			STATUS current
			DESCRIPTION
				"Description."
			INDEX { fkV2Security4ACLClassIndex, fkV2Security4ACLClassFlowIndex }
			::= { fkV2Security4ACLClassFlowTable 1 }

		
		FkV2Security4ACLClassFlowEntry ::=
			SEQUENCE { 
				fkV2Security4ACLClassFlowIndex
					IntFlowIndex,
				fkV2Security4ACLClassFlowID
					IntFlowIndex,
				fkV2Security4ACLClassFlowName
					OctetName
			 }

		-- 1.3.6.1.4.1.10428 9 1.102.7.2.5.3.2.1.1.1
		fkV2Security4ACLClassFlowIndex OBJECT-TYPE
			SYNTAX IntFlowIndex
			MAX-ACCESS read-only
			STATUS current
			DESCRIPTION
				"The index of flow in class"
			::= { fkV2Security4ACLClassFlowEntry 1 }

		
		-- 1.3.6.1.4.1.10428 9 1.102.7.2.5.3.2.1.1.2
		fkV2Security4ACLClassFlowID OBJECT-TYPE
			SYNTAX IntFlowIndex
			MAX-ACCESS read-only
			STATUS current
			DESCRIPTION
				"The identifier of flow"
			::= { fkV2Security4ACLClassFlowEntry 2 }

		
		-- 1.3.6.1.4.1.10428 9 1.102.7.2.5.3.2.1.1.3
		fkV2Security4ACLClassFlowName OBJECT-TYPE
			SYNTAX OctetName
			MAX-ACCESS read-only
			STATUS current
			DESCRIPTION
				"The name of the flow"
			::= { fkV2Security4ACLClassFlowEntry 3 }

		
		-- 1.3.6.1.4.1.10428 9 1.102.7.2.5.3.2.2
		fkV2Security4ACLClassFlowControl OBJECT IDENTIFIER ::= { fkV2Security4ACLClassFlow 2 }

		
		-- 1.3.6.1.4.1.10428 9 1.102.7.2.5.3.2.2.1
		fkV2Security4ACLClassFlowControlRequest OBJECT-TYPE
			SYNTAX INTEGER
				{
				addFlow(1),
				deleteFlow(2),
				deleteAllFlow(3)
				}
			MAX-ACCESS read-write
			STATUS current
			DESCRIPTION
				"The request of a user command"
			::= { fkV2Security4ACLClassFlowControl 1 }

		
		-- 1.3.6.1.4.1.10428 9 1.102.7.2.5.3.2.2.2
		fkV2Security4ACLClassFlowControlStatus OBJECT-TYPE
			SYNTAX FkControlStatusType
			MAX-ACCESS read-only
			STATUS current
			DESCRIPTION
				"The status of user command"
			::= { fkV2Security4ACLClassFlowControl 2 }

		
		-- 1.3.6.1.4.1.10428 9 1.102.7.2.5.3.2.2.3
		fkV2Security4ACLClassFlowControlTimer OBJECT-TYPE
			SYNTAX Gauge32
			MAX-ACCESS read-write
			STATUS current
			DESCRIPTION
				"The maximum time for the manager for a long running user command"
			::= { fkV2Security4ACLClassFlowControl 3 }

		
		-- 1.3.6.1.4.1.10428 9 1.102.7.2.5.3.2.2.4
		fkV2Security4ACLClassFlowControlTimeStamp OBJECT-TYPE
			SYNTAX TimeTicks
			MAX-ACCESS read-only
			STATUS current
			DESCRIPTION
				"The time stamp of the last command(end of command)"
			::= { fkV2Security4ACLClassFlowControl 4 }

		
		-- 1.3.6.1.4.1.10428 9 1.102.7.2.5.3.2.2.5
		fkV2Security4ACLClassFlowControlReqResult OBJECT-TYPE
			SYNTAX FkControlRequestResultType
			MAX-ACCESS read-only
			STATUS current
			DESCRIPTION
				"The result of the last user command"
			::= { fkV2Security4ACLClassFlowControl 5 }

		
		-- 1.3.6.1.4.1.10428 9 1.102.7.2.5.3.2.2.6
		fkV2Security4ACLClassFlowControlClassIndex OBJECT-TYPE
			SYNTAX IntClassIndex
			MAX-ACCESS read-write
			STATUS current
			DESCRIPTION
				"The index of class"
			::= { fkV2Security4ACLClassFlowControl 6 }

		
		-- 1.3.6.1.4.1.10428 9 1.102.7.2.5.3.2.2.7
		fkV2Security4ACLClassFlowControlFlowIndex OBJECT-TYPE
			SYNTAX IntFlowIndex
			MAX-ACCESS read-write
			STATUS current
			DESCRIPTION
				"The index of flow in this class"
			::= { fkV2Security4ACLClassFlowControl 7 }

		
		-- 1.3.6.1.4.1.10428 9 1.102.7.2.5.3.2.2.8
		fkV2Security4ACLClassFlowControlFlowID OBJECT-TYPE
			SYNTAX IntFlowIndex
			MAX-ACCESS read-write
			STATUS current
			DESCRIPTION
				"The index of flow
				Refer to fkV2QoS4FlowIndex
				"
			::= { fkV2Security4ACLClassFlowControl 8 }

		
		-- 1.3.6.1.4.1.10428 9 1.102.7.2.5.3.2.3
		fkV2Security4ACLClassFlowNotification OBJECT IDENTIFIER ::= { fkV2Security4ACLClassFlow 3 }

		
		-- 1.3.6.1.4.1.10428 9 1.102.7.2.5.3.2.3.1
		fkACLClassFlowAdded NOTIFICATION-TYPE
			OBJECTS { fkV2Security4ACLClassFlowControlRequest, fkV2Security4ACLClassFlowControlTimeStamp, fkV2Security4ACLClassFlowControlReqResult, fkV2Security4ACLClassFlowControlClassIndex, fkV2Security4ACLClassFlowID
				 }
			STATUS current
			DESCRIPTION 
				"Description."
			::= { fkV2Security4ACLClassFlowNotification 1 }

		
		-- 1.3.6.1.4.1.10428 9 1.102.7.2.5.3.2.3.2
		fkACLClassFlowDeleted NOTIFICATION-TYPE
			OBJECTS { fkV2Security4ACLClassFlowControlRequest, fkV2Security4ACLClassFlowControlTimeStamp, fkV2Security4ACLClassFlowControlReqResult, fkV2Security4ACLClassFlowControlClassIndex, fkV2Security4ACLClassFlowControlFlowIndex
				 }
			STATUS current
			DESCRIPTION 
				"Description."
			::= { fkV2Security4ACLClassFlowNotification 2 }

		
		-- 1.3.6.1.4.1.10428 9 1.102.7.2.5.3.2.3.3
		fkACLClassFlowAllDeleted NOTIFICATION-TYPE
			OBJECTS { fkV2Security4ACLClassFlowControlRequest, fkV2Security4ACLClassFlowControlTimeStamp, fkV2Security4ACLClassFlowControlReqResult, fkV2Security4ACLClassFlowControlClassIndex }
			STATUS current
			DESCRIPTION 
				"Description."
			::= { fkV2Security4ACLClassFlowNotification 3 }

		
		-- 1.3.6.1.4.1.10428 9 1.102.7.2.5.3.3
		fkV2Security4ACLClassPolicy OBJECT IDENTIFIER ::= { fkV2Security4ACLClass 3 }

		
		-- 1.3.6.1.4.1.10428 9 1.102.7.2.5.3.3.1
		fkV2Security4ACLClassPolicyTable OBJECT-TYPE
			SYNTAX SEQUENCE OF FkV2Security4ACLClassPolicyEntry
			MAX-ACCESS not-accessible
			STATUS current
			DESCRIPTION
				"Description."
			::= { fkV2Security4ACLClassPolicy 1 }

		
		-- 1.3.6.1.4.1.10428 9 1.102.7.2.5.3.3.1.1
		fkV2Security4ACLClassPolicyEntry OBJECT-TYPE
			SYNTAX FkV2Security4ACLClassPolicyEntry
			MAX-ACCESS not-accessible
			STATUS current
			DESCRIPTION
				"Description."
			INDEX { fkV2Security4ACLClassIndex, fkV2Security4ACLClassPolicyIndex }
			::= { fkV2Security4ACLClassPolicyTable 1 }

		
		FkV2Security4ACLClassPolicyEntry ::=
			SEQUENCE { 
				fkV2Security4ACLClassPolicyIndex
					IntPolicyIndex,
				fkV2Security4ACLClassPolicyID
					IntPolicyIndex,
				fkV2Security4ACLClassPolicyName
					OctetName
			 }

		-- 1.3.6.1.4.1.10428 9 1.102.7.2.5.3.3.1.1.1
		fkV2Security4ACLClassPolicyIndex OBJECT-TYPE
			SYNTAX IntPolicyIndex
			MAX-ACCESS read-only
			STATUS current
			DESCRIPTION
				"The index of the policy for the class"
			::= { fkV2Security4ACLClassPolicyEntry 1 }

		
		-- 1.3.6.1.4.1.10428 9 1.102.7.2.5.3.3.1.1.2
		fkV2Security4ACLClassPolicyID OBJECT-TYPE
			SYNTAX IntPolicyIndex
			MAX-ACCESS read-only
			STATUS current
			DESCRIPTION
				"The identifier of the policy"
			::= { fkV2Security4ACLClassPolicyEntry 2 }

		
		-- 1.3.6.1.4.1.10428 9 1.102.7.2.5.3.3.1.1.3
		fkV2Security4ACLClassPolicyName OBJECT-TYPE
			SYNTAX OctetName
			MAX-ACCESS read-only
			STATUS current
			DESCRIPTION
				"The name of the policy"
			::= { fkV2Security4ACLClassPolicyEntry 3 }

		
		-- 1.3.6.1.4.1.10428 9 1.102.7.2.5.4
		fkV2Security4ACLPolicy OBJECT IDENTIFIER ::= { fkV2SecurityACL 4 }

		
		-- 1.3.6.1.4.1.10428 9 1.102.7.2.5.4.1
		fkV2Security4ACLPolicyInfo OBJECT IDENTIFIER ::= { fkV2Security4ACLPolicy 1 }

		
		-- 1.3.6.1.4.1.10428 9 1.102.7.2.5.4.1.1
		fkV2Security4ACLPolicyTable OBJECT-TYPE
			SYNTAX SEQUENCE OF FkV2Security4ACLPolicyEntry
			MAX-ACCESS not-accessible
			STATUS current
			DESCRIPTION
				"ACL policy table."
			::= { fkV2Security4ACLPolicyInfo 1 }

		
		-- 1.3.6.1.4.1.10428 9 1.102.7.2.5.4.1.1.1
		fkV2Security4ACLPolicyEntry OBJECT-TYPE
			SYNTAX FkV2Security4ACLPolicyEntry
			MAX-ACCESS not-accessible
			STATUS current
			DESCRIPTION
				"key: fkV2Security4ACLPolicyIndex"
			INDEX { fkV2Security4ACLPolicyIndex }
			::= { fkV2Security4ACLPolicyTable 1 }

		
		FkV2Security4ACLPolicyEntry ::=
			SEQUENCE { 
				fkV2Security4ACLPolicyIndex
					IntPolicyIndex,
				fkV2Security4ACLPolicyName
					OctetName,
				fkV2Security4ACLPolicyFlowCnt
					Integer32,
				fkV2Security4ACLPolicyClassCnt
					Integer32,
				fkV2Security4ACLPolicyPriority
					INTEGER,
				fkV2Security4ACLPolicyMatchFlag
					IntPermit,
				fkV2Security4ACLPolicyNomatchFlag
					IntPermit
			 }

		-- 1.3.6.1.4.1.10428 9 1.102.7.2.5.4.1.1.1.1
		fkV2Security4ACLPolicyIndex OBJECT-TYPE
			SYNTAX IntPolicyIndex
			MAX-ACCESS read-only
			STATUS current
			DESCRIPTION
				"The index of policy"
			::= { fkV2Security4ACLPolicyEntry 1 }

		
		-- 1.3.6.1.4.1.10428 9 1.102.7.2.5.4.1.1.1.2
		fkV2Security4ACLPolicyName OBJECT-TYPE
			SYNTAX OctetName
			MAX-ACCESS read-only
			STATUS current
			DESCRIPTION
				"The name of policy"
			::= { fkV2Security4ACLPolicyEntry 2 }

		
		-- 1.3.6.1.4.1.10428 9 1.102.7.2.5.4.1.1.1.3
		fkV2Security4ACLPolicyFlowCnt OBJECT-TYPE
			SYNTAX Integer32
			MAX-ACCESS read-only
			STATUS current
			DESCRIPTION
				"The counter of flow that was included to policy"
			::= { fkV2Security4ACLPolicyEntry 3 }

		
		-- 1.3.6.1.4.1.10428 9 1.102.7.2.5.4.1.1.1.4
		fkV2Security4ACLPolicyClassCnt OBJECT-TYPE
			SYNTAX Integer32
			MAX-ACCESS read-only
			STATUS current
			DESCRIPTION
				"The counter of class that was included to policy"
			::= { fkV2Security4ACLPolicyEntry 4 }

		
		-- 1.3.6.1.4.1.10428 9 1.102.7.2.5.4.1.1.1.5
		fkV2Security4ACLPolicyPriority OBJECT-TYPE
			SYNTAX INTEGER
				{
				low(1),
				medium(2),
				high(3),
				highest(4)
				}
			MAX-ACCESS read-only
			STATUS current
			DESCRIPTION
				"The priority of the policy
				
				low : default value
				"
			::= { fkV2Security4ACLPolicyEntry 5 }

		
		-- 1.3.6.1.4.1.10428 9 1.102.7.2.5.4.1.1.1.6
		fkV2Security4ACLPolicyMatchFlag OBJECT-TYPE
			SYNTAX IntPermit
			MAX-ACCESS read-only
			STATUS current
			DESCRIPTION
				"The action to be apply for matched packets.
				bit 0: deny the matched packets
				bit 1: mirror the matched packets
				bit 2: copy to CPU
				bit 3: set 802.1p value to ToS precedence 
				bit 4: set ToS precedence to 802.1p value
				bit 5 : set 802.1p value from flow
				bit 6 : set TaoS precedence from flow
				"
			::= { fkV2Security4ACLPolicyEntry 6 }

		
		-- 1.3.6.1.4.1.10428 9 1.102.7.2.5.4.1.1.1.7
		fkV2Security4ACLPolicyNomatchFlag OBJECT-TYPE
			SYNTAX IntPermit
			MAX-ACCESS read-only
			STATUS current
			DESCRIPTION
				"The action to be apply for matched packets.
				bit 0: deny the nomatched packets
				bit 1: mirror the nomatched packets
				bit 2: copy to CPU
				bit 3: set 802.1p value to ToS precedence 
				bit 4: set ToS precedence to 802.1p value
				bit 5 : set 802.1p value from flow
				bit 6 : set TaoS precedence from flow
				"
			::= { fkV2Security4ACLPolicyEntry 7 }

		
		-- 1.3.6.1.4.1.10428 9 1.102.7.2.5.4.1.2
		fkV2Security4ACLPolicyControl OBJECT IDENTIFIER ::= { fkV2Security4ACLPolicyInfo 2 }

		
		-- 1.3.6.1.4.1.10428 9 1.102.7.2.5.4.1.2.1
		fkV2Security4ACLPolicyControlRequest OBJECT-TYPE
			SYNTAX INTEGER
				{
				createPolicy(1),
				setPolicyInfo(2),
				setMatchAction(3),
				setNomatchAction(4),
				destroyPolicy(5)
				}
			MAX-ACCESS read-write
			STATUS current
			DESCRIPTION
				"The request of a user command"
			::= { fkV2Security4ACLPolicyControl 1 }

		
		-- 1.3.6.1.4.1.10428 9 1.102.7.2.5.4.1.2.2
		fkV2Security4ACLPolicyControlStatus OBJECT-TYPE
			SYNTAX FkControlStatusType
			MAX-ACCESS read-only
			STATUS current
			DESCRIPTION
				"The status of user command"
			::= { fkV2Security4ACLPolicyControl 2 }

		
		-- 1.3.6.1.4.1.10428 9 1.102.7.2.5.4.1.2.3
		fkV2Security4ACLPolicyControlTimer OBJECT-TYPE
			SYNTAX Gauge32
			MAX-ACCESS read-write
			STATUS current
			DESCRIPTION
				"The maximum time for the manager for a long running user command"
			::= { fkV2Security4ACLPolicyControl 3 }

		
		-- 1.3.6.1.4.1.10428 9 1.102.7.2.5.4.1.2.4
		fkV2Security4ACLPolicyControlTimeStamp OBJECT-TYPE
			SYNTAX TimeTicks
			MAX-ACCESS read-only
			STATUS current
			DESCRIPTION
				"The time stamp of the last command(end of command)"
			::= { fkV2Security4ACLPolicyControl 4 }

		
		-- 1.3.6.1.4.1.10428 9 1.102.7.2.5.4.1.2.5
		fkV2Security4ACLPolicyControlReqResult OBJECT-TYPE
			SYNTAX FkControlRequestResultType
			MAX-ACCESS read-only
			STATUS current
			DESCRIPTION
				"The result of the last user command"
			::= { fkV2Security4ACLPolicyControl 5 }

		
		-- 1.3.6.1.4.1.10428 9 1.102.7.2.5.4.1.2.6
		fkV2Security4ACLPolicyControlIndex OBJECT-TYPE
			SYNTAX IntPolicyIndex
			MAX-ACCESS read-write
			STATUS current
			DESCRIPTION
				"The index of policy"
			::= { fkV2Security4ACLPolicyControl 6 }

		
		-- 1.3.6.1.4.1.10428 9 1.102.7.2.5.4.1.2.7
		fkV2Security4ACLPolicyControlName OBJECT-TYPE
			SYNTAX OctetName
			MAX-ACCESS read-write
			STATUS current
			DESCRIPTION
				"The name of policy"
			::= { fkV2Security4ACLPolicyControl 7 }

		
		-- 1.3.6.1.4.1.10428 9 1.102.7.2.5.4.1.2.8
		fkV2Security4ACLPolicyControlPriority OBJECT-TYPE
			SYNTAX IntRulePriority
			MAX-ACCESS read-write
			STATUS current
			DESCRIPTION
				"The priority of the policy
				
				low : default
				"
			::= { fkV2Security4ACLPolicyControl 8 }

		
		-- 1.3.6.1.4.1.10428 9 1.102.7.2.5.4.1.2.9
		fkV2Security4ACLPolicyControlMatchFlag OBJECT-TYPE
			SYNTAX IntPermit
			MAX-ACCESS read-write
			STATUS current
			DESCRIPTION
				"The action to be apply for matched packets.
				bit 0: deny the matched packets
				bit 1: mirror the matched packets
				bit 2: copy to CPU
				bit 3: set 802.1p value to ToS precedence 
				bit 4: set ToS precedence to 802.1p value
				bit 5 : set 802.1p value from flow
				bit 6 : set TaoS precedence from flow
				"
			::= { fkV2Security4ACLPolicyControl 9 }

		
		-- 1.3.6.1.4.1.10428 9 1.102.7.2.5.4.1.2.10
		fkV2Security4ACLPolicyControlNomatchFlag OBJECT-TYPE
			SYNTAX IntPermit
			MAX-ACCESS read-write
			STATUS current
			DESCRIPTION
				"The action to be apply for matched packets.
				bit 0: deny the nomatched packets
				bit 1: mirror the nomatched packets
				bit 2: copy to CPU
				bit 3: set 802.1p value to ToS precedence 
				bit 4: set ToS precedence to 802.1p value
				bit 5 : set 802.1p value from flow
				bit 6 : set TaoS precedence from flow
				"
			::= { fkV2Security4ACLPolicyControl 10 }

		
		-- 1.3.6.1.4.1.10428 9 1.102.7.2.5.4.1.3
		fkV2Security4ACLPolicyNotification OBJECT IDENTIFIER ::= { fkV2Security4ACLPolicyInfo 3 }

		
		-- 1.3.6.1.4.1.10428 9 1.102.7.2.5.4.1.3.1
		fkACLPolicyCreated NOTIFICATION-TYPE
			OBJECTS { fkV2Security4ACLPolicyControlRequest, fkV2Security4ACLPolicyControlTimeStamp, fkV2Security4ACLPolicyControlReqResult, fkV2Security4ACLClassPolicyName, fkV2Security4ACLPolicyPriority, 
				fkV2Security4ACLPolicyMatchFlag, fkV2Security4ACLPolicyNomatchFlag }
			STATUS current
			DESCRIPTION 
				"Description."
			::= { fkV2Security4ACLPolicyNotification 1 }

		
		-- 1.3.6.1.4.1.10428 9 1.102.7.2.5.4.1.3.2
		fkACLPolicyInfoChanged NOTIFICATION-TYPE
			OBJECTS { fkV2Security4ACLPolicyControlRequest, fkV2Security4ACLPolicyControlTimeStamp, fkV2Security4ACLPolicyControlReqResult, fkV2Security4ACLPolicyPriority }
			STATUS current
			DESCRIPTION 
				"Description."
			::= { fkV2Security4ACLPolicyNotification 2 }

		
		-- 1.3.6.1.4.1.10428 9 1.102.7.2.5.4.1.3.3
		fkACLPolicyMatchActionChanged NOTIFICATION-TYPE
			OBJECTS { fkV2Security4ACLPolicyControlRequest, fkV2Security4ACLPolicyControlTimeStamp, fkV2Security4ACLPolicyControlReqResult, fkV2Security4ACLPolicyMatchFlag }
			STATUS current
			DESCRIPTION 
				"Description."
			::= { fkV2Security4ACLPolicyNotification 3 }

		
		-- 1.3.6.1.4.1.10428 9 1.102.7.2.5.4.1.3.4
		fkACLPolicyNomatchActionChanged NOTIFICATION-TYPE
			OBJECTS { fkV2Security4ACLPolicyControlRequest, fkV2Security4ACLPolicyControlTimeStamp, fkV2Security4ACLPolicyControlReqResult, fkV2Security4ACLPolicyNomatchFlag }
			STATUS current
			DESCRIPTION 
				"Description."
			::= { fkV2Security4ACLPolicyNotification 4 }

		
		-- 1.3.6.1.4.1.10428 9 1.102.7.2.5.4.1.3.5
		fkACLPolicyDestroyed NOTIFICATION-TYPE
			OBJECTS { fkV2Security4ACLPolicyControlRequest, fkV2Security4ACLPolicyControlTimeStamp, fkV2Security4ACLPolicyControlReqResult, fkV2Security4ACLPolicyControlIndex }
			STATUS current
			DESCRIPTION 
				"Description."
			::= { fkV2Security4ACLPolicyNotification 5 }

		
		-- 1.3.6.1.4.1.10428 9 1.102.7.2.5.4.2
		fkV2Security4ACLPolicyFlowClass OBJECT IDENTIFIER ::= { fkV2Security4ACLPolicy 2 }

		
		-- 1.3.6.1.4.1.10428 9 1.102.7.2.5.4.2.1
		fkV2Security4ACLPolicyFlowClassTable OBJECT-TYPE
			SYNTAX SEQUENCE OF FkV2Security4ACLPolicyFlowClassEntry
			MAX-ACCESS not-accessible
			STATUS current
			DESCRIPTION
				"ACL policy flow class table."
			::= { fkV2Security4ACLPolicyFlowClass 1 }

		
		-- 1.3.6.1.4.1.10428 9 1.102.7.2.5.4.2.1.1
		fkV2Security4ACLPolicyFlowClassEntry OBJECT-TYPE
			SYNTAX FkV2Security4ACLPolicyFlowClassEntry
			MAX-ACCESS not-accessible
			STATUS current
			DESCRIPTION
				"key: fkV2Security4ACLPolicyIndex, fkV2Security4ACLPolicyFlowClassIndex"
			INDEX { fkV2Security4ACLPolicyIndex, fkV2Security4ACLPolicyFlowClassIndex }
			::= { fkV2Security4ACLPolicyFlowClassTable 1 }

		
		FkV2Security4ACLPolicyFlowClassEntry ::=
			SEQUENCE { 
				fkV2Security4ACLPolicyFlowClassIndex
					IntFlowIndex,
				fkV2Security4ACLPolicyFlowClassType
					IntFlowOrClass,
				fkV2Security4ACLPolicyFlowClassID
					IntFlowIndex,
				fkV2Security4ACLPolicyFlowClassName
					OctetName
			 }

		-- 1.3.6.1.4.1.10428 9 1.102.7.2.5.4.2.1.1.1
		fkV2Security4ACLPolicyFlowClassIndex OBJECT-TYPE
			SYNTAX IntFlowIndex
			MAX-ACCESS read-only
			STATUS current
			DESCRIPTION
				"The index of flow or class in policy"
			::= { fkV2Security4ACLPolicyFlowClassEntry 1 }

		
		-- 1.3.6.1.4.1.10428 9 1.102.7.2.5.4.2.1.1.2
		fkV2Security4ACLPolicyFlowClassType OBJECT-TYPE
			SYNTAX IntFlowOrClass
			MAX-ACCESS read-only
			STATUS current
			DESCRIPTION
				"The flag about flow or class"
			::= { fkV2Security4ACLPolicyFlowClassEntry 2 }

		
		-- 1.3.6.1.4.1.10428 9 1.102.7.2.5.4.2.1.1.3
		fkV2Security4ACLPolicyFlowClassID OBJECT-TYPE
			SYNTAX IntFlowIndex
			MAX-ACCESS read-only
			STATUS current
			DESCRIPTION
				"The identifier of class or flow"
			::= { fkV2Security4ACLPolicyFlowClassEntry 3 }

		
		-- 1.3.6.1.4.1.10428 9 1.102.7.2.5.4.2.1.1.4
		fkV2Security4ACLPolicyFlowClassName OBJECT-TYPE
			SYNTAX OctetName
			MAX-ACCESS read-only
			STATUS current
			DESCRIPTION
				"The name of class or flow"
			::= { fkV2Security4ACLPolicyFlowClassEntry 4 }

		
		-- 1.3.6.1.4.1.10428 9 1.102.7.2.5.4.2.2
		fkV2Security4ACLPolicyFlowClassControl OBJECT IDENTIFIER ::= { fkV2Security4ACLPolicyFlowClass 2 }

		
		-- 1.3.6.1.4.1.10428 9 1.102.7.2.5.4.2.2.1
		fkV2Security4ACLPolicyFlowClassControlRequest OBJECT-TYPE
			SYNTAX INTEGER
				{
				addFlowClass(1),
				deleteFlowClass(2),
				deleteAllFlow(3),
				deleteAllClass(4),
				deleteAllFlowClass(5)
				}
			MAX-ACCESS read-write
			STATUS current
			DESCRIPTION
				"The request of a user command"
			::= { fkV2Security4ACLPolicyFlowClassControl 1 }

		
		-- 1.3.6.1.4.1.10428 9 1.102.7.2.5.4.2.2.2
		fkV2Security4ACLPolicyFlowClassControlStatus OBJECT-TYPE
			SYNTAX FkControlStatusType
			MAX-ACCESS read-write
			STATUS current
			DESCRIPTION
				"The status of user command"
			::= { fkV2Security4ACLPolicyFlowClassControl 2 }

		
		-- 1.3.6.1.4.1.10428 9 1.102.7.2.5.4.2.2.3
		fkV2Security4ACLPolicyFlowClassControlTimer OBJECT-TYPE
			SYNTAX Gauge32
			MAX-ACCESS read-write
			STATUS current
			DESCRIPTION
				"The maximum time for the manager for a long running user command"
			::= { fkV2Security4ACLPolicyFlowClassControl 3 }

		
		-- 1.3.6.1.4.1.10428 9 1.102.7.2.5.4.2.2.4
		fkV2Security4ACLPolicyFlowClassControlTimeStamp OBJECT-TYPE
			SYNTAX TimeTicks
			MAX-ACCESS read-write
			STATUS current
			DESCRIPTION
				"The time stamp of the last command(end of command)"
			::= { fkV2Security4ACLPolicyFlowClassControl 4 }

		
		-- 1.3.6.1.4.1.10428 9 1.102.7.2.5.4.2.2.5
		fkV2Security4ACLPolicyFlowClassControlReqResult OBJECT-TYPE
			SYNTAX FkControlRequestResultType
			MAX-ACCESS read-write
			STATUS current
			DESCRIPTION
				"The result of the last user command"
			::= { fkV2Security4ACLPolicyFlowClassControl 5 }

		
		-- 1.3.6.1.4.1.10428 9 1.102.7.2.5.4.2.2.6
		fkV2Security4ACLPolicyFlowClassControlPolicyIndex OBJECT-TYPE
			SYNTAX IntPolicyIndex
			MAX-ACCESS read-write
			STATUS current
			DESCRIPTION
				"The index of Policy"
			::= { fkV2Security4ACLPolicyFlowClassControl 6 }

		
		-- 1.3.6.1.4.1.10428 9 1.102.7.2.5.4.2.2.7
		fkV2Security4ACLPolicyFlowClassControlIndex OBJECT-TYPE
			SYNTAX IntFlowIndex
			MAX-ACCESS read-write
			STATUS current
			DESCRIPTION
				"The index of flow or class in this policy"
			::= { fkV2Security4ACLPolicyFlowClassControl 7 }

		
		-- 1.3.6.1.4.1.10428 9 1.102.7.2.5.4.2.2.8
		fkV2Security4ACLPolicyFlowClassControlType OBJECT-TYPE
			SYNTAX IntFlowOrClass
			MAX-ACCESS read-write
			STATUS current
			DESCRIPTION
				"The type of flow or class"
			::= { fkV2Security4ACLPolicyFlowClassControl 8 }

		
		-- 1.3.6.1.4.1.10428 9 1.102.7.2.5.4.2.2.9
		fkV2Security4ACLPolicyFlowClassControlFlowID OBJECT-TYPE
			SYNTAX IntFlowIndex
			MAX-ACCESS read-write
			STATUS current
			DESCRIPTION
				"The index of flow
				Available according to fkV2QoS4PolicyFlowClassControlType.
				"
			::= { fkV2Security4ACLPolicyFlowClassControl 9 }

		
		-- 1.3.6.1.4.1.10428 9 1.102.7.2.5.4.2.2.10
		fkV2Security4ACLPolicyFlowClassControlClassID OBJECT-TYPE
			SYNTAX IntClassIndex
			MAX-ACCESS read-write
			STATUS current
			DESCRIPTION
				"The index of class
				Available according to fkV2QoS4PolicyFlowClassControlType.
				"
			::= { fkV2Security4ACLPolicyFlowClassControl 10 }

		
		-- 1.3.6.1.4.1.10428 9 1.102.7.2.5.4.2.3
		fkV2Security4ACLPolicyFlowClassNotification OBJECT IDENTIFIER ::= { fkV2Security4ACLPolicyFlowClass 3 }

		
		-- 1.3.6.1.4.1.10428 9 1.102.7.2.5.4.2.3.1
		fkACLPolicyFlowAdded NOTIFICATION-TYPE
			OBJECTS { fkV2Security4ACLPolicyFlowClassControlRequest, fkV2Security4ACLPolicyFlowClassControlTimeStamp, fkV2Security4ACLPolicyFlowClassControlReqResult, fkV2Security4ACLPolicyFlowClassType, fkV2Security4ACLPolicyFlowClassID
				 }
			STATUS current
			DESCRIPTION 
				"Description."
			::= { fkV2Security4ACLPolicyFlowClassNotification 1 }

		
		-- 1.3.6.1.4.1.10428 9 1.102.7.2.5.4.2.3.2
		fkACLPolicyFlowDeleted NOTIFICATION-TYPE
			OBJECTS { fkV2Security4ACLPolicyFlowClassControlRequest, fkV2Security4ACLPolicyFlowClassControlTimeStamp, fkV2Security4ACLPolicyFlowClassControlReqResult, fkV2Security4ACLPolicyFlowClassControlPolicyIndex, fkV2Security4ACLPolicyFlowClassControlIndex
				 }
			STATUS current
			DESCRIPTION 
				"Description."
			::= { fkV2Security4ACLPolicyFlowClassNotification 2 }

		
		-- 1.3.6.1.4.1.10428 9 1.102.7.2.5.4.2.3.3
		fkACLPolicyAllFlowDeleted NOTIFICATION-TYPE
			OBJECTS { fkV2Security4ACLPolicyFlowClassControlRequest, fkV2Security4ACLPolicyFlowClassControlTimeStamp, fkV2Security4ACLPolicyFlowClassControlReqResult, fkV2Security4ACLPolicyFlowClassControlPolicyIndex }
			STATUS current
			DESCRIPTION 
				"Description."
			::= { fkV2Security4ACLPolicyFlowClassNotification 3 }

		
		-- 1.3.6.1.4.1.10428 9 1.102.7.2.5.4.2.3.4
		fkACLPolicyAllClassDeleted NOTIFICATION-TYPE
			OBJECTS { fkV2Security4ACLPolicyFlowClassControlRequest, fkV2Security4ACLPolicyFlowClassControlTimeStamp, fkV2Security4ACLPolicyFlowClassControlReqResult, fkV2Security4ACLPolicyFlowClassControlPolicyIndex }
			STATUS current
			DESCRIPTION 
				"Description."
			::= { fkV2Security4ACLPolicyFlowClassNotification 4 }

		
		-- 1.3.6.1.4.1.10428 9 1.102.7.2.5.4.2.3.5
		fkACLPolicyAllFlowClassDeleted NOTIFICATION-TYPE
			OBJECTS { fkV2Security4ACLPolicyFlowClassControlRequest, fkV2Security4ACLPolicyFlowClassControlTimeStamp, fkV2Security4ACLPolicyFlowClassControlReqResult, fkV2Security4ACLPolicyFlowClassControlPolicyIndex }
			STATUS current
			DESCRIPTION 
				"Description."
			::= { fkV2Security4ACLPolicyFlowClassNotification 5 }

		
		-- 1.3.6.1.4.1.10428 9 1.102.7.2.6
		fkV2SecuritySACL OBJECT IDENTIFIER ::= { fkVSecurity4 6 }

		
		-- 1.3.6.1.4.1.10428 9 1.102.7.2.6.1
		fkV2SecuritySACLTable OBJECT-TYPE
			SYNTAX SEQUENCE OF FkV2SecuritySACLEntry
			MAX-ACCESS not-accessible
			STATUS current
			DESCRIPTION
				"ACL table."
			::= { fkV2SecuritySACL 1 }

		
		-- 1.3.6.1.4.1.10428 9 1.102.7.2.6.1.1
		fkV2SecuritySACLEntry OBJECT-TYPE
			SYNTAX FkV2SecuritySACLEntry
			MAX-ACCESS not-accessible
			STATUS current
			DESCRIPTION
				"key: fkV2SecuritySACLName"
			INDEX { fkV2SecuritySACLName }
			::= { fkV2SecuritySACLTable 1 }

		
		FkV2SecuritySACLEntry ::=
			SEQUENCE { 
				fkV2SecuritySACLName
					OctetName,
				fkV2SecuritySACLSrcIpaddr
					IpAddress,
				fkV2SecuritySACLSrcPrefixLength
					Integer32,
				fkV2SecuritySACLDstIpAddr
					IpAddress,
				fkV2SecuritySACLDstPrefixLength
					Integer32,
				fkV2SecuritySACLProtocolType
					IntProtocolType,
				fkV2SecuritySACLTcpflag
					BITS,
				fkV2SecuritySACLSrcL4Port
					IntL4Port,
				fkV2SecuritySACLDstL4Port
					IntL4Port,
				fkV2SecuritySACLIcmpType
					IntProtocolType,
				fkV2SecuritySACLIcmpCode
					IntProtocolType,
				fkV2SecuritySACLPriority
					INTEGER,
				fkV2SecuritySACLMatchAction
					INTEGER,
				fkV2SecuritySACLNomatchAction
					INTEGER
			 }

		-- 1.3.6.1.4.1.10428 9 1.102.7.2.6.1.1.1
		fkV2SecuritySACLName OBJECT-TYPE
			SYNTAX OctetName
			MAX-ACCESS read-only
			STATUS current
			DESCRIPTION
				"Name of this ACL rule"
			::= { fkV2SecuritySACLEntry 1 }

		
		-- 1.3.6.1.4.1.10428 9 1.102.7.2.6.1.1.2
		fkV2SecuritySACLSrcIpaddr OBJECT-TYPE
			SYNTAX IpAddress
			MAX-ACCESS read-only
			STATUS current
			DESCRIPTION
				"The IP address to match against the packet¡¯s source IP address"
			::= { fkV2SecuritySACLEntry 2 }

		
		-- 1.3.6.1.4.1.10428 9 1.102.7.2.6.1.1.3
		fkV2SecuritySACLSrcPrefixLength OBJECT-TYPE
			SYNTAX Integer32 (0..32)
			MAX-ACCESS read-only
			STATUS current
			DESCRIPTION
				"Subnet mask."
			::= { fkV2SecuritySACLEntry 3 }

		
		-- 1.3.6.1.4.1.10428 9 1.102.7.2.6.1.1.4
		fkV2SecuritySACLDstIpAddr OBJECT-TYPE
			SYNTAX IpAddress
			MAX-ACCESS read-only
			STATUS current
			DESCRIPTION
				"The IP address to match against the packet¡¯s destination IP address"
			::= { fkV2SecuritySACLEntry 4 }

		
		-- 1.3.6.1.4.1.10428 9 1.102.7.2.6.1.1.5
		fkV2SecuritySACLDstPrefixLength OBJECT-TYPE
			SYNTAX Integer32 (0..32)
			MAX-ACCESS read-only
			STATUS current
			DESCRIPTION
				"Subnet mask."
			::= { fkV2SecuritySACLEntry 5 }

		
		-- 1.3.6.1.4.1.10428 9 1.102.7.2.6.1.1.6
		fkV2SecuritySACLProtocolType OBJECT-TYPE
			SYNTAX IntProtocolType
			MAX-ACCESS read-only
			STATUS current
			DESCRIPTION
				"The type of IP protocol
				 	The flat internet protocol is from fkV2SecuritySACLTcpflag to fkV2SecuritySACLIcmpCode
				 	If the value is tcp(6) or udp(17),
				 	From fkV2SecuritySACLTcpflag to fkV2SecuritySACLDstL4Port value is available
				 	If the value is icmp(1),
				 	The value of fkV2SecuritySACLIcmpType and fkV2SecuritySACLIcmpCode is available
				 	The value of -1 means any(not set)
				"
			::= { fkV2SecuritySACLEntry 6 }

		
		-- 1.3.6.1.4.1.10428 9 1.102.7.2.6.1.1.7
		fkV2SecuritySACLTcpflag OBJECT-TYPE
			SYNTAX BITS
				{
				reserv(0),
				reserv1(1),
				urg(2),
				ack(3),
				psh(4),
				rst(5),
				syn(6),
				fin(7)
				}
			MAX-ACCESS read-only
			STATUS current
			DESCRIPTION
				"TCP flag"
			::= { fkV2SecuritySACLEntry 7 }

		
		-- 1.3.6.1.4.1.10428 9 1.102.7.2.6.1.1.8
		fkV2SecuritySACLSrcL4Port OBJECT-TYPE
			SYNTAX IntL4Port
			MAX-ACCESS read-only
			STATUS current
			DESCRIPTION
				"The source service port number (only valid for TCP or UDP packet).."
			::= { fkV2SecuritySACLEntry 8 }

		
		-- 1.3.6.1.4.1.10428 9 1.102.7.2.6.1.1.9
		fkV2SecuritySACLDstL4Port OBJECT-TYPE
			SYNTAX IntL4Port
			MAX-ACCESS read-only
			STATUS current
			DESCRIPTION
				"The destination service port number (only valid for TCP or UDP packet). "
			::= { fkV2SecuritySACLEntry 9 }

		
		-- 1.3.6.1.4.1.10428 9 1.102.7.2.6.1.1.10
		fkV2SecuritySACLIcmpType OBJECT-TYPE
			SYNTAX IntProtocolType
			MAX-ACCESS read-only
			STATUS current
			DESCRIPTION
				"The Type of ICMP message
				The value of -1 means any(not set)"
			::= { fkV2SecuritySACLEntry 10 }

		
		-- 1.3.6.1.4.1.10428 9 1.102.7.2.6.1.1.11
		fkV2SecuritySACLIcmpCode OBJECT-TYPE
			SYNTAX IntProtocolType
			MAX-ACCESS read-only
			STATUS current
			DESCRIPTION
				"The code of ICMP message
				The value of -1 means any(not set)"
			::= { fkV2SecuritySACLEntry 11 }

		
		-- 1.3.6.1.4.1.10428 9 1.102.7.2.6.1.1.12
		fkV2SecuritySACLPriority OBJECT-TYPE
			SYNTAX INTEGER
				{
				low(1),
				medium(2),
				high(3),
				highest(4)
				}
			MAX-ACCESS read-only
			STATUS current
			DESCRIPTION
				"The type of ICMP message
				The value of -1 means any(not set)
				"
			::= { fkV2SecuritySACLEntry 12 }

		
		-- 1.3.6.1.4.1.10428 9 1.102.7.2.6.1.1.13
		fkV2SecuritySACLMatchAction OBJECT-TYPE
			SYNTAX INTEGER
				{
				none(0),
				permit(1),
				deny(2)
				}
			MAX-ACCESS read-only
			STATUS current
			DESCRIPTION
				"Action for packets that match against this ACL rule."
			::= { fkV2SecuritySACLEntry 13 }

		
		-- 1.3.6.1.4.1.10428 9 1.102.7.2.6.1.1.14
		fkV2SecuritySACLNomatchAction OBJECT-TYPE
			SYNTAX INTEGER
				{
				none(0),
				permit(1),
				deny(2)
				}
			MAX-ACCESS read-only
			STATUS current
			DESCRIPTION
				"Action for packets that don¡¯t match against this ACL rule."
			::= { fkV2SecuritySACLEntry 14 }

		
		-- 1.3.6.1.4.1.10428 9 1.102.7.2.6.2
		fkV2SecuritySACLControl OBJECT IDENTIFIER ::= { fkV2SecuritySACL 2 }

		
		-- 1.3.6.1.4.1.10428 9 1.102.7.2.6.2.1
		fkV2SecuritySACLControlRequest OBJECT-TYPE
			SYNTAX INTEGER
				{
				createSAclRule(1),
				destroySAclRule(2),
				destroyAllSAclRule(3)
				}
			MAX-ACCESS read-write
			STATUS current
			DESCRIPTION
				"The request of a user command"
			::= { fkV2SecuritySACLControl 1 }

		
		-- 1.3.6.1.4.1.10428 9 1.102.7.2.6.2.2
		fkV2SecuritySACLControlStatus OBJECT-TYPE
			SYNTAX FkControlStatusType
			MAX-ACCESS read-only
			STATUS current
			DESCRIPTION
				"The status of user command"
			::= { fkV2SecuritySACLControl 2 }

		
		-- 1.3.6.1.4.1.10428 9 1.102.7.2.6.2.3
		fkV2SecuritySACLControlTimer OBJECT-TYPE
			SYNTAX Gauge32
			MAX-ACCESS read-write
			STATUS current
			DESCRIPTION
				"The maximum time for the manager for a long running user command"
			::= { fkV2SecuritySACLControl 3 }

		
		-- 1.3.6.1.4.1.10428 9 1.102.7.2.6.2.4
		fkV2SecuritySACLControlTimeStamp OBJECT-TYPE
			SYNTAX TimeStamp
			MAX-ACCESS read-only
			STATUS current
			DESCRIPTION
				"The time stamp of the last command(end of command)"
			::= { fkV2SecuritySACLControl 4 }

		
		-- 1.3.6.1.4.1.10428 9 1.102.7.2.6.2.5
		fkV2SecuritySACLControlReqResult OBJECT-TYPE
			SYNTAX FkControlRequestResultType
			MAX-ACCESS read-only
			STATUS current
			DESCRIPTION
				"The result of the last user command"
			::= { fkV2SecuritySACLControl 5 }

		
		-- 1.3.6.1.4.1.10428 9 1.102.7.2.6.2.6
		fkV2SecuritySACLControlName OBJECT-TYPE
			SYNTAX OctetName
			MAX-ACCESS read-write
			STATUS current
			DESCRIPTION
				"Name of this ACL rule"
			::= { fkV2SecuritySACLControl 6 }

		
		-- 1.3.6.1.4.1.10428 9 1.102.7.2.6.2.7
		fkV2SecuritySACLControlSrcIpaddr OBJECT-TYPE
			SYNTAX IpAddress
			MAX-ACCESS read-write
			STATUS current
			DESCRIPTION
				"The IP address to match against the packet¡¯s source IP address"
			::= { fkV2SecuritySACLControl 7 }

		
		-- 1.3.6.1.4.1.10428 9 1.102.7.2.6.2.8
		fkV2SecuritySACLControlSrcPrefixLength OBJECT-TYPE
			SYNTAX IntIpAddrMask
			MAX-ACCESS read-write
			STATUS current
			DESCRIPTION
				"Subnet mask."
			::= { fkV2SecuritySACLControl 8 }

		
		-- 1.3.6.1.4.1.10428 9 1.102.7.2.6.2.9
		fkV2SecuritySACLControlDstIpaddr OBJECT-TYPE
			SYNTAX IpAddress
			MAX-ACCESS read-write
			STATUS current
			DESCRIPTION
				"The IP address to match against the packet¡¯s destination IP address"
			::= { fkV2SecuritySACLControl 9 }

		
		-- 1.3.6.1.4.1.10428 9 1.102.7.2.6.2.10
		fkV2SecuritySACLControlDstPrefixLength OBJECT-TYPE
			SYNTAX IntIpAddrMask
			MAX-ACCESS read-write
			STATUS current
			DESCRIPTION
				"Subnet mask."
			::= { fkV2SecuritySACLControl 10 }

		
		-- 1.3.6.1.4.1.10428 9 1.102.7.2.6.2.11
		fkV2SecuritySACLControlProtocolType OBJECT-TYPE
			SYNTAX IntProtocolType
			MAX-ACCESS read-write
			STATUS current
			DESCRIPTION
				"The IP protocol type value"
			::= { fkV2SecuritySACLControl 11 }

		
		-- 1.3.6.1.4.1.10428 9 1.102.7.2.6.2.12
		fkV2SecuritySACLControlTcpflag OBJECT-TYPE
			SYNTAX BITS
				{
				reserv(0),
				reserv1(1),
				urg(2),
				ack(3),
				psh(4),
				rst(5),
				syn(6),
				fin(7)
				}
			MAX-ACCESS read-write
			STATUS current
			DESCRIPTION
				"TCP flag"
			::= { fkV2SecuritySACLControl 12 }

		
		-- 1.3.6.1.4.1.10428 9 1.102.7.2.6.2.13
		fkV2SecuritySACLControlSrcL4Port OBJECT-TYPE
			SYNTAX IntL4Port
			MAX-ACCESS read-write
			STATUS current
			DESCRIPTION
				"The source service port number (only valid for TCP or UDP packet).."
			::= { fkV2SecuritySACLControl 13 }

		
		-- 1.3.6.1.4.1.10428 9 1.102.7.2.6.2.14
		fkV2SecuritySACLControlDstL4Port OBJECT-TYPE
			SYNTAX IntL4Port
			MAX-ACCESS read-write
			STATUS current
			DESCRIPTION
				"The destination service port number (only valid for TCP or UDP packet). "
			::= { fkV2SecuritySACLControl 14 }

		
		-- 1.3.6.1.4.1.10428 9 1.102.7.2.6.2.15
		fkV2SecuritySACLControlIcmpType OBJECT-TYPE
			SYNTAX IntProtocolType
			MAX-ACCESS read-write
			STATUS current
			DESCRIPTION
				"The type of ICMP message
				The value of -1 means any(not set)
				"
			::= { fkV2SecuritySACLControl 15 }

		
		-- 1.3.6.1.4.1.10428 9 1.102.7.2.6.2.16
		fkV2SecuritySACLControlIcmpCode OBJECT-TYPE
			SYNTAX IntProtocolType
			MAX-ACCESS read-write
			STATUS current
			DESCRIPTION
				"The code of ICMP message
				The value of -1 means any(not set)
				"
			::= { fkV2SecuritySACLControl 16 }

		
		-- 1.3.6.1.4.1.10428 9 1.102.7.2.6.2.17
		fkV2SecuritySACLControlPriority OBJECT-TYPE
			SYNTAX INTEGER
				{
				low(1),
				medium(2),
				high(3),
				highest(4)
				}
			MAX-ACCESS read-write
			STATUS current
			DESCRIPTION
				"The Priority of this ACL rule)"
			::= { fkV2SecuritySACLControl 17 }

		
		-- 1.3.6.1.4.1.10428 9 1.102.7.2.6.2.18
		fkV2SecuritySACLControlMatchAction OBJECT-TYPE
			SYNTAX INTEGER
				{
				none(0),
				permit(1),
				deny(2)
				}
			MAX-ACCESS read-write
			STATUS current
			DESCRIPTION
				"Action for packets that match against this ACL rule."
			::= { fkV2SecuritySACLControl 18 }

		
		-- 1.3.6.1.4.1.10428 9 1.102.7.2.6.2.19
		fkV2SecuritySACLControlNomatchAction OBJECT-TYPE
			SYNTAX INTEGER
				{
				none(0),
				permit(1),
				deny(2)
				}
			MAX-ACCESS read-write
			STATUS current
			DESCRIPTION
				"Action for packets that don¡¯t match against this ACL rule."
			::= { fkV2SecuritySACLControl 19 }

		
		-- 1.3.6.1.4.1.10428 9 1.102.7.2.6.3
		fkV2SecuritySACLNotification OBJECT IDENTIFIER ::= { fkV2SecuritySACL 3 }

		
		-- 1.3.6.1.4.1.10428 9 1.102.7.2.6.3.1
		fkSACLCreated NOTIFICATION-TYPE
			OBJECTS { fkV2SecuritySACLControlRequest, fkV2SecuritySACLControlTimeStamp, fkV2SecuritySACLControlReqResult, fkV2SecuritySACLSrcIpaddr, fkV2SecuritySACLSrcPrefixLength, 
				fkV2SecuritySACLDstIpAddr, fkV2SecuritySACLDstPrefixLength, fkV2SecuritySACLProtocolType, fkV2SecuritySACLTcpflag, fkV2SecuritySACLIcmpType, 
				fkV2SecuritySACLIcmpCode, fkV2SecuritySACLPriority, fkV2SecuritySACLMatchAction, fkV2SecuritySACLNomatchAction, fkV2SecuritySACLSrcL4Port, 
				fkV2SecuritySACLDstL4Port }
			STATUS current
			DESCRIPTION 
				"Description."
			::= { fkV2SecuritySACLNotification 1 }

		
		-- 1.3.6.1.4.1.10428 9 1.102.7.2.6.3.2
		fkSACLDestroyed NOTIFICATION-TYPE
			OBJECTS { fkV2SecuritySACLControlRequest, fkV2SecuritySACLControlTimeStamp, fkV2SecuritySACLControlName, fkV2SecuritySACLControlReqResult }
			STATUS current
			DESCRIPTION 
				"Description."
			::= { fkV2SecuritySACLNotification 2 }

		
		-- 1.3.6.1.4.1.10428 9 1.102.7.2.6.3.3
		fkSACLAllDestroyed NOTIFICATION-TYPE
			OBJECTS { fkV2SecuritySACLControlRequest, fkV2SecuritySACLControlTimeStamp, fkV2SecuritySACLControlReqResult }
			STATUS current
			DESCRIPTION 
				"Description."
			::= { fkV2SecuritySACLNotification 3 }

		
		-- 1.3.6.1.4.1.10428 9 1.102.7.2.7
		fkV2SecurityACLStatistics OBJECT IDENTIFIER ::= { fkVSecurity4 7 }

		
		-- 1.3.6.1.4.1.10428 9 1.102.7.2.7.1
		fkV2SecurityACLStatisticsBase OBJECT IDENTIFIER ::= { fkV2SecurityACLStatistics 1 }

		
		-- 1.3.6.1.4.1.10428 9 1.102.7.2.7.1.1
		fkV2SecurityACLStatisticsBaseInfo OBJECT IDENTIFIER ::= { fkV2SecurityACLStatisticsBase 1 }

		
		-- 1.3.6.1.4.1.10428 9 1.102.7.2.7.1.1.1
		fkV2SecurityACLStatisticsSyslogStatus OBJECT-TYPE
			SYNTAX INTEGER
				{
				enable(1),
				disable(2)
				}
			MAX-ACCESS read-only
			STATUS current
			DESCRIPTION
				"ACL statistics syslog status"
			::= { fkV2SecurityACLStatisticsBaseInfo 1 }

		
		-- 1.3.6.1.4.1.10428 9 1.102.7.2.7.1.2
		fkV2SecurityACLStatisticsBaseControl OBJECT IDENTIFIER ::= { fkV2SecurityACLStatisticsBase 2 }

		
		-- 1.3.6.1.4.1.10428 9 1.102.7.2.7.1.2.1
		fkV2SecurityACLStatisticsBaseControlRequest OBJECT-TYPE
			SYNTAX INTEGER { aclSyslogModeChange(1) }
			MAX-ACCESS read-write
			STATUS current
			DESCRIPTION
				"The request of a user command"
			::= { fkV2SecurityACLStatisticsBaseControl 1 }

		
		-- 1.3.6.1.4.1.10428 9 1.102.7.2.7.1.2.2
		fkV2SecurityACLStatisticsBaseControlStatus OBJECT-TYPE
			SYNTAX FkControlStatusType
			MAX-ACCESS read-only
			STATUS current
			DESCRIPTION
				"The status of user command"
			::= { fkV2SecurityACLStatisticsBaseControl 2 }

		
		-- 1.3.6.1.4.1.10428 9 1.102.7.2.7.1.2.3
		fkV2SecurityACLStatisticsBaseControlTimer OBJECT-TYPE
			SYNTAX Gauge32
			MAX-ACCESS read-write
			STATUS current
			DESCRIPTION
				"The maximum time for the manager for a long running user command"
			::= { fkV2SecurityACLStatisticsBaseControl 3 }

		
		-- 1.3.6.1.4.1.10428 9 1.102.7.2.7.1.2.4
		fkV2SecurityACLStatisticsBaseControlTimeStamp OBJECT-TYPE
			SYNTAX TimeStamp
			MAX-ACCESS read-only
			STATUS current
			DESCRIPTION
				"The time stamp of the last command(end of command)"
			::= { fkV2SecurityACLStatisticsBaseControl 4 }

		
		-- 1.3.6.1.4.1.10428 9 1.102.7.2.7.1.2.5
		fkV2SecurityACLStatisticsBaseControlReqResult OBJECT-TYPE
			SYNTAX FkControlRequestResultType
			MAX-ACCESS read-only
			STATUS current
			DESCRIPTION
				"The result of the last user command"
			::= { fkV2SecurityACLStatisticsBaseControl 5 }

		
		-- 1.3.6.1.4.1.10428 9 1.102.7.2.7.1.2.6
		fkV2SecurityACLStatisticsBaseControlSyslogMode OBJECT-TYPE
			SYNTAX INTEGER
				{
				enable(1),
				disable(2)
				}
			MAX-ACCESS read-write
			STATUS current
			DESCRIPTION
				"The ACL statistics syslog mode"
			::= { fkV2SecurityACLStatisticsBaseControl 6 }

		
		-- 1.3.6.1.4.1.10428 9 1.102.7.2.7.1.3
		fkV2SecurityACLStatisticsBaseNotification OBJECT IDENTIFIER ::= { fkV2SecurityACLStatisticsBase 3 }

		
		-- 1.3.6.1.4.1.10428 9 1.102.7.2.7.1.3.1
		fkV2SecurityACLStatisticsSyslogModeChanged NOTIFICATION-TYPE
			OBJECTS { fkV2SecurityACLStatisticsBaseControlRequest, fkV2SecurityACLStatisticsBaseControlTimeStamp, fkV2SecurityACLStatisticsBaseControlReqResult, fkV2SecurityACLStatisticsBaseControlSyslogMode }
			STATUS current
			DESCRIPTION 
				"Description."
			::= { fkV2SecurityACLStatisticsBaseNotification 1 }

		
		-- 1.3.6.1.4.1.10428 9 1.102.7.2.7.2
		fkV2SecurityACLStatisticsPacketHistory OBJECT IDENTIFIER ::= { fkV2SecurityACLStatistics 2 }

		
		-- 1.3.6.1.4.1.10428 9 1.102.7.2.7.2.1
		fkV2SecurityACLPacketCountTable OBJECT-TYPE
			SYNTAX SEQUENCE OF FkV2SecurityACLPacketCountEntry
			MAX-ACCESS not-accessible
			STATUS current
			DESCRIPTION
				"ACL packet count table."
			::= { fkV2SecurityACLStatisticsPacketHistory 1 }

		
		-- 1.3.6.1.4.1.10428 9 1.102.7.2.7.2.1.1
		fkV2SecurityACLPacketCountEntry OBJECT-TYPE
			SYNTAX FkV2SecurityACLPacketCountEntry
			MAX-ACCESS not-accessible
			STATUS current
			DESCRIPTION
				"key: fkV2SecuritySACLName"
			INDEX { fkV2SecuritySACLName }
			::= { fkV2SecurityACLPacketCountTable 1 }

		
		FkV2SecurityACLPacketCountEntry ::=
			SEQUENCE { 
				fkV2SecurityACLTotalPacket
					Counter64
			 }

		-- 1.3.6.1.4.1.10428 9 1.102.7.2.7.2.1.1.1
		fkV2SecurityACLTotalPacket OBJECT-TYPE
			SYNTAX Counter64
			MAX-ACCESS read-only
			STATUS current
			DESCRIPTION
				"ACL total packet"
			::= { fkV2SecurityACLPacketCountEntry 1 }

		
		-- 1.3.6.1.4.1.10428 9 1.102.7.2.7.2.2
		fkV2SecurityACLSrcHistoryTable OBJECT-TYPE
			SYNTAX SEQUENCE OF FkV2SecurityACLSrcHistoryEntry
			MAX-ACCESS not-accessible
			STATUS current
			DESCRIPTION
				"ACL source history table."
			::= { fkV2SecurityACLStatisticsPacketHistory 2 }

		
		-- 1.3.6.1.4.1.10428 9 1.102.7.2.7.2.2.1
		fkV2SecurityACLSrcHistoryEntry OBJECT-TYPE
			SYNTAX FkV2SecurityACLSrcHistoryEntry
			MAX-ACCESS not-accessible
			STATUS current
			DESCRIPTION
				"key: fkV2SecuritySACLName, fkV2SecurityACLSrcHistoryIndex"
			INDEX { fkV2SecuritySACLName, fkV2SecurityACLSrcHistoryIndex }
			::= { fkV2SecurityACLSrcHistoryTable 1 }

		
		FkV2SecurityACLSrcHistoryEntry ::=
			SEQUENCE { 
				fkV2SecurityACLSrcHistoryIndex
					Integer32,
				fkV2SecurityACLSrcHistoryIpAddr
					IpAddress
			 }

		-- 1.3.6.1.4.1.10428 9 1.102.7.2.7.2.2.1.1
		fkV2SecurityACLSrcHistoryIndex OBJECT-TYPE
			SYNTAX Integer32 (1..1024)
			MAX-ACCESS read-only
			STATUS current
			DESCRIPTION
				"The ACL index."
			::= { fkV2SecurityACLSrcHistoryEntry 1 }

		
		-- 1.3.6.1.4.1.10428 9 1.102.7.2.7.2.2.1.2
		fkV2SecurityACLSrcHistoryIpAddr OBJECT-TYPE
			SYNTAX IpAddress
			MAX-ACCESS read-only
			STATUS current
			DESCRIPTION
				"The ACl IP address"
			::= { fkV2SecurityACLSrcHistoryEntry 2 }

		
		-- 1.3.6.1.4.1.10428 9 1.102.7.2.7.2.3
		fkV2SecurityACLStatisticsControl OBJECT IDENTIFIER ::= { fkV2SecurityACLStatisticsPacketHistory 3 }

		
		-- 1.3.6.1.4.1.10428 9 1.102.7.2.7.2.3.1
		fkV2SecurityACLStatisticsControlRequest OBJECT-TYPE
			SYNTAX INTEGER { clearAruleStatus(1) }
			MAX-ACCESS read-write
			STATUS current
			DESCRIPTION
				"The request of a user command"
			::= { fkV2SecurityACLStatisticsControl 1 }

		
		-- 1.3.6.1.4.1.10428 9 1.102.7.2.7.2.3.2
		fkV2SecurityACLStatisticsControlStatus OBJECT-TYPE
			SYNTAX FkControlStatusType
			MAX-ACCESS read-only
			STATUS current
			DESCRIPTION
				"The status of user command"
			::= { fkV2SecurityACLStatisticsControl 2 }

		
		-- 1.3.6.1.4.1.10428 9 1.102.7.2.7.2.3.3
		fkV2SecurityACLStatisticsControlTimer OBJECT-TYPE
			SYNTAX Gauge32
			MAX-ACCESS read-write
			STATUS current
			DESCRIPTION
				"The maximum time for the manager for a long running user command"
			::= { fkV2SecurityACLStatisticsControl 3 }

		
		-- 1.3.6.1.4.1.10428 9 1.102.7.2.7.2.3.4
		fkV2SecurityACLStatisticsControlTimeStamp OBJECT-TYPE
			SYNTAX TimeStamp
			MAX-ACCESS read-only
			STATUS current
			DESCRIPTION
				"The time stamp of the last command(end of command)"
			::= { fkV2SecurityACLStatisticsControl 4 }

		
		-- 1.3.6.1.4.1.10428 9 1.102.7.2.7.2.3.5
		fkV2SecurityACLStatisticsControlReqResult OBJECT-TYPE
			SYNTAX FkControlRequestResultType
			MAX-ACCESS read-only
			STATUS current
			DESCRIPTION
				"The result of the last user command"
			::= { fkV2SecurityACLStatisticsControl 5 }

		
		-- 1.3.6.1.4.1.10428 9 1.102.7.2.7.2.3.6
		fkV2SecurityACLStatisticsControlName OBJECT-TYPE
			SYNTAX OctetName
			MAX-ACCESS read-write
			STATUS current
			DESCRIPTION
				"The ACL statistics name"
			::= { fkV2SecurityACLStatisticsControl 6 }

		
		-- 1.3.6.1.4.1.10428 9 1.102.7.2.7.2.4
		fkV2SecurityACLStatisticsNotification OBJECT IDENTIFIER ::= { fkV2SecurityACLStatisticsPacketHistory 4 }

		
		-- 1.3.6.1.4.1.10428 9 1.102.7.2.7.2.4.1
		fkV2SecurityACLStatisticsCleared NOTIFICATION-TYPE
			OBJECTS { fkV2SecurityACLStatisticsControlRequest, fkV2SecurityACLStatisticsControlTimeStamp, fkV2SecurityACLStatisticsControlReqResult, fkV2SecurityACLStatisticsControlName }
			STATUS current
			DESCRIPTION 
				"Description."
			::= { fkV2SecurityACLStatisticsNotification 1 }

		
		-- 1.3.6.1.4.1.10428 9 1.102.7.2.8
		fkV2CpuPacketFilter OBJECT IDENTIFIER ::= { fkVSecurity4 8 }

		
		-- 1.3.6.1.4.1.10428 9 1.102.7.2.8.1
		fkV2CpuPacketFilterTable OBJECT-TYPE
			SYNTAX SEQUENCE OF FkV2CpuPacketFilterEntry
			MAX-ACCESS not-accessible
			STATUS current
			DESCRIPTION
				"cpu packet filter table."
			::= { fkV2CpuPacketFilter 1 }

		
		-- 1.3.6.1.4.1.10428 9 1.102.7.2.8.1.1
		fkV2CpuPacketFilterEntry OBJECT-TYPE
			SYNTAX FkV2CpuPacketFilterEntry
			MAX-ACCESS not-accessible
			STATUS current
			DESCRIPTION
				"key: fkV2CpuPacketFilterIndex"
			INDEX { fkV2CpuPacketFilterIndex }
			::= { fkV2CpuPacketFilterTable 1 }

		
		FkV2CpuPacketFilterEntry ::=
			SEQUENCE { 
				fkV2CpuPacketFilterIndex
					Integer32,
				fkV2CpuPacketFilterName
					OCTET STRING,
				fkV2CpuPacketFilterCreationTime
					Counter32,
				fkV2CpuPacketFilterElapsedtimeAfterClear
					Counter32,
				fkV2CpuPacketFilterStage
					INTEGER,
				fkV2CpuPacketFilterPriority
					Integer32,
				fkV2CpuPacketFilterAction
					INTEGER,
				fkV2CpuPacketFilterActionRateLimit
					Integer32,
				fkV2CpuPacketFilterActionBurstSize
					Integer32,
				fkV2CpuPacketFilterActionTpid
					Integer32,
				fkV2CpuPacketFilterActionPcp
					Integer32,
				fkV2CpuPacketFilterActionVid
					Integer32,
				fkV2CpuPacketFilterActionTagPosition
					Integer32
			 }

		-- 1.3.6.1.4.1.10428 9 1.102.7.2.8.1.1.1
		fkV2CpuPacketFilterIndex OBJECT-TYPE
			SYNTAX Integer32 (1..2147483647)
			MAX-ACCESS read-only
			STATUS current
			DESCRIPTION
				"The index of cpu packet filter"
			::= { fkV2CpuPacketFilterEntry 1 }

		
		-- 1.3.6.1.4.1.10428 9 1.102.7.2.8.1.1.2
		fkV2CpuPacketFilterName OBJECT-TYPE
			SYNTAX OCTET STRING
			MAX-ACCESS read-only
			STATUS current
			DESCRIPTION
				"The name of cpu packet filter"
			::= { fkV2CpuPacketFilterEntry 2 }

		
		-- 1.3.6.1.4.1.10428 9 1.102.7.2.8.1.1.3
		fkV2CpuPacketFilterCreationTime OBJECT-TYPE
			SYNTAX Counter32
			MAX-ACCESS read-only
			STATUS current
			DESCRIPTION
				"The creation time.  (unit : sec)"
			::= { fkV2CpuPacketFilterEntry 3 }

		
		-- 1.3.6.1.4.1.10428 9 1.102.7.2.8.1.1.4
		fkV2CpuPacketFilterElapsedtimeAfterClear OBJECT-TYPE
			SYNTAX Counter32
			MAX-ACCESS read-only
			STATUS current
			DESCRIPTION
				"The elapsed time after clear   (unit : sec)"
			::= { fkV2CpuPacketFilterEntry 4 }

		
		-- 1.3.6.1.4.1.10428 9 1.102.7.2.8.1.1.5
		fkV2CpuPacketFilterStage OBJECT-TYPE
			SYNTAX INTEGER
				{
				cpuingress(1),
				cpuegress(2),
				portrx(3),
				porttx(4),
				vlanAssigned(5),
				unknown(255)
				}
			MAX-ACCESS read-only
			STATUS current
			DESCRIPTION
				"The stage of cpu packet filter."
			::= { fkV2CpuPacketFilterEntry 5 }

		
		-- 1.3.6.1.4.1.10428 9 1.102.7.2.8.1.1.6
		fkV2CpuPacketFilterPriority OBJECT-TYPE
			SYNTAX Integer32 (1..65535)
			MAX-ACCESS read-only
			STATUS current
			DESCRIPTION
				"The priority of cpu packet filter."
			::= { fkV2CpuPacketFilterEntry 6 }

		
		-- 1.3.6.1.4.1.10428 9 1.102.7.2.8.1.1.7
		fkV2CpuPacketFilterAction OBJECT-TYPE
			SYNTAX INTEGER
				{
				drop(1),
				permit(2),
				rateLimit(3),
				pass(4),
				dot1q(5),
				dot1qAttach(6),
				dot1qDetach(7),
				unknown(255)
				}
			MAX-ACCESS read-only
			STATUS current
			DESCRIPTION
				"The action to matched packet.
				Dot1q -> replace
				dot1qAttach -> add
				dot1qDettach -> remove"
			::= { fkV2CpuPacketFilterEntry 7 }

		
		-- 1.3.6.1.4.1.10428 9 1.102.7.2.8.1.1.8
		fkV2CpuPacketFilterActionRateLimit OBJECT-TYPE
			SYNTAX Integer32 (1..100)
			MAX-ACCESS read-only
			STATUS current
			DESCRIPTION
				"The allowed-packet count per second."
			::= { fkV2CpuPacketFilterEntry 8 }

		
		-- 1.3.6.1.4.1.10428 9 1.102.7.2.8.1.1.9
		fkV2CpuPacketFilterActionBurstSize OBJECT-TYPE
			SYNTAX Integer32 (1..100)
			MAX-ACCESS read-only
			STATUS current
			DESCRIPTION
				"The burst-allowed-packet count."
			::= { fkV2CpuPacketFilterEntry 9 }

		
		-- 1.3.6.1.4.1.10428 9 1.102.7.2.8.1.1.10
		fkV2CpuPacketFilterActionTpid OBJECT-TYPE
			SYNTAX Integer32 (0..65535)
			MAX-ACCESS read-only
			STATUS current
			DESCRIPTION
				"The Action TPID
				The value 65535(0xffff) means any."
			::= { fkV2CpuPacketFilterEntry 10 }

		
		-- 1.3.6.1.4.1.10428 9 1.102.7.2.8.1.1.11
		fkV2CpuPacketFilterActionPcp OBJECT-TYPE
			SYNTAX Integer32 (0..7 | 255)
			MAX-ACCESS read-only
			STATUS current
			DESCRIPTION
				"The Action PCP.
				The value 255(0xff) means any."
			::= { fkV2CpuPacketFilterEntry 11 }

		
		-- 1.3.6.1.4.1.10428 9 1.102.7.2.8.1.1.12
		fkV2CpuPacketFilterActionVid OBJECT-TYPE
			SYNTAX Integer32 (0 | 1..4094 | 65535)
			MAX-ACCESS read-only
			STATUS current
			DESCRIPTION
				"The Action VID
				The value 65535(0xffff) means any."
			::= { fkV2CpuPacketFilterEntry 12 }

		
		-- 1.3.6.1.4.1.10428 9 1.102.7.2.8.1.1.13
		fkV2CpuPacketFilterActionTagPosition OBJECT-TYPE
			SYNTAX Integer32 (0 | 1..8)
			MAX-ACCESS read-only
			STATUS current
			DESCRIPTION
				"The Action tag position.
				1 s-vlan
				2 c-vlan"
			::= { fkV2CpuPacketFilterEntry 13 }

		
		-- 1.3.6.1.4.1.10428 9 1.102.7.2.8.2
		fkV2CpuPacketFilterMatchTable OBJECT-TYPE
			SYNTAX SEQUENCE OF FkV2CpuPacketFilterMatchEntry
			MAX-ACCESS not-accessible
			STATUS current
			DESCRIPTION
				"cpu packet filter match table."
			::= { fkV2CpuPacketFilter 2 }

		
		-- 1.3.6.1.4.1.10428 9 1.102.7.2.8.2.1
		fkV2CpuPacketFilterMatchEntry OBJECT-TYPE
			SYNTAX FkV2CpuPacketFilterMatchEntry
			MAX-ACCESS not-accessible
			STATUS current
			DESCRIPTION
				"key: fkV2CpuPacketFilterIndex, fkV2CpuPacketFilterMatchIndex"
			INDEX { fkV2CpuPacketFilterIndex, fkV2CpuPacketFilterMatchIndex }
			::= { fkV2CpuPacketFilterMatchTable 1 }

		
		FkV2CpuPacketFilterMatchEntry ::=
			SEQUENCE { 
				fkV2CpuPacketFilterMatchIndex
					Integer32,
				fkV2CpuPacketFilterMatchType
					BITS,
				fkV2CpuPacketFilterMatchCos
					OCTET STRING,
				fkV2CpuPacketFilterMatchPort
					OCTET STRING,
				fkV2CpuPacketFilterMatchVidmap
					OCTET STRING,
				fkV2CpuPacketFilterMatchTagPosition
					Integer32,
				fkV2CpuPacketFilterMatchTpid
					Integer32,
				fkV2CpuPacketFilterMatchPcp
					Integer32,
				fkV2CpuPacketFilterMatchVid
					Integer32,
				fkV2CpuPacketFilterMatchOffset
					Integer32,
				fkV2CpuPacketFilterMatchLength
					Integer32,
				fkV2CpuPacketFilterMatchData
					OCTET STRING,
				fkV2CpuPacketFilterMatchMask
					OCTET STRING,
				fkV2CpuPacketFilterMatchDesc
					OCTET STRING
			 }

		-- 1.3.6.1.4.1.10428 9 1.102.7.2.8.2.1.1
		fkV2CpuPacketFilterMatchIndex OBJECT-TYPE
			SYNTAX Integer32 (1..65535)
			MAX-ACCESS read-only
			STATUS current
			DESCRIPTION
				"The match entry Index"
			::= { fkV2CpuPacketFilterMatchEntry 1 }

		
		-- 1.3.6.1.4.1.10428 9 1.102.7.2.8.2.1.2
		fkV2CpuPacketFilterMatchType OBJECT-TYPE
			SYNTAX BITS
				{
				vid(0),
				cos(1),
				port(2),
				offset(3),
				dot1q(4)
				}
			MAX-ACCESS read-only
			STATUS current
			DESCRIPTION
				"The  match classifiter type."
			::= { fkV2CpuPacketFilterMatchEntry 2 }

		
		-- 1.3.6.1.4.1.10428 9 1.102.7.2.8.2.1.3
		fkV2CpuPacketFilterMatchCos OBJECT-TYPE
			SYNTAX OCTET STRING
			MAX-ACCESS read-only
			STATUS current
			DESCRIPTION
				"The matched CoS Queue."
			::= { fkV2CpuPacketFilterMatchEntry 3 }

		
		-- 1.3.6.1.4.1.10428 9 1.102.7.2.8.2.1.4
		fkV2CpuPacketFilterMatchPort OBJECT-TYPE
			SYNTAX OCTET STRING
			MAX-ACCESS read-only
			STATUS current
			DESCRIPTION
				"The matched port index."
			::= { fkV2CpuPacketFilterMatchEntry 4 }

		
		-- 1.3.6.1.4.1.10428 9 1.102.7.2.8.2.1.5
		fkV2CpuPacketFilterMatchVidmap OBJECT-TYPE
			SYNTAX OCTET STRING
			MAX-ACCESS read-only
			STATUS current
			DESCRIPTION
				"The matched VID."
			::= { fkV2CpuPacketFilterMatchEntry 5 }

		
		-- 1.3.6.1.4.1.10428 9 1.102.7.2.8.2.1.6
		fkV2CpuPacketFilterMatchTagPosition OBJECT-TYPE
			SYNTAX Integer32 (0 | 1..8)
			MAX-ACCESS read-only
			STATUS current
			DESCRIPTION
				"The matched tag position."
			::= { fkV2CpuPacketFilterMatchEntry 6 }

		
		-- 1.3.6.1.4.1.10428 9 1.102.7.2.8.2.1.7
		fkV2CpuPacketFilterMatchTpid OBJECT-TYPE
			SYNTAX Integer32 (0..65535)
			MAX-ACCESS read-only
			STATUS current
			DESCRIPTION
				"The matched TPID."
			::= { fkV2CpuPacketFilterMatchEntry 7 }

		
		-- 1.3.6.1.4.1.10428 9 1.102.7.2.8.2.1.8
		fkV2CpuPacketFilterMatchPcp OBJECT-TYPE
			SYNTAX Integer32 (0..7 | 255)
			MAX-ACCESS read-only
			STATUS current
			DESCRIPTION
				"The matched PCP"
			::= { fkV2CpuPacketFilterMatchEntry 8 }

		
		-- 1.3.6.1.4.1.10428 9 1.102.7.2.8.2.1.9
		fkV2CpuPacketFilterMatchVid OBJECT-TYPE
			SYNTAX Integer32 (0 | 1..4094 | 65535)
			MAX-ACCESS read-only
			STATUS current
			DESCRIPTION
				"The matched VID"
			::= { fkV2CpuPacketFilterMatchEntry 9 }

		
		-- 1.3.6.1.4.1.10428 9 1.102.7.2.8.2.1.10
		fkV2CpuPacketFilterMatchOffset OBJECT-TYPE
			SYNTAX Integer32 (0..127)
			MAX-ACCESS read-only
			STATUS current
			DESCRIPTION
				"The matched offset"
			::= { fkV2CpuPacketFilterMatchEntry 10 }

		
		-- 1.3.6.1.4.1.10428 9 1.102.7.2.8.2.1.11
		fkV2CpuPacketFilterMatchLength OBJECT-TYPE
			SYNTAX Integer32 (1..16)
			MAX-ACCESS read-only
			STATUS current
			DESCRIPTION
				"The matched Length"
			::= { fkV2CpuPacketFilterMatchEntry 11 }

		
		-- 1.3.6.1.4.1.10428 9 1.102.7.2.8.2.1.12
		fkV2CpuPacketFilterMatchData OBJECT-TYPE
			SYNTAX OCTET STRING
			MAX-ACCESS read-only
			STATUS current
			DESCRIPTION
				"The matched data. (HEX string)"
			::= { fkV2CpuPacketFilterMatchEntry 12 }

		
		-- 1.3.6.1.4.1.10428 9 1.102.7.2.8.2.1.13
		fkV2CpuPacketFilterMatchMask OBJECT-TYPE
			SYNTAX OCTET STRING
			MAX-ACCESS read-only
			STATUS current
			DESCRIPTION
				"The matched mask. (HEX string)"
			::= { fkV2CpuPacketFilterMatchEntry 13 }

		
		-- 1.3.6.1.4.1.10428 9 1.102.7.2.8.2.1.14
		fkV2CpuPacketFilterMatchDesc OBJECT-TYPE
			SYNTAX OCTET STRING
			MAX-ACCESS read-only
			STATUS current
			DESCRIPTION
				"The matched Description"
			::= { fkV2CpuPacketFilterMatchEntry 14 }

		
		-- 1.3.6.1.4.1.10428 9 1.102.7.2.8.3
		fkV2CpuPacketFilterControl OBJECT IDENTIFIER ::= { fkV2CpuPacketFilter 3 }

		
		-- 1.3.6.1.4.1.10428 9 1.102.7.2.8.3.1
		fkV2CpuPacketFilterControlRequest OBJECT-TYPE
			SYNTAX INTEGER
				{
				addCpuPktFilter(1),
				delCpuPktfilter(2),
				setAction(3),
				addMatch(4),
				delMatch(5)
				}
			MAX-ACCESS read-write
			STATUS current
			DESCRIPTION
				"The request of a user command"
			::= { fkV2CpuPacketFilterControl 1 }

		
		-- 1.3.6.1.4.1.10428 9 1.102.7.2.8.3.2
		fkV2CpuPacketFilterControlStatus OBJECT-TYPE
			SYNTAX FkControlStatusType
			MAX-ACCESS read-only
			STATUS current
			DESCRIPTION
				"The status of user command"
			::= { fkV2CpuPacketFilterControl 2 }

		
		-- 1.3.6.1.4.1.10428 9 1.102.7.2.8.3.3
		fkV2CpuPacketFilterControlTimer OBJECT-TYPE
			SYNTAX Gauge32
			MAX-ACCESS read-write
			STATUS current
			DESCRIPTION
				"The maximum time for the manager for a long running user command"
			::= { fkV2CpuPacketFilterControl 3 }

		
		-- 1.3.6.1.4.1.10428 9 1.102.7.2.8.3.4
		fkV2CpuPacketFilterControlTimeStamp OBJECT-TYPE
			SYNTAX TimeStamp
			MAX-ACCESS read-only
			STATUS current
			DESCRIPTION
				"The time stamp of the last command(end of command)"
			::= { fkV2CpuPacketFilterControl 4 }

		
		-- 1.3.6.1.4.1.10428 9 1.102.7.2.8.3.5
		fkV2CpuPacketFilterControlReqResult OBJECT-TYPE
			SYNTAX FkControlRequestResultType
			MAX-ACCESS read-only
			STATUS current
			DESCRIPTION
				"The result of the last user command"
			::= { fkV2CpuPacketFilterControl 5 }

		
		-- 1.3.6.1.4.1.10428 9 1.102.7.2.8.3.6
		fkV2CpuPacketFilterControlIndex OBJECT-TYPE
			SYNTAX Integer32 (1..2147483647)
			MAX-ACCESS read-write
			STATUS current
			DESCRIPTION
				"The match entry Index"
			::= { fkV2CpuPacketFilterControl 6 }

		
		-- 1.3.6.1.4.1.10428 9 1.102.7.2.8.3.7
		fkV2CpuPacketFilterControlName OBJECT-TYPE
			SYNTAX OCTET STRING
			MAX-ACCESS read-write
			STATUS current
			DESCRIPTION
				"Cpu packet filter name."
			::= { fkV2CpuPacketFilterControl 7 }

		
		-- 1.3.6.1.4.1.10428 9 1.102.7.2.8.3.8
		fkV2CpuPacketFilterControlStage OBJECT-TYPE
			SYNTAX INTEGER
				{
				cpuingress(1),
				cpuegress(2),
				portrx(3),
				porttx(4),
				vlanAssigned(5),
				unknown(255)
				}
			MAX-ACCESS read-write
			STATUS current
			DESCRIPTION
				"The stage of cpu packet filter."
			::= { fkV2CpuPacketFilterControl 8 }

		
		-- 1.3.6.1.4.1.10428 9 1.102.7.2.8.3.9
		fkV2CpuPacketFilterControlPriority OBJECT-TYPE
			SYNTAX Integer32 (1..65535)
			MAX-ACCESS read-write
			STATUS current
			DESCRIPTION
				"The priority of cpu packet filter."
			::= { fkV2CpuPacketFilterControl 9 }

		
		-- 1.3.6.1.4.1.10428 9 1.102.7.2.8.3.10
		fkV2CpuPacketFilterControlAction OBJECT-TYPE
			SYNTAX INTEGER
				{
				drop(1),
				permit(2),
				rateLimit(3),
				pass(4),
				dot1q(5),
				dot1qAttach(6),
				dot1qDetach(7),
				unknown(255)
				}
			MAX-ACCESS read-write
			STATUS current
			DESCRIPTION
				"The action to matched packet.
				Dot1q -> replace
				dot1qAttach -> add
				dot1qDettach -> remove"
			::= { fkV2CpuPacketFilterControl 10 }

		
		-- 1.3.6.1.4.1.10428 9 1.102.7.2.8.3.11
		fkV2CpuPacketFilterControlActionRateLimit OBJECT-TYPE
			SYNTAX Integer32 (1..100)
			MAX-ACCESS read-write
			STATUS current
			DESCRIPTION
				"The allowed-packet count per second."
			::= { fkV2CpuPacketFilterControl 11 }

		
		-- 1.3.6.1.4.1.10428 9 1.102.7.2.8.3.12
		fkV2CpuPacketFilterControlActionBurstSize OBJECT-TYPE
			SYNTAX Integer32 (1..100)
			MAX-ACCESS read-write
			STATUS current
			DESCRIPTION
				"The burst-allowed-packet count."
			::= { fkV2CpuPacketFilterControl 12 }

		
		-- 1.3.6.1.4.1.10428 9 1.102.7.2.8.3.13
		fkV2CpuPacketFilterControlActionTpid OBJECT-TYPE
			SYNTAX Integer32 (0..65535)
			MAX-ACCESS read-write
			STATUS current
			DESCRIPTION
				"The Action TPID
				The value 65535(0xffff) means any.
				"
			::= { fkV2CpuPacketFilterControl 13 }

		
		-- 1.3.6.1.4.1.10428 9 1.102.7.2.8.3.14
		fkV2CpuPacketFilterControlActionPcp OBJECT-TYPE
			SYNTAX Integer32 (0..7 | 255)
			MAX-ACCESS read-write
			STATUS current
			DESCRIPTION
				"The Action PCP.
				The value 255(0xff) means any.
				"
			::= { fkV2CpuPacketFilterControl 14 }

		
		-- 1.3.6.1.4.1.10428 9 1.102.7.2.8.3.15
		fkV2CpuPacketFilterControlActionVid OBJECT-TYPE
			SYNTAX Integer32 (0 | 1..4094 | 65535)
			MAX-ACCESS read-write
			STATUS current
			DESCRIPTION
				"The Action VID
				The value 65535(0xffff) means any.
				"
			::= { fkV2CpuPacketFilterControl 15 }

		
		-- 1.3.6.1.4.1.10428 9 1.102.7.2.8.3.16
		fkV2CpuPacketFilterControlActionTagPosition OBJECT-TYPE
			SYNTAX Integer32 (0 | 1..8)
			MAX-ACCESS read-write
			STATUS current
			DESCRIPTION
				"The Action tag position.
				1: S-vlan
				2: C-vlan
				M2200 uses only 1 and 2.
				"
			::= { fkV2CpuPacketFilterControl 16 }

		
		-- 1.3.6.1.4.1.10428 9 1.102.7.2.8.3.17
		fkV2CpuPacketFilterControlMatchType OBJECT-TYPE
			SYNTAX BITS
				{
				vid(0),
				cos(1),
				port(2),
				offset(3),
				dot1q(4)
				}
			MAX-ACCESS read-write
			STATUS current
			DESCRIPTION
				"The  match classifiter type."
			::= { fkV2CpuPacketFilterControl 17 }

		
		-- 1.3.6.1.4.1.10428 9 1.102.7.2.8.3.18
		fkV2CpuPacketFilterControlMatchCos OBJECT-TYPE
			SYNTAX OCTET STRING
			MAX-ACCESS read-write
			STATUS current
			DESCRIPTION
				"The matched CoS Queue.   
				M2200 doesn't  use
				"
			::= { fkV2CpuPacketFilterControl 18 }

		
		-- 1.3.6.1.4.1.10428 9 1.102.7.2.8.3.19
		fkV2CpuPacketFilterControlMatchPort OBJECT-TYPE
			SYNTAX OCTET STRING
			MAX-ACCESS read-write
			STATUS current
			DESCRIPTION
				"The matched port index."
			::= { fkV2CpuPacketFilterControl 19 }

		
		-- 1.3.6.1.4.1.10428 9 1.102.7.2.8.3.20
		fkV2CpuPacketFilterControlMatchVidmap OBJECT-TYPE
			SYNTAX OCTET STRING
			MAX-ACCESS read-write
			STATUS current
			DESCRIPTION
				"The matched VID
				M2200 doesn't  use
				"
			::= { fkV2CpuPacketFilterControl 20 }

		
		-- 1.3.6.1.4.1.10428 9 1.102.7.2.8.3.21
		fkV2CpuPacketFilterControlMatchTagPosition OBJECT-TYPE
			SYNTAX Integer32 (0 | 1..8)
			MAX-ACCESS read-write
			STATUS current
			DESCRIPTION
				"The matched tag position
				M2200 doesn't use
				"
			::= { fkV2CpuPacketFilterControl 21 }

		
		-- 1.3.6.1.4.1.10428 9 1.102.7.2.8.3.22
		fkV2CpuPacketFilterControlMatchTpid OBJECT-TYPE
			SYNTAX Integer32 (0..65535)
			MAX-ACCESS read-write
			STATUS current
			DESCRIPTION
				"The matched TPID."
			::= { fkV2CpuPacketFilterControl 22 }

		
		-- 1.3.6.1.4.1.10428 9 1.102.7.2.8.3.23
		fkV2CpuPacketFilterControlMatchPcp OBJECT-TYPE
			SYNTAX Integer32 (0..7 | 255)
			MAX-ACCESS read-write
			STATUS current
			DESCRIPTION
				"The matched PCP"
			::= { fkV2CpuPacketFilterControl 23 }

		
		-- 1.3.6.1.4.1.10428 9 1.102.7.2.8.3.24
		fkV2CpuPacketFilterControlMatchVid OBJECT-TYPE
			SYNTAX Integer32 (0 | 1..4094 | 65535)
			MAX-ACCESS read-write
			STATUS current
			DESCRIPTION
				"The matched VID"
			::= { fkV2CpuPacketFilterControl 24 }

		
		-- 1.3.6.1.4.1.10428 9 1.102.7.2.8.3.25
		fkV2CpuPacketFilterControlMatchOffset OBJECT-TYPE
			SYNTAX Integer32 (0..127)
			MAX-ACCESS read-write
			STATUS current
			DESCRIPTION
				"The matched offset"
			::= { fkV2CpuPacketFilterControl 25 }

		
		-- 1.3.6.1.4.1.10428 9 1.102.7.2.8.3.26
		fkV2CpuPacketFilterControlMatchLength OBJECT-TYPE
			SYNTAX Integer32 (1..16)
			MAX-ACCESS read-write
			STATUS current
			DESCRIPTION
				"The matched Length"
			::= { fkV2CpuPacketFilterControl 26 }

		
		-- 1.3.6.1.4.1.10428 9 1.102.7.2.8.3.27
		fkV2CpuPacketFilterControlMatchData OBJECT-TYPE
			SYNTAX OCTET STRING
			MAX-ACCESS read-write
			STATUS current
			DESCRIPTION
				"he matched data. (HEX string)"
			::= { fkV2CpuPacketFilterControl 27 }

		
		-- 1.3.6.1.4.1.10428 9 1.102.7.2.8.3.28
		fkV2CpuPacketFilterControlMatchMask OBJECT-TYPE
			SYNTAX OCTET STRING
			MAX-ACCESS read-write
			STATUS current
			DESCRIPTION
				"The matched mask. (HEX string)"
			::= { fkV2CpuPacketFilterControl 28 }

		
		-- 1.3.6.1.4.1.10428 9 1.102.7.2.8.3.29
		fkV2CpuPacketFilterControlMatchDesc OBJECT-TYPE
			SYNTAX OCTET STRING
			MAX-ACCESS read-write
			STATUS current
			DESCRIPTION
				"The matched Description"
			::= { fkV2CpuPacketFilterControl 29 }

		
		-- 1.3.6.1.4.1.10428 9 1.102.7.2.8.4
		fkV2CpuPacketFilterNotification OBJECT IDENTIFIER ::= { fkV2CpuPacketFilter 4 }

		
		-- 1.3.6.1.4.1.10428 9 1.102.7.2.8.4.1
		fkV2CpuPacketFilterAdded NOTIFICATION-TYPE
			OBJECTS { fkV2CpuPacketFilterControlRequest, fkV2CpuPacketFilterControlName, fkV2CpuPacketFilterControlStage, fkV2CpuPacketFilterControlPriority, fkV2CpuPacketFilterControlAction, 
				fkV2CpuPacketFilterControlActionRateLimit, fkV2CpuPacketFilterControlActionBurstSize, fkV2CpuPacketFilterControlActionTpid, fkV2CpuPacketFilterControlActionPcp, fkV2CpuPacketFilterControlActionVid, 
				fkV2CpuPacketFilterControlActionTagPosition, fkV2CpuPacketFilterControlMatchType, fkV2CpuPacketFilterControlMatchCos, fkV2CpuPacketFilterControlMatchPort, fkV2CpuPacketFilterControlMatchVid, 
				fkV2CpuPacketFilterControlMatchTagPosition, fkV2CpuPacketFilterControlMatchOffset, fkV2CpuPacketFilterControlMatchLength, fkV2CpuPacketFilterControlMatchData, fkV2CpuPacketFilterControlMatchMask, 
				fkV2CpuPacketFilterControlStatus, fkV2CpuPacketFilterControlTimer, fkV2CpuPacketFilterControlMatchVidmap, fkV2CpuPacketFilterControlMatchTpid, fkV2CpuPacketFilterControlMatchPcp, 
				fkV2CpuPacketFilterControlMatchDesc, fkV2CpuPacketFilterControlTimeStamp, fkV2CpuPacketFilterControlReqResult }
			STATUS current
			DESCRIPTION 
				"Description."
			::= { fkV2CpuPacketFilterNotification 1 }

		
		-- 1.3.6.1.4.1.10428 9 1.102.7.2.8.4.2
		fkV2CpuPacketFilterDeleted NOTIFICATION-TYPE
			OBJECTS { fkV2CpuPacketFilterControlRequest, fkV2CpuPacketFilterControlTimeStamp, fkV2CpuPacketFilterControlReqResult, fkV2CpuPacketFilterControlIndex }
			STATUS current
			DESCRIPTION 
				"Description."
			::= { fkV2CpuPacketFilterNotification 2 }

		
		-- 1.3.6.1.4.1.10428 9 1.102.7.2.8.4.3
		fkV2CpuPacketFilterActionChanged NOTIFICATION-TYPE
			OBJECTS { fkV2CpuPacketFilterControlRequest, fkV2CpuPacketFilterControlTimeStamp, fkV2CpuPacketFilterControlReqResult, fkV2CpuPacketFilterControlIndex, fkV2CpuPacketFilterControlAction, 
				fkV2CpuPacketFilterControlActionRateLimit, fkV2CpuPacketFilterControlActionBurstSize, fkV2CpuPacketFilterControlActionTpid, fkV2CpuPacketFilterControlActionPcp, fkV2CpuPacketFilterControlActionVid, 
				fkV2CpuPacketFilterControlActionTagPosition, fkV2CpuPacketFilterControlMatchType }
			STATUS current
			DESCRIPTION 
				"Description."
			::= { fkV2CpuPacketFilterNotification 3 }

		
		-- 1.3.6.1.4.1.10428 9 1.102.7.2.8.4.4
		fkV2CpuPacketFilterMatchChanged NOTIFICATION-TYPE
			OBJECTS { fkV2CpuPacketFilterControlRequest, fkV2CpuPacketFilterControlTimeStamp, fkV2CpuPacketFilterControlReqResult, fkV2CpuPacketFilterControlIndex, fkV2CpuPacketFilterControlMatchType, 
				fkV2CpuPacketFilterControlMatchCos, fkV2CpuPacketFilterControlMatchPort, fkV2CpuPacketFilterControlMatchVidmap, fkV2CpuPacketFilterControlMatchTagPosition, fkV2CpuPacketFilterControlMatchTpid, 
				fkV2CpuPacketFilterControlMatchPcp, fkV2CpuPacketFilterControlMatchVid, fkV2CpuPacketFilterControlMatchOffset, fkV2CpuPacketFilterControlMatchLength, fkV2CpuPacketFilterControlMatchData, 
				fkV2CpuPacketFilterControlMatchMask, fkV2CpuPacketFilterControlMatchDesc }
			STATUS current
			DESCRIPTION 
				"Description."
			::= { fkV2CpuPacketFilterNotification 4 }

		
		-- 1.3.6.1.4.1.10428 9 1.102.7.2.9
		fkV2VlanOperation OBJECT IDENTIFIER ::= { fkVSecurity4 9 }

		
		-- 1.3.6.1.4.1.10428 9 1.102.7.2.9.1
		fkV2VlanOperationTable OBJECT-TYPE
			SYNTAX SEQUENCE OF FkV2VlanOperationEntry
			MAX-ACCESS not-accessible
			STATUS current
			DESCRIPTION
				"Description."
			::= { fkV2VlanOperation 1 }

		
		-- 1.3.6.1.4.1.10428 9 1.102.7.2.9.1.1
		fkV2VlanOperationEntry OBJECT-TYPE
			SYNTAX FkV2VlanOperationEntry
			MAX-ACCESS not-accessible
			STATUS current
			DESCRIPTION
				"Description."
			INDEX { fkV2VlanOperationIndex, fkV2VlanOperationName }
			::= { fkV2VlanOperationTable 1 }

		
		FkV2VlanOperationEntry ::=
			SEQUENCE { 
				fkV2VlanOperationIndex
					Integer32,
				fkV2VlanOperationName
					OCTET STRING,
				fkV2VlanOperationStage
					INTEGER,
				fkV2VlanOperationProiroty
					Integer32,
				fkV2VlanOperationPort
					OCTET STRING,
				fkV2VlanOperationOuterVlan
					OCTET STRING,
				fkV2VlanOperationInnerVlan
					OCTET STRING,
				fkV2VlanOperationEtherType
					Integer32,
				fkV2VlanOperationIpProtocol
					Integer32,
				fkV2VlanOperationArpSip
					OCTET STRING,
				fkV2VlanOperationArpSipPfxLen
					Integer32,
				fkV2VlanOperationSip
					OCTET STRING,
				fkV2VlanOperationSipPfxLen
					Integer32,
				fkV2VlanOperationDip
					OCTET STRING,
				fkV2VlanOperationDipPfxLen
					Integer32,
				fkV2VlanOperationAction
					INTEGER,
				fkV2VlanOperationActionVid
					Integer32
			 }

		-- 1.3.6.1.4.1.10428 9 1.102.7.2.9.1.1.1
		fkV2VlanOperationIndex OBJECT-TYPE
			SYNTAX Integer32 (1..65565)
			MAX-ACCESS read-only
			STATUS current
			DESCRIPTION
				"The vlan operation index."
			::= { fkV2VlanOperationEntry 1 }

		
		-- 1.3.6.1.4.1.10428 9 1.102.7.2.9.1.1.2
		fkV2VlanOperationName OBJECT-TYPE
			SYNTAX OCTET STRING
			MAX-ACCESS read-only
			STATUS current
			DESCRIPTION
				"The vlan operation name"
			::= { fkV2VlanOperationEntry 2 }

		
		-- 1.3.6.1.4.1.10428 9 1.102.7.2.9.1.1.3
		fkV2VlanOperationStage OBJECT-TYPE
			SYNTAX INTEGER
				{
				ingressSlowPath(1),
				egressSlowPath(2)
				}
			MAX-ACCESS read-only
			STATUS current
			DESCRIPTION
				"The vlan operation stage."
			::= { fkV2VlanOperationEntry 3 }

		
		-- 1.3.6.1.4.1.10428 9 1.102.7.2.9.1.1.4
		fkV2VlanOperationProiroty OBJECT-TYPE
			SYNTAX Integer32 (1..65535)
			MAX-ACCESS read-only
			STATUS current
			DESCRIPTION
				"The vlan operation priority."
			::= { fkV2VlanOperationEntry 4 }

		
		-- 1.3.6.1.4.1.10428 9 1.102.7.2.9.1.1.5
		fkV2VlanOperationPort OBJECT-TYPE
			SYNTAX OCTET STRING
			MAX-ACCESS read-only
			STATUS current
			DESCRIPTION
				"The vlan operation ports"
			::= { fkV2VlanOperationEntry 5 }

		
		-- 1.3.6.1.4.1.10428 9 1.102.7.2.9.1.1.6
		fkV2VlanOperationOuterVlan OBJECT-TYPE
			SYNTAX OCTET STRING
			MAX-ACCESS read-only
			STATUS current
			DESCRIPTION
				"The Outer vlan."
			::= { fkV2VlanOperationEntry 6 }

		
		-- 1.3.6.1.4.1.10428 9 1.102.7.2.9.1.1.7
		fkV2VlanOperationInnerVlan OBJECT-TYPE
			SYNTAX OCTET STRING
			MAX-ACCESS read-only
			STATUS current
			DESCRIPTION
				"The inner Vlan."
			::= { fkV2VlanOperationEntry 7 }

		
		-- 1.3.6.1.4.1.10428 9 1.102.7.2.9.1.1.8
		fkV2VlanOperationEtherType OBJECT-TYPE
			SYNTAX Integer32
			MAX-ACCESS read-only
			STATUS current
			DESCRIPTION
				"The vlan operation ether-type."
			::= { fkV2VlanOperationEntry 8 }

		
		-- 1.3.6.1.4.1.10428 9 1.102.7.2.9.1.1.9
		fkV2VlanOperationIpProtocol OBJECT-TYPE
			SYNTAX Integer32
			MAX-ACCESS read-only
			STATUS current
			DESCRIPTION
				"The vlan operation IP Protocol"
			::= { fkV2VlanOperationEntry 9 }

		
		-- 1.3.6.1.4.1.10428 9 1.102.7.2.9.1.1.10
		fkV2VlanOperationArpSip OBJECT-TYPE
			SYNTAX OCTET STRING
			MAX-ACCESS read-only
			STATUS current
			DESCRIPTION
				"The vlan operation source-IPaddress."
			::= { fkV2VlanOperationEntry 10 }

		
		-- 1.3.6.1.4.1.10428 9 1.102.7.2.9.1.1.11
		fkV2VlanOperationArpSipPfxLen OBJECT-TYPE
			SYNTAX Integer32
			MAX-ACCESS read-only
			STATUS current
			DESCRIPTION
				"The vlan operation source-IPAddress prefix-length."
			::= { fkV2VlanOperationEntry 11 }

		
		-- 1.3.6.1.4.1.10428 9 1.102.7.2.9.1.1.12
		fkV2VlanOperationSip OBJECT-TYPE
			SYNTAX OCTET STRING
			MAX-ACCESS read-only
			STATUS current
			DESCRIPTION
				"The vlan operation Source-IPaddress."
			::= { fkV2VlanOperationEntry 12 }

		
		-- 1.3.6.1.4.1.10428 9 1.102.7.2.9.1.1.13
		fkV2VlanOperationSipPfxLen OBJECT-TYPE
			SYNTAX Integer32
			MAX-ACCESS read-only
			STATUS current
			DESCRIPTION
				"The vlan operation Source-IPAddress prefix-length."
			::= { fkV2VlanOperationEntry 13 }

		
		-- 1.3.6.1.4.1.10428 9 1.102.7.2.9.1.1.14
		fkV2VlanOperationDip OBJECT-TYPE
			SYNTAX OCTET STRING
			MAX-ACCESS read-only
			STATUS current
			DESCRIPTION
				"The vlan operation Destination-IPaddress."
			::= { fkV2VlanOperationEntry 14 }

		
		-- 1.3.6.1.4.1.10428 9 1.102.7.2.9.1.1.15
		fkV2VlanOperationDipPfxLen OBJECT-TYPE
			SYNTAX Integer32
			MAX-ACCESS read-only
			STATUS current
			DESCRIPTION
				"The vlan operation Destination-IPAddress prefix-length."
			::= { fkV2VlanOperationEntry 15 }

		
		-- 1.3.6.1.4.1.10428 9 1.102.7.2.9.1.1.16
		fkV2VlanOperationAction OBJECT-TYPE
			SYNTAX INTEGER
				{
				addServiceVlanTag(1),
				replaceServiceVlanID(2),
				removeServiceVlanTag(3),
				addCustomerVlanTag(4),
				replaceCustomerVlanID(5),
				removeCustomerVlanTag(6)
				}
			MAX-ACCESS read-only
			STATUS current
			DESCRIPTION
				"The vlan-operation action types."
			::= { fkV2VlanOperationEntry 16 }

		
		-- 1.3.6.1.4.1.10428 9 1.102.7.2.9.1.1.17
		fkV2VlanOperationActionVid OBJECT-TYPE
			SYNTAX Integer32 (1..4095)
			MAX-ACCESS read-only
			STATUS current
			DESCRIPTION
				"The vlan operation action-vid."
			::= { fkV2VlanOperationEntry 17 }

		
		-- 1.3.6.1.4.1.10428 9 1.102.7.2.9.2
		fkV2VlanOperationControl OBJECT IDENTIFIER ::= { fkV2VlanOperation 2 }

		
		-- 1.3.6.1.4.1.10428 9 1.102.7.2.9.2.1
		fkV2VlanOperationControlRequest OBJECT-TYPE
			SYNTAX INTEGER
				{
				addVlanOperation(1),
				delVlanOperation(2)
				}
			MAX-ACCESS read-write
			STATUS current
			DESCRIPTION
				"The request of a user command"
			::= { fkV2VlanOperationControl 1 }

		
		-- 1.3.6.1.4.1.10428 9 1.102.7.2.9.2.2
		fkV2VlanOperationControlStatus OBJECT-TYPE
			SYNTAX FkControlStatusType
			MAX-ACCESS read-only
			STATUS current
			DESCRIPTION
				"The status of user command"
			::= { fkV2VlanOperationControl 2 }

		
		-- 1.3.6.1.4.1.10428 9 1.102.7.2.9.2.3
		fkV2VlanOperationControlTimer OBJECT-TYPE
			SYNTAX Gauge32
			MAX-ACCESS read-write
			STATUS current
			DESCRIPTION
				"The maximum time for the manager for a long running user command"
			::= { fkV2VlanOperationControl 3 }

		
		-- 1.3.6.1.4.1.10428 9 1.102.7.2.9.2.4
		fkV2VlanOperationControlTimeStamp OBJECT-TYPE
			SYNTAX TimeTicks
			MAX-ACCESS read-only
			STATUS current
			DESCRIPTION
				"The time stamp of the last command(end of command)"
			::= { fkV2VlanOperationControl 4 }

		
		-- 1.3.6.1.4.1.10428 9 1.102.7.2.9.2.5
		fkV2VlanOperationControlReqResult OBJECT-TYPE
			SYNTAX FkControlRequestResultType
			MAX-ACCESS read-only
			STATUS current
			DESCRIPTION
				"The result of the last user command"
			::= { fkV2VlanOperationControl 5 }

		
		-- 1.3.6.1.4.1.10428 9 1.102.7.2.9.2.6
		fkV2VlanOperationControlIndex OBJECT-TYPE
			SYNTAX Integer32 (1..65535)
			MAX-ACCESS read-write
			STATUS current
			DESCRIPTION
				"The vlan operation index."
			::= { fkV2VlanOperationControl 6 }

		
		-- 1.3.6.1.4.1.10428 9 1.102.7.2.9.2.7
		fkV2VlanOperationControlName OBJECT-TYPE
			SYNTAX OCTET STRING
			MAX-ACCESS read-write
			STATUS current
			DESCRIPTION
				"The vlan operation name"
			::= { fkV2VlanOperationControl 7 }

		
		-- 1.3.6.1.4.1.10428 9 1.102.7.2.9.2.8
		fkV2VlanOperationControlStage OBJECT-TYPE
			SYNTAX INTEGER
				{
				ingressSlowPath(1),
				egressSlowPath(2)
				}
			MAX-ACCESS read-write
			STATUS current
			DESCRIPTION
				"The vlan operation stage."
			::= { fkV2VlanOperationControl 8 }

		
		-- 1.3.6.1.4.1.10428 9 1.102.7.2.9.2.9
		fkV2VlanOperationControlProiroty OBJECT-TYPE
			SYNTAX Integer32 (1..65535)
			MAX-ACCESS read-write
			STATUS current
			DESCRIPTION
				"The vlan operation priority."
			::= { fkV2VlanOperationControl 9 }

		
		-- 1.3.6.1.4.1.10428 9 1.102.7.2.9.2.10
		fkV2VlanOperationControlPort OBJECT-TYPE
			SYNTAX OCTET STRING
			MAX-ACCESS read-write
			STATUS current
			DESCRIPTION
				"The vlan operation ports"
			::= { fkV2VlanOperationControl 10 }

		
		-- 1.3.6.1.4.1.10428 9 1.102.7.2.9.2.11
		fkV2VlanOperationControlOuterVlan OBJECT-TYPE
			SYNTAX OCTET STRING
			MAX-ACCESS read-write
			STATUS current
			DESCRIPTION
				"The Outer vlan."
			::= { fkV2VlanOperationControl 11 }

		
		-- 1.3.6.1.4.1.10428 9 1.102.7.2.9.2.12
		fkV2VlanOperationControlInnerVlan OBJECT-TYPE
			SYNTAX OCTET STRING
			MAX-ACCESS read-write
			STATUS current
			DESCRIPTION
				"The Inner vlan."
			::= { fkV2VlanOperationControl 12 }

		
		-- 1.3.6.1.4.1.10428 9 1.102.7.2.9.2.13
		fkV2VlanOperationControlEtherType OBJECT-TYPE
			SYNTAX Integer32
			MAX-ACCESS read-write
			STATUS current
			DESCRIPTION
				"The vlan operation ether-type."
			::= { fkV2VlanOperationControl 13 }

		
		-- 1.3.6.1.4.1.10428 9 1.102.7.2.9.2.14
		fkV2VlanOperationControlIpProtocol OBJECT-TYPE
			SYNTAX Integer32
			MAX-ACCESS read-write
			STATUS current
			DESCRIPTION
				"The vlan operation IP Protocol"
			::= { fkV2VlanOperationControl 14 }

		
		-- 1.3.6.1.4.1.10428 9 1.102.7.2.9.2.15
		fkV2VlanOperationControlArpSip OBJECT-TYPE
			SYNTAX OCTET STRING
			MAX-ACCESS read-write
			STATUS current
			DESCRIPTION
				"The vlan operation source-IPaddress."
			::= { fkV2VlanOperationControl 15 }

		
		-- 1.3.6.1.4.1.10428 9 1.102.7.2.9.2.16
		fkV2VlanOperationControlArpSipPfxLen OBJECT-TYPE
			SYNTAX Integer32
			MAX-ACCESS read-write
			STATUS current
			DESCRIPTION
				"The vlan operation source-IPAddress prefix-length."
			::= { fkV2VlanOperationControl 16 }

		
		-- 1.3.6.1.4.1.10428 9 1.102.7.2.9.2.17
		fkV2VlanOperationControlSip OBJECT-TYPE
			SYNTAX OCTET STRING
			MAX-ACCESS read-write
			STATUS current
			DESCRIPTION
				"The vlan operation Source-IPaddress."
			::= { fkV2VlanOperationControl 17 }

		
		-- 1.3.6.1.4.1.10428 9 1.102.7.2.9.2.18
		fkV2VlanOperationControlSipPfxLen OBJECT-TYPE
			SYNTAX Integer32
			MAX-ACCESS read-write
			STATUS current
			DESCRIPTION
				"The vlan operation Source-IPAddress prefix-length."
			::= { fkV2VlanOperationControl 18 }

		
		-- 1.3.6.1.4.1.10428 9 1.102.7.2.9.2.19
		fkV2VlanOperationControlDip OBJECT-TYPE
			SYNTAX OCTET STRING
			MAX-ACCESS read-write
			STATUS current
			DESCRIPTION
				"The vlan operation Destination-IPaddress."
			::= { fkV2VlanOperationControl 19 }

		
		-- 1.3.6.1.4.1.10428 9 1.102.7.2.9.2.20
		fkV2VlanOperationControlDipPfxLen OBJECT-TYPE
			SYNTAX Integer32
			MAX-ACCESS read-write
			STATUS current
			DESCRIPTION
				"The vlan operation Destination-IPAddress prefix-length."
			::= { fkV2VlanOperationControl 20 }

		
		-- 1.3.6.1.4.1.10428 9 1.102.7.2.9.2.21
		fkV2VlanOperationControlAction OBJECT-TYPE
			SYNTAX INTEGER
				{
				addServiceVlanTag(1),
				replaceServiceVlanID(2),
				removeServiceVlanTag(3),
				addCustomerVlanTag(4),
				replaceCustomerVlanID(5),
				removeCustomerVlanTag(6)
				}
			MAX-ACCESS read-write
			STATUS current
			DESCRIPTION
				"The vlan-operation action types."
			::= { fkV2VlanOperationControl 21 }

		
		-- 1.3.6.1.4.1.10428 9 1.102.7.2.9.2.22
		fkV2VlanOperationControlActionVid OBJECT-TYPE
			SYNTAX Integer32 (1..4095)
			MAX-ACCESS read-write
			STATUS current
			DESCRIPTION
				"The vlan operation action-vid."
			::= { fkV2VlanOperationControl 22 }

		
		-- 1.3.6.1.4.1.10428 9 1.102.7.2.9.3
		fkV2VlanOperationNotification OBJECT IDENTIFIER ::= { fkV2VlanOperation 3 }

		
		-- 1.3.6.1.4.1.10428 9 1.102.7.2.9.3.1
		fkV2VlanOperationCreated NOTIFICATION-TYPE
			OBJECTS { fkV2VlanOperationControlRequest, fkV2VlanOperationControlTimeStamp, fkV2VlanOperationControlReqResult, fkV2VlanOperationControlName, fkV2VlanOperationControlStage, 
				fkV2VlanOperationControlProiroty, fkV2VlanOperationControlPort, fkV2VlanOperationControlOuterVlan, fkV2VlanOperationControlInnerVlan, fkV2VlanOperationControlEtherType, 
				fkV2VlanOperationControlIpProtocol, fkV2VlanOperationControlArpSip, fkV2VlanOperationControlArpSipPfxLen, fkV2VlanOperationControlSip, fkV2VlanOperationControlSipPfxLen, 
				fkV2VlanOperationControlDip, fkV2VlanOperationControlDipPfxLen, fkV2VlanOperationControlAction, fkV2VlanOperationControlActionVid }
			STATUS current
			DESCRIPTION 
				"addVlanOperation"
			::= { fkV2VlanOperationNotification 1 }

		
		-- 1.3.6.1.4.1.10428 9 1.102.7.2.9.3.2
		fkV2VlanOperationDeleted NOTIFICATION-TYPE
			OBJECTS { fkV2VlanOperationControlRequest, fkV2VlanOperationControlTimeStamp, fkV2VlanOperationControlReqResult, fkV2VlanOperationControlName }
			STATUS current
			DESCRIPTION 
				"delVlanOperation"
			::= { fkV2VlanOperationNotification 2 }

		
		-- 1.3.6.1.4.1.10428 9 1.102.7.2.10
		fkV2EthernetService OBJECT IDENTIFIER ::= { fkVSecurity4 10 }

		
		-- 1.3.6.1.4.1.10428 9 1.102.7.2.10.1
		fkV2EthernetServiceBase OBJECT IDENTIFIER ::= { fkV2EthernetService 1 }

		
		-- 1.3.6.1.4.1.10428 9 1.102.7.2.10.1.1
		fkV2EthernetServiceEnableStatus OBJECT-TYPE
			SYNTAX INTEGER
				{
				none(0),
				rt(1),
				cot(2)
				}
			MAX-ACCESS read-only
			STATUS current
			DESCRIPTION
				"The ethernet service mode status."
			::= { fkV2EthernetServiceBase 1 }

		
		-- 1.3.6.1.4.1.10428 9 1.102.7.2.10.1.2
		fkV2EthernetServiceEnableManagement OBJECT-TYPE
			SYNTAX INTEGER
				{
				enable(1),
				disable(2)
				}
			MAX-ACCESS read-only
			STATUS current
			DESCRIPTION
				"The global management access status ( only in RT mode )"
			::= { fkV2EthernetServiceBase 2 }

		
		-- 1.3.6.1.4.1.10428 9 1.102.7.2.10.1.3
		fkV2EthernetServiceHealthCheckPort OBJECT-TYPE
			SYNTAX OCTET STRING
			MAX-ACCESS read-only
			STATUS current
			DESCRIPTION
				"The health check port of uplink. ( only in COT mode )"
			::= { fkV2EthernetServiceBase 3 }

		
		-- 1.3.6.1.4.1.10428 9 1.102.7.2.10.1.4
		fkV2EthernetServiceHealthCheckVid OBJECT-TYPE
			SYNTAX OCTET STRING
			MAX-ACCESS read-only
			STATUS current
			DESCRIPTION
				"The health check vid of uplink. ( only in COT mode )"
			::= { fkV2EthernetServiceBase 4 }

		
		-- 1.3.6.1.4.1.10428 9 1.102.7.2.10.2
		fkV2EthernetServiceTable OBJECT-TYPE
			SYNTAX SEQUENCE OF FkV2EthernetServiceEntry
			MAX-ACCESS not-accessible
			STATUS current
			DESCRIPTION
				"Description."
			::= { fkV2EthernetService 2 }

		
		-- 1.3.6.1.4.1.10428 9 1.102.7.2.10.2.1
		fkV2EthernetServiceEntry OBJECT-TYPE
			SYNTAX FkV2EthernetServiceEntry
			MAX-ACCESS not-accessible
			STATUS current
			DESCRIPTION
				"Description."
			INDEX { fkV2EthernetServiceSid }
			::= { fkV2EthernetServiceTable 1 }

		
		FkV2EthernetServiceEntry ::=
			SEQUENCE { 
				fkV2EthernetServiceSid
					INTEGER,
				fkV2EthernetServiceType
					INTEGER,
				fkV2EthernetServiceRtCustomerPort
					OCTET STRING,
				fkV2EthernetServiceRtCustomerVid
					OCTET STRING,
				fkV2EthernetServiceRtNetworkPort
					OCTET STRING,
				fkV2EthernetServiceRtNetworkVid
					OCTET STRING,
				fkV2EthernetServiceRtEnableManagement
					INTEGER,
				fkV2EthernetServiceCotExternalPort
					OCTET STRING,
				fkV2EthernetServiceCotExternalVid
					OCTET STRING,
				fkV2EthernetServiceCotInternalPort
					OCTET STRING,
				fkV2EthernetServiceCotInternalVid
					OCTET STRING
			 }

		-- 1.3.6.1.4.1.10428 9 1.102.7.2.10.2.1.1
		fkV2EthernetServiceSid OBJECT-TYPE
			SYNTAX INTEGER (1..65535)
			MAX-ACCESS read-only
			STATUS current
			DESCRIPTION
				"The unique number is given by service identifier."
			::= { fkV2EthernetServiceEntry 1 }

		
		-- 1.3.6.1.4.1.10428 9 1.102.7.2.10.2.1.2
		fkV2EthernetServiceType OBJECT-TYPE
			SYNTAX INTEGER
				{
				unicast(1),
				multicast(2)
				}
			MAX-ACCESS read-only
			STATUS current
			DESCRIPTION
				"The ethernet service type
				1: unicast
				2: multicast"
			::= { fkV2EthernetServiceEntry 2 }

		
		-- 1.3.6.1.4.1.10428 9 1.102.7.2.10.2.1.3
		fkV2EthernetServiceRtCustomerPort OBJECT-TYPE
			SYNTAX OCTET STRING
			MAX-ACCESS read-only
			STATUS current
			DESCRIPTION
				"The Configuring service's customer port for RT mode."
			::= { fkV2EthernetServiceEntry 3 }

		
		-- 1.3.6.1.4.1.10428 9 1.102.7.2.10.2.1.4
		fkV2EthernetServiceRtCustomerVid OBJECT-TYPE
			SYNTAX OCTET STRING
			MAX-ACCESS read-only
			STATUS current
			DESCRIPTION
				"The Configuring service's customer vid for RT mode."
			::= { fkV2EthernetServiceEntry 4 }

		
		-- 1.3.6.1.4.1.10428 9 1.102.7.2.10.2.1.5
		fkV2EthernetServiceRtNetworkPort OBJECT-TYPE
			SYNTAX OCTET STRING
			MAX-ACCESS read-only
			STATUS current
			DESCRIPTION
				"The Configuring service's network port for RT mode."
			::= { fkV2EthernetServiceEntry 5 }

		
		-- 1.3.6.1.4.1.10428 9 1.102.7.2.10.2.1.6
		fkV2EthernetServiceRtNetworkVid OBJECT-TYPE
			SYNTAX OCTET STRING
			MAX-ACCESS read-only
			STATUS current
			DESCRIPTION
				"The Configuring service's network vid for RT mode."
			::= { fkV2EthernetServiceEntry 6 }

		
		-- 1.3.6.1.4.1.10428 9 1.102.7.2.10.2.1.7
		fkV2EthernetServiceRtEnableManagement OBJECT-TYPE
			SYNTAX INTEGER
				{
				enable(1),
				disable(2)
				}
			MAX-ACCESS read-only
			STATUS current
			DESCRIPTION
				"Description."
			::= { fkV2EthernetServiceEntry 7 }

		
		-- 1.3.6.1.4.1.10428 9 1.102.7.2.10.2.1.8
		fkV2EthernetServiceCotExternalPort OBJECT-TYPE
			SYNTAX OCTET STRING
			MAX-ACCESS read-only
			STATUS current
			DESCRIPTION
				"The Configuring service's external port for COT mode."
			::= { fkV2EthernetServiceEntry 8 }

		
		-- 1.3.6.1.4.1.10428 9 1.102.7.2.10.2.1.9
		fkV2EthernetServiceCotExternalVid OBJECT-TYPE
			SYNTAX OCTET STRING
			MAX-ACCESS read-only
			STATUS current
			DESCRIPTION
				"The Configuring service's external vid for COT mode."
			::= { fkV2EthernetServiceEntry 9 }

		
		-- 1.3.6.1.4.1.10428 9 1.102.7.2.10.2.1.10
		fkV2EthernetServiceCotInternalPort OBJECT-TYPE
			SYNTAX OCTET STRING
			MAX-ACCESS read-only
			STATUS current
			DESCRIPTION
				"The Configuring service's internal port for COT mode."
			::= { fkV2EthernetServiceEntry 10 }

		
		-- 1.3.6.1.4.1.10428 9 1.102.7.2.10.2.1.11
		fkV2EthernetServiceCotInternalVid OBJECT-TYPE
			SYNTAX OCTET STRING
			MAX-ACCESS read-only
			STATUS current
			DESCRIPTION
				"The Configuring service's internal vid for COT mode."
			::= { fkV2EthernetServiceEntry 11 }

		
		-- 1.3.6.1.4.1.10428 9 1.102.7.2.10.3
		fkV2EthernetServiceControl OBJECT IDENTIFIER ::= { fkV2EthernetService 3 }

		
		-- 1.3.6.1.4.1.10428 9 1.102.7.2.10.3.1
		fkV2EthernetServiceControlRequest OBJECT-TYPE
			SYNTAX INTEGER
				{
				setEnableStatus(1),
				setEnableManagement(2),
				setHealthCheck(3),
				delHealthCheck(4),
				setSidForRT(5),
				setSidForCOT(6),
				delService(7)
				}
			MAX-ACCESS read-write
			STATUS current
			DESCRIPTION
				"The request of a user command"
			::= { fkV2EthernetServiceControl 1 }

		
		-- 1.3.6.1.4.1.10428 9 1.102.7.2.10.3.2
		fkV2EthernetServiceControlStatus OBJECT-TYPE
			SYNTAX FkControlStatusType
			MAX-ACCESS read-only
			STATUS current
			DESCRIPTION
				"The status of user command"
			::= { fkV2EthernetServiceControl 2 }

		
		-- 1.3.6.1.4.1.10428 9 1.102.7.2.10.3.3
		fkV2EthernetServiceControlTimer OBJECT-TYPE
			SYNTAX Gauge32
			MAX-ACCESS read-write
			STATUS current
			DESCRIPTION
				"The maximum time for the manager for a long running user command"
			::= { fkV2EthernetServiceControl 3 }

		
		-- 1.3.6.1.4.1.10428 9 1.102.7.2.10.3.4
		fkV2EthernetServiceControlTimeStamp OBJECT-TYPE
			SYNTAX TimeTicks
			MAX-ACCESS read-only
			STATUS current
			DESCRIPTION
				"The time stamp of the last command(end of command)"
			::= { fkV2EthernetServiceControl 4 }

		
		-- 1.3.6.1.4.1.10428 9 1.102.7.2.10.3.5
		fkV2EthernetServiceControlReqResult OBJECT-TYPE
			SYNTAX FkControlRequestResultType
			MAX-ACCESS read-only
			STATUS current
			DESCRIPTION
				"The result of the last user command"
			::= { fkV2EthernetServiceControl 5 }

		
		-- 1.3.6.1.4.1.10428 9 1.102.7.2.10.3.6
		fkV2EthernetServiceControlEnableStatus OBJECT-TYPE
			SYNTAX INTEGER
				{
				none(0),
				rt(1),
				cot(2)
				}
			MAX-ACCESS read-write
			STATUS current
			DESCRIPTION
				"The ethernet service mode status."
			::= { fkV2EthernetServiceControl 6 }

		
		-- 1.3.6.1.4.1.10428 9 1.102.7.2.10.3.7
		fkV2EthernetServiceControlEnableManagement OBJECT-TYPE
			SYNTAX INTEGER
				{
				enable(1),
				disable(2)
				}
			MAX-ACCESS read-write
			STATUS current
			DESCRIPTION
				"The local management access status ( only in RT mode )"
			::= { fkV2EthernetServiceControl 7 }

		
		-- 1.3.6.1.4.1.10428 9 1.102.7.2.10.3.8
		fkV2EthernetServiceControlHealthCheckPort OBJECT-TYPE
			SYNTAX OCTET STRING
			MAX-ACCESS read-write
			STATUS current
			DESCRIPTION
				"The health check port of uplink. ( only in COT mode )"
			::= { fkV2EthernetServiceControl 8 }

		
		-- 1.3.6.1.4.1.10428 9 1.102.7.2.10.3.9
		fkV2EthernetServiceControlHealthCheckVid OBJECT-TYPE
			SYNTAX OCTET STRING
			MAX-ACCESS read-write
			STATUS current
			DESCRIPTION
				"The health check vid of uplink. ( only in COT mode )"
			::= { fkV2EthernetServiceControl 9 }

		
		-- 1.3.6.1.4.1.10428 9 1.102.7.2.10.3.10
		fkV2EthernetServiceControlSid OBJECT-TYPE
			SYNTAX INTEGER (1..65535)
			MAX-ACCESS read-write
			STATUS current
			DESCRIPTION
				"The unique number is given by service identifier."
			::= { fkV2EthernetServiceControl 10 }

		
		-- 1.3.6.1.4.1.10428 9 1.102.7.2.10.3.11
		fkV2EthernetServiceControlType OBJECT-TYPE
			SYNTAX INTEGER
				{
				unicast(1),
				multicast(2)
				}
			MAX-ACCESS read-write
			STATUS current
			DESCRIPTION
				"The ethernet service type
				1: unicast
				2: multicast"
			::= { fkV2EthernetServiceControl 11 }

		
		-- 1.3.6.1.4.1.10428 9 1.102.7.2.10.3.12
		fkV2EthernetServiceControlRtCustomerPort OBJECT-TYPE
			SYNTAX OCTET STRING
			MAX-ACCESS read-write
			STATUS current
			DESCRIPTION
				"The Configuring service's customer port for RT mode."
			::= { fkV2EthernetServiceControl 12 }

		
		-- 1.3.6.1.4.1.10428 9 1.102.7.2.10.3.13
		fkV2EthernetServiceControlRtCustomerVid OBJECT-TYPE
			SYNTAX OCTET STRING
			MAX-ACCESS read-write
			STATUS current
			DESCRIPTION
				"The Configuring service's customer vid for RT mode."
			::= { fkV2EthernetServiceControl 13 }

		
		-- 1.3.6.1.4.1.10428 9 1.102.7.2.10.3.14
		fkV2EthernetServiceControlRtNetworkPort OBJECT-TYPE
			SYNTAX OCTET STRING
			MAX-ACCESS read-write
			STATUS current
			DESCRIPTION
				"The Configuring service's network port for RT mode."
			::= { fkV2EthernetServiceControl 14 }

		
		-- 1.3.6.1.4.1.10428 9 1.102.7.2.10.3.15
		fkV2EthernetServiceControlRtNetworkVid OBJECT-TYPE
			SYNTAX OCTET STRING
			MAX-ACCESS read-write
			STATUS current
			DESCRIPTION
				"The Configuring service's network vid for RT mode."
			::= { fkV2EthernetServiceControl 15 }

		
		-- 1.3.6.1.4.1.10428 9 1.102.7.2.10.3.16
		fkV2EthernetServiceControlRtEnableManagement OBJECT-TYPE
			SYNTAX INTEGER
				{
				enable(1),
				disable(2)
				}
			MAX-ACCESS read-write
			STATUS current
			DESCRIPTION
				"Description."
			::= { fkV2EthernetServiceControl 16 }

		
		-- 1.3.6.1.4.1.10428 9 1.102.7.2.10.3.17
		fkV2EthernetServiceControlCotExternalPort OBJECT-TYPE
			SYNTAX OCTET STRING
			MAX-ACCESS read-write
			STATUS current
			DESCRIPTION
				"The Configuring service's external port for COT mode."
			::= { fkV2EthernetServiceControl 17 }

		
		-- 1.3.6.1.4.1.10428 9 1.102.7.2.10.3.18
		fkV2EthernetServiceControlCotExternalVid OBJECT-TYPE
			SYNTAX OCTET STRING
			MAX-ACCESS read-write
			STATUS current
			DESCRIPTION
				"The Configuring service's external vid for COT mode."
			::= { fkV2EthernetServiceControl 18 }

		
		-- 1.3.6.1.4.1.10428 9 1.102.7.2.10.3.19
		fkV2EthernetServiceControlCotInternalPort OBJECT-TYPE
			SYNTAX OCTET STRING
			MAX-ACCESS read-write
			STATUS current
			DESCRIPTION
				"The Configuring service's internal port for COT mode."
			::= { fkV2EthernetServiceControl 19 }

		
		-- 1.3.6.1.4.1.10428 9 1.102.7.2.10.3.20
		fkV2EthernetServiceControlCotInternalVid OBJECT-TYPE
			SYNTAX OCTET STRING
			MAX-ACCESS read-write
			STATUS current
			DESCRIPTION
				"The Configuring service's internal vid for COT mode."
			::= { fkV2EthernetServiceControl 20 }

		
		-- 1.3.6.1.4.1.10428 9 1.102.7.2.10.4
		fkV2EthernetServiceNotification OBJECT IDENTIFIER ::= { fkV2EthernetService 4 }

		
		-- 1.3.6.1.4.1.10428 9 1.102.7.2.10.4.1
		fkV2EthernetServiceEnableStatusChanged NOTIFICATION-TYPE
			OBJECTS { fkV2EthernetServiceControlRequest, fkV2EthernetServiceControlTimeStamp, fkV2EthernetServiceControlReqResult, fkV2EthernetServiceControlEnableStatus }
			STATUS current
			DESCRIPTION 
				"setEnableStatus"
			::= { fkV2EthernetServiceNotification 1 }

		
		-- 1.3.6.1.4.1.10428 9 1.102.7.2.10.4.2
		fkV2EthernetServiceEnableManagementChanged NOTIFICATION-TYPE
			OBJECTS { fkV2EthernetServiceControlRequest, fkV2EthernetServiceControlTimeStamp, fkV2EthernetServiceControlReqResult, fkV2EthernetServiceControlEnableManagement }
			STATUS current
			DESCRIPTION 
				"setEnableManagement"
			::= { fkV2EthernetServiceNotification 2 }

		
		-- 1.3.6.1.4.1.10428 9 1.102.7.2.10.4.3
		fkV2EthernetServiceHealthCheckChanged NOTIFICATION-TYPE
			OBJECTS { fkV2EthernetServiceControlRequest, fkV2EthernetServiceControlTimeStamp, fkV2EthernetServiceControlReqResult, fkV2EthernetServiceControlHealthCheckPort, fkV2EthernetServiceControlHealthCheckVid
				 }
			STATUS current
			DESCRIPTION 
				"setHealthCheck"
			::= { fkV2EthernetServiceNotification 3 }

		
		-- 1.3.6.1.4.1.10428 9 1.102.7.2.10.4.4
		fkV2EthernetServiceHealthCheckDeleted NOTIFICATION-TYPE
			OBJECTS { fkV2EthernetServiceControlRequest, fkV2EthernetServiceControlTimeStamp, fkV2EthernetServiceControlReqResult }
			STATUS current
			DESCRIPTION 
				"delHealthCheck"
			::= { fkV2EthernetServiceNotification 4 }

		
		-- 1.3.6.1.4.1.10428 9 1.102.7.2.10.4.5
		fkV2EthernetServiceSidForRtModeCreated NOTIFICATION-TYPE
			OBJECTS { fkV2EthernetServiceControlRequest, fkV2EthernetServiceControlTimeStamp, fkV2EthernetServiceControlReqResult, fkV2EthernetServiceControlSid, fkV2EthernetServiceControlType, 
				fkV2EthernetServiceControlRtCustomerPort, fkV2EthernetServiceControlRtCustomerVid, fkV2EthernetServiceControlRtNetworkPort, fkV2EthernetServiceControlRtNetworkVid, fkV2EthernetServiceControlRtEnableManagement
				 }
			STATUS current
			DESCRIPTION 
				"setSidForRT"
			::= { fkV2EthernetServiceNotification 5 }

		
		-- 1.3.6.1.4.1.10428 9 1.102.7.2.10.4.6
		fkV2EthernetServiceSidForCotModeCreated NOTIFICATION-TYPE
			OBJECTS { fkV2EthernetServiceControlRequest, fkV2EthernetServiceControlTimeStamp, fkV2EthernetServiceControlReqResult, fkV2EthernetServiceControlSid, fkV2EthernetServiceControlType, 
				fkV2EthernetServiceControlCotExternalPort, fkV2EthernetServiceControlCotExternalVid, fkV2EthernetServiceControlCotInternalPort, fkV2EthernetServiceControlCotInternalVid }
			STATUS current
			DESCRIPTION 
				"setSidForCOT"
			::= { fkV2EthernetServiceNotification 6 }

		
		-- 1.3.6.1.4.1.10428 9 1.102.7.2.10.4.7
		fkV2EthernetServiceSidDeleted NOTIFICATION-TYPE
			OBJECTS { fkV2EthernetServiceControlRequest, fkV2EthernetServiceControlTimeStamp, fkV2EthernetServiceControlReqResult, fkV2EthernetServiceControlSid }
			STATUS current
			DESCRIPTION 
				"delService"
			::= { fkV2EthernetServiceNotification 7 }

		
		-- 1.3.6.1.4.1.10428 9 1.102.7.3
		fkV2Security6 OBJECT IDENTIFIER ::= { fkV2Security 3 }

		
		-- 1.3.6.1.4.1.10428 9 1.102.7.4
		fkV2SecurityGroup OBJECT-GROUP
			OBJECTS { fkV2Security4ACLFlowIndex, fkV2Security4ACLFlowName, fkV2Security4ACLFlowSrcIpAddr, fkV2Security4ACLFlowSrcIpAddrMask, fkV2Security4ACLFlowDstIpAddr, 
				fkV2Security4ACLFlowDstIpAddrMask, fkV2Security4ACLFlowProtocolType, fkV2Security4ACLFlowTcpSrcStartPort, fkV2Security4ACLFlowTcpSrcEndPort, fkV2Security4ACLFlowTcpDstStartPort, 
				fkV2Security4ACLFlowTcpDstEndPort, fkV2Security4ACLFlowTcpFlag, fkV2Security4ACLFlowUdpSrcStartPort, fkV2Security4ACLFlowUdpSrcEndPort, fkV2Security4ACLFlowUdpDstStartPort, 
				fkV2Security4ACLFlowUdpDstEndPort, fkV2Security4ACLFlowIcmpType, fkV2Security4ACLFlowIcmpCode, fkV2Security4ACLFlowControlTcpFlag, fkV2Security4ACLFlowClassIndex, 
				fkV2Security4ACLFlowClassID, fkV2Security4ACLFlowClassName, fkV2Security4ACLFlowPolicyIndex, fkV2Security4ACLFlowPolicyID, fkV2Security4ACLFlowPolicyName, 
				fkV2Security4ACLClassIndex, fkV2Security4ACLClassName, fkV2Security4ACLClassFlowCnt, fkV2Security4ACLClassFlowIndex, fkV2Security4ACLClassFlowID, 
				fkV2Security4ACLClassFlowName, fkV2Security4ACLClassPolicyIndex, fkV2Security4ACLClassPolicyID, fkV2Security4ACLClassPolicyName, fkV2Security4ACLPolicyIndex, 
				fkV2Security4ACLPolicyName, fkV2Security4ACLPolicyFlowCnt, fkV2Security4ACLPolicyClassCnt, fkV2Security4ACLPolicyPriority, fkV2Security4ACLPolicyMatchFlag, 
				fkV2Security4ACLPolicyNomatchFlag, fkV2Security4ACLPolicyFlowClassIndex, fkV2Security4ACLPolicyFlowClassType, fkV2Security4ACLPolicyFlowClassID, fkV2Security4ACLFlowControlRequest, 
				fkV2Security4ACLFlowControlStatus, fkV2Security4ACLFlowControlTimer, fkV2Security4ACLFlowControlTimeStamp, fkV2Security4ACLFlowControlReqResult, fkV2Security4ACLFlowControlIndex, 
				fkV2Security4ACLFlowControlName, fkV2Security4ACLFlowControlSrcIpAddr, fkV2Security4ACLFlowControlSrcIpAddrMask, fkV2Security4ACLFlowControlDstIpAddr, fkV2Security4ACLFlowControlDstIpAddrMask, 
				fkV2Security4ACLFlowControlProtocolType, fkV2Security4ACLFlowControlTcpSrcStartPort, fkV2Security4ACLFlowControlTcpSrcEndPort, fkV2Security4ACLFlowControlTcpDstStartPort, fkV2Security4ACLFlowControlTcpDstEndPort, 
				fkV2Security4ACLFlowControlUdpSrcStartPort, fkV2Security4ACLFlowControlUdpSrcEndPort, fkV2Security4ACLFlowControlUdpDstStartPort, fkV2Security4ACLFlowControlUdpDstEndPort, fkV2Security4ACLFlowControlIcmpType, 
				fkV2Security4ACLFlowControlIcmpCode, fkV2Security4ACLFlowControlHdrlen, fkV2Security4ACLClassControlRequest, fkV2Security4ACLClassControlStatus, fkV2Security4ACLClassControlTimer, 
				fkV2Security4ACLClassControlTimeStamp, fkV2Security4ACLClassControlReqResult, fkV2Security4ACLClassControlIndex, fkV2Security4ACLClassControlName, fkV2Security4ACLClassFlowControlRequest, 
				fkV2Security4ACLClassFlowControlStatus, fkV2Security4ACLClassFlowControlTimer, fkV2Security4ACLClassFlowControlTimeStamp, fkV2Security4ACLClassFlowControlReqResult, fkV2Security4ACLClassFlowControlClassIndex, 
				fkV2Security4ACLClassFlowControlFlowIndex, fkV2Security4ACLClassFlowControlFlowID, fkV2Security4ACLPolicyControlRequest, fkV2Security4ACLPolicyControlStatus, fkV2Security4ACLPolicyControlTimer, 
				fkV2Security4ACLPolicyControlTimeStamp, fkV2Security4ACLPolicyControlReqResult, fkV2Security4ACLPolicyControlIndex, fkV2Security4ACLPolicyControlName, fkV2Security4ACLPolicyControlPriority, 
				fkV2Security4ACLPolicyControlMatchFlag, fkV2Security4ACLPolicyControlNomatchFlag, fkV2Security4ACLPolicyFlowClassControlRequest, fkV2Security4ACLPolicyFlowClassControlStatus, fkV2Security4ACLPolicyFlowClassControlTimer, 
				fkV2Security4ACLPolicyFlowClassControlTimeStamp, fkV2Security4ACLPolicyFlowClassControlReqResult, fkV2Security4ACLPolicyFlowClassControlPolicyIndex, fkV2Security4ACLPolicyFlowClassControlIndex, fkV2Security4ACLPolicyFlowClassControlType, 
				fkV2Security4ACLPolicyFlowClassControlFlowID, fkV2Security4ACLPolicyFlowClassControlClassID, fkV2SecuritySACLName, fkV2SecuritySACLSrcIpaddr, fkV2SecuritySACLSrcPrefixLength, 
				fkV2SecuritySACLDstIpAddr, fkV2SecuritySACLDstPrefixLength, fkV2SecuritySACLProtocolType, fkV2SecuritySACLTcpflag, fkV2SecuritySACLIcmpType, 
				fkV2SecuritySACLIcmpCode, fkV2SecuritySACLPriority, fkV2SecuritySACLMatchAction, fkV2SecuritySACLNomatchAction, fkV2SecuritySACLControlRequest, 
				fkV2SecuritySACLControlStatus, fkV2SecuritySACLControlTimer, fkV2SecuritySACLControlTimeStamp, fkV2SecuritySACLControlReqResult, fkV2SecuritySACLControlName, 
				fkV2SecuritySACLControlSrcIpaddr, fkV2SecuritySACLControlSrcPrefixLength, fkV2SecuritySACLControlDstIpaddr, fkV2SecuritySACLControlDstPrefixLength, fkV2SecuritySACLControlProtocolType, 
				fkV2SecuritySACLControlTcpflag, fkV2SecuritySACLControlIcmpType, fkV2SecuritySACLControlIcmpCode, fkV2SecuritySACLControlPriority, fkV2SecuritySACLControlMatchAction, 
				fkV2SecuritySACLControlNomatchAction, fkV2Security4ACLPolicyFlowClassName, fkV2Security4ACLFlowHdrlen, fkV2SecuritySACLDstL4Port, fkV2SecuritySACLSrcL4Port, 
				fkV2SecuritySACLControlSrcL4Port, fkV2SecuritySACLControlDstL4Port, fkV2SecurityACLTotalPacket, fkV2SecurityACLSrcHistoryIpAddr, fkV2SecurityACLStatisticsControlRequest, 
				fkV2SecurityACLStatisticsControlStatus, fkV2SecurityACLStatisticsControlTimer, fkV2SecurityACLStatisticsControlTimeStamp, fkV2SecurityACLStatisticsControlReqResult, fkV2SecurityACLStatisticsBaseControlTimer, 
				fkV2SecurityACLStatisticsBaseControlStatus, fkV2SecurityACLStatisticsBaseControlRequest, fkV2SecurityACLStatisticsControlName, fkV2SecurityACLSrcHistoryIndex, fkV2SecurityACLStatisticsBaseControlTimeStamp, 
				fkV2SecurityACLStatisticsBaseControlReqResult, fkV2CpuPacketFilterIndex, fkV2CpuPacketFilterName, fkV2CpuPacketFilterCreationTime, fkV2CpuPacketFilterElapsedtimeAfterClear, 
				fkV2CpuPacketFilterStage, fkV2CpuPacketFilterPriority, fkV2CpuPacketFilterAction, fkV2CpuPacketFilterActionRateLimit, fkV2CpuPacketFilterActionBurstSize, 
				fkV2CpuPacketFilterActionTpid, fkV2CpuPacketFilterActionPcp, fkV2CpuPacketFilterActionVid, fkV2CpuPacketFilterActionTagPosition, fkV2CpuPacketFilterMatchType, 
				fkV2CpuPacketFilterMatchCos, fkV2CpuPacketFilterMatchPort, fkV2CpuPacketFilterMatchVid, fkV2CpuPacketFilterMatchTagPosition, fkV2CpuPacketFilterMatchOffset, 
				fkV2CpuPacketFilterMatchLength, fkV2CpuPacketFilterMatchData, fkV2CpuPacketFilterMatchMask, fkV2CpuPacketFilterMatchDesc, fkV2CpuPacketFilterControlRequest, 
				fkV2CpuPacketFilterControlStatus, fkV2CpuPacketFilterControlTimer, fkV2CpuPacketFilterControlTimeStamp, fkV2CpuPacketFilterControlReqResult, fkV2CpuPacketFilterControlIndex, 
				fkV2CpuPacketFilterControlName, fkV2CpuPacketFilterControlStage, fkV2CpuPacketFilterControlPriority, fkV2CpuPacketFilterControlAction, fkV2CpuPacketFilterControlActionRateLimit, 
				fkV2CpuPacketFilterControlActionBurstSize, fkV2CpuPacketFilterControlActionTpid, fkV2CpuPacketFilterControlActionPcp, fkV2CpuPacketFilterControlActionVid, fkV2CpuPacketFilterControlActionTagPosition, 
				fkV2CpuPacketFilterControlMatchType, fkV2CpuPacketFilterControlMatchCos, fkV2CpuPacketFilterControlMatchPort, fkV2CpuPacketFilterControlMatchVid, fkV2CpuPacketFilterControlMatchTagPosition, 
				fkV2CpuPacketFilterControlMatchOffset, fkV2CpuPacketFilterControlMatchLength, fkV2CpuPacketFilterControlMatchData, fkV2CpuPacketFilterControlMatchMask, fkV2CpuPacketFilterControlMatchDesc, 
				fkV2CpuPacketFilterMatchIndex, fkV2CpuPacketFilterMatchVidmap, fkV2CpuPacketFilterMatchTpid, fkV2CpuPacketFilterMatchPcp, fkV2CpuPacketFilterControlMatchVidmap, 
				fkV2CpuPacketFilterControlMatchTpid, fkV2CpuPacketFilterControlMatchPcp, fkV2Security4ACLFlowIpFlag, fkV2Security4ACLFlowControlIpFlag, fkV2VlanOperationIndex, 
				fkV2VlanOperationName, fkV2VlanOperationStage, fkV2VlanOperationPort, fkV2VlanOperationEtherType, fkV2VlanOperationIpProtocol, 
				fkV2VlanOperationArpSip, fkV2VlanOperationArpSipPfxLen, fkV2VlanOperationDip, fkV2VlanOperationDipPfxLen, fkV2VlanOperationAction, 
				fkV2VlanOperationActionVid, fkV2VlanOperationProiroty, fkV2VlanOperationControlIndex, fkV2VlanOperationControlName, fkV2VlanOperationControlStage, 
				fkV2VlanOperationControlProiroty, fkV2VlanOperationControlPort, fkV2VlanOperationControlEtherType, fkV2VlanOperationControlIpProtocol, fkV2VlanOperationControlArpSip, 
				fkV2VlanOperationControlArpSipPfxLen, fkV2VlanOperationControlDip, fkV2VlanOperationControlDipPfxLen, fkV2VlanOperationControlAction, fkV2VlanOperationControlActionVid, 
				fkV2VlanOperationSip, fkV2VlanOperationSipPfxLen, fkV2VlanOperationControlSip, fkV2VlanOperationControlSipPfxLen, fkV2VlanOperationOuterVlan, 
				fkV2VlanOperationInnerVlan, fkV2VlanOperationControlOuterVlan, fkV2VlanOperationControlInnerVlan, fkV2EthernetServiceEnableStatus, fkV2EthernetServiceEnableManagement, 
				fkV2EthernetServiceHealthCheckPort, fkV2EthernetServiceHealthCheckVid, fkV2EthernetServiceSid, fkV2EthernetServiceType, fkV2EthernetServiceRtCustomerPort, 
				fkV2EthernetServiceRtCustomerVid, fkV2EthernetServiceRtNetworkPort, fkV2EthernetServiceRtNetworkVid, fkV2EthernetServiceRtEnableManagement, fkV2EthernetServiceCotExternalPort, 
				fkV2EthernetServiceCotExternalVid, fkV2EthernetServiceCotInternalPort, fkV2EthernetServiceCotInternalVid, fkV2EthernetServiceControlRequest, fkV2EthernetServiceControlStatus, 
				fkV2EthernetServiceControlTimer, fkV2EthernetServiceControlTimeStamp, fkV2EthernetServiceControlReqResult, fkV2EthernetServiceControlEnableStatus, fkV2EthernetServiceControlEnableManagement, 
				fkV2EthernetServiceControlHealthCheckPort, fkV2EthernetServiceControlHealthCheckVid, fkV2EthernetServiceControlSid, fkV2EthernetServiceControlType, fkV2EthernetServiceControlRtCustomerPort, 
				fkV2EthernetServiceControlRtCustomerVid, fkV2EthernetServiceControlRtNetworkPort, fkV2EthernetServiceControlRtNetworkVid, fkV2EthernetServiceControlRtEnableManagement, fkV2EthernetServiceControlCotExternalPort, 
				fkV2EthernetServiceControlCotExternalVid, fkV2EthernetServiceControlCotInternalPort, fkV2EthernetServiceControlCotInternalVid, fkV2SecurityACLStatisticsBaseControlSyslogMode, fkV2SecurityACLStatisticsSyslogStatus, 
				fkV2VlanOperationControlRequest, fkV2VlanOperationControlStatus, fkV2VlanOperationControlTimer, fkV2VlanOperationControlTimeStamp, fkV2VlanOperationControlReqResult
				 }
			STATUS current
			DESCRIPTION 
				"Description."
			::= { fkV2Security 4 }

		
		-- 1.3.6.1.4.1.10428 9 1.102.7.5
		fkV2SecurityNotificationGroup NOTIFICATION-GROUP
			NOTIFICATIONS { fkACLFlowCreated, fkACLFlowChanged, fkACLFlowDestroyed, fkACLFlowAllDestroyed, fkACLClassCreated, 
				fkACLClassDestroyed, fkACLClassAllDestroyed, fkACLClassFlowAdded, fkACLClassFlowDeleted, fkACLClassFlowAllDeleted, 
				fkACLPolicyCreated, fkACLPolicyInfoChanged, fkACLPolicyMatchActionChanged, fkACLPolicyNomatchActionChanged, fkACLPolicyDestroyed, 
				fkACLPolicyFlowAdded, fkACLPolicyFlowDeleted, fkACLPolicyAllFlowDeleted, fkACLPolicyAllClassDeleted, fkACLPolicyAllFlowClassDeleted, 
				fkSACLCreated, fkSACLDestroyed, fkSACLAllDestroyed, fkV2SecurityACLStatisticsSyslogModeChanged, fkV2SecurityACLStatisticsCleared, 
				fkV2CpuPacketFilterAdded, fkV2CpuPacketFilterDeleted, fkV2CpuPacketFilterActionChanged, fkV2CpuPacketFilterMatchChanged, fkV2VlanOperationCreated, 
				fkV2VlanOperationDeleted, fkV2EthernetServiceEnableStatusChanged, fkV2EthernetServiceEnableManagementChanged, fkV2EthernetServiceHealthCheckChanged, fkV2EthernetServiceHealthCheckDeleted, 
				fkV2EthernetServiceSidForRtModeCreated, fkV2EthernetServiceSidForCotModeCreated, fkV2EthernetServiceSidDeleted }
			STATUS current
			DESCRIPTION 
				"Description."
			::= { fkV2Security 5 }

		
	
	END

--
-- fkv2-security-mib.mib
--
