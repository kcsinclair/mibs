--
-- FK-RED-MIB.my
-- MIB generated by MG-SOFT Visual MIB Builder Version 6.0  Build 88
-- Monday, December 21, 2009 at 16:16:11
--

        FK-RED-MIB DEFINITIONS ::= BEGIN
 
                IMPORTS
                        fkMgmt                  
                                FROM FKOLTG1040-SMI                     
                        FkControlStatusType, FkControlRequestResultType                 
                                FROM FK-TC-MIB                  
                        OBJECT-GROUP, NOTIFICATION-GROUP                        
                                FROM SNMPv2-CONF                        
                        TimeTicks, Gauge32, OBJECT-TYPE, MODULE-IDENTITY, NOTIFICATION-TYPE                     
                                FROM SNMPv2-SMI;
        
        
--  October 19, 2007 at 22:00 GMT
                -- 1.3.6.1.4.1.10428 9 1.101.22
                fkRed MODULE-IDENTITY 
                        LAST-UPDATED "200710192200Z"            -- October 19, 2007 at 22:00 GMT
                        ORGANIZATION 
                                "Furukawa Industrial S.A."
                        CONTACT-INFO 
                                "Furukawa Industrial S.A. Produtos Eletricos
        Rua Hasdrubal Bellegard, 820 - CIC
        CEP 81460-120 - Curitiba - Parana - Brasil
        CSC 0800-41-2100
        E-mail: fisa@furukawa.com.br"
                        DESCRIPTION 
                                "The MIB module for Furukawa GPON OLT FK-OLT-G1040."
                        ::= { fkMgmt 22 }

                
        
--
-- Type definitions
--
        
                FkRedBoardIdType ::= INTEGER
                        {
                        sfuA(1),
                        sfuB(2)
                        }

                FkRedModeType ::= INTEGER
                        {
                        redundant(1),
                        standalone(2)
                        }

                FkRedFaultActionType ::= INTEGER
                        {
                        switchover(1),
                        log(2),
                        disable(3)
                        }

                FkRedReloadOSType ::= INTEGER
                        {
                        os1(1),
                        os2(2),
                        default(3)
                        }

        
        
--
-- Node definitions
--
        
                -- 1.3.6.1.4.1.10428 9 1.101.22.1
                fkRedBase OBJECT IDENTIFIER ::= { fkRed 1 }

                
                -- 1.3.6.1.4.1.10428 9 1.101.22.1.1
                fkRedInfo OBJECT IDENTIFIER ::= { fkRedBase 1 }

                
                -- 1.3.6.1.4.1.10428 9 1.101.22.1.1.1
                fkRedActiveBoard OBJECT-TYPE
                        SYNTAX FkRedBoardIdType
                        MAX-ACCESS read-only
                        STATUS current
                        DESCRIPTION
                                "Indication of the actual service board identifier. 
                                Regardless of redundancy mode, it has actual service board id.
                                "
                        ::= { fkRedInfo 1 }

                
                -- 1.3.6.1.4.1.10428 9 1.101.22.1.1.2
                fkRedMode OBJECT-TYPE
                        SYNTAX FkRedModeType
                        MAX-ACCESS read-only
                        STATUS current
                        DESCRIPTION
                                "If two SFUs are installed in the system,
                                it works as redundant mode. Otherwise, it works as standalone mode.
                                "
                        ::= { fkRedInfo 2 }

                
                -- 1.3.6.1.4.1.10428 9 1.101.22.1.1.3
                fkRedFaultCrashAction OBJECT-TYPE
                        SYNTAX FkRedFaultActionType
                        MAX-ACCESS read-only
                        STATUS current
                        DESCRIPTION
                                "If any software module is crashed, the given action is taken.
                                For 'switchover' action, if the board is active and a standby board is available,
                                'switchover' is carried out. 
                                
                                If a standby board is not available, just warning message is left.
                                If it is a standby board, 'reset' is carried out.
                                "
                        ::= { fkRedInfo 3 }

                
                -- 1.3.6.1.4.1.10428 9 1.101.22.1.1.4
                fkRedFaultTimeoutAction OBJECT-TYPE
                        SYNTAX FkRedFaultActionType
                        MAX-ACCESS read-only
                        STATUS current
                        DESCRIPTION
                                "If any software module doesn't respond for healthcheck messages for the certain time,
                                the given action is taken.
                                For 'switchover' action, if the board is active and a standby board is available,
                                'switchover' is carried out.
                                
                                If a standby board is not available, just warning message is left.
                                If it is a standby board, 'reset' is carried out.
                                "
                        ::= { fkRedInfo 4 }

                
                -- 1.3.6.1.4.1.10428 9 1.101.22.1.1.5
                fkRedFaultTimeout OBJECT-TYPE
                        SYNTAX INTEGER (5..720000)
                        MAX-ACCESS read-only
                        STATUS current
                        DESCRIPTION
                                "Healthcheck timeout. If a software module doesn't respond for the given time,
                                it is regarded as a timed-out module.
                                
                                (Unit: second, default is '5')
                                "
                        ::= { fkRedInfo 5 }

                
                -- 1.3.6.1.4.1.10428 9 1.101.22.1.1.6
                fkRedActivePrevState OBJECT-TYPE
                        SYNTAX INTEGER
                                {
                                activeInit(0),
                                singleActiveReady(1),
                                versionReport(2),
                                softwareXfer(3),
                                softwareXferDone(4),
                                configXfer(5),
                                configXferDone(6),
                                stateXfer(7),
                                activeReady(8),
                                disconnectStandby(9),
                                standbyWait(10),
                                versionCheck(11),
                                updateMac(12),
                                softwareSync(13),
                                softwareSyncDone(14),
                                configSync(15),
                                configSyncDone(16),
                                startupSync(17),
                                standbyReady(18),
                                standbyReset(19)
                                }
                        MAX-ACCESS read-only
                        STATUS current
                        DESCRIPTION
                                "Previous state of active board."
                        ::= { fkRedInfo 6 }

                
                -- 1.3.6.1.4.1.10428 9 1.101.22.1.1.7
                fkRedActiveCurrState OBJECT-TYPE
                        SYNTAX INTEGER
                                {
                                activeInit(0),
                                singleActiveReady(1),
                                versionReport(2),
                                softwareXfer(3),
                                softwareXferDone(4),
                                configXfer(5),
                                configXferDone(6),
                                stateXfer(7),
                                activeReady(8),
                                disconnectStandby(9),
                                standbyWait(10),
                                versionCheck(11),
                                updateMac(12),
                                softwareSync(13),
                                softwareSyncDone(14),
                                configSync(15),
                                configSyncDone(16),
                                startupSync(17),
                                standbyReady(18),
                                standbyReset(19)
                                }
                        MAX-ACCESS read-only
                        STATUS current
                        DESCRIPTION
                                "Current state of active board."
                        ::= { fkRedInfo 7 }

                
                -- 1.3.6.1.4.1.10428 9 1.101.22.1.2
                fkRedControl OBJECT IDENTIFIER ::= { fkRedBase 2 }

                
                -- 1.3.6.1.4.1.10428 9 1.101.22.1.2.1
                fkRedControlRequest OBJECT-TYPE
                        SYNTAX INTEGER
                                {
                                reloadStandby(1),
                                switchover(2),
                                setFaultMonitor(3)
                                }
                        MAX-ACCESS read-write
                        STATUS current
                        DESCRIPTION
                                "System commands related to control redundancy function.
                                "
                        ::= { fkRedControl 1 }

                
                -- 1.3.6.1.4.1.10428 9 1.101.22.1.2.2
                fkRedControlStatus OBJECT-TYPE
                        SYNTAX FkControlStatusType
                        MAX-ACCESS read-only
                        STATUS current
                        DESCRIPTION
                                "The status of a user command. 
                                "
                        ::= { fkRedControl 2 }

                
                -- 1.3.6.1.4.1.10428 9 1.101.22.1.2.3
                fkRedControlTimer OBJECT-TYPE
                        SYNTAX Gauge32
                        MAX-ACCESS read-write
                        STATUS current
                        DESCRIPTION
                                "The maximum wait time for the manager for a long running user command. 
                                "
                        ::= { fkRedControl 3 }

                
                -- 1.3.6.1.4.1.10428 9 1.101.22.1.2.4
                fkRedControlTimeStamp OBJECT-TYPE
                        SYNTAX TimeTicks
                        MAX-ACCESS read-only
                        STATUS current
                        DESCRIPTION
                                "The time stamp of the last command (end of command)."
                        ::= { fkRedControl 4 }

                
                -- 1.3.6.1.4.1.10428 9 1.101.22.1.2.5
                fkRedControlReqResult OBJECT-TYPE
                        SYNTAX FkControlRequestResultType
                        MAX-ACCESS read-only
                        STATUS current
                        DESCRIPTION
                                "The result of the last user command."
                        ::= { fkRedControl 5 }

                
                -- 1.3.6.1.4.1.10428 9 1.101.22.1.2.6
                fkRedControlReloadOS OBJECT-TYPE
                        SYNTAX FkRedReloadOSType
                        MAX-ACCESS read-write
                        STATUS current
                        DESCRIPTION
                                "A mate board is reloaded with the given os.
                                If 'default' is given, the board is reloaded with 'default' OS.
                                "
                        ::= { fkRedControl 6 }

                
                -- 1.3.6.1.4.1.10428 9 1.101.22.1.2.7
                fkRedControlFaultCrashAction OBJECT-TYPE
                        SYNTAX FkRedFaultActionType
                        MAX-ACCESS read-write
                        STATUS current
                        DESCRIPTION
                                "If any software module is crashed, the given action is taken.
                                For 'switchover' action, if the board is active and a standby board is available,
                                'switchover' is carried out. 
                                
                                If a standby board is not available, just warning message is left.
                                If it is a standby board, 'reset' is carried out.
                                "
                        ::= { fkRedControl 7 }

                
                -- 1.3.6.1.4.1.10428 9 1.101.22.1.2.8
                fkRedControlFaultTimeoutAction OBJECT-TYPE
                        SYNTAX FkRedFaultActionType
                        MAX-ACCESS read-write
                        STATUS current
                        DESCRIPTION
                                "If any software module doesn't respond for healthcheck messages for the certain time,
                                the given action is taken.
                                For 'switchover' action, if the board is active and a standby board is available,
                                'switchover' is carried out.
                                
                                If a standby board is not available, just warning message is left.
                                If it is a standby board, 'reset' is carried out.
                                "
                        ::= { fkRedControl 8 }

                
                -- 1.3.6.1.4.1.10428 9 1.101.22.1.2.9
                fkRedControlFaultTimeout OBJECT-TYPE
                        SYNTAX INTEGER (5..720000)
                        MAX-ACCESS read-write
                        STATUS current
                        DESCRIPTION
                                "Healthcheck timeout. If a software module doesn't respond for the given time,
                                it is regarded as a timed-out module.
                                
                                (Unit: second, default is '5')
                                "
                        ::= { fkRedControl 9 }

                
                -- 1.3.6.1.4.1.10428 9 1.101.22.1.3
                fkRedNotification OBJECT IDENTIFIER ::= { fkRedBase 3 }

                
                -- 1.3.6.1.4.1.10428 9 1.101.22.1.3.1
                fkRedMateReloadRequested NOTIFICATION-TYPE
                        OBJECTS { fkRedControlRequest, fkRedControlTimeStamp, fkRedControlReqResult, fkRedActiveBoard }
                        STATUS current
                        DESCRIPTION 
                                "A new active SFU indication"
                        ::= { fkRedNotification 1 }

                
                -- 1.3.6.1.4.1.10428 9 1.101.22.1.3.2
                fkRedSwitchoverRequested NOTIFICATION-TYPE
                        OBJECTS { fkRedControlRequest, fkRedControlTimeStamp, fkRedControlReqResult }
                        STATUS current
                        DESCRIPTION 
                                "The system redundancy mode has been changed. A standby board is pluged out or in."
                        ::= { fkRedNotification 2 }

                
                -- 1.3.6.1.4.1.10428 9 1.101.22.1.3.3
                fkRedFaultMonitorChanged NOTIFICATION-TYPE
                        OBJECTS { fkRedControlRequest, fkRedControlTimeStamp, fkRedControlReqResult, fkRedControlFaultCrashAction, fkRedControlFaultTimeoutAction, 
                                fkRedControlFaultTimeout }
                        STATUS current
                        DESCRIPTION 
                                "Fault monitor configuration has been changed."
                        ::= { fkRedNotification 3 }

                
                -- 1.3.6.1.4.1.10428 9 1.101.22.2
                fkRedGroup OBJECT-GROUP
                        OBJECTS { fkRedActiveBoard, fkRedMode, fkRedFaultCrashAction, fkRedFaultTimeoutAction, fkRedFaultTimeout, 
                                fkRedControlStatus, fkRedControlTimer, fkRedControlTimeStamp, fkRedControlReqResult, fkRedControlReloadOS, 
                                fkRedControlFaultCrashAction, fkRedControlFaultTimeoutAction, fkRedActivePrevState, fkRedActiveCurrState, fkRedControlFaultTimeout, 
                                fkRedControlRequest }
                        STATUS current
                        DESCRIPTION 
                                "Description."
                        ::= { fkRed 2 }

                
                -- 1.3.6.1.4.1.10428 9 1.101.22.3
                fkRedNotificationGroup NOTIFICATION-GROUP
                        NOTIFICATIONS { fkRedMateReloadRequested, fkRedSwitchoverRequested, fkRedFaultMonitorChanged }
                        STATUS current
                        DESCRIPTION 
                                "Description."
                        ::= { fkRed 3 }

                
        
        END

--
-- FK-RED-MIB.my
--
