--
-- fk-snmp-mib.mib
-- MIB generated by MG-SOFT Visual MIB Builder Version 6.0  Build 88
-- Friday, December 14, 2012 at 14:23:44
--

	FK-SNMP-MIB DEFINITIONS ::= BEGIN
 
		IMPORTS
			fkMgmt			
				FROM FKOLTG1040-SMI			
			OBJECT-GROUP, NOTIFICATION-GROUP			
				FROM SNMPv2-CONF			
			TimeTicks, IpAddress, Integer32, Gauge32, OBJECT-TYPE, 
			MODULE-IDENTITY, NOTIFICATION-TYPE			
				FROM SNMPv2-SMI;
	
	
		-- 1.3.6.1.4.1.10428 9 1.101.8
		fkSnmp MODULE-IDENTITY 
			LAST-UPDATED "200412092259Z"		-- December 09, 2004 at 22:59 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 8 }

		
	
--
-- Node definitions
--
	
		-- 1.3.6.1.4.1.10428 9 1.101.8.1
		fkSnmpBase OBJECT IDENTIFIER ::= { fkSnmp 1 }

		
		-- 1.3.6.1.4.1.10428 9 1.101.8.1.1
		fkSnmpBaseInfo OBJECT IDENTIFIER ::= { fkSnmpBase 1 }

		
		-- 1.3.6.1.4.1.10428 9 1.101.8.1.1.1
		fkSnmpSysContact OBJECT-TYPE
			SYNTAX OCTET STRING
			MAX-ACCESS read-only
			STATUS current
			DESCRIPTION
				"Description."
			::= { fkSnmpBaseInfo 1 }

		
		-- 1.3.6.1.4.1.10428 9 1.101.8.1.1.2
		fkSnmpSysLocation OBJECT-TYPE
			SYNTAX OCTET STRING
			MAX-ACCESS read-only
			STATUS current
			DESCRIPTION
				"Description."
			::= { fkSnmpBaseInfo 2 }

		
		-- 1.3.6.1.4.1.10428 9 1.101.8.1.1.3
		fkSnmpLogStatus OBJECT-TYPE
			SYNTAX INTEGER
				{
				disable(1),
				enable(2)
				}
			MAX-ACCESS read-only
			STATUS current
			DESCRIPTION
				"The status of setrequest user-history"
			::= { fkSnmpBaseInfo 3 }

		
		-- 1.3.6.1.4.1.10428 9 1.101.8.1.1.4
		fkSnmpConnectionType OBJECT-TYPE
			SYNTAX INTEGER
				{
				normal(1),
				lct(2),
				tmn(3),
				unknown(255)
				}
			MAX-ACCESS read-only
			STATUS current
			DESCRIPTION
				"The connection type."
			::= { fkSnmpBaseInfo 4 }

		
		-- 1.3.6.1.4.1.10428 9 1.101.8.1.1.5
		fkSnmpInformTrapRetry OBJECT-TYPE
			SYNTAX Integer32
			MAX-ACCESS read-only
			STATUS current
			DESCRIPTION
				"The inform trap configuration - retry
				default:5 (times)"
			::= { fkSnmpBaseInfo 5 }

		
		-- 1.3.6.1.4.1.10428 9 1.101.8.1.1.6
		fksnmpInformTrapInterval OBJECT-TYPE
			SYNTAX Integer32
			MAX-ACCESS read-only
			STATUS current
			DESCRIPTION
				"The inform trap configuration - interval
				default:3 (sec)
				"
			::= { fkSnmpBaseInfo 6 }

		
		-- 1.3.6.1.4.1.10428 9 1.101.8.1.2
		fkSnmpBaseControl OBJECT IDENTIFIER ::= { fkSnmpBase 2 }

		
		-- 1.3.6.1.4.1.10428 9 1.101.8.1.2.1
		fkSnmpControlRequest OBJECT-TYPE
			SYNTAX INTEGER
				{
				setSnmpSysInfoProfile(1),
				setSnmpLogStatus(2),
				setSnmpConnectionType(3),
				setInformTrapConf(4)
				}
			MAX-ACCESS read-write
			STATUS current
			DESCRIPTION
				"Description."
			::= { fkSnmpBaseControl 1 }

		
		-- 1.3.6.1.4.1.10428 9 1.101.8.1.2.2
		fkSnmpControlStatus OBJECT-TYPE
			SYNTAX Integer32
			MAX-ACCESS read-only
			STATUS current
			DESCRIPTION
				"Description."
			::= { fkSnmpBaseControl 2 }

		
		-- 1.3.6.1.4.1.10428 9 1.101.8.1.2.3
		fkSnmpControlTimer OBJECT-TYPE
			SYNTAX Gauge32
			MAX-ACCESS read-write
			STATUS current
			DESCRIPTION
				"Description."
			::= { fkSnmpBaseControl 3 }

		
		-- 1.3.6.1.4.1.10428 9 1.101.8.1.2.4
		fkSnmpControlTimeStamp OBJECT-TYPE
			SYNTAX TimeTicks
			MAX-ACCESS read-only
			STATUS current
			DESCRIPTION
				"Description."
			::= { fkSnmpBaseControl 4 }

		
		-- 1.3.6.1.4.1.10428 9 1.101.8.1.2.5
		fkSnmpControlReqResult OBJECT-TYPE
			SYNTAX Integer32
			MAX-ACCESS read-only
			STATUS current
			DESCRIPTION
				"Result of the last command."
			::= { fkSnmpBaseControl 5 }

		
		-- 1.3.6.1.4.1.10428 9 1.101.8.1.2.6
		fkSnmpControlSysContact OBJECT-TYPE
			SYNTAX OCTET STRING
			MAX-ACCESS read-write
			STATUS current
			DESCRIPTION
				"Description."
			::= { fkSnmpBaseControl 6 }

		
		-- 1.3.6.1.4.1.10428 9 1.101.8.1.2.7
		fkSnmpControlSysLocation OBJECT-TYPE
			SYNTAX OCTET STRING
			MAX-ACCESS read-write
			STATUS current
			DESCRIPTION
				"Description."
			::= { fkSnmpBaseControl 7 }

		
		-- 1.3.6.1.4.1.10428 9 1.101.8.1.2.8
		fkSnmpControlLogStatus OBJECT-TYPE
			SYNTAX INTEGER
				{
				disable(1),
				enable(2)
				}
			MAX-ACCESS read-write
			STATUS current
			DESCRIPTION
				"The status of setrequest user-history"
			::= { fkSnmpBaseControl 8 }

		
		-- 1.3.6.1.4.1.10428 9 1.101.8.1.2.9
		fkSnmpControlConnectionType OBJECT-TYPE
			SYNTAX INTEGER
				{
				normal(1),
				lct(2),
				tmn(3),
				unknown(255)
				}
			MAX-ACCESS read-write
			STATUS current
			DESCRIPTION
				"The connection type."
			::= { fkSnmpBaseControl 9 }

		
		-- 1.3.6.1.4.1.10428 9 1.101.8.1.2.10
		fkSnmpControlInformTrapRetry OBJECT-TYPE
			SYNTAX Integer32
			MAX-ACCESS read-write
			STATUS current
			DESCRIPTION
				"The inform trap configuration - retry
				default:5 (times)"
			::= { fkSnmpBaseControl 10 }

		
		-- 1.3.6.1.4.1.10428 9 1.101.8.1.2.11
		fkSnmpControlInformTrapInterval OBJECT-TYPE
			SYNTAX Integer32
			MAX-ACCESS read-write
			STATUS current
			DESCRIPTION
				"The inform trap configuration - interval
				default:3 (sec)
				"
			::= { fkSnmpBaseControl 11 }

		
		-- 1.3.6.1.4.1.10428 9 1.101.8.1.3
		fkSnmpBaseNotification OBJECT IDENTIFIER ::= { fkSnmpBase 3 }

		
		-- 1.3.6.1.4.1.10428 9 1.101.8.1.3.1
		fkSnmpSysInfoProfileChanged NOTIFICATION-TYPE
			OBJECTS { fkSnmpControlRequest, fkSnmpControlReqResult, fkSnmpControlSysContact, fkSnmpControlSysLocation, fkSnmpControlTimeStamp
				 }
			STATUS current
			DESCRIPTION 
				"Description."
			::= { fkSnmpBaseNotification 1 }

		
		-- 1.3.6.1.4.1.10428 9 1.101.8.1.3.2
		fkSnmpSysInfoLogStatusChanged NOTIFICATION-TYPE
			OBJECTS { fkSnmpControlRequest, fkSnmpControlTimeStamp, fkSnmpControlReqResult, fkSnmpControlLogStatus }
			STATUS current
			DESCRIPTION 
				"Description."
			::= { fkSnmpBaseNotification 2 }

		
		-- 1.3.6.1.4.1.10428 9 1.101.8.1.3.3
		fkSnmpSysInfoConnectionTypeChanged NOTIFICATION-TYPE
			OBJECTS { fkSnmpControlRequest, fkSnmpControlTimeStamp, fkSnmpControlReqResult, fkSnmpControlConnectionType }
			STATUS current
			DESCRIPTION 
				"Description."
			::= { fkSnmpBaseNotification 3 }

		
		-- 1.3.6.1.4.1.10428 9 1.101.8.1.3.4
		fkSnmpInformTrapConfChanged NOTIFICATION-TYPE
			OBJECTS { fkSnmpControlRequest, fkSnmpControlTimeStamp, fkSnmpControlReqResult, fkSnmpControlInformTrapRetry, fkSnmpControlInformTrapInterval
				 }
			STATUS current
			DESCRIPTION 
				"Description."
			::= { fkSnmpBaseNotification 4 }

		
-- ----------------
--  fkCom2Sec
		-- 1.3.6.1.4.1.10428 9 1.101.8.2
		fkCom2Sec OBJECT IDENTIFIER ::= { fkSnmp 2 }

		
		-- 1.3.6.1.4.1.10428 9 1.101.8.2.1
		fkCom2SecTable OBJECT-TYPE
			SYNTAX SEQUENCE OF FkCom2SecEntry
			MAX-ACCESS not-accessible
			STATUS current
			DESCRIPTION
				"Description."
			::= { fkCom2Sec 1 }

		
		-- 1.3.6.1.4.1.10428 9 1.101.8.2.1.1
		fkCom2SecEntry OBJECT-TYPE
			SYNTAX FkCom2SecEntry
			MAX-ACCESS not-accessible
			STATUS current
			DESCRIPTION
				"Description."
			INDEX { fkCom2SecName }
			::= { fkCom2SecTable 1 }

		
		FkCom2SecEntry ::=
			SEQUENCE { 
				fkCom2SecName
					OCTET STRING,
				fkCom2SecHost
					IpAddress,
				fkCom2SecHostMaskLen
					Integer32,
				fkCom2SecCommunity
					OCTET STRING
			 }

		-- 1.3.6.1.4.1.10428 9 1.101.8.2.1.1.1
		fkCom2SecName OBJECT-TYPE
			SYNTAX OCTET STRING
			MAX-ACCESS read-only
			STATUS current
			DESCRIPTION
				"Com2sec Name"
			::= { fkCom2SecEntry 1 }

		
		-- 1.3.6.1.4.1.10428 9 1.101.8.2.1.1.2
		fkCom2SecHost OBJECT-TYPE
			SYNTAX IpAddress
			MAX-ACCESS read-only
			STATUS current
			DESCRIPTION
				"Accessable host address"
			::= { fkCom2SecEntry 2 }

		
		-- 1.3.6.1.4.1.10428 9 1.101.8.2.1.1.3
		fkCom2SecHostMaskLen OBJECT-TYPE
			SYNTAX Integer32
			MAX-ACCESS read-only
			STATUS current
			DESCRIPTION
				"Mask length for Host address.
				If fkSNMPCom2secHost is network address, 
				fkSNMPCom2secHostMaskLen is 0.
				"
			::= { fkCom2SecEntry 3 }

		
		-- 1.3.6.1.4.1.10428 9 1.101.8.2.1.1.4
		fkCom2SecCommunity OBJECT-TYPE
			SYNTAX OCTET STRING
			MAX-ACCESS read-only
			STATUS current
			DESCRIPTION
				"Community"
			::= { fkCom2SecEntry 4 }

		
		-- 1.3.6.1.4.1.10428 9 1.101.8.2.2
		fkCom2SecControl OBJECT IDENTIFIER ::= { fkCom2Sec 2 }

		
		-- 1.3.6.1.4.1.10428 9 1.101.8.2.2.1
		fkCom2SecControlRequest OBJECT-TYPE
			SYNTAX INTEGER
				{
				createCom2Sec(1),
				destroyCom2Sec(2),
				setCom2SecProfile(3)
				}
			MAX-ACCESS read-write
			STATUS current
			DESCRIPTION
				"Description."
			::= { fkCom2SecControl 1 }

		
		-- 1.3.6.1.4.1.10428 9 1.101.8.2.2.2
		fkCom2SecControlStatus OBJECT-TYPE
			SYNTAX Integer32
			MAX-ACCESS read-only
			STATUS current
			DESCRIPTION
				"Description."
			::= { fkCom2SecControl 2 }

		
		-- 1.3.6.1.4.1.10428 9 1.101.8.2.2.3
		fkCom2SecControlTimer OBJECT-TYPE
			SYNTAX Gauge32
			MAX-ACCESS read-write
			STATUS current
			DESCRIPTION
				"Description."
			::= { fkCom2SecControl 3 }

		
		-- 1.3.6.1.4.1.10428 9 1.101.8.2.2.4
		fkCom2SecControlTimeStamp OBJECT-TYPE
			SYNTAX TimeTicks
			MAX-ACCESS read-only
			STATUS current
			DESCRIPTION
				"Description."
			::= { fkCom2SecControl 4 }

		
		-- 1.3.6.1.4.1.10428 9 1.101.8.2.2.5
		fkCom2SecControlReqResult OBJECT-TYPE
			SYNTAX Integer32
			MAX-ACCESS read-only
			STATUS current
			DESCRIPTION
				"Result of the last command"
			::= { fkCom2SecControl 5 }

		
		-- 1.3.6.1.4.1.10428 9 1.101.8.2.2.6
		fkCom2SecControlName OBJECT-TYPE
			SYNTAX OCTET STRING
			MAX-ACCESS read-write
			STATUS current
			DESCRIPTION
				"Description."
			::= { fkCom2SecControl 6 }

		
		-- 1.3.6.1.4.1.10428 9 1.101.8.2.2.7
		fkCom2SecControlHost OBJECT-TYPE
			SYNTAX IpAddress
			MAX-ACCESS read-write
			STATUS current
			DESCRIPTION
				"Accessable host address"
			::= { fkCom2SecControl 7 }

		
		-- 1.3.6.1.4.1.10428 9 1.101.8.2.2.8
		fkCom2secControlHostMaskLen OBJECT-TYPE
			SYNTAX Integer32
			MAX-ACCESS read-write
			STATUS current
			DESCRIPTION
				"Description."
			::= { fkCom2SecControl 8 }

		
		-- 1.3.6.1.4.1.10428 9 1.101.8.2.2.9
		fkCom2SecControlCommunity OBJECT-TYPE
			SYNTAX OCTET STRING
			MAX-ACCESS read-write
			STATUS current
			DESCRIPTION
				"Description."
			::= { fkCom2SecControl 9 }

		
		-- 1.3.6.1.4.1.10428 9 1.101.8.2.3
		fkCom2SecNotification OBJECT IDENTIFIER ::= { fkCom2Sec 3 }

		
		-- 1.3.6.1.4.1.10428 9 1.101.8.2.3.1
		fkCom2SecCreated NOTIFICATION-TYPE
			OBJECTS { fkCom2SecControlRequest, fkCom2SecControlReqResult, fkCom2SecControlTimeStamp, fkCom2SecHost, fkCom2SecHostMaskLen, 
				fkCom2SecCommunity }
			STATUS current
			DESCRIPTION 
				"Description."
			::= { fkCom2SecNotification 1 }

		
		-- 1.3.6.1.4.1.10428 9 1.101.8.2.3.2
		fkCom2SecDestroyed NOTIFICATION-TYPE
			OBJECTS { fkCom2SecControlRequest, fkCom2SecControlReqResult, fkCom2SecControlTimeStamp, fkCom2SecControlName }
			STATUS current
			DESCRIPTION 
				"Description."
			::= { fkCom2SecNotification 2 }

		
		-- 1.3.6.1.4.1.10428 9 1.101.8.2.3.3
		fkCom2SecProfileChanged NOTIFICATION-TYPE
			OBJECTS { fkCom2SecControlRequest, fkCom2SecControlReqResult, fkCom2SecControlTimeStamp, fkCom2SecHost, fkCom2SecHostMaskLen, 
				fkCom2SecCommunity }
			STATUS current
			DESCRIPTION 
				"Description."
			::= { fkCom2SecNotification 3 }

		
-- 
--  fkTrapHost
		-- 1.3.6.1.4.1.10428 9 1.101.8.3
		fkTrapHost OBJECT IDENTIFIER ::= { fkSnmp 3 }

		
		-- 1.3.6.1.4.1.10428 9 1.101.8.3.1
		fkTrapHostTable OBJECT-TYPE
			SYNTAX SEQUENCE OF FkTrapHostEntry
			MAX-ACCESS not-accessible
			STATUS current
			DESCRIPTION
				"Description."
			::= { fkTrapHost 1 }

		
		-- 1.3.6.1.4.1.10428 9 1.101.8.3.1.1
		fkTrapHostEntry OBJECT-TYPE
			SYNTAX FkTrapHostEntry
			MAX-ACCESS not-accessible
			STATUS current
			DESCRIPTION
				"Description."
			INDEX { fkTrapHostType, fkTrapHostAddress }
			::= { fkTrapHostTable 1 }

		
		FkTrapHostEntry ::=
			SEQUENCE { 
				fkTrapHostType
					INTEGER,
				fkTrapHostAddress
					IpAddress,
				fkTrapHostCommunity
					OCTET STRING,
				fkTrapHostPort
					Integer32
			 }

		-- 1.3.6.1.4.1.10428 9 1.101.8.3.1.1.1
		fkTrapHostType OBJECT-TYPE
			SYNTAX INTEGER
				{
				trapHost(1),
				trap2Host(2),
				informTrapHost(3)
				}
			MAX-ACCESS read-only
			STATUS current
			DESCRIPTION
				"Description."
			::= { fkTrapHostEntry 1 }

		
		-- 1.3.6.1.4.1.10428 9 1.101.8.3.1.1.2
		fkTrapHostAddress OBJECT-TYPE
			SYNTAX IpAddress
			MAX-ACCESS read-only
			STATUS current
			DESCRIPTION
				"Host address for received traps"
			::= { fkTrapHostEntry 2 }

		
		-- 1.3.6.1.4.1.10428 9 1.101.8.3.1.1.3
		fkTrapHostCommunity OBJECT-TYPE
			SYNTAX OCTET STRING
			MAX-ACCESS read-only
			STATUS current
			DESCRIPTION
				"Trap commnity"
			::= { fkTrapHostEntry 3 }

		
		-- 1.3.6.1.4.1.10428 9 1.101.8.3.1.1.4
		fkTrapHostPort OBJECT-TYPE
			SYNTAX Integer32
			MAX-ACCESS read-only
			STATUS current
			DESCRIPTION
				"Trap commnunication port. (advanced)"
			::= { fkTrapHostEntry 4 }

		
		-- 1.3.6.1.4.1.10428 9 1.101.8.3.2
		fkTrapHostControl OBJECT IDENTIFIER ::= { fkTrapHost 2 }

		
		-- 1.3.6.1.4.1.10428 9 1.101.8.3.2.1
		fkTrapHostControlRequest OBJECT-TYPE
			SYNTAX INTEGER
				{
				createTrapHost(1),
				destroyTrapHost(2)
				}
			MAX-ACCESS read-write
			STATUS current
			DESCRIPTION
				"setInformTrapConf"
			::= { fkTrapHostControl 1 }

		
		-- 1.3.6.1.4.1.10428 9 1.101.8.3.2.2
		fkTrapHostControlStatus OBJECT-TYPE
			SYNTAX Integer32
			MAX-ACCESS read-only
			STATUS current
			DESCRIPTION
				"Description."
			::= { fkTrapHostControl 2 }

		
		-- 1.3.6.1.4.1.10428 9 1.101.8.3.2.3
		fkTrapHostControlTimer OBJECT-TYPE
			SYNTAX Gauge32
			MAX-ACCESS read-write
			STATUS current
			DESCRIPTION
				"Description."
			::= { fkTrapHostControl 3 }

		
		-- 1.3.6.1.4.1.10428 9 1.101.8.3.2.4
		fkTrapHostControlTimeStamp OBJECT-TYPE
			SYNTAX TimeTicks
			MAX-ACCESS read-only
			STATUS current
			DESCRIPTION
				"Description."
			::= { fkTrapHostControl 4 }

		
		-- 1.3.6.1.4.1.10428 9 1.101.8.3.2.5
		fkTrapHostControlReqResult OBJECT-TYPE
			SYNTAX Integer32
			MAX-ACCESS read-only
			STATUS current
			DESCRIPTION
				"Description."
			::= { fkTrapHostControl 5 }

		
		-- 1.3.6.1.4.1.10428 9 1.101.8.3.2.6
		fkTrapHostControlType OBJECT-TYPE
			SYNTAX INTEGER
				{
				trapHost(1),
				trap2Host(2),
				informTrapHost(3)
				}
			MAX-ACCESS read-write
			STATUS current
			DESCRIPTION
				"Description."
			::= { fkTrapHostControl 6 }

		
		-- 1.3.6.1.4.1.10428 9 1.101.8.3.2.7
		fkTrapHostControlAddress OBJECT-TYPE
			SYNTAX IpAddress
			MAX-ACCESS read-write
			STATUS current
			DESCRIPTION
				"Host address for received traps"
			::= { fkTrapHostControl 7 }

		
		-- 1.3.6.1.4.1.10428 9 1.101.8.3.2.8
		fkTrapHostControlCommunity OBJECT-TYPE
			SYNTAX OCTET STRING
			MAX-ACCESS read-write
			STATUS current
			DESCRIPTION
				"Description."
			::= { fkTrapHostControl 8 }

		
		-- 1.3.6.1.4.1.10428 9 1.101.8.3.2.9
		fkTrapHostControlPort OBJECT-TYPE
			SYNTAX INTEGER (0..65535)
			MAX-ACCESS read-write
			STATUS current
			DESCRIPTION
				"Description."
			::= { fkTrapHostControl 9 }

		
		-- 1.3.6.1.4.1.10428 9 1.101.8.3.3
		fkTrapHostNotification OBJECT IDENTIFIER ::= { fkTrapHost 3 }

		
		-- 1.3.6.1.4.1.10428 9 1.101.8.3.3.1
		fkTrapHostCreated NOTIFICATION-TYPE
			OBJECTS { fkTrapHostControlRequest, fkTrapHostControlReqResult, fkTrapHostControlTimeStamp, fkTrapHostCommunity }
			STATUS current
			DESCRIPTION 
				"Description."
			::= { fkTrapHostNotification 1 }

		
		-- 1.3.6.1.4.1.10428 9 1.101.8.3.3.2
		fkTrapHostDestroyed NOTIFICATION-TYPE
			OBJECTS { fkTrapHostControlRequest, fkTrapHostControlReqResult, fkTrapHostControlTimeStamp, fkTrapHostControlType, fkTrapHostControlAddress
				 }
			STATUS current
			DESCRIPTION 
				"Description."
			::= { fkTrapHostNotification 2 }

		
-- 
--  fkCommunity
		-- 1.3.6.1.4.1.10428 9 1.101.8.4
		fkCommunity OBJECT IDENTIFIER ::= { fkSnmp 4 }

		
		-- 1.3.6.1.4.1.10428 9 1.101.8.4.1
		fkCommunityTable OBJECT-TYPE
			SYNTAX SEQUENCE OF FkCommunityEntry
			MAX-ACCESS not-accessible
			STATUS current
			DESCRIPTION
				"Description."
			::= { fkCommunity 1 }

		
		-- 1.3.6.1.4.1.10428 9 1.101.8.4.1.1
		fkCommunityEntry OBJECT-TYPE
			SYNTAX FkCommunityEntry
			MAX-ACCESS not-accessible
			STATUS current
			DESCRIPTION
				"Description."
			INDEX { fkCommunityType, fkCommunityValue }
			::= { fkCommunityTable 1 }

		
		FkCommunityEntry ::=
			SEQUENCE { 
				fkCommunityType
					INTEGER,
				fkCommunityValue
					OCTET STRING,
				fkCommunityHost
					IpAddress,
				fkCommunityOID
					OBJECT IDENTIFIER,
				fkCommunityHostMaskLen
					Integer32
			 }

		-- 1.3.6.1.4.1.10428 9 1.101.8.4.1.1.1
		fkCommunityType OBJECT-TYPE
			SYNTAX INTEGER
				{
				readonly(1),
				readwrite(2)
				}
			MAX-ACCESS read-only
			STATUS current
			DESCRIPTION
				"Community Type"
			::= { fkCommunityEntry 1 }

		
		-- 1.3.6.1.4.1.10428 9 1.101.8.4.1.1.2
		fkCommunityValue OBJECT-TYPE
			SYNTAX OCTET STRING
			MAX-ACCESS read-only
			STATUS current
			DESCRIPTION
				"Community key"
			::= { fkCommunityEntry 2 }

		
		-- 1.3.6.1.4.1.10428 9 1.101.8.4.1.1.3
		fkCommunityHost OBJECT-TYPE
			SYNTAX IpAddress
			MAX-ACCESS read-only
			STATUS current
			DESCRIPTION
				"Accessable host address"
			::= { fkCommunityEntry 3 }

		
		-- 1.3.6.1.4.1.10428 9 1.101.8.4.1.1.4
		fkCommunityOID OBJECT-TYPE
			SYNTAX OBJECT IDENTIFIER
			MAX-ACCESS read-only
			STATUS current
			DESCRIPTION
				"Accessable Object ID"
			::= { fkCommunityEntry 4 }

		
		-- 1.3.6.1.4.1.10428 9 1.101.8.4.1.1.5
		fkCommunityHostMaskLen OBJECT-TYPE
			SYNTAX Integer32
			MAX-ACCESS read-only
			STATUS current
			DESCRIPTION
				"Mask length for host address"
			::= { fkCommunityEntry 5 }

		
		-- 1.3.6.1.4.1.10428 9 1.101.8.4.2
		fkCommunityControl OBJECT IDENTIFIER ::= { fkCommunity 2 }

		
		-- 1.3.6.1.4.1.10428 9 1.101.8.4.2.1
		fkCommunityControlRequest OBJECT-TYPE
			SYNTAX INTEGER
				{
				createCommunity(1),
				destroyCommunity(2)
				}
			MAX-ACCESS read-write
			STATUS current
			DESCRIPTION
				"Description."
			::= { fkCommunityControl 1 }

		
		-- 1.3.6.1.4.1.10428 9 1.101.8.4.2.2
		fkCommunityControlStatus OBJECT-TYPE
			SYNTAX Integer32
			MAX-ACCESS read-only
			STATUS current
			DESCRIPTION
				"Description."
			::= { fkCommunityControl 2 }

		
		-- 1.3.6.1.4.1.10428 9 1.101.8.4.2.3
		fkCommunityControlTimer OBJECT-TYPE
			SYNTAX Gauge32
			MAX-ACCESS read-write
			STATUS current
			DESCRIPTION
				"Description."
			::= { fkCommunityControl 3 }

		
		-- 1.3.6.1.4.1.10428 9 1.101.8.4.2.4
		fkCommunityControlTimeStamp OBJECT-TYPE
			SYNTAX TimeTicks
			MAX-ACCESS read-only
			STATUS current
			DESCRIPTION
				"Description."
			::= { fkCommunityControl 4 }

		
		-- 1.3.6.1.4.1.10428 9 1.101.8.4.2.5
		fkCommunityControlReqResult OBJECT-TYPE
			SYNTAX Integer32
			MAX-ACCESS read-only
			STATUS current
			DESCRIPTION
				"Result of the last command"
			::= { fkCommunityControl 5 }

		
		-- 1.3.6.1.4.1.10428 9 1.101.8.4.2.6
		fkCommunityControlType OBJECT-TYPE
			SYNTAX INTEGER
				{
				readonly(1),
				readwrite(2)
				}
			MAX-ACCESS read-write
			STATUS current
			DESCRIPTION
				"Community Type"
			::= { fkCommunityControl 6 }

		
		-- 1.3.6.1.4.1.10428 9 1.101.8.4.2.7
		fkCommunityControlValue OBJECT-TYPE
			SYNTAX OCTET STRING
			MAX-ACCESS read-write
			STATUS current
			DESCRIPTION
				"Community key"
			::= { fkCommunityControl 7 }

		
		-- 1.3.6.1.4.1.10428 9 1.101.8.4.2.8
		fkCommunityControlHost OBJECT-TYPE
			SYNTAX IpAddress
			MAX-ACCESS read-write
			STATUS current
			DESCRIPTION
				"Accessable host address"
			::= { fkCommunityControl 8 }

		
		-- 1.3.6.1.4.1.10428 9 1.101.8.4.2.9
		fkCommunityControlOID OBJECT-TYPE
			SYNTAX OBJECT IDENTIFIER
			MAX-ACCESS read-write
			STATUS current
			DESCRIPTION
				"Accessable Object ID"
			::= { fkCommunityControl 9 }

		
		-- 1.3.6.1.4.1.10428 9 1.101.8.4.2.10
		fkCommunityControlHostMaskLen OBJECT-TYPE
			SYNTAX Integer32
			MAX-ACCESS read-write
			STATUS current
			DESCRIPTION
				"Mask length for host address"
			::= { fkCommunityControl 10 }

		
		-- 1.3.6.1.4.1.10428 9 1.101.8.4.3
		fkCommunityNotification OBJECT IDENTIFIER ::= { fkCommunity 3 }

		
		-- 1.3.6.1.4.1.10428 9 1.101.8.4.3.1
		fkCommunityCreated NOTIFICATION-TYPE
			OBJECTS { fkCommunityControlRequest, fkCommunityControlReqResult, fkCommunityControlTimeStamp, fkCommunityHostMaskLen, fkCommunityHost, 
				fkCommunityOID }
			STATUS current
			DESCRIPTION 
				"Description."
			::= { fkCommunityNotification 1 }

		
		-- 1.3.6.1.4.1.10428 9 1.101.8.4.3.2
		fkCommunityDestroyed NOTIFICATION-TYPE
			OBJECTS { fkCommunityControlRequest, fkCommunityControlReqResult, fkCommunityControlTimeStamp, fkCommunityControlType, fkCommunityControlValue
				 }
			STATUS current
			DESCRIPTION 
				"Description."
			::= { fkCommunityNotification 2 }

		
-- 
--  fkViewTreeFamily
		-- 1.3.6.1.4.1.10428 9 1.101.8.5
		fkViewTreeFamily OBJECT IDENTIFIER ::= { fkSnmp 5 }

		
		-- 1.3.6.1.4.1.10428 9 1.101.8.5.1
		fkViewTreeFamilyTable OBJECT-TYPE
			SYNTAX SEQUENCE OF FkViewTreeFamilyEntry
			MAX-ACCESS not-accessible
			STATUS current
			DESCRIPTION
				"Description."
			::= { fkViewTreeFamily 1 }

		
		-- 1.3.6.1.4.1.10428 9 1.101.8.5.1.1
		fkViewTreeFamilyEntry OBJECT-TYPE
			SYNTAX FkViewTreeFamilyEntry
			MAX-ACCESS not-accessible
			STATUS current
			DESCRIPTION
				"Description."
			INDEX { fkViewTreeFamilyName, fkViewTreeFamilySubtree }
			::= { fkViewTreeFamilyTable 1 }

		
		FkViewTreeFamilyEntry ::=
			SEQUENCE { 
				fkViewTreeFamilyName
					OCTET STRING,
				fkViewTreeFamilySubtree
					OBJECT IDENTIFIER,
				fkViewTreeFamilyMask
					OCTET STRING,
				fkViewTreeFamilyType
					INTEGER
			 }

		-- 1.3.6.1.4.1.10428 9 1.101.8.5.1.1.1
		fkViewTreeFamilyName OBJECT-TYPE
			SYNTAX OCTET STRING
			MAX-ACCESS read-only
			STATUS current
			DESCRIPTION
				"View Name"
			::= { fkViewTreeFamilyEntry 1 }

		
		-- 1.3.6.1.4.1.10428 9 1.101.8.5.1.1.2
		fkViewTreeFamilySubtree OBJECT-TYPE
			SYNTAX OBJECT IDENTIFIER
			MAX-ACCESS read-only
			STATUS current
			DESCRIPTION
				"The MIB subtree which when combined with 
				the corresponding instance of ViewTreeFamilyMask 
				defines a family of view subtrees."
			::= { fkViewTreeFamilyEntry 2 }

		
		-- 1.3.6.1.4.1.10428 9 1.101.8.5.1.1.3
		fkViewTreeFamilyMask OBJECT-TYPE
			SYNTAX OCTET STRING
			MAX-ACCESS read-only
			STATUS current
			DESCRIPTION
				"The bit mask which, in combination with 
				the corresponding instance of ViewTreeFamilySubtree,
				defines a family of view subtrees."
			::= { fkViewTreeFamilyEntry 3 }

		
		-- 1.3.6.1.4.1.10428 9 1.101.8.5.1.1.4
		fkViewTreeFamilyType OBJECT-TYPE
			SYNTAX INTEGER
				{
				included(1),
				excluded(2)
				}
			MAX-ACCESS read-only
			STATUS current
			DESCRIPTION
				"Indicates whether the corresponding
				instances of ViewTreeFamilySubtree and ViewTreeFamilyMask
				define a family of view subtrees which is included in or 
				excluded from the MIB view."
			::= { fkViewTreeFamilyEntry 4 }

		
		-- 1.3.6.1.4.1.10428 9 1.101.8.5.2
		fkViewTreeFamilyControl OBJECT IDENTIFIER ::= { fkViewTreeFamily 2 }

		
		-- 1.3.6.1.4.1.10428 9 1.101.8.5.2.1
		fkViewTreeFamilyControlRequest OBJECT-TYPE
			SYNTAX INTEGER
				{
				createViewTreeFamily(1),
				destroyViewTreeFamily(2)
				}
			MAX-ACCESS read-write
			STATUS current
			DESCRIPTION
				"Description."
			::= { fkViewTreeFamilyControl 1 }

		
		-- 1.3.6.1.4.1.10428 9 1.101.8.5.2.2
		fkViewTreeFamilyControlStatus OBJECT-TYPE
			SYNTAX Integer32
			MAX-ACCESS read-only
			STATUS current
			DESCRIPTION
				"Description."
			::= { fkViewTreeFamilyControl 2 }

		
		-- 1.3.6.1.4.1.10428 9 1.101.8.5.2.3
		fkViewTreeFamilyControlTimer OBJECT-TYPE
			SYNTAX Gauge32
			MAX-ACCESS read-write
			STATUS current
			DESCRIPTION
				"Description."
			::= { fkViewTreeFamilyControl 3 }

		
		-- 1.3.6.1.4.1.10428 9 1.101.8.5.2.4
		fkViewTreeFamilyControlTimeStamp OBJECT-TYPE
			SYNTAX TimeTicks
			MAX-ACCESS read-only
			STATUS current
			DESCRIPTION
				"Description."
			::= { fkViewTreeFamilyControl 4 }

		
		-- 1.3.6.1.4.1.10428 9 1.101.8.5.2.5
		fkViewTreeFamilyControlReqResult OBJECT-TYPE
			SYNTAX Integer32
			MAX-ACCESS read-only
			STATUS current
			DESCRIPTION
				"Description."
			::= { fkViewTreeFamilyControl 5 }

		
		-- 1.3.6.1.4.1.10428 9 1.101.8.5.2.6
		fkViewTreeFamilyControlName OBJECT-TYPE
			SYNTAX OCTET STRING
			MAX-ACCESS read-write
			STATUS current
			DESCRIPTION
				"View Name"
			::= { fkViewTreeFamilyControl 6 }

		
		-- 1.3.6.1.4.1.10428 9 1.101.8.5.2.7
		fkViewTreeFamilyControlSubtree OBJECT-TYPE
			SYNTAX OBJECT IDENTIFIER
			MAX-ACCESS read-write
			STATUS current
			DESCRIPTION
				"Description."
			::= { fkViewTreeFamilyControl 7 }

		
		-- 1.3.6.1.4.1.10428 9 1.101.8.5.2.8
		fkViewTreeFamilyControlMask OBJECT-TYPE
			SYNTAX OCTET STRING
			MAX-ACCESS read-write
			STATUS current
			DESCRIPTION
				"Description."
			::= { fkViewTreeFamilyControl 8 }

		
		-- 1.3.6.1.4.1.10428 9 1.101.8.5.2.9
		fkViewTreeFamilyControlType OBJECT-TYPE
			SYNTAX INTEGER
				{
				included(1),
				excluded(2)
				}
			MAX-ACCESS read-write
			STATUS current
			DESCRIPTION
				"Description."
			::= { fkViewTreeFamilyControl 9 }

		
		-- 1.3.6.1.4.1.10428 9 1.101.8.5.3
		fkViewTreeFamilyNotification OBJECT IDENTIFIER ::= { fkViewTreeFamily 3 }

		
		-- 1.3.6.1.4.1.10428 9 1.101.8.5.3.1
		fkViewTreeFamilyCreated NOTIFICATION-TYPE
			OBJECTS { fkViewTreeFamilyControlRequest, fkViewTreeFamilyControlReqResult, fkViewTreeFamilyControlTimeStamp, fkViewTreeFamilyMask, fkViewTreeFamilyType
				 }
			STATUS current
			DESCRIPTION 
				"Description."
			::= { fkViewTreeFamilyNotification 1 }

		
		-- 1.3.6.1.4.1.10428 9 1.101.8.5.3.2
		fkViewTreeFamilyDestroyed NOTIFICATION-TYPE
			OBJECTS { fkViewTreeFamilyControlRequest, fkViewTreeFamilyControlReqResult, fkViewTreeFamilyControlTimeStamp, fkViewTreeFamilyControlName, fkViewTreeFamilyControlSubtree
				 }
			STATUS current
			DESCRIPTION 
				"Description."
			::= { fkViewTreeFamilyNotification 2 }

		
-- 
--  fkAccess
		-- 1.3.6.1.4.1.10428 9 1.101.8.6
		fkAccess OBJECT IDENTIFIER ::= { fkSnmp 6 }

		
		-- 1.3.6.1.4.1.10428 9 1.101.8.6.1
		fkAccessTable OBJECT-TYPE
			SYNTAX SEQUENCE OF FkAccessEntry
			MAX-ACCESS not-accessible
			STATUS current
			DESCRIPTION
				"Description."
			::= { fkAccess 1 }

		
		-- 1.3.6.1.4.1.10428 9 1.101.8.6.1.1
		fkAccessEntry OBJECT-TYPE
			SYNTAX FkAccessEntry
			MAX-ACCESS not-accessible
			STATUS current
			DESCRIPTION
				"Description."
			INDEX { fkAccessGroupName }
			::= { fkAccessTable 1 }

		
		FkAccessEntry ::=
			SEQUENCE { 
				fkAccessGroupName
					OCTET STRING,
				fkAccessSecurityModel
					INTEGER,
				fkAccessSecurityLevel
					INTEGER,
				fkAccessReadViewName
					OCTET STRING,
				fkAccessWriteViewName
					OCTET STRING,
				fkAccessNotifyViewName
					OCTET STRING
			 }

		-- 1.3.6.1.4.1.10428 9 1.101.8.6.1.1.1
		fkAccessGroupName OBJECT-TYPE
			SYNTAX OCTET STRING
			MAX-ACCESS read-only
			STATUS current
			DESCRIPTION
				"The name of the group to which this entry belongs"
			::= { fkAccessEntry 1 }

		
		-- 1.3.6.1.4.1.10428 9 1.101.8.6.1.1.2
		fkAccessSecurityModel OBJECT-TYPE
			SYNTAX INTEGER
				{
				any(0),
				snmpV1(1),
				snmpV2(2),
				usm(3)
				}
			MAX-ACCESS read-write
			STATUS current
			DESCRIPTION
				"Security Model"
			::= { fkAccessEntry 2 }

		
		-- 1.3.6.1.4.1.10428 9 1.101.8.6.1.1.3
		fkAccessSecurityLevel OBJECT-TYPE
			SYNTAX INTEGER
				{
				noAuthNoPrivn(1),
				authNoPriv(2),
				authPriv(3)
				}
			MAX-ACCESS read-only
			STATUS current
			DESCRIPTION
				"Security Level"
			::= { fkAccessEntry 3 }

		
		-- 1.3.6.1.4.1.10428 9 1.101.8.6.1.1.4
		fkAccessReadViewName OBJECT-TYPE
			SYNTAX OCTET STRING
			MAX-ACCESS read-only
			STATUS current
			DESCRIPTION
				"The value of an instance of this object
				identifies the MIB view of the SNMP context to which 
				this conceptual row authorizes read access."
			::= { fkAccessEntry 4 }

		
		-- 1.3.6.1.4.1.10428 9 1.101.8.6.1.1.5
		fkAccessWriteViewName OBJECT-TYPE
			SYNTAX OCTET STRING
			MAX-ACCESS read-only
			STATUS current
			DESCRIPTION
				"The value of an instance of this object identifies 
				the MIB view of the SNMP context to which 
				this conceptual row authorizes write access."
			::= { fkAccessEntry 5 }

		
		-- 1.3.6.1.4.1.10428 9 1.101.8.6.1.1.6
		fkAccessNotifyViewName OBJECT-TYPE
			SYNTAX OCTET STRING
			MAX-ACCESS read-only
			STATUS current
			DESCRIPTION
				"The value of an instance of this object identifies
				the MIB view of the SNMP context to which this 
				conceptual row authorizes access for notifications."
			::= { fkAccessEntry 6 }

		
		-- 1.3.6.1.4.1.10428 9 1.101.8.6.2
		fkAccessControl OBJECT IDENTIFIER ::= { fkAccess 2 }

		
		-- 1.3.6.1.4.1.10428 9 1.101.8.6.2.1
		fkAccessControlRequest OBJECT-TYPE
			SYNTAX INTEGER
				{
				createAccess(1),
				destroyAccess(2),
				setAccessProfile(3)
				}
			MAX-ACCESS read-write
			STATUS current
			DESCRIPTION
				"Description."
			::= { fkAccessControl 1 }

		
		-- 1.3.6.1.4.1.10428 9 1.101.8.6.2.2
		fkAccessControlStatus OBJECT-TYPE
			SYNTAX Integer32
			MAX-ACCESS read-only
			STATUS current
			DESCRIPTION
				"Description."
			::= { fkAccessControl 2 }

		
		-- 1.3.6.1.4.1.10428 9 1.101.8.6.2.3
		fkAccessControlTimer OBJECT-TYPE
			SYNTAX Gauge32
			MAX-ACCESS read-write
			STATUS current
			DESCRIPTION
				"Description."
			::= { fkAccessControl 3 }

		
		-- 1.3.6.1.4.1.10428 9 1.101.8.6.2.4
		fkAccessControlTimeStamp OBJECT-TYPE
			SYNTAX TimeTicks
			MAX-ACCESS read-only
			STATUS current
			DESCRIPTION
				"Description."
			::= { fkAccessControl 4 }

		
		-- 1.3.6.1.4.1.10428 9 1.101.8.6.2.5
		fkAccessControlReqResult OBJECT-TYPE
			SYNTAX Integer32
			MAX-ACCESS read-only
			STATUS current
			DESCRIPTION
				"Description."
			::= { fkAccessControl 5 }

		
		-- 1.3.6.1.4.1.10428 9 1.101.8.6.2.6
		fkAccessControlGroupName OBJECT-TYPE
			SYNTAX OCTET STRING
			MAX-ACCESS read-write
			STATUS current
			DESCRIPTION
				"Description."
			::= { fkAccessControl 6 }

		
		-- 1.3.6.1.4.1.10428 9 1.101.8.6.2.7
		fkAccessControlSecurityModel OBJECT-TYPE
			SYNTAX INTEGER
				{
				any(0),
				snmpV1(1),
				snmpV2(2),
				usm(3)
				}
			MAX-ACCESS read-write
			STATUS current
			DESCRIPTION
				"Security Model"
			::= { fkAccessControl 7 }

		
		-- 1.3.6.1.4.1.10428 9 1.101.8.6.2.8
		fkAccessControlSecurityLevel OBJECT-TYPE
			SYNTAX INTEGER
				{
				noAuthNoPrivn(1),
				authNoPriv(2),
				authPriv(3)
				}
			MAX-ACCESS read-write
			STATUS current
			DESCRIPTION
				"Security Level"
			::= { fkAccessControl 8 }

		
		-- 1.3.6.1.4.1.10428 9 1.101.8.6.2.9
		fkAccessControlReadViewName OBJECT-TYPE
			SYNTAX OCTET STRING
			MAX-ACCESS read-write
			STATUS current
			DESCRIPTION
				"The value of an instance of this object identifies
				the MIB view of the SNMP context to which this 
				conceptual row authorizes read access."
			::= { fkAccessControl 9 }

		
		-- 1.3.6.1.4.1.10428 9 1.101.8.6.2.10
		fkAccessControlWriteViewName OBJECT-TYPE
			SYNTAX OCTET STRING
			MAX-ACCESS read-write
			STATUS current
			DESCRIPTION
				"The value of an instance of this object identifies 
				the MIB view of the SNMP context to which this 
				conceptual row authorizes write access."
			::= { fkAccessControl 10 }

		
		-- 1.3.6.1.4.1.10428 9 1.101.8.6.2.11
		fkAccessControlNotifyViewName OBJECT-TYPE
			SYNTAX OCTET STRING
			MAX-ACCESS read-write
			STATUS current
			DESCRIPTION
				"The value of an instance of this object identifies 
				the MIB view of the SNMP context to which this 
				conceptual row authorizes access for notifications."
			::= { fkAccessControl 11 }

		
		-- 1.3.6.1.4.1.10428 9 1.101.8.6.3
		fkAccessNotification OBJECT IDENTIFIER ::= { fkAccess 3 }

		
		-- 1.3.6.1.4.1.10428 9 1.101.8.6.3.1
		fkAccessCreated NOTIFICATION-TYPE
			OBJECTS { fkAccessControlRequest, fkAccessControlReqResult, fkAccessControlTimeStamp, fkAccessSecurityModel, fkAccessSecurityLevel, 
				fkAccessReadViewName, fkAccessWriteViewName, fkAccessNotifyViewName }
			STATUS current
			DESCRIPTION 
				"Description."
			::= { fkAccessNotification 1 }

		
		-- 1.3.6.1.4.1.10428 9 1.101.8.6.3.2
		fkAccessDestroyed NOTIFICATION-TYPE
			OBJECTS { fkAccessControlRequest, fkAccessControlReqResult, fkAccessControlTimeStamp, fkAccessControlGroupName }
			STATUS current
			DESCRIPTION 
				"Description."
			::= { fkAccessNotification 2 }

		
		-- 1.3.6.1.4.1.10428 9 1.101.8.6.3.3
		fkAccessProfileChanged NOTIFICATION-TYPE
			OBJECTS { fkAccessControlRequest, fkAccessControlReqResult, fkAccessControlTimeStamp, fkAccessSecurityModel, fkAccessSecurityLevel, 
				fkAccessReadViewName, fkAccessWriteViewName, fkAccessNotifyViewName }
			STATUS current
			DESCRIPTION 
				"Description."
			::= { fkAccessNotification 3 }

		
-- 
--  fkSecurityToGroup
		-- 1.3.6.1.4.1.10428 9 1.101.8.7
		fkSecurityToGroup OBJECT IDENTIFIER ::= { fkSnmp 7 }

		
		-- 1.3.6.1.4.1.10428 9 1.101.8.7.1
		fkSecurityToGroupTable OBJECT-TYPE
			SYNTAX SEQUENCE OF FkSecurityToGroupEntry
			MAX-ACCESS not-accessible
			STATUS current
			DESCRIPTION
				"Description."
			::= { fkSecurityToGroup 1 }

		
		-- 1.3.6.1.4.1.10428 9 1.101.8.7.1.1
		fkSecurityToGroupEntry OBJECT-TYPE
			SYNTAX FkSecurityToGroupEntry
			MAX-ACCESS not-accessible
			STATUS current
			DESCRIPTION
				"Description."
			INDEX { fkSecurityToGroupSName, fkSecurityToGroupModel }
			::= { fkSecurityToGroupTable 1 }

		
		FkSecurityToGroupEntry ::=
			SEQUENCE { 
				fkSecurityToGroupSName
					OCTET STRING,
				fkSecurityToGroupModel
					INTEGER,
				fkSecurityToGroupGName
					OCTET STRING
			 }

		-- 1.3.6.1.4.1.10428 9 1.101.8.7.1.1.1
		fkSecurityToGroupSName OBJECT-TYPE
			SYNTAX OCTET STRING
			MAX-ACCESS read-only
			STATUS current
			DESCRIPTION
				"The securityName for the principal, 
				which is mapped by this entry to a groupName."
			::= { fkSecurityToGroupEntry 1 }

		
		-- 1.3.6.1.4.1.10428 9 1.101.8.7.1.1.2
		fkSecurityToGroupModel OBJECT-TYPE
			SYNTAX INTEGER
				{
				any(0),
				snmpV1(1),
				snmpV2(2),
				usm(3)
				}
			MAX-ACCESS read-only
			STATUS current
			DESCRIPTION
				"Security Model"
			::= { fkSecurityToGroupEntry 2 }

		
		-- 1.3.6.1.4.1.10428 9 1.101.8.7.1.1.3
		fkSecurityToGroupGName OBJECT-TYPE
			SYNTAX OCTET STRING
			MAX-ACCESS read-only
			STATUS current
			DESCRIPTION
				"The name of the group to which this entry belongs."
			::= { fkSecurityToGroupEntry 3 }

		
		-- 1.3.6.1.4.1.10428 9 1.101.8.7.2
		fkSecurityToGroupControl OBJECT IDENTIFIER ::= { fkSecurityToGroup 2 }

		
		-- 1.3.6.1.4.1.10428 9 1.101.8.7.2.1
		fkSecurityToGroupControlRequest OBJECT-TYPE
			SYNTAX INTEGER
				{
				createSecurityToGroup(1),
				destroySecurityToGroup(2),
				setSecurityToGroupProfile(3)
				}
			MAX-ACCESS read-write
			STATUS current
			DESCRIPTION
				"Description."
			::= { fkSecurityToGroupControl 1 }

		
		-- 1.3.6.1.4.1.10428 9 1.101.8.7.2.2
		fkSecurityToGroupControlStatus OBJECT-TYPE
			SYNTAX Integer32
			MAX-ACCESS read-only
			STATUS current
			DESCRIPTION
				"Description."
			::= { fkSecurityToGroupControl 2 }

		
		-- 1.3.6.1.4.1.10428 9 1.101.8.7.2.3
		fkSecurityToGroupControlTimer OBJECT-TYPE
			SYNTAX Gauge32
			MAX-ACCESS read-write
			STATUS current
			DESCRIPTION
				"Description."
			::= { fkSecurityToGroupControl 3 }

		
		-- 1.3.6.1.4.1.10428 9 1.101.8.7.2.4
		fkSecurityToGroupControlTimeStamp OBJECT-TYPE
			SYNTAX TimeTicks
			MAX-ACCESS read-only
			STATUS current
			DESCRIPTION
				"Time stamp attribute set at the end of a command"
			::= { fkSecurityToGroupControl 4 }

		
		-- 1.3.6.1.4.1.10428 9 1.101.8.7.2.5
		fkSecurityToGroupControlReqResult OBJECT-TYPE
			SYNTAX Integer32
			MAX-ACCESS read-only
			STATUS current
			DESCRIPTION
				"Description."
			::= { fkSecurityToGroupControl 5 }

		
		-- 1.3.6.1.4.1.10428 9 1.101.8.7.2.6
		fkSecurityToGroupControlGName OBJECT-TYPE
			SYNTAX OCTET STRING
			MAX-ACCESS read-write
			STATUS current
			DESCRIPTION
				"The name of the group to which this entry belongs."
			::= { fkSecurityToGroupControl 6 }

		
		-- 1.3.6.1.4.1.10428 9 1.101.8.7.2.7
		fkSecurityToGroupControlModel OBJECT-TYPE
			SYNTAX INTEGER
				{
				any(0),
				snmpV1(1),
				snmpV2(2),
				usm(3)
				}
			MAX-ACCESS read-write
			STATUS current
			DESCRIPTION
				"Description."
			::= { fkSecurityToGroupControl 7 }

		
		-- 1.3.6.1.4.1.10428 9 1.101.8.7.2.8
		fkSecurityToGroupControlSName OBJECT-TYPE
			SYNTAX OCTET STRING
			MAX-ACCESS read-write
			STATUS current
			DESCRIPTION
				"The securityName for the principal, 
				which is mapped by this entry to a groupName."
			::= { fkSecurityToGroupControl 8 }

		
		-- 1.3.6.1.4.1.10428 9 1.101.8.7.3
		fkSecurityToGroupNotification OBJECT IDENTIFIER ::= { fkSecurityToGroup 3 }

		
		-- 1.3.6.1.4.1.10428 9 1.101.8.7.3.1
		fkSecurityToGroupCreated NOTIFICATION-TYPE
			OBJECTS { fkSecurityToGroupControlRequest, fkSecurityToGroupControlReqResult, fkSecurityToGroupControlTimeStamp, fkSecurityToGroupSName }
			STATUS current
			DESCRIPTION 
				"Description."
			::= { fkSecurityToGroupNotification 1 }

		
		-- 1.3.6.1.4.1.10428 9 1.101.8.7.3.2
		fkSecurityToGroupDestroyed NOTIFICATION-TYPE
			OBJECTS { fkSecurityToGroupControlRequest, fkSecurityToGroupControlReqResult, fkSecurityToGroupControlTimeStamp, fkSecurityToGroupControlGName, fkSecurityToGroupControlModel
				 }
			STATUS current
			DESCRIPTION 
				"Description."
			::= { fkSecurityToGroupNotification 2 }

		
		-- 1.3.6.1.4.1.10428 9 1.101.8.7.3.3
		fkSecurityToGroupProfileChanged NOTIFICATION-TYPE
			OBJECTS { fkSecurityToGroupControlTimeStamp, fkSecurityToGroupControlReqResult, fkSecurityToGroupControlRequest, fkSecurityToGroupSName }
			STATUS current
			DESCRIPTION 
				"Description."
			::= { fkSecurityToGroupNotification 3 }

		
-- 
--  fkUser
		-- 1.3.6.1.4.1.10428 9 1.101.8.8
		fkUser OBJECT IDENTIFIER ::= { fkSnmp 8 }

		
		-- 1.3.6.1.4.1.10428 9 1.101.8.8.1
		fkUserTable OBJECT-TYPE
			SYNTAX SEQUENCE OF FkUserEntry
			MAX-ACCESS not-accessible
			STATUS current
			DESCRIPTION
				"Description."
			::= { fkUser 1 }

		
		-- 1.3.6.1.4.1.10428 9 1.101.8.8.1.1
		fkUserEntry OBJECT-TYPE
			SYNTAX FkUserEntry
			MAX-ACCESS not-accessible
			STATUS current
			DESCRIPTION
				"Description."
			INDEX { fkUserName }
			::= { fkUserTable 1 }

		
		FkUserEntry ::=
			SEQUENCE { 
				fkUserName
					OCTET STRING,
				fkUserAuthType
					INTEGER,
				fkUserAuthKey
					OCTET STRING,
				fkUserPrivType
					INTEGER,
				fkUserPrivKey
					OCTET STRING
			 }

		-- 1.3.6.1.4.1.10428 9 1.101.8.8.1.1.1
		fkUserName OBJECT-TYPE
			SYNTAX OCTET STRING
			MAX-ACCESS read-only
			STATUS current
			DESCRIPTION
				"User name"
			::= { fkUserEntry 1 }

		
		-- 1.3.6.1.4.1.10428 9 1.101.8.8.1.1.2
		fkUserAuthType OBJECT-TYPE
			SYNTAX INTEGER
				{
				md5(1),
				sha(2)
				}
			MAX-ACCESS read-only
			STATUS current
			DESCRIPTION
				"Authentication type"
			::= { fkUserEntry 2 }

		
		-- 1.3.6.1.4.1.10428 9 1.101.8.8.1.1.3
		fkUserAuthKey OBJECT-TYPE
			SYNTAX OCTET STRING
			MAX-ACCESS read-only
			STATUS current
			DESCRIPTION
				"Authentication key (length >=8)"
			::= { fkUserEntry 3 }

		
		-- 1.3.6.1.4.1.10428 9 1.101.8.8.1.1.4
		fkUserPrivType OBJECT-TYPE
			SYNTAX INTEGER
				{
				noPrivacy(1),
				des(2)
				}
			MAX-ACCESS read-only
			STATUS current
			DESCRIPTION
				"Privacy type"
			::= { fkUserEntry 4 }

		
		-- 1.3.6.1.4.1.10428 9 1.101.8.8.1.1.5
		fkUserPrivKey OBJECT-TYPE
			SYNTAX OCTET STRING
			MAX-ACCESS read-only
			STATUS current
			DESCRIPTION
				"Privacy key (length >=8)"
			::= { fkUserEntry 5 }

		
		-- 1.3.6.1.4.1.10428 9 1.101.8.8.2
		fkUserControl OBJECT IDENTIFIER ::= { fkUser 2 }

		
		-- 1.3.6.1.4.1.10428 9 1.101.8.8.2.1
		fkUserControlRequest OBJECT-TYPE
			SYNTAX INTEGER
				{
				createUser(1),
				destroyUser(2)
				}
			MAX-ACCESS read-write
			STATUS current
			DESCRIPTION
				"Description."
			::= { fkUserControl 1 }

		
		-- 1.3.6.1.4.1.10428 9 1.101.8.8.2.2
		fkUserControlStatus OBJECT-TYPE
			SYNTAX Integer32
			MAX-ACCESS read-only
			STATUS current
			DESCRIPTION
				"Description."
			::= { fkUserControl 2 }

		
		-- 1.3.6.1.4.1.10428 9 1.101.8.8.2.3
		fkUserControlTimer OBJECT-TYPE
			SYNTAX Gauge32
			MAX-ACCESS read-write
			STATUS current
			DESCRIPTION
				"Description."
			::= { fkUserControl 3 }

		
		-- 1.3.6.1.4.1.10428 9 1.101.8.8.2.4
		fkUserControlTimeStamp OBJECT-TYPE
			SYNTAX TimeTicks
			MAX-ACCESS read-only
			STATUS current
			DESCRIPTION
				"Description."
			::= { fkUserControl 4 }

		
		-- 1.3.6.1.4.1.10428 9 1.101.8.8.2.5
		fkUserControlReqResult OBJECT-TYPE
			SYNTAX Integer32
			MAX-ACCESS read-only
			STATUS current
			DESCRIPTION
				"Description."
			::= { fkUserControl 5 }

		
		-- 1.3.6.1.4.1.10428 9 1.101.8.8.2.6
		fkUserControlName OBJECT-TYPE
			SYNTAX OCTET STRING
			MAX-ACCESS read-write
			STATUS current
			DESCRIPTION
				"User name"
			::= { fkUserControl 6 }

		
		-- 1.3.6.1.4.1.10428 9 1.101.8.8.2.7
		fkUserControlAuthType OBJECT-TYPE
			SYNTAX INTEGER
				{
				md5(1),
				sha(2)
				}
			MAX-ACCESS read-write
			STATUS current
			DESCRIPTION
				"Authentication type"
			::= { fkUserControl 7 }

		
		-- 1.3.6.1.4.1.10428 9 1.101.8.8.2.8
		fkUserControlAuthKey OBJECT-TYPE
			SYNTAX OCTET STRING
			MAX-ACCESS read-write
			STATUS current
			DESCRIPTION
				"Authentication key (length >=8)"
			::= { fkUserControl 8 }

		
		-- 1.3.6.1.4.1.10428 9 1.101.8.8.2.9
		fkUserControlPrivType OBJECT-TYPE
			SYNTAX INTEGER
				{
				noPrivacy(1),
				des(2)
				}
			MAX-ACCESS read-write
			STATUS current
			DESCRIPTION
				"Privacy type"
			::= { fkUserControl 9 }

		
		-- 1.3.6.1.4.1.10428 9 1.101.8.8.2.10
		fkUserControlPrivKey OBJECT-TYPE
			SYNTAX OCTET STRING
			MAX-ACCESS read-write
			STATUS current
			DESCRIPTION
				"Privacy key (length >=8)"
			::= { fkUserControl 10 }

		
		-- 1.3.6.1.4.1.10428 9 1.101.8.8.3
		fkUserNotification OBJECT IDENTIFIER ::= { fkUser 3 }

		
		-- 1.3.6.1.4.1.10428 9 1.101.8.8.3.1
		fkUserCreated NOTIFICATION-TYPE
			OBJECTS { fkUserControlRequest, fkUserControlReqResult, fkUserControlTimeStamp, fkUserAuthType, fkUserAuthKey, 
				fkUserPrivType, fkUserPrivKey }
			STATUS current
			DESCRIPTION 
				"Description."
			::= { fkUserNotification 1 }

		
		-- 1.3.6.1.4.1.10428 9 1.101.8.8.3.2
		fkUserDestroyed NOTIFICATION-TYPE
			OBJECTS { fkUserControlRequest, fkUserControlReqResult, fkUserControlTimeStamp, fkUserControlName }
			STATUS current
			DESCRIPTION 
				"Description."
			::= { fkUserNotification 2 }

		
		-- 1.3.6.1.4.1.10428 9 1.101.8.9
		fkAgent OBJECT IDENTIFIER ::= { fkSnmp 9 }

		
		-- 1.3.6.1.4.1.10428 9 1.101.8.9.1
		fkAgentInfo OBJECT IDENTIFIER ::= { fkAgent 1 }

		
		-- 1.3.6.1.4.1.10428 9 1.101.8.9.1.1
		fkAgentAddress OBJECT-TYPE
			SYNTAX IpAddress
			MAX-ACCESS read-only
			STATUS current
			DESCRIPTION
				"Snmp agent address
				If this value is setted, fkAgentInterface value is NULL
				"
			::= { fkAgentInfo 1 }

		
		-- 1.3.6.1.4.1.10428 9 1.101.8.9.1.2
		fkAgentInterface OBJECT-TYPE
			SYNTAX OCTET STRING
			MAX-ACCESS read-only
			STATUS current
			DESCRIPTION
				"Snmp agent interface
				If this value is setted, fkAgentAddress value is 0
				"
			::= { fkAgentInfo 2 }

		
		-- 1.3.6.1.4.1.10428 9 1.101.8.9.2
		fkAgentControl OBJECT IDENTIFIER ::= { fkAgent 2 }

		
		-- 1.3.6.1.4.1.10428 9 1.101.8.9.2.1
		fkAgentControlRequest OBJECT-TYPE
			SYNTAX INTEGER
				{
				setSnmpAgentAddress(1),
				setSnmpAgentInterface(2),
				destroySnmpAgentAddress(3),
				destroySnmpAgentInterface(4)
				}
			MAX-ACCESS read-write
			STATUS current
			DESCRIPTION
				"Description."
			::= { fkAgentControl 1 }

		
		-- 1.3.6.1.4.1.10428 9 1.101.8.9.2.2
		fkAgentControlStatus OBJECT-TYPE
			SYNTAX Integer32
			MAX-ACCESS read-only
			STATUS current
			DESCRIPTION
				"Description."
			::= { fkAgentControl 2 }

		
		-- 1.3.6.1.4.1.10428 9 1.101.8.9.2.3
		fkAgentControlTimer OBJECT-TYPE
			SYNTAX Gauge32
			MAX-ACCESS read-write
			STATUS current
			DESCRIPTION
				"Description."
			::= { fkAgentControl 3 }

		
		-- 1.3.6.1.4.1.10428 9 1.101.8.9.2.4
		fkAgentControlTimeStamp OBJECT-TYPE
			SYNTAX TimeTicks
			MAX-ACCESS read-only
			STATUS current
			DESCRIPTION
				"Description."
			::= { fkAgentControl 4 }

		
		-- 1.3.6.1.4.1.10428 9 1.101.8.9.2.5
		fkAgentControlReqResult OBJECT-TYPE
			SYNTAX Integer32
			MAX-ACCESS read-only
			STATUS current
			DESCRIPTION
				"Description."
			::= { fkAgentControl 5 }

		
		-- 1.3.6.1.4.1.10428 9 1.101.8.9.2.6
		fkAgentControlAddress OBJECT-TYPE
			SYNTAX IpAddress
			MAX-ACCESS read-write
			STATUS current
			DESCRIPTION
				"snmp agent address"
			::= { fkAgentControl 6 }

		
		-- 1.3.6.1.4.1.10428 9 1.101.8.9.2.7
		fkAgentControlInterface OBJECT-TYPE
			SYNTAX OCTET STRING
			MAX-ACCESS read-write
			STATUS current
			DESCRIPTION
				"Snmp agent interface"
			::= { fkAgentControl 7 }

		
		-- 1.3.6.1.4.1.10428 9 1.101.8.9.3
		fkAgentNotification OBJECT IDENTIFIER ::= { fkAgent 3 }

		
		-- 1.3.6.1.4.1.10428 9 1.101.8.9.3.1
		fkAgentAddressChanged NOTIFICATION-TYPE
			OBJECTS { fkAgentControlRequest, fkAgentControlTimeStamp, fkAgentControlReqResult, fkAgentAddress }
			STATUS current
			DESCRIPTION 
				"Create agent address"
			::= { fkAgentNotification 1 }

		
		-- 1.3.6.1.4.1.10428 9 1.101.8.9.3.2
		fkAgentInterfaceChanged NOTIFICATION-TYPE
			OBJECTS { fkAgentControlRequest, fkAgentControlTimeStamp, fkAgentControlReqResult, fkAgentInterface }
			STATUS current
			DESCRIPTION 
				"Create agent interface"
			::= { fkAgentNotification 2 }

		
		-- 1.3.6.1.4.1.10428 9 1.101.8.9.3.3
		fkAgentAddressDestroyed NOTIFICATION-TYPE
			OBJECTS { fkAgentControlRequest, fkAgentControlTimeStamp, fkAgentControlReqResult }
			STATUS current
			DESCRIPTION 
				"Destroy agent address"
			::= { fkAgentNotification 3 }

		
		-- 1.3.6.1.4.1.10428 9 1.101.8.9.3.4
		fkAgentInterfaceDestroyed NOTIFICATION-TYPE
			OBJECTS { fkAgentControlRequest, fkAgentControlTimeStamp, fkAgentControlReqResult }
			STATUS current
			DESCRIPTION 
				"Destroy agent interface"
			::= { fkAgentNotification 4 }

		
		-- 1.3.6.1.4.1.10428 9 1.101.8.10
		fkSnmpSesson OBJECT IDENTIFIER ::= { fkSnmp 10 }

		
		-- 1.3.6.1.4.1.10428 9 1.101.8.10.1
		fkSnmpSessionInfo OBJECT IDENTIFIER ::= { fkSnmpSesson 1 }

		
		-- 1.3.6.1.4.1.10428 9 1.101.8.10.1.1
		fkSnmpSessionTimeout OBJECT-TYPE
			SYNTAX Integer32
			UNITS "sec"
			MAX-ACCESS read-only
			STATUS current
			DESCRIPTION
				"Snmp session timeout 
				
				"
			::= { fkSnmpSessionInfo 1 }

		
		-- 1.3.6.1.4.1.10428 9 1.101.8.10.2
		fkSnmpSessionTable OBJECT-TYPE
			SYNTAX SEQUENCE OF FkSnmpSessionEntry
			MAX-ACCESS not-accessible
			STATUS current
			DESCRIPTION
				"Description."
			::= { fkSnmpSesson 2 }

		
		-- 1.3.6.1.4.1.10428 9 1.101.8.10.2.1
		fkSnmpSessionEntry OBJECT-TYPE
			SYNTAX FkSnmpSessionEntry
			MAX-ACCESS not-accessible
			STATUS current
			DESCRIPTION
				"Description."
			INDEX { fkSnmpSessionIpAddr, fkSnmpSessionCommunity }
			::= { fkSnmpSessionTable 1 }

		
		FkSnmpSessionEntry ::=
			SEQUENCE { 
				fkSnmpSessionIpAddr
					IpAddress,
				fkSnmpSessionCommunity
					OCTET STRING,
				fkSnmpSessionSnmpVersion
					Integer32,
				fkSnmpSessionAccessTIme
					OCTET STRING
			 }

		-- 1.3.6.1.4.1.10428 9 1.101.8.10.2.1.1
		fkSnmpSessionIpAddr OBJECT-TYPE
			SYNTAX IpAddress
			MAX-ACCESS read-only
			STATUS current
			DESCRIPTION
				"Snmp session ip address"
			::= { fkSnmpSessionEntry 1 }

		
		-- 1.3.6.1.4.1.10428 9 1.101.8.10.2.1.2
		fkSnmpSessionCommunity OBJECT-TYPE
			SYNTAX OCTET STRING
			MAX-ACCESS read-only
			STATUS current
			DESCRIPTION
				"Snmp session SNMP version"
			::= { fkSnmpSessionEntry 2 }

		
		-- 1.3.6.1.4.1.10428 9 1.101.8.10.2.1.3
		fkSnmpSessionSnmpVersion OBJECT-TYPE
			SYNTAX Integer32
			MAX-ACCESS read-only
			STATUS current
			DESCRIPTION
				"Snmp session SNMP version"
			::= { fkSnmpSessionEntry 3 }

		
		-- 1.3.6.1.4.1.10428 9 1.101.8.10.2.1.4
		fkSnmpSessionAccessTIme OBJECT-TYPE
			SYNTAX OCTET STRING
			MAX-ACCESS read-only
			STATUS current
			DESCRIPTION
				"Snmp session last access time"
			::= { fkSnmpSessionEntry 4 }

		
		-- 1.3.6.1.4.1.10428 9 1.101.8.10.3
		fkSnmpSessiontControl OBJECT IDENTIFIER ::= { fkSnmpSesson 3 }

		
		-- 1.3.6.1.4.1.10428 9 1.101.8.10.3.1
		fkSnmpSessionControlRequest OBJECT-TYPE
			SYNTAX INTEGER { setSnmpsessionTimeout(1) }
			MAX-ACCESS read-write
			STATUS current
			DESCRIPTION
				"Description."
			::= { fkSnmpSessiontControl 1 }

		
		-- 1.3.6.1.4.1.10428 9 1.101.8.10.3.2
		fkSnmpSessionControlStatus OBJECT-TYPE
			SYNTAX Integer32
			MAX-ACCESS read-write
			STATUS current
			DESCRIPTION
				"Description."
			::= { fkSnmpSessiontControl 2 }

		
		-- 1.3.6.1.4.1.10428 9 1.101.8.10.3.3
		fkSnmpSessionControlTimer OBJECT-TYPE
			SYNTAX Gauge32
			MAX-ACCESS read-write
			STATUS current
			DESCRIPTION
				"Description."
			::= { fkSnmpSessiontControl 3 }

		
		-- 1.3.6.1.4.1.10428 9 1.101.8.10.3.4
		fkSnmpSessionControlTimeStamp OBJECT-TYPE
			SYNTAX TimeTicks
			MAX-ACCESS read-write
			STATUS current
			DESCRIPTION
				"Description."
			::= { fkSnmpSessiontControl 4 }

		
		-- 1.3.6.1.4.1.10428 9 1.101.8.10.3.5
		fkSnmpSessionControlReqResult OBJECT-TYPE
			SYNTAX Integer32
			MAX-ACCESS read-write
			STATUS current
			DESCRIPTION
				"Description."
			::= { fkSnmpSessiontControl 5 }

		
		-- 1.3.6.1.4.1.10428 9 1.101.8.10.3.6
		fkSnmpSessionControlTimeout OBJECT-TYPE
			SYNTAX Integer32
			MAX-ACCESS read-write
			STATUS current
			DESCRIPTION
				"Description."
			::= { fkSnmpSessiontControl 6 }

		
		-- 1.3.6.1.4.1.10428 9 1.101.8.10.4
		fkSnmpSessionNotifications OBJECT IDENTIFIER ::= { fkSnmpSesson 4 }

		
		-- 1.3.6.1.4.1.10428 9 1.101.8.10.4.1
		fkSnmpSessionTimeoutChanged NOTIFICATION-TYPE
			OBJECTS { fkSnmpSessionControlRequest, fkSnmpSessionControlReqResult, fkSnmpSessionControlTimeStamp, fkSnmpSessionTimeout }
			STATUS current
			DESCRIPTION 
				"Description."
			::= { fkSnmpSessionNotifications 1 }

		
		-- 1.3.6.1.4.1.10428 9 1.101.8.11
		fkSnmpTrap OBJECT IDENTIFIER ::= { fkSnmp 11 }

		
		-- 1.3.6.1.4.1.10428 9 1.101.8.11.1
		fkSnmpTrapTable OBJECT-TYPE
			SYNTAX SEQUENCE OF FkSnmpTrapEntry
			MAX-ACCESS not-accessible
			STATUS current
			DESCRIPTION
				"Description."
			::= { fkSnmpTrap 1 }

		
		-- 1.3.6.1.4.1.10428 9 1.101.8.11.1.1
		fkSnmpTrapEntry OBJECT-TYPE
			SYNTAX FkSnmpTrapEntry
			MAX-ACCESS not-accessible
			STATUS current
			DESCRIPTION
				"Description."
			INDEX { fkSnmpTrapIndex }
			::= { fkSnmpTrapTable 1 }

		
		FkSnmpTrapEntry ::=
			SEQUENCE { 
				fkSnmpTrapIndex
					INTEGER,
				fkSnmpTrapStatus
					INTEGER
			 }

		-- 1.3.6.1.4.1.10428 9 1.101.8.11.1.1.1
		fkSnmpTrapIndex OBJECT-TYPE
			SYNTAX INTEGER
				{
				linkUp(1),
				linkDown(2),
				authFail(3),
				coldStart(4),
				cpuThreshold(5),
				portThreshold(6),
				power(7),
				module(8),
				fan(9),
				dhcpLease(10),
				temperThreshold(11),
				memoryThreshold(12),
				igmp(13),
				autoCli(14),
				autoReset(15),
				door(16),
				battery(17),
				epon(18),
				adminAccess(19),
				swWatchdog(20),
				cliHistory(50),
				commandLog(51)
				}
			MAX-ACCESS read-only
			STATUS current
			DESCRIPTION
				"Description."
			::= { fkSnmpTrapEntry 1 }

		
		-- 1.3.6.1.4.1.10428 9 1.101.8.11.1.1.2
		fkSnmpTrapStatus OBJECT-TYPE
			SYNTAX INTEGER
				{
				enable(1),
				disable(2)
				}
			MAX-ACCESS read-only
			STATUS current
			DESCRIPTION
				"Description."
			::= { fkSnmpTrapEntry 2 }

		
		-- 1.3.6.1.4.1.10428 9 1.101.8.11.2
		fkSnmpTrapPortTable OBJECT-TYPE
			SYNTAX SEQUENCE OF FkSnmpTrapPortEntry
			MAX-ACCESS not-accessible
			STATUS current
			DESCRIPTION
				"Description."
			::= { fkSnmpTrap 2 }

		
		-- 1.3.6.1.4.1.10428 9 1.101.8.11.2.1
		fkSnmpTrapPortEntry OBJECT-TYPE
			SYNTAX FkSnmpTrapPortEntry
			MAX-ACCESS not-accessible
			STATUS current
			DESCRIPTION
				"Description."
			INDEX { fkSnmpTrapPortIndex, fkSnmpTrapPortType }
			::= { fkSnmpTrapPortTable 1 }

		
		FkSnmpTrapPortEntry ::=
			SEQUENCE { 
				fkSnmpTrapPortIndex
					INTEGER,
				fkSnmpTrapPortType
					INTEGER,
				fkSnmpTrapPortStatus
					INTEGER
			 }

		-- 1.3.6.1.4.1.10428 9 1.101.8.11.2.1.1
		fkSnmpTrapPortIndex OBJECT-TYPE
			SYNTAX INTEGER (1..512)
			MAX-ACCESS read-only
			STATUS current
			DESCRIPTION
				"Description."
			::= { fkSnmpTrapPortEntry 1 }

		
		-- 1.3.6.1.4.1.10428 9 1.101.8.11.2.1.2
		fkSnmpTrapPortType OBJECT-TYPE
			SYNTAX INTEGER
				{
				linkUp(1),
				linkDown(2)
				}
			MAX-ACCESS read-only
			STATUS current
			DESCRIPTION
				"Description."
			::= { fkSnmpTrapPortEntry 2 }

		
		-- 1.3.6.1.4.1.10428 9 1.101.8.11.2.1.3
		fkSnmpTrapPortStatus OBJECT-TYPE
			SYNTAX INTEGER
				{
				enable(1),
				disable(2)
				}
			MAX-ACCESS read-only
			STATUS current
			DESCRIPTION
				"Description."
			::= { fkSnmpTrapPortEntry 3 }

		
		-- 1.3.6.1.4.1.10428 9 1.101.8.11.3
		fkSnmpTrapControl OBJECT IDENTIFIER ::= { fkSnmpTrap 3 }

		
		-- 1.3.6.1.4.1.10428 9 1.101.8.11.3.1
		fkSnmpTrapControlRequest OBJECT-TYPE
			SYNTAX INTEGER
				{
				setSnmpTrapStatus(1),
				setSnmpTrapStatusByport(2)
				}
			MAX-ACCESS read-write
			STATUS current
			DESCRIPTION
				"Description."
			::= { fkSnmpTrapControl 1 }

		
		-- 1.3.6.1.4.1.10428 9 1.101.8.11.3.2
		fkSnmpTrapControlStatus OBJECT-TYPE
			SYNTAX Integer32
			MAX-ACCESS read-write
			STATUS current
			DESCRIPTION
				"Description."
			::= { fkSnmpTrapControl 2 }

		
		-- 1.3.6.1.4.1.10428 9 1.101.8.11.3.3
		fkSnmpTrapControlTimer OBJECT-TYPE
			SYNTAX Gauge32
			MAX-ACCESS read-write
			STATUS current
			DESCRIPTION
				"Description."
			::= { fkSnmpTrapControl 3 }

		
		-- 1.3.6.1.4.1.10428 9 1.101.8.11.3.4
		fkSnmpTrapControlTimeStamp OBJECT-TYPE
			SYNTAX TimeTicks
			MAX-ACCESS read-write
			STATUS current
			DESCRIPTION
				"Description."
			::= { fkSnmpTrapControl 4 }

		
		-- 1.3.6.1.4.1.10428 9 1.101.8.11.3.5
		fkSnmpTrapControlReqResult OBJECT-TYPE
			SYNTAX Integer32
			MAX-ACCESS read-write
			STATUS current
			DESCRIPTION
				"Description."
			::= { fkSnmpTrapControl 5 }

		
		-- 1.3.6.1.4.1.10428 9 1.101.8.11.3.6
		fkSnmpTrapControlTrapIndex OBJECT-TYPE
			SYNTAX INTEGER
				{
				linkUp(1),
				linkDown(2),
				authFail(3),
				coldStart(4),
				cpuThreshold(5),
				portThreshold(6),
				power(7),
				module(8),
				fan(9),
				dhcpLease(10),
				temperThreshold(11),
				memoryThreshold(12),
				igmp(13),
				autoCli(14),
				autoReset(15),
				door(16),
				battery(17),
				epon(18),
				adminAccess(19),
				swWatchdog(20),
				cliHistory(50),
				commandLog(51)
				}
			MAX-ACCESS read-write
			STATUS current
			DESCRIPTION
				"Description."
			::= { fkSnmpTrapControl 6 }

		
		-- 1.3.6.1.4.1.10428 9 1.101.8.11.3.7
		fkSnmpTrapControlPortIndex OBJECT-TYPE
			SYNTAX Integer32
			MAX-ACCESS read-write
			STATUS current
			DESCRIPTION
				"Description."
			::= { fkSnmpTrapControl 7 }

		
		-- 1.3.6.1.4.1.10428 9 1.101.8.11.3.8
		fkSnmpTrapControlTrapStatus OBJECT-TYPE
			SYNTAX INTEGER
				{
				enable(1),
				disable(2)
				}
			MAX-ACCESS read-write
			STATUS current
			DESCRIPTION
				"Description."
			::= { fkSnmpTrapControl 8 }

		
		-- 1.3.6.1.4.1.10428 9 1.101.8.11.4
		fkSnmpTrapNotification OBJECT IDENTIFIER ::= { fkSnmpTrap 4 }

		
		-- 1.3.6.1.4.1.10428 9 1.101.8.11.4.1
		fkSnmpTrapStatusChanged NOTIFICATION-TYPE
			OBJECTS { fkSnmpTrapControlRequest, fkSnmpTrapControlReqResult, fkSnmpTrapControlTimeStamp, fkSnmpTrapControlTrapStatus }
			STATUS current
			DESCRIPTION 
				"Description."
			::= { fkSnmpTrapNotification 1 }

		
		-- 1.3.6.1.4.1.10428 9 1.101.8.11.4.2
		fkSnmpTrapPortStatusChanged NOTIFICATION-TYPE
			OBJECTS { fkSnmpTrapControlRequest, fkSnmpTrapControlTimeStamp, fkSnmpTrapControlReqResult, fkSnmpTrapControlTrapStatus }
			STATUS current
			DESCRIPTION 
				"Description."
			::= { fkSnmpTrapNotification 2 }

		
		-- 1.3.6.1.4.1.10428 9 1.101.8.12
		fkSnmpTrapSource OBJECT IDENTIFIER ::= { fkSnmp 12 }

		
		-- 1.3.6.1.4.1.10428 9 1.101.8.12.1
		fkSnmpTrapSourceInfo OBJECT IDENTIFIER ::= { fkSnmpTrapSource 1 }

		
		-- 1.3.6.1.4.1.10428 9 1.101.8.12.1.1
		fkSnmpTrapSourceAddress OBJECT-TYPE
			SYNTAX IpAddress
			MAX-ACCESS read-only
			STATUS current
			DESCRIPTION
				"Snmp Trap Source address
				If this value is setted, fkTrapSourceInterface value is NULL
				"
			::= { fkSnmpTrapSourceInfo 1 }

		
		-- 1.3.6.1.4.1.10428 9 1.101.8.12.1.2
		fkSnmpTrapSourceInterface OBJECT-TYPE
			SYNTAX OCTET STRING
			MAX-ACCESS read-only
			STATUS current
			DESCRIPTION
				"Snmp Trap Source interface
				If this value is setted, fkTrapSourceAddress value is 0
				"
			::= { fkSnmpTrapSourceInfo 2 }

		
		-- 1.3.6.1.4.1.10428 9 1.101.8.12.2
		fkSnmpTrapSourceControl OBJECT IDENTIFIER ::= { fkSnmpTrapSource 2 }

		
		-- 1.3.6.1.4.1.10428 9 1.101.8.12.2.1
		fkSnmpTrapSourceControlRequest OBJECT-TYPE
			SYNTAX INTEGER
				{
				setSnmpTrapSourceAddress(1),
				setSnmpTrapSourceInterface(2),
				destroySnmpTrapSourceAddress(3),
				destroySnmpTrapSourceInterface(4)
				}
			MAX-ACCESS read-write
			STATUS current
			DESCRIPTION
				"Description."
			::= { fkSnmpTrapSourceControl 1 }

		
		-- 1.3.6.1.4.1.10428 9 1.101.8.12.2.2
		fkSnmpTrapSourceControlStatus OBJECT-TYPE
			SYNTAX Integer32
			MAX-ACCESS read-only
			STATUS current
			DESCRIPTION
				"Description."
			::= { fkSnmpTrapSourceControl 2 }

		
		-- 1.3.6.1.4.1.10428 9 1.101.8.12.2.3
		fkSnmpTrapSourceControlTimer OBJECT-TYPE
			SYNTAX Gauge32
			MAX-ACCESS read-write
			STATUS current
			DESCRIPTION
				"Description."
			::= { fkSnmpTrapSourceControl 3 }

		
		-- 1.3.6.1.4.1.10428 9 1.101.8.12.2.4
		fkSnmpTrapSourceControlTimeStamp OBJECT-TYPE
			SYNTAX TimeTicks
			MAX-ACCESS read-only
			STATUS current
			DESCRIPTION
				"Description."
			::= { fkSnmpTrapSourceControl 4 }

		
		-- 1.3.6.1.4.1.10428 9 1.101.8.12.2.5
		fkSnmpTrapSourceControlReqResult OBJECT-TYPE
			SYNTAX Integer32
			MAX-ACCESS read-only
			STATUS current
			DESCRIPTION
				"Description."
			::= { fkSnmpTrapSourceControl 5 }

		
		-- 1.3.6.1.4.1.10428 9 1.101.8.12.2.6
		fkSnmpTrapSourceControlAddress OBJECT-TYPE
			SYNTAX IpAddress
			MAX-ACCESS read-write
			STATUS current
			DESCRIPTION
				"snmp trap source address"
			::= { fkSnmpTrapSourceControl 6 }

		
		-- 1.3.6.1.4.1.10428 9 1.101.8.12.2.7
		fkSnmpTrapSourceControlInterface OBJECT-TYPE
			SYNTAX OCTET STRING
			MAX-ACCESS read-write
			STATUS current
			DESCRIPTION
				"Snmp trap source interface"
			::= { fkSnmpTrapSourceControl 7 }

		
		-- 1.3.6.1.4.1.10428 9 1.101.8.12.3
		fkSnmpTrapSourceNotification OBJECT IDENTIFIER ::= { fkSnmpTrapSource 3 }

		
		-- 1.3.6.1.4.1.10428 9 1.101.8.12.3.1
		fkSnmpTrapSourceAddressChanged NOTIFICATION-TYPE
			OBJECTS { fkSnmpTrapSourceControlRequest, fkSnmpTrapSourceControlReqResult, fkSnmpTrapSourceControlTimeStamp, fkSnmpTrapSourceAddress }
			STATUS current
			DESCRIPTION 
				"Create trap source address"
			::= { fkSnmpTrapSourceNotification 1 }

		
		-- 1.3.6.1.4.1.10428 9 1.101.8.12.3.2
		fkSnmpTrapSourceInterfaceChanged NOTIFICATION-TYPE
			OBJECTS { fkSnmpTrapSourceControlRequest, fkSnmpTrapSourceControlReqResult, fkSnmpTrapSourceControlTimeStamp, fkSnmpTrapSourceInterface }
			STATUS current
			DESCRIPTION 
				"Create trap source interface"
			::= { fkSnmpTrapSourceNotification 2 }

		
		-- 1.3.6.1.4.1.10428 9 1.101.8.12.3.3
		fkSnmpTrapSourcetAddressDestroyed NOTIFICATION-TYPE
			OBJECTS { fkSnmpTrapSourceControlRequest, fkSnmpTrapSourceControlTimeStamp, fkSnmpTrapSourceControlReqResult }
			STATUS current
			DESCRIPTION 
				"Destroy trap source address"
			::= { fkSnmpTrapSourceNotification 3 }

		
		-- 1.3.6.1.4.1.10428 9 1.101.8.12.3.4
		fkSnmpTrapSourceInterfaceDestroyed NOTIFICATION-TYPE
			OBJECTS { fkSnmpTrapSourceControlRequest, fkSnmpTrapSourceControlTimeStamp, fkSnmpTrapSourceControlReqResult }
			STATUS current
			DESCRIPTION 
				"Destroy trap source interface"
			::= { fkSnmpTrapSourceNotification 4 }

		
		-- 1.3.6.1.4.1.10428 9 1.101.8.13
		fkSnmpLog OBJECT IDENTIFIER ::= { fkSnmp 13 }

		
		-- 1.3.6.1.4.1.10428 9 1.101.8.13.1
		fkSnmpLogTable OBJECT-TYPE
			SYNTAX SEQUENCE OF FkSnmpLogEntry
			MAX-ACCESS not-accessible
			STATUS current
			DESCRIPTION
				"Description."
			::= { fkSnmpLog 1 }

		
		-- 1.3.6.1.4.1.10428 9 1.101.8.13.1.1
		fkSnmpLogEntry OBJECT-TYPE
			SYNTAX FkSnmpLogEntry
			MAX-ACCESS not-accessible
			STATUS current
			DESCRIPTION
				"Description."
			INDEX { fkSnmpLogIndex }
			::= { fkSnmpLogTable 1 }

		
		FkSnmpLogEntry ::=
			SEQUENCE { 
				fkSnmpLogIndex
					INTEGER,
				fkSnmpLogText
					Integer32
			 }

		-- 1.3.6.1.4.1.10428 9 1.101.8.13.1.1.1
		fkSnmpLogIndex OBJECT-TYPE
			SYNTAX INTEGER (1..2000)
			MAX-ACCESS read-only
			STATUS current
			DESCRIPTION
				"The index of SNMP Trap Log"
			::= { fkSnmpLogEntry 1 }

		
		-- 1.3.6.1.4.1.10428 9 1.101.8.13.1.1.2
		fkSnmpLogText OBJECT-TYPE
			SYNTAX Integer32
			MAX-ACCESS read-only
			STATUS current
			DESCRIPTION
				"Textual description of specific problem reported by SNMP trap. To be discussed: Option is to define an SNMP trap for every problem."
			::= { fkSnmpLogEntry 2 }

		
		-- 1.3.6.1.4.1.10428 9 1.101.8.13.2
		fkSnmpLogControl OBJECT IDENTIFIER ::= { fkSnmpLog 2 }

		
		-- 1.3.6.1.4.1.10428 9 1.101.8.13.2.1
		fkSnmpLogControlRequest OBJECT-TYPE
			SYNTAX INTEGER { clearSnmpLog(1) }
			MAX-ACCESS read-write
			STATUS current
			DESCRIPTION
				"Description."
			::= { fkSnmpLogControl 1 }

		
		-- 1.3.6.1.4.1.10428 9 1.101.8.13.2.2
		fkSnmpLogControlStatus OBJECT-TYPE
			SYNTAX Integer32
			MAX-ACCESS read-only
			STATUS current
			DESCRIPTION
				"Description."
			::= { fkSnmpLogControl 2 }

		
		-- 1.3.6.1.4.1.10428 9 1.101.8.13.2.3
		fkSnmpLogControlTimer OBJECT-TYPE
			SYNTAX Gauge32
			MAX-ACCESS read-write
			STATUS current
			DESCRIPTION
				"Description."
			::= { fkSnmpLogControl 3 }

		
		-- 1.3.6.1.4.1.10428 9 1.101.8.13.2.4
		fkSnmpLogControlTimeStamp OBJECT-TYPE
			SYNTAX TimeTicks
			MAX-ACCESS read-only
			STATUS current
			DESCRIPTION
				"Description."
			::= { fkSnmpLogControl 4 }

		
		-- 1.3.6.1.4.1.10428 9 1.101.8.13.2.5
		fkSnmpLogControlReqResult OBJECT-TYPE
			SYNTAX Integer32
			MAX-ACCESS read-only
			STATUS current
			DESCRIPTION
				"Result of the last command."
			::= { fkSnmpLogControl 5 }

		
		-- 1.3.6.1.4.1.10428 9 1.101.8.13.3
		fkSnmpLogNotifications OBJECT IDENTIFIER ::= { fkSnmpLog 3 }

		
		-- 1.3.6.1.4.1.10428 9 1.101.8.13.3.1
		fkSnmpLogCleared NOTIFICATION-TYPE
			OBJECTS { fkSnmpLogControlRequest, fkSnmpLogControlTimeStamp, fkSnmpLogControlReqResult }
			STATUS current
			DESCRIPTION 
				"Description."
			::= { fkSnmpLogNotifications 1 }

		
-- 
--  fkTrapHost
		-- 1.3.6.1.4.1.10428 9 1.101.8.14
		fkTrapHostDomainName OBJECT IDENTIFIER ::= { fkSnmp 14 }

		
		-- 1.3.6.1.4.1.10428 9 1.101.8.14.1
		fkTrapHostDNTable OBJECT-TYPE
			SYNTAX SEQUENCE OF FkTrapHostDNEntry
			MAX-ACCESS not-accessible
			STATUS current
			DESCRIPTION
				"Description."
			::= { fkTrapHostDomainName 1 }

		
		-- 1.3.6.1.4.1.10428 9 1.101.8.14.1.1
		fkTrapHostDNEntry OBJECT-TYPE
			SYNTAX FkTrapHostDNEntry
			MAX-ACCESS not-accessible
			STATUS current
			DESCRIPTION
				"Description."
			INDEX { fkTrapHostDNName }
			::= { fkTrapHostDNTable 1 }

		
		FkTrapHostDNEntry ::=
			SEQUENCE { 
				fkTrapHostDNType
					INTEGER,
				fkTrapHostDNName
					OCTET STRING,
				fkTrapHostDNCommunity
					OCTET STRING
			 }

		-- 1.3.6.1.4.1.10428 9 1.101.8.14.1.1.1
		fkTrapHostDNType OBJECT-TYPE
			SYNTAX INTEGER
				{
				trapHost(1),
				trap2Host(2),
				informTrapHost(3)
				}
			MAX-ACCESS read-only
			STATUS current
			DESCRIPTION
				"The snmp trap host type."
			::= { fkTrapHostDNEntry 1 }

		
		-- 1.3.6.1.4.1.10428 9 1.101.8.14.1.1.2
		fkTrapHostDNName OBJECT-TYPE
			SYNTAX OCTET STRING (SIZE (1..512))
			MAX-ACCESS read-only
			STATUS current
			DESCRIPTION
				"The snmp trap host domain-name"
			::= { fkTrapHostDNEntry 2 }

		
		-- 1.3.6.1.4.1.10428 9 1.101.8.14.1.1.3
		fkTrapHostDNCommunity OBJECT-TYPE
			SYNTAX OCTET STRING
			MAX-ACCESS read-only
			STATUS current
			DESCRIPTION
				"The trap host commnity"
			::= { fkTrapHostDNEntry 3 }

		
		-- 1.3.6.1.4.1.10428 9 1.101.8.14.2
		fkTrapHostDNControl OBJECT IDENTIFIER ::= { fkTrapHostDomainName 2 }

		
		-- 1.3.6.1.4.1.10428 9 1.101.8.14.2.1
		fkTrapHostDNControlRequest OBJECT-TYPE
			SYNTAX INTEGER
				{
				createTrapHost(1),
				destroyTrapHost(2)
				}
			MAX-ACCESS read-write
			STATUS current
			DESCRIPTION
				"setInformTrapConf"
			::= { fkTrapHostDNControl 1 }

		
		-- 1.3.6.1.4.1.10428 9 1.101.8.14.2.2
		fkTrapHostDNControlStatus OBJECT-TYPE
			SYNTAX Integer32
			MAX-ACCESS read-only
			STATUS current
			DESCRIPTION
				"Description."
			::= { fkTrapHostDNControl 2 }

		
		-- 1.3.6.1.4.1.10428 9 1.101.8.14.2.3
		fkTrapHostDNControlTimer OBJECT-TYPE
			SYNTAX Gauge32
			MAX-ACCESS read-write
			STATUS current
			DESCRIPTION
				"Description."
			::= { fkTrapHostDNControl 3 }

		
		-- 1.3.6.1.4.1.10428 9 1.101.8.14.2.4
		fkTrapHostDNControlTimeStamp OBJECT-TYPE
			SYNTAX TimeTicks
			MAX-ACCESS read-only
			STATUS current
			DESCRIPTION
				"Description."
			::= { fkTrapHostDNControl 4 }

		
		-- 1.3.6.1.4.1.10428 9 1.101.8.14.2.5
		fkTrapHostDNControlReqResult OBJECT-TYPE
			SYNTAX Integer32
			MAX-ACCESS read-only
			STATUS current
			DESCRIPTION
				"Description."
			::= { fkTrapHostDNControl 5 }

		
		-- 1.3.6.1.4.1.10428 9 1.101.8.14.2.6
		fkTrapHostDNControlType OBJECT-TYPE
			SYNTAX INTEGER
				{
				trapHost(1),
				trap2Host(2),
				informTrapHost(3)
				}
			MAX-ACCESS read-write
			STATUS current
			DESCRIPTION
				"The snmp trap host type."
			::= { fkTrapHostDNControl 6 }

		
		-- 1.3.6.1.4.1.10428 9 1.101.8.14.2.7
		fkTrapHostDNControlName OBJECT-TYPE
			SYNTAX OCTET STRING (SIZE (1..512))
			MAX-ACCESS read-write
			STATUS current
			DESCRIPTION
				"The snmp trap host domain-name"
			::= { fkTrapHostDNControl 7 }

		
		-- 1.3.6.1.4.1.10428 9 1.101.8.14.2.8
		fkTrapHostDNControlCommunity OBJECT-TYPE
			SYNTAX OCTET STRING
			MAX-ACCESS read-write
			STATUS current
			DESCRIPTION
				"The trap host commnity"
			::= { fkTrapHostDNControl 8 }

		
		-- 1.3.6.1.4.1.10428 9 1.101.8.14.3
		fkTrapHostDNNotification OBJECT IDENTIFIER ::= { fkTrapHostDomainName 3 }

		
		-- 1.3.6.1.4.1.10428 9 1.101.8.14.3.1
		fkTrapHostDNCreated NOTIFICATION-TYPE
			OBJECTS { fkTrapHostDNControlRequest, fkTrapHostDNControlTimeStamp, fkTrapHostDNControlReqResult, fkTrapHostDNControlType, fkTrapHostDNControlName, 
				fkTrapHostDNControlCommunity }
			STATUS current
			DESCRIPTION 
				"createTrapHost"
			::= { fkTrapHostDNNotification 1 }

		
		-- 1.3.6.1.4.1.10428 9 1.101.8.14.3.2
		fkTrapHostDNDestroyed NOTIFICATION-TYPE
			OBJECTS { fkTrapHostDNControlRequest, fkTrapHostDNControlTimeStamp, fkTrapHostDNControlReqResult, fkTrapHostDNControlType, fkTrapHostDNControlName
				 }
			STATUS current
			DESCRIPTION 
				"destroyTrapHost"
			::= { fkTrapHostDNNotification 2 }

		
		-- 1.3.6.1.4.1.10428 9 1.101.8.15
		fkSnmpPing OBJECT IDENTIFIER ::= { fkSnmp 15 }
-- The ping MIB for LG U+
		
		-- 1.3.6.1.4.1.10428 9 1.101.8.15.1
		fkSnmpPingTable OBJECT IDENTIFIER ::= { fkSnmpPing 1 }

		
		-- 1.3.6.1.4.1.10428 9 1.101.8.15.1.1
		fkSnmpPingSourceIp OBJECT-TYPE
			SYNTAX OCTET STRING
			MAX-ACCESS read-only
			STATUS current
			DESCRIPTION
				"The source Ip address."
			::= { fkSnmpPingTable 1 }

		
		-- 1.3.6.1.4.1.10428 9 1.101.8.15.1.2
		fkSnmpPingDestinationIp OBJECT-TYPE
			SYNTAX OCTET STRING
			MAX-ACCESS read-only
			STATUS current
			DESCRIPTION
				"The destination Ip address."
			::= { fkSnmpPingTable 2 }

		
		-- 1.3.6.1.4.1.10428 9 1.101.8.15.1.3
		fkSnmpPingPacketLossResult OBJECT-TYPE
			SYNTAX Integer32
			MAX-ACCESS read-only
			STATUS current
			DESCRIPTION
				"The result of packet loss.(%)"
			::= { fkSnmpPingTable 3 }

		
		-- 1.3.6.1.4.1.10428 9 1.101.8.15.2
		fkSnmpPingControl OBJECT IDENTIFIER ::= { fkSnmpPing 2 }

		
		-- 1.3.6.1.4.1.10428 9 1.101.8.15.2.1
		fkSnmpPingControlRequest OBJECT-TYPE
			SYNTAX INTEGER
				{
				setPingDefault(1),
				setPingWithSourceIp(2)
				}
			MAX-ACCESS read-write
			STATUS current
			DESCRIPTION
				"setInformTrapConf"
			::= { fkSnmpPingControl 1 }

		
		-- 1.3.6.1.4.1.10428 9 1.101.8.15.2.2
		fkSnmpPingControlStatus OBJECT-TYPE
			SYNTAX Integer32
			MAX-ACCESS read-only
			STATUS current
			DESCRIPTION
				"Description."
			::= { fkSnmpPingControl 2 }

		
		-- 1.3.6.1.4.1.10428 9 1.101.8.15.2.3
		fkSnmpPingControlTimer OBJECT-TYPE
			SYNTAX Gauge32
			MAX-ACCESS read-write
			STATUS current
			DESCRIPTION
				"Description."
			::= { fkSnmpPingControl 3 }

		
		-- 1.3.6.1.4.1.10428 9 1.101.8.15.2.4
		fkSnmpPingControlTimeStamp OBJECT-TYPE
			SYNTAX TimeTicks
			MAX-ACCESS read-only
			STATUS current
			DESCRIPTION
				"Description."
			::= { fkSnmpPingControl 4 }

		
		-- 1.3.6.1.4.1.10428 9 1.101.8.15.2.5
		fkSnmpPingControlReqResult OBJECT-TYPE
			SYNTAX Integer32
			MAX-ACCESS read-only
			STATUS current
			DESCRIPTION
				"Description."
			::= { fkSnmpPingControl 5 }

		
		-- 1.3.6.1.4.1.10428 9 1.101.8.15.2.6
		fkSnmpPingControlSourceIp OBJECT-TYPE
			SYNTAX OCTET STRING
			MAX-ACCESS read-write
			STATUS current
			DESCRIPTION
				"The source Ip address."
			::= { fkSnmpPingControl 6 }

		
		-- 1.3.6.1.4.1.10428 9 1.101.8.15.2.7
		fkSnmpPingControlDestinationIp OBJECT-TYPE
			SYNTAX OCTET STRING
			MAX-ACCESS read-write
			STATUS current
			DESCRIPTION
				"The destination Ip address."
			::= { fkSnmpPingControl 7 }

		
		-- 1.3.6.1.4.1.10428 9 1.101.8.15.3
		fkSnmpPingNotification OBJECT IDENTIFIER ::= { fkSnmpPing 3 }

		
		-- 1.3.6.1.4.1.10428 9 1.101.8.15.3.1
		fkSnmpPingDefaultChanged NOTIFICATION-TYPE
			OBJECTS { fkSnmpPingControlRequest, fkSnmpPingControlTimeStamp, fkSnmpPingControlReqResult, fkSnmpPingControlDestinationIp, fkSnmpPingPacketLossResult
				 }
			STATUS current
			DESCRIPTION 
				"setPingDefault."
			::= { fkSnmpPingNotification 1 }

		
		-- 1.3.6.1.4.1.10428 9 1.101.8.15.3.2
		fkSnmpPingWithSourceIpChanged NOTIFICATION-TYPE
			OBJECTS { fkSnmpPingControlRequest, fkSnmpPingControlTimeStamp, fkSnmpPingControlReqResult, fkSnmpPingControlSourceIp, fkSnmpPingControlDestinationIp, 
				fkSnmpPingPacketLossResult }
			STATUS current
			DESCRIPTION 
				"setPingWithSourceIp"
			::= { fkSnmpPingNotification 2 }

		
		-- 1.3.6.1.4.1.10428 9 1.101.8.16
		fkSnmpGroup OBJECT-GROUP
			OBJECTS { fkSnmpSysContact, fkSnmpControlRequest, fkSnmpControlStatus, fkSnmpControlTimer, fkSnmpControlTimeStamp, 
				fkSnmpControlReqResult, fkSnmpControlSysContact, fkCom2SecName, fkCom2SecHost, fkCom2SecHostMaskLen, 
				fkCom2SecCommunity, fkCom2SecControlRequest, fkCom2SecControlStatus, fkCom2SecControlTimer, fkCom2SecControlTimeStamp, 
				fkCom2SecControlReqResult, fkCom2SecControlName, fkCom2SecControlHost, fkCom2secControlHostMaskLen, fkCom2SecControlCommunity, 
				fkTrapHostType, fkTrapHostAddress, fkTrapHostCommunity, fkTrapHostPort, fkTrapHostControlRequest, 
				fkTrapHostControlStatus, fkTrapHostControlTimer, fkTrapHostControlTimeStamp, fkTrapHostControlReqResult, fkTrapHostControlType, 
				fkTrapHostControlAddress, fkTrapHostControlCommunity, fkTrapHostControlPort, fkCommunityType, fkCommunityValue, 
				fkCommunityHost, fkCommunityOID, fkCommunityHostMaskLen, fkCommunityControlRequest, fkCommunityControlStatus, 
				fkCommunityControlTimer, fkCommunityControlTimeStamp, fkCommunityControlReqResult, fkCommunityControlType, fkCommunityControlValue, 
				fkCommunityControlHost, fkCommunityControlOID, fkCommunityControlHostMaskLen, fkViewTreeFamilyName, fkViewTreeFamilySubtree, 
				fkViewTreeFamilyMask, fkViewTreeFamilyType, fkViewTreeFamilyControlRequest, fkViewTreeFamilyControlStatus, fkViewTreeFamilyControlTimer, 
				fkViewTreeFamilyControlTimeStamp, fkViewTreeFamilyControlReqResult, fkViewTreeFamilyControlName, fkViewTreeFamilyControlSubtree, fkViewTreeFamilyControlMask, 
				fkViewTreeFamilyControlType, fkAccessGroupName, fkAccessSecurityModel, fkAccessSecurityLevel, fkAccessReadViewName, 
				fkAccessWriteViewName, fkAccessNotifyViewName, fkAccessControlRequest, fkAccessControlStatus, fkAccessControlTimer, 
				fkAccessControlTimeStamp, fkAccessControlReqResult, fkAccessControlGroupName, fkAccessControlSecurityModel, fkAccessControlSecurityLevel, 
				fkAccessControlReadViewName, fkAccessControlWriteViewName, fkAccessControlNotifyViewName, fkSecurityToGroupGName, fkSnmpLogStatus, 
				fkSnmpControlLogStatus, fkSnmpLogIndex, fkSnmpLogText, fkSnmpLogControlRequest, fkSnmpLogControlStatus, 
				fkSnmpLogControlTimer, fkSnmpLogControlTimeStamp, fkSnmpLogControlReqResult, fkSecurityToGroupModel, fkSecurityToGroupSName, 
				fkSecurityToGroupControlRequest, fkSecurityToGroupControlStatus, fkSecurityToGroupControlTimer, fkSecurityToGroupControlTimeStamp, fkSecurityToGroupControlReqResult, 
				fkSecurityToGroupControlGName, fkSecurityToGroupControlModel, fkSecurityToGroupControlSName, fkUserName, fkUserAuthType, 
				fkUserAuthKey, fkUserPrivType, fkUserPrivKey, fkUserControlRequest, fkUserControlStatus, 
				fkUserControlTimer, fkUserControlTimeStamp, fkUserControlReqResult, fkUserControlName, fkUserControlAuthType, 
				fkUserControlAuthKey, fkUserControlPrivType, fkUserControlPrivKey, fkAgentAddress, fkAgentInterface, 
				fkAgentControlRequest, fkAgentControlStatus, fkAgentControlTimer, fkAgentControlTimeStamp, fkAgentControlReqResult, 
				fkAgentControlAddress, fkAgentControlInterface, fkSnmpSessionTimeout, fkSnmpSessionIpAddr, fkSnmpSessionCommunity, 
				fkSnmpSessionSnmpVersion, fkSnmpSessionAccessTIme, fkSnmpSessionControlRequest, fkSnmpSessionControlStatus, fkSnmpSessionControlTimer, 
				fkSnmpSessionControlTimeStamp, fkSnmpSessionControlReqResult, fkSnmpSessionControlTimeout, fkSnmpTrapIndex, fkSnmpTrapStatus, 
				fkSnmpTrapPortIndex, fkSnmpTrapPortType, fkSnmpTrapPortStatus, fkSnmpTrapControlRequest, fkSnmpTrapControlStatus, 
				fkSnmpTrapControlTimer, fkSnmpTrapControlTimeStamp, fkSnmpTrapControlReqResult, fkSnmpTrapControlTrapIndex, fkSnmpTrapControlPortIndex, 
				fkSnmpTrapControlTrapStatus, fkSnmpTrapSourceAddress, fkSnmpTrapSourceInterface, fkSnmpTrapSourceControlRequest, fkSnmpTrapSourceControlStatus, 
				fkSnmpTrapSourceControlTimer, fkSnmpTrapSourceControlTimeStamp, fkSnmpTrapSourceControlReqResult, fkSnmpTrapSourceControlAddress, fkSnmpConnectionType, 
				fkSnmpControlConnectionType, fkSnmpTrapSourceControlInterface, fkSnmpSysLocation, fkSnmpPingSourceIp, fkSnmpPingDestinationIp, 
				fkSnmpPingControlRequest, fkSnmpPingControlStatus, fkSnmpPingControlTimer, fkSnmpPingControlTimeStamp, fkSnmpPingControlReqResult, 
				fkSnmpPingControlSourceIp, fkSnmpPingControlDestinationIp, fkSnmpControlSysLocation, fkSnmpInformTrapRetry, fksnmpInformTrapInterval, 
				fkSnmpControlInformTrapRetry, fkSnmpControlInformTrapInterval, fkTrapHostDNType, fkTrapHostDNName, fkTrapHostDNCommunity, 
				fkTrapHostDNControlRequest, fkTrapHostDNControlStatus, fkTrapHostDNControlTimer, fkTrapHostDNControlTimeStamp, fkTrapHostDNControlReqResult, 
				fkTrapHostDNControlType, fkTrapHostDNControlName, fkTrapHostDNControlCommunity, fkSnmpPingPacketLossResult }
			STATUS current
			DESCRIPTION 
				"Description."
			::= { fkSnmp 16 }

		
		-- 1.3.6.1.4.1.10428 9 1.101.8.17
		fkSnmpNotificationGroup NOTIFICATION-GROUP
			NOTIFICATIONS { fkSnmpSysInfoProfileChanged, fkCom2SecCreated, fkCom2SecDestroyed, fkCom2SecProfileChanged, fkTrapHostCreated, 
				fkTrapHostDestroyed, fkCommunityCreated, fkCommunityDestroyed, fkViewTreeFamilyCreated, fkViewTreeFamilyDestroyed, 
				fkAccessCreated, fkAccessDestroyed, fkAccessProfileChanged, fkUserCreated, fkUserDestroyed, 
				fkAgentAddressChanged, fkAgentInterfaceChanged, fkAgentAddressDestroyed, fkAgentInterfaceDestroyed, fkSnmpSessionTimeoutChanged, 
				fkSnmpTrapStatusChanged, fkSnmpTrapPortStatusChanged, fkSnmpTrapSourceInterfaceChanged, fkSnmpTrapSourcetAddressDestroyed, fkSnmpTrapSourceInterfaceDestroyed, 
				fkSnmpTrapSourceAddressChanged, fkSecurityToGroupProfileChanged, fkSnmpSysInfoLogStatusChanged, fkSnmpLogCleared, fkSnmpSysInfoConnectionTypeChanged, 
				fkSecurityToGroupDestroyed, fkTrapHostDNCreated, fkTrapHostDNDestroyed, fkSnmpPingDefaultChanged, fkSnmpPingWithSourceIpChanged, 
				fkSecurityToGroupCreated, fkSnmpInformTrapConfChanged }
			STATUS current
			DESCRIPTION 
				"Description."
			::= { fkSnmp 17 }

		
	
	END

--
-- fk-snmp-mib.mib
--
