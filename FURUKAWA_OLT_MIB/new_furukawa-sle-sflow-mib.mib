--
-- FK-SFLOW-MIB.my
-- MIB generated by MG-SOFT Visual MIB Builder Version 3.0 Build 285
-- Friday, June 09, 2006 at 14:03:22
--

	FK-SFLOW-MIB DEFINITIONS ::= BEGIN
 
		IMPORTS
			fkMgmt			
				FROM FKOLTG1040-SMI			
			InterfaceIndex			
				FROM IF-MIB			
			FkControlStatusType, FkControlRequestResultType			
				FROM FK-TC-MIB			
			OBJECT-GROUP, NOTIFICATION-GROUP			
				FROM SNMPv2-CONF			
			TimeTicks, IpAddress, Gauge32, OBJECT-TYPE, MODULE-IDENTITY, 
			NOTIFICATION-TYPE			
				FROM SNMPv2-SMI;
	
	
		-- 1.3.6.1.4.1.10428 9 1.101.21
		fkSFlow MODULE-IDENTITY 
			LAST-UPDATED "200605181609Z"		-- May 18, 2006 at 16:09 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 21 }

		
	
	
--
-- Node definitions
--
	
		-- 1.3.6.1.4.1.10428 9 1.101.21.1
		fkSFlowBase OBJECT IDENTIFIER::= { fkSFlow 1 }

		
		-- 1.3.6.1.4.1.10428 9 1.101.21.1.1
		fkSFlowInfo OBJECT IDENTIFIER::= { fkSFlowBase 1 }

		
		-- 1.3.6.1.4.1.10428 9 1.101.21.1.1.1
		fkSFlowEnable OBJECT-TYPE
			SYNTAX INTEGER
				{
				disable(0),
				enable(1)
				}
			MAX-ACCESS read-only
			STATUS current
			DESCRIPTION
				"Description."
			::= { fkSFlowInfo 1 }

		
		-- 1.3.6.1.4.1.10428 9 1.101.21.1.1.2
		fkSFlowVersion OBJECT-TYPE
			SYNTAX OCTET STRING
			MAX-ACCESS read-only
			STATUS current
			DESCRIPTION
				"Description."
			::= { fkSFlowInfo 2 }

		
		-- 1.3.6.1.4.1.10428 9 1.101.21.1.1.3
		fkSFlowAgentAddress OBJECT-TYPE
			SYNTAX IpAddress
			MAX-ACCESS read-only
			STATUS current
			DESCRIPTION
				"Description."
			::= { fkSFlowInfo 3 }

		
		-- 1.3.6.1.4.1.10428 9 1.101.21.1.1.4
		fkSFlowMaxInstance OBJECT-TYPE
			SYNTAX INTEGER (1..65535)
			MAX-ACCESS read-only
			STATUS current
			DESCRIPTION
				"Description."
			::= { fkSFlowInfo 4 }

		
		-- 1.3.6.1.4.1.10428 9 1.101.21.1.2
		fkSFlowControl OBJECT IDENTIFIER::= { fkSFlowBase 2 }

		
		-- 1.3.6.1.4.1.10428 9 1.101.21.1.2.1
		fkSFlowControlRequest OBJECT-TYPE
			SYNTAX INTEGER
				{
				setSFlowEnable(1),
				setSFlowAgentAddress(2)
				}
			MAX-ACCESS read-write
			STATUS current
			DESCRIPTION
				"Description."
			::= { fkSFlowControl 1 }

		
		-- 1.3.6.1.4.1.10428 9 1.101.21.1.2.2
		fkSFlowControlStatus OBJECT-TYPE
			SYNTAX FkControlStatusType
			MAX-ACCESS read-write
			STATUS current
			DESCRIPTION
				"Description."
			::= { fkSFlowControl 2 }

		
		-- 1.3.6.1.4.1.10428 9 1.101.21.1.2.3
		fkSFlowControlTimer OBJECT-TYPE
			SYNTAX Gauge32
			MAX-ACCESS read-write
			STATUS current
			DESCRIPTION
				"Description."
			::= { fkSFlowControl 3 }

		
		-- 1.3.6.1.4.1.10428 9 1.101.21.1.2.4
		fkSFlowControlTimeStamp OBJECT-TYPE
			SYNTAX TimeTicks
			MAX-ACCESS read-write
			STATUS current
			DESCRIPTION
				"Description."
			::= { fkSFlowControl 4 }

		
		-- 1.3.6.1.4.1.10428 9 1.101.21.1.2.5
		fkSFlowControlReqResult OBJECT-TYPE
			SYNTAX FkControlRequestResultType
			MAX-ACCESS read-write
			STATUS current
			DESCRIPTION
				"Description."
			::= { fkSFlowControl 5 }

		
		-- 1.3.6.1.4.1.10428 9 1.101.21.1.2.6
		fkSFlowControlEnable OBJECT-TYPE
			SYNTAX INTEGER
				{
				disable(0),
				enable(1)
				}
			MAX-ACCESS read-write
			STATUS current
			DESCRIPTION
				"Description."
			::= { fkSFlowControl 6 }

		
		-- 1.3.6.1.4.1.10428 9 1.101.21.1.2.7
		fkSFlowControlAgentAddress OBJECT-TYPE
			SYNTAX IpAddress
			MAX-ACCESS read-write
			STATUS current
			DESCRIPTION
				"Description."
			::= { fkSFlowControl 7 }

		
		-- 1.3.6.1.4.1.10428 9 1.101.21.1.3
		fkSFlowNotification OBJECT IDENTIFIER::= { fkSFlowBase 3 }

		
		-- 1.3.6.1.4.1.10428 9 1.101.21.1.3.1
		fkSFlowEnableChanged NOTIFICATION-TYPE
			OBJECTS { fkSFlowControlRequest, fkSFlowControlTimeStamp, fkSFlowControlReqResult, fkSFlowEnable }
			STATUS current
			DESCRIPTION 
				"Description."
			::= { fkSFlowNotification 1 }

		
		-- 1.3.6.1.4.1.10428 9 1.101.21.1.3.2
		fkSFlowAgentAddressChanged NOTIFICATION-TYPE
			OBJECTS { fkSFlowControlRequest, fkSFlowControlTimeStamp, fkSFlowControlReqResult, fkSFlowAgentAddress }
			STATUS current
			DESCRIPTION 
				"Description."
			::= { fkSFlowNotification 2 }

		
		-- 1.3.6.1.4.1.10428 9 1.101.21.2
		fkSFlowRcvr OBJECT IDENTIFIER::= { fkSFlow 2 }

		
		-- 1.3.6.1.4.1.10428 9 1.101.21.2.1
		fkSFlowRcvrTable OBJECT-TYPE
			SYNTAX SEQUENCE OF FkSFlowRcvrEntry
			MAX-ACCESS not-accessible
			STATUS current
			DESCRIPTION
				"Description."
			::= { fkSFlowRcvr 1 }

		
		-- 1.3.6.1.4.1.10428 9 1.101.21.2.1.1
		fkSFlowRcvrEntry OBJECT-TYPE
			SYNTAX FkSFlowRcvrEntry
			MAX-ACCESS not-accessible
			STATUS current
			DESCRIPTION
				"Description."
			INDEX { fkSFlowRcvrIndex }
			::= { fkSFlowRcvrTable 1 }

		
		FkSFlowRcvrEntry ::=
			SEQUENCE { 
				fkSFlowRcvrIndex
					INTEGER,
				fkSFlowRcvrOwner
					OCTET STRING,
				fkSFlowRcvrTimeout
					INTEGER,
				fkSFlowRcvrMaxDatagramSize
					INTEGER,
				fkSFlowRcvrAddress
					IpAddress,
				fkSFlowRcvrPort
					INTEGER,
				fkSFlowRcvrDatagramVersion
					INTEGER
			 }

		-- 1.3.6.1.4.1.10428 9 1.101.21.2.1.1.1
		fkSFlowRcvrIndex OBJECT-TYPE
			SYNTAX INTEGER (1..65535)
			MAX-ACCESS read-only
			STATUS current
			DESCRIPTION
				"Description."
			::= { fkSFlowRcvrEntry 1 }

		
		-- 1.3.6.1.4.1.10428 9 1.101.21.2.1.1.2
		fkSFlowRcvrOwner OBJECT-TYPE
			SYNTAX OCTET STRING (SIZE (0..127))
			MAX-ACCESS read-only
			STATUS current
			DESCRIPTION
				"Description."
			::= { fkSFlowRcvrEntry 2 }

		
		-- 1.3.6.1.4.1.10428 9 1.101.21.2.1.1.3
		fkSFlowRcvrTimeout OBJECT-TYPE
			SYNTAX INTEGER (0..2147483647)
			MAX-ACCESS read-only
			STATUS current
			DESCRIPTION
				"Description."
			DEFVAL { 0 }
			::= { fkSFlowRcvrEntry 3 }

		
		-- 1.3.6.1.4.1.10428 9 1.101.21.2.1.1.4
		fkSFlowRcvrMaxDatagramSize OBJECT-TYPE
			SYNTAX INTEGER (256..1400)
			MAX-ACCESS read-only
			STATUS current
			DESCRIPTION
				"Description."
			DEFVAL { 1400 }
			::= { fkSFlowRcvrEntry 4 }

		
		-- 1.3.6.1.4.1.10428 9 1.101.21.2.1.1.5
		fkSFlowRcvrAddress OBJECT-TYPE
			SYNTAX IpAddress
			MAX-ACCESS read-only
			STATUS current
			DESCRIPTION
				"Description."
			::= { fkSFlowRcvrEntry 5 }

		
		-- 1.3.6.1.4.1.10428 9 1.101.21.2.1.1.6
		fkSFlowRcvrPort OBJECT-TYPE
			SYNTAX INTEGER (1..65535)
			MAX-ACCESS read-only
			STATUS current
			DESCRIPTION
				"Description."
			DEFVAL { 6343 }
			::= { fkSFlowRcvrEntry 6 }

		
		-- 1.3.6.1.4.1.10428 9 1.101.21.2.1.1.7
		fkSFlowRcvrDatagramVersion OBJECT-TYPE
			SYNTAX INTEGER { version5(5) }
			MAX-ACCESS read-only
			STATUS current
			DESCRIPTION
				"Description."
			::= { fkSFlowRcvrEntry 7 }

		
		-- 1.3.6.1.4.1.10428 9 1.101.21.2.2
		fkSFlowRcvrControl OBJECT IDENTIFIER::= { fkSFlowRcvr 2 }

		
		-- 1.3.6.1.4.1.10428 9 1.101.21.2.2.1
		fkSFlowRcvrControlRequest OBJECT-TYPE
			SYNTAX INTEGER
				{
				createSFlowRcvr(1),
				setSFlowRcvr(2),
				destroySFlowRcvr(3)
				}
			MAX-ACCESS read-write
			STATUS current
			DESCRIPTION
				"Description."
			::= { fkSFlowRcvrControl 1 }

		
		-- 1.3.6.1.4.1.10428 9 1.101.21.2.2.2
		fkSFlowRcvrControlStatus OBJECT-TYPE
			SYNTAX FkControlStatusType
			MAX-ACCESS read-write
			STATUS current
			DESCRIPTION
				"Description."
			::= { fkSFlowRcvrControl 2 }

		
		-- 1.3.6.1.4.1.10428 9 1.101.21.2.2.3
		fkSFlowRcvrControlTimer OBJECT-TYPE
			SYNTAX Gauge32
			MAX-ACCESS read-write
			STATUS current
			DESCRIPTION
				"Description."
			::= { fkSFlowRcvrControl 3 }

		
		-- 1.3.6.1.4.1.10428 9 1.101.21.2.2.4
		fkSFlowRcvrControlTimeStamp OBJECT-TYPE
			SYNTAX TimeTicks
			MAX-ACCESS read-write
			STATUS current
			DESCRIPTION
				"Description."
			::= { fkSFlowRcvrControl 4 }

		
		-- 1.3.6.1.4.1.10428 9 1.101.21.2.2.5
		fkSFlowRcvrControlReqResult OBJECT-TYPE
			SYNTAX FkControlRequestResultType
			MAX-ACCESS read-write
			STATUS current
			DESCRIPTION
				"Description."
			::= { fkSFlowRcvrControl 5 }

		
		-- 1.3.6.1.4.1.10428 9 1.101.21.2.2.6
		fkSFlowRcvrControlIndex OBJECT-TYPE
			SYNTAX INTEGER (1..65535)
			MAX-ACCESS read-write
			STATUS current
			DESCRIPTION
				"Description."
			::= { fkSFlowRcvrControl 6 }

		
		-- 1.3.6.1.4.1.10428 9 1.101.21.2.2.7
		fkSFlowRcvrControlOwner OBJECT-TYPE
			SYNTAX OCTET STRING (SIZE (0..127))
			MAX-ACCESS read-write
			STATUS current
			DESCRIPTION
				"Description."
			::= { fkSFlowRcvrControl 7 }

		
		-- 1.3.6.1.4.1.10428 9 1.101.21.2.2.8
		fkSFlowRcvrControlTimeout OBJECT-TYPE
			SYNTAX INTEGER (0..2147483647)
			MAX-ACCESS read-write
			STATUS current
			DESCRIPTION
				"Description."
			DEFVAL { 0 }
			::= { fkSFlowRcvrControl 8 }

		
		-- 1.3.6.1.4.1.10428 9 1.101.21.2.2.9
		fkSFlowRcvrControlMaxDatagramSize OBJECT-TYPE
			SYNTAX INTEGER (256..1400)
			MAX-ACCESS read-write
			STATUS current
			DESCRIPTION
				"Description."
			DEFVAL { 1400 }
			::= { fkSFlowRcvrControl 9 }

		
		-- 1.3.6.1.4.1.10428 9 1.101.21.2.2.10
		fkSFlowRcvrControlAddress OBJECT-TYPE
			SYNTAX IpAddress
			MAX-ACCESS read-write
			STATUS current
			DESCRIPTION
				"Description."
			::= { fkSFlowRcvrControl 10 }

		
		-- 1.3.6.1.4.1.10428 9 1.101.21.2.2.11
		fkSFlowRcvrControlPort OBJECT-TYPE
			SYNTAX INTEGER (1..65535)
			MAX-ACCESS read-only
			STATUS current
			DESCRIPTION
				"Description."
			DEFVAL { 6343 }
			::= { fkSFlowRcvrControl 11 }

		
		-- 1.3.6.1.4.1.10428 9 1.101.21.2.3
		fkSFlowRcvrNotification OBJECT IDENTIFIER::= { fkSFlowRcvr 3 }

		
		-- 1.3.6.1.4.1.10428 9 1.101.21.2.3.1
		fkSFlowRcvrCreated NOTIFICATION-TYPE
			OBJECTS { fkSFlowRcvrControlRequest, fkSFlowRcvrControlTimeStamp, fkSFlowRcvrControlReqResult, fkSFlowRcvrOwner, fkSFlowRcvrTimeout, 
				fkSFlowRcvrMaxDatagramSize, fkSFlowRcvrAddress, fkSFlowRcvrPort, fkSFlowRcvrDatagramVersion }
			STATUS current
			DESCRIPTION 
				"Description."
			::= { fkSFlowRcvrNotification 1 }

		
		-- 1.3.6.1.4.1.10428 9 1.101.21.2.3.2
		fkSFlowRcvrChanged NOTIFICATION-TYPE
			OBJECTS { fkSFlowRcvrControlRequest, fkSFlowRcvrControlTimeStamp, fkSFlowRcvrControlReqResult, fkSFlowRcvrOwner, fkSFlowRcvrTimeout, 
				fkSFlowRcvrMaxDatagramSize, fkSFlowRcvrAddress, fkSFlowRcvrPort, fkSFlowRcvrDatagramVersion }
			STATUS current
			DESCRIPTION 
				"Description."
			::= { fkSFlowRcvrNotification 2 }

		
		-- 1.3.6.1.4.1.10428 9 1.101.21.2.3.3
		fkSFlowRcvrDestroyed NOTIFICATION-TYPE
			OBJECTS { fkSFlowRcvrControlRequest, fkSFlowRcvrControlTimeStamp, fkSFlowRcvrControlReqResult, fkSFlowRcvrControlIndex }
			STATUS current
			DESCRIPTION 
				"Description."
			::= { fkSFlowRcvrNotification 3 }

		
		-- 1.3.6.1.4.1.10428 9 1.101.21.3
		fkSFlowFs OBJECT IDENTIFIER::= { fkSFlow 3 }

		
		-- 1.3.6.1.4.1.10428 9 1.101.21.3.1
		fkSFlowFsTable OBJECT-TYPE
			SYNTAX SEQUENCE OF FkSFlowFsEntry
			MAX-ACCESS not-accessible
			STATUS current
			DESCRIPTION
				"Description."
			::= { fkSFlowFs 1 }

		
		-- 1.3.6.1.4.1.10428 9 1.101.21.3.1.1
		fkSFlowFsEntry OBJECT-TYPE
			SYNTAX FkSFlowFsEntry
			MAX-ACCESS not-accessible
			STATUS current
			DESCRIPTION
				"Description."
			INDEX { fkSFlowFsDataSource, fkSFlowFsInstance }
			::= { fkSFlowFsTable 1 }

		
		FkSFlowFsEntry ::=
			SEQUENCE { 
				fkSFlowFsDataSource
					InterfaceIndex,
				fkSFlowFsInstance
					INTEGER,
				fkSFlowFsReceiver
					INTEGER,
				fkSFlowFsPacketSamplingRate
					INTEGER,
				fkSFlowFsMaxHeaderSize
					INTEGER
			 }

		-- 1.3.6.1.4.1.10428 9 1.101.21.3.1.1.1
		fkSFlowFsDataSource OBJECT-TYPE
			SYNTAX InterfaceIndex
			MAX-ACCESS read-only
			STATUS current
			DESCRIPTION
				"Description."
			::= { fkSFlowFsEntry 1 }

		
		-- 1.3.6.1.4.1.10428 9 1.101.21.3.1.1.2
		fkSFlowFsInstance OBJECT-TYPE
			SYNTAX INTEGER (1..65535)
			MAX-ACCESS read-only
			STATUS current
			DESCRIPTION
				"Description."
			::= { fkSFlowFsEntry 2 }

		
		-- 1.3.6.1.4.1.10428 9 1.101.21.3.1.1.3
		fkSFlowFsReceiver OBJECT-TYPE
			SYNTAX INTEGER (0..65535)
			MAX-ACCESS read-only
			STATUS current
			DESCRIPTION
				"Description."
			DEFVAL { 0 }
			::= { fkSFlowFsEntry 3 }

		
		-- 1.3.6.1.4.1.10428 9 1.101.21.3.1.1.4
		fkSFlowFsPacketSamplingRate OBJECT-TYPE
			SYNTAX INTEGER (0..2000)
			MAX-ACCESS read-only
			STATUS current
			DESCRIPTION
				"Description."
			DEFVAL { 0 }
			::= { fkSFlowFsEntry 4 }

		
		-- 1.3.6.1.4.1.10428 9 1.101.21.3.1.1.5
		fkSFlowFsMaxHeaderSize OBJECT-TYPE
			SYNTAX INTEGER (16..256)
			MAX-ACCESS read-only
			STATUS current
			DESCRIPTION
				"Description."
			DEFVAL { 128 }
			::= { fkSFlowFsEntry 5 }

		
		-- 1.3.6.1.4.1.10428 9 1.101.21.3.2
		fkSFlowFsControl OBJECT IDENTIFIER::= { fkSFlowFs 2 }

		
		-- 1.3.6.1.4.1.10428 9 1.101.21.3.2.1
		fkSFlowFsControlRequest OBJECT-TYPE
			SYNTAX INTEGER
				{
				createSFlowFs(1),
				setSFlowFs(2),
				destroySFlowFs(3)
				}
			MAX-ACCESS read-write
			STATUS current
			DESCRIPTION
				"Description."
			::= { fkSFlowFsControl 1 }

		
		-- 1.3.6.1.4.1.10428 9 1.101.21.3.2.2
		fkSFlowFsControlStatus OBJECT-TYPE
			SYNTAX FkControlStatusType
			MAX-ACCESS read-write
			STATUS current
			DESCRIPTION
				"Description."
			::= { fkSFlowFsControl 2 }

		
		-- 1.3.6.1.4.1.10428 9 1.101.21.3.2.3
		fkSFlowFsControlTimer OBJECT-TYPE
			SYNTAX Gauge32
			MAX-ACCESS read-write
			STATUS current
			DESCRIPTION
				"Description."
			::= { fkSFlowFsControl 3 }

		
		-- 1.3.6.1.4.1.10428 9 1.101.21.3.2.4
		fkSFlowFsControlTimeStamp OBJECT-TYPE
			SYNTAX TimeTicks
			MAX-ACCESS read-write
			STATUS current
			DESCRIPTION
				"Description."
			::= { fkSFlowFsControl 4 }

		
		-- 1.3.6.1.4.1.10428 9 1.101.21.3.2.5
		fkSFlowFsControlReqResult OBJECT-TYPE
			SYNTAX FkControlRequestResultType
			MAX-ACCESS read-write
			STATUS current
			DESCRIPTION
				"Description."
			::= { fkSFlowFsControl 5 }

		
		-- 1.3.6.1.4.1.10428 9 1.101.21.3.2.6
		fkSFlowFsControlDataSource OBJECT-TYPE
			SYNTAX InterfaceIndex
			MAX-ACCESS read-write
			STATUS current
			DESCRIPTION
				"Description."
			::= { fkSFlowFsControl 6 }

		
		-- 1.3.6.1.4.1.10428 9 1.101.21.3.2.7
		fkSFlowFsControlInstance OBJECT-TYPE
			SYNTAX INTEGER (1..65535)
			MAX-ACCESS read-write
			STATUS current
			DESCRIPTION
				"Description."
			::= { fkSFlowFsControl 7 }

		
		-- 1.3.6.1.4.1.10428 9 1.101.21.3.2.8
		fkSFlowFsControlReceiver OBJECT-TYPE
			SYNTAX INTEGER (0..65535)
			MAX-ACCESS read-write
			STATUS current
			DESCRIPTION
				"Description."
			DEFVAL { 0 }
			::= { fkSFlowFsControl 8 }

		
		-- 1.3.6.1.4.1.10428 9 1.101.21.3.2.9
		fkSFlowFsControlPacketSamplingRate OBJECT-TYPE
			SYNTAX INTEGER (0..2000)
			MAX-ACCESS read-write
			STATUS current
			DESCRIPTION
				"Description."
			DEFVAL { 0 }
			::= { fkSFlowFsControl 9 }

		
		-- 1.3.6.1.4.1.10428 9 1.101.21.3.2.10
		fkSFlowFsControlMaxHeaderSize OBJECT-TYPE
			SYNTAX INTEGER (16..256)
			MAX-ACCESS read-write
			STATUS current
			DESCRIPTION
				"Description."
			DEFVAL { 128 }
			::= { fkSFlowFsControl 10 }

		
		-- 1.3.6.1.4.1.10428 9 1.101.21.3.3
		fkSFlowFsNotification OBJECT IDENTIFIER::= { fkSFlowFs 3 }

		
		-- 1.3.6.1.4.1.10428 9 1.101.21.3.3.1
		fkSFlowFsCreated NOTIFICATION-TYPE
			OBJECTS { fkSFlowFsControlRequest, fkSFlowFsControlTimeStamp, fkSFlowFsControlReqResult, fkSFlowFsReceiver, fkSFlowFsPacketSamplingRate, 
				fkSFlowFsMaxHeaderSize }
			STATUS current
			DESCRIPTION 
				"Description."
			::= { fkSFlowFsNotification 1 }

		
		-- 1.3.6.1.4.1.10428 9 1.101.21.3.3.2
		fkSFlowFsChanged NOTIFICATION-TYPE
			OBJECTS { fkSFlowFsControlRequest, fkSFlowFsControlTimeStamp, fkSFlowFsControlReqResult, fkSFlowFsReceiver, fkSFlowFsPacketSamplingRate, 
				fkSFlowFsMaxHeaderSize }
			STATUS current
			DESCRIPTION 
				"Description."
			::= { fkSFlowFsNotification 2 }

		
		-- 1.3.6.1.4.1.10428 9 1.101.21.3.3.3
		fkSFlowFsDestroyed NOTIFICATION-TYPE
			OBJECTS { fkSFlowFsControlRequest, fkSFlowFsControlTimeStamp, fkSFlowFsControlReqResult, fkSFlowFsControlDataSource, fkSFlowFsControlInstance
				 }
			STATUS current
			DESCRIPTION 
				"Description."
			::= { fkSFlowFsNotification 3 }

		
		-- 1.3.6.1.4.1.10428 9 1.101.21.4
		fkSFlowCp OBJECT IDENTIFIER::= { fkSFlow 4 }

		
		-- 1.3.6.1.4.1.10428 9 1.101.21.4.1
		fkSFlowCpTable OBJECT-TYPE
			SYNTAX SEQUENCE OF FkSFlowCpEntry
			MAX-ACCESS not-accessible
			STATUS current
			DESCRIPTION
				"Description."
			::= { fkSFlowCp 1 }

		
		-- 1.3.6.1.4.1.10428 9 1.101.21.4.1.1
		fkSFlowCpEntry OBJECT-TYPE
			SYNTAX FkSFlowCpEntry
			MAX-ACCESS not-accessible
			STATUS current
			DESCRIPTION
				"Description."
			INDEX { fkSFlowCpDataSource, fkSFlowCpInstance }
			::= { fkSFlowCpTable 1 }

		
		FkSFlowCpEntry ::=
			SEQUENCE { 
				fkSFlowCpDataSource
					InterfaceIndex,
				fkSFlowCpInstance
					INTEGER,
				fkSFlowCpReceiver
					INTEGER,
				fkSFlowCpInterval
					INTEGER
			 }

		-- 1.3.6.1.4.1.10428 9 1.101.21.4.1.1.1
		fkSFlowCpDataSource OBJECT-TYPE
			SYNTAX InterfaceIndex
			MAX-ACCESS read-only
			STATUS current
			DESCRIPTION
				"Description."
			::= { fkSFlowCpEntry 1 }

		
		-- 1.3.6.1.4.1.10428 9 1.101.21.4.1.1.2
		fkSFlowCpInstance OBJECT-TYPE
			SYNTAX INTEGER (1..65535)
			MAX-ACCESS read-only
			STATUS current
			DESCRIPTION
				"Description."
			::= { fkSFlowCpEntry 2 }

		
		-- 1.3.6.1.4.1.10428 9 1.101.21.4.1.1.3
		fkSFlowCpReceiver OBJECT-TYPE
			SYNTAX INTEGER (0..65535)
			MAX-ACCESS read-only
			STATUS current
			DESCRIPTION
				"Description."
			DEFVAL { 0 }
			::= { fkSFlowCpEntry 3 }

		
		-- 1.3.6.1.4.1.10428 9 1.101.21.4.1.1.4
		fkSFlowCpInterval OBJECT-TYPE
			SYNTAX INTEGER (0..1000)
			MAX-ACCESS read-only
			STATUS current
			DESCRIPTION
				"Description."
			DEFVAL { 0 }
			::= { fkSFlowCpEntry 4 }

		
		-- 1.3.6.1.4.1.10428 9 1.101.21.4.2
		fkSFlowCpControl OBJECT IDENTIFIER::= { fkSFlowCp 2 }

		
		-- 1.3.6.1.4.1.10428 9 1.101.21.4.2.1
		fkSFlowCpControlRequest OBJECT-TYPE
			SYNTAX INTEGER
				{
				createSFlowCp(1),
				setSFlowCp(2),
				destroySFlowCp(3)
				}
			MAX-ACCESS read-write
			STATUS current
			DESCRIPTION
				"Description."
			::= { fkSFlowCpControl 1 }

		
		-- 1.3.6.1.4.1.10428 9 1.101.21.4.2.2
		fkSFlowCpControlStatus OBJECT-TYPE
			SYNTAX FkControlStatusType
			MAX-ACCESS read-write
			STATUS current
			DESCRIPTION
				"Description."
			::= { fkSFlowCpControl 2 }

		
		-- 1.3.6.1.4.1.10428 9 1.101.21.4.2.3
		fkSFlowCpControlTimer OBJECT-TYPE
			SYNTAX Gauge32
			MAX-ACCESS read-write
			STATUS current
			DESCRIPTION
				"Description."
			::= { fkSFlowCpControl 3 }

		
		-- 1.3.6.1.4.1.10428 9 1.101.21.4.2.4
		fkSFlowCpControlTimeStamp OBJECT-TYPE
			SYNTAX TimeTicks
			MAX-ACCESS read-write
			STATUS current
			DESCRIPTION
				"Description."
			::= { fkSFlowCpControl 4 }

		
		-- 1.3.6.1.4.1.10428 9 1.101.21.4.2.5
		fkSFlowCpControlReqResult OBJECT-TYPE
			SYNTAX FkControlRequestResultType
			MAX-ACCESS read-write
			STATUS current
			DESCRIPTION
				"Description."
			::= { fkSFlowCpControl 5 }

		
		-- 1.3.6.1.4.1.10428 9 1.101.21.4.2.6
		fkSFlowCpControlDataSource OBJECT-TYPE
			SYNTAX InterfaceIndex
			MAX-ACCESS read-write
			STATUS current
			DESCRIPTION
				"Description."
			::= { fkSFlowCpControl 6 }

		
		-- 1.3.6.1.4.1.10428 9 1.101.21.4.2.7
		fkSFlowCpControlInstance OBJECT-TYPE
			SYNTAX INTEGER (1..65535)
			MAX-ACCESS read-write
			STATUS current
			DESCRIPTION
				"Description."
			::= { fkSFlowCpControl 7 }

		
		-- 1.3.6.1.4.1.10428 9 1.101.21.4.2.8
		fkSFlowCpControlReceiver OBJECT-TYPE
			SYNTAX INTEGER (0..65535)
			MAX-ACCESS read-write
			STATUS current
			DESCRIPTION
				"Description."
			DEFVAL { 0 }
			::= { fkSFlowCpControl 8 }

		
		-- 1.3.6.1.4.1.10428 9 1.101.21.4.2.9
		fkSFlowCpControlInterval OBJECT-TYPE
			SYNTAX INTEGER (0..1000)
			MAX-ACCESS read-write
			STATUS current
			DESCRIPTION
				"Description."
			DEFVAL { 0 }
			::= { fkSFlowCpControl 9 }

		
		-- 1.3.6.1.4.1.10428 9 1.101.21.4.3
		fkSFlowCpNotification OBJECT IDENTIFIER::= { fkSFlowCp 3 }

		
		-- 1.3.6.1.4.1.10428 9 1.101.21.4.3.1
		fkSFlowCpCreated NOTIFICATION-TYPE
			OBJECTS { fkSFlowCpControlRequest, fkSFlowCpControlTimeStamp, fkSFlowCpControlReqResult, fkSFlowCpReceiver, fkSFlowCpInterval
				 }
			STATUS current
			DESCRIPTION 
				"Description."
			::= { fkSFlowCpNotification 1 }

		
		-- 1.3.6.1.4.1.10428 9 1.101.21.4.3.2
		fkSFlowCpChanged NOTIFICATION-TYPE
			OBJECTS { fkSFlowCpControlRequest, fkSFlowCpControlTimeStamp, fkSFlowCpControlReqResult, fkSFlowCpReceiver, fkSFlowCpInterval
				 }
			STATUS current
			DESCRIPTION 
				"Description."
			::= { fkSFlowCpNotification 2 }

		
		-- 1.3.6.1.4.1.10428 9 1.101.21.4.3.3
		fkSFlowCpDestroyed NOTIFICATION-TYPE
			OBJECTS { fkSFlowCpControlRequest, fkSFlowCpControlTimeStamp, fkSFlowCpControlReqResult, fkSFlowCpControlDataSource, fkSFlowCpControlInstance
				 }
			STATUS current
			DESCRIPTION 
				"Description."
			::= { fkSFlowCpNotification 3 }

		
		-- 1.3.6.1.4.1.10428 9 1.101.21.5
		fkSFlowGroup OBJECT-GROUP
			OBJECTS { fkSFlowEnable, fkSFlowVersion, fkSFlowAgentAddress, fkSFlowMaxInstance, fkSFlowRcvrIndex, 
				fkSFlowRcvrOwner, fkSFlowRcvrTimeout, fkSFlowRcvrMaxDatagramSize, fkSFlowRcvrAddress, fkSFlowRcvrPort, 
				fkSFlowRcvrDatagramVersion, fkSFlowFsDataSource, fkSFlowFsInstance, fkSFlowFsReceiver, fkSFlowFsPacketSamplingRate, 
				fkSFlowFsMaxHeaderSize, fkSFlowCpDataSource, fkSFlowCpInstance, fkSFlowCpReceiver, fkSFlowCpInterval
				 }
			STATUS current
			DESCRIPTION 
				"Description."
			::= { fkSFlow 5 }

		
		-- 1.3.6.1.4.1.10428 9 1.101.21.6
		fkSFlowControlGroup OBJECT-GROUP
			OBJECTS { fkSFlowControlRequest, fkSFlowControlStatus, fkSFlowControlTimer, fkSFlowControlTimeStamp, fkSFlowControlReqResult, 
				fkSFlowControlEnable, fkSFlowControlAgentAddress, fkSFlowRcvrControlRequest, fkSFlowRcvrControlStatus, fkSFlowRcvrControlTimer, 
				fkSFlowRcvrControlTimeStamp, fkSFlowRcvrControlReqResult, fkSFlowRcvrControlIndex, fkSFlowRcvrControlOwner, fkSFlowRcvrControlTimeout, 
				fkSFlowRcvrControlMaxDatagramSize, fkSFlowRcvrControlAddress, fkSFlowRcvrControlPort, fkSFlowFsControlRequest, fkSFlowFsControlStatus, 
				fkSFlowFsControlTimer, fkSFlowFsControlTimeStamp, fkSFlowFsControlReqResult, fkSFlowFsControlDataSource, fkSFlowFsControlInstance, 
				fkSFlowFsControlReceiver, fkSFlowFsControlPacketSamplingRate, fkSFlowFsControlMaxHeaderSize, fkSFlowCpControlRequest, fkSFlowCpControlStatus, 
				fkSFlowCpControlTimer, fkSFlowCpControlTimeStamp, fkSFlowCpControlReqResult, fkSFlowCpControlDataSource, fkSFlowCpControlInstance, 
				fkSFlowCpControlReceiver, fkSFlowCpControlInterval }
			STATUS current
			DESCRIPTION 
				"Description."
			::= { fkSFlow 6 }

		
		-- 1.3.6.1.4.1.10428 9 1.101.21.7
		fkSFlowNotificationGroup NOTIFICATION-GROUP
			NOTIFICATIONS { fkSFlowEnableChanged, fkSFlowAgentAddressChanged, fkSFlowRcvrCreated, fkSFlowRcvrChanged, fkSFlowRcvrDestroyed, 
				fkSFlowFsCreated, fkSFlowFsChanged, fkSFlowFsDestroyed, fkSFlowCpCreated, fkSFlowCpChanged, 
				fkSFlowCpDestroyed }
			STATUS current
			DESCRIPTION 
				"Description."
			::= { fkSFlow 7 }

		
	
	END

--
-- FK-SFLOW-MIB.my
--
