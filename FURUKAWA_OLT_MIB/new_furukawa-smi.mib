-- *****************************************************************
-- FKOLTG1040-SMI.my:  Fkoltg1040 Enterprise Structure of Management Information
-- *****************************************************************
--

FKOLTG1040-SMI DEFINITIONS ::= BEGIN

IMPORTS
	MODULE-IDENTITY,
	OBJECT-IDENTITY,
	enterprises
		FROM SNMPv2-SMI;
	
fkoltg1040 MODULE-IDENTITY
	LAST-UPDATED "200104190000Z"
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
	::= { enterprises 10428 9 1 } -- assigned by IANA

fkoltg1040Events OBJECT-IDENTITY
  STATUS current
	DESCRIPTION
    "fkoltg1040Events is the root OBJECT IDENTIFIER of EVENTS(or TRAPS).
     Each EVENT(TRAP) is defined in Each Product MIB file." 
  ::= { fkoltg1040 0 }

fkoltg1040Products OBJECT-IDENTITY
	STATUS	current
	DESCRIPTION
		"fkoltg1040Products is the root OBJECT IDENTIFIER from
		which sysObjectID values are assigned.  Actual
		values are defined in FKOLTG1040-PRODUCTS-MIB."
	::= { fkoltg1040 1 }

local OBJECT-IDENTITY
	STATUS	current
	DESCRIPTION
		"Subtree beneath which pre-10.2 MIBS were built."
	::= { fkoltg1040 2 }

temporary OBJECT-IDENTITY
	STATUS	current
	DESCRIPTION
		"Subtree beneath which pre-10.2 experiments were
		placed."
	::= { fkoltg1040 3 }

pakmon OBJECT-IDENTITY
	STATUS	current
	DESCRIPTION
		"reserved for pakmon"
	::= { fkoltg1040 4 }

workgroup OBJECT-IDENTITY
	STATUS	current
	DESCRIPTION
		"subtree reserved for use by the Workgroup Business Unit"
	::= { fkoltg1040 5 }

otherEnterprises OBJECT-IDENTITY
	STATUS	current
	DESCRIPTION
		"otherEnterprises provides a root object identifier
		from which mibs produced by other companies may be
		placed.  mibs produced by other enterprises are
		typicially implemented with the object identifiers
		as defined in the mib, but if the mib is deemed to
		be uncontrolled, we may reroot the mib at this
		subtree in order to have a controlled version."
	::= { fkoltg1040 6 }

fkoltg1040AgentCapability OBJECT-IDENTITY
	STATUS	current
	DESCRIPTION
		"fkoltg1040AgentCapability provides a root object identifier
		from which AGENT-CAPABILITIES values may be assigned."
	::= { fkoltg1040 7 }

fkoltg1040Config OBJECT-IDENTITY
	STATUS	current
	DESCRIPTION
		"fkoltg1040Config is the main subtree for configuration mibs."
	::= { fkoltg1040 8 }

fkoltg1040Mgmt OBJECT-IDENTITY
	STATUS	current
	DESCRIPTION
		"fkoltg1040Mgmt is the main subtree for new mib development."
	::= { fkoltg1040 9 }

fkoltg1040Experiment OBJECT-IDENTITY
	STATUS	current
	DESCRIPTION
		"fkoltg1040Experiment provides a root object identifier
		from which experimental mibs may be temporarily
		based.  mibs are typicially based here if they
		fall in one of two categories
		1) are IETF work-in-process mibs which have not
		been assigned a permanent object identifier by
		the IANA.
		2) are fkoltg1040 work-in-process which has not been
		assigned a permanent object identifier by the
		fkoltg1040 assigned number authority, typicially because
		the mib is not ready for deployment.

		NOTE WELL:  support for mibs in the fkoltg1040Experiment
		subtree will be deleted when a permanent object
		identifier assignment is made."
	::= { fkoltg1040 10 }

fkoltg1040Admin OBJECT-IDENTITY
	STATUS	current
	DESCRIPTION
		"fkoltg1040Admin is reserved for administratively assigned
		OBJECT IDENTIFIERS, i.e. those not associated with MIB
		objects"
	::= { fkoltg1040 11 }

fkoltg1040Modules OBJECT-IDENTITY
	STATUS	current
	DESCRIPTION
		"fkoltg1040Modules provides a root object identifier
		from which MODULE-IDENTITY values may be assigned."
	::= { fkoltg1040 12 }

lightstream OBJECT-IDENTITY
	STATUS	current
	DESCRIPTION
		"subtree reserved for use by Lightstream"
	::= { fkoltg1040 13 }

fkoltg1040works OBJECT-IDENTITY
	STATUS	current
	DESCRIPTION
		"fkoltg1040works provides a root object identifier beneath
		which mibs applicable to the fkoltg1040Works family of network
		management products are defined."
	::= { fkoltg1040 14 }

newport OBJECT-IDENTITY
	STATUS	current
	DESCRIPTION
		"subtree reserved for use by the former Newport Systems
		Solutions, now a portion of the Access Business Unit."
	::= { fkoltg1040 15 }

fkoltg1040PartnerProducts OBJECT-IDENTITY
        STATUS  current
        DESCRIPTION
		"fkoltg1040PartnerProducts is the root OBJECT IDENTIFIER from
		which partner sysObjectID values may be assigned. Such 
		sysObjectID values are composed of the fkoltg1040PartnerProducts
		prefix, followed by a single identifier that is unique for 
		each partner, followed by the value of sysObjectID of the
		fkoltg1040 product from which partner product is derived.  Note
		that the chassisPartner MIB object defines the value of the
		identifier assigned to each partner."
        ::= { fkoltg1040 16 }

fkoltg1040Policy OBJECT-IDENTITY
         STATUS current
         DESCRIPTION
                "fkoltg1040Policy is the root of the fkoltg1040-assigned OID
                subtree for use with Policy Management."
         ::= { fkoltg1040 17 }         
         
         
fkMgmt OBJECT-IDENTITY
         STATUS current
         DESCRIPTION
                "FK Mgmt."
         ::= { fkoltg1040 101 }         

fkV2Mgmt OBJECT-IDENTITY
	 STATUS  current
	 DESCRIPTION
	 "fkV2Management."
	 ::= { fkoltg1040 102 }

dsShe OBJECT IDENTIFIER ::= { otherEnterprises 2 }

END
