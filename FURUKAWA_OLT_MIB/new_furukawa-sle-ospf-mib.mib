--
-- FK-OSPF-MIB.my
-- MIB generated by MG-SOFT Visual MIB Builder Version 6.0  Build 88
-- Saturday, May 15, 2010 at 12:03:04
--

	FK-OSPF-MIB DEFINITIONS ::= BEGIN
 
		IMPORTS
			fkMgmt			
				FROM FKOLTG1040-SMI			
			FkControlStatusType, FkControlRequestResultType			
				FROM FK-TC-MIB			
			OBJECT-GROUP, NOTIFICATION-GROUP			
				FROM SNMPv2-CONF			
			TimeTicks, IpAddress, Integer32, Gauge32, OBJECT-TYPE, 
			MODULE-IDENTITY, NOTIFICATION-TYPE			
				FROM SNMPv2-SMI;
	
	
		-- 1.3.6.1.4.1.10428 9 1.101.51
		fkOspf MODULE-IDENTITY 
			LAST-UPDATED "200412291441Z"		-- December 29, 2004 at 14:41 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 51 }

		
	
	
	
--
-- Node definitions
--
	
		-- 1.3.6.1.4.1.10428 9 1.101.51.1
		fkOSPFBase OBJECT IDENTIFIER ::= { fkOspf 1 }

		
		-- 1.3.6.1.4.1.10428 9 1.101.51.1.1
		fkOSPFBaseInfo OBJECT IDENTIFIER ::= { fkOSPFBase 1 }

		
		-- 1.3.6.1.4.1.10428 9 1.101.51.1.1.1
		fkOSPFRestartPeriod OBJECT-TYPE
			SYNTAX INTEGER (0..1800)
			MAX-ACCESS read-only
			STATUS current
			DESCRIPTION
				"Description."
			::= { fkOSPFBaseInfo 1 }

		
		-- 1.3.6.1.4.1.10428 9 1.101.51.1.1.2
		fkOSPFRestartHelperPolicy OBJECT-TYPE
			SYNTAX INTEGER
				{
				unspec(0),
				never(1),
				onlyreload(2),
				onlyugrade(3)
				}
			MAX-ACCESS read-only
			STATUS current
			DESCRIPTION
				"Description."
			::= { fkOSPFBaseInfo 2 }

		
		-- 1.3.6.1.4.1.10428 9 1.101.51.1.1.3
		fkOSPFRestartHelperPeriod OBJECT-TYPE
			SYNTAX INTEGER (0..1800)
			MAX-ACCESS read-only
			STATUS current
			DESCRIPTION
				"Description."
			::= { fkOSPFBaseInfo 3 }

		
		-- 1.3.6.1.4.1.10428 9 1.101.51.1.2
		fkOSPFBaseControl OBJECT IDENTIFIER ::= { fkOSPFBase 2 }

		
		-- 1.3.6.1.4.1.10428 9 1.101.51.1.2.1
		fkOSPFControlRequest OBJECT-TYPE
			SYNTAX INTEGER
				{
				setOSPFRestartPeriod(1),
				setOSPFRestartHelperProfile(2),
				restartOSPFGraceful(3)
				}
			MAX-ACCESS read-write
			STATUS current
			DESCRIPTION
				"Description."
			::= { fkOSPFBaseControl 1 }

		
		-- 1.3.6.1.4.1.10428 9 1.101.51.1.2.2
		fkOSPFControlStatus OBJECT-TYPE
			SYNTAX FkControlStatusType
			MAX-ACCESS read-only
			STATUS current
			DESCRIPTION
				"Description."
			::= { fkOSPFBaseControl 2 }

		
		-- 1.3.6.1.4.1.10428 9 1.101.51.1.2.3
		fkOSPFControlTimer OBJECT-TYPE
			SYNTAX Gauge32
			MAX-ACCESS read-write
			STATUS current
			DESCRIPTION
				"Description."
			::= { fkOSPFBaseControl 3 }

		
		-- 1.3.6.1.4.1.10428 9 1.101.51.1.2.4
		fkOSPFControlTimeStamp OBJECT-TYPE
			SYNTAX TimeTicks
			MAX-ACCESS read-only
			STATUS current
			DESCRIPTION
				"Description."
			::= { fkOSPFBaseControl 4 }

		
		-- 1.3.6.1.4.1.10428 9 1.101.51.1.2.5
		fkOSPFControlReqResult OBJECT-TYPE
			SYNTAX FkControlRequestResultType
			MAX-ACCESS read-only
			STATUS current
			DESCRIPTION
				"Description."
			::= { fkOSPFBaseControl 5 }

		
		-- 1.3.6.1.4.1.10428 9 1.101.51.1.2.6
		fkOSPFControlRestartPeriod OBJECT-TYPE
			SYNTAX INTEGER (0..1800)
			MAX-ACCESS read-write
			STATUS current
			DESCRIPTION
				"Description."
			::= { fkOSPFBaseControl 6 }

		
		-- 1.3.6.1.4.1.10428 9 1.101.51.1.2.7
		fkOSPFControlRestartHelperPolicy OBJECT-TYPE
			SYNTAX INTEGER
				{
				unspec(0),
				never(1),
				onlyreload(2),
				onlyugrade(3)
				}
			MAX-ACCESS read-write
			STATUS current
			DESCRIPTION
				"Description."
			::= { fkOSPFBaseControl 7 }

		
		-- 1.3.6.1.4.1.10428 9 1.101.51.1.2.8
		fkOSPFControlRestartHelperPeriod OBJECT-TYPE
			SYNTAX INTEGER (0..1800)
			MAX-ACCESS read-write
			STATUS current
			DESCRIPTION
				"Description."
			::= { fkOSPFBaseControl 8 }

		
		-- 1.3.6.1.4.1.10428 9 1.101.51.1.3
		fkOSPFBaseNotification OBJECT IDENTIFIER ::= { fkOSPFBase 3 }

		
		-- 1.3.6.1.4.1.10428 9 1.101.51.1.3.1
		fkOSPFRestartPeriodChanged NOTIFICATION-TYPE
			OBJECTS { fkOSPFControlRequest, fkOSPFControlTimeStamp, fkOSPFControlReqResult, fkOSPFRestartPeriod }
			STATUS current
			DESCRIPTION 
				"Description."
			::= { fkOSPFBaseNotification 1 }

		
		-- 1.3.6.1.4.1.10428 9 1.101.51.1.3.2
		fkOSPFRestartHelperProfileChanged NOTIFICATION-TYPE
			OBJECTS { fkOSPFControlRequest, fkOSPFControlTimeStamp, fkOSPFControlReqResult, fkOSPFRestartHelperPolicy, fkOSPFRestartHelperPeriod
				 }
			STATUS current
			DESCRIPTION 
				"Description."
			::= { fkOSPFBaseNotification 2 }

		
		-- 1.3.6.1.4.1.10428 9 1.101.51.1.3.3
		fkOSPFGracefulRestarted NOTIFICATION-TYPE
			OBJECTS { fkOSPFControlRequest, fkOSPFControlTimeStamp, fkOSPFControlReqResult, fkOSPFControlRestartPeriod }
			STATUS current
			DESCRIPTION 
				"Description."
			::= { fkOSPFBaseNotification 3 }

		
		-- 1.3.6.1.4.1.10428 9 1.101.51.2
		fkOSPFProc OBJECT IDENTIFIER ::= { fkOspf 2 }

		
		-- 1.3.6.1.4.1.10428 9 1.101.51.2.1
		fkOSPFProcInfo OBJECT IDENTIFIER ::= { fkOSPFProc 1 }

		
		-- 1.3.6.1.4.1.10428 9 1.101.51.2.1.1
		fkOSPFProcInfoTable OBJECT-TYPE
			SYNTAX SEQUENCE OF FkOSPFProcInfoEntry
			MAX-ACCESS not-accessible
			STATUS current
			DESCRIPTION
				"Description."
			::= { fkOSPFProcInfo 1 }

		
		-- 1.3.6.1.4.1.10428 9 1.101.51.2.1.1.1
		fkOSPFProcInfoEntry OBJECT-TYPE
			SYNTAX FkOSPFProcInfoEntry
			MAX-ACCESS not-accessible
			STATUS current
			DESCRIPTION
				"Description."
			INDEX { fkOSPFProcID }
			::= { fkOSPFProcInfoTable 1 }

		
		FkOSPFProcInfoEntry ::=
			SEQUENCE { 
				fkOSPFProcID
					Integer32,
				fkOSPFProcRouterID
					IpAddress,
				fkOSPFProcSPFDelayTime
					INTEGER,
				fkOSPFProcSPFHoldTime
					INTEGER,
				fkOSPFProcAutoCost
					INTEGER,
				fkOSPFProcAbrType
					INTEGER,
				fkOSPFProcSnmpNotification
					INTEGER,
				fkOSPFProcDefaultMetricConfig
					INTEGER,
				fkOSPFProcDefaultMetricValue
					INTEGER,
				fkOSPFProcMaxArea
					Gauge32,
				fkOSPFProcMaxConcurrentDD
					INTEGER,
				fkOSPFProcCompatiblerfc1583
					INTEGER,
				fkOSPFProcCapabilityOpaque
					INTEGER,
				fkOSPFProcLSDBOverflowType
					INTEGER,
				fkOSPFProcLSDBOverflowLimit
					Gauge32,
				fkOSPFProcExtLSDBLimit
					INTEGER,
				fkOSPFProcExitOverFlowInterval
					INTEGER,
				fkOSPFProcAdminDistance
					INTEGER,
				fkOSPFProcExternalDistance
					INTEGER,
				fkOSPFProcIntraAreaDistance
					INTEGER,
				fkOSPFProcInterAreaDistance
					INTEGER,
				fkOSPFProcDefaultOriginType
					INTEGER,
				fkOSPFProcDefaultOriginMetricType
					INTEGER,
				fkOSPFProcDefaultOriginMetric
					INTEGER,
				fkOSPFProcDefaultOriginRouteMap
					OCTET STRING,
				fkOSPFProcLogNeighborChange
					INTEGER,
				fkOSPFProcPassiveIfAll
					INTEGER,
				fkOSPFProcBfdIFAll
					INTEGER,
				fkOSPFProcEfmIFAll
					INTEGER,
				fkOSPFProcCapabilityRestart
					INTEGER
			 }

		-- 1.3.6.1.4.1.10428 9 1.101.51.2.1.1.1.1
		fkOSPFProcID OBJECT-TYPE
			SYNTAX Integer32 (1..65535)
			MAX-ACCESS read-only
			STATUS current
			DESCRIPTION
				"Description."
			::= { fkOSPFProcInfoEntry 1 }

		
		-- 1.3.6.1.4.1.10428 9 1.101.51.2.1.1.1.2
		fkOSPFProcRouterID OBJECT-TYPE
			SYNTAX IpAddress
			MAX-ACCESS read-only
			STATUS current
			DESCRIPTION
				"Description."
			::= { fkOSPFProcInfoEntry 2 }

		
		-- 1.3.6.1.4.1.10428 9 1.101.51.2.1.1.1.3
		fkOSPFProcSPFDelayTime OBJECT-TYPE
			SYNTAX INTEGER (0..2147483647)
			MAX-ACCESS read-only
			STATUS current
			DESCRIPTION
				"Description."
			::= { fkOSPFProcInfoEntry 3 }

		
		-- 1.3.6.1.4.1.10428 9 1.101.51.2.1.1.1.4
		fkOSPFProcSPFHoldTime OBJECT-TYPE
			SYNTAX INTEGER (0..2147483647)
			MAX-ACCESS read-only
			STATUS current
			DESCRIPTION
				"Description."
			::= { fkOSPFProcInfoEntry 4 }

		
		-- 1.3.6.1.4.1.10428 9 1.101.51.2.1.1.1.5
		fkOSPFProcAutoCost OBJECT-TYPE
			SYNTAX INTEGER (1..4294967)
			MAX-ACCESS read-only
			STATUS current
			DESCRIPTION
				"Description."
			::= { fkOSPFProcInfoEntry 5 }

		
		-- 1.3.6.1.4.1.10428 9 1.101.51.2.1.1.1.6
		fkOSPFProcAbrType OBJECT-TYPE
			SYNTAX INTEGER
				{
				standard(1),
				cisco(2),
				ibm(3),
				shortcut(4)
				}
			MAX-ACCESS read-only
			STATUS current
			DESCRIPTION
				"Description."
			::= { fkOSPFProcInfoEntry 6 }

		
		-- 1.3.6.1.4.1.10428 9 1.101.51.2.1.1.1.7
		fkOSPFProcSnmpNotification OBJECT-TYPE
			SYNTAX INTEGER
				{
				disable(0),
				enable(1)
				}
			MAX-ACCESS read-only
			STATUS current
			DESCRIPTION
				"Description."
			::= { fkOSPFProcInfoEntry 7 }

		
		-- 1.3.6.1.4.1.10428 9 1.101.51.2.1.1.1.8
		fkOSPFProcDefaultMetricConfig OBJECT-TYPE
			SYNTAX INTEGER
				{
				disable(0),
				enable(1)
				}
			MAX-ACCESS read-only
			STATUS current
			DESCRIPTION
				"Description."
			::= { fkOSPFProcInfoEntry 8 }

		
		-- 1.3.6.1.4.1.10428 9 1.101.51.2.1.1.1.9
		fkOSPFProcDefaultMetricValue OBJECT-TYPE
			SYNTAX INTEGER (0..16777214)
			MAX-ACCESS read-only
			STATUS current
			DESCRIPTION
				"Description."
			::= { fkOSPFProcInfoEntry 9 }

		
		-- 1.3.6.1.4.1.10428 9 1.101.51.2.1.1.1.10
		fkOSPFProcMaxArea OBJECT-TYPE
			SYNTAX Gauge32 (1..4294967294)
			MAX-ACCESS read-only
			STATUS current
			DESCRIPTION
				"Description."
			::= { fkOSPFProcInfoEntry 10 }

		
		-- 1.3.6.1.4.1.10428 9 1.101.51.2.1.1.1.11
		fkOSPFProcMaxConcurrentDD OBJECT-TYPE
			SYNTAX INTEGER (0..65535)
			MAX-ACCESS read-only
			STATUS current
			DESCRIPTION
				"Description."
			::= { fkOSPFProcInfoEntry 11 }

		
		-- 1.3.6.1.4.1.10428 9 1.101.51.2.1.1.1.12
		fkOSPFProcCompatiblerfc1583 OBJECT-TYPE
			SYNTAX INTEGER
				{
				uncompatible(0),
				compatible(1)
				}
			MAX-ACCESS read-only
			STATUS current
			DESCRIPTION
				"Description."
			::= { fkOSPFProcInfoEntry 12 }

		
		-- 1.3.6.1.4.1.10428 9 1.101.51.2.1.1.1.13
		fkOSPFProcCapabilityOpaque OBJECT-TYPE
			SYNTAX INTEGER
				{
				uncapability(0),
				capability(1)
				}
			MAX-ACCESS read-only
			STATUS current
			DESCRIPTION
				"Description."
			::= { fkOSPFProcInfoEntry 13 }

		
		-- 1.3.6.1.4.1.10428 9 1.101.51.2.1.1.1.14
		fkOSPFProcLSDBOverflowType OBJECT-TYPE
			SYNTAX INTEGER
				{
				unspec(0),
				soft(1),
				hard(2)
				}
			MAX-ACCESS read-only
			STATUS current
			DESCRIPTION
				"Description."
			::= { fkOSPFProcInfoEntry 14 }

		
		-- 1.3.6.1.4.1.10428 9 1.101.51.2.1.1.1.15
		fkOSPFProcLSDBOverflowLimit OBJECT-TYPE
			SYNTAX Gauge32 (0..4294967294)
			MAX-ACCESS read-only
			STATUS current
			DESCRIPTION
				"Description."
			::= { fkOSPFProcInfoEntry 15 }

		
		-- 1.3.6.1.4.1.10428 9 1.101.51.2.1.1.1.16
		fkOSPFProcExtLSDBLimit OBJECT-TYPE
			SYNTAX INTEGER (-1..2147483647)
			MAX-ACCESS read-only
			STATUS current
			DESCRIPTION
				"Description."
			::= { fkOSPFProcInfoEntry 16 }

		
		-- 1.3.6.1.4.1.10428 9 1.101.51.2.1.1.1.17
		fkOSPFProcExitOverFlowInterval OBJECT-TYPE
			SYNTAX INTEGER (0..65535)
			MAX-ACCESS read-only
			STATUS current
			DESCRIPTION
				"Description."
			::= { fkOSPFProcInfoEntry 17 }

		
		-- 1.3.6.1.4.1.10428 9 1.101.51.2.1.1.1.18
		fkOSPFProcAdminDistance OBJECT-TYPE
			SYNTAX INTEGER (0..255)
			MAX-ACCESS read-only
			STATUS current
			DESCRIPTION
				"Description."
			::= { fkOSPFProcInfoEntry 18 }

		
		-- 1.3.6.1.4.1.10428 9 1.101.51.2.1.1.1.19
		fkOSPFProcExternalDistance OBJECT-TYPE
			SYNTAX INTEGER (0..255)
			MAX-ACCESS read-only
			STATUS current
			DESCRIPTION
				"Description."
			::= { fkOSPFProcInfoEntry 19 }

		
		-- 1.3.6.1.4.1.10428 9 1.101.51.2.1.1.1.20
		fkOSPFProcIntraAreaDistance OBJECT-TYPE
			SYNTAX INTEGER (0..255)
			MAX-ACCESS read-only
			STATUS current
			DESCRIPTION
				"Description."
			::= { fkOSPFProcInfoEntry 20 }

		
		-- 1.3.6.1.4.1.10428 9 1.101.51.2.1.1.1.21
		fkOSPFProcInterAreaDistance OBJECT-TYPE
			SYNTAX INTEGER (0..255)
			MAX-ACCESS read-only
			STATUS current
			DESCRIPTION
				"Description."
			::= { fkOSPFProcInfoEntry 21 }

		
		-- 1.3.6.1.4.1.10428 9 1.101.51.2.1.1.1.22
		fkOSPFProcDefaultOriginType OBJECT-TYPE
			SYNTAX INTEGER
				{
				unspec(0),
				normal(1),
				always(2)
				}
			MAX-ACCESS read-only
			STATUS current
			DESCRIPTION
				"Description."
			::= { fkOSPFProcInfoEntry 22 }

		
		-- 1.3.6.1.4.1.10428 9 1.101.51.2.1.1.1.23
		fkOSPFProcDefaultOriginMetricType OBJECT-TYPE
			SYNTAX INTEGER
				{
				unspec(0),
				external1(1),
				external2(2)
				}
			MAX-ACCESS read-only
			STATUS current
			DESCRIPTION
				"Description."
			::= { fkOSPFProcInfoEntry 23 }

		
		-- 1.3.6.1.4.1.10428 9 1.101.51.2.1.1.1.24
		fkOSPFProcDefaultOriginMetric OBJECT-TYPE
			SYNTAX INTEGER (0..16777215)
			MAX-ACCESS read-only
			STATUS current
			DESCRIPTION
				"Description."
			::= { fkOSPFProcInfoEntry 24 }

		
		-- 1.3.6.1.4.1.10428 9 1.101.51.2.1.1.1.25
		fkOSPFProcDefaultOriginRouteMap OBJECT-TYPE
			SYNTAX OCTET STRING (SIZE (0..255))
			MAX-ACCESS read-only
			STATUS current
			DESCRIPTION
				"Description."
			::= { fkOSPFProcInfoEntry 25 }

		
		-- 1.3.6.1.4.1.10428 9 1.101.51.2.1.1.1.26
		fkOSPFProcLogNeighborChange OBJECT-TYPE
			SYNTAX INTEGER
				{
				disable(0),
				enable(1)
				}
			MAX-ACCESS read-only
			STATUS current
			DESCRIPTION
				"Description."
			::= { fkOSPFProcInfoEntry 26 }

		
		-- 1.3.6.1.4.1.10428 9 1.101.51.2.1.1.1.27
		fkOSPFProcPassiveIfAll OBJECT-TYPE
			SYNTAX INTEGER
				{
				disable(0),
				enable(1)
				}
			MAX-ACCESS read-only
			STATUS current
			DESCRIPTION
				"Description."
			::= { fkOSPFProcInfoEntry 27 }

		
		-- 1.3.6.1.4.1.10428 9 1.101.51.2.1.1.1.28
		fkOSPFProcBfdIFAll OBJECT-TYPE
			SYNTAX INTEGER
				{
				disable(0),
				enable(1)
				}
			MAX-ACCESS read-only
			STATUS current
			DESCRIPTION
				"Description."
			::= { fkOSPFProcInfoEntry 28 }

		
		-- 1.3.6.1.4.1.10428 9 1.101.51.2.1.1.1.29
		fkOSPFProcEfmIFAll OBJECT-TYPE
			SYNTAX INTEGER
				{
				disable(0),
				enable(1)
				}
			MAX-ACCESS read-only
			STATUS current
			DESCRIPTION
				"Description."
			::= { fkOSPFProcInfoEntry 29 }

		
		-- 1.3.6.1.4.1.10428 9 1.101.51.2.1.1.1.30
		fkOSPFProcCapabilityRestart OBJECT-TYPE
			SYNTAX INTEGER
				{
				none(0),
				graceful(1),
				signaling(2),
				gracefulAck(3)
				}
			MAX-ACCESS read-only
			STATUS current
			DESCRIPTION
				"The Restart-Capability that this OSPF Process has. "
			::= { fkOSPFProcInfoEntry 30 }

		
		-- 1.3.6.1.4.1.10428 9 1.101.51.2.1.2
		fkOSPFProcInfoControl OBJECT IDENTIFIER ::= { fkOSPFProcInfo 2 }

		
		-- 1.3.6.1.4.1.10428 9 1.101.51.2.1.2.1
		fkOSPFProcControlRequest OBJECT-TYPE
			SYNTAX INTEGER
				{
				createOSPFProcess(1),
				deleteOSPFProcess(2),
				createOSPFProcRouterID(3),
				deleteOSPFProcRouterID(4),
				setOSPFProcSPFTimer(5),
				setOSPFProcAutoCost(6),
				setOSPFProcAbrType(7),
				setOSPFProcSnmpNotification(8),
				setOSPFProcDefaultMetricProfile(9),
				setOSPFProcMaximumArea(10),
				setOSPFProcMaxConcurDD(11),
				setOSPFProcComprfc1583(12),
				setOSPFProcCapOpaque(13),
				setOSPFProcLSDBOverflowProfile(14),
				setOSPFProcExtOverflowProfile(15),
				setOSPFProcAdminDistance(16),
				setOSPFProcExtDistance(17),
				setOSPFProcIntraDistance(18),
				setOSPFProcInterDistance(19),
				setOSPFProcDefaultOriginType(20),
				setOSPFProcDefaultOriginMetricType(21),
				setOSPFProcDefaultOriginMetric(22),
				setOSPFProcDefaultOriginRouteMap(23),
				setOSPFProcLogNeighborChange(24),
				setOSPFProcPassiveIfAll(25),
				setOSPFProcBfdIFAll(26),
				setOSPFProcEfmIFAll(27),
				setOSPFProcCapRestart(28),
				clearOSPFProcess(29)
				}
			MAX-ACCESS read-write
			STATUS current
			DESCRIPTION
				"Description."
			::= { fkOSPFProcInfoControl 1 }

		
		-- 1.3.6.1.4.1.10428 9 1.101.51.2.1.2.2
		fkOSPFProcControlStatus OBJECT-TYPE
			SYNTAX FkControlStatusType
			MAX-ACCESS read-only
			STATUS current
			DESCRIPTION
				"Description."
			::= { fkOSPFProcInfoControl 2 }

		
		-- 1.3.6.1.4.1.10428 9 1.101.51.2.1.2.3
		fkOSPFProcControlTimer OBJECT-TYPE
			SYNTAX Gauge32
			MAX-ACCESS read-write
			STATUS current
			DESCRIPTION
				"Description."
			::= { fkOSPFProcInfoControl 3 }

		
		-- 1.3.6.1.4.1.10428 9 1.101.51.2.1.2.4
		fkOSPFProcControlTimeStamp OBJECT-TYPE
			SYNTAX TimeTicks
			MAX-ACCESS read-only
			STATUS current
			DESCRIPTION
				"Description."
			::= { fkOSPFProcInfoControl 4 }

		
		-- 1.3.6.1.4.1.10428 9 1.101.51.2.1.2.5
		fkOSPFProcControlReqResult OBJECT-TYPE
			SYNTAX FkControlRequestResultType
			MAX-ACCESS read-only
			STATUS current
			DESCRIPTION
				"Description."
			::= { fkOSPFProcInfoControl 5 }

		
		-- 1.3.6.1.4.1.10428 9 1.101.51.2.1.2.6
		fkOSPFProcControlID OBJECT-TYPE
			SYNTAX INTEGER (0..65535)
			MAX-ACCESS read-write
			STATUS current
			DESCRIPTION
				"Description."
			::= { fkOSPFProcInfoControl 6 }

		
		-- 1.3.6.1.4.1.10428 9 1.101.51.2.1.2.7
		fkOSPFProcControlRouterID OBJECT-TYPE
			SYNTAX IpAddress
			MAX-ACCESS read-write
			STATUS current
			DESCRIPTION
				"Description."
			::= { fkOSPFProcInfoControl 7 }

		
		-- 1.3.6.1.4.1.10428 9 1.101.51.2.1.2.8
		fkOSPFProcControlSPFDelayTime OBJECT-TYPE
			SYNTAX INTEGER (0..2147483647)
			MAX-ACCESS read-write
			STATUS current
			DESCRIPTION
				"Description."
			::= { fkOSPFProcInfoControl 8 }

		
		-- 1.3.6.1.4.1.10428 9 1.101.51.2.1.2.9
		fkOSPFProcControlSPFHoldTime OBJECT-TYPE
			SYNTAX INTEGER (0..2147483647)
			MAX-ACCESS read-write
			STATUS current
			DESCRIPTION
				"Description."
			::= { fkOSPFProcInfoControl 9 }

		
		-- 1.3.6.1.4.1.10428 9 1.101.51.2.1.2.10
		fkOSPFProcControlAutoCost OBJECT-TYPE
			SYNTAX INTEGER (0..4294967)
			MAX-ACCESS read-write
			STATUS current
			DESCRIPTION
				"Description."
			::= { fkOSPFProcInfoControl 10 }

		
		-- 1.3.6.1.4.1.10428 9 1.101.51.2.1.2.11
		fkOSPFProcControlAbrType OBJECT-TYPE
			SYNTAX INTEGER
				{
				standard(1),
				cisco(2),
				ibm(3),
				shortcut(4)
				}
			MAX-ACCESS read-write
			STATUS current
			DESCRIPTION
				"Description."
			::= { fkOSPFProcInfoControl 11 }

		
		-- 1.3.6.1.4.1.10428 9 1.101.51.2.1.2.12
		fkOSPFProcControlSnmpNotification OBJECT-TYPE
			SYNTAX INTEGER
				{
				disable(0),
				enable(1)
				}
			MAX-ACCESS read-write
			STATUS current
			DESCRIPTION
				"Description."
			::= { fkOSPFProcInfoControl 12 }

		
		-- 1.3.6.1.4.1.10428 9 1.101.51.2.1.2.13
		fkOSPFProcControlDefaultMetricConfig OBJECT-TYPE
			SYNTAX INTEGER
				{
				disable(0),
				enable(1)
				}
			MAX-ACCESS read-write
			STATUS current
			DESCRIPTION
				"Description."
			::= { fkOSPFProcInfoControl 13 }

		
		-- 1.3.6.1.4.1.10428 9 1.101.51.2.1.2.14
		fkOSPFProcControlDefaultMetricValue OBJECT-TYPE
			SYNTAX INTEGER (0..16777214)
			MAX-ACCESS read-write
			STATUS current
			DESCRIPTION
				"Description."
			::= { fkOSPFProcInfoControl 14 }

		
		-- 1.3.6.1.4.1.10428 9 1.101.51.2.1.2.15
		fkOSPFProcControlMaxArea OBJECT-TYPE
			SYNTAX Gauge32 (1..4294967294)
			MAX-ACCESS read-write
			STATUS current
			DESCRIPTION
				"Description."
			::= { fkOSPFProcInfoControl 15 }

		
		-- 1.3.6.1.4.1.10428 9 1.101.51.2.1.2.16
		fkOSPFProcControlMaxConcurDD OBJECT-TYPE
			SYNTAX INTEGER (0..65535)
			MAX-ACCESS read-write
			STATUS current
			DESCRIPTION
				"Description."
			::= { fkOSPFProcInfoControl 16 }

		
		-- 1.3.6.1.4.1.10428 9 1.101.51.2.1.2.17
		fkOSPFProcControlComprfc1583 OBJECT-TYPE
			SYNTAX INTEGER
				{
				uncompatible(0),
				compatible(1)
				}
			MAX-ACCESS read-write
			STATUS current
			DESCRIPTION
				"Description."
			::= { fkOSPFProcInfoControl 17 }

		
		-- 1.3.6.1.4.1.10428 9 1.101.51.2.1.2.18
		fkOSPFProcControlCapabilityOpaque OBJECT-TYPE
			SYNTAX INTEGER
				{
				uncapability(0),
				capability(1)
				}
			MAX-ACCESS read-write
			STATUS current
			DESCRIPTION
				"Description."
			::= { fkOSPFProcInfoControl 18 }

		
		-- 1.3.6.1.4.1.10428 9 1.101.51.2.1.2.19
		fkOSPFProcControlLSDBOverflowType OBJECT-TYPE
			SYNTAX INTEGER
				{
				unspec(0),
				soft(1),
				hard(2)
				}
			MAX-ACCESS read-write
			STATUS current
			DESCRIPTION
				"Description."
			::= { fkOSPFProcInfoControl 19 }

		
		-- 1.3.6.1.4.1.10428 9 1.101.51.2.1.2.20
		fkOSPFProcControlLSDBOverflowLimit OBJECT-TYPE
			SYNTAX Gauge32 (0..4294967294)
			MAX-ACCESS read-write
			STATUS current
			DESCRIPTION
				"Description."
			::= { fkOSPFProcInfoControl 20 }

		
		-- 1.3.6.1.4.1.10428 9 1.101.51.2.1.2.21
		fkOSPFProcControlExtLSDBLimit OBJECT-TYPE
			SYNTAX INTEGER (-1..2147483647)
			MAX-ACCESS read-write
			STATUS current
			DESCRIPTION
				"Description."
			::= { fkOSPFProcInfoControl 21 }

		
		-- 1.3.6.1.4.1.10428 9 1.101.51.2.1.2.22
		fkOSPFProcControlExitOverFlowInterval OBJECT-TYPE
			SYNTAX INTEGER (0..65535)
			MAX-ACCESS read-write
			STATUS current
			DESCRIPTION
				"Description."
			::= { fkOSPFProcInfoControl 22 }

		
		-- 1.3.6.1.4.1.10428 9 1.101.51.2.1.2.23
		fkOSPFProcControlAdminDistance OBJECT-TYPE
			SYNTAX INTEGER (0..255)
			MAX-ACCESS read-write
			STATUS current
			DESCRIPTION
				"Description."
			::= { fkOSPFProcInfoControl 23 }

		
		-- 1.3.6.1.4.1.10428 9 1.101.51.2.1.2.24
		fkOSPFProcControlExtDistance OBJECT-TYPE
			SYNTAX INTEGER (0..255)
			MAX-ACCESS read-write
			STATUS current
			DESCRIPTION
				"Description."
			::= { fkOSPFProcInfoControl 24 }

		
		-- 1.3.6.1.4.1.10428 9 1.101.51.2.1.2.25
		fkOSPFProcControlIntraAreaDistance OBJECT-TYPE
			SYNTAX INTEGER (0..255)
			MAX-ACCESS read-write
			STATUS current
			DESCRIPTION
				"Description."
			::= { fkOSPFProcInfoControl 25 }

		
		-- 1.3.6.1.4.1.10428 9 1.101.51.2.1.2.26
		fkOSPFProcControlInterAreaDistance OBJECT-TYPE
			SYNTAX INTEGER (0..255)
			MAX-ACCESS read-write
			STATUS current
			DESCRIPTION
				"Description."
			::= { fkOSPFProcInfoControl 26 }

		
		-- 1.3.6.1.4.1.10428 9 1.101.51.2.1.2.27
		fkOSPFProcControlDefOriginType OBJECT-TYPE
			SYNTAX INTEGER
				{
				unspec(0),
				normal(1),
				always(2)
				}
			MAX-ACCESS read-write
			STATUS current
			DESCRIPTION
				"Description."
			::= { fkOSPFProcInfoControl 27 }

		
		-- 1.3.6.1.4.1.10428 9 1.101.51.2.1.2.28
		fkOSPFProcControlDefOriginMetricType OBJECT-TYPE
			SYNTAX INTEGER
				{
				unspec(0),
				external1(1),
				external2(2)
				}
			MAX-ACCESS read-write
			STATUS current
			DESCRIPTION
				"Description."
			::= { fkOSPFProcInfoControl 28 }

		
		-- 1.3.6.1.4.1.10428 9 1.101.51.2.1.2.29
		fkOSPFProcControlDefOriginMetric OBJECT-TYPE
			SYNTAX INTEGER (0..16777215)
			MAX-ACCESS read-write
			STATUS current
			DESCRIPTION
				"Description."
			::= { fkOSPFProcInfoControl 29 }

		
		-- 1.3.6.1.4.1.10428 9 1.101.51.2.1.2.30
		fkOSPFProcControlDefOriginRouteMap OBJECT-TYPE
			SYNTAX OCTET STRING (SIZE (0..255))
			MAX-ACCESS read-write
			STATUS current
			DESCRIPTION
				"Description."
			::= { fkOSPFProcInfoControl 30 }

		
		-- 1.3.6.1.4.1.10428 9 1.101.51.2.1.2.31
		fkOSPFProcControlLogNeighborChange OBJECT-TYPE
			SYNTAX INTEGER
				{
				disable(0),
				enable(1)
				}
			MAX-ACCESS read-write
			STATUS current
			DESCRIPTION
				"Description."
			::= { fkOSPFProcInfoControl 31 }

		
		-- 1.3.6.1.4.1.10428 9 1.101.51.2.1.2.32
		fkOSPFProcControlPassiveIFAll OBJECT-TYPE
			SYNTAX INTEGER
				{
				disable(0),
				enable(1)
				}
			MAX-ACCESS read-write
			STATUS current
			DESCRIPTION
				"Description."
			::= { fkOSPFProcInfoControl 32 }

		
		-- 1.3.6.1.4.1.10428 9 1.101.51.2.1.2.33
		fkOSPFProcControlBfdIFAll OBJECT-TYPE
			SYNTAX INTEGER
				{
				disable(0),
				enable(1)
				}
			MAX-ACCESS read-write
			STATUS current
			DESCRIPTION
				"Description."
			::= { fkOSPFProcInfoControl 33 }

		
		-- 1.3.6.1.4.1.10428 9 1.101.51.2.1.2.34
		fkOSPFProcControlEfmIFAll OBJECT-TYPE
			SYNTAX INTEGER
				{
				disable(0),
				enable(1)
				}
			MAX-ACCESS read-write
			STATUS current
			DESCRIPTION
				"Description."
			::= { fkOSPFProcInfoControl 34 }

		
		-- 1.3.6.1.4.1.10428 9 1.101.51.2.1.2.35
		fkOSPFProcControlCapabilityRestart OBJECT-TYPE
			SYNTAX INTEGER
				{
				none(0),
				graceful(1),
				signaling(2),
				gracefulAck(3)
				}
			MAX-ACCESS read-write
			STATUS current
			DESCRIPTION
				"The Restart-Capability that this OSPF Process has. "
			::= { fkOSPFProcInfoControl 35 }

		
		-- 1.3.6.1.4.1.10428 9 1.101.51.2.1.3
		fkOSPFProcInfoNotification OBJECT IDENTIFIER ::= { fkOSPFProcInfo 3 }

		
		-- 1.3.6.1.4.1.10428 9 1.101.51.2.1.3.1
		fkOSPFProcCreated NOTIFICATION-TYPE
			OBJECTS { fkOSPFProcControlRequest, fkOSPFProcControlTimeStamp, fkOSPFProcControlReqResult, fkOSPFProcID }
			STATUS current
			DESCRIPTION 
				"Description."
			::= { fkOSPFProcInfoNotification 1 }

		
		-- 1.3.6.1.4.1.10428 9 1.101.51.2.1.3.2
		fkOSPFProcDeleted NOTIFICATION-TYPE
			OBJECTS { fkOSPFProcControlRequest, fkOSPFProcControlTimeStamp, fkOSPFProcControlReqResult, fkOSPFProcControlID }
			STATUS current
			DESCRIPTION 
				"Description."
			::= { fkOSPFProcInfoNotification 2 }

		
		-- 1.3.6.1.4.1.10428 9 1.101.51.2.1.3.3
		fkOSPFRouterIDCreated NOTIFICATION-TYPE
			OBJECTS { fkOSPFProcControlRequest, fkOSPFProcControlTimeStamp, fkOSPFProcControlReqResult, fkOSPFProcID, fkOSPFProcRouterID
				 }
			STATUS current
			DESCRIPTION 
				"Description."
			::= { fkOSPFProcInfoNotification 3 }

		
		-- 1.3.6.1.4.1.10428 9 1.101.51.2.1.3.4
		fkOSPFRouterIDDeleted NOTIFICATION-TYPE
			OBJECTS { fkOSPFProcControlRequest, fkOSPFProcControlTimeStamp, fkOSPFProcControlReqResult, fkOSPFProcID, fkOSPFProcControlRouterID
				 }
			STATUS current
			DESCRIPTION 
				"Description."
			::= { fkOSPFProcInfoNotification 4 }

		
		-- 1.3.6.1.4.1.10428 9 1.101.51.2.1.3.5
		fkOSPFProcSPFTimerChanged NOTIFICATION-TYPE
			OBJECTS { fkOSPFProcControlRequest, fkOSPFProcControlTimeStamp, fkOSPFProcControlReqResult, fkOSPFProcID, fkOSPFProcSPFDelayTime, 
				fkOSPFProcSPFHoldTime }
			STATUS current
			DESCRIPTION 
				"Description."
			::= { fkOSPFProcInfoNotification 5 }

		
		-- 1.3.6.1.4.1.10428 9 1.101.51.2.1.3.6
		fkOSPFProcAutoCostChanged NOTIFICATION-TYPE
			OBJECTS { fkOSPFProcControlRequest, fkOSPFProcControlTimeStamp, fkOSPFProcControlReqResult, fkOSPFProcID, fkOSPFProcAutoCost
				 }
			STATUS current
			DESCRIPTION 
				"Description."
			::= { fkOSPFProcInfoNotification 6 }

		
		-- 1.3.6.1.4.1.10428 9 1.101.51.2.1.3.7
		fkOSPFProcAbrTypeChanged NOTIFICATION-TYPE
			OBJECTS { fkOSPFProcControlRequest, fkOSPFProcControlTimeStamp, fkOSPFProcControlReqResult, fkOSPFProcID, fkOSPFProcAbrType
				 }
			STATUS current
			DESCRIPTION 
				"Description."
			::= { fkOSPFProcInfoNotification 7 }

		
		-- 1.3.6.1.4.1.10428 9 1.101.51.2.1.3.8
		fkOSPFProcSnmpNotificationChanged NOTIFICATION-TYPE
			OBJECTS { fkOSPFProcControlRequest, fkOSPFProcControlTimeStamp, fkOSPFProcControlReqResult, fkOSPFProcID, fkOSPFProcSnmpNotification
				 }
			STATUS current
			DESCRIPTION 
				"Description."
			::= { fkOSPFProcInfoNotification 8 }

		
		-- 1.3.6.1.4.1.10428 9 1.101.51.2.1.3.9
		fkOSPFProcDefaultMetricProfileChanged NOTIFICATION-TYPE
			OBJECTS { fkOSPFProcControlRequest, fkOSPFProcControlTimeStamp, fkOSPFProcControlReqResult, fkOSPFProcID, fkOSPFProcDefaultMetricConfig, 
				fkOSPFProcDefaultMetricValue }
			STATUS current
			DESCRIPTION 
				"Description."
			::= { fkOSPFProcInfoNotification 9 }

		
		-- 1.3.6.1.4.1.10428 9 1.101.51.2.1.3.10
		fkOSPFProcMaxAreaChanged NOTIFICATION-TYPE
			OBJECTS { fkOSPFProcControlRequest, fkOSPFProcControlTimeStamp, fkOSPFProcControlReqResult, fkOSPFProcID, fkOSPFProcMaxArea
				 }
			STATUS current
			DESCRIPTION 
				"Description."
			::= { fkOSPFProcInfoNotification 10 }

		
		-- 1.3.6.1.4.1.10428 9 1.101.51.2.1.3.11
		fkOSPFProcMaxConcurDDChanged NOTIFICATION-TYPE
			OBJECTS { fkOSPFProcControlRequest, fkOSPFProcControlTimeStamp, fkOSPFProcControlReqResult, fkOSPFProcID, fkOSPFProcMaxConcurrentDD
				 }
			STATUS current
			DESCRIPTION 
				"Description."
			::= { fkOSPFProcInfoNotification 11 }

		
		-- 1.3.6.1.4.1.10428 9 1.101.51.2.1.3.12
		fkOSPFProcComrfc1853Changed NOTIFICATION-TYPE
			OBJECTS { fkOSPFProcControlRequest, fkOSPFProcControlTimeStamp, fkOSPFProcControlReqResult, fkOSPFProcID, fkOSPFProcCompatiblerfc1583
				 }
			STATUS current
			DESCRIPTION 
				"Description."
			::= { fkOSPFProcInfoNotification 12 }

		
		-- 1.3.6.1.4.1.10428 9 1.101.51.2.1.3.13
		fkOSPFProcCapOpaqueChanged NOTIFICATION-TYPE
			OBJECTS { fkOSPFProcControlRequest, fkOSPFProcControlTimeStamp, fkOSPFProcControlReqResult, fkOSPFProcID, fkOSPFProcCapabilityOpaque
				 }
			STATUS current
			DESCRIPTION 
				"Description."
			::= { fkOSPFProcInfoNotification 13 }

		
		-- 1.3.6.1.4.1.10428 9 1.101.51.2.1.3.14
		fkOSPFProcLSDBOverflowProfileChanged NOTIFICATION-TYPE
			OBJECTS { fkOSPFProcControlRequest, fkOSPFProcControlTimeStamp, fkOSPFProcControlReqResult, fkOSPFProcID, fkOSPFProcLSDBOverflowType, 
				fkOSPFProcLSDBOverflowLimit }
			STATUS current
			DESCRIPTION 
				"Description."
			::= { fkOSPFProcInfoNotification 14 }

		
		-- 1.3.6.1.4.1.10428 9 1.101.51.2.1.3.15
		fkOSPFProcExtOverflowProfileChanged NOTIFICATION-TYPE
			OBJECTS { fkOSPFProcControlRequest, fkOSPFProcControlTimeStamp, fkOSPFProcControlReqResult, fkOSPFProcID, fkOSPFProcExtLSDBLimit, 
				fkOSPFProcExitOverFlowInterval }
			STATUS current
			DESCRIPTION 
				"Description."
			::= { fkOSPFProcInfoNotification 15 }

		
		-- 1.3.6.1.4.1.10428 9 1.101.51.2.1.3.16
		fkOSPFProcAdminDistanceChanged NOTIFICATION-TYPE
			OBJECTS { fkOSPFProcControlRequest, fkOSPFProcControlTimeStamp, fkOSPFProcControlReqResult, fkOSPFProcID, fkOSPFProcAdminDistance
				 }
			STATUS current
			DESCRIPTION 
				"Description."
			::= { fkOSPFProcInfoNotification 16 }

		
		-- 1.3.6.1.4.1.10428 9 1.101.51.2.1.3.17
		fkOSPFProcExtDistanceChanged NOTIFICATION-TYPE
			OBJECTS { fkOSPFProcControlRequest, fkOSPFProcControlTimeStamp, fkOSPFProcControlReqResult, fkOSPFProcID, fkOSPFProcExternalDistance
				 }
			STATUS current
			DESCRIPTION 
				"Description."
			::= { fkOSPFProcInfoNotification 17 }

		
		-- 1.3.6.1.4.1.10428 9 1.101.51.2.1.3.18
		fkOSPFProcIntraDistanceChanged NOTIFICATION-TYPE
			OBJECTS { fkOSPFProcControlRequest, fkOSPFProcControlTimeStamp, fkOSPFProcControlReqResult, fkOSPFProcID, fkOSPFProcIntraAreaDistance
				 }
			STATUS current
			DESCRIPTION 
				"Description."
			::= { fkOSPFProcInfoNotification 18 }

		
		-- 1.3.6.1.4.1.10428 9 1.101.51.2.1.3.19
		fkOSPFProcInterDistanceChanged NOTIFICATION-TYPE
			OBJECTS { fkOSPFProcControlRequest, fkOSPFProcControlTimeStamp, fkOSPFProcControlReqResult, fkOSPFProcID, fkOSPFProcInterAreaDistance
				 }
			STATUS current
			DESCRIPTION 
				"Description."
			::= { fkOSPFProcInfoNotification 19 }

		
		-- 1.3.6.1.4.1.10428 9 1.101.51.2.1.3.20
		fkOSPFProcDefaultOriginTypeChanged NOTIFICATION-TYPE
			OBJECTS { fkOSPFProcControlRequest, fkOSPFProcControlTimeStamp, fkOSPFProcControlReqResult, fkOSPFProcID, fkOSPFProcDefaultOriginType
				 }
			STATUS current
			DESCRIPTION 
				"Description."
			::= { fkOSPFProcInfoNotification 20 }

		
		-- 1.3.6.1.4.1.10428 9 1.101.51.2.1.3.21
		fkOSPFProcDefaultOriginMetricTypeChanged NOTIFICATION-TYPE
			OBJECTS { fkOSPFProcControlRequest, fkOSPFProcControlTimeStamp, fkOSPFProcControlReqResult, fkOSPFProcID, fkOSPFProcDefaultOriginMetricType
				 }
			STATUS current
			DESCRIPTION 
				"Description."
			::= { fkOSPFProcInfoNotification 21 }

		
		-- 1.3.6.1.4.1.10428 9 1.101.51.2.1.3.22
		fkOSPFProcDefaultOriginMetricChanged NOTIFICATION-TYPE
			OBJECTS { fkOSPFProcControlRequest, fkOSPFProcControlTimeStamp, fkOSPFProcControlReqResult, fkOSPFProcID, fkOSPFProcDefaultOriginMetric
				 }
			STATUS current
			DESCRIPTION 
				"Description."
			::= { fkOSPFProcInfoNotification 22 }

		
		-- 1.3.6.1.4.1.10428 9 1.101.51.2.1.3.23
		fkOSPFProcDefaultOriginRouteMapChanged NOTIFICATION-TYPE
			OBJECTS { fkOSPFProcControlRequest, fkOSPFProcControlTimeStamp, fkOSPFProcControlReqResult, fkOSPFProcID, fkOSPFProcDefaultOriginRouteMap
				 }
			STATUS current
			DESCRIPTION 
				"Description."
			::= { fkOSPFProcInfoNotification 23 }

		
		-- 1.3.6.1.4.1.10428 9 1.101.51.2.1.3.24
		fkOSPFProcLogNeighborChanged NOTIFICATION-TYPE
			OBJECTS { fkOSPFProcControlRequest, fkOSPFProcControlTimeStamp, fkOSPFProcControlReqResult, fkOSPFProcID, fkOSPFProcLogNeighborChange
				 }
			STATUS current
			DESCRIPTION 
				"Description."
			::= { fkOSPFProcInfoNotification 24 }

		
		-- 1.3.6.1.4.1.10428 9 1.101.51.2.1.3.25
		fkOSPFProcPassiveIFAllChanged NOTIFICATION-TYPE
			OBJECTS { fkOSPFProcControlRequest, fkOSPFProcControlTimeStamp, fkOSPFProcControlReqResult, fkOSPFProcID, fkOSPFProcPassiveIfAll
				 }
			STATUS current
			DESCRIPTION 
				"Description."
			::= { fkOSPFProcInfoNotification 25 }

		
		-- 1.3.6.1.4.1.10428 9 1.101.51.2.1.3.26
		fkOSPFProcBfdIFAllChanged NOTIFICATION-TYPE
			OBJECTS { fkOSPFProcControlRequest, fkOSPFProcControlTimeStamp, fkOSPFProcControlReqResult, fkOSPFProcID, fkOSPFProcBfdIFAll
				 }
			STATUS current
			DESCRIPTION 
				"Description."
			::= { fkOSPFProcInfoNotification 26 }

		
		-- 1.3.6.1.4.1.10428 9 1.101.51.2.1.3.27
		fkOSPFProcEfmIFAllChanged NOTIFICATION-TYPE
			OBJECTS { fkOSPFProcControlRequest, fkOSPFProcControlTimeStamp, fkOSPFProcControlReqResult, fkOSPFProcID, fkOSPFProcEfmIFAll
				 }
			STATUS current
			DESCRIPTION 
				"Description."
			::= { fkOSPFProcInfoNotification 27 }

		
		-- 1.3.6.1.4.1.10428 9 1.101.51.2.1.3.28
		fkOSPFProcCapRestartChanged NOTIFICATION-TYPE
			OBJECTS { fkOSPFProcControlRequest, fkOSPFProcControlTimeStamp, fkOSPFProcCapabilityRestart, fkOSPFProcControlReqResult, fkOSPFProcID
				 }
			STATUS current
			DESCRIPTION 
				"Description."
			::= { fkOSPFProcInfoNotification 28 }

		
		-- 1.3.6.1.4.1.10428 9 1.101.51.2.1.3.29
		fkOSPFProcCleared NOTIFICATION-TYPE
			OBJECTS { fkOSPFProcControlRequest, fkOSPFProcControlTimeStamp, fkOSPFProcControlReqResult, fkOSPFProcID }
			STATUS current
			DESCRIPTION 
				"Description."
			::= { fkOSPFProcInfoNotification 29 }

		
		-- 1.3.6.1.4.1.10428 9 1.101.51.2.2
		fkOSPFProcNetwork OBJECT IDENTIFIER ::= { fkOSPFProc 2 }

		
		-- 1.3.6.1.4.1.10428 9 1.101.51.2.2.1
		fkOSPFProcNetworkTable OBJECT-TYPE
			SYNTAX SEQUENCE OF FkOSPFProcNetworkEntry
			MAX-ACCESS not-accessible
			STATUS current
			DESCRIPTION
				"Description."
			::= { fkOSPFProcNetwork 1 }

		
		-- 1.3.6.1.4.1.10428 9 1.101.51.2.2.1.1
		fkOSPFProcNetworkEntry OBJECT-TYPE
			SYNTAX FkOSPFProcNetworkEntry
			MAX-ACCESS not-accessible
			STATUS current
			DESCRIPTION
				"Description."
			INDEX { fkOSPFProcID, fkOSPFProcNetworkIP, fkOSPFProcNetworkIPMask }
			::= { fkOSPFProcNetworkTable 1 }

		
		FkOSPFProcNetworkEntry ::=
			SEQUENCE { 
				fkOSPFProcNetworkIP
					IpAddress,
				fkOSPFProcNetworkIPMask
					Integer32,
				fkOSPFProcNetworkAreaID
					IpAddress
			 }

		-- 1.3.6.1.4.1.10428 9 1.101.51.2.2.1.1.1
		fkOSPFProcNetworkIP OBJECT-TYPE
			SYNTAX IpAddress
			MAX-ACCESS read-only
			STATUS current
			DESCRIPTION
				"Description."
			::= { fkOSPFProcNetworkEntry 1 }

		
		-- 1.3.6.1.4.1.10428 9 1.101.51.2.2.1.1.2
		fkOSPFProcNetworkIPMask OBJECT-TYPE
			SYNTAX Integer32 (0..32)
			MAX-ACCESS read-only
			STATUS current
			DESCRIPTION
				"Description."
			::= { fkOSPFProcNetworkEntry 2 }

		
		-- 1.3.6.1.4.1.10428 9 1.101.51.2.2.1.1.3
		fkOSPFProcNetworkAreaID OBJECT-TYPE
			SYNTAX IpAddress
			MAX-ACCESS read-only
			STATUS current
			DESCRIPTION
				"Description."
			::= { fkOSPFProcNetworkEntry 3 }

		
		-- 1.3.6.1.4.1.10428 9 1.101.51.2.2.2
		fkOSPFProcNetworkControl OBJECT IDENTIFIER ::= { fkOSPFProcNetwork 2 }

		
		-- 1.3.6.1.4.1.10428 9 1.101.51.2.2.2.1
		fkOSPFProcNetworkControlRequest OBJECT-TYPE
			SYNTAX INTEGER
				{
				createOSPFProcNetwork(1),
				deleteOSPFProcNetwork(2)
				}
			MAX-ACCESS read-write
			STATUS current
			DESCRIPTION
				"Description."
			::= { fkOSPFProcNetworkControl 1 }

		
		-- 1.3.6.1.4.1.10428 9 1.101.51.2.2.2.2
		fkOSPFProcNetworkControlStatus OBJECT-TYPE
			SYNTAX FkControlStatusType
			MAX-ACCESS read-only
			STATUS current
			DESCRIPTION
				"Description."
			::= { fkOSPFProcNetworkControl 2 }

		
		-- 1.3.6.1.4.1.10428 9 1.101.51.2.2.2.3
		fkOSPFProcNetworkControlTimer OBJECT-TYPE
			SYNTAX Gauge32
			MAX-ACCESS read-only
			STATUS current
			DESCRIPTION
				"Description."
			::= { fkOSPFProcNetworkControl 3 }

		
		-- 1.3.6.1.4.1.10428 9 1.101.51.2.2.2.4
		fkOSPFProcNetworkControlTimeStamp OBJECT-TYPE
			SYNTAX TimeTicks
			MAX-ACCESS read-only
			STATUS current
			DESCRIPTION
				"Description."
			::= { fkOSPFProcNetworkControl 4 }

		
		-- 1.3.6.1.4.1.10428 9 1.101.51.2.2.2.5
		fkOSPFProcNetworkControlReqResult OBJECT-TYPE
			SYNTAX FkControlRequestResultType
			MAX-ACCESS read-write
			STATUS current
			DESCRIPTION
				"Description."
			::= { fkOSPFProcNetworkControl 5 }

		
		-- 1.3.6.1.4.1.10428 9 1.101.51.2.2.2.6
		fkOSPFProcNetworkControlProcID OBJECT-TYPE
			SYNTAX INTEGER (0..65535)
			MAX-ACCESS read-write
			STATUS current
			DESCRIPTION
				"Description."
			::= { fkOSPFProcNetworkControl 6 }

		
		-- 1.3.6.1.4.1.10428 9 1.101.51.2.2.2.7
		fkOSPFProcNetworkControlIP OBJECT-TYPE
			SYNTAX IpAddress
			MAX-ACCESS read-write
			STATUS current
			DESCRIPTION
				"Description."
			::= { fkOSPFProcNetworkControl 7 }

		
		-- 1.3.6.1.4.1.10428 9 1.101.51.2.2.2.8
		fkOSPFProcNetworkControlIPMask OBJECT-TYPE
			SYNTAX INTEGER (0..32)
			MAX-ACCESS read-write
			STATUS current
			DESCRIPTION
				"Description."
			::= { fkOSPFProcNetworkControl 8 }

		
		-- 1.3.6.1.4.1.10428 9 1.101.51.2.2.2.9
		fkOSPFProcNetworkControlAreaID OBJECT-TYPE
			SYNTAX IpAddress
			MAX-ACCESS read-write
			STATUS current
			DESCRIPTION
				"Description."
			::= { fkOSPFProcNetworkControl 9 }

		
		-- 1.3.6.1.4.1.10428 9 1.101.51.2.2.3
		fkOSPFProcNetworkNotification OBJECT IDENTIFIER ::= { fkOSPFProcNetwork 3 }

		
		-- 1.3.6.1.4.1.10428 9 1.101.51.2.2.3.1
		fkOSPFProcNetworkCreated NOTIFICATION-TYPE
			OBJECTS { fkOSPFProcNetworkControlRequest, fkOSPFProcNetworkControlTimeStamp, fkOSPFProcNetworkControlReqResult, fkOSPFProcID, fkOSPFProcNetworkIP, 
				fkOSPFProcNetworkIPMask, fkOSPFProcNetworkAreaID }
			STATUS current
			DESCRIPTION 
				"Description."
			::= { fkOSPFProcNetworkNotification 1 }

		
		-- 1.3.6.1.4.1.10428 9 1.101.51.2.2.3.2
		fkOSPFProcNetworkDeleted NOTIFICATION-TYPE
			OBJECTS { fkOSPFProcNetworkControlRequest, fkOSPFProcNetworkControlTimeStamp, fkOSPFProcNetworkControlReqResult, fkOSPFProcID, fkOSPFProcNetworkControlIP, 
				fkOSPFProcNetworkControlIPMask, fkOSPFProcNetworkControlAreaID }
			STATUS current
			DESCRIPTION 
				"Description."
			::= { fkOSPFProcNetworkNotification 2 }

		
		-- 1.3.6.1.4.1.10428 9 1.101.51.2.3
		fkOSPFProcSummary OBJECT IDENTIFIER ::= { fkOSPFProc 3 }

		
		-- 1.3.6.1.4.1.10428 9 1.101.51.2.3.1
		fkOSPFProcSummaryTable OBJECT-TYPE
			SYNTAX SEQUENCE OF FkOSPFProcSummaryEntry
			MAX-ACCESS not-accessible
			STATUS current
			DESCRIPTION
				"Description."
			::= { fkOSPFProcSummary 1 }

		
		-- 1.3.6.1.4.1.10428 9 1.101.51.2.3.1.1
		fkOSPFProcSummaryEntry OBJECT-TYPE
			SYNTAX FkOSPFProcSummaryEntry
			MAX-ACCESS not-accessible
			STATUS current
			DESCRIPTION
				"Description."
			INDEX { fkOSPFProcID, fkOSPFProcSummaryIPAddress, fkOSPFProcSummaryIPMask }
			::= { fkOSPFProcSummaryTable 1 }

		
		FkOSPFProcSummaryEntry ::=
			SEQUENCE { 
				fkOSPFProcSummaryIPAddress
					IpAddress,
				fkOSPFProcSummaryIPMask
					Integer32,
				fkOSPFProcSummaryTag
					Gauge32,
				fkOSPFProcSummaryAdvertiseFlag
					INTEGER
			 }

		-- 1.3.6.1.4.1.10428 9 1.101.51.2.3.1.1.1
		fkOSPFProcSummaryIPAddress OBJECT-TYPE
			SYNTAX IpAddress
			MAX-ACCESS read-only
			STATUS current
			DESCRIPTION
				"Description."
			::= { fkOSPFProcSummaryEntry 1 }

		
		-- 1.3.6.1.4.1.10428 9 1.101.51.2.3.1.1.2
		fkOSPFProcSummaryIPMask OBJECT-TYPE
			SYNTAX Integer32 (0..32)
			MAX-ACCESS read-only
			STATUS current
			DESCRIPTION
				"Description."
			::= { fkOSPFProcSummaryEntry 2 }

		
		-- 1.3.6.1.4.1.10428 9 1.101.51.2.3.1.1.3
		fkOSPFProcSummaryTag OBJECT-TYPE
			SYNTAX Gauge32 (0..4294967295)
			MAX-ACCESS read-only
			STATUS current
			DESCRIPTION
				"Description."
			::= { fkOSPFProcSummaryEntry 3 }

		
		-- 1.3.6.1.4.1.10428 9 1.101.51.2.3.1.1.4
		fkOSPFProcSummaryAdvertiseFlag OBJECT-TYPE
			SYNTAX INTEGER
				{
				disable(0),
				enable(1)
				}
			MAX-ACCESS read-only
			STATUS current
			DESCRIPTION
				"Description."
			::= { fkOSPFProcSummaryEntry 4 }

		
		-- 1.3.6.1.4.1.10428 9 1.101.51.2.3.2
		fkOSPFProcSummaryControl OBJECT IDENTIFIER ::= { fkOSPFProcSummary 2 }

		
		-- 1.3.6.1.4.1.10428 9 1.101.51.2.3.2.1
		fkOSPFProcSummaryControlRequest OBJECT-TYPE
			SYNTAX INTEGER
				{
				createOSPFProcSummary(1),
				deleteOSPFProcSummary(2),
				setOSPFProcSummary(3)
				}
			MAX-ACCESS read-write
			STATUS current
			DESCRIPTION
				"Description."
			::= { fkOSPFProcSummaryControl 1 }

		
		-- 1.3.6.1.4.1.10428 9 1.101.51.2.3.2.2
		fkOSPFProcSummaryControlStatus OBJECT-TYPE
			SYNTAX FkControlStatusType
			MAX-ACCESS read-only
			STATUS current
			DESCRIPTION
				"Description."
			::= { fkOSPFProcSummaryControl 2 }

		
		-- 1.3.6.1.4.1.10428 9 1.101.51.2.3.2.3
		fkOSPFProcSummaryControlTimer OBJECT-TYPE
			SYNTAX Gauge32
			MAX-ACCESS read-write
			STATUS current
			DESCRIPTION
				"Description."
			::= { fkOSPFProcSummaryControl 3 }

		
		-- 1.3.6.1.4.1.10428 9 1.101.51.2.3.2.4
		fkOSPFProcSummaryControlTimeStamp OBJECT-TYPE
			SYNTAX TimeTicks
			MAX-ACCESS read-only
			STATUS current
			DESCRIPTION
				"Description."
			::= { fkOSPFProcSummaryControl 4 }

		
		-- 1.3.6.1.4.1.10428 9 1.101.51.2.3.2.5
		fkOSPFProcSummaryControlReqResult OBJECT-TYPE
			SYNTAX FkControlRequestResultType
			MAX-ACCESS read-only
			STATUS current
			DESCRIPTION
				"Description."
			::= { fkOSPFProcSummaryControl 5 }

		
		-- 1.3.6.1.4.1.10428 9 1.101.51.2.3.2.6
		fkOSPFProcSummaryControlProcID OBJECT-TYPE
			SYNTAX INTEGER (0..65535)
			MAX-ACCESS read-write
			STATUS current
			DESCRIPTION
				"Description."
			::= { fkOSPFProcSummaryControl 6 }

		
		-- 1.3.6.1.4.1.10428 9 1.101.51.2.3.2.7
		fkOSPFProcSummaryControlIPAddress OBJECT-TYPE
			SYNTAX IpAddress
			MAX-ACCESS read-write
			STATUS current
			DESCRIPTION
				"Description."
			::= { fkOSPFProcSummaryControl 7 }

		
		-- 1.3.6.1.4.1.10428 9 1.101.51.2.3.2.8
		fkOSPFProcSummaryControlIPMask OBJECT-TYPE
			SYNTAX INTEGER (0..32)
			MAX-ACCESS read-write
			STATUS current
			DESCRIPTION
				"Description."
			::= { fkOSPFProcSummaryControl 8 }

		
		-- 1.3.6.1.4.1.10428 9 1.101.51.2.3.2.9
		fkOSPFProcSummaryControlTag OBJECT-TYPE
			SYNTAX Gauge32 (0..4294967295)
			MAX-ACCESS read-write
			STATUS current
			DESCRIPTION
				"Description."
			::= { fkOSPFProcSummaryControl 9 }

		
		-- 1.3.6.1.4.1.10428 9 1.101.51.2.3.2.10
		fkOSPFProcSummaryControlAdvertiseFlag OBJECT-TYPE
			SYNTAX INTEGER
				{
				disable(0),
				enable(1)
				}
			MAX-ACCESS read-write
			STATUS current
			DESCRIPTION
				"Description."
			::= { fkOSPFProcSummaryControl 10 }

		
		-- 1.3.6.1.4.1.10428 9 1.101.51.2.3.3
		fkOSPFProcSummaryNotification OBJECT IDENTIFIER ::= { fkOSPFProcSummary 3 }

		
		-- 1.3.6.1.4.1.10428 9 1.101.51.2.3.3.1
		fkOSPFSummaryCreated NOTIFICATION-TYPE
			OBJECTS { fkOSPFProcSummaryControlRequest, fkOSPFProcSummaryControlTimeStamp, fkOSPFProcSummaryControlReqResult, fkOSPFProcID, fkOSPFProcSummaryIPAddress, 
				fkOSPFProcSummaryIPMask, fkOSPFProcSummaryTag, fkOSPFProcSummaryAdvertiseFlag }
			STATUS current
			DESCRIPTION 
				"Description."
			::= { fkOSPFProcSummaryNotification 1 }

		
		-- 1.3.6.1.4.1.10428 9 1.101.51.2.3.3.2
		fkOSPFSummaryDeleted NOTIFICATION-TYPE
			OBJECTS { fkOSPFProcSummaryControlRequest, fkOSPFProcSummaryControlTimeStamp, fkOSPFProcSummaryControlReqResult, fkOSPFProcID, fkOSPFProcSummaryControlIPAddress, 
				fkOSPFProcSummaryControlIPMask, fkOSPFProcSummaryControlTag, fkOSPFProcSummaryControlAdvertiseFlag }
			STATUS current
			DESCRIPTION 
				"Description."
			::= { fkOSPFProcSummaryNotification 2 }

		
		-- 1.3.6.1.4.1.10428 9 1.101.51.2.3.3.3
		fkOSPFSummaryChanged NOTIFICATION-TYPE
			OBJECTS { fkOSPFProcSummaryControlRequest, fkOSPFProcSummaryControlTimeStamp, fkOSPFProcSummaryControlReqResult, fkOSPFProcID, fkOSPFProcSummaryIPAddress, 
				fkOSPFProcSummaryIPMask, fkOSPFProcSummaryTag, fkOSPFProcSummaryAdvertiseFlag }
			STATUS current
			DESCRIPTION 
				"Description."
			::= { fkOSPFProcSummaryNotification 3 }

		
		-- 1.3.6.1.4.1.10428 9 1.101.51.2.4
		fkOSPFProcDistributeList OBJECT IDENTIFIER ::= { fkOSPFProc 4 }

		
		-- 1.3.6.1.4.1.10428 9 1.101.51.2.4.1
		fkOSPFProcDistributeListTable OBJECT-TYPE
			SYNTAX SEQUENCE OF FkOSPFProcDistributeListEntry
			MAX-ACCESS not-accessible
			STATUS current
			DESCRIPTION
				"Description."
			::= { fkOSPFProcDistributeList 1 }

		
		-- 1.3.6.1.4.1.10428 9 1.101.51.2.4.1.1
		fkOSPFProcDistributeListEntry OBJECT-TYPE
			SYNTAX FkOSPFProcDistributeListEntry
			MAX-ACCESS not-accessible
			STATUS current
			DESCRIPTION
				"Description."
			INDEX { fkOSPFProcID, fkOSPFProcDistributeListOutFilterType }
			::= { fkOSPFProcDistributeListTable 1 }

		
		FkOSPFProcDistributeListEntry ::=
			SEQUENCE { 
				fkOSPFProcDistributeListOutFilterType
					INTEGER,
				fkOSPFProcDistributeListAccessName
					OCTET STRING
			 }

		-- 1.3.6.1.4.1.10428 9 1.101.51.2.4.1.1.1
		fkOSPFProcDistributeListOutFilterType OBJECT-TYPE
			SYNTAX INTEGER
				{
				kernel(1),
				connected(2),
				static(3),
				rip(4),
				bgp(8)
				}
			MAX-ACCESS read-only
			STATUS current
			DESCRIPTION
				"Description."
			::= { fkOSPFProcDistributeListEntry 1 }

		
		-- 1.3.6.1.4.1.10428 9 1.101.51.2.4.1.1.2
		fkOSPFProcDistributeListAccessName OBJECT-TYPE
			SYNTAX OCTET STRING
			MAX-ACCESS read-only
			STATUS current
			DESCRIPTION
				"Description."
			::= { fkOSPFProcDistributeListEntry 2 }

		
		-- 1.3.6.1.4.1.10428 9 1.101.51.2.4.2
		fkOSPFProcDistributeListControl OBJECT IDENTIFIER ::= { fkOSPFProcDistributeList 2 }

		
		-- 1.3.6.1.4.1.10428 9 1.101.51.2.4.2.1
		fkOSPFProcDistributeListControlRequest OBJECT-TYPE
			SYNTAX INTEGER
				{
				createOSPFProcDistributeList(1),
				deleteOSPFProcDistributeList(2)
				}
			MAX-ACCESS read-write
			STATUS current
			DESCRIPTION
				"Description."
			::= { fkOSPFProcDistributeListControl 1 }

		
		-- 1.3.6.1.4.1.10428 9 1.101.51.2.4.2.2
		fkOSPFProcDistributeListControlStatus OBJECT-TYPE
			SYNTAX FkControlStatusType
			MAX-ACCESS read-only
			STATUS current
			DESCRIPTION
				"Description."
			::= { fkOSPFProcDistributeListControl 2 }

		
		-- 1.3.6.1.4.1.10428 9 1.101.51.2.4.2.3
		fkOSPFProcDistributeListControlTimer OBJECT-TYPE
			SYNTAX Gauge32
			MAX-ACCESS read-write
			STATUS current
			DESCRIPTION
				"Description."
			::= { fkOSPFProcDistributeListControl 3 }

		
		-- 1.3.6.1.4.1.10428 9 1.101.51.2.4.2.4
		fkOSPFProcDistributeListControlTimeStamp OBJECT-TYPE
			SYNTAX TimeTicks
			MAX-ACCESS read-only
			STATUS current
			DESCRIPTION
				"Description."
			::= { fkOSPFProcDistributeListControl 4 }

		
		-- 1.3.6.1.4.1.10428 9 1.101.51.2.4.2.5
		fkOSPFProcDistributeListControlReqResult OBJECT-TYPE
			SYNTAX FkControlRequestResultType
			MAX-ACCESS read-only
			STATUS current
			DESCRIPTION
				"Description."
			::= { fkOSPFProcDistributeListControl 5 }

		
		-- 1.3.6.1.4.1.10428 9 1.101.51.2.4.2.6
		fkOSPFProcDistributeListControlProcID OBJECT-TYPE
			SYNTAX INTEGER (0..65535)
			MAX-ACCESS read-write
			STATUS current
			DESCRIPTION
				"Description."
			::= { fkOSPFProcDistributeListControl 6 }

		
		-- 1.3.6.1.4.1.10428 9 1.101.51.2.4.2.7
		fkOSPFProcDistributeListControlOutFilterType OBJECT-TYPE
			SYNTAX INTEGER
				{
				kernel(1),
				connected(2),
				static(3),
				rip(4),
				bgp(8)
				}
			MAX-ACCESS read-write
			STATUS current
			DESCRIPTION
				"Description."
			::= { fkOSPFProcDistributeListControl 7 }

		
		-- 1.3.6.1.4.1.10428 9 1.101.51.2.4.2.8
		fkOSPFProcDistributeListControlAccessName OBJECT-TYPE
			SYNTAX OCTET STRING
			MAX-ACCESS read-write
			STATUS current
			DESCRIPTION
				"Description."
			::= { fkOSPFProcDistributeListControl 8 }

		
		-- 1.3.6.1.4.1.10428 9 1.101.51.2.4.3
		fkOSPFProcDistributeListNotification OBJECT IDENTIFIER ::= { fkOSPFProcDistributeList 3 }

		
		-- 1.3.6.1.4.1.10428 9 1.101.51.2.4.3.1
		fkOSPFDistributeListCreated NOTIFICATION-TYPE
			OBJECTS { fkOSPFProcDistributeListControlRequest, fkOSPFProcDistributeListControlTimeStamp, fkOSPFProcDistributeListControlReqResult, fkOSPFProcID, fkOSPFProcDistributeListOutFilterType, 
				fkOSPFProcDistributeListAccessName }
			STATUS current
			DESCRIPTION 
				"Description."
			::= { fkOSPFProcDistributeListNotification 1 }

		
		-- 1.3.6.1.4.1.10428 9 1.101.51.2.4.3.2
		fkOSPFDistributeListDeleted NOTIFICATION-TYPE
			OBJECTS { fkOSPFProcDistributeListControlRequest, fkOSPFProcDistributeListControlTimeStamp, fkOSPFProcDistributeListControlReqResult, fkOSPFProcID, fkOSPFProcDistributeListControlOutFilterType, 
				fkOSPFProcDistributeListControlAccessName }
			STATUS current
			DESCRIPTION 
				"Description."
			::= { fkOSPFProcDistributeListNotification 2 }

		
		-- 1.3.6.1.4.1.10428 9 1.101.51.2.5
		fkOSPFProcNeighbor OBJECT IDENTIFIER ::= { fkOSPFProc 5 }

		
		-- 1.3.6.1.4.1.10428 9 1.101.51.2.5.1
		fkOSPFProcNeighborTable OBJECT-TYPE
			SYNTAX SEQUENCE OF FkOSPFProcNeighborEntry
			MAX-ACCESS not-accessible
			STATUS current
			DESCRIPTION
				"Description."
			::= { fkOSPFProcNeighbor 1 }

		
		-- 1.3.6.1.4.1.10428 9 1.101.51.2.5.1.1
		fkOSPFProcNeighborEntry OBJECT-TYPE
			SYNTAX FkOSPFProcNeighborEntry
			MAX-ACCESS not-accessible
			STATUS current
			DESCRIPTION
				"Description."
			INDEX { fkOSPFProcID, fkOSPFProcNeighborIPAddr }
			::= { fkOSPFProcNeighborTable 1 }

		
		FkOSPFProcNeighborEntry ::=
			SEQUENCE { 
				fkOSPFProcNeighborIPAddr
					IpAddress,
				fkOSPFProcNeighborPriority
					INTEGER,
				fkOSPFProcNeighborPollInterval
					INTEGER,
				fkOSPFProcNeighborCost
					INTEGER
			 }

		-- 1.3.6.1.4.1.10428 9 1.101.51.2.5.1.1.1
		fkOSPFProcNeighborIPAddr OBJECT-TYPE
			SYNTAX IpAddress
			MAX-ACCESS read-only
			STATUS current
			DESCRIPTION
				"Description."
			::= { fkOSPFProcNeighborEntry 1 }

		
		-- 1.3.6.1.4.1.10428 9 1.101.51.2.5.1.1.2
		fkOSPFProcNeighborPriority OBJECT-TYPE
			SYNTAX INTEGER (1..255)
			MAX-ACCESS read-only
			STATUS current
			DESCRIPTION
				"Description."
			::= { fkOSPFProcNeighborEntry 2 }

		
		-- 1.3.6.1.4.1.10428 9 1.101.51.2.5.1.1.3
		fkOSPFProcNeighborPollInterval OBJECT-TYPE
			SYNTAX INTEGER (1..65535)
			MAX-ACCESS read-only
			STATUS current
			DESCRIPTION
				"Description."
			::= { fkOSPFProcNeighborEntry 3 }

		
		-- 1.3.6.1.4.1.10428 9 1.101.51.2.5.1.1.4
		fkOSPFProcNeighborCost OBJECT-TYPE
			SYNTAX INTEGER (1..65535)
			MAX-ACCESS read-only
			STATUS current
			DESCRIPTION
				"Description."
			::= { fkOSPFProcNeighborEntry 4 }

		
		-- 1.3.6.1.4.1.10428 9 1.101.51.2.5.2
		fkOSPFProcNeighborControl OBJECT IDENTIFIER ::= { fkOSPFProcNeighbor 2 }

		
		-- 1.3.6.1.4.1.10428 9 1.101.51.2.5.2.1
		fkOSPFProcNeighborControlRequest OBJECT-TYPE
			SYNTAX INTEGER
				{
				createOSPFProcNeighbor(1),
				deleteOSPFProcNeighbor(2),
				setOSPFProcNeighbor(3)
				}
			MAX-ACCESS read-write
			STATUS current
			DESCRIPTION
				"Description."
			::= { fkOSPFProcNeighborControl 1 }

		
		-- 1.3.6.1.4.1.10428 9 1.101.51.2.5.2.2
		fkOSPFProcNeighborControlStatus OBJECT-TYPE
			SYNTAX FkControlStatusType
			MAX-ACCESS read-only
			STATUS current
			DESCRIPTION
				"Description."
			::= { fkOSPFProcNeighborControl 2 }

		
		-- 1.3.6.1.4.1.10428 9 1.101.51.2.5.2.3
		fkOSPFProcNeighborControlTimer OBJECT-TYPE
			SYNTAX Gauge32
			MAX-ACCESS read-write
			STATUS current
			DESCRIPTION
				"Description."
			::= { fkOSPFProcNeighborControl 3 }

		
		-- 1.3.6.1.4.1.10428 9 1.101.51.2.5.2.4
		fkOSPFProcNeighborControlTimeStamp OBJECT-TYPE
			SYNTAX TimeTicks
			MAX-ACCESS read-only
			STATUS current
			DESCRIPTION
				"Description."
			::= { fkOSPFProcNeighborControl 4 }

		
		-- 1.3.6.1.4.1.10428 9 1.101.51.2.5.2.5
		fkOSPFProcNeighborControlReqResult OBJECT-TYPE
			SYNTAX FkControlRequestResultType
			MAX-ACCESS read-only
			STATUS current
			DESCRIPTION
				"Description."
			::= { fkOSPFProcNeighborControl 5 }

		
		-- 1.3.6.1.4.1.10428 9 1.101.51.2.5.2.6
		fkOSPFProcNeighborControlProcID OBJECT-TYPE
			SYNTAX INTEGER (0..65535)
			MAX-ACCESS read-write
			STATUS current
			DESCRIPTION
				"Description."
			::= { fkOSPFProcNeighborControl 6 }

		
		-- 1.3.6.1.4.1.10428 9 1.101.51.2.5.2.7
		fkOSPFProcNeighborControlIPAddr OBJECT-TYPE
			SYNTAX IpAddress
			MAX-ACCESS read-write
			STATUS current
			DESCRIPTION
				"Description."
			::= { fkOSPFProcNeighborControl 7 }

		
		-- 1.3.6.1.4.1.10428 9 1.101.51.2.5.2.8
		fkOSPFProcNeighborControlPriority OBJECT-TYPE
			SYNTAX INTEGER (1..255)
			MAX-ACCESS read-write
			STATUS current
			DESCRIPTION
				"Description."
			::= { fkOSPFProcNeighborControl 8 }

		
		-- 1.3.6.1.4.1.10428 9 1.101.51.2.5.2.9
		fkOSPFProcNeighborControlPollInterval OBJECT-TYPE
			SYNTAX INTEGER (1..65535)
			MAX-ACCESS read-write
			STATUS current
			DESCRIPTION
				"Description."
			::= { fkOSPFProcNeighborControl 9 }

		
		-- 1.3.6.1.4.1.10428 9 1.101.51.2.5.2.10
		fkOSPFProcNeighborControlCost OBJECT-TYPE
			SYNTAX INTEGER (1..65535)
			MAX-ACCESS read-write
			STATUS current
			DESCRIPTION
				"Description."
			::= { fkOSPFProcNeighborControl 10 }

		
		-- 1.3.6.1.4.1.10428 9 1.101.51.2.5.3
		fkOSPFProcNeighborNotification OBJECT IDENTIFIER ::= { fkOSPFProcNeighbor 3 }

		
		-- 1.3.6.1.4.1.10428 9 1.101.51.2.5.3.1
		fkOSPFProcNeighborCreated NOTIFICATION-TYPE
			OBJECTS { fkOSPFProcNeighborControlRequest, fkOSPFProcNeighborControlTimeStamp, fkOSPFProcNeighborControlReqResult, fkOSPFProcID, fkOSPFProcNeighborIPAddr, 
				fkOSPFProcNeighborCost, fkOSPFProcNeighborPollInterval, fkOSPFProcNeighborPriority }
			STATUS current
			DESCRIPTION 
				"Description."
			::= { fkOSPFProcNeighborNotification 1 }

		
		-- 1.3.6.1.4.1.10428 9 1.101.51.2.5.3.2
		fkOSPFProcNeighborDeleted NOTIFICATION-TYPE
			OBJECTS { fkOSPFProcNeighborControlRequest, fkOSPFProcNeighborControlTimeStamp, fkOSPFProcNeighborControlReqResult, fkOSPFProcID, fkOSPFProcNeighborControlIPAddr
				 }
			STATUS current
			DESCRIPTION 
				"Description."
			::= { fkOSPFProcNeighborNotification 2 }

		
		-- 1.3.6.1.4.1.10428 9 1.101.51.2.5.3.3
		fkOSPFProcNeighborChanged NOTIFICATION-TYPE
			OBJECTS { fkOSPFProcNeighborControlRequest, fkOSPFProcNeighborControlTimeStamp, fkOSPFProcNeighborControlReqResult, fkOSPFProcNeighborIPAddr, fkOSPFProcID, 
				fkOSPFProcNeighborCost, fkOSPFProcNeighborPollInterval, fkOSPFProcNeighborPriority }
			STATUS current
			DESCRIPTION 
				"Description."
			::= { fkOSPFProcNeighborNotification 3 }

		
		-- 1.3.6.1.4.1.10428 9 1.101.51.2.6
		fkOSPFProcPassIf OBJECT IDENTIFIER ::= { fkOSPFProc 6 }

		
		-- 1.3.6.1.4.1.10428 9 1.101.51.2.6.1
		fkOSPFProcPassIfTable OBJECT-TYPE
			SYNTAX SEQUENCE OF FkOSPFProcPassIfEntry
			MAX-ACCESS not-accessible
			STATUS current
			DESCRIPTION
				"Description."
			::= { fkOSPFProcPassIf 1 }

		
		-- 1.3.6.1.4.1.10428 9 1.101.51.2.6.1.1
		fkOSPFProcPassIfEntry OBJECT-TYPE
			SYNTAX FkOSPFProcPassIfEntry
			MAX-ACCESS not-accessible
			STATUS current
			DESCRIPTION
				"Description."
			INDEX { fkOSPFProcID, fkOSPFProcPassIfAddr, fkOSPFProcPassIfName }
			::= { fkOSPFProcPassIfTable 1 }

		
		FkOSPFProcPassIfEntry ::=
			SEQUENCE { 
				fkOSPFProcPassIfAddr
					IpAddress,
				fkOSPFProcPassIfName
					OCTET STRING
			 }

		-- 1.3.6.1.4.1.10428 9 1.101.51.2.6.1.1.1
		fkOSPFProcPassIfAddr OBJECT-TYPE
			SYNTAX IpAddress
			MAX-ACCESS read-only
			STATUS current
			DESCRIPTION
				"Description."
			::= { fkOSPFProcPassIfEntry 1 }

		
		-- 1.3.6.1.4.1.10428 9 1.101.51.2.6.1.1.2
		fkOSPFProcPassIfName OBJECT-TYPE
			SYNTAX OCTET STRING
			MAX-ACCESS read-only
			STATUS current
			DESCRIPTION
				"Description."
			::= { fkOSPFProcPassIfEntry 2 }

		
		-- 1.3.6.1.4.1.10428 9 1.101.51.2.6.2
		fkOSPFProcPassIfControl OBJECT IDENTIFIER ::= { fkOSPFProcPassIf 2 }

		
		-- 1.3.6.1.4.1.10428 9 1.101.51.2.6.2.1
		fkOSPFProcPassIfControlRequest OBJECT-TYPE
			SYNTAX INTEGER
				{
				createOSPFProcPassInterface(1),
				deleteOSPFProcPassInterface(2)
				}
			MAX-ACCESS read-write
			STATUS current
			DESCRIPTION
				"Description."
			::= { fkOSPFProcPassIfControl 1 }

		
		-- 1.3.6.1.4.1.10428 9 1.101.51.2.6.2.2
		fkOSPFProcPassIfControlStatus OBJECT-TYPE
			SYNTAX FkControlStatusType
			MAX-ACCESS read-only
			STATUS current
			DESCRIPTION
				"Description."
			::= { fkOSPFProcPassIfControl 2 }

		
		-- 1.3.6.1.4.1.10428 9 1.101.51.2.6.2.3
		fkOSPFProcPassIfControlTimer OBJECT-TYPE
			SYNTAX Gauge32
			MAX-ACCESS read-write
			STATUS current
			DESCRIPTION
				"Description."
			::= { fkOSPFProcPassIfControl 3 }

		
		-- 1.3.6.1.4.1.10428 9 1.101.51.2.6.2.4
		fkOSPFProcPassIfControlTimeStamp OBJECT-TYPE
			SYNTAX TimeTicks
			MAX-ACCESS read-only
			STATUS current
			DESCRIPTION
				"Description."
			::= { fkOSPFProcPassIfControl 4 }

		
		-- 1.3.6.1.4.1.10428 9 1.101.51.2.6.2.5
		fkOSPFProcPassIfControlReqResult OBJECT-TYPE
			SYNTAX FkControlRequestResultType
			MAX-ACCESS read-only
			STATUS current
			DESCRIPTION
				"Description."
			::= { fkOSPFProcPassIfControl 5 }

		
		-- 1.3.6.1.4.1.10428 9 1.101.51.2.6.2.6
		fkOSPFProcPassIfControlProcID OBJECT-TYPE
			SYNTAX INTEGER (0..65535)
			MAX-ACCESS read-write
			STATUS current
			DESCRIPTION
				"Description."
			::= { fkOSPFProcPassIfControl 6 }

		
		-- 1.3.6.1.4.1.10428 9 1.101.51.2.6.2.7
		fkOSPFProcPassIfControlIPAddr OBJECT-TYPE
			SYNTAX IpAddress
			MAX-ACCESS read-write
			STATUS current
			DESCRIPTION
				"Description."
			::= { fkOSPFProcPassIfControl 7 }

		
		-- 1.3.6.1.4.1.10428 9 1.101.51.2.6.2.8
		fkOSPFProcPassIfControlName OBJECT-TYPE
			SYNTAX OCTET STRING
			MAX-ACCESS read-write
			STATUS current
			DESCRIPTION
				"Description."
			::= { fkOSPFProcPassIfControl 8 }

		
		-- 1.3.6.1.4.1.10428 9 1.101.51.2.6.3
		fkOSPFProcPassIfNotification OBJECT IDENTIFIER ::= { fkOSPFProcPassIf 3 }

		
		-- 1.3.6.1.4.1.10428 9 1.101.51.2.6.3.1
		fkOSPFPassInterfaceCreated NOTIFICATION-TYPE
			OBJECTS { fkOSPFProcPassIfControlRequest, fkOSPFProcPassIfControlTimeStamp, fkOSPFProcPassIfControlReqResult, fkOSPFProcPassIfName, fkOSPFProcPassIfAddr
				 }
			STATUS current
			DESCRIPTION 
				"Description."
			::= { fkOSPFProcPassIfNotification 1 }

		
		-- 1.3.6.1.4.1.10428 9 1.101.51.2.6.3.2
		fkOSPFPassInterfaceDeleted NOTIFICATION-TYPE
			OBJECTS { fkOSPFProcPassIfControlRequest, fkOSPFProcPassIfControlTimeStamp, fkOSPFProcPassIfControlReqResult, fkOSPFProcID, fkOSPFProcPassIfControlName, 
				fkOSPFProcPassIfControlIPAddr }
			STATUS current
			DESCRIPTION 
				"Description."
			::= { fkOSPFProcPassIfNotification 2 }

		
		-- 1.3.6.1.4.1.10428 9 1.101.51.2.7
		fkOSPFProcHost OBJECT IDENTIFIER ::= { fkOSPFProc 7 }

		
		-- 1.3.6.1.4.1.10428 9 1.101.51.2.7.1
		fkOSPFProcHostTable OBJECT-TYPE
			SYNTAX SEQUENCE OF FkOSPFProcHostEntry
			MAX-ACCESS not-accessible
			STATUS current
			DESCRIPTION
				"Description."
			::= { fkOSPFProcHost 1 }

		
		-- 1.3.6.1.4.1.10428 9 1.101.51.2.7.1.1
		fkOSPFProcHostEntry OBJECT-TYPE
			SYNTAX FkOSPFProcHostEntry
			MAX-ACCESS not-accessible
			STATUS current
			DESCRIPTION
				"Description."
			INDEX { fkOSPFProcID, fkOSPFProcHostIPAddr }
			::= { fkOSPFProcHostTable 1 }

		
		FkOSPFProcHostEntry ::=
			SEQUENCE { 
				fkOSPFProcHostIPAddr
					IpAddress,
				fkOSPFProcHostAreaID
					Gauge32,
				fkOSPFProcHostAreaCost
					INTEGER
			 }

		-- 1.3.6.1.4.1.10428 9 1.101.51.2.7.1.1.1
		fkOSPFProcHostIPAddr OBJECT-TYPE
			SYNTAX IpAddress
			MAX-ACCESS read-only
			STATUS current
			DESCRIPTION
				"Description."
			::= { fkOSPFProcHostEntry 1 }

		
		-- 1.3.6.1.4.1.10428 9 1.101.51.2.7.1.1.2
		fkOSPFProcHostAreaID OBJECT-TYPE
			SYNTAX Gauge32 (1..4294967295)
			MAX-ACCESS read-only
			STATUS current
			DESCRIPTION
				"Description."
			::= { fkOSPFProcHostEntry 2 }

		
		-- 1.3.6.1.4.1.10428 9 1.101.51.2.7.1.1.3
		fkOSPFProcHostAreaCost OBJECT-TYPE
			SYNTAX INTEGER (1..65535)
			MAX-ACCESS read-only
			STATUS current
			DESCRIPTION
				"Description."
			::= { fkOSPFProcHostEntry 3 }

		
		-- 1.3.6.1.4.1.10428 9 1.101.51.2.7.2
		fkOSPFProcHostControl OBJECT IDENTIFIER ::= { fkOSPFProcHost 2 }

		
		-- 1.3.6.1.4.1.10428 9 1.101.51.2.7.2.1
		fkOSPFProcHostControlRequest OBJECT-TYPE
			SYNTAX INTEGER
				{
				createOSPFProcHost(1),
				deleteOSPFProcHost(2),
				setOSPFProcHostCost(3)
				}
			MAX-ACCESS read-write
			STATUS current
			DESCRIPTION
				"Description."
			::= { fkOSPFProcHostControl 1 }

		
		-- 1.3.6.1.4.1.10428 9 1.101.51.2.7.2.2
		fkOSPFProcHostControlStatus OBJECT-TYPE
			SYNTAX FkControlStatusType
			MAX-ACCESS read-only
			STATUS current
			DESCRIPTION
				"Description."
			::= { fkOSPFProcHostControl 2 }

		
		-- 1.3.6.1.4.1.10428 9 1.101.51.2.7.2.3
		fkOSPFProcHostControlTimer OBJECT-TYPE
			SYNTAX Gauge32
			MAX-ACCESS read-write
			STATUS current
			DESCRIPTION
				"Description."
			::= { fkOSPFProcHostControl 3 }

		
		-- 1.3.6.1.4.1.10428 9 1.101.51.2.7.2.4
		fkOSPFProcHostControlTimeStamp OBJECT-TYPE
			SYNTAX TimeTicks
			MAX-ACCESS read-only
			STATUS current
			DESCRIPTION
				"Description."
			::= { fkOSPFProcHostControl 4 }

		
		-- 1.3.6.1.4.1.10428 9 1.101.51.2.7.2.5
		fkOSPFProcHostControlReqResult OBJECT-TYPE
			SYNTAX FkControlRequestResultType
			MAX-ACCESS read-only
			STATUS current
			DESCRIPTION
				"Description."
			::= { fkOSPFProcHostControl 5 }

		
		-- 1.3.6.1.4.1.10428 9 1.101.51.2.7.2.6
		fkOSPFProcHostControlProcID OBJECT-TYPE
			SYNTAX INTEGER (0..65535)
			MAX-ACCESS read-write
			STATUS current
			DESCRIPTION
				"Description."
			::= { fkOSPFProcHostControl 6 }

		
		-- 1.3.6.1.4.1.10428 9 1.101.51.2.7.2.7
		fkOSPFProcHostControlIPAddr OBJECT-TYPE
			SYNTAX IpAddress
			MAX-ACCESS read-write
			STATUS current
			DESCRIPTION
				"Description."
			::= { fkOSPFProcHostControl 7 }

		
		-- 1.3.6.1.4.1.10428 9 1.101.51.2.7.2.8
		fkOSPFProcHostControlAreaID OBJECT-TYPE
			SYNTAX Gauge32 (1..4294967295)
			MAX-ACCESS read-write
			STATUS current
			DESCRIPTION
				"Description."
			::= { fkOSPFProcHostControl 8 }

		
		-- 1.3.6.1.4.1.10428 9 1.101.51.2.7.2.9
		fkOSPFProcHostControlAreaCost OBJECT-TYPE
			SYNTAX INTEGER (1..65535)
			MAX-ACCESS read-write
			STATUS current
			DESCRIPTION
				"Description."
			::= { fkOSPFProcHostControl 9 }

		
		-- 1.3.6.1.4.1.10428 9 1.101.51.2.7.3
		fkOSPFProcHostNotification OBJECT IDENTIFIER ::= { fkOSPFProcHost 3 }

		
		-- 1.3.6.1.4.1.10428 9 1.101.51.2.7.3.1
		fkOSPFProcHostCreated NOTIFICATION-TYPE
			OBJECTS { fkOSPFProcHostControlRequest, fkOSPFProcHostControlTimeStamp, fkOSPFProcHostControlReqResult, fkOSPFProcHostIPAddr, fkOSPFProcHostAreaID, 
				fkOSPFProcHostAreaCost }
			STATUS current
			DESCRIPTION 
				"Description."
			::= { fkOSPFProcHostNotification 1 }

		
		-- 1.3.6.1.4.1.10428 9 1.101.51.2.7.3.2
		fkOSPFProcHostDeleted NOTIFICATION-TYPE
			OBJECTS { fkOSPFProcHostControlRequest, fkOSPFProcHostControlTimeStamp, fkOSPFProcHostControlReqResult, fkOSPFProcID, fkOSPFProcHostControlIPAddr, 
				fkOSPFProcHostControlAreaID }
			STATUS current
			DESCRIPTION 
				"Description."
			::= { fkOSPFProcHostNotification 2 }

		
		-- 1.3.6.1.4.1.10428 9 1.101.51.2.7.3.3
		fkOSPFProcHostCostChanged NOTIFICATION-TYPE
			OBJECTS { fkOSPFProcHostControlRequest, fkOSPFProcHostControlTimeStamp, fkOSPFProcHostControlReqResult, fkOSPFProcHostIPAddr, fkOSPFProcHostAreaID, 
				fkOSPFProcHostAreaCost }
			STATUS current
			DESCRIPTION 
				"Description."
			::= { fkOSPFProcHostNotification 3 }

		
		-- 1.3.6.1.4.1.10428 9 1.101.51.2.8
		fkOSPFProcRedistribute OBJECT IDENTIFIER ::= { fkOSPFProc 8 }

		
		-- 1.3.6.1.4.1.10428 9 1.101.51.2.8.1
		fkOSPFProcRedistTable OBJECT-TYPE
			SYNTAX SEQUENCE OF FkOSPFProcRedistEntry
			MAX-ACCESS not-accessible
			STATUS current
			DESCRIPTION
				"Description."
			::= { fkOSPFProcRedistribute 1 }

		
		-- 1.3.6.1.4.1.10428 9 1.101.51.2.8.1.1
		fkOSPFProcRedistEntry OBJECT-TYPE
			SYNTAX FkOSPFProcRedistEntry
			MAX-ACCESS not-accessible
			STATUS current
			DESCRIPTION
				"Description."
			INDEX { fkOSPFProcID, fkOSPFProcRedistType }
			::= { fkOSPFProcRedistTable 1 }

		
		FkOSPFProcRedistEntry ::=
			SEQUENCE { 
				fkOSPFProcRedistType
					INTEGER,
				fkOSPFProcRedistMetricType
					INTEGER,
				fkOSPFProcRedistMetric
					INTEGER,
				fkOSPFProcRedistRouteMapName
					OCTET STRING,
				fkOSPFProcRedistTag
					Gauge32,
				fkOSPFProcRedistSubnets
					INTEGER
			 }

		-- 1.3.6.1.4.1.10428 9 1.101.51.2.8.1.1.1
		fkOSPFProcRedistType OBJECT-TYPE
			SYNTAX INTEGER
				{
				kernel(1),
				connected(2),
				static(3),
				rip(4),
				bgp(5)
				}
			MAX-ACCESS read-only
			STATUS current
			DESCRIPTION
				"Description."
			::= { fkOSPFProcRedistEntry 1 }

		
		-- 1.3.6.1.4.1.10428 9 1.101.51.2.8.1.1.2
		fkOSPFProcRedistMetricType OBJECT-TYPE
			SYNTAX INTEGER
				{
				external1(1),
				external2(2)
				}
			MAX-ACCESS read-only
			STATUS current
			DESCRIPTION
				"Description."
			::= { fkOSPFProcRedistEntry 2 }

		
		-- 1.3.6.1.4.1.10428 9 1.101.51.2.8.1.1.3
		fkOSPFProcRedistMetric OBJECT-TYPE
			SYNTAX INTEGER (1..16777214)
			MAX-ACCESS read-only
			STATUS current
			DESCRIPTION
				"Description."
			::= { fkOSPFProcRedistEntry 3 }

		
		-- 1.3.6.1.4.1.10428 9 1.101.51.2.8.1.1.4
		fkOSPFProcRedistRouteMapName OBJECT-TYPE
			SYNTAX OCTET STRING
			MAX-ACCESS read-only
			STATUS current
			DESCRIPTION
				"Description."
			::= { fkOSPFProcRedistEntry 4 }

		
		-- 1.3.6.1.4.1.10428 9 1.101.51.2.8.1.1.5
		fkOSPFProcRedistTag OBJECT-TYPE
			SYNTAX Gauge32 (1..4294967295)
			MAX-ACCESS read-only
			STATUS current
			DESCRIPTION
				"Description."
			::= { fkOSPFProcRedistEntry 5 }

		
		-- 1.3.6.1.4.1.10428 9 1.101.51.2.8.1.1.6
		fkOSPFProcRedistSubnets OBJECT-TYPE
			SYNTAX INTEGER
				{
				disable(0),
				enable(1)
				}
			MAX-ACCESS read-only
			STATUS current
			DESCRIPTION
				"Description."
			::= { fkOSPFProcRedistEntry 6 }

		
		-- 1.3.6.1.4.1.10428 9 1.101.51.2.8.2
		fkOSPFProcRedistControl OBJECT IDENTIFIER ::= { fkOSPFProcRedistribute 2 }

		
		-- 1.3.6.1.4.1.10428 9 1.101.51.2.8.2.1
		fkOSPFProcRedistControlRequest OBJECT-TYPE
			SYNTAX INTEGER
				{
				createOSPFProcRedist(1),
				deleteOSPFProcRedist(2),
				setOSPFProcRedist(3)
				}
			MAX-ACCESS read-write
			STATUS current
			DESCRIPTION
				"Description."
			::= { fkOSPFProcRedistControl 1 }

		
		-- 1.3.6.1.4.1.10428 9 1.101.51.2.8.2.2
		fkOSPFProcRedistControlStatus OBJECT-TYPE
			SYNTAX FkControlStatusType
			MAX-ACCESS read-only
			STATUS current
			DESCRIPTION
				"Description."
			::= { fkOSPFProcRedistControl 2 }

		
		-- 1.3.6.1.4.1.10428 9 1.101.51.2.8.2.3
		fkOSPFProcRedistControlTimer OBJECT-TYPE
			SYNTAX Gauge32
			MAX-ACCESS read-write
			STATUS current
			DESCRIPTION
				"Description."
			::= { fkOSPFProcRedistControl 3 }

		
		-- 1.3.6.1.4.1.10428 9 1.101.51.2.8.2.4
		fkOSPFProcRedistControlTimeStamp OBJECT-TYPE
			SYNTAX TimeTicks
			MAX-ACCESS read-only
			STATUS current
			DESCRIPTION
				"Description."
			::= { fkOSPFProcRedistControl 4 }

		
		-- 1.3.6.1.4.1.10428 9 1.101.51.2.8.2.5
		fkOSPFProcRedistControlReqResult OBJECT-TYPE
			SYNTAX FkControlRequestResultType
			MAX-ACCESS read-only
			STATUS current
			DESCRIPTION
				"Description."
			::= { fkOSPFProcRedistControl 5 }

		
		-- 1.3.6.1.4.1.10428 9 1.101.51.2.8.2.6
		fkOSPFProcRedistControlProcID OBJECT-TYPE
			SYNTAX INTEGER (0..65535)
			MAX-ACCESS read-write
			STATUS current
			DESCRIPTION
				"Description."
			::= { fkOSPFProcRedistControl 6 }

		
		-- 1.3.6.1.4.1.10428 9 1.101.51.2.8.2.7
		fkOSPFProcRedistControlType OBJECT-TYPE
			SYNTAX INTEGER
				{
				kernel(1),
				connected(2),
				static(3),
				rip(4),
				bgp(5)
				}
			MAX-ACCESS read-write
			STATUS current
			DESCRIPTION
				"Description."
			::= { fkOSPFProcRedistControl 7 }

		
		-- 1.3.6.1.4.1.10428 9 1.101.51.2.8.2.8
		fkOSPFProcRedistControlMetricType OBJECT-TYPE
			SYNTAX INTEGER
				{
				external1(1),
				external2(2)
				}
			MAX-ACCESS read-write
			STATUS current
			DESCRIPTION
				"Description."
			::= { fkOSPFProcRedistControl 8 }

		
		-- 1.3.6.1.4.1.10428 9 1.101.51.2.8.2.9
		fkOSPFProcRedistControlMetric OBJECT-TYPE
			SYNTAX INTEGER (1..16777214)
			MAX-ACCESS read-write
			STATUS current
			DESCRIPTION
				"Description."
			::= { fkOSPFProcRedistControl 9 }

		
		-- 1.3.6.1.4.1.10428 9 1.101.51.2.8.2.10
		fkOSPFProcRedistControlRouteMapName OBJECT-TYPE
			SYNTAX OCTET STRING
			MAX-ACCESS read-write
			STATUS current
			DESCRIPTION
				"Description."
			::= { fkOSPFProcRedistControl 10 }

		
		-- 1.3.6.1.4.1.10428 9 1.101.51.2.8.2.11
		fkOSPFProcRedistControlTag OBJECT-TYPE
			SYNTAX Gauge32 (1..4294967295)
			MAX-ACCESS read-write
			STATUS current
			DESCRIPTION
				"Description."
			::= { fkOSPFProcRedistControl 11 }

		
		-- 1.3.6.1.4.1.10428 9 1.101.51.2.8.2.12
		fkOSPFProcRedistControlSubnets OBJECT-TYPE
			SYNTAX INTEGER
				{
				disable(0),
				enable(1)
				}
			MAX-ACCESS read-write
			STATUS current
			DESCRIPTION
				"Description."
			::= { fkOSPFProcRedistControl 12 }

		
		-- 1.3.6.1.4.1.10428 9 1.101.51.2.8.3
		fkOSPFProcRedistNotification OBJECT IDENTIFIER ::= { fkOSPFProcRedistribute 3 }

		
		-- 1.3.6.1.4.1.10428 9 1.101.51.2.8.3.1
		fkOSPFProcRedistCreated NOTIFICATION-TYPE
			OBJECTS { fkOSPFProcRedistControlRequest, fkOSPFProcRedistControlTimeStamp, fkOSPFProcRedistSubnets, fkOSPFProcRedistControlReqResult, fkOSPFProcRedistType, 
				fkOSPFProcRedistMetricType, fkOSPFProcRedistMetric, fkOSPFProcRedistRouteMapName, fkOSPFProcRedistTag }
			STATUS current
			DESCRIPTION 
				"Description."
			::= { fkOSPFProcRedistNotification 1 }

		
		-- 1.3.6.1.4.1.10428 9 1.101.51.2.8.3.2
		fkOSPFProcRedistDeleted NOTIFICATION-TYPE
			OBJECTS { fkOSPFProcRedistControlRequest, fkOSPFProcRedistControlReqResult, fkOSPFProcRedistControlTimeStamp, fkOSPFProcID, fkOSPFProcRedistControlType, 
				fkOSPFProcRedistControlMetricType, fkOSPFProcRedistControlMetric, fkOSPFProcRedistControlRouteMapName, fkOSPFProcRedistControlTag, fkOSPFProcRedistControlSubnets
				 }
			STATUS current
			DESCRIPTION 
				"Description."
			::= { fkOSPFProcRedistNotification 2 }

		
		-- 1.3.6.1.4.1.10428 9 1.101.51.2.8.3.3
		fkOSPFProcRedistChanged NOTIFICATION-TYPE
			OBJECTS { fkOSPFProcRedistControlRequest, fkOSPFProcRedistControlTimeStamp, fkOSPFProcRedistControlReqResult, fkOSPFProcRedistType, fkOSPFProcRedistMetricType, 
				fkOSPFProcRedistMetric, fkOSPFProcRedistRouteMapName, fkOSPFProcRedistTag, fkOSPFProcRedistControlSubnets }
			STATUS current
			DESCRIPTION 
				"Description."
			::= { fkOSPFProcRedistNotification 3 }

		
		-- 1.3.6.1.4.1.10428 9 1.101.51.2.9
		fkOSPFProcArea OBJECT IDENTIFIER ::= { fkOSPFProc 9 }

		
		-- 1.3.6.1.4.1.10428 9 1.101.51.2.9.1
		fkOSPFProcAreaInfo OBJECT IDENTIFIER ::= { fkOSPFProcArea 1 }

		
		-- 1.3.6.1.4.1.10428 9 1.101.51.2.9.1.1
		fkOSPFProcAreaInfoTable OBJECT-TYPE
			SYNTAX SEQUENCE OF FkOSPFProcAreaInfoEntry
			MAX-ACCESS not-accessible
			STATUS current
			DESCRIPTION
				"Description."
			::= { fkOSPFProcAreaInfo 1 }

		
		-- 1.3.6.1.4.1.10428 9 1.101.51.2.9.1.1.1
		fkOSPFProcAreaInfoEntry OBJECT-TYPE
			SYNTAX FkOSPFProcAreaInfoEntry
			MAX-ACCESS not-accessible
			STATUS current
			DESCRIPTION
				"Description."
			INDEX { fkOSPFProcID, fkOSPFProcAreaID }
			::= { fkOSPFProcAreaInfoTable 1 }

		
		FkOSPFProcAreaInfoEntry ::=
			SEQUENCE { 
				fkOSPFProcAreaID
					IpAddress,
				fkOSPFProcAreaType
					INTEGER,
				fkOSPFProcAreaDefaultCost
					INTEGER,
				fkOSPFProcAreaAuthenType
					INTEGER,
				fkOSPFProcAreaFAInName
					OCTET STRING,
				fkOSPFProcAreaFAOutName
					OBJECT IDENTIFIER,
				fkOSPFProcAreaFPInName
					OCTET STRING,
				fkOSPFProcAreaFPOutName
					OCTET STRING,
				fkOSPFProcAreaShortcutType
					INTEGER,
				fkOSPFProcAreaSpfRuns
					INTEGER,
				fkOSPFProcAreaLsaCount
					INTEGER,
				fkOSPFProcAreaLsaCheckSum
					INTEGER,
				fkOSPFProcAreaSummary
					INTEGER,
				fkOSPFProcAreaNssaTransRole
					INTEGER,
				fkOSPFProcAreaNssaNoRedist
					INTEGER,
				fkOSPFProcAreaNssaDefOriginate
					INTEGER,
				fkOSPFProcAreaNssaDefMetricType
					INTEGER,
				fkOSPFProcAreaNssaDefMetric
					INTEGER
			 }

		-- 1.3.6.1.4.1.10428 9 1.101.51.2.9.1.1.1.1
		fkOSPFProcAreaID OBJECT-TYPE
			SYNTAX IpAddress
			MAX-ACCESS read-only
			STATUS current
			DESCRIPTION
				"Description."
			::= { fkOSPFProcAreaInfoEntry 1 }

		
		-- 1.3.6.1.4.1.10428 9 1.101.51.2.9.1.1.1.2
		fkOSPFProcAreaType OBJECT-TYPE
			SYNTAX INTEGER
				{
				general(0),
				stub(1),
				nssa(2)
				}
			MAX-ACCESS read-only
			STATUS current
			DESCRIPTION
				"Description."
			::= { fkOSPFProcAreaInfoEntry 2 }

		
		-- 1.3.6.1.4.1.10428 9 1.101.51.2.9.1.1.1.3
		fkOSPFProcAreaDefaultCost OBJECT-TYPE
			SYNTAX INTEGER (0..16777215)
			MAX-ACCESS read-only
			STATUS current
			DESCRIPTION
				"Description."
			::= { fkOSPFProcAreaInfoEntry 3 }

		
		-- 1.3.6.1.4.1.10428 9 1.101.51.2.9.1.1.1.4
		fkOSPFProcAreaAuthenType OBJECT-TYPE
			SYNTAX INTEGER
				{
				null(0),
				simple(1),
				crypt(2)
				}
			MAX-ACCESS read-only
			STATUS current
			DESCRIPTION
				"Description."
			::= { fkOSPFProcAreaInfoEntry 4 }

		
		-- 1.3.6.1.4.1.10428 9 1.101.51.2.9.1.1.1.5
		fkOSPFProcAreaFAInName OBJECT-TYPE
			SYNTAX OCTET STRING
			MAX-ACCESS read-only
			STATUS current
			DESCRIPTION
				"Description."
			::= { fkOSPFProcAreaInfoEntry 5 }

		
		-- 1.3.6.1.4.1.10428 9 1.101.51.2.9.1.1.1.6
		fkOSPFProcAreaFAOutName OBJECT-TYPE
			SYNTAX OBJECT IDENTIFIER
			MAX-ACCESS read-only
			STATUS current
			DESCRIPTION
				"Description."
			::= { fkOSPFProcAreaInfoEntry 6 }

		
		-- 1.3.6.1.4.1.10428 9 1.101.51.2.9.1.1.1.7
		fkOSPFProcAreaFPInName OBJECT-TYPE
			SYNTAX OCTET STRING
			MAX-ACCESS read-only
			STATUS current
			DESCRIPTION
				"Description."
			::= { fkOSPFProcAreaInfoEntry 7 }

		
		-- 1.3.6.1.4.1.10428 9 1.101.51.2.9.1.1.1.8
		fkOSPFProcAreaFPOutName OBJECT-TYPE
			SYNTAX OCTET STRING
			MAX-ACCESS read-only
			STATUS current
			DESCRIPTION
				"Description."
			::= { fkOSPFProcAreaInfoEntry 8 }

		
		-- 1.3.6.1.4.1.10428 9 1.101.51.2.9.1.1.1.9
		fkOSPFProcAreaShortcutType OBJECT-TYPE
			SYNTAX INTEGER
				{
				default(0),
				enable(1),
				disable(2)
				}
			MAX-ACCESS read-only
			STATUS current
			DESCRIPTION
				"Description."
			::= { fkOSPFProcAreaInfoEntry 9 }

		
		-- 1.3.6.1.4.1.10428 9 1.101.51.2.9.1.1.1.10
		fkOSPFProcAreaSpfRuns OBJECT-TYPE
			SYNTAX INTEGER
			MAX-ACCESS read-only
			STATUS current
			DESCRIPTION
				"Description."
			::= { fkOSPFProcAreaInfoEntry 10 }

		
		-- 1.3.6.1.4.1.10428 9 1.101.51.2.9.1.1.1.11
		fkOSPFProcAreaLsaCount OBJECT-TYPE
			SYNTAX INTEGER
			MAX-ACCESS read-only
			STATUS current
			DESCRIPTION
				"Description."
			::= { fkOSPFProcAreaInfoEntry 11 }

		
		-- 1.3.6.1.4.1.10428 9 1.101.51.2.9.1.1.1.12
		fkOSPFProcAreaLsaCheckSum OBJECT-TYPE
			SYNTAX INTEGER
			MAX-ACCESS read-only
			STATUS current
			DESCRIPTION
				"Description."
			::= { fkOSPFProcAreaInfoEntry 12 }

		
		-- 1.3.6.1.4.1.10428 9 1.101.51.2.9.1.1.1.13
		fkOSPFProcAreaSummary OBJECT-TYPE
			SYNTAX INTEGER
				{
				none(0),
				noAreaSummary(1),
				sendAreaSummary(2)
				}
			MAX-ACCESS read-only
			STATUS current
			DESCRIPTION
				"Description."
			::= { fkOSPFProcAreaInfoEntry 13 }

		
		-- 1.3.6.1.4.1.10428 9 1.101.51.2.9.1.1.1.14
		fkOSPFProcAreaNssaTransRole OBJECT-TYPE
			SYNTAX INTEGER
				{
				never(0),
				always(1),
				candidate(2),
				none(3)
				}
			MAX-ACCESS read-only
			STATUS current
			DESCRIPTION
				"Description."
			::= { fkOSPFProcAreaInfoEntry 14 }

		
		-- 1.3.6.1.4.1.10428 9 1.101.51.2.9.1.1.1.15
		fkOSPFProcAreaNssaNoRedist OBJECT-TYPE
			SYNTAX INTEGER
				{
				none(0),
				enable(1),
				disable(2)
				}
			MAX-ACCESS read-only
			STATUS current
			DESCRIPTION
				"Description."
			::= { fkOSPFProcAreaInfoEntry 15 }

		
		-- 1.3.6.1.4.1.10428 9 1.101.51.2.9.1.1.1.16
		fkOSPFProcAreaNssaDefOriginate OBJECT-TYPE
			SYNTAX INTEGER
				{
				disable(0),
				enable(1)
				}
			MAX-ACCESS read-only
			STATUS current
			DESCRIPTION
				"Description."
			::= { fkOSPFProcAreaInfoEntry 16 }

		
		-- 1.3.6.1.4.1.10428 9 1.101.51.2.9.1.1.1.17
		fkOSPFProcAreaNssaDefMetricType OBJECT-TYPE
			SYNTAX INTEGER
				{
				none(0),
				external1(1),
				external2(2)
				}
			MAX-ACCESS read-only
			STATUS current
			DESCRIPTION
				"Description."
			::= { fkOSPFProcAreaInfoEntry 17 }

		
		-- 1.3.6.1.4.1.10428 9 1.101.51.2.9.1.1.1.18
		fkOSPFProcAreaNssaDefMetric OBJECT-TYPE
			SYNTAX INTEGER (0..16777214)
			MAX-ACCESS read-only
			STATUS current
			DESCRIPTION
				"Description."
			::= { fkOSPFProcAreaInfoEntry 18 }

		
		-- 1.3.6.1.4.1.10428 9 1.101.51.2.9.1.2
		fkOSPFProcAreaInfoControl OBJECT IDENTIFIER ::= { fkOSPFProcAreaInfo 2 }

		
		-- 1.3.6.1.4.1.10428 9 1.101.51.2.9.1.2.1
		fkOSPFProcAreaControlRequest OBJECT-TYPE
			SYNTAX INTEGER
				{
				createOSPFGeneralArea(1),
				createOSPFStubNssaArea(2),
				deleteOSPFArea(3),
				setOSPFAreaDefaultCostChange(4),
				setOSPFAreaAuthenTypeChange(5),
				setOSPFAreaFAInNameChange(6),
				setOSPFAreaFAOutNameChang(7),
				setOSPFAreaFPInNameChange(8),
				setOSPFAreaFPOutNameChange(9),
				setOSPFAreaShortcutTypeChange(10),
				setOSPFAreaSummary(11),
				setOSPFNssaAreaTranslateRole(12),
				setOSPFNssaAreaNoRedist(13),
				setOSPFNssaAreaDefaultProfile(14)
				}
			MAX-ACCESS read-write
			STATUS current
			DESCRIPTION
				"Description."
			::= { fkOSPFProcAreaInfoControl 1 }

		
		-- 1.3.6.1.4.1.10428 9 1.101.51.2.9.1.2.2
		fkOSPFProcAreaControlStatus OBJECT-TYPE
			SYNTAX FkControlStatusType
			MAX-ACCESS read-only
			STATUS current
			DESCRIPTION
				"Description."
			::= { fkOSPFProcAreaInfoControl 2 }

		
		-- 1.3.6.1.4.1.10428 9 1.101.51.2.9.1.2.3
		fkOSPFProcAreaControlTimer OBJECT-TYPE
			SYNTAX Gauge32
			MAX-ACCESS read-write
			STATUS current
			DESCRIPTION
				"Description."
			::= { fkOSPFProcAreaInfoControl 3 }

		
		-- 1.3.6.1.4.1.10428 9 1.101.51.2.9.1.2.4
		fkOSPFProcAreaControlTimeStamp OBJECT-TYPE
			SYNTAX TimeTicks
			MAX-ACCESS read-only
			STATUS current
			DESCRIPTION
				"Description."
			::= { fkOSPFProcAreaInfoControl 4 }

		
		-- 1.3.6.1.4.1.10428 9 1.101.51.2.9.1.2.5
		fkOSPFProcAreaControlReqResult OBJECT-TYPE
			SYNTAX FkControlRequestResultType
			MAX-ACCESS read-only
			STATUS current
			DESCRIPTION
				"Description."
			::= { fkOSPFProcAreaInfoControl 5 }

		
		-- 1.3.6.1.4.1.10428 9 1.101.51.2.9.1.2.6
		fkOSPFProcAreaControlProcID OBJECT-TYPE
			SYNTAX INTEGER (0..65535)
			MAX-ACCESS read-write
			STATUS current
			DESCRIPTION
				"Description."
			::= { fkOSPFProcAreaInfoControl 6 }

		
		-- 1.3.6.1.4.1.10428 9 1.101.51.2.9.1.2.7
		fkOSPFProcAreaControlID OBJECT-TYPE
			SYNTAX IpAddress
			MAX-ACCESS read-write
			STATUS current
			DESCRIPTION
				"Description."
			::= { fkOSPFProcAreaInfoControl 7 }

		
		-- 1.3.6.1.4.1.10428 9 1.101.51.2.9.1.2.8
		fkOSPFProcAreaControlType OBJECT-TYPE
			SYNTAX INTEGER
				{
				general(0),
				stub(1),
				nssa(2)
				}
			MAX-ACCESS read-write
			STATUS current
			DESCRIPTION
				"Description."
			::= { fkOSPFProcAreaInfoControl 8 }

		
		-- 1.3.6.1.4.1.10428 9 1.101.51.2.9.1.2.9
		fkOSPFProcAreaControlDefaultCost OBJECT-TYPE
			SYNTAX INTEGER (0..16777215)
			MAX-ACCESS read-write
			STATUS current
			DESCRIPTION
				"Description."
			::= { fkOSPFProcAreaInfoControl 9 }

		
		-- 1.3.6.1.4.1.10428 9 1.101.51.2.9.1.2.10
		fkOSPFProcAreaControlAuthenType OBJECT-TYPE
			SYNTAX INTEGER
				{
				null(0),
				simple(1),
				crypt(2)
				}
			MAX-ACCESS read-write
			STATUS current
			DESCRIPTION
				"Description."
			::= { fkOSPFProcAreaInfoControl 10 }

		
		-- 1.3.6.1.4.1.10428 9 1.101.51.2.9.1.2.11
		fkOSPFProcAreaControlFAInName OBJECT-TYPE
			SYNTAX OCTET STRING
			MAX-ACCESS read-write
			STATUS current
			DESCRIPTION
				"Description."
			::= { fkOSPFProcAreaInfoControl 11 }

		
		-- 1.3.6.1.4.1.10428 9 1.101.51.2.9.1.2.12
		fkOSPFProcAreaControlFAOutName OBJECT-TYPE
			SYNTAX OCTET STRING
			MAX-ACCESS read-write
			STATUS current
			DESCRIPTION
				"Description."
			::= { fkOSPFProcAreaInfoControl 12 }

		
		-- 1.3.6.1.4.1.10428 9 1.101.51.2.9.1.2.13
		fkOSPFProcAreaControlFPInName OBJECT-TYPE
			SYNTAX OCTET STRING
			MAX-ACCESS read-write
			STATUS current
			DESCRIPTION
				"Description."
			::= { fkOSPFProcAreaInfoControl 13 }

		
		-- 1.3.6.1.4.1.10428 9 1.101.51.2.9.1.2.14
		fkOSPFProcAreaControlFPOutName OBJECT-TYPE
			SYNTAX OCTET STRING
			MAX-ACCESS read-write
			STATUS current
			DESCRIPTION
				"Description."
			::= { fkOSPFProcAreaInfoControl 14 }

		
		-- 1.3.6.1.4.1.10428 9 1.101.51.2.9.1.2.15
		fkOSPFProcAreaControlShortcutType OBJECT-TYPE
			SYNTAX INTEGER
				{
				default(0),
				enable(1),
				disable(2)
				}
			MAX-ACCESS read-write
			STATUS current
			DESCRIPTION
				"Description."
			::= { fkOSPFProcAreaInfoControl 15 }

		
		-- 1.3.6.1.4.1.10428 9 1.101.51.2.9.1.2.16
		fkOSPFProcAreaControlSummary OBJECT-TYPE
			SYNTAX INTEGER
				{
				noAreaSummary(1),
				sendAreaSummary(2)
				}
			MAX-ACCESS read-write
			STATUS current
			DESCRIPTION
				"Description."
			::= { fkOSPFProcAreaInfoControl 16 }

		
		-- 1.3.6.1.4.1.10428 9 1.101.51.2.9.1.2.17
		fkOSPFProcAreaControlNssaTransRole OBJECT-TYPE
			SYNTAX INTEGER
				{
				never(0),
				always(1),
				candidate(2)
				}
			MAX-ACCESS read-write
			STATUS current
			DESCRIPTION
				"Description."
			::= { fkOSPFProcAreaInfoControl 17 }

		
		-- 1.3.6.1.4.1.10428 9 1.101.51.2.9.1.2.18
		fkOSPFProcAreaControlNssaNoRedist OBJECT-TYPE
			SYNTAX INTEGER
				{
				enable(1),
				disable(2)
				}
			MAX-ACCESS read-write
			STATUS current
			DESCRIPTION
				"Description."
			::= { fkOSPFProcAreaInfoControl 18 }

		
		-- 1.3.6.1.4.1.10428 9 1.101.51.2.9.1.2.19
		fkOSPFProcAreaControlNssaDefOriginate OBJECT-TYPE
			SYNTAX INTEGER
				{
				disable(0),
				enable(1)
				}
			MAX-ACCESS read-write
			STATUS current
			DESCRIPTION
				"Description."
			::= { fkOSPFProcAreaInfoControl 19 }

		
		-- 1.3.6.1.4.1.10428 9 1.101.51.2.9.1.2.20
		fkOSPFProcAreaControlNssaDefMetricType OBJECT-TYPE
			SYNTAX INTEGER
				{
				external1(1),
				external2(2)
				}
			MAX-ACCESS read-write
			STATUS current
			DESCRIPTION
				"Description."
			::= { fkOSPFProcAreaInfoControl 20 }

		
		-- 1.3.6.1.4.1.10428 9 1.101.51.2.9.1.2.21
		fkOSPFProcAreaControlNssaDefMetric OBJECT-TYPE
			SYNTAX INTEGER (0..16777214)
			MAX-ACCESS read-write
			STATUS current
			DESCRIPTION
				"Description."
			::= { fkOSPFProcAreaInfoControl 21 }

		
		-- 1.3.6.1.4.1.10428 9 1.101.51.2.9.1.3
		fkOSPFProcAreaInfoNotification OBJECT IDENTIFIER ::= { fkOSPFProcAreaInfo 3 }

		
		-- 1.3.6.1.4.1.10428 9 1.101.51.2.9.1.3.1
		fkOSPFProcGeneralAreaCreated NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaAuthenType, fkOSPFProcAreaFAInName, fkOSPFProcAreaFAOutName, fkOSPFProcAreaFPInName, 
				fkOSPFProcAreaFPOutName, fkOSPFProcAreaShortcutType }
			STATUS current
			DESCRIPTION 
				"Description."
			::= { fkOSPFProcAreaInfoNotification 1 }

		
		-- 1.3.6.1.4.1.10428 9 1.101.51.2.9.1.3.2
		fkOSPFProcStubNssaAreaCreated NOTIFICATION-TYPE
			OBJECTS { fkOSPFProcAreaControlRequest, fkOSPFProcAreaControlTimeStamp, fkOSPFProcAreaControlReqResult, fkOSPFProcID, fkOSPFProcAreaID, 
				fkOSPFProcAreaType }
			STATUS current
			DESCRIPTION 
				"Description."
			::= { fkOSPFProcAreaInfoNotification 2 }

		
		-- 1.3.6.1.4.1.10428 9 1.101.51.2.9.1.3.3
		fkOSPFProcAreaDeleted NOTIFICATION-TYPE
			OBJECTS { fkOSPFProcAreaControlRequest, fkOSPFProcAreaControlTimeStamp, fkOSPFProcAreaControlReqResult, fkOSPFProcID, fkOSPFProcAreaControlID, 
				fkOSPFProcAreaControlType }
			STATUS current
			DESCRIPTION 
				"Description."
			::= { fkOSPFProcAreaInfoNotification 3 }

		
		-- 1.3.6.1.4.1.10428 9 1.101.51.2.9.1.3.4
		fkOSPFProcAreaDefaultCostChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaDefaultCost }
			STATUS current
			DESCRIPTION 
				"Description."
			::= { fkOSPFProcAreaInfoNotification 4 }

		
		-- 1.3.6.1.4.1.10428 9 1.101.51.2.9.1.3.5
		fkOSPFProcAreaAuthenTypeChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaAuthenType }
			STATUS current
			DESCRIPTION 
				"Description."
			::= { fkOSPFProcAreaInfoNotification 5 }

		
		-- 1.3.6.1.4.1.10428 9 1.101.51.2.9.1.3.6
		fkOSPFProcAreaFAInNameChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaFAInName }
			STATUS current
			DESCRIPTION 
				"Description."
			::= { fkOSPFProcAreaInfoNotification 6 }

		
		-- 1.3.6.1.4.1.10428 9 1.101.51.2.9.1.3.7
		fkOSPFProcAreaFAOutNameChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaFAOutName }
			STATUS current
			DESCRIPTION 
				"Description."
			::= { fkOSPFProcAreaInfoNotification 7 }

		
		-- 1.3.6.1.4.1.10428 9 1.101.51.2.9.1.3.8
		fkOSPFProcAreaFPInNameChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaFPInName }
			STATUS current
			DESCRIPTION 
				"Description."
			::= { fkOSPFProcAreaInfoNotification 8 }

		
		-- 1.3.6.1.4.1.10428 9 1.101.51.2.9.1.3.9
		fkOSPFProcAreaFPOutNameChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaFPOutName }
			STATUS current
			DESCRIPTION 
				"Description."
			::= { fkOSPFProcAreaInfoNotification 9 }

		
		-- 1.3.6.1.4.1.10428 9 1.101.51.2.9.1.3.10
		fkOSPFProcAreaShortcutTypeChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaShortcutType }
			STATUS current
			DESCRIPTION 
				"Description."
			::= { fkOSPFProcAreaInfoNotification 10 }

		
		-- 1.3.6.1.4.1.10428 9 1.101.51.2.9.1.3.11
		fkOSPFProcAreaSummaryChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaSummary }
			STATUS current
			DESCRIPTION 
				"Description."
			::= { fkOSPFProcAreaInfoNotification 11 }

		
		-- 1.3.6.1.4.1.10428 9 1.101.51.2.9.1.3.12
		fkOSPFProcNssaAreaTransRoleChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaNssaTransRole }
			STATUS current
			DESCRIPTION 
				"Description."
			::= { fkOSPFProcAreaInfoNotification 12 }

		
		-- 1.3.6.1.4.1.10428 9 1.101.51.2.9.1.3.13
		fkOSPFProcNssaAreaTransNoRedistChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaNssaNoRedist }
			STATUS current
			DESCRIPTION 
				"Description."
			::= { fkOSPFProcAreaInfoNotification 13 }

		
		-- 1.3.6.1.4.1.10428 9 1.101.51.2.9.1.3.14
		fkOSPFProcNssaAreaDefProfileChanged NOTIFICATION-TYPE
			OBJECTS { fkOSPFProcAreaControlRequest, fkOSPFProcAreaControlTimeStamp, fkOSPFProcAreaControlReqResult, fkOSPFProcID, fkOSPFProcAreaID, 
				fkOSPFProcAreaType, fkOSPFProcAreaNssaDefOriginate, fkOSPFProcAreaNssaDefMetricType, fkOSPFProcAreaNssaDefMetric }
			STATUS current
			DESCRIPTION 
				"Description."
			::= { fkOSPFProcAreaInfoNotification 14 }

		
		-- 1.3.6.1.4.1.10428 9 1.101.51.2.9.2
		fkOSPFProcAreaRange OBJECT IDENTIFIER ::= { fkOSPFProcArea 2 }

		
		-- 1.3.6.1.4.1.10428 9 1.101.51.2.9.2.1
		fkOSPFProcAreaRangeTable OBJECT-TYPE
			SYNTAX SEQUENCE OF FkOSPFProcAreaRangeEntry
			MAX-ACCESS not-accessible
			STATUS current
			DESCRIPTION
				"Description."
			::= { fkOSPFProcAreaRange 1 }

		
		-- 1.3.6.1.4.1.10428 9 1.101.51.2.9.2.1.1
		fkOSPFProcAreaRangeEntry OBJECT-TYPE
			SYNTAX FkOSPFProcAreaRangeEntry
			MAX-ACCESS not-accessible
			STATUS current
			DESCRIPTION
				"Description."
			INDEX { fkOSPFProcID, fkOSPFProcAreaID, fkOSPFProcAreaRangeIP, fkOSPFProcAreaRangeIPMask }
			::= { fkOSPFProcAreaRangeTable 1 }

		
		FkOSPFProcAreaRangeEntry ::=
			SEQUENCE { 
				fkOSPFProcAreaRangeIP
					IpAddress,
				fkOSPFProcAreaRangeIPMask
					Integer32,
				fkOSPFProcAreaRangeAdverType
					INTEGER
			 }

		-- 1.3.6.1.4.1.10428 9 1.101.51.2.9.2.1.1.1
		fkOSPFProcAreaRangeIP OBJECT-TYPE
			SYNTAX IpAddress
			MAX-ACCESS read-only
			STATUS current
			DESCRIPTION
				"Description."
			::= { fkOSPFProcAreaRangeEntry 1 }

		
		-- 1.3.6.1.4.1.10428 9 1.101.51.2.9.2.1.1.2
		fkOSPFProcAreaRangeIPMask OBJECT-TYPE
			SYNTAX Integer32 (0..32)
			MAX-ACCESS read-only
			STATUS current
			DESCRIPTION
				"Description."
			::= { fkOSPFProcAreaRangeEntry 2 }

		
		-- 1.3.6.1.4.1.10428 9 1.101.51.2.9.2.1.1.3
		fkOSPFProcAreaRangeAdverType OBJECT-TYPE
			SYNTAX INTEGER
				{
				notAdvertise(0),
				advertise(1)
				}
			MAX-ACCESS read-only
			STATUS current
			DESCRIPTION
				"Description."
			::= { fkOSPFProcAreaRangeEntry 3 }

		
		-- 1.3.6.1.4.1.10428 9 1.101.51.2.9.2.2
		fkOSPFProcAreaRangeControl OBJECT IDENTIFIER ::= { fkOSPFProcAreaRange 2 }

		
		-- 1.3.6.1.4.1.10428 9 1.101.51.2.9.2.2.1
		fkOSPFProcAreaRangeControlRequest OBJECT-TYPE
			SYNTAX INTEGER
				{
				createOSPFAreaRange(1),
				deleteOSPFAreaRange(2),
				setOSPFAreaRange(3)
				}
			MAX-ACCESS read-write
			STATUS current
			DESCRIPTION
				"Description."
			::= { fkOSPFProcAreaRangeControl 1 }

		
		-- 1.3.6.1.4.1.10428 9 1.101.51.2.9.2.2.2
		fkOSPFProcAreaRangeControlStatus OBJECT-TYPE
			SYNTAX FkControlStatusType
			MAX-ACCESS read-only
			STATUS current
			DESCRIPTION
				"Description."
			::= { fkOSPFProcAreaRangeControl 2 }

		
		-- 1.3.6.1.4.1.10428 9 1.101.51.2.9.2.2.3
		fkOSPFProcAreaRangeControlTimer OBJECT-TYPE
			SYNTAX Gauge32
			MAX-ACCESS read-write
			STATUS current
			DESCRIPTION
				"Description."
			::= { fkOSPFProcAreaRangeControl 3 }

		
		-- 1.3.6.1.4.1.10428 9 1.101.51.2.9.2.2.4
		fkOSPFProcAreaRangeControlTimeStamp OBJECT-TYPE
			SYNTAX TimeTicks
			MAX-ACCESS read-only
			STATUS current
			DESCRIPTION
				"Description."
			::= { fkOSPFProcAreaRangeControl 4 }

		
		-- 1.3.6.1.4.1.10428 9 1.101.51.2.9.2.2.5
		fkOSPFProcAreaRangeControlReqResult OBJECT-TYPE
			SYNTAX FkControlRequestResultType
			MAX-ACCESS read-write
			STATUS current
			DESCRIPTION
				"Description."
			::= { fkOSPFProcAreaRangeControl 5 }

		
		-- 1.3.6.1.4.1.10428 9 1.101.51.2.9.2.2.6
		fkOSPFProcAreaRangeControlProcID OBJECT-TYPE
			SYNTAX INTEGER (0..65535)
			MAX-ACCESS read-write
			STATUS current
			DESCRIPTION
				"Description."
			::= { fkOSPFProcAreaRangeControl 6 }

		
		-- 1.3.6.1.4.1.10428 9 1.101.51.2.9.2.2.7
		fkOSPFProcAreaRangeControlID OBJECT-TYPE
			SYNTAX IpAddress
			MAX-ACCESS read-write
			STATUS current
			DESCRIPTION
				"Description."
			::= { fkOSPFProcAreaRangeControl 7 }

		
		-- 1.3.6.1.4.1.10428 9 1.101.51.2.9.2.2.8
		fkOSPFProcAreaRangeControlIP OBJECT-TYPE
			SYNTAX IpAddress
			MAX-ACCESS read-write
			STATUS current
			DESCRIPTION
				"Description."
			::= { fkOSPFProcAreaRangeControl 8 }

		
		-- 1.3.6.1.4.1.10428 9 1.101.51.2.9.2.2.9
		fkOSPFProcAreaRangeControlIPMask OBJECT-TYPE
			SYNTAX INTEGER (0..32)
			MAX-ACCESS read-write
			STATUS current
			DESCRIPTION
				"Description."
			::= { fkOSPFProcAreaRangeControl 9 }

		
		-- 1.3.6.1.4.1.10428 9 1.101.51.2.9.2.2.10
		fkOSPFProcAreaRangeControlAdverType OBJECT-TYPE
			SYNTAX INTEGER
				{
				notAdvertise(0),
				advertise(1)
				}
			MAX-ACCESS read-write
			STATUS current
			DESCRIPTION
				"Description."
			::= { fkOSPFProcAreaRangeControl 10 }

		
		-- 1.3.6.1.4.1.10428 9 1.101.51.2.9.2.3
		fkOSPFProcAreaRangeNotification OBJECT IDENTIFIER ::= { fkOSPFProcAreaRange 3 }

		
		-- 1.3.6.1.4.1.10428 9 1.101.51.2.9.2.3.1
		fkOSPFAreaRangeCreated NOTIFICATION-TYPE
			OBJECTS { fkOSPFProcAreaRangeControlRequest, fkOSPFProcAreaRangeControlTimeStamp, fkOSPFProcAreaRangeControlReqResult, fkOSPFProcID, fkOSPFProcAreaID, 
				fkOSPFProcAreaRangeIP, fkOSPFProcAreaRangeIPMask, fkOSPFProcAreaRangeAdverType }
			STATUS current
			DESCRIPTION 
				"Description."
			::= { fkOSPFProcAreaRangeNotification 1 }

		
		-- 1.3.6.1.4.1.10428 9 1.101.51.2.9.2.3.2
		fkOSPFAreaRangeDeleted NOTIFICATION-TYPE
			OBJECTS { fkOSPFProcAreaRangeControlRequest, fkOSPFProcAreaRangeControlTimeStamp, fkOSPFProcAreaRangeControlReqResult, fkOSPFProcID, fkOSPFProcAreaRangeControlID, 
				fkOSPFProcAreaRangeControlIP, fkOSPFProcAreaRangeControlIPMask, fkOSPFProcAreaRangeControlAdverType }
			STATUS current
			DESCRIPTION 
				"Description."
			::= { fkOSPFProcAreaRangeNotification 2 }

		
		-- 1.3.6.1.4.1.10428 9 1.101.51.2.9.2.3.3
		fkOSPFAreaRangeChanged NOTIFICATION-TYPE
			OBJECTS { fkOSPFProcAreaRangeControlRequest, fkOSPFProcAreaRangeControlTimeStamp, fkOSPFProcAreaRangeControlReqResult, fkOSPFProcID, fkOSPFProcAreaID, 
				fkOSPFProcAreaRangeIP, fkOSPFProcAreaRangeIPMask, fkOSPFProcAreaRangeAdverType }
			STATUS current
			DESCRIPTION 
				"Description."
			::= { fkOSPFProcAreaRangeNotification 3 }

		
		-- 1.3.6.1.4.1.10428 9 1.101.51.2.9.3
		fkOSPFProcAreaVlink OBJECT IDENTIFIER ::= { fkOSPFProcArea 3 }

		
		-- 1.3.6.1.4.1.10428 9 1.101.51.2.9.3.1
		fkOSPFProcAreaVlinkInfo OBJECT IDENTIFIER ::= { fkOSPFProcAreaVlink 1 }

		
		-- 1.3.6.1.4.1.10428 9 1.101.51.2.9.3.1.1
		fkOSPFProcAreaVlinkInfoTable OBJECT-TYPE
			SYNTAX SEQUENCE OF FkOSPFProcAreaVlinkInfoEntry
			MAX-ACCESS not-accessible
			STATUS current
			DESCRIPTION
				"Description."
			::= { fkOSPFProcAreaVlinkInfo 1 }

		
		-- 1.3.6.1.4.1.10428 9 1.101.51.2.9.3.1.1.1
		fkOSPFProcAreaVlinkInfoEntry OBJECT-TYPE
			SYNTAX FkOSPFProcAreaVlinkInfoEntry
			MAX-ACCESS not-accessible
			STATUS current
			DESCRIPTION
				"Description."
			INDEX { fkOSPFProcID, fkOSPFProcAreaID, fkOSPFProcAreaVlinkIP }
			::= { fkOSPFProcAreaVlinkInfoTable 1 }

		
		FkOSPFProcAreaVlinkInfoEntry ::=
			SEQUENCE { 
				fkOSPFProcAreaVlinkIP
					IpAddress,
				fkOSPFProcAreaVlinkAuthenType
					INTEGER,
				fkOSPFProcAreaVlinkAuthenKey
					OCTET STRING,
				fkOSPFProcAreaVlinkDeadInterval
					INTEGER,
				fkOSPFProcAreaVlinkHelloInterval
					INTEGER,
				fkOSPFProcAreaVlinkRetranInterval
					INTEGER,
				fkOSPFProcAreaVlinkTransDelay
					INTEGER
			 }

		-- 1.3.6.1.4.1.10428 9 1.101.51.2.9.3.1.1.1.1
		fkOSPFProcAreaVlinkIP OBJECT-TYPE
			SYNTAX IpAddress
			MAX-ACCESS read-only
			STATUS current
			DESCRIPTION
				"Description."
			::= { fkOSPFProcAreaVlinkInfoEntry 1 }

		
		-- 1.3.6.1.4.1.10428 9 1.101.51.2.9.3.1.1.1.2
		fkOSPFProcAreaVlinkAuthenType OBJECT-TYPE
			SYNTAX INTEGER
				{
				null(0),
				simple(1),
				crypto(2)
				}
			MAX-ACCESS read-only
			STATUS current
			DESCRIPTION
				"Description."
			::= { fkOSPFProcAreaVlinkInfoEntry 2 }

		
		-- 1.3.6.1.4.1.10428 9 1.101.51.2.9.3.1.1.1.3
		fkOSPFProcAreaVlinkAuthenKey OBJECT-TYPE
			SYNTAX OCTET STRING
			MAX-ACCESS read-only
			STATUS current
			DESCRIPTION
				"Description."
			::= { fkOSPFProcAreaVlinkInfoEntry 3 }

		
		-- 1.3.6.1.4.1.10428 9 1.101.51.2.9.3.1.1.1.4
		fkOSPFProcAreaVlinkDeadInterval OBJECT-TYPE
			SYNTAX INTEGER (0..65535)
			MAX-ACCESS read-only
			STATUS current
			DESCRIPTION
				"Description."
			::= { fkOSPFProcAreaVlinkInfoEntry 4 }

		
		-- 1.3.6.1.4.1.10428 9 1.101.51.2.9.3.1.1.1.5
		fkOSPFProcAreaVlinkHelloInterval OBJECT-TYPE
			SYNTAX INTEGER (0..65535)
			MAX-ACCESS read-only
			STATUS current
			DESCRIPTION
				"Description."
			::= { fkOSPFProcAreaVlinkInfoEntry 5 }

		
		-- 1.3.6.1.4.1.10428 9 1.101.51.2.9.3.1.1.1.6
		fkOSPFProcAreaVlinkRetranInterval OBJECT-TYPE
			SYNTAX INTEGER (0..65535)
			MAX-ACCESS read-only
			STATUS current
			DESCRIPTION
				"Description."
			::= { fkOSPFProcAreaVlinkInfoEntry 6 }

		
		-- 1.3.6.1.4.1.10428 9 1.101.51.2.9.3.1.1.1.7
		fkOSPFProcAreaVlinkTransDelay OBJECT-TYPE
			SYNTAX INTEGER (0..65535)
			MAX-ACCESS read-only
			STATUS current
			DESCRIPTION
				"Description."
			::= { fkOSPFProcAreaVlinkInfoEntry 7 }

		
		-- 1.3.6.1.4.1.10428 9 1.101.51.2.9.3.1.2
		fkOSPFProcAreaVlinkControl OBJECT IDENTIFIER ::= { fkOSPFProcAreaVlinkInfo 2 }

		
		-- 1.3.6.1.4.1.10428 9 1.101.51.2.9.3.1.2.1
		fkOSPFProcAreaVlinkControlRequest OBJECT-TYPE
			SYNTAX INTEGER
				{
				createOSPFAreaVlink(1),
				deleteOSPFAreaVlink(2),
				setOSPFAreaVlink(3)
				}
			MAX-ACCESS read-write
			STATUS current
			DESCRIPTION
				"Description."
			::= { fkOSPFProcAreaVlinkControl 1 }

		
		-- 1.3.6.1.4.1.10428 9 1.101.51.2.9.3.1.2.2
		fkOSPFProcAreaVlinkControlStatus OBJECT-TYPE
			SYNTAX FkControlStatusType
			MAX-ACCESS read-only
			STATUS current
			DESCRIPTION
				"Description."
			::= { fkOSPFProcAreaVlinkControl 2 }

		
		-- 1.3.6.1.4.1.10428 9 1.101.51.2.9.3.1.2.3
		fkOSPFProcAreaVlinkControlTimer OBJECT-TYPE
			SYNTAX Gauge32
			MAX-ACCESS read-write
			STATUS current
			DESCRIPTION
				"Description."
			::= { fkOSPFProcAreaVlinkControl 3 }

		
		-- 1.3.6.1.4.1.10428 9 1.101.51.2.9.3.1.2.4
		fkOSPFProcAreaVlinkControlTimeStamp OBJECT-TYPE
			SYNTAX TimeTicks
			MAX-ACCESS read-only
			STATUS current
			DESCRIPTION
				"Description."
			::= { fkOSPFProcAreaVlinkControl 4 }

		
		-- 1.3.6.1.4.1.10428 9 1.101.51.2.9.3.1.2.5
		fkOSPFProcAreaVlinkControlReqResult OBJECT-TYPE
			SYNTAX FkControlRequestResultType
			MAX-ACCESS read-only
			STATUS current
			DESCRIPTION
				"Description."
			::= { fkOSPFProcAreaVlinkControl 5 }

		
		-- 1.3.6.1.4.1.10428 9 1.101.51.2.9.3.1.2.6
		fkOSPFProcAreaVlinkControlProcID OBJECT-TYPE
			SYNTAX INTEGER (0..65535)
			MAX-ACCESS read-write
			STATUS current
			DESCRIPTION
				"Description."
			::= { fkOSPFProcAreaVlinkControl 6 }

		
		-- 1.3.6.1.4.1.10428 9 1.101.51.2.9.3.1.2.7
		fkOSPFProcAreaVlinkControlControlID OBJECT-TYPE
			SYNTAX Gauge32 (0..4294967295)
			MAX-ACCESS read-write
			STATUS current
			DESCRIPTION
				"Description."
			::= { fkOSPFProcAreaVlinkControl 7 }

		
		-- 1.3.6.1.4.1.10428 9 1.101.51.2.9.3.1.2.8
		fkOSPFProcAreaVlinkControlIP OBJECT-TYPE
			SYNTAX IpAddress
			MAX-ACCESS read-write
			STATUS current
			DESCRIPTION
				"Description."
			::= { fkOSPFProcAreaVlinkControl 8 }

		
		-- 1.3.6.1.4.1.10428 9 1.101.51.2.9.3.1.2.9
		fkOSPFProcAreaVlinkControlAuthenType OBJECT-TYPE
			SYNTAX INTEGER
				{
				null(0),
				simple(1),
				crypto(2)
				}
			MAX-ACCESS read-write
			STATUS current
			DESCRIPTION
				"Description."
			::= { fkOSPFProcAreaVlinkControl 9 }

		
		-- 1.3.6.1.4.1.10428 9 1.101.51.2.9.3.1.2.10
		fkOSPFProcAreaVlinkControlAuthenKey OBJECT-TYPE
			SYNTAX OCTET STRING
			MAX-ACCESS read-write
			STATUS current
			DESCRIPTION
				"Description."
			::= { fkOSPFProcAreaVlinkControl 10 }

		
		-- 1.3.6.1.4.1.10428 9 1.101.51.2.9.3.1.2.11
		fkOSPFProcAreaVlinkControlDeadInterval OBJECT-TYPE
			SYNTAX INTEGER (0..65535)
			MAX-ACCESS read-write
			STATUS current
			DESCRIPTION
				"Description."
			::= { fkOSPFProcAreaVlinkControl 11 }

		
		-- 1.3.6.1.4.1.10428 9 1.101.51.2.9.3.1.2.12
		fkOSPFProcAreaVlinkControlHelloInterval OBJECT-TYPE
			SYNTAX INTEGER (0..65535)
			MAX-ACCESS read-write
			STATUS current
			DESCRIPTION
				"Description."
			::= { fkOSPFProcAreaVlinkControl 12 }

		
		-- 1.3.6.1.4.1.10428 9 1.101.51.2.9.3.1.2.13
		fkOSPFProcAreaVlinkControlRetranInterval OBJECT-TYPE
			SYNTAX INTEGER (0..65535)
			MAX-ACCESS read-write
			STATUS current
			DESCRIPTION
				"Description."
			::= { fkOSPFProcAreaVlinkControl 13 }

		
		-- 1.3.6.1.4.1.10428 9 1.101.51.2.9.3.1.2.14
		fkOSPFProcAreaVlinkControlTransInterval OBJECT-TYPE
			SYNTAX INTEGER (0..65535)
			MAX-ACCESS read-write
			STATUS current
			DESCRIPTION
				"Description."
			::= { fkOSPFProcAreaVlinkControl 14 }

		
		-- 1.3.6.1.4.1.10428 9 1.101.51.2.9.3.1.3
		fkOSPFProcAreaVlinkNotification OBJECT IDENTIFIER ::= { fkOSPFProcAreaVlinkInfo 3 }

		
		-- 1.3.6.1.4.1.10428 9 1.101.51.2.9.3.1.3.1
		fkOSPFAreaVlinkCreated NOTIFICATION-TYPE
			OBJECTS { fkOSPFProcAreaVlinkControlRequest, fkOSPFProcAreaVlinkControlTimeStamp, fkOSPFProcAreaVlinkControlReqResult, fkOSPFProcID, fkOSPFProcAreaID, 
				fkOSPFProcAreaVlinkIP, fkOSPFProcAreaVlinkAuthenType, fkOSPFProcAreaVlinkAuthenKey, fkOSPFProcAreaVlinkDeadInterval, fkOSPFProcAreaVlinkHelloInterval, 
				fkOSPFProcAreaVlinkRetranInterval, fkOSPFProcAreaVlinkTransInterval }
			STATUS current
			DESCRIPTION 
				"Description."
			::= { fkOSPFProcAreaVlinkNotification 1 }

		
		-- 1.3.6.1.4.1.10428 9 1.101.51.2.9.3.1.3.2
		fkOSPFAreaVLinkDeleted NOTIFICATION-TYPE
			OBJECTS { fkOSPFProcAreaVlinkControlRequest, fkOSPFProcAreaVlinkControlTimeStamp, fkOSPFProcAreaVlinkControlReqResult, fkOSPFProcID, fkOSPFProcAreaVlinkControlControlID, 
				fkOSPFProcAreaVlinkControlIP }
			STATUS current
			DESCRIPTION 
				"Description."
			::= { fkOSPFProcAreaVlinkNotification 2 }

		
		-- 1.3.6.1.4.1.10428 9 1.101.51.2.9.3.1.3.3
		fkOSPFAreaVLinkChanged NOTIFICATION-TYPE
			OBJECTS { fkOSPFProcAreaVlinkControlRequest, fkOSPFProcAreaVlinkControlTimeStamp, fkOSPFProcAreaVlinkControlReqResult, fkOSPFProcID, fkOSPFProcAreaID, 
				fkOSPFProcAreaVlinkIP, fkOSPFProcAreaVlinkAuthenType, fkOSPFProcAreaVlinkAuthenKey, fkOSPFProcAreaVlinkDeadInterval, fkOSPFProcAreaVlinkHelloInterval, 
				fkOSPFProcAreaVlinkRetranInterval, fkOSPFProcAreaVlinkTransInterval }
			STATUS current
			DESCRIPTION 
				"Description."
			::= { fkOSPFProcAreaVlinkNotification 3 }

		
		-- 1.3.6.1.4.1.10428 9 1.101.51.2.9.3.2
		fkOSPFProcAreaVlinkMsgKey OBJECT IDENTIFIER ::= { fkOSPFProcAreaVlink 2 }

		
		-- 1.3.6.1.4.1.10428 9 1.101.51.2.9.3.2.1
		fkOSPFProcAreaVlinkMsgKeyTable OBJECT-TYPE
			SYNTAX SEQUENCE OF FkOSPFProcAreaVlinkMsgKeyEntry
			MAX-ACCESS not-accessible
			STATUS current
			DESCRIPTION
				"Description."
			::= { fkOSPFProcAreaVlinkMsgKey 1 }

		
		-- 1.3.6.1.4.1.10428 9 1.101.51.2.9.3.2.1.1
		fkOSPFProcAreaVlinkMsgKeyEntry OBJECT-TYPE
			SYNTAX FkOSPFProcAreaVlinkMsgKeyEntry
			MAX-ACCESS not-accessible
			STATUS current
			DESCRIPTION
				"Description."
			INDEX { fkOSPFProcID, fkOSPFProcAreaID, fkOSPFProcAreaVlinkIP, fkOSPFProcAreaVlinkMsgKeyID }
			::= { fkOSPFProcAreaVlinkMsgKeyTable 1 }

		
		FkOSPFProcAreaVlinkMsgKeyEntry ::=
			SEQUENCE { 
				fkOSPFProcAreaVlinkMsgKeyID
					Integer32,
				fkOSPFProcAreaVlinkMsgKeyVal
					OCTET STRING
			 }

		-- 1.3.6.1.4.1.10428 9 1.101.51.2.9.3.2.1.1.1
		fkOSPFProcAreaVlinkMsgKeyID OBJECT-TYPE
			SYNTAX Integer32 (0..255)
			MAX-ACCESS read-only
			STATUS current
			DESCRIPTION
				"Description."
			::= { fkOSPFProcAreaVlinkMsgKeyEntry 1 }

		
		-- 1.3.6.1.4.1.10428 9 1.101.51.2.9.3.2.1.1.2
		fkOSPFProcAreaVlinkMsgKeyVal OBJECT-TYPE
			SYNTAX OCTET STRING (SIZE (0..16))
			MAX-ACCESS read-only
			STATUS current
			DESCRIPTION
				"Description."
			::= { fkOSPFProcAreaVlinkMsgKeyEntry 2 }

		
		-- 1.3.6.1.4.1.10428 9 1.101.51.2.9.3.2.2
		fkOSPFProcAreaVlinkMsgKeyControl OBJECT IDENTIFIER ::= { fkOSPFProcAreaVlinkMsgKey 2 }

		
		-- 1.3.6.1.4.1.10428 9 1.101.51.2.9.3.2.2.1
		fkOSPFProcAreaVlinkMsgKeyControlRequest OBJECT-TYPE
			SYNTAX INTEGER
				{
				createOSPFAreaVlinkMsgKey(1),
				deleteOSPFAreaVlinkMsgKey(2)
				}
			MAX-ACCESS read-write
			STATUS current
			DESCRIPTION
				"Description."
			::= { fkOSPFProcAreaVlinkMsgKeyControl 1 }

		
		-- 1.3.6.1.4.1.10428 9 1.101.51.2.9.3.2.2.2
		fkOSPFProcAreaVlinkMsgKeyControlControlStatus OBJECT-TYPE
			SYNTAX FkControlStatusType
			MAX-ACCESS read-only
			STATUS current
			DESCRIPTION
				"Description."
			::= { fkOSPFProcAreaVlinkMsgKeyControl 2 }

		
		-- 1.3.6.1.4.1.10428 9 1.101.51.2.9.3.2.2.3
		fkOSPFProcAreaVlinkMsgKeyControlControlTimer OBJECT-TYPE
			SYNTAX Gauge32
			MAX-ACCESS read-write
			STATUS current
			DESCRIPTION
				"Description."
			::= { fkOSPFProcAreaVlinkMsgKeyControl 3 }

		
		-- 1.3.6.1.4.1.10428 9 1.101.51.2.9.3.2.2.4
		fkOSPFProcAreaVlinkMsgKeyControlTimeStamp OBJECT-TYPE
			SYNTAX TimeTicks
			MAX-ACCESS read-only
			STATUS current
			DESCRIPTION
				"Description."
			::= { fkOSPFProcAreaVlinkMsgKeyControl 4 }

		
		-- 1.3.6.1.4.1.10428 9 1.101.51.2.9.3.2.2.5
		fkOSPFProcAreaVlinkMsgKeyControlReqResult OBJECT-TYPE
			SYNTAX FkControlRequestResultType
			MAX-ACCESS read-only
			STATUS current
			DESCRIPTION
				"Description."
			::= { fkOSPFProcAreaVlinkMsgKeyControl 5 }

		
		-- 1.3.6.1.4.1.10428 9 1.101.51.2.9.3.2.2.6
		fkOSPFProcAreaVlinkMsgKeyControlProcID OBJECT-TYPE
			SYNTAX INTEGER (0..65535)
			MAX-ACCESS read-write
			STATUS current
			DESCRIPTION
				"Description."
			::= { fkOSPFProcAreaVlinkMsgKeyControl 6 }

		
		-- 1.3.6.1.4.1.10428 9 1.101.51.2.9.3.2.2.7
		fkOSPFProcAreaVlinkMsgKeyControlID OBJECT-TYPE
			SYNTAX Gauge32 (0..4294967295)
			MAX-ACCESS read-write
			STATUS current
			DESCRIPTION
				"Description."
			::= { fkOSPFProcAreaVlinkMsgKeyControl 7 }

		
		-- 1.3.6.1.4.1.10428 9 1.101.51.2.9.3.2.2.8
		fkOSPFProcAreaVlinkMsgKeyControlIP OBJECT-TYPE
			SYNTAX IpAddress
			MAX-ACCESS read-write
			STATUS current
			DESCRIPTION
				"Description."
			::= { fkOSPFProcAreaVlinkMsgKeyControl 8 }

		
		-- 1.3.6.1.4.1.10428 9 1.101.51.2.9.3.2.2.9
		fkOSPFProcAreaVlinkMsgKeyControlKeyID OBJECT-TYPE
			SYNTAX INTEGER (0..255)
			MAX-ACCESS read-write
			STATUS current
			DESCRIPTION
				"Description."
			::= { fkOSPFProcAreaVlinkMsgKeyControl 9 }

		
		-- 1.3.6.1.4.1.10428 9 1.101.51.2.9.3.2.2.10
		fkOSPFProcAreaVlinkMsgKeyControlKeyVal OBJECT-TYPE
			SYNTAX OCTET STRING (SIZE (0..16))
			MAX-ACCESS read-write
			STATUS current
			DESCRIPTION
				"Description."
			::= { fkOSPFProcAreaVlinkMsgKeyControl 10 }

		
		-- 1.3.6.1.4.1.10428 9 1.101.51.2.9.3.2.3
		fkOSPFProcAreaVlinkMsgKeyNotification OBJECT IDENTIFIER ::= { fkOSPFProcAreaVlinkMsgKey 3 }

		
		-- 1.3.6.1.4.1.10428 9 1.101.51.2.9.3.2.3.1
		fkOSPFAreaVlinkMsgKeyCreated NOTIFICATION-TYPE
			OBJECTS { fkOSPFProcAreaVlinkControlRequest, fkOSPFProcAreaVlinkControlTimeStamp, fkOSPFProcAreaVlinkControlReqResult, fkOSPFProcID, fkOSPFProcAreaID, 
				fkOSPFProcAreaVlinkIP, fkOSPFProcAreaVlinkMsgKeyID, fkOSPFProcAreaVlinkMsgKeyVal }
			STATUS current
			DESCRIPTION 
				"Description."
			::= { fkOSPFProcAreaVlinkMsgKeyNotification 1 }

		
		-- 1.3.6.1.4.1.10428 9 1.101.51.2.9.3.2.3.2
		fkOSPFAreaVLinkMsgKeyDeleted NOTIFICATION-TYPE
			OBJECTS { fkOSPFProcAreaVlinkControlRequest, fkOSPFProcAreaVlinkControlTimeStamp, fkOSPFProcAreaVlinkControlReqResult, fkOSPFProcID, fkOSPFProcAreaID, 
				fkOSPFProcAreaVlinkIP, fkOSPFProcAreaVlinkMsgKeyControlKeyID }
			STATUS current
			DESCRIPTION 
				"Description."
			::= { fkOSPFProcAreaVlinkMsgKeyNotification 2 }

		
		-- 1.3.6.1.4.1.10428 9 1.101.51.3
		fkOSPFInterface OBJECT IDENTIFIER ::= { fkOspf 3 }

		
		-- 1.3.6.1.4.1.10428 9 1.101.51.3.1
		fkOSPFIf OBJECT IDENTIFIER ::= { fkOSPFInterface 1 }

		
		-- 1.3.6.1.4.1.10428 9 1.101.51.3.1.1
		fkOSPFIfTable OBJECT-TYPE
			SYNTAX SEQUENCE OF FkOSPFIfEntry
			MAX-ACCESS not-accessible
			STATUS current
			DESCRIPTION
				"Description."
			::= { fkOSPFIf 1 }

		
		-- 1.3.6.1.4.1.10428 9 1.101.51.3.1.1.1
		fkOSPFIfEntry OBJECT-TYPE
			SYNTAX FkOSPFIfEntry
			MAX-ACCESS not-accessible
			STATUS current
			DESCRIPTION
				"Description."
			INDEX { fkOSPFIfIndex }
			::= { fkOSPFIfTable 1 }

		
		FkOSPFIfEntry ::=
			SEQUENCE { 
				fkOSPFIfIndex
					Integer32,
				fkOSFPIfEnabled
					INTEGER,
				fkOSPFIfNetworkType
					INTEGER,
				fkOSFPIfMTU
					INTEGER,
				fkOSFPIfBFD
					INTEGER,
				fkOSFPIfEFM
					INTEGER
			 }

		-- 1.3.6.1.4.1.10428 9 1.101.51.3.1.1.1.1
		fkOSPFIfIndex OBJECT-TYPE
			SYNTAX Integer32 (1..4097)
			MAX-ACCESS read-only
			STATUS current
			DESCRIPTION
				"Description."
			::= { fkOSPFIfEntry 1 }

		
		-- 1.3.6.1.4.1.10428 9 1.101.51.3.1.1.1.2
		fkOSFPIfEnabled OBJECT-TYPE
			SYNTAX INTEGER
				{
				disable(0),
				enable(1)
				}
			MAX-ACCESS read-only
			STATUS current
			DESCRIPTION
				"Description."
			::= { fkOSPFIfEntry 2 }

		
		-- 1.3.6.1.4.1.10428 9 1.101.51.3.1.1.1.3
		fkOSPFIfNetworkType OBJECT-TYPE
			SYNTAX INTEGER
				{
				none(0),
				p2p(1),
				broadcast(2),
				nbma(3),
				p2mp(4),
				p2mpNbma(5),
				virtuallink(6),
				loopback(7)
				}
			MAX-ACCESS read-only
			STATUS current
			DESCRIPTION
				"Description."
			::= { fkOSPFIfEntry 3 }

		
		-- 1.3.6.1.4.1.10428 9 1.101.51.3.1.1.1.4
		fkOSFPIfMTU OBJECT-TYPE
			SYNTAX INTEGER (576..65535)
			MAX-ACCESS read-only
			STATUS current
			DESCRIPTION
				"Description."
			::= { fkOSPFIfEntry 4 }

		
		-- 1.3.6.1.4.1.10428 9 1.101.51.3.1.1.1.5
		fkOSFPIfBFD OBJECT-TYPE
			SYNTAX INTEGER
				{
				disable(0),
				enable(1),
				none(2)
				}
			MAX-ACCESS read-only
			STATUS current
			DESCRIPTION
				"Description."
			::= { fkOSPFIfEntry 5 }

		
		-- 1.3.6.1.4.1.10428 9 1.101.51.3.1.1.1.6
		fkOSFPIfEFM OBJECT-TYPE
			SYNTAX INTEGER
				{
				disable(0),
				enable(1),
				none(2)
				}
			MAX-ACCESS read-only
			STATUS current
			DESCRIPTION
				"Description."
			::= { fkOSPFIfEntry 6 }

		
		-- 1.3.6.1.4.1.10428 9 1.101.51.3.1.2
		fkOSPFIfControl OBJECT IDENTIFIER ::= { fkOSPFIf 2 }

		
		-- 1.3.6.1.4.1.10428 9 1.101.51.3.1.2.1
		fkOSPFIfControlRequest OBJECT-TYPE
			SYNTAX INTEGER
				{
				setOSPFIFEnabled(1),
				setOSPFIFNetworkType(2),
				setOSPFIFMTU(3),
				setOSPFIFBFD(4),
				setOSPFIFEFM(5)
				}
			MAX-ACCESS read-write
			STATUS current
			DESCRIPTION
				"Description."
			::= { fkOSPFIfControl 1 }

		
		-- 1.3.6.1.4.1.10428 9 1.101.51.3.1.2.2
		fkOSPFIfControlStatus OBJECT-TYPE
			SYNTAX FkControlStatusType
			MAX-ACCESS read-only
			STATUS current
			DESCRIPTION
				"Description."
			::= { fkOSPFIfControl 2 }

		
		-- 1.3.6.1.4.1.10428 9 1.101.51.3.1.2.3
		fkOSPFIfControlTimer OBJECT-TYPE
			SYNTAX Gauge32
			MAX-ACCESS read-write
			STATUS current
			DESCRIPTION
				"Description."
			::= { fkOSPFIfControl 3 }

		
		-- 1.3.6.1.4.1.10428 9 1.101.51.3.1.2.4
		fkOSPFIfControlTimeStamp OBJECT-TYPE
			SYNTAX TimeTicks
			MAX-ACCESS read-only
			STATUS current
			DESCRIPTION
				"Description."
			::= { fkOSPFIfControl 4 }

		
		-- 1.3.6.1.4.1.10428 9 1.101.51.3.1.2.5
		fkOSPFIfControlReqResult OBJECT-TYPE
			SYNTAX FkControlRequestResultType
			MAX-ACCESS read-only
			STATUS current
			DESCRIPTION
				"Description."
			::= { fkOSPFIfControl 5 }

		
		-- 1.3.6.1.4.1.10428 9 1.101.51.3.1.2.6
		fkOSPFIfControlIndex OBJECT-TYPE
			SYNTAX INTEGER (0..65535)
			MAX-ACCESS read-write
			STATUS current
			DESCRIPTION
				"Description."
			::= { fkOSPFIfControl 6 }

		
		-- 1.3.6.1.4.1.10428 9 1.101.51.3.1.2.7
		fkOSPFIfControlEnabled OBJECT-TYPE
			SYNTAX INTEGER
				{
				disable(0),
				enable(1)
				}
			MAX-ACCESS read-write
			STATUS current
			DESCRIPTION
				"Description."
			::= { fkOSPFIfControl 7 }

		
		-- 1.3.6.1.4.1.10428 9 1.101.51.3.1.2.8
		fkOSPFIfControlNetworkType OBJECT-TYPE
			SYNTAX INTEGER
				{
				none(0),
				p2p(1),
				broadcast(2),
				nbma(3),
				p2mp(4),
				p2mpNbma(5)
				}
			MAX-ACCESS read-write
			STATUS current
			DESCRIPTION
				"Description."
			::= { fkOSPFIfControl 8 }

		
		-- 1.3.6.1.4.1.10428 9 1.101.51.3.1.2.9
		fkOSPFIfControlMTU OBJECT-TYPE
			SYNTAX INTEGER (576..65535)
			MAX-ACCESS read-write
			STATUS current
			DESCRIPTION
				"Description."
			::= { fkOSPFIfControl 9 }

		
		-- 1.3.6.1.4.1.10428 9 1.101.51.3.1.2.10
		fkOSPFIfControlBFD OBJECT-TYPE
			SYNTAX INTEGER
				{
				disable(0),
				enable(1),
				none(2)
				}
			MAX-ACCESS read-write
			STATUS current
			DESCRIPTION
				"Description."
			::= { fkOSPFIfControl 10 }

		
		-- 1.3.6.1.4.1.10428 9 1.101.51.3.1.2.11
		fkOSPFIfControlEFM OBJECT-TYPE
			SYNTAX INTEGER
				{
				disable(0),
				enable(1),
				none(2)
				}
			MAX-ACCESS read-write
			STATUS current
			DESCRIPTION
				"Description."
			::= { fkOSPFIfControl 11 }

		
		-- 1.3.6.1.4.1.10428 9 1.101.51.3.1.3
		fkOSPFIfBaseNotification OBJECT IDENTIFIER ::= { fkOSPFIf 3 }

		
		-- 1.3.6.1.4.1.10428 9 1.101.51.3.1.3.1
		fkOSPFIfEnableChanged NOTIFICATION-TYPE
			OBJECTS { fkOSPFIfControlRequest, fkOSPFIfControlTimeStamp, fkOSPFIfControlReqResult, fkOSFPIfEnabled, fkOSPFIfIndex
				 }
			STATUS current
			DESCRIPTION 
				"Description."
			::= { fkOSPFIfBaseNotification 1 }

		
		-- 1.3.6.1.4.1.10428 9 1.101.51.3.1.3.2
		fkOSPFIfNetworkTypeChanged NOTIFICATION-TYPE
			OBJECTS { fkOSPFIfControlRequest, fkOSPFIfControlTimeStamp, fkOSPFIfControlReqResult, fkOSPFIfIndex, fkOSPFIfNetworkType
				 }
			STATUS current
			DESCRIPTION 
				"Description."
			::= { fkOSPFIfBaseNotification 2 }

		
		-- 1.3.6.1.4.1.10428 9 1.101.51.3.1.3.3
		fkOSPFIfMTUChanged NOTIFICATION-TYPE
			OBJECTS { fkOSPFIfControlRequest, fkOSPFIfControlTimeStamp, fkOSPFIfControlReqResult, fkOSPFIfIndex, fkOSFPIfMTU
				 }
			STATUS current
			DESCRIPTION 
				"Description."
			::= { fkOSPFIfBaseNotification 3 }

		
		-- 1.3.6.1.4.1.10428 9 1.101.51.3.1.3.4
		fkOSPFIfBFDChanged NOTIFICATION-TYPE
			OBJECTS { fkOSPFIfControlRequest, fkOSPFIfControlTimeStamp, fkOSPFIfControlReqResult, fkOSPFIfIndex, fkOSFPIfBFD
				 }
			STATUS current
			DESCRIPTION 
				"Description."
			::= { fkOSPFIfBaseNotification 4 }

		
		-- 1.3.6.1.4.1.10428 9 1.101.51.3.1.3.5
		fkOSPFIfEFMChanged NOTIFICATION-TYPE
			OBJECTS { fkOSPFIfControlRequest, fkOSPFIfControlTimeStamp, fkOSPFIfControlReqResult, fkOSPFIfIndex, fkOSFPIfEFM
				 }
			STATUS current
			DESCRIPTION 
				"Description."
			::= { fkOSPFIfBaseNotification 5 }

		
		-- 1.3.6.1.4.1.10428 9 1.101.51.3.2
		fkOSPFIfInfo OBJECT IDENTIFIER ::= { fkOSPFInterface 2 }

		
		-- 1.3.6.1.4.1.10428 9 1.101.51.3.2.1
		fkOSPFIfInfoTable OBJECT-TYPE
			SYNTAX SEQUENCE OF FkOSPFIfInfoEntry
			MAX-ACCESS not-accessible
			STATUS current
			DESCRIPTION
				"Description."
			::= { fkOSPFIfInfo 1 }

		
		-- 1.3.6.1.4.1.10428 9 1.101.51.3.2.1.1
		fkOSPFIfInfoEntry OBJECT-TYPE
			SYNTAX FkOSPFIfInfoEntry
			MAX-ACCESS not-accessible
			STATUS current
			DESCRIPTION
				"Description."
			INDEX { fkOSPFIfIndex, fkOSPFIfIpAddr }
			::= { fkOSPFIfInfoTable 1 }

		
		FkOSPFIfInfoEntry ::=
			SEQUENCE { 
				fkOSPFIfIpAddr
					IpAddress,
				fkOSPFIfCost
					INTEGER,
				fkOSPFIfTransmitDelay
					INTEGER,
				fkOSPFIfPriority
					INTEGER,
				fkOSPFIfHelloInterval
					INTEGER,
				fkOSPFIfDeadInterval
					INTEGER,
				fkOSPFIfRetransInterval
					INTEGER,
				fkOSPFIfAuth
					INTEGER,
				fkOSPFIfAuthType
					INTEGER,
				fkOSPFIfDataFilterOut
					INTEGER,
				fkOSPFIfMTUIgnore
					INTEGER,
				fkOSPFIfResync
					INTEGER,
				fkOSPFIfResyncTimeout
					INTEGER,
				fkOSPFIfAuthKeyFirst
					OCTET STRING,
				fkOSPFIfAuthKeyFirstAct
					INTEGER,
				fkOSPFIfAuthKeySecond
					OCTET STRING,
				fkOSPFIfAuthKeySecondAct
					INTEGER
			 }

		-- 1.3.6.1.4.1.10428 9 1.101.51.3.2.1.1.1
		fkOSPFIfIpAddr OBJECT-TYPE
			SYNTAX IpAddress
			MAX-ACCESS read-only
			STATUS current
			DESCRIPTION
				"Description."
			::= { fkOSPFIfInfoEntry 1 }

		
		-- 1.3.6.1.4.1.10428 9 1.101.51.3.2.1.1.2
		fkOSPFIfCost OBJECT-TYPE
			SYNTAX INTEGER (0..65535)
			MAX-ACCESS read-only
			STATUS current
			DESCRIPTION
				"Description."
			::= { fkOSPFIfInfoEntry 2 }

		
		-- 1.3.6.1.4.1.10428 9 1.101.51.3.2.1.1.3
		fkOSPFIfTransmitDelay OBJECT-TYPE
			SYNTAX INTEGER (0..65535)
			MAX-ACCESS read-only
			STATUS current
			DESCRIPTION
				"Description."
			::= { fkOSPFIfInfoEntry 3 }

		
		-- 1.3.6.1.4.1.10428 9 1.101.51.3.2.1.1.4
		fkOSPFIfPriority OBJECT-TYPE
			SYNTAX INTEGER (0..255)
			MAX-ACCESS read-only
			STATUS current
			DESCRIPTION
				"Description."
			::= { fkOSPFIfInfoEntry 4 }

		
		-- 1.3.6.1.4.1.10428 9 1.101.51.3.2.1.1.5
		fkOSPFIfHelloInterval OBJECT-TYPE
			SYNTAX INTEGER (0..65535)
			MAX-ACCESS read-only
			STATUS current
			DESCRIPTION
				"Description."
			::= { fkOSPFIfInfoEntry 5 }

		
		-- 1.3.6.1.4.1.10428 9 1.101.51.3.2.1.1.6
		fkOSPFIfDeadInterval OBJECT-TYPE
			SYNTAX INTEGER (0..65535)
			MAX-ACCESS read-only
			STATUS current
			DESCRIPTION
				"Description."
			::= { fkOSPFIfInfoEntry 6 }

		
		-- 1.3.6.1.4.1.10428 9 1.101.51.3.2.1.1.7
		fkOSPFIfRetransInterval OBJECT-TYPE
			SYNTAX INTEGER (0..65535)
			MAX-ACCESS read-only
			STATUS current
			DESCRIPTION
				"Description."
			::= { fkOSPFIfInfoEntry 7 }

		
		-- 1.3.6.1.4.1.10428 9 1.101.51.3.2.1.1.8
		fkOSPFIfAuth OBJECT-TYPE
			SYNTAX INTEGER
				{
				disable(0),
				enable(1)
				}
			MAX-ACCESS read-only
			STATUS current
			DESCRIPTION
				"Description."
			::= { fkOSPFIfInfoEntry 8 }

		
		-- 1.3.6.1.4.1.10428 9 1.101.51.3.2.1.1.9
		fkOSPFIfAuthType OBJECT-TYPE
			SYNTAX INTEGER
				{
				null(0),
				simple(1),
				crypt(2)
				}
			MAX-ACCESS read-only
			STATUS current
			DESCRIPTION
				"Description."
			::= { fkOSPFIfInfoEntry 9 }

		
		-- 1.3.6.1.4.1.10428 9 1.101.51.3.2.1.1.10
		fkOSPFIfDataFilterOut OBJECT-TYPE
			SYNTAX INTEGER
				{
				disable(0),
				enable(1)
				}
			MAX-ACCESS read-only
			STATUS current
			DESCRIPTION
				"Description."
			::= { fkOSPFIfInfoEntry 10 }

		
		-- 1.3.6.1.4.1.10428 9 1.101.51.3.2.1.1.11
		fkOSPFIfMTUIgnore OBJECT-TYPE
			SYNTAX INTEGER
				{
				disable(0),
				enable(1)
				}
			MAX-ACCESS read-only
			STATUS current
			DESCRIPTION
				"Description."
			::= { fkOSPFIfInfoEntry 11 }

		
		-- 1.3.6.1.4.1.10428 9 1.101.51.3.2.1.1.12
		fkOSPFIfResync OBJECT-TYPE
			SYNTAX INTEGER
				{
				disable(0),
				enable(1)
				}
			MAX-ACCESS read-only
			STATUS current
			DESCRIPTION
				"Description."
			::= { fkOSPFIfInfoEntry 12 }

		
		-- 1.3.6.1.4.1.10428 9 1.101.51.3.2.1.1.13
		fkOSPFIfResyncTimeout OBJECT-TYPE
			SYNTAX INTEGER (0..65535)
			MAX-ACCESS read-only
			STATUS current
			DESCRIPTION
				"Description."
			::= { fkOSPFIfInfoEntry 13 }

		
		-- 1.3.6.1.4.1.10428 9 1.101.51.3.2.1.1.14
		fkOSPFIfAuthKeyFirst OBJECT-TYPE
			SYNTAX OCTET STRING
			MAX-ACCESS read-only
			STATUS current
			DESCRIPTION
				"Description."
			::= { fkOSPFIfInfoEntry 14 }

		
		-- 1.3.6.1.4.1.10428 9 1.101.51.3.2.1.1.15
		fkOSPFIfAuthKeyFirstAct OBJECT-TYPE
			SYNTAX INTEGER
				{
				deactive(0),
				active(1)
				}
			MAX-ACCESS read-only
			STATUS current
			DESCRIPTION
				"Description."
			::= { fkOSPFIfInfoEntry 15 }

		
		-- 1.3.6.1.4.1.10428 9 1.101.51.3.2.1.1.16
		fkOSPFIfAuthKeySecond OBJECT-TYPE
			SYNTAX OCTET STRING
			MAX-ACCESS read-only
			STATUS current
			DESCRIPTION
				"Description."
			::= { fkOSPFIfInfoEntry 16 }

		
		-- 1.3.6.1.4.1.10428 9 1.101.51.3.2.1.1.17
		fkOSPFIfAuthKeySecondAct OBJECT-TYPE
			SYNTAX INTEGER
				{
				deactive(0),
				active(1)
				}
			MAX-ACCESS read-only
			STATUS current
			DESCRIPTION
				"Description."
			::= { fkOSPFIfInfoEntry 17 }

		
		-- 1.3.6.1.4.1.10428 9 1.101.51.3.2.2
		fkOSPFIfInfoControl OBJECT IDENTIFIER ::= { fkOSPFIfInfo 2 }

		
		-- 1.3.6.1.4.1.10428 9 1.101.51.3.2.2.1
		fkOSPFIfInfoControlRequest OBJECT-TYPE
			SYNTAX INTEGER
				{
				setOSPFIFCost(1),
				setOSPFIFPriority(2),
				setOSPFIFTransmitDelay(3),
				setOSPFIFHelloInterval(4),
				setOSPFIFDeadInterval(5),
				setOSPFIFRetransInterval(6),
				setOSPFIFAuthProfile(7),
				setOSPFIFDataFilterOut(8),
				setOSPFIFMtuIgnore(9),
				setOSPFIFResyncProfile(10),
				setOSPFIFAuthKeyFirstProfile(11),
				setOSPFIFAuthKeySecondProfile(12)
				}
			MAX-ACCESS read-write
			STATUS current
			DESCRIPTION
				"Description."
			::= { fkOSPFIfInfoControl 1 }

		
		-- 1.3.6.1.4.1.10428 9 1.101.51.3.2.2.2
		fkOSPFIfInfoControlStatus OBJECT-TYPE
			SYNTAX FkControlStatusType
			MAX-ACCESS read-only
			STATUS current
			DESCRIPTION
				"Description."
			::= { fkOSPFIfInfoControl 2 }

		
		-- 1.3.6.1.4.1.10428 9 1.101.51.3.2.2.3
		fkOSPFIfInfoControlTimer OBJECT-TYPE
			SYNTAX Gauge32
			MAX-ACCESS read-write
			STATUS current
			DESCRIPTION
				"Description."
			::= { fkOSPFIfInfoControl 3 }

		
		-- 1.3.6.1.4.1.10428 9 1.101.51.3.2.2.4
		fkOSPFIfInfoControlTimeStamp OBJECT-TYPE
			SYNTAX TimeTicks
			MAX-ACCESS read-only
			STATUS current
			DESCRIPTION
				"Description."
			::= { fkOSPFIfInfoControl 4 }

		
		-- 1.3.6.1.4.1.10428 9 1.101.51.3.2.2.5
		fkOSPFIfInfoControlReqResult OBJECT-TYPE
			SYNTAX FkControlRequestResultType
			MAX-ACCESS read-only
			STATUS current
			DESCRIPTION
				"Description."
			::= { fkOSPFIfInfoControl 5 }

		
		-- 1.3.6.1.4.1.10428 9 1.101.51.3.2.2.6
		fkOSPFIfInfoControlIndex OBJECT-TYPE
			SYNTAX INTEGER (0..65535)
			MAX-ACCESS read-write
			STATUS current
			DESCRIPTION
				"Description."
			::= { fkOSPFIfInfoControl 6 }

		
		-- 1.3.6.1.4.1.10428 9 1.101.51.3.2.2.7
		fkOSPFIfInfoControlIpAddr OBJECT-TYPE
			SYNTAX IpAddress
			MAX-ACCESS read-write
			STATUS current
			DESCRIPTION
				"Description."
			::= { fkOSPFIfInfoControl 7 }

		
		-- 1.3.6.1.4.1.10428 9 1.101.51.3.2.2.8
		fkOSPFIfInfoControlCost OBJECT-TYPE
			SYNTAX INTEGER (0..65535)
			MAX-ACCESS read-write
			STATUS current
			DESCRIPTION
				"Description."
			::= { fkOSPFIfInfoControl 8 }

		
		-- 1.3.6.1.4.1.10428 9 1.101.51.3.2.2.9
		fkOSPFIfInfoControlTransmitDelay OBJECT-TYPE
			SYNTAX INTEGER (0..65535)
			MAX-ACCESS read-write
			STATUS current
			DESCRIPTION
				"Description."
			::= { fkOSPFIfInfoControl 9 }

		
		-- 1.3.6.1.4.1.10428 9 1.101.51.3.2.2.10
		fkOSPFIfInfoControlPriority OBJECT-TYPE
			SYNTAX INTEGER (0..255)
			MAX-ACCESS read-write
			STATUS current
			DESCRIPTION
				"Description."
			::= { fkOSPFIfInfoControl 10 }

		
		-- 1.3.6.1.4.1.10428 9 1.101.51.3.2.2.11
		fkOSPFIfInfoControlHelloInterval OBJECT-TYPE
			SYNTAX INTEGER (0..65535)
			MAX-ACCESS read-write
			STATUS current
			DESCRIPTION
				"Description."
			::= { fkOSPFIfInfoControl 11 }

		
		-- 1.3.6.1.4.1.10428 9 1.101.51.3.2.2.12
		fkOSPFIfInfoControlDeadInterval OBJECT-TYPE
			SYNTAX INTEGER (0..65535)
			MAX-ACCESS read-write
			STATUS current
			DESCRIPTION
				"Description."
			::= { fkOSPFIfInfoControl 12 }

		
		-- 1.3.6.1.4.1.10428 9 1.101.51.3.2.2.13
		fkOSPFIfInfoControlRetransInterval OBJECT-TYPE
			SYNTAX INTEGER (0..65535)
			MAX-ACCESS read-write
			STATUS current
			DESCRIPTION
				"Description."
			::= { fkOSPFIfInfoControl 13 }

		
		-- 1.3.6.1.4.1.10428 9 1.101.51.3.2.2.14
		fkOSPFIfInfoControlAuth OBJECT-TYPE
			SYNTAX INTEGER
				{
				disable(0),
				enable(1)
				}
			MAX-ACCESS read-write
			STATUS current
			DESCRIPTION
				"Description."
			::= { fkOSPFIfInfoControl 14 }

		
		-- 1.3.6.1.4.1.10428 9 1.101.51.3.2.2.15
		fkOSPFIfInfoControlAuthType OBJECT-TYPE
			SYNTAX INTEGER
				{
				null(0),
				simple(1),
				crypt(2)
				}
			MAX-ACCESS read-write
			STATUS current
			DESCRIPTION
				"Description."
			::= { fkOSPFIfInfoControl 15 }

		
		-- 1.3.6.1.4.1.10428 9 1.101.51.3.2.2.16
		fkOSPFIfInfoControlDataFilterOut OBJECT-TYPE
			SYNTAX INTEGER
				{
				disable(0),
				enable(1)
				}
			MAX-ACCESS read-write
			STATUS current
			DESCRIPTION
				"Description."
			::= { fkOSPFIfInfoControl 16 }

		
		-- 1.3.6.1.4.1.10428 9 1.101.51.3.2.2.17
		fkOSPFIfInfoControlMTUIgnore OBJECT-TYPE
			SYNTAX INTEGER
				{
				disable(0),
				enable(1)
				}
			MAX-ACCESS read-write
			STATUS current
			DESCRIPTION
				"Description."
			::= { fkOSPFIfInfoControl 17 }

		
		-- 1.3.6.1.4.1.10428 9 1.101.51.3.2.2.18
		fkOSPFIfInfoControlResync OBJECT-TYPE
			SYNTAX INTEGER
				{
				disable(0),
				enable(1)
				}
			MAX-ACCESS read-write
			STATUS current
			DESCRIPTION
				"Description."
			::= { fkOSPFIfInfoControl 18 }

		
		-- 1.3.6.1.4.1.10428 9 1.101.51.3.2.2.19
		fkOSPFIfInfoControlResyncTimeout OBJECT-TYPE
			SYNTAX INTEGER (0..65535)
			MAX-ACCESS read-write
			STATUS current
			DESCRIPTION
				"Description."
			::= { fkOSPFIfInfoControl 19 }

		
		-- 1.3.6.1.4.1.10428 9 1.101.51.3.2.2.20
		fkOSPFIfInfoControlAuthKeyFirst OBJECT-TYPE
			SYNTAX OCTET STRING
			MAX-ACCESS read-write
			STATUS current
			DESCRIPTION
				"Description."
			::= { fkOSPFIfInfoControl 20 }

		
		-- 1.3.6.1.4.1.10428 9 1.101.51.3.2.2.21
		fkOSPFIfInfoControlAuthKeyFirstAct OBJECT-TYPE
			SYNTAX INTEGER
				{
				deactive(0),
				active(1)
				}
			MAX-ACCESS read-write
			STATUS current
			DESCRIPTION
				"Description."
			::= { fkOSPFIfInfoControl 21 }

		
		-- 1.3.6.1.4.1.10428 9 1.101.51.3.2.2.22
		fkOSPFIfInfoControlAuthKeySecond OBJECT-TYPE
			SYNTAX OCTET STRING
			MAX-ACCESS read-write
			STATUS current
			DESCRIPTION
				"Description."
			::= { fkOSPFIfInfoControl 22 }

		
		-- 1.3.6.1.4.1.10428 9 1.101.51.3.2.2.23
		fkOSPFIfInfoControlAuthKeySecondAct OBJECT-TYPE
			SYNTAX INTEGER
				{
				deactive(0),
				active(1)
				}
			MAX-ACCESS read-write
			STATUS current
			DESCRIPTION
				"Description."
			::= { fkOSPFIfInfoControl 23 }

		
		-- 1.3.6.1.4.1.10428 9 1.101.51.3.2.3
		fkOSPFIfInfoNotification OBJECT IDENTIFIER ::= { fkOSPFIfInfo 3 }

		
		-- 1.3.6.1.4.1.10428 9 1.101.51.3.2.3.1
		fkOSPFIfCostChanged NOTIFICATION-TYPE
			OBJECTS { fkOSPFIfInfoControlRequest, fkOSPFIfInfoControlTimeStamp, fkOSPFIfInfoControlReqResult, fkOSPFIfIndex, fkOSPFIfIpAddr, 
				fkOSPFIfCost }
			STATUS current
			DESCRIPTION 
				"Description."
			::= { fkOSPFIfInfoNotification 1 }

		
		-- 1.3.6.1.4.1.10428 9 1.101.51.3.2.3.2
		fkOSPFIfPriorityChanged NOTIFICATION-TYPE
			OBJECTS { fkOSPFIfInfoControlRequest, fkOSPFIfInfoControlTimeStamp, fkOSPFIfInfoControlReqResult, fkOSPFIfIndex, fkOSPFIfIpAddr, 
				fkOSPFIfPriority }
			STATUS current
			DESCRIPTION 
				"Description."
			::= { fkOSPFIfInfoNotification 2 }

		
		-- 1.3.6.1.4.1.10428 9 1.101.51.3.2.3.3
		fkOSPFIfTransmitDelayChanged NOTIFICATION-TYPE
			OBJECTS { fkOSPFIfInfoControlRequest, fkOSPFIfInfoControlTimeStamp, fkOSPFIfInfoControlReqResult, fkOSPFIfIndex, fkOSPFIfIpAddr, 
				fkOSPFIfTransmitDelay }
			STATUS current
			DESCRIPTION 
				"Description."
			::= { fkOSPFIfInfoNotification 3 }

		
		-- 1.3.6.1.4.1.10428 9 1.101.51.3.2.3.4
		fkOSPFIfHelloIntervalChanged NOTIFICATION-TYPE
			OBJECTS { fkOSPFIfInfoControlRequest, fkOSPFIfInfoControlTimeStamp, fkOSPFIfInfoControlReqResult, fkOSPFIfIndex, fkOSPFIfIpAddr, 
				fkOSPFIfHelloInterval }
			STATUS current
			DESCRIPTION 
				"Description."
			::= { fkOSPFIfInfoNotification 4 }

		
		-- 1.3.6.1.4.1.10428 9 1.101.51.3.2.3.5
		fkOSPFIfDeadIntervalChanged NOTIFICATION-TYPE
			OBJECTS { fkOSPFIfInfoControlRequest, fkOSPFIfInfoControlTimeStamp, fkOSPFIfInfoControlReqResult, fkOSPFIfIndex, fkOSPFIfIpAddr, 
				fkOSPFIfDeadInterval }
			STATUS current
			DESCRIPTION 
				"Description."
			::= { fkOSPFIfInfoNotification 5 }

		
		-- 1.3.6.1.4.1.10428 9 1.101.51.3.2.3.6
		fkOSPFIfRetransIntervalChanged NOTIFICATION-TYPE
			OBJECTS { fkOSPFIfInfoControlRequest, fkOSPFIfInfoControlTimeStamp, fkOSPFIfInfoControlReqResult, fkOSPFIfIndex, fkOSPFIfIpAddr, 
				fkOSPFIfRetransInterval }
			STATUS current
			DESCRIPTION 
				"Description."
			::= { fkOSPFIfInfoNotification 6 }

		
		-- 1.3.6.1.4.1.10428 9 1.101.51.3.2.3.7
		fkOSPFIfAuthProfileChanged NOTIFICATION-TYPE
			OBJECTS { fkOSPFIfInfoControlRequest, fkOSPFIfInfoControlTimeStamp, fkOSPFIfInfoControlReqResult, fkOSPFIfIndex, fkOSPFIfIpAddr, 
				fkOSPFIfAuth, fkOSPFIfAuthType }
			STATUS current
			DESCRIPTION 
				"Description."
			::= { fkOSPFIfInfoNotification 7 }

		
		-- 1.3.6.1.4.1.10428 9 1.101.51.3.2.3.8
		fkOSPFIfDatafilterOutChanged NOTIFICATION-TYPE
			OBJECTS { fkOSPFIfInfoControlRequest, fkOSPFIfInfoControlTimeStamp, fkOSPFIfInfoControlReqResult, fkOSPFIfIndex, fkOSPFIfIpAddr, 
				fkOSPFIfDataFilterOut }
			STATUS current
			DESCRIPTION 
				"Description."
			::= { fkOSPFIfInfoNotification 8 }

		
		-- 1.3.6.1.4.1.10428 9 1.101.51.3.2.3.9
		fkOSPFIfMTUIgnoreChanged NOTIFICATION-TYPE
			OBJECTS { fkOSPFIfInfoControlRequest, fkOSPFIfInfoControlTimeStamp, fkOSPFIfInfoControlReqResult, fkOSPFIfIndex, fkOSPFIfIpAddr, 
				fkOSPFIfMTUIgnore }
			STATUS current
			DESCRIPTION 
				"Description."
			::= { fkOSPFIfInfoNotification 9 }

		
		-- 1.3.6.1.4.1.10428 9 1.101.51.3.2.3.10
		fkOSPFIfResyncProfileChanged NOTIFICATION-TYPE
			OBJECTS { fkOSPFIfInfoControlRequest, fkOSPFIfInfoControlTimeStamp, fkOSPFIfInfoControlReqResult, fkOSPFIfIndex, fkOSPFIfIpAddr, 
				fkOSPFIfResync, fkOSPFIfResyncTimeout }
			STATUS current
			DESCRIPTION 
				"Description."
			::= { fkOSPFIfInfoNotification 10 }

		
		-- 1.3.6.1.4.1.10428 9 1.101.51.3.2.3.11
		fkOSPFIfAuthKeyFirstProfileChanged NOTIFICATION-TYPE
			OBJECTS { fkOSPFIfInfoControlRequest, fkOSPFIfInfoControlTimeStamp, fkOSPFIfInfoControlReqResult, fkOSPFIfIndex, fkOSPFIfIpAddr, 
				fkOSPFIfAuthKeyFirst, fkOSPFIfAuthKeyFirstAct }
			STATUS current
			DESCRIPTION 
				"Description."
			::= { fkOSPFIfInfoNotification 11 }

		
		-- 1.3.6.1.4.1.10428 9 1.101.51.3.2.3.12
		fkOSPFIfAuthKeyProfileSecondChanged NOTIFICATION-TYPE
			OBJECTS { fkOSPFIfInfoControlRequest, fkOSPFIfInfoControlTimeStamp, fkOSPFIfInfoControlReqResult, fkOSPFIfIndex, fkOSPFIfIpAddr, 
				fkOSPFIfAuthKeySecond, fkOSPFIfAuthKeySecondAct }
			STATUS current
			DESCRIPTION 
				"Description."
			::= { fkOSPFIfInfoNotification 12 }

		
		-- 1.3.6.1.4.1.10428 9 1.101.51.3.3
		fkOSPFIfMsgKey OBJECT IDENTIFIER ::= { fkOSPFInterface 3 }

		
		-- 1.3.6.1.4.1.10428 9 1.101.51.3.3.1
		fkOSPFIfMsgKeyTable OBJECT-TYPE
			SYNTAX SEQUENCE OF FkOSPFIfMsgKeyEntry
			MAX-ACCESS not-accessible
			STATUS current
			DESCRIPTION
				"Description."
			::= { fkOSPFIfMsgKey 1 }

		
		-- 1.3.6.1.4.1.10428 9 1.101.51.3.3.1.1
		fkOSPFIfMsgKeyEntry OBJECT-TYPE
			SYNTAX FkOSPFIfMsgKeyEntry
			MAX-ACCESS not-accessible
			STATUS current
			DESCRIPTION
				"Description."
			INDEX { fkOSPFIfIndex, fkOSPFIfIpAddr, fkOSPFIfMsgKeyID }
			::= { fkOSPFIfMsgKeyTable 1 }

		
		FkOSPFIfMsgKeyEntry ::=
			SEQUENCE { 
				fkOSPFIfMsgKeyID
					Integer32,
				fkOSPFIfMsgKeyVal
					OCTET STRING,
				fkOSPFIfMsgKeyAct
					INTEGER
			 }

		-- 1.3.6.1.4.1.10428 9 1.101.51.3.3.1.1.1
		fkOSPFIfMsgKeyID OBJECT-TYPE
			SYNTAX Integer32 (0..255)
			MAX-ACCESS read-only
			STATUS current
			DESCRIPTION
				"Description."
			::= { fkOSPFIfMsgKeyEntry 1 }

		
		-- 1.3.6.1.4.1.10428 9 1.101.51.3.3.1.1.2
		fkOSPFIfMsgKeyVal OBJECT-TYPE
			SYNTAX OCTET STRING
			MAX-ACCESS read-only
			STATUS current
			DESCRIPTION
				"Description."
			::= { fkOSPFIfMsgKeyEntry 2 }

		
		-- 1.3.6.1.4.1.10428 9 1.101.51.3.3.1.1.3
		fkOSPFIfMsgKeyAct OBJECT-TYPE
			SYNTAX INTEGER
				{
				deactive(0),
				active(1)
				}
			MAX-ACCESS read-only
			STATUS current
			DESCRIPTION
				"Description."
			::= { fkOSPFIfMsgKeyEntry 3 }

		
		-- 1.3.6.1.4.1.10428 9 1.101.51.3.3.2
		fkOSPFIfMsgKeyControl OBJECT IDENTIFIER ::= { fkOSPFIfMsgKey 2 }

		
		-- 1.3.6.1.4.1.10428 9 1.101.51.3.3.2.1
		fkOSPFIfMsgKeyControlRequest OBJECT-TYPE
			SYNTAX INTEGER
				{
				createMsgDigestKey(1),
				deleteMsgDigestKey(2)
				}
			MAX-ACCESS read-write
			STATUS current
			DESCRIPTION
				"Description."
			::= { fkOSPFIfMsgKeyControl 1 }

		
		-- 1.3.6.1.4.1.10428 9 1.101.51.3.3.2.2
		fkOSPFIfMsgKeyControlStatus OBJECT-TYPE
			SYNTAX FkControlStatusType
			MAX-ACCESS read-only
			STATUS current
			DESCRIPTION
				"Description."
			::= { fkOSPFIfMsgKeyControl 2 }

		
		-- 1.3.6.1.4.1.10428 9 1.101.51.3.3.2.3
		fkOSPFIfMsgKeyControlTimer OBJECT-TYPE
			SYNTAX Gauge32
			MAX-ACCESS read-write
			STATUS current
			DESCRIPTION
				"Description."
			::= { fkOSPFIfMsgKeyControl 3 }

		
		-- 1.3.6.1.4.1.10428 9 1.101.51.3.3.2.4
		fkOSPFIfMsgKeyControlTimeStamp OBJECT-TYPE
			SYNTAX TimeTicks
			MAX-ACCESS read-only
			STATUS current
			DESCRIPTION
				"Description."
			::= { fkOSPFIfMsgKeyControl 4 }

		
		-- 1.3.6.1.4.1.10428 9 1.101.51.3.3.2.5
		fkOSPFIfMsgKeyControlReqResult OBJECT-TYPE
			SYNTAX FkControlRequestResultType
			MAX-ACCESS read-only
			STATUS current
			DESCRIPTION
				"Description."
			::= { fkOSPFIfMsgKeyControl 5 }

		
		-- 1.3.6.1.4.1.10428 9 1.101.51.3.3.2.6
		fkOSPFIfMsgKeyControlIndex OBJECT-TYPE
			SYNTAX INTEGER (0..65535)
			MAX-ACCESS read-write
			STATUS current
			DESCRIPTION
				"Description."
			::= { fkOSPFIfMsgKeyControl 6 }

		
		-- 1.3.6.1.4.1.10428 9 1.101.51.3.3.2.7
		fkOSPFIfMsgKeyControlIpAddr OBJECT-TYPE
			SYNTAX IpAddress
			MAX-ACCESS read-write
			STATUS current
			DESCRIPTION
				"Description."
			::= { fkOSPFIfMsgKeyControl 7 }

		
		-- 1.3.6.1.4.1.10428 9 1.101.51.3.3.2.8
		fkOSPFIfMsgKeyControlKeyID OBJECT-TYPE
			SYNTAX INTEGER (0..255)
			MAX-ACCESS read-write
			STATUS current
			DESCRIPTION
				"Description."
			::= { fkOSPFIfMsgKeyControl 8 }

		
		-- 1.3.6.1.4.1.10428 9 1.101.51.3.3.2.9
		fkOSPFIfMsgKeyControlKeyVal OBJECT-TYPE
			SYNTAX OCTET STRING
			MAX-ACCESS read-write
			STATUS current
			DESCRIPTION
				"Description."
			::= { fkOSPFIfMsgKeyControl 9 }

		
		-- 1.3.6.1.4.1.10428 9 1.101.51.3.3.2.10
		fkOSPFIfMsgKeyControlKeyAct OBJECT-TYPE
			SYNTAX INTEGER
				{
				deactive(0),
				active(1)
				}
			MAX-ACCESS read-write
			STATUS current
			DESCRIPTION
				"Description."
			::= { fkOSPFIfMsgKeyControl 10 }

		
		-- 1.3.6.1.4.1.10428 9 1.101.51.3.3.3
		fkOSPFIfMsgKeyNotification OBJECT IDENTIFIER ::= { fkOSPFIfMsgKey 3 }

		
		-- 1.3.6.1.4.1.10428 9 1.101.51.3.3.3.1
		fkOSPFIfMsgKeyCreated NOTIFICATION-TYPE
			OBJECTS { fkOSPFIfInfoControlRequest, fkOSPFIfInfoControlTimeStamp, fkOSPFIfInfoControlReqResult, fkOSPFIfIndex, fkOSPFIfIpAddr, 
				fkOSPFIfMsgKeyID, fkOSPFIfMsgKeyVal, fkOSPFIfMsgKeyAct }
			STATUS current
			DESCRIPTION 
				"Description."
			::= { fkOSPFIfMsgKeyNotification 1 }

		
		-- 1.3.6.1.4.1.10428 9 1.101.51.3.3.3.2
		fkOSPFIfMsgKeyDeleted NOTIFICATION-TYPE
			OBJECTS { fkOSPFIfInfoControlRequest, fkOSPFIfInfoControlTimeStamp, fkOSPFIfInfoControlReqResult, fkOSPFIfIndex, fkOSPFIfIpAddr, 
				fkOSPFIfMsgKeyControlKeyID }
			STATUS current
			DESCRIPTION 
				"Description."
			::= { fkOSPFIfMsgKeyNotification 2 }

		
		-- 1.3.6.1.4.1.10428 9 1.101.51.3.4
		fkOSPFIfStatus OBJECT IDENTIFIER ::= { fkOSPFInterface 4 }

		
		-- 1.3.6.1.4.1.10428 9 1.101.51.3.4.1
		fkOSPFIfStatusTable OBJECT-TYPE
			SYNTAX SEQUENCE OF FkOSPFIfStatusEntry
			MAX-ACCESS not-accessible
			STATUS current
			DESCRIPTION
				"Description."
			::= { fkOSPFIfStatus 1 }

		
		-- 1.3.6.1.4.1.10428 9 1.101.51.3.4.1.1
		fkOSPFIfStatusEntry OBJECT-TYPE
			SYNTAX FkOSPFIfStatusEntry
			MAX-ACCESS not-accessible
			STATUS current
			DESCRIPTION
				"Description."
			INDEX { fkOSPFIfIndex, fkOSPFIfIpAddr }
			::= { fkOSPFIfStatusTable 1 }

		
		FkOSPFIfStatusEntry ::=
			SEQUENCE { 
				fkOSPFIfStatusAddr
					IpAddress,
				fkOSPFIfStatusUpState
					INTEGER,
				fkOSPFIfStatusAreaID
					IpAddress,
				fkOSPFIfStatusProcID
					INTEGER,
				fkOSPFIfStatusRouterID
					IpAddress,
				fkOSPFIfStatusNetworkType
					INTEGER,
				fkOSPFIfStatusCost
					INTEGER,
				fkOSPFIfStatusTransmitDelay
					INTEGER,
				fkOSPFIfStatusState
					INTEGER,
				fkOSPFIfStatusPriorityUse
					INTEGER,
				fkOSPFIfStatusPriority
					INTEGER,
				fkOSPFIfStatusDRRouterUse
					INTEGER,
				fkOSPFIfStatusDRRouterID
					IpAddress,
				fkOSPFIfStatusDRIfIpAddr
					IpAddress,
				fkOSPFIfStatusBDRRouterUse
					INTEGER,
				fkOSPFIfStatusBDRRouterID
					IpAddress,
				fkOSPFIfStatusBDRIfIpAddr
					IpAddress,
				fkOSPFIfStatusHelloInterval
					INTEGER,
				fkOSPFIfStatusDeadInterval
					INTEGER,
				fkOSPFIfStatusRetransInterval
					INTEGER,
				fkOSPFIfStatusWaitInterval
					INTEGER,
				fkOSPFIfStatusNeighborCount
					INTEGER,
				fkOSPFIfCryptSeqNum
					Gauge32,
				fkOSPFIfStatusRcvHello
					Gauge32,
				fkOSPFIfStatusSendHello
					Gauge32,
				fkOSPFIfStatusRcvDD
					Gauge32,
				fkOSPFIfStatusSendDD
					Gauge32,
				fkOSPFIfStatusRcvLSReq
					Gauge32,
				fkOSPFIfStatusSendLSReq
					Gauge32,
				fkOSPFIfStatusRcvLSUpd
					Gauge32,
				fkOSPFIfStatusSendLSUpd
					Gauge32,
				fkOSPFIfStatusRcvLSAck
					Gauge32,
				fkOSPFIfStatusSendLSAck
					Gauge32,
				fkOSPFIfStatusDiscarded
					Gauge32,
				fkOSPFIfStatusMtu
					Integer32
			 }

		-- 1.3.6.1.4.1.10428 9 1.101.51.3.4.1.1.1
		fkOSPFIfStatusAddr OBJECT-TYPE
			SYNTAX IpAddress
			MAX-ACCESS read-only
			STATUS current
			DESCRIPTION
				"Description."
			::= { fkOSPFIfStatusEntry 1 }

		
		-- 1.3.6.1.4.1.10428 9 1.101.51.3.4.1.1.2
		fkOSPFIfStatusUpState OBJECT-TYPE
			SYNTAX INTEGER
				{
				down(0),
				up(1)
				}
			MAX-ACCESS read-only
			STATUS current
			DESCRIPTION
				"Description."
			::= { fkOSPFIfStatusEntry 2 }

		
		-- 1.3.6.1.4.1.10428 9 1.101.51.3.4.1.1.3
		fkOSPFIfStatusAreaID OBJECT-TYPE
			SYNTAX IpAddress
			MAX-ACCESS read-only
			STATUS current
			DESCRIPTION
				"Description."
			::= { fkOSPFIfStatusEntry 3 }

		
		-- 1.3.6.1.4.1.10428 9 1.101.51.3.4.1.1.4
		fkOSPFIfStatusProcID OBJECT-TYPE
			SYNTAX INTEGER (0..65535)
			MAX-ACCESS read-only
			STATUS current
			DESCRIPTION
				"Description."
			::= { fkOSPFIfStatusEntry 4 }

		
		-- 1.3.6.1.4.1.10428 9 1.101.51.3.4.1.1.5
		fkOSPFIfStatusRouterID OBJECT-TYPE
			SYNTAX IpAddress
			MAX-ACCESS read-only
			STATUS current
			DESCRIPTION
				"Description."
			::= { fkOSPFIfStatusEntry 5 }

		
		-- 1.3.6.1.4.1.10428 9 1.101.51.3.4.1.1.6
		fkOSPFIfStatusNetworkType OBJECT-TYPE
			SYNTAX INTEGER
				{
				none(0),
				pointTopoint(1),
				broadcast(2),
				nbma(3),
				pointTomultipoint(4),
				poiintTomultipointnbma(5),
				virtuallink(6),
				loopback(7)
				}
			MAX-ACCESS read-only
			STATUS current
			DESCRIPTION
				"Description."
			::= { fkOSPFIfStatusEntry 6 }

		
		-- 1.3.6.1.4.1.10428 9 1.101.51.3.4.1.1.7
		fkOSPFIfStatusCost OBJECT-TYPE
			SYNTAX INTEGER (0..65535)
			MAX-ACCESS read-only
			STATUS current
			DESCRIPTION
				"Description."
			::= { fkOSPFIfStatusEntry 7 }

		
		-- 1.3.6.1.4.1.10428 9 1.101.51.3.4.1.1.8
		fkOSPFIfStatusTransmitDelay OBJECT-TYPE
			SYNTAX INTEGER (0..65535)
			MAX-ACCESS read-only
			STATUS current
			DESCRIPTION
				"Description."
			::= { fkOSPFIfStatusEntry 8 }

		
		-- 1.3.6.1.4.1.10428 9 1.101.51.3.4.1.1.9
		fkOSPFIfStatusState OBJECT-TYPE
			SYNTAX INTEGER
				{
				dependUpon(0),
				down(1),
				loopback(2),
				waiting(3),
				pointTopoint(4),
				drother(5),
				backup(6),
				dr(7)
				}
			MAX-ACCESS read-only
			STATUS current
			DESCRIPTION
				"Description."
			::= { fkOSPFIfStatusEntry 9 }

		
		-- 1.3.6.1.4.1.10428 9 1.101.51.3.4.1.1.10
		fkOSPFIfStatusPriorityUse OBJECT-TYPE
			SYNTAX INTEGER
				{
				nouse(0),
				use(1)
				}
			MAX-ACCESS read-only
			STATUS current
			DESCRIPTION
				"Description."
			::= { fkOSPFIfStatusEntry 10 }

		
		-- 1.3.6.1.4.1.10428 9 1.101.51.3.4.1.1.11
		fkOSPFIfStatusPriority OBJECT-TYPE
			SYNTAX INTEGER (0..255)
			MAX-ACCESS read-only
			STATUS current
			DESCRIPTION
				"Description."
			::= { fkOSPFIfStatusEntry 11 }

		
		-- 1.3.6.1.4.1.10428 9 1.101.51.3.4.1.1.12
		fkOSPFIfStatusDRRouterUse OBJECT-TYPE
			SYNTAX INTEGER
				{
				nouse(0),
				use(1)
				}
			MAX-ACCESS read-only
			STATUS current
			DESCRIPTION
				"Description."
			::= { fkOSPFIfStatusEntry 12 }

		
		-- 1.3.6.1.4.1.10428 9 1.101.51.3.4.1.1.13
		fkOSPFIfStatusDRRouterID OBJECT-TYPE
			SYNTAX IpAddress
			MAX-ACCESS read-only
			STATUS current
			DESCRIPTION
				"Description."
			::= { fkOSPFIfStatusEntry 13 }

		
		-- 1.3.6.1.4.1.10428 9 1.101.51.3.4.1.1.14
		fkOSPFIfStatusDRIfIpAddr OBJECT-TYPE
			SYNTAX IpAddress
			MAX-ACCESS read-only
			STATUS current
			DESCRIPTION
				"Description."
			::= { fkOSPFIfStatusEntry 14 }

		
		-- 1.3.6.1.4.1.10428 9 1.101.51.3.4.1.1.15
		fkOSPFIfStatusBDRRouterUse OBJECT-TYPE
			SYNTAX INTEGER
				{
				nouse(0),
				use(1)
				}
			MAX-ACCESS read-only
			STATUS current
			DESCRIPTION
				"Description."
			::= { fkOSPFIfStatusEntry 15 }

		
		-- 1.3.6.1.4.1.10428 9 1.101.51.3.4.1.1.16
		fkOSPFIfStatusBDRRouterID OBJECT-TYPE
			SYNTAX IpAddress
			MAX-ACCESS read-only
			STATUS current
			DESCRIPTION
				"Description."
			::= { fkOSPFIfStatusEntry 16 }

		
		-- 1.3.6.1.4.1.10428 9 1.101.51.3.4.1.1.17
		fkOSPFIfStatusBDRIfIpAddr OBJECT-TYPE
			SYNTAX IpAddress
			MAX-ACCESS read-only
			STATUS current
			DESCRIPTION
				"Description."
			::= { fkOSPFIfStatusEntry 17 }

		
		-- 1.3.6.1.4.1.10428 9 1.101.51.3.4.1.1.18
		fkOSPFIfStatusHelloInterval OBJECT-TYPE
			SYNTAX INTEGER (0..65535)
			MAX-ACCESS read-only
			STATUS current
			DESCRIPTION
				"Description."
			::= { fkOSPFIfStatusEntry 18 }

		
		-- 1.3.6.1.4.1.10428 9 1.101.51.3.4.1.1.19
		fkOSPFIfStatusDeadInterval OBJECT-TYPE
			SYNTAX INTEGER (0..65535)
			MAX-ACCESS read-only
			STATUS current
			DESCRIPTION
				"Description."
			::= { fkOSPFIfStatusEntry 19 }

		
		-- 1.3.6.1.4.1.10428 9 1.101.51.3.4.1.1.20
		fkOSPFIfStatusRetransInterval OBJECT-TYPE
			SYNTAX INTEGER (0..65535)
			MAX-ACCESS read-only
			STATUS current
			DESCRIPTION
				"Description."
			::= { fkOSPFIfStatusEntry 20 }

		
		-- 1.3.6.1.4.1.10428 9 1.101.51.3.4.1.1.21
		fkOSPFIfStatusWaitInterval OBJECT-TYPE
			SYNTAX INTEGER (0..65535)
			MAX-ACCESS read-only
			STATUS current
			DESCRIPTION
				"Description."
			::= { fkOSPFIfStatusEntry 21 }

		
		-- 1.3.6.1.4.1.10428 9 1.101.51.3.4.1.1.22
		fkOSPFIfStatusNeighborCount OBJECT-TYPE
			SYNTAX INTEGER
			MAX-ACCESS read-only
			STATUS current
			DESCRIPTION
				"Description."
			::= { fkOSPFIfStatusEntry 22 }

		
		-- 1.3.6.1.4.1.10428 9 1.101.51.3.4.1.1.23
		fkOSPFIfCryptSeqNum OBJECT-TYPE
			SYNTAX Gauge32
			MAX-ACCESS read-only
			STATUS current
			DESCRIPTION
				"Description."
			::= { fkOSPFIfStatusEntry 23 }

		
		-- 1.3.6.1.4.1.10428 9 1.101.51.3.4.1.1.24
		fkOSPFIfStatusRcvHello OBJECT-TYPE
			SYNTAX Gauge32
			MAX-ACCESS read-only
			STATUS current
			DESCRIPTION
				"Description."
			::= { fkOSPFIfStatusEntry 24 }

		
		-- 1.3.6.1.4.1.10428 9 1.101.51.3.4.1.1.25
		fkOSPFIfStatusSendHello OBJECT-TYPE
			SYNTAX Gauge32
			MAX-ACCESS read-only
			STATUS current
			DESCRIPTION
				"Description."
			::= { fkOSPFIfStatusEntry 25 }

		
		-- 1.3.6.1.4.1.10428 9 1.101.51.3.4.1.1.26
		fkOSPFIfStatusRcvDD OBJECT-TYPE
			SYNTAX Gauge32
			MAX-ACCESS read-only
			STATUS current
			DESCRIPTION
				"Description."
			::= { fkOSPFIfStatusEntry 26 }

		
		-- 1.3.6.1.4.1.10428 9 1.101.51.3.4.1.1.27
		fkOSPFIfStatusSendDD OBJECT-TYPE
			SYNTAX Gauge32
			MAX-ACCESS read-only
			STATUS current
			DESCRIPTION
				"Description."
			::= { fkOSPFIfStatusEntry 27 }

		
		-- 1.3.6.1.4.1.10428 9 1.101.51.3.4.1.1.28
		fkOSPFIfStatusRcvLSReq OBJECT-TYPE
			SYNTAX Gauge32
			MAX-ACCESS read-only
			STATUS current
			DESCRIPTION
				"Description."
			::= { fkOSPFIfStatusEntry 28 }

		
		-- 1.3.6.1.4.1.10428 9 1.101.51.3.4.1.1.29
		fkOSPFIfStatusSendLSReq OBJECT-TYPE
			SYNTAX Gauge32
			MAX-ACCESS read-only
			STATUS current
			DESCRIPTION
				"Description."
			::= { fkOSPFIfStatusEntry 29 }

		
		-- 1.3.6.1.4.1.10428 9 1.101.51.3.4.1.1.30
		fkOSPFIfStatusRcvLSUpd OBJECT-TYPE
			SYNTAX Gauge32
			MAX-ACCESS read-only
			STATUS current
			DESCRIPTION
				"Description."
			::= { fkOSPFIfStatusEntry 30 }

		
		-- 1.3.6.1.4.1.10428 9 1.101.51.3.4.1.1.31
		fkOSPFIfStatusSendLSUpd OBJECT-TYPE
			SYNTAX Gauge32
			MAX-ACCESS read-only
			STATUS current
			DESCRIPTION
				"Description."
			::= { fkOSPFIfStatusEntry 31 }

		
		-- 1.3.6.1.4.1.10428 9 1.101.51.3.4.1.1.32
		fkOSPFIfStatusRcvLSAck OBJECT-TYPE
			SYNTAX Gauge32
			MAX-ACCESS read-only
			STATUS current
			DESCRIPTION
				"Description."
			::= { fkOSPFIfStatusEntry 32 }

		
		-- 1.3.6.1.4.1.10428 9 1.101.51.3.4.1.1.33
		fkOSPFIfStatusSendLSAck OBJECT-TYPE
			SYNTAX Gauge32
			MAX-ACCESS read-only
			STATUS current
			DESCRIPTION
				"Description."
			::= { fkOSPFIfStatusEntry 33 }

		
		-- 1.3.6.1.4.1.10428 9 1.101.51.3.4.1.1.34
		fkOSPFIfStatusDiscarded OBJECT-TYPE
			SYNTAX Gauge32
			MAX-ACCESS read-only
			STATUS current
			DESCRIPTION
				"Description."
			::= { fkOSPFIfStatusEntry 34 }

		
		-- 1.3.6.1.4.1.10428 9 1.101.51.3.4.1.1.35
		fkOSPFIfStatusMtu OBJECT-TYPE
			SYNTAX Integer32
			MAX-ACCESS read-only
			STATUS current
			DESCRIPTION
				"The MTU of OSPF interface."
			::= { fkOSPFIfStatusEntry 35 }

		
		-- 1.3.6.1.4.1.10428 9 1.101.51.4
		fkOSPFLsa OBJECT IDENTIFIER ::= { fkOspf 4 }

		
		-- 1.3.6.1.4.1.10428 9 1.101.51.4.1
		fkOSPFLsaTable OBJECT-TYPE
			SYNTAX SEQUENCE OF FkOSPFLsaEntry
			MAX-ACCESS not-accessible
			STATUS current
			DESCRIPTION
				"Description."
			::= { fkOSPFLsa 1 }

		
		-- 1.3.6.1.4.1.10428 9 1.101.51.4.1.1
		fkOSPFLsaEntry OBJECT-TYPE
			SYNTAX FkOSPFLsaEntry
			MAX-ACCESS not-accessible
			STATUS current
			DESCRIPTION
				"Description."
			INDEX { fkOSPFProcID, fkOSPFLsaType, fkOSPFLsaAreaID, fkOSPFLsaLinkID, fkOSPFLsaAdvRouter
				 }
			::= { fkOSPFLsaTable 1 }

		
		FkOSPFLsaEntry ::=
			SEQUENCE { 
				fkOSPFLsaType
					INTEGER,
				fkOSPFLsaAreaID
					IpAddress,
				fkOSPFLsaLinkID
					IpAddress,
				fkOSPFLsaAdvRouter
					IpAddress,
				fkOSPFLsaAge
					INTEGER,
				fkOSPFLsaSequence
					Gauge32
			 }

		-- 1.3.6.1.4.1.10428 9 1.101.51.4.1.1.1
		fkOSPFLsaType OBJECT-TYPE
			SYNTAX INTEGER
				{
				unknown(1),
				routerLsa(2),
				networkLsa(3),
				summaryLsa(4),
				summaryLsaAsbr(5),
				asExternalLsa(6),
				groupMemberLsa(7),
				asNssaLsa(8),
				externalAttributeLsa(9),
				linkOpaqueLsa(10),
				areaOpaqueLsa(11),
				asOpaqueLsa(12)
				}
			MAX-ACCESS read-only
			STATUS current
			DESCRIPTION
				"Description."
			::= { fkOSPFLsaEntry 1 }

		
		-- 1.3.6.1.4.1.10428 9 1.101.51.4.1.1.2
		fkOSPFLsaAreaID OBJECT-TYPE
			SYNTAX IpAddress
			MAX-ACCESS read-only
			STATUS current
			DESCRIPTION
				"Description."
			::= { fkOSPFLsaEntry 2 }

		
		-- 1.3.6.1.4.1.10428 9 1.101.51.4.1.1.3
		fkOSPFLsaLinkID OBJECT-TYPE
			SYNTAX IpAddress
			MAX-ACCESS read-only
			STATUS current
			DESCRIPTION
				"Description."
			::= { fkOSPFLsaEntry 3 }

		
		-- 1.3.6.1.4.1.10428 9 1.101.51.4.1.1.4
		fkOSPFLsaAdvRouter OBJECT-TYPE
			SYNTAX IpAddress
			MAX-ACCESS read-only
			STATUS current
			DESCRIPTION
				"Description."
			::= { fkOSPFLsaEntry 4 }

		
		-- 1.3.6.1.4.1.10428 9 1.101.51.4.1.1.5
		fkOSPFLsaAge OBJECT-TYPE
			SYNTAX INTEGER
			MAX-ACCESS read-only
			STATUS current
			DESCRIPTION
				"Description."
			::= { fkOSPFLsaEntry 5 }

		
		-- 1.3.6.1.4.1.10428 9 1.101.51.4.1.1.6
		fkOSPFLsaSequence OBJECT-TYPE
			SYNTAX Gauge32
			MAX-ACCESS read-only
			STATUS current
			DESCRIPTION
				"Description."
			::= { fkOSPFLsaEntry 6 }

		
		-- 1.3.6.1.4.1.10428 9 1.101.51.5
		fkOSPFNeighbor OBJECT IDENTIFIER ::= { fkOspf 5 }

		
		-- 1.3.6.1.4.1.10428 9 1.101.51.5.1
		fkOSPFNeighborTable OBJECT-TYPE
			SYNTAX SEQUENCE OF FkOSPFNeighborEntry
			MAX-ACCESS not-accessible
			STATUS current
			DESCRIPTION
				"Description."
			::= { fkOSPFNeighbor 1 }

		
		-- 1.3.6.1.4.1.10428 9 1.101.51.5.1.1
		fkOSPFNeighborEntry OBJECT-TYPE
			SYNTAX FkOSPFNeighborEntry
			MAX-ACCESS not-accessible
			STATUS current
			DESCRIPTION
				"Description."
			INDEX { fkOSPFProcID, fkOSPFNeighborIPAddr }
			::= { fkOSPFNeighborTable 1 }

		
		FkOSPFNeighborEntry ::=
			SEQUENCE { 
				fkOSPFNeighborIPAddr
					IpAddress,
				fkOSPFNeighborID
					IpAddress,
				fkOSPFNeighborPriority
					INTEGER,
				fkOSPFNeighborState
					INTEGER,
				fkOSPFNeighborIfName
					OCTET STRING
			 }

		-- 1.3.6.1.4.1.10428 9 1.101.51.5.1.1.1
		fkOSPFNeighborIPAddr OBJECT-TYPE
			SYNTAX IpAddress
			MAX-ACCESS read-only
			STATUS current
			DESCRIPTION
				"Description."
			::= { fkOSPFNeighborEntry 1 }

		
		-- 1.3.6.1.4.1.10428 9 1.101.51.5.1.1.2
		fkOSPFNeighborID OBJECT-TYPE
			SYNTAX IpAddress
			MAX-ACCESS read-only
			STATUS current
			DESCRIPTION
				"Description."
			::= { fkOSPFNeighborEntry 2 }

		
		-- 1.3.6.1.4.1.10428 9 1.101.51.5.1.1.3
		fkOSPFNeighborPriority OBJECT-TYPE
			SYNTAX INTEGER
			MAX-ACCESS read-only
			STATUS current
			DESCRIPTION
				"Description."
			::= { fkOSPFNeighborEntry 3 }

		
		-- 1.3.6.1.4.1.10428 9 1.101.51.5.1.1.4
		fkOSPFNeighborState OBJECT-TYPE
			SYNTAX INTEGER
				{
				dependUpon(0),
				down(1),
				attempt(2),
				init(3),
				twoway(4),
				exstart(5),
				exchange(6),
				loading(7),
				full(8)
				}
			MAX-ACCESS read-only
			STATUS current
			DESCRIPTION
				"Description."
			::= { fkOSPFNeighborEntry 4 }

		
		-- 1.3.6.1.4.1.10428 9 1.101.51.5.1.1.5
		fkOSPFNeighborIfName OBJECT-TYPE
			SYNTAX OCTET STRING
			MAX-ACCESS read-only
			STATUS current
			DESCRIPTION
				"Description."
			::= { fkOSPFNeighborEntry 5 }

		
		-- 1.3.6.1.4.1.10428 9 1.101.51.6
		fkOSPFRoute OBJECT IDENTIFIER ::= { fkOspf 6 }

		
		-- 1.3.6.1.4.1.10428 9 1.101.51.6.1
		fkOSPFRouteTable OBJECT-TYPE
			SYNTAX SEQUENCE OF FkOSPFRouteEntry
			MAX-ACCESS not-accessible
			STATUS current
			DESCRIPTION
				"Description."
			::= { fkOSPFRoute 1 }

		
		-- 1.3.6.1.4.1.10428 9 1.101.51.6.1.1
		fkOSPFRouteEntry OBJECT-TYPE
			SYNTAX FkOSPFRouteEntry
			MAX-ACCESS not-accessible
			STATUS current
			DESCRIPTION
				"Description."
			INDEX { fkOSPFProcID, fkOSPFRouteNexthop, fkOSPFRouteNbrID, fkOSPFRoutePathType }
			::= { fkOSPFRouteTable 1 }

		
		FkOSPFRouteEntry ::=
			SEQUENCE { 
				fkOSPFRoutePathType
					INTEGER,
				fkOSPFRouteNexthop
					IpAddress,
				fkOSPFRouteNbrID
					IpAddress,
				fkOSPFRoutePathTypeCode
					INTEGER,
				fkOSPFRouteMetric
					INTEGER,
				fkOSPFRouteIfName
					OCTET STRING,
				fkOSPFRouteAreaUse
					INTEGER,
				fkOSPFRouteAreaID
					IpAddress
			 }

		-- 1.3.6.1.4.1.10428 9 1.101.51.6.1.1.1
		fkOSPFRoutePathType OBJECT-TYPE
			SYNTAX INTEGER
				{
				connected(1),
				intraArea(2),
				interArea(3),
				external(4),
				discard(5),
				unknown(255)
				}
			MAX-ACCESS read-only
			STATUS current
			DESCRIPTION
				"Description."
			::= { fkOSPFRouteEntry 1 }

		
		-- 1.3.6.1.4.1.10428 9 1.101.51.6.1.1.2
		fkOSPFRouteNexthop OBJECT-TYPE
			SYNTAX IpAddress
			MAX-ACCESS read-only
			STATUS current
			DESCRIPTION
				"Description."
			::= { fkOSPFRouteEntry 2 }

		
		-- 1.3.6.1.4.1.10428 9 1.101.51.6.1.1.3
		fkOSPFRouteNbrID OBJECT-TYPE
			SYNTAX IpAddress
			MAX-ACCESS read-only
			STATUS current
			DESCRIPTION
				"Description."
			::= { fkOSPFRouteEntry 3 }

		
		-- 1.3.6.1.4.1.10428 9 1.101.51.6.1.1.4
		fkOSPFRoutePathTypeCode OBJECT-TYPE
			SYNTAX INTEGER
				{
				unknown(0),
				connected(1),
				discard(2),
				ospf(3),
				ia(4),
				e1(5),
				e2(6),
				n1(7),
				n2(8)
				}
			MAX-ACCESS read-only
			STATUS current
			DESCRIPTION
				"Description."
			::= { fkOSPFRouteEntry 4 }

		
		-- 1.3.6.1.4.1.10428 9 1.101.51.6.1.1.5
		fkOSPFRouteMetric OBJECT-TYPE
			SYNTAX INTEGER (0..65535)
			MAX-ACCESS read-only
			STATUS current
			DESCRIPTION
				"Description."
			::= { fkOSPFRouteEntry 5 }

		
		-- 1.3.6.1.4.1.10428 9 1.101.51.6.1.1.6
		fkOSPFRouteIfName OBJECT-TYPE
			SYNTAX OCTET STRING
			MAX-ACCESS read-only
			STATUS current
			DESCRIPTION
				"Description."
			::= { fkOSPFRouteEntry 6 }

		
		-- 1.3.6.1.4.1.10428 9 1.101.51.6.1.1.7
		fkOSPFRouteAreaUse OBJECT-TYPE
			SYNTAX INTEGER
				{
				nouse(0),
				use(1)
				}
			MAX-ACCESS read-only
			STATUS current
			DESCRIPTION
				"Description."
			::= { fkOSPFRouteEntry 7 }

		
		-- 1.3.6.1.4.1.10428 9 1.101.51.6.1.1.8
		fkOSPFRouteAreaID OBJECT-TYPE
			SYNTAX IpAddress
			MAX-ACCESS read-only
			STATUS current
			DESCRIPTION
				"Description."
			::= { fkOSPFRouteEntry 8 }

		
		-- 1.3.6.1.4.1.10428 9 1.101.51.7
		fkOspfGroup OBJECT-GROUP
			OBJECTS { fkOSPFRestartPeriod, fkOSPFRestartHelperPolicy, fkOSPFRestartHelperPeriod, fkOSPFControlRequest, fkOSPFControlStatus, 
				fkOSPFControlTimer, fkOSPFControlTimeStamp, fkOSPFControlReqResult, fkOSPFControlRestartPeriod, fkOSPFControlRestartHelperPolicy, 
				fkOSPFControlRestartHelperPeriod, fkOSPFProcID, fkOSPFProcRouterID, fkOSPFProcSPFDelayTime, fkOSPFProcSPFHoldTime, 
				fkOSPFProcAutoCost, fkOSPFProcAbrType, fkOSPFProcSnmpNotification, fkOSPFProcDefaultMetricConfig, fkOSPFProcDefaultMetricValue, 
				fkOSPFProcMaxArea, fkOSPFProcMaxConcurrentDD, fkOSPFProcCompatiblerfc1583, fkOSPFProcCapabilityOpaque, fkOSPFProcLSDBOverflowType, 
				fkOSPFProcLSDBOverflowLimit, fkOSPFProcExtLSDBLimit, fkOSPFProcExitOverFlowInterval, fkOSPFProcAdminDistance, fkOSPFProcExternalDistance, 
				fkOSPFProcIntraAreaDistance, fkOSPFProcInterAreaDistance, fkOSPFProcDefaultOriginType, fkOSPFProcDefaultOriginMetricType, fkOSPFProcDefaultOriginMetric, 
				fkOSPFProcDefaultOriginRouteMap, fkOSPFProcLogNeighborChange, fkOSPFProcPassiveIfAll, fkOSPFProcBfdIFAll, fkOSPFProcEfmIFAll, 
				fkOSPFProcCapabilityRestart, fkOSPFProcControlRequest, fkOSPFProcControlStatus, fkOSPFProcControlTimer, fkOSPFProcControlTimeStamp, 
				fkOSPFProcControlReqResult, fkOSPFProcControlID, fkOSPFProcControlRouterID, fkOSPFProcControlSPFDelayTime, fkOSPFProcControlSPFHoldTime, 
				fkOSPFProcControlAutoCost, fkOSPFProcControlAbrType, fkOSPFProcControlSnmpNotification, fkOSPFProcControlDefaultMetricConfig, fkOSPFProcControlDefaultMetricValue, 
				fkOSPFProcControlMaxArea, fkOSPFProcControlMaxConcurDD, fkOSPFProcControlComprfc1583, fkOSPFProcControlCapabilityOpaque, fkOSPFProcControlLSDBOverflowType, 
				fkOSPFProcControlLSDBOverflowLimit, fkOSPFProcControlExtLSDBLimit, fkOSPFProcControlExitOverFlowInterval, fkOSPFProcControlAdminDistance, fkOSPFProcControlExtDistance, 
				fkOSPFProcControlIntraAreaDistance, fkOSPFProcControlInterAreaDistance, fkOSPFProcControlDefOriginType, fkOSPFProcControlDefOriginMetricType, fkOSPFProcControlDefOriginMetric, 
				fkOSPFProcControlDefOriginRouteMap, fkOSPFProcControlLogNeighborChange, fkOSPFProcControlPassiveIFAll, fkOSPFProcControlBfdIFAll, fkOSPFProcControlEfmIFAll, 
				fkOSPFProcControlCapabilityRestart, fkOSPFProcNetworkIP, fkOSPFProcNetworkIPMask, fkOSPFProcNetworkAreaID, fkOSPFProcNetworkControlRequest, 
				fkOSPFProcNetworkControlStatus, fkOSPFProcNetworkControlTimer, fkOSPFProcNetworkControlTimeStamp, fkOSPFProcNetworkControlReqResult, fkOSPFProcNetworkControlProcID, 
				fkOSPFProcNetworkControlIP, fkOSPFProcNetworkControlIPMask, fkOSPFProcNetworkControlAreaID, fkOSPFProcSummaryIPAddress, fkOSPFProcSummaryIPMask, 
				fkOSPFProcSummaryTag, fkOSPFProcSummaryAdvertiseFlag, fkOSPFProcSummaryControlRequest, fkOSPFProcSummaryControlStatus, fkOSPFProcSummaryControlTimer, 
				fkOSPFProcSummaryControlTimeStamp, fkOSPFProcSummaryControlReqResult, fkOSPFProcSummaryControlProcID, fkOSPFProcSummaryControlIPAddress, fkOSPFProcSummaryControlIPMask, 
				fkOSPFProcSummaryControlTag, fkOSPFProcSummaryControlAdvertiseFlag, fkOSPFProcDistributeListOutFilterType, fkOSPFProcDistributeListAccessName, fkOSPFProcDistributeListControlRequest, 
				fkOSPFProcDistributeListControlStatus, fkOSPFProcDistributeListControlTimer, fkOSPFProcDistributeListControlTimeStamp, fkOSPFProcDistributeListControlReqResult, fkOSPFProcDistributeListControlProcID, 
				fkOSPFProcDistributeListControlOutFilterType, fkOSPFProcDistributeListControlAccessName, fkOSPFProcNeighborIPAddr, fkOSPFProcNeighborPriority, fkOSPFProcNeighborPollInterval, 
				fkOSPFProcNeighborCost, fkOSPFProcNeighborControlRequest, fkOSPFProcNeighborControlStatus, fkOSPFProcNeighborControlTimer, fkOSPFProcNeighborControlTimeStamp, 
				fkOSPFProcNeighborControlReqResult, fkOSPFProcNeighborControlProcID, fkOSPFProcNeighborControlIPAddr, fkOSPFProcNeighborControlPriority, fkOSPFProcNeighborControlPollInterval, 
				fkOSPFProcNeighborControlCost, fkOSPFProcPassIfAddr, fkOSPFProcPassIfName, fkOSPFProcPassIfControlRequest, fkOSPFProcPassIfControlStatus, 
				fkOSPFProcPassIfControlTimer, fkOSPFProcPassIfControlTimeStamp, fkOSPFProcPassIfControlReqResult, fkOSPFProcPassIfControlProcID, fkOSPFProcPassIfControlIPAddr, 
				fkOSPFProcPassIfControlName, fkOSPFProcHostIPAddr, fkOSPFProcHostAreaID, fkOSPFProcHostAreaCost, fkOSPFProcHostControlRequest, 
				fkOSPFProcHostControlStatus, fkOSPFProcHostControlTimer, fkOSPFProcHostControlTimeStamp, fkOSPFProcHostControlReqResult, fkOSPFProcHostControlProcID, 
				fkOSPFProcHostControlIPAddr, fkOSPFProcHostControlAreaID, fkOSPFProcHostControlAreaCost, fkOSPFProcRedistType, fkOSPFProcRedistMetricType, 
				fkOSPFProcRedistMetric, fkOSPFProcRedistRouteMapName, fkOSPFProcRedistTag, fkOSPFProcRedistSubnets, fkOSPFProcRedistControlRequest, 
				fkOSPFProcRedistControlStatus, fkOSPFProcRedistControlTimer, fkOSPFProcRedistControlTimeStamp, fkOSPFProcRedistControlReqResult, fkOSPFProcRedistControlProcID, 
				fkOSPFProcRedistControlType, fkOSPFProcRedistControlMetricType, fkOSPFProcRedistControlMetric, fkOSPFProcRedistControlRouteMapName, fkOSPFProcRedistControlTag, 
				fkOSPFProcRedistControlSubnets, fkOSPFProcAreaID, fkOSPFProcAreaType, fkOSPFProcAreaDefaultCost, fkOSPFProcAreaAuthenType, 
				fkOSPFProcAreaFAInName, fkOSPFProcAreaFAOutName, fkOSPFProcAreaFPInName, fkOSPFProcAreaFPOutName, fkOSPFProcAreaShortcutType, 
				fkOSPFProcAreaSpfRuns, fkOSPFProcAreaLsaCount, fkOSPFProcAreaLsaCheckSum, fkOSPFProcAreaSummary, fkOSPFProcAreaNssaTransRole, 
				fkOSPFProcAreaNssaNoRedist, fkOSPFProcAreaNssaDefOriginate, fkOSPFProcAreaNssaDefMetricType, fkOSPFProcAreaNssaDefMetric, fkOSPFProcAreaControlRequest, 
				fkOSPFProcAreaControlStatus, fkOSPFProcAreaControlTimer, fkOSPFProcAreaControlTimeStamp, fkOSPFProcAreaControlReqResult, fkOSPFProcAreaControlProcID, 
				fkOSPFProcAreaControlID, fkOSPFProcAreaControlType, fkOSPFProcAreaControlDefaultCost, fkOSPFProcAreaControlAuthenType, fkOSPFProcAreaControlFAInName, 
				fkOSPFProcAreaControlFAOutName, fkOSPFProcAreaControlFPInName, fkOSPFProcAreaControlFPOutName, fkOSPFProcAreaControlShortcutType, fkOSPFProcAreaControlSummary, 
				fkOSPFProcAreaControlNssaTransRole, fkOSPFProcAreaControlNssaNoRedist, fkOSPFProcAreaControlNssaDefOriginate, fkOSPFProcAreaControlNssaDefMetricType, fkOSPFProcAreaControlNssaDefMetric, 
				fkOSPFProcAreaRangeIP, fkOSPFProcAreaRangeIPMask, fkOSPFProcAreaRangeAdverType, fkOSPFProcAreaRangeControlRequest, fkOSPFProcAreaRangeControlStatus, 
				fkOSPFProcAreaRangeControlTimer, fkOSPFProcAreaRangeControlTimeStamp, fkOSPFProcAreaRangeControlReqResult, fkOSPFProcAreaRangeControlProcID, fkOSPFProcAreaRangeControlID, 
				fkOSPFProcAreaRangeControlIP, fkOSPFProcAreaRangeControlIPMask, fkOSPFProcAreaRangeControlAdverType, fkOSPFProcAreaVlinkIP, fkOSPFProcAreaVlinkAuthenType, 
				fkOSPFProcAreaVlinkAuthenKey, fkOSPFProcAreaVlinkDeadInterval, fkOSPFProcAreaVlinkHelloInterval, fkOSPFProcAreaVlinkRetranInterval, fkOSPFProcAreaVlinkTransDelay, 
				fkOSPFProcAreaVlinkControlRequest, fkOSPFProcAreaVlinkControlStatus, fkOSPFProcAreaVlinkControlTimer, fkOSPFProcAreaVlinkControlTimeStamp, fkOSPFProcAreaVlinkControlReqResult, 
				fkOSPFProcAreaVlinkControlProcID, fkOSPFProcAreaVlinkControlControlID, fkOSPFProcAreaVlinkControlIP, fkOSPFProcAreaVlinkControlAuthenType, fkOSPFProcAreaVlinkControlAuthenKey, 
				fkOSPFProcAreaVlinkControlDeadInterval, fkOSPFProcAreaVlinkControlHelloInterval, fkOSPFProcAreaVlinkControlRetranInterval, fkOSPFProcAreaVlinkControlTransInterval, fkOSPFProcAreaVlinkMsgKeyID, 
				fkOSPFProcAreaVlinkMsgKeyVal, fkOSPFProcAreaVlinkMsgKeyControlRequest, fkOSPFProcAreaVlinkMsgKeyControlControlStatus, fkOSPFProcAreaVlinkMsgKeyControlControlTimer, fkOSPFProcAreaVlinkMsgKeyControlTimeStamp, 
				fkOSPFProcAreaVlinkMsgKeyControlReqResult, fkOSPFProcAreaVlinkMsgKeyControlProcID, fkOSPFProcAreaVlinkMsgKeyControlID, fkOSPFProcAreaVlinkMsgKeyControlIP, fkOSPFProcAreaVlinkMsgKeyControlKeyID, 
				fkOSPFProcAreaVlinkMsgKeyControlKeyVal, fkOSPFIfIndex, fkOSFPIfEnabled, fkOSPFIfNetworkType, fkOSFPIfMTU, 
				fkOSFPIfBFD, fkOSFPIfEFM, fkOSPFIfControlRequest, fkOSPFIfControlStatus, fkOSPFIfControlTimer, 
				fkOSPFIfControlTimeStamp, fkOSPFIfControlReqResult, fkOSPFIfControlIndex, fkOSPFIfControlEnabled, fkOSPFIfControlNetworkType, 
				fkOSPFIfControlMTU, fkOSPFIfControlBFD, fkOSPFIfControlEFM, fkOSPFIfIpAddr, fkOSPFIfCost, 
				fkOSPFIfTransmitDelay, fkOSPFIfPriority, fkOSPFIfHelloInterval, fkOSPFIfDeadInterval, fkOSPFIfRetransInterval, 
				fkOSPFIfAuth, fkOSPFIfAuthType, fkOSPFIfDataFilterOut, fkOSPFIfMTUIgnore, fkOSPFIfResync, 
				fkOSPFIfResyncTimeout, fkOSPFIfAuthKeyFirst, fkOSPFIfAuthKeyFirstAct, fkOSPFIfAuthKeySecond, fkOSPFIfAuthKeySecondAct, 
				fkOSPFIfInfoControlRequest, fkOSPFIfInfoControlStatus, fkOSPFIfInfoControlTimer, fkOSPFIfInfoControlTimeStamp, fkOSPFIfInfoControlReqResult, 
				fkOSPFIfInfoControlIndex, fkOSPFIfInfoControlIpAddr, fkOSPFIfInfoControlCost, fkOSPFIfInfoControlTransmitDelay, fkOSPFIfInfoControlPriority, 
				fkOSPFIfInfoControlHelloInterval, fkOSPFIfInfoControlDeadInterval, fkOSPFIfInfoControlRetransInterval, fkOSPFIfInfoControlAuth, fkOSPFIfInfoControlAuthType, 
				fkOSPFIfInfoControlDataFilterOut, fkOSPFIfInfoControlMTUIgnore, fkOSPFIfInfoControlResync, fkOSPFIfInfoControlResyncTimeout, fkOSPFIfInfoControlAuthKeyFirst, 
				fkOSPFIfInfoControlAuthKeyFirstAct, fkOSPFIfInfoControlAuthKeySecond, fkOSPFIfInfoControlAuthKeySecondAct, fkOSPFIfMsgKeyID, fkOSPFIfMsgKeyVal, 
				fkOSPFIfMsgKeyAct, fkOSPFIfMsgKeyControlRequest, fkOSPFIfMsgKeyControlStatus, fkOSPFIfMsgKeyControlTimer, fkOSPFIfMsgKeyControlTimeStamp, 
				fkOSPFIfMsgKeyControlReqResult, fkOSPFIfMsgKeyControlIndex, fkOSPFIfMsgKeyControlIpAddr, fkOSPFIfMsgKeyControlKeyID, fkOSPFIfMsgKeyControlKeyVal, 
				fkOSPFIfMsgKeyControlKeyAct, fkOSPFIfStatusAddr, fkOSPFIfStatusUpState, fkOSPFIfStatusAreaID, fkOSPFIfStatusProcID, 
				fkOSPFIfStatusRouterID, fkOSPFIfStatusNetworkType, fkOSPFIfStatusCost, fkOSPFIfStatusTransmitDelay, fkOSPFIfStatusState, 
				fkOSPFIfStatusPriorityUse, fkOSPFIfStatusPriority, fkOSPFIfStatusDRRouterUse, fkOSPFIfStatusDRRouterID, fkOSPFIfStatusDRIfIpAddr, 
				fkOSPFIfStatusBDRRouterUse, fkOSPFIfStatusBDRRouterID, fkOSPFIfStatusBDRIfIpAddr, fkOSPFIfStatusHelloInterval, fkOSPFIfStatusDeadInterval, 
				fkOSPFIfStatusRetransInterval, fkOSPFIfStatusWaitInterval, fkOSPFIfStatusNeighborCount, fkOSPFIfCryptSeqNum, fkOSPFIfStatusRcvHello, 
				fkOSPFIfStatusSendHello, fkOSPFIfStatusRcvDD, fkOSPFIfStatusSendDD, fkOSPFIfStatusRcvLSReq, fkOSPFIfStatusSendLSReq, 
				fkOSPFIfStatusRcvLSUpd, fkOSPFIfStatusSendLSUpd, fkOSPFIfStatusRcvLSAck, fkOSPFIfStatusSendLSAck, fkOSPFIfStatusDiscarded, 
				fkOSPFLsaType, fkOSPFLsaAreaID, fkOSPFLsaLinkID, fkOSPFLsaAdvRouter, fkOSPFLsaAge, 
				fkOSPFLsaSequence, fkOSPFNeighborIPAddr, fkOSPFNeighborID, fkOSPFNeighborPriority, fkOSPFNeighborState, 
				fkOSPFNeighborIfName, fkOSPFRoutePathType, fkOSPFRouteNexthop, fkOSPFRouteNbrID, fkOSPFRoutePathTypeCode, 
				fkOSPFRouteMetric, fkOSPFRouteIfName, fkOSPFRouteAreaUse, fkOSPFRouteAreaID }
			STATUS current
			DESCRIPTION 
				"Description."
			::= { fkOspf 7 }

		
		-- 1.3.6.1.4.1.10428 9 1.101.51.8
		fkOspfNotificationGroup NOTIFICATION-GROUP
			NOTIFICATIONS { fkOSPFRestartPeriodChanged, fkOSPFRestartHelperProfileChanged, fkOSPFGracefulRestarted, fkOSPFProcCreated, fkOSPFProcDeleted, 
				fkOSPFRouterIDCreated, fkOSPFRouterIDDeleted, fkOSPFProcSPFTimerChanged, fkOSPFProcAutoCostChanged, fkOSPFProcAbrTypeChanged, 
				fkOSPFProcSnmpNotificationChanged, fkOSPFProcDefaultMetricProfileChanged, fkOSPFProcMaxAreaChanged, fkOSPFProcMaxConcurDDChanged, fkOSPFProcComrfc1853Changed, 
				fkOSPFProcCapOpaqueChanged, fkOSPFProcLSDBOverflowProfileChanged, fkOSPFProcExtOverflowProfileChanged, fkOSPFProcAdminDistanceChanged, fkOSPFProcExtDistanceChanged, 
				fkOSPFProcIntraDistanceChanged, fkOSPFProcInterDistanceChanged, fkOSPFProcDefaultOriginTypeChanged, fkOSPFProcDefaultOriginMetricTypeChanged, fkOSPFProcDefaultOriginMetricChanged, 
				fkOSPFProcDefaultOriginRouteMapChanged, fkOSPFProcLogNeighborChanged, fkOSPFProcPassiveIFAllChanged, fkOSPFProcBfdIFAllChanged, fkOSPFProcEfmIFAllChanged, 
				fkOSPFProcCapRestartChanged, fkOSPFProcCleared, fkOSPFProcNetworkCreated, fkOSPFProcNetworkDeleted, fkOSPFSummaryCreated, 
				fkOSPFSummaryDeleted, fkOSPFSummaryChanged, fkOSPFDistributeListCreated, fkOSPFDistributeListDeleted, fkOSPFProcNeighborCreated, 
				fkOSPFProcNeighborDeleted, fkOSPFProcNeighborChanged, fkOSPFPassInterfaceCreated, fkOSPFPassInterfaceDeleted, fkOSPFProcHostCreated, 
				fkOSPFProcHostDeleted, fkOSPFProcHostCostChanged, fkOSPFProcRedistCreated, fkOSPFProcRedistDeleted, fkOSPFProcRedistChanged, 
				fkOSPFProcGeneralAreaCreated, fkOSPFProcStubNssaAreaCreated, fkOSPFProcAreaDeleted, fkOSPFProcAreaDefaultCostChanged, fkOSPFProcAreaAuthenTypeChanged, 
				fkOSPFProcAreaFAInNameChanged, fkOSPFProcAreaFAOutNameChanged, fkOSPFProcAreaFPInNameChanged, fkOSPFProcAreaFPOutNameChanged, fkOSPFProcAreaShortcutTypeChanged, 
				fkOSPFProcAreaSummaryChanged, fkOSPFProcNssaAreaTransRoleChanged, fkOSPFProcNssaAreaTransNoRedistChanged, fkOSPFProcNssaAreaDefProfileChanged, fkOSPFAreaRangeCreated, 
				fkOSPFAreaRangeDeleted, fkOSPFAreaRangeChanged, fkOSPFAreaVlinkCreated, fkOSPFAreaVLinkDeleted, fkOSPFAreaVLinkChanged, 
				fkOSPFAreaVlinkMsgKeyCreated, fkOSPFAreaVLinkMsgKeyDeleted, fkOSPFIfEnableChanged, fkOSPFIfNetworkTypeChanged, fkOSPFIfMTUChanged, 
				fkOSPFIfBFDChanged, fkOSPFIfEFMChanged, fkOSPFIfCostChanged, fkOSPFIfPriorityChanged, fkOSPFIfTransmitDelayChanged, 
				fkOSPFIfHelloIntervalChanged, fkOSPFIfDeadIntervalChanged, fkOSPFIfRetransIntervalChanged, fkOSPFIfAuthProfileChanged, fkOSPFIfDatafilterOutChanged, 
				fkOSPFIfMTUIgnoreChanged, fkOSPFIfResyncProfileChanged, fkOSPFIfAuthKeyFirstProfileChanged, fkOSPFIfAuthKeyProfileSecondChanged, fkOSPFIfMsgKeyCreated, 
				fkOSPFIfMsgKeyDeleted }
			STATUS current
			DESCRIPTION 
				"Description."
			::= { fkOspf 8 }

		
	
	END

--
-- FK-OSPF-MIB.my
--
