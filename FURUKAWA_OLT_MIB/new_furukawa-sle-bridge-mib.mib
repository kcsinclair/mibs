--
-- 

        FK-BRIDGE-MIB DEFINITIONS ::= BEGIN
 
                IMPORTS
                        fkMgmt                  
                                FROM FKOLTG1040-SMI                     
                        AddressFamilyNumbers                    
                                FROM IANA-ADDRESS-FAMILY-NUMBERS-MIB                    
                        InterfaceIndex                  
                                FROM IF-MIB                     
                        FkControlStatusType, FkControlRequestResultType                 
                                FROM FK-TC-MIB                  
                        OBJECT-GROUP, NOTIFICATION-GROUP                        
                                FROM SNMPv2-CONF                        
                        TimeTicks, IpAddress, Integer32, Unsigned32, Gauge32, 
                        Counter32, Counter64, OBJECT-TYPE, MODULE-IDENTITY, 
                        NOTIFICATION-TYPE                       
                                FROM SNMPv2-SMI                 
                        TimeStamp, MacAddress, TruthValue                       
                                FROM SNMPv2-TC;
        
        
--                      fk                      
-- FROM AN-MIB                  
-- December 08, 2004 at 08:40 GMT
-- 
-- 1.3.6.1.4.1.10428 9 1.9.8
-- December 08, 2004 at 09:03 GMT
-- December 08, 2004 at 08:40 GMT
                -- 1.3.6.1.4.1.10428 9 1.101.3
                fkBridge MODULE-IDENTITY 
                        LAST-UPDATED "200412080903Z"            -- December 08, 2004 at 09:03 GMT
                        ORGANIZATION 
                                "Furukawa Industrial S.A."
                        CONTACT-INFO 
                                "Furukawa Industrial S.A. Produtos Eletricos
        Rua Hasdrubal Bellegard, 820 - CIC
        CEP 81460-120 - Curitiba - Parana - Brasil
        CSC 0800-41-2100
        E-mail: fisa@furukawa.com.br"
                        DESCRIPTION 
                                "The MIB module for Furukawa GPON OLT FK-OLT-G1040."
                        ::= { fkMgmt 3 }

                
        
--
-- Type definitions
--
        
                Boolean ::= INTEGER
                        {
                        disable(0),
                        enable(1)
                        }

                FkLldpSysCapType ::= BITS
                        {
                        other(0),
                        repeater(1),
                        bridge(2),
                        wlanAccessPoint(3),
                        router(4),
                        telephone(5),
                        docsisCableDevice(6),
                        stationOnly(7)
                        }

--  Type definitions
-- 
                FkIgmpMcastControlRequestType ::= INTEGER
                        {
                        createIgmpStaticMcast(1),
                        destroyIgmpStaticMcast(2)
                        }

                FkIgmpConfControlRequestType ::= INTEGER { setIgmpConfProfile(1) }

                FkLldpManAddrIfSubType ::= INTEGER
                        {
                        unknown(1),
                        ifIndex(2),
                        systemPortNumber(3)
                        }

        
        
--
-- Node definitions
--
        
--  Node definitions
-- 
-- 1.3.6.1.4.1.10428 9 1.9.8.1
                -- 1.3.6.1.4.1.10428 9 1.101.3.1
                fkBridgeBase OBJECT IDENTIFIER ::= { fkBridge 1 }

                
--  1.3.6.1.4.1.10428 9 1.9.8.1.1
                -- 1.3.6.1.4.1.10428 9 1.101.3.1.1
                fkBridgeBaseInfo OBJECT IDENTIFIER ::= { fkBridgeBase 1 }

                
--  1.3.6.1.4.1.10428 9 1.9.8.1.1.1
                -- 1.3.6.1.4.1.10428 9 1.101.3.1.1.1
                fkBridgeMacAddress OBJECT-TYPE
                        SYNTAX OCTET STRING (SIZE (6))
                        MAX-ACCESS read-only
                        STATUS current
                        DESCRIPTION
                                "System MAC Address of bridge"
                        ::= { fkBridgeBaseInfo 1 }

                
--  1.3.6.1.4.1.10428 9 1.9.8.1.1.2
                -- 1.3.6.1.4.1.10428 9 1.101.3.1.1.2
                fkBridgePortNum OBJECT-TYPE
                        SYNTAX INTEGER (1..256)
                        MAX-ACCESS read-only
                        STATUS current
                        DESCRIPTION
                                "Number of bridge ports"
                        ::= { fkBridgeBaseInfo 2 }

                
--  1.3.6.1.4.1.10428 9 1.9.8.1.1.3
                -- 1.3.6.1.4.1.10428 9 1.101.3.1.1.3
                fkBridgeLagMaxId OBJECT-TYPE
                        SYNTAX INTEGER (1..14)
                        MAX-ACCESS read-only
                        STATUS current
                        DESCRIPTION
                                "This value assigned to the aggregation max id."
                        ::= { fkBridgeBaseInfo 3 }

                
--  1.3.6.1.4.1.10428 9 1.9.8.1.1.4
                -- 1.3.6.1.4.1.10428 9 1.101.3.1.1.4
                fkBridgeLacpActivity OBJECT-TYPE
                        SYNTAX INTEGER
                                {
                                disabled(0),
                                enabled(1)
                                }
                        MAX-ACCESS read-only
                        STATUS current
                        DESCRIPTION
                                "The LACP enabled/disabled status of the switch"
                        ::= { fkBridgeBaseInfo 4 }

                
--  1.3.6.1.4.1.10428 9 1.9.8.1.1.5
                -- 1.3.6.1.4.1.10428 9 1.101.3.1.1.5
                fkBridgeLacpPriority OBJECT-TYPE
                        SYNTAX INTEGER (1..65535)
                        MAX-ACCESS read-only
                        STATUS current
                        DESCRIPTION
                                "The priority assigned to the Actor System"
                        ::= { fkBridgeBaseInfo 5 }

                
--  1.3.6.1.4.1.10428 9 1.9.8.1.1.6
                -- 1.3.6.1.4.1.10428 9 1.101.3.1.1.6
                fkBridgeVlanSupportMode OBJECT-TYPE
                        SYNTAX BITS
                                {
                                portbased(0),
                                protocolbased(1),
                                subnetbased(2)
                                }
                        MAX-ACCESS read-only
                        STATUS current
                        DESCRIPTION
                                "The supported VLAN mode for ingress untagged frame"
                        ::= { fkBridgeBaseInfo 6 }

                
--  1.3.6.1.4.1.10428 9 1.9.8.1.1.7
                -- 1.3.6.1.4.1.10428 9 1.101.3.1.1.7
                fkBridgeVlanMaxNum OBJECT-TYPE
                        SYNTAX INTEGER (0..4096)
                        MAX-ACCESS read-only
                        STATUS current
                        DESCRIPTION
                                "fkBridgeVlanMaxNum"
                        ::= { fkBridgeBaseInfo 7 }

                
--  1.3.6.1.4.1.10428 9 1.9.8.1.1.8
                -- 1.3.6.1.4.1.10428 9 1.101.3.1.1.8
                fkBridgeDoubleTagProtoId OBJECT-TYPE
                        SYNTAX INTEGER
                                {
                                dtag8100(33024),
                                dtag9100(37120)
                                }
                        MAX-ACCESS read-only
                        STATUS current
                        DESCRIPTION
                                "programmable Double Tag Protocol Identifier.
                                It means outerTPID."
                        ::= { fkBridgeBaseInfo 8 }

                
--  1.3.6.1.4.1.10428 9 1.9.8.1.1.23
                -- 1.3.6.1.4.1.10428 9 1.101.3.1.1.9
                fkBridgeMirrorMode OBJECT-TYPE
                        SYNTAX INTEGER
                                {
                                disabled(0),
                                enabled(1)
                                }
                        MAX-ACCESS read-only
                        STATUS current
                        DESCRIPTION
                                "Mirror mode of bridge"
                        ::= { fkBridgeBaseInfo 9 }

                
--  1.3.6.1.4.1.10428 9 1.9.8.1.1.24
                -- 1.3.6.1.4.1.10428 9 1.101.3.1.1.10
                fkBridgeMirrorMonitorPortId OBJECT-TYPE
                        SYNTAX INTEGER (1..255)
                        MAX-ACCESS read-only
                        STATUS current
                        DESCRIPTION
                                "Mirroring port ID
                                1-254: physical port ID
                                255: mirror to cpu"
                        ::= { fkBridgeBaseInfo 10 }

                
                -- 1.3.6.1.4.1.10428 9 1.101.3.1.1.11
                fkBridgeMirroredIngressPorts OBJECT-TYPE
                        SYNTAX OCTET STRING (SIZE (0..32))
                        MAX-ACCESS read-only
                        STATUS current
                        DESCRIPTION
                                "Ingress mirrored port map"
                        ::= { fkBridgeBaseInfo 11 }

                
                -- 1.3.6.1.4.1.10428 9 1.101.3.1.1.12
                fkBridgeMirroredEgressPorts OBJECT-TYPE
                        SYNTAX OCTET STRING (SIZE (0..32))
                        MAX-ACCESS read-only
                        STATUS current
                        DESCRIPTION
                                "Egress mirrored port map"
                        ::= { fkBridgeBaseInfo 12 }

                
                -- 1.3.6.1.4.1.10428 9 1.101.3.1.1.13
                fkBridgeMaxLearnPerUnit OBJECT-TYPE
                        SYNTAX INTEGER (-1..2147483647)
                        MAX-ACCESS read-only
                        STATUS current
                        DESCRIPTION
                                "Limit maximum number of MAC addresses learning 
                                newly per unit time(one second) on a bridge.
                                (0: nothing learned, -l: unlimited.)"
                        ::= { fkBridgeBaseInfo 13 }

                
--  1.3.6.1.4.1.10428 9 1.9.8.1.1.25
                -- 1.3.6.1.4.1.10428 9 1.101.3.1.1.14
                fkBridgeFdbAgeingTime OBJECT-TYPE
                        SYNTAX Integer32 (10..21474830)
                        MAX-ACCESS read-only
                        STATUS current
                        DESCRIPTION
                                "The timeout period in seconds for aging out 
                                dynamically learned forwarding information."
                        DEFVAL { 300 }
                        ::= { fkBridgeBaseInfo 14 }

                
--  1.3.6.1.4.1.10428 9 1.9.8.1.1.26
                -- 1.3.6.1.4.1.10428 9 1.101.3.1.1.15
                fkBridgeFdbMaxEntries OBJECT-TYPE
                        SYNTAX Integer32
                        MAX-ACCESS read-only
                        STATUS current
                        DESCRIPTION
                                "The supported maximum fdb entries."
                        ::= { fkBridgeBaseInfo 15 }

                
                -- 1.3.6.1.4.1.10428 9 1.101.3.1.1.16
                fkBridgeFdbCurrentEntries OBJECT-TYPE
                        SYNTAX Integer32
                        MAX-ACCESS read-only
                        STATUS current
                        DESCRIPTION
                                "Number of Fdb entries learned currently."
                        ::= { fkBridgeBaseInfo 16 }

                
--  1.3.6.1.4.1.10428 9 1.9.8.1.1.27
                -- 1.3.6.1.4.1.10428 9 1.101.3.1.1.17
                fkBridgeStackMode OBJECT-TYPE
                        SYNTAX INTEGER
                                {
                                disable(0),
                                master(1),
                                slave(2)
                                }
                        MAX-ACCESS read-only
                        STATUS current
                        DESCRIPTION
                                "Stack status of device."
                        ::= { fkBridgeBaseInfo 17 }

                
--  1.3.6.1.4.1.10428 9 1.9.8.1.1.28
                -- 1.3.6.1.4.1.10428 9 1.101.3.1.1.18
                fkBridgeStackDeviceName OBJECT-TYPE
                        SYNTAX OCTET STRING (SIZE (0..8))
                        MAX-ACCESS read-only
                        STATUS current
                        DESCRIPTION
                                "Device name of stack device."
                        ::= { fkBridgeBaseInfo 18 }

                
--  1.3.6.1.4.1.10428 9 1.9.8.1.1.29
                -- 1.3.6.1.4.1.10428 9 1.101.3.1.1.19
                fkBridgeStackNodeId OBJECT-TYPE
                        SYNTAX INTEGER (1..65534)
                        MAX-ACCESS read-only
                        STATUS current
                        DESCRIPTION
                                "Node ID of stack device"
                        ::= { fkBridgeBaseInfo 19 }

                
--  1.3.6.1.4.1.10428 9 1.9.8.1.1.30
                -- 1.3.6.1.4.1.10428 9 1.101.3.1.1.20
                fkBridgeLldpMessageTxInterval OBJECT-TYPE
                        SYNTAX Integer32 (5..32768)
                        MAX-ACCESS read-write
                        STATUS current
                        DESCRIPTION
                                "The interval at which LLDP frames are transmitted on behalf of this LLDP agent."
                        ::= { fkBridgeBaseInfo 20 }

                
--  1.3.6.1.4.1.10428 9 1.9.8.1.1.31
                -- 1.3.6.1.4.1.10428 9 1.101.3.1.1.21
                fkBridgeLldpTxHoldMultiplier OBJECT-TYPE
                        SYNTAX Integer32 (2..10)
                        MAX-ACCESS read-write
                        STATUS current
                        DESCRIPTION
                                "The time-to-live value expressed as a multiple of the fkBridgeLldpMessageTxInterval object."
                        ::= { fkBridgeBaseInfo 21 }

                
--  1.3.6.1.4.1.10428 9 1.9.8.1.1.32
                -- 1.3.6.1.4.1.10428 9 1.101.3.1.1.22
                fkBridgeLldpReinitDelay OBJECT-TYPE
                        SYNTAX Integer32 (1..10)
                        MAX-ACCESS read-write
                        STATUS current
                        DESCRIPTION
                                "Delay (in units of seconds) from when lldpPortConfigAdminStatus object of a particular port  becomes 'disabled' until re-initialization will be attempted."
                        ::= { fkBridgeBaseInfo 22 }

                
--  1.3.6.1.4.1.10428 9 1.9.8.1.1.33
                -- 1.3.6.1.4.1.10428 9 1.101.3.1.1.23
                fkBridgeLldpTxDelay OBJECT-TYPE
                        SYNTAX Integer32 (1..8192)
                        MAX-ACCESS read-write
                        STATUS current
                        DESCRIPTION
                                "Delay (in units of seconds) between successive LLDP frame transmissions initiated by value/status changes in the LLDP local systems MIB."
                        ::= { fkBridgeBaseInfo 23 }

                
--  1.3.6.1.4.1.10428 9 1.9.8.1.1.34
                -- 1.3.6.1.4.1.10428 9 1.101.3.1.1.24
                fkBridgeLldpNotificationInterval OBJECT-TYPE
                        SYNTAX Integer32 (5..3600)
                        MAX-ACCESS read-write
                        STATUS current
                        DESCRIPTION
                                "The agent must not generate more than one lldpRemTablesChangenotification-event in the indicated period."
                        DEFVAL { 5 }
                        ::= { fkBridgeBaseInfo 24 }

                
--  1.3.6.1.4.1.10428 9 1.9.8.1.1.36
                -- 1.3.6.1.4.1.10428 9 1.101.3.1.1.25
                fkBridgeLldpStatsRemTablesLastChangeTime OBJECT-TYPE
                        SYNTAX TimeTicks
                        MAX-ACCESS read-only
                        STATUS current
                        DESCRIPTION
                                "The value of sysUpTime object (defined in IETF RFC 3418)at the time an entry is created, modified, or deleted in thein tables associated with the lldpRemoteSystemsData objects and all LLDP extension objects associated with remote systems."
                        ::= { fkBridgeBaseInfo 25 }

                
--  1.3.6.1.4.1.10428 9 1.9.8.1.1.37
                -- 1.3.6.1.4.1.10428 9 1.101.3.1.1.26
                fkBridgeLldpStatsRemTablesInserts OBJECT-TYPE
                        SYNTAX Integer32
                        MAX-ACCESS read-only
                        STATUS current
                        DESCRIPTION
                                "The number of times the complete set of informationadvertised by a particular MSAP has been inserted into tables contained in lldpRemoteSystemsData and lldpExtensions objects."
                        ::= { fkBridgeBaseInfo 26 }

                
--  1.3.6.1.4.1.10428 9 1.9.8.1.1.38
                -- 1.3.6.1.4.1.10428 9 1.101.3.1.1.27
                fkBridgeLldpStatsRemTablesDeletes OBJECT-TYPE
                        SYNTAX Integer32
                        MAX-ACCESS read-only
                        STATUS current
                        DESCRIPTION
                                "The number of times the complete set of informationadvertised by a particular MSAP has been deleted fromtables contained in lldpRemoteSystemsData and lldpExtensions objects."
                        ::= { fkBridgeBaseInfo 27 }

                
--  1.3.6.1.4.1.10428 9 1.9.8.1.1.39
                -- 1.3.6.1.4.1.10428 9 1.101.3.1.1.28
                fkBridgeLldpStatsRemTablesDrops OBJECT-TYPE
                        SYNTAX Integer32
                        MAX-ACCESS read-only
                        STATUS current
                        DESCRIPTION
                                "The number of times the complete set of information advertised by a particular MSAP could not be entered intotables contained in lldpRemoteSystemsData and lldpExtensions objects because of insufficient resources."
                        ::= { fkBridgeBaseInfo 28 }

                
--  1.3.6.1.4.1.10428 9 1.9.8.1.1.40
                -- 1.3.6.1.4.1.10428 9 1.101.3.1.1.29
                fkBridgeLldpStatsRemTablesAgeouts OBJECT-TYPE
                        SYNTAX Integer32
                        MAX-ACCESS read-only
                        STATUS current
                        DESCRIPTION
                                "The number of times the complete set of informationadvertised by a particular MSAP has been deleted from tables contained in lldpRemoteSystemsData and lldpExtensions objectsbecause the information timeliness interval has expired."
                        ::= { fkBridgeBaseInfo 29 }

                
--  1.3.6.1.4.1.10428 9 1.9.8.1.1.41
                -- 1.3.6.1.4.1.10428 9 1.101.3.1.1.30
                fkBridgeLldpLocalChassisIdSubtype OBJECT-TYPE
                        SYNTAX INTEGER
                                {
                                chassisComponent(1),
                                interfaceAlias(2),
                                portComponent(3),
                                macAddress(4),
                                networkAddress(5),
                                interfaceName(6),
                                local(7)
                                }
                        MAX-ACCESS read-only
                        STATUS current
                        DESCRIPTION
                                "The type of encoding used to identify the chassis associated with the local system."
                        ::= { fkBridgeBaseInfo 30 }

                
--  1.3.6.1.4.1.10428 9 1.9.8.1.1.42
                -- 1.3.6.1.4.1.10428 9 1.101.3.1.1.31
                fkBridgeLldpLocalChassisId OBJECT-TYPE
                        SYNTAX OCTET STRING (SIZE (1..255))
                        MAX-ACCESS read-only
                        STATUS current
                        DESCRIPTION
                                "The string value used to identify the chassis component associated with the local system."
                        ::= { fkBridgeBaseInfo 31 }

                
--  1.3.6.1.4.1.10428 9 1.9.8.1.1.43
                -- 1.3.6.1.4.1.10428 9 1.101.3.1.1.32
                fkBridgeLldpLocalSysName OBJECT-TYPE
                        SYNTAX OCTET STRING (SIZE (0..255))
                        MAX-ACCESS read-only
                        STATUS current
                        DESCRIPTION
                                "The string value used to identify the system name of the local system."
                        ::= { fkBridgeBaseInfo 32 }

                
--  1.3.6.1.4.1.10428 9 1.9.8.1.1.44
                -- 1.3.6.1.4.1.10428 9 1.101.3.1.1.33
                fkBridgeLldpLocalSysDes OBJECT-TYPE
                        SYNTAX OCTET STRING (SIZE (0..255))
                        MAX-ACCESS read-write
                        STATUS current
                        DESCRIPTION
                                "The string value used to identify the system description of the local system."
                        ::= { fkBridgeBaseInfo 33 }

                
--  1.3.6.1.4.1.10428 9 1.9.8.1.1.45
                -- 1.3.6.1.4.1.10428 9 1.101.3.1.1.34
                fkBridgeLldpLocalSysCapSupported OBJECT-TYPE
                        SYNTAX BITS
                                {
                                other(0),
                                repeater(1),
                                bridge(2),
                                wlanAccessPoint(3),
                                router(4),
                                telephone(5),
                                docsisCableDevice(6),
                                stationOnly(7)
                                }
                        MAX-ACCESS read-only
                        STATUS current
                        DESCRIPTION
                                "The bitmap value used to identify which system capabilities are supported on the local system."
                        ::= { fkBridgeBaseInfo 34 }

                
--  1.3.6.1.4.1.10428 9 1.9.8.1.1.46
                -- 1.3.6.1.4.1.10428 9 1.101.3.1.1.35
                fkBridgeLldpLocalSysCapEnabled OBJECT-TYPE
                        SYNTAX BITS
                                {
                                other(0),
                                repeater(1),
                                bridge(2),
                                wlanAccessPoint(3),
                                router(4),
                                telephone(5),
                                docsisCableDevice(6),
                                stationOnly(7)
                                }
                        MAX-ACCESS read-only
                        STATUS current
                        DESCRIPTION
                                "The bitmap value used to identify which system capabilities are enabled on the local system."
                        ::= { fkBridgeBaseInfo 35 }

                
--  1.3.6.1.4.1.10428 9 1.9.8.1.1.47
                -- 1.3.6.1.4.1.10428 9 1.101.3.1.1.36
                fkBridgeStpActivity OBJECT-TYPE
                        SYNTAX INTEGER
                                {
                                disabled(0),
                                enabled(1)
                                }
                        MAX-ACCESS read-only
                        STATUS current
                        DESCRIPTION
                                "The STP enabled/disabled status of the switch."
                        ::= { fkBridgeBaseInfo 36 }

                
                -- 1.3.6.1.4.1.10428 9 1.101.3.1.1.37
                fkBridgeStpSelfLoop OBJECT-TYPE
                        SYNTAX INTEGER
                                {
                                disable(0),
                                enable(1)
                                }
                        MAX-ACCESS read-write
                        STATUS current
                        DESCRIPTION
                                "The STP self loop
                                0: disabled
                                1: enabled
                                "
                        ::= { fkBridgeBaseInfo 37 }

                
                -- 1.3.6.1.4.1.10428 9 1.101.3.1.1.38
                fkBridgePvlanOnePromPortEnable OBJECT-TYPE
                        SYNTAX INTEGER
                                {
                                disable(0),
                                enable(1)
                                }
                        MAX-ACCESS read-write
                        STATUS current
                        DESCRIPTION
                                "The value used to identify that a isolated port can be associated with only one or entire promiscuous ports on the local system."
                        DEFVAL { disable }
                        ::= { fkBridgeBaseInfo 38 }

                
                -- 1.3.6.1.4.1.10428 9 1.101.3.1.1.39
                fkBridgeTcpSyncookie OBJECT-TYPE
                        SYNTAX INTEGER
                                {
                                disable(0),
                                enable(1)
                                }
                        MAX-ACCESS read-only
                        STATUS current
                        DESCRIPTION
                                "The value permits only when transmitted cookies are returned after sending cookies with SYN"
                        ::= { fkBridgeBaseInfo 39 }

                
                -- 1.3.6.1.4.1.10428 9 1.101.3.1.1.40
                fkBridgeTcpIgnoreRstUnknown OBJECT-TYPE
                        SYNTAX INTEGER
                                {
                                disable(0),
                                enable(1)
                                }
                        MAX-ACCESS read-only
                        STATUS current
                        DESCRIPTION
                                "The value configures not to send the message that informs TCP connection cannot be done."
                        ::= { fkBridgeBaseInfo 40 }

                
                -- 1.3.6.1.4.1.10428 9 1.101.3.1.1.41
                fkBridgeAutoInterfaceActivation OBJECT-TYPE
                        SYNTAX INTEGER
                                {
                                enable(1),
                                disable(2)
                                }
                        MAX-ACCESS read-only
                        STATUS current
                        DESCRIPTION
                                "The value configures auto Interface activation.
                                (supported only model 5924N)"
                        ::= { fkBridgeBaseInfo 41 }

                
                -- 1.3.6.1.4.1.10428 9 1.101.3.1.1.42
                fkBridgeLoopDetectStatus OBJECT-TYPE
                        SYNTAX INTEGER
                                {
                                enable(1),
                                disable(2)
                                }
                        MAX-ACCESS read-only
                        STATUS current
                        DESCRIPTION
                                "The global adminStatus of Loop-Detect."
                        ::= { fkBridgeBaseInfo 42 }

                
                -- 1.3.6.1.4.1.10428 9 1.101.3.1.1.43
                fkBridgeLoopDetectPacketType OBJECT-TYPE
                        SYNTAX INTEGER
                                {
                                laa(1),
                                system(2)
                                }
                        MAX-ACCESS read-only
                        STATUS current
                        DESCRIPTION
                                "The type of srcmac to be detected.
                                1.laa : Locally Administered Address
                                2.system : System MAC (default)"
                        ::= { fkBridgeBaseInfo 43 }

                
                -- 1.3.6.1.4.1.10428 9 1.101.3.1.1.44
                fkBridgePvlanPromSelectMode OBJECT-TYPE
                        SYNTAX INTEGER
                                {
                                normal(0),
                                manual(1),
                                stp(2),
                                erp(3)
                                }
                        MAX-ACCESS read-only
                        STATUS current
                        DESCRIPTION
                                "The value is used to indicate promiscuous ports selection mode:
                                normal ?default
                                manual ? by user
                                stp ? by STP (not supported)
                                erp ? by ERP
                                "
                        ::= { fkBridgeBaseInfo 44 }

                
                -- 1.3.6.1.4.1.10428 9 1.101.3.1.1.45
                fkBridgePvlanPromiscuousPorts OBJECT-TYPE
                        SYNTAX OCTET STRING
                        MAX-ACCESS read-only
                        STATUS current
                        DESCRIPTION
                                "Bitmap of promiscuous ports on bridge."
                        ::= { fkBridgeBaseInfo 45 }

                
                -- 1.3.6.1.4.1.10428 9 1.101.3.1.1.46
                fkBridgeInnerTagProtoId OBJECT-TYPE
                        SYNTAX INTEGER
                                {
                                dtag8100(33024),
                                dtag9100(37120)
                                }
                        MAX-ACCESS read-only
                        STATUS current
                        DESCRIPTION
                                "programmable Inner Double Tag Protocol Identifier.
                                It means innerTPID"
                        ::= { fkBridgeBaseInfo 46 }

                
                -- 1.3.6.1.4.1.10428 9 1.101.3.1.1.47
                fkBridgeUnknownMcastBlockAllPorts OBJECT-TYPE
                        SYNTAX INTEGER
                                {
                                enable(1),
                                disable(2)
                                }
                        MAX-ACCESS read-only
                        STATUS current
                        DESCRIPTION
                                "Unknown multicast block setting for all ports."
                        ::= { fkBridgeBaseInfo 47 }

                
                -- 1.3.6.1.4.1.10428 9 1.101.3.1.1.48
                fkBridgeEcmpHashType OBJECT-TYPE
                        SYNTAX INTEGER
                                {
                                sip(1),
                                sipDip(2)
                                }
                        MAX-ACCESS read-only
                        STATUS current
                        DESCRIPTION
                                "ECMP Hash Type"
                        ::= { fkBridgeBaseInfo 48 }

                
                -- 1.3.6.1.4.1.10428 9 1.101.3.1.1.49
                fkBridgeTcpSynguard OBJECT-TYPE
                        SYNTAX Integer32 (0..2147483647)
                        MAX-ACCESS read-only
                        STATUS current
                        DESCRIPTION
                                "The tcp-synguard bandwidth."
                        ::= { fkBridgeBaseInfo 49 }

                
                -- 1.3.6.1.4.1.10428 9 1.101.3.1.1.50
                fkBridgeOuterTagProtoId OBJECT-TYPE
                        SYNTAX INTEGER
                                {
                                dtag8100(33024),
                                dtag9100(37120)
                                }
                        MAX-ACCESS read-only
                        STATUS current
                        DESCRIPTION
                                "programmable outer Double Tag Protocol Identifier.
                                  It means OutTPID"
                        ::= { fkBridgeBaseInfo 50 }

                
                -- 1.3.6.1.4.1.10428 9 1.101.3.1.1.51
                fkBridgeMacAntiSpoofing OBJECT-TYPE
                        SYNTAX INTEGER
                                {
                                enable(1),
                                disable(2)
                                }
                        MAX-ACCESS read-only
                        STATUS current
                        DESCRIPTION
                                "The protect uplink mac address"
                        ::= { fkBridgeBaseInfo 51 }

                
                -- 1.3.6.1.4.1.10428 9 1.101.3.1.1.52
                fkBridgeMacReplace OBJECT-TYPE
                        SYNTAX INTEGER
                                {
                                enable(1),
                                disable(2)
                                }
                        MAX-ACCESS read-only
                        STATUS current
                        DESCRIPTION
                                "The mac address replace mode"
                        ::= { fkBridgeBaseInfo 52 }

                
                -- 1.3.6.1.4.1.10428 9 1.101.3.1.1.53
                fkBridgeStormControlBcast OBJECT-TYPE
                        SYNTAX INTEGER (0 | 1..65535)
                        MAX-ACCESS read-only
                        STATUS current
                        DESCRIPTION
                                "The Storm Control Broadcast Configuration
                                0: disable bcast
                                "
                        ::= { fkBridgeBaseInfo 53 }

                
                -- 1.3.6.1.4.1.10428 9 1.101.3.1.1.54
                fkBridgeStormControlDLF OBJECT-TYPE
                        SYNTAX INTEGER (0 | 1..65535)
                        MAX-ACCESS read-only
                        STATUS current
                        DESCRIPTION
                                "The Storm Control DLF Configuration
                                0: disable DLF
                                "
                        ::= { fkBridgeBaseInfo 54 }

                
                -- 1.3.6.1.4.1.10428 9 1.101.3.1.1.55
                fkBridgeStormControlMulticast OBJECT-TYPE
                        SYNTAX INTEGER (0 | 1..65535)
                        MAX-ACCESS read-only
                        STATUS current
                        DESCRIPTION
                                "The Storm Control MultiCast Configuration
                                0: disable multicast
                                "
                        ::= { fkBridgeBaseInfo 55 }

                
                -- 1.3.6.1.4.1.10428 9 1.101.3.1.1.56
                fkBridgeMacLearningMode OBJECT-TYPE
                        SYNTAX INTEGER
                                {
                                cml(1),
                                sml(2),
                                cmlsml(3)
                                }
                        MAX-ACCESS read-only
                        STATUS current
                        DESCRIPTION
                                "The MAC Learning Mode.
                                1: cml
                                2: sml
                                3: cmlsml"
                        ::= { fkBridgeBaseInfo 56 }

                
                -- 1.3.6.1.4.1.10428 9 1.101.3.1.1.57
                fkBridgeLagGlobalDistMode OBJECT-TYPE
                        SYNTAX INTEGER
                                {
                                none(0),
                                srcmac(1),
                                dstmac(2),
                                srcdstmac(3),
                                srcip(4),
                                dstip(5),
                                srcdstip(6),
                                srcdstl4(7),
                                label(8)
                                }
                        MAX-ACCESS read-only
                        STATUS current
                        DESCRIPTION
                                "The LAG global distmode."
                        ::= { fkBridgeBaseInfo 57 }

                
                -- 1.3.6.1.4.1.10428 9 1.101.3.1.1.58
                fkBridgeMultiPortLlcfPortA OBJECT-TYPE
                        SYNTAX OCTET STRING
                        MAX-ACCESS read-only
                        STATUS current
                        DESCRIPTION
                                "The Multi port LLCF - RAPS East/West Port."
                        ::= { fkBridgeBaseInfo 58 }

                
                -- 1.3.6.1.4.1.10428 9 1.101.3.1.1.59
                fkBridgeMultiPortLlcfPortB OBJECT-TYPE
                        SYNTAX OCTET STRING
                        MAX-ACCESS read-only
                        STATUS current
                        DESCRIPTION
                                "The Multi port LLCF - RAPS East/West Port."
                        ::= { fkBridgeBaseInfo 59 }

                
                -- 1.3.6.1.4.1.10428 9 1.101.3.1.1.60
                fkBridgeMultiPortLlcfUpPortC OBJECT-TYPE
                        SYNTAX OCTET STRING
                        MAX-ACCESS read-only
                        STATUS current
                        DESCRIPTION
                                "The Multi port LLCF - force down ports"
                        ::= { fkBridgeBaseInfo 60 }

                
                -- 1.3.6.1.4.1.10428 9 1.101.3.1.1.61
                fkBridgeMultiPortLlcfDownPortC OBJECT-TYPE
                        SYNTAX OCTET STRING
                        MAX-ACCESS read-only
                        STATUS current
                        DESCRIPTION
                                "The Multi port LLCF - force down ports"
                        ::= { fkBridgeBaseInfo 61 }

                
                -- 1.3.6.1.4.1.10428 9 1.101.3.1.1.62
                fkBridgeMultiPortLlcfPortAStatus OBJECT-TYPE
                        SYNTAX INTEGER
                                {
                                none(0),
                                loc(1),
                                disable(2),
                                forcedToDown(3)
                                }
                        MAX-ACCESS read-only
                        STATUS current
                        DESCRIPTION
                                "The Multi port LLCF port's status."
                        ::= { fkBridgeBaseInfo 62 }

                
                -- 1.3.6.1.4.1.10428 9 1.101.3.1.1.63
                fkBridgeMultiPortLlcfPortBStatus OBJECT-TYPE
                        SYNTAX INTEGER
                                {
                                none(0),
                                loc(1),
                                disable(2),
                                forcedToDown(3)
                                }
                        MAX-ACCESS read-only
                        STATUS current
                        DESCRIPTION
                                "The Multi port LLCF port's status."
                        ::= { fkBridgeBaseInfo 63 }

                
                -- 1.3.6.1.4.1.10428 9 1.101.3.1.1.64
                fkBridgeMultiPortLlcfUpPortCStatus OBJECT-TYPE
                        SYNTAX INTEGER
                                {
                                none(0),
                                loc(1),
                                disable(2),
                                forcedToDown(3)
                                }
                        MAX-ACCESS read-only
                        STATUS current
                        DESCRIPTION
                                "The Multi port LLCF port's status."
                        ::= { fkBridgeBaseInfo 64 }

                
                -- 1.3.6.1.4.1.10428 9 1.101.3.1.1.65
                fkBridgeMultiPortLlcfDownPortCStatus OBJECT-TYPE
                        SYNTAX INTEGER
                                {
                                none(0),
                                loc(1),
                                disable(2),
                                forcedToDown(3)
                                }
                        MAX-ACCESS read-only
                        STATUS current
                        DESCRIPTION
                                "The Multi port LLCF port's status."
                        ::= { fkBridgeBaseInfo 65 }

                
                -- 1.3.6.1.4.1.10428 9 1.101.3.1.1.66
                fkBridgeMultiPortLlcfTimer OBJECT-TYPE
                        SYNTAX Integer32 (1000..10000)
                        MAX-ACCESS read-only
                        STATUS current
                        DESCRIPTION
                                "The LLCF's checking interval. 1000~10000ms
                                
                                (default: 2500ms)"
                        ::= { fkBridgeBaseInfo 66 }

                
--  1.3.6.1.4.1.10428 9 1.9.8.1.2
                -- 1.3.6.1.4.1.10428 9 1.101.3.1.2
                fkBridgeBaseControl OBJECT IDENTIFIER ::= { fkBridgeBase 2 }

                
--   1.3.6.1.4.1.10428 9 1.9.8.1.2.1
-- 1.3.6.1.4.1.10428 9 1.101.3.1.2.1
                -- 1.3.6.1.4.1.10428 9 1.101.3.1.2.1
                fkBridgeControlRequest OBJECT-TYPE
                        SYNTAX INTEGER
                                {
                                setLacpProfile(1),
                                setDoubleTagProtoId(2),
                                setMirrorProfile(3),
                                setMaxLearnPerUnit(4),
                                setFdbAgeingTime(5),
                                setStackProfile(6),
                                setLldpProfile(7),
                                setStpProfile(8),
                                setTcpSyncookie(9),
                                setTcpIgnoreRstUnknown(10),
                                setAutoInterfaceActivation(11),
                                setLoopDetectProfile(12),
                                setPvlanPromSelectMode(13),
                                setInnerTagProtoId(14),
                                setUnknownMcastBlockAllPorts(15),
                                setEcmpHashType(16),
                                setTcpSynguard(17),
                                setOuterTagProtoId(18),
                                setMacAntiSpoofing(19),
                                setMacReplace(20),
                                setStormControl(21),
                                setMacLearningMode(22),
                                setLagGlobalDistMode(23),
                                setMultiPortLlcf(24),
                                delMultiPortLlcf(25),
                                setMultiPortLlcfTimer(26)
                                }
                        MAX-ACCESS read-write
                        STATUS current
                        DESCRIPTION
                                "The request of a user command"
                        ::= { fkBridgeBaseControl 1 }

                
--  1.3.6.1.4.1.10428 9 1.9.8.1.2.2
                -- 1.3.6.1.4.1.10428 9 1.101.3.1.2.2
                fkBridgeControlStatus OBJECT-TYPE
                        SYNTAX FkControlStatusType
                        MAX-ACCESS read-only
                        STATUS current
                        DESCRIPTION
                                " The status of user command"
                        ::= { fkBridgeBaseControl 2 }

                
--  1.3.6.1.4.1.10428 9 1.9.8.1.2.3
                -- 1.3.6.1.4.1.10428 9 1.101.3.1.2.3
                fkBridgeControlTimer OBJECT-TYPE
                        SYNTAX Gauge32
                        MAX-ACCESS read-write
                        STATUS current
                        DESCRIPTION
                                " The maximum time for the manager for a long running user command"
                        ::= { fkBridgeBaseControl 3 }

                
--  1.3.6.1.4.1.10428 9 1.9.8.1.2.5
                -- 1.3.6.1.4.1.10428 9 1.101.3.1.2.4
                fkBridgeControlTimeStamp OBJECT-TYPE
                        SYNTAX TimeTicks
                        MAX-ACCESS read-only
                        STATUS current
                        DESCRIPTION
                                " The time stamp of the last command(end of command)"
                        ::= { fkBridgeBaseControl 4 }

                
--  1.3.6.1.4.1.10428 9 1.9.8.1.2.4
                -- 1.3.6.1.4.1.10428 9 1.101.3.1.2.5
                fkBridgeControlReqResult OBJECT-TYPE
                        SYNTAX FkControlRequestResultType
                        MAX-ACCESS read-only
                        STATUS current
                        DESCRIPTION
                                "The result of the last user command"
                        ::= { fkBridgeBaseControl 5 }

                
--  1.3.6.1.4.1.10428 9 1.9.8.1.2.6
                -- 1.3.6.1.4.1.10428 9 1.101.3.1.2.6
                fkBridgeControlLacpActivity OBJECT-TYPE
                        SYNTAX INTEGER
                                {
                                disabled(0),
                                enabled(1)
                                }
                        MAX-ACCESS read-write
                        STATUS current
                        DESCRIPTION
                                " The LACP enabled/disabled status of the switch"
                        ::= { fkBridgeBaseControl 6 }

                
--  1.3.6.1.4.1.10428 9 1.9.8.1.2.7
                -- 1.3.6.1.4.1.10428 9 1.101.3.1.2.7
                fkBridgeControlLacpPriority OBJECT-TYPE
                        SYNTAX INTEGER (1..65535)
                        MAX-ACCESS read-write
                        STATUS current
                        DESCRIPTION
                                " The priority assigned to the Actor System"
                        ::= { fkBridgeBaseControl 7 }

                
--  1.3.6.1.4.1.10428 9 1.9.8.1.2.8
                -- 1.3.6.1.4.1.10428 9 1.101.3.1.2.8
                fkBridgeControlDoubleTagProtoId OBJECT-TYPE
                        SYNTAX Integer32
                        MAX-ACCESS read-write
                        STATUS current
                        DESCRIPTION
                                " programmable Double Tag Protocol Identifier.
                                It means outerTPID.
                                "
                        ::= { fkBridgeBaseControl 8 }

                
--  1.3.6.1.4.1.10428 9 1.9.8.1.2.18
                -- 1.3.6.1.4.1.10428 9 1.101.3.1.2.9
                fkBridgeControlMirrorMode OBJECT-TYPE
                        SYNTAX INTEGER
                                {
                                disabled(0),
                                enabled(1)
                                }
                        MAX-ACCESS read-write
                        STATUS current
                        DESCRIPTION
                                " Mirror mode of bridge"
                        ::= { fkBridgeBaseControl 9 }

                
--  1.3.6.1.4.1.10428 9 1.9.8.1.2.19
                -- 1.3.6.1.4.1.10428 9 1.101.3.1.2.10
                fkBridgeControlMirrorMonitorPortId OBJECT-TYPE
                        SYNTAX INTEGER (1..255)
                        MAX-ACCESS read-write
                        STATUS current
                        DESCRIPTION
                                "Mirroring port ID
                                1-254: physical port ID
                                255: mirror to cpu"
                        ::= { fkBridgeBaseControl 10 }

                
                -- 1.3.6.1.4.1.10428 9 1.101.3.1.2.11
                fkBridgeControlMaxLearnPerUnit OBJECT-TYPE
                        SYNTAX INTEGER (-1..2147483647)
                        MAX-ACCESS read-write
                        STATUS current
                        DESCRIPTION
                                "Limit maximum number of MAC addresses learning 
                                newly per unit time(one second) on a bridge.
                                (0: nothing learned, -l: unlimited.)"
                        ::= { fkBridgeBaseControl 11 }

                
--  1.3.6.1.4.1.10428 9 1.9.8.1.2.20
                -- 1.3.6.1.4.1.10428 9 1.101.3.1.2.12
                fkBridgeControlFdbAgeingTime OBJECT-TYPE
                        SYNTAX Unsigned32 (10..21474830)
                        MAX-ACCESS read-write
                        STATUS current
                        DESCRIPTION
                                "The timeout period in seconds for aging out
                                dynamically learned forwarding information."
                        DEFVAL { 300 }
                        ::= { fkBridgeBaseControl 12 }

                
--  1.3.6.1.4.1.10428 9 1.9.8.1.2.21
                -- 1.3.6.1.4.1.10428 9 1.101.3.1.2.13
                fkBridgeControlStackMode OBJECT-TYPE
                        SYNTAX INTEGER
                                {
                                disable(0),
                                master(1),
                                slave(2)
                                }
                        MAX-ACCESS read-write
                        STATUS current
                        DESCRIPTION
                                "Stack status of device."
                        ::= { fkBridgeBaseControl 13 }

                
--  1.3.6.1.4.1.10428 9 1.9.8.1.2.22
                -- 1.3.6.1.4.1.10428 9 1.101.3.1.2.14
                fkBridgeControlStackDeviceName OBJECT-TYPE
                        SYNTAX OCTET STRING (SIZE (0..8))
                        MAX-ACCESS read-write
                        STATUS current
                        DESCRIPTION
                                "Device name of stack device."
                        ::= { fkBridgeBaseControl 14 }

                
--  1.3.6.1.4.1.10428 9 1.9.8.1.2.23
                -- 1.3.6.1.4.1.10428 9 1.101.3.1.2.15
                fkBridgeControlLldpMessageTxInterval OBJECT-TYPE
                        SYNTAX INTEGER (5..32767)
                        MAX-ACCESS read-write
                        STATUS current
                        DESCRIPTION
                                " The interval at which LLDP frames are transmitted on behalf of this LLDP agent."
                        ::= { fkBridgeBaseControl 15 }

                
--  1.3.6.1.4.1.10428 9 1.9.8.1.2.24
                -- 1.3.6.1.4.1.10428 9 1.101.3.1.2.16
                fkBridgeControlLldpTxHoldMultiplier OBJECT-TYPE
                        SYNTAX INTEGER (2..10)
                        MAX-ACCESS read-write
                        STATUS current
                        DESCRIPTION
                                "The time-to-live value expressed as a multiple of the fkBridgeLldpMessageTxInterval object."
                        ::= { fkBridgeBaseControl 16 }

                
--  1.3.6.1.4.1.10428 9 1.9.8.1.2.25
                -- 1.3.6.1.4.1.10428 9 1.101.3.1.2.17
                fkBridgeControlLldpReinitDelay OBJECT-TYPE
                        SYNTAX INTEGER (1..10)
                        MAX-ACCESS read-write
                        STATUS current
                        DESCRIPTION
                                " Delay (in units of seconds) from when lldpPortConfigAdminStatus object of a particular port  becomes 'disabled' until re-initialization will be attempted."
                        ::= { fkBridgeBaseControl 17 }

                
--  1.3.6.1.4.1.10428 9 1.9.8.1.2.26
                -- 1.3.6.1.4.1.10428 9 1.101.3.1.2.18
                fkBridgeControlLldpTxDelay OBJECT-TYPE
                        SYNTAX INTEGER (1..8192)
                        MAX-ACCESS read-write
                        STATUS current
                        DESCRIPTION
                                "Delay (in units of seconds) between successive LLDP frame transmissions initiated by value/status changes in the LLDP local systems MIB."
                        ::= { fkBridgeBaseControl 18 }

                
--  1.3.6.1.4.1.10428 9 1.9.8.1.2.27
                -- 1.3.6.1.4.1.10428 9 1.101.3.1.2.19
                fkBridgeControlLldpNotificationInterval OBJECT-TYPE
                        SYNTAX INTEGER (5..3600)
                        MAX-ACCESS read-write
                        STATUS current
                        DESCRIPTION
                                " The agent must not generate more than one lldpRemTablesChangenotification-event in the indicated period."
                        ::= { fkBridgeBaseControl 19 }

                
--  1.3.6.1.4.1.10428 9 1.9.8.1.2.29
                -- 1.3.6.1.4.1.10428 9 1.101.3.1.2.20
                fkBridgeControlStpActivity OBJECT-TYPE
                        SYNTAX INTEGER
                                {
                                disabled(0),
                                enabled(1)
                                }
                        MAX-ACCESS read-write
                        STATUS current
                        DESCRIPTION
                                " The STP enabled/disabled status of the switch."
                        ::= { fkBridgeBaseControl 20 }

                
                -- 1.3.6.1.4.1.10428 9 1.101.3.1.2.21
                fkBridgeControlStpSelfLoop OBJECT-TYPE
                        SYNTAX INTEGER
                                {
                                disable(0),
                                enable(1)
                                }
                        MAX-ACCESS read-write
                        STATUS current
                        DESCRIPTION
                                "The STP self loop
                                0: disabled
                                1: enabled"
                        ::= { fkBridgeBaseControl 21 }

                
                -- 1.3.6.1.4.1.10428 9 1.101.3.1.2.22
                fkBridgeControlTcpSyncookie OBJECT-TYPE
                        SYNTAX INTEGER
                                {
                                disable(0),
                                enable(1)
                                }
                        MAX-ACCESS read-write
                        STATUS current
                        DESCRIPTION
                                "The value permits only when transmitted cookies are returned after sending cookies with SYN"
                        ::= { fkBridgeBaseControl 22 }

                
                -- 1.3.6.1.4.1.10428 9 1.101.3.1.2.23
                fkBridgeControlTcpIgnoreRstUnknown OBJECT-TYPE
                        SYNTAX INTEGER
                                {
                                disable(0),
                                enable(1)
                                }
                        MAX-ACCESS read-write
                        STATUS current
                        DESCRIPTION
                                "The value configures not to send the message that informs TCP connection cannot be done."
                        ::= { fkBridgeBaseControl 23 }

                
                -- 1.3.6.1.4.1.10428 9 1.101.3.1.2.24
                fkBridgeControlAutoInterfaceActivation OBJECT-TYPE
                        SYNTAX INTEGER
                                {
                                enable(1),
                                disable(2)
                                }
                        MAX-ACCESS read-write
                        STATUS current
                        DESCRIPTION
                                "The value configures auto Interface activation.
                                (supported only model 5924N)"
                        ::= { fkBridgeBaseControl 24 }

                
                -- 1.3.6.1.4.1.10428 9 1.101.3.1.2.25
                fkBridgeControlLoopDetectStatus OBJECT-TYPE
                        SYNTAX INTEGER
                                {
                                enable(1),
                                disable(2)
                                }
                        MAX-ACCESS read-write
                        STATUS current
                        DESCRIPTION
                                "The global adminStatus of Loop-Detect."
                        ::= { fkBridgeBaseControl 25 }

                
                -- 1.3.6.1.4.1.10428 9 1.101.3.1.2.26
                fkBridgeControlLoopDetectPacketType OBJECT-TYPE
                        SYNTAX INTEGER
                                {
                                laa(1),
                                system(2)
                                }
                        MAX-ACCESS read-write
                        STATUS current
                        DESCRIPTION
                                "The type of srcmac to be detected.
                                1.laa : Locally Administered Address
                                2.system : System MAC (default)"
                        ::= { fkBridgeBaseControl 26 }

                
                -- 1.3.6.1.4.1.10428 9 1.101.3.1.2.27
                fkBridgeControlPvlanPromSelectMode OBJECT-TYPE
                        SYNTAX INTEGER
                                {
                                normal(0),
                                manual(1),
                                stp(2),
                                erp(3)
                                }
                        MAX-ACCESS read-write
                        STATUS current
                        DESCRIPTION
                                "The value is used to indicate promiscuous ports selection mode:
                                normal ?default
                                manual ? by user
                                stp ? by STP (not supported)
                                erp ? by ERP"
                        ::= { fkBridgeBaseControl 27 }

                
                -- 1.3.6.1.4.1.10428 9 1.101.3.1.2.28
                fkBridgeControlPvlanPromiscuousPorts OBJECT-TYPE
                        SYNTAX OCTET STRING
                        MAX-ACCESS read-write
                        STATUS current
                        DESCRIPTION
                                "Valid if only if fkBridgeControlPvlanPromSelectMode is not manual.
                                If fkBridgePvlanOnePromPortEnable is enabled, then it can only indicate one port or none."
                        ::= { fkBridgeBaseControl 28 }

                
                -- 1.3.6.1.4.1.10428 9 1.101.3.1.2.29
                fkBridgeControlInnerTagProtoId OBJECT-TYPE
                        SYNTAX INTEGER
                                {
                                dtag8100(33024),
                                dtag9100(37120)
                                }
                        MAX-ACCESS read-write
                        STATUS current
                        DESCRIPTION
                                "programmable Inner Double Tag Protocol Identifier. It means innerTPID."
                        ::= { fkBridgeBaseControl 29 }

                
                -- 1.3.6.1.4.1.10428 9 1.101.3.1.2.30
                fkBridgeControlUnknownMcastBlockAllPorts OBJECT-TYPE
                        SYNTAX INTEGER
                                {
                                enable(1),
                                disable(2)
                                }
                        MAX-ACCESS read-write
                        STATUS current
                        DESCRIPTION
                                "Unknown multicast block setting for all ports."
                        ::= { fkBridgeBaseControl 30 }

                
                -- 1.3.6.1.4.1.10428 9 1.101.3.1.2.31
                fkBridgeControlEcmpHashType OBJECT-TYPE
                        SYNTAX INTEGER
                                {
                                sip(1),
                                sipDip(2)
                                }
                        MAX-ACCESS read-write
                        STATUS current
                        DESCRIPTION
                                "ECMP Hash Type
                                "
                        ::= { fkBridgeBaseControl 31 }

                
                -- 1.3.6.1.4.1.10428 9 1.101.3.1.2.32
                fkBridgeControlTcpSynguard OBJECT-TYPE
                        SYNTAX Integer32 (0..2147483647)
                        MAX-ACCESS read-write
                        STATUS current
                        DESCRIPTION
                                "The tcp-synguard bandwidth."
                        ::= { fkBridgeBaseControl 32 }

                
                -- 1.3.6.1.4.1.10428 9 1.101.3.1.2.33
                fkBridgeControlOuterTagProtoId OBJECT-TYPE
                        SYNTAX INTEGER
                                {
                                dtag8100(33024),
                                dtag9100(37120)
                                }
                        MAX-ACCESS read-write
                        STATUS current
                        DESCRIPTION
                                "programmable outer Double Tag Protocol Identifier.
                                  It means OutTPID"
                        ::= { fkBridgeBaseControl 33 }

                
                -- 1.3.6.1.4.1.10428 9 1.101.3.1.2.34
                fkBridgeControlMacAntiSpoofing OBJECT-TYPE
                        SYNTAX INTEGER
                                {
                                enable(1),
                                disable(2)
                                }
                        MAX-ACCESS read-write
                        STATUS current
                        DESCRIPTION
                                "The protect uplink mac address
                                2011/01/20 V5924CR supports."
                        ::= { fkBridgeBaseControl 34 }

                
                -- 1.3.6.1.4.1.10428 9 1.101.3.1.2.35
                fkBridgeControlMacReplace OBJECT-TYPE
                        SYNTAX INTEGER
                                {
                                enable(1),
                                disable(2)
                                }
                        MAX-ACCESS read-write
                        STATUS current
                        DESCRIPTION
                                "The mac address replace mode
                                2011/01/20 V5924CR supports."
                        ::= { fkBridgeBaseControl 35 }

                
                -- 1.3.6.1.4.1.10428 9 1.101.3.1.2.36
                fkBridgeControlStormControlBcast OBJECT-TYPE
                        SYNTAX INTEGER (0 | 1..65535)
                        MAX-ACCESS read-write
                        STATUS current
                        DESCRIPTION
                                "The Storm Control Broadcast Configuration
                                0: disable bcast
                                "
                        ::= { fkBridgeBaseControl 36 }

                
                -- 1.3.6.1.4.1.10428 9 1.101.3.1.2.37
                fkBridgeControlStormControlDLF OBJECT-TYPE
                        SYNTAX INTEGER (0 | 1..65535)
                        MAX-ACCESS read-write
                        STATUS current
                        DESCRIPTION
                                "The Storm Control DLF Configuration
                                0: disable DLF
                                "
                        ::= { fkBridgeBaseControl 37 }

                
                -- 1.3.6.1.4.1.10428 9 1.101.3.1.2.38
                fkBridgeControlStormControlMulticast OBJECT-TYPE
                        SYNTAX INTEGER (0 | 1..65535)
                        MAX-ACCESS read-only
                        STATUS current
                        DESCRIPTION
                                "The Storm Control Multicast Configuration
                                0: disable multicast
                                "
                        ::= { fkBridgeBaseControl 38 }

                
                -- 1.3.6.1.4.1.10428 9 1.101.3.1.2.39
                fkBridgeControlMacLearningMode OBJECT-TYPE
                        SYNTAX INTEGER
                                {
                                cml(1),
                                sml(2),
                                cmlsml(3)
                                }
                        MAX-ACCESS read-write
                        STATUS current
                        DESCRIPTION
                                "The MAC Learning Mode.
                                1: cml
                                2: sml
                                3: cmlsml"
                        ::= { fkBridgeBaseControl 39 }

                
                -- 1.3.6.1.4.1.10428 9 1.101.3.1.2.40
                fkBridgeControlLagGlobalDistMode OBJECT-TYPE
                        SYNTAX INTEGER
                                {
                                none(0),
                                srcmac(1),
                                dstmac(2),
                                srcdstmac(3),
                                srcip(4),
                                dstip(5),
                                srcdstip(6),
                                srcdstl4(7),
                                label(8)
                                }
                        MAX-ACCESS read-write
                        STATUS current
                        DESCRIPTION
                                "The LAG global distmode."
                        ::= { fkBridgeBaseControl 40 }

                
                -- 1.3.6.1.4.1.10428 9 1.101.3.1.2.41
                fkBridgeControlMultiPortLlcfPortA OBJECT-TYPE
                        SYNTAX OCTET STRING
                        MAX-ACCESS read-write
                        STATUS current
                        DESCRIPTION
                                "The Multi port LLCF - RAPS East/West Port."
                        ::= { fkBridgeBaseControl 41 }

                
                -- 1.3.6.1.4.1.10428 9 1.101.3.1.2.42
                fkBridgeControlMultiPortLlcfPortB OBJECT-TYPE
                        SYNTAX OCTET STRING
                        MAX-ACCESS read-write
                        STATUS current
                        DESCRIPTION
                                "The Multi port LLCF - RAPS East/West Port."
                        ::= { fkBridgeBaseControl 42 }

                
                -- 1.3.6.1.4.1.10428 9 1.101.3.1.2.43
                fkBridgeControlMultiPortLlcfPortC OBJECT-TYPE
                        SYNTAX OCTET STRING
                        MAX-ACCESS read-write
                        STATUS current
                        DESCRIPTION
                                "The Multi port LLCF - force down ports"
                        ::= { fkBridgeBaseControl 43 }

                
                -- 1.3.6.1.4.1.10428 9 1.101.3.1.2.44
                fkBridgeControlMultiPortLlcfTimer OBJECT-TYPE
                        SYNTAX Integer32 (-1 | 1000..10000)
                        MAX-ACCESS read-write
                        STATUS current
                        DESCRIPTION
                                "The LLCF's checking interval. 1000~10000ms (default:2500ms)
                                clear set value is -1."
                        ::= { fkBridgeBaseControl 44 }

                
--  1.3.6.1.4.1.10428 9 1.9.8.1.4
                -- 1.3.6.1.4.1.10428 9 1.101.3.1.3
                fkBridgeBaseNotification OBJECT IDENTIFIER ::= { fkBridgeBase 3 }

                
--  1.3.6.1.4.1.10428 9 1.9.8.1.4.1
                -- 1.3.6.1.4.1.10428 9 1.101.3.1.3.1
                fkBridgeLacpProfileChanged NOTIFICATION-TYPE
                        OBJECTS { fkBridgeLacpActivity, fkBridgeLacpPriority, fkBridgeControlRequest, fkBridgeControlTimeStamp, fkBridgeControlReqResult
                                 }
                        STATUS current
                        DESCRIPTION 
                                " "
                        ::= { fkBridgeBaseNotification 1 }

                
--  1.3.6.1.4.1.10428 9 1.9.8.1.4.2
                -- 1.3.6.1.4.1.10428 9 1.101.3.1.3.2
                fkBridgeDoubleTagProtoIdChanged NOTIFICATION-TYPE
                        OBJECTS { fkBridgeDoubleTagProtoId, fkBridgeControlRequest, fkBridgeControlTimeStamp, fkBridgeControlReqResult }
                        STATUS current
                        DESCRIPTION 
                                " "
                        ::= { fkBridgeBaseNotification 2 }

                
--  1.3.6.1.4.1.10428 9 1.9.8.1.4.5
                -- 1.3.6.1.4.1.10428 9 1.101.3.1.3.3
                fkBridgeMirrorProfileChanged NOTIFICATION-TYPE
                        OBJECTS { fkBridgeMirrorMode, fkBridgeMirrorMonitorPortId, fkBridgeControlRequest, fkBridgeControlTimeStamp, fkBridgeControlReqResult
                                 }
                        STATUS current
                        DESCRIPTION 
                                " "
                        ::= { fkBridgeBaseNotification 3 }

                
                -- 1.3.6.1.4.1.10428 9 1.101.3.1.3.4
                fkBridgeMaxLearnPerUnitChanged NOTIFICATION-TYPE
                        OBJECTS { fkBridgeControlRequest, fkBridgeControlTimeStamp, fkBridgeControlReqResult, fkBridgeMaxLearnPerUnit }
                        STATUS current
                        DESCRIPTION 
                                "Description."
                        ::= { fkBridgeBaseNotification 4 }

                
--  1.3.6.1.4.1.10428 9 1.9.8.1.4.6
                -- 1.3.6.1.4.1.10428 9 1.101.3.1.3.5
                fkBridgeFdbAgeingTimeChanged NOTIFICATION-TYPE
                        OBJECTS { fkBridgeFdbAgeingTime, fkBridgeControlRequest, fkBridgeControlTimeStamp, fkBridgeControlReqResult }
                        STATUS current
                        DESCRIPTION 
                                "Changed Fdb ageding time."
                        ::= { fkBridgeBaseNotification 5 }

                
--  1.3.6.1.4.1.10428 9 1.9.8.1.4.7
                -- 1.3.6.1.4.1.10428 9 1.101.3.1.3.6
                fkBridgeStackProfileChanged NOTIFICATION-TYPE
                        OBJECTS { fkBridgeStackMode, fkBridgeStackDeviceName, fkBridgeControlRequest, fkBridgeControlTimeStamp, fkBridgeControlReqResult
                                 }
                        STATUS current
                        DESCRIPTION 
                                "Changed Stack device's profile."
                        ::= { fkBridgeBaseNotification 6 }

                
--  1.3.6.1.4.1.10428 9 1.9.8.1.4.8
                -- 1.3.6.1.4.1.10428 9 1.101.3.1.3.7
                fkBridgeLldpProfileChanged NOTIFICATION-TYPE
                        OBJECTS { fkBridgeLldpMessageTxInterval, fkBridgeLldpTxHoldMultiplier, fkBridgeLldpReinitDelay, fkBridgeLldpTxDelay, fkBridgeLldpNotificationInterval, 
                                fkBridgeControlRequest, fkBridgeControlTimeStamp, fkBridgeControlReqResult }
                        STATUS current
                        DESCRIPTION 
                                " "
                        ::= { fkBridgeBaseNotification 7 }

                
--  1.3.6.1.4.1.10428 9 1.9.8.1.4.9
                -- 1.3.6.1.4.1.10428 9 1.101.3.1.3.8
                fkBridgeStpProfileChanged NOTIFICATION-TYPE
                        OBJECTS { fkBridgeControlRequest, fkBridgeControlReqResult, fkBridgeControlTimeStamp, fkBridgeStpActivity, fkBridgeStpSelfLoop
                                 }
                        STATUS current
                        DESCRIPTION 
                                " "
                        ::= { fkBridgeBaseNotification 8 }

                
                -- 1.3.6.1.4.1.10428 9 1.101.3.1.3.9
                fkBridgeTcpSyncookieChanged NOTIFICATION-TYPE
                        OBJECTS { fkBridgeControlRequest, fkBridgeControlTimeStamp, fkBridgeControlReqResult, fkBridgeTcpSyncookie }
                        STATUS current
                        DESCRIPTION 
                                "Description."
                        ::= { fkBridgeBaseNotification 9 }

                
                -- 1.3.6.1.4.1.10428 9 1.101.3.1.3.10
                fkBridgeTcpIgnoreRstUnknownChanged NOTIFICATION-TYPE
                        OBJECTS { fkBridgeControlRequest, fkBridgeControlTimeStamp, fkBridgeControlReqResult, fkBridgeTcpIgnoreRstUnknown }
                        STATUS current
                        DESCRIPTION 
                                "Description."
                        ::= { fkBridgeBaseNotification 10 }

                
                -- 1.3.6.1.4.1.10428 9 1.101.3.1.3.11
                fkBridgeAutoInterfaceActivationChanged NOTIFICATION-TYPE
                        OBJECTS { fkBridgeControlRequest, fkBridgeControlTimeStamp, fkBridgeControlReqResult, fkBridgeAutoInterfaceActivation }
                        STATUS current
                        DESCRIPTION 
                                "Description."
                        ::= { fkBridgeBaseNotification 11 }

                
                -- 1.3.6.1.4.1.10428 9 1.101.3.1.3.12
                fkBridgeLoopDetectProfileChanged NOTIFICATION-TYPE
                        OBJECTS { fkBridgeControlRequest, fkBridgeControlTimeStamp, fkBridgeControlReqResult, fkBridgeLoopDetectStatus, fkBridgeLoopDetectPacketType
                                 }
                        STATUS current
                        DESCRIPTION 
                                "Description."
                        ::= { fkBridgeBaseNotification 12 }

                
                -- 1.3.6.1.4.1.10428 9 1.101.3.1.3.13
                fkBridgePvlanPormSelectModeChanged NOTIFICATION-TYPE
                        OBJECTS { fkBridgeControlRequest, fkBridgeControlTimeStamp, fkBridgeControlReqResult, fkBridgeControlPvlanPromSelectMode, fkBridgeControlPvlanPromiscuousPorts
                                 }
                        STATUS current
                        DESCRIPTION 
                                "Description."
                        ::= { fkBridgeBaseNotification 13 }

                
                -- 1.3.6.1.4.1.10428 9 1.101.3.1.3.14
                fkBridgeInnerTagProtoIdChanged NOTIFICATION-TYPE
                        OBJECTS { fkBridgeControlRequest, fkBridgeControlTimeStamp, fkBridgeControlReqResult, fkBridgeControlInnerTagProtoId }
                        STATUS current
                        DESCRIPTION 
                                "Description."
                        ::= { fkBridgeBaseNotification 14 }

                
                -- 1.3.6.1.4.1.10428 9 1.101.3.1.3.15
                fkBridgeUnknownMcastBlockAllPortsChanged NOTIFICATION-TYPE
                        OBJECTS { fkBridgeControlRequest, fkBridgeControlTimeStamp, fkBridgeControlReqResult, fkBridgeControlUnknownMcastBlockAllPorts }
                        STATUS current
                        DESCRIPTION 
                                "Description."
                        ::= { fkBridgeBaseNotification 15 }

                
                -- 1.3.6.1.4.1.10428 9 1.101.3.1.3.16
                fkBridgeEcmpHashTypeChanged NOTIFICATION-TYPE
                        OBJECTS { fkBridgeControlRequest, fkBridgeControlTimeStamp, fkBridgeControlReqResult, fkBridgeControlEcmpHashType }
                        STATUS current
                        DESCRIPTION 
                                "Description."
                        ::= { fkBridgeBaseNotification 16 }

                
                -- 1.3.6.1.4.1.10428 9 1.101.3.1.3.17
                fkBridgeTcpSynguardChanged NOTIFICATION-TYPE
                        OBJECTS { fkBridgeTcpSynguard, fkBridgeControlRequest, fkBridgeControlTimeStamp, fkBridgeControlReqResult }
                        STATUS current
                        DESCRIPTION 
                                "Description."
                        ::= { fkBridgeBaseNotification 17 }

                
                -- 1.3.6.1.4.1.10428 9 1.101.3.1.3.18
                fkBridgeOuterTagProtoIdChanged NOTIFICATION-TYPE
                        OBJECTS { fkBridgeControlRequest, fkBridgeControlTimeStamp, fkBridgeControlReqResult, fkBridgeControlOuterTagProtoId }
                        STATUS current
                        DESCRIPTION 
                                "fkBridgeControlOuterTagProtoId"
                        ::= { fkBridgeBaseNotification 18 }

                
                -- 1.3.6.1.4.1.10428 9 1.101.3.1.3.19
                fkBridgeMacAntiSpoofingChanged NOTIFICATION-TYPE
                        OBJECTS { fkBridgeControlRequest, fkBridgeControlTimeStamp, fkBridgeControlReqResult, fkBridgeControlMacAntiSpoofing }
                        STATUS current
                        DESCRIPTION 
                                "Description."
                        ::= { fkBridgeBaseNotification 19 }

                
                -- 1.3.6.1.4.1.10428 9 1.101.3.1.3.20
                fkBridgeMacReplaceChanged NOTIFICATION-TYPE
                        OBJECTS { fkBridgeControlRequest, fkBridgeControlTimeStamp, fkBridgeControlReqResult, fkBridgeControlMacReplace }
                        STATUS current
                        DESCRIPTION 
                                "Description."
                        ::= { fkBridgeBaseNotification 20 }

                
                -- 1.3.6.1.4.1.10428 9 1.101.3.1.3.21
                fkBridgeStormControlChanged NOTIFICATION-TYPE
                        OBJECTS { fkBridgeControlRequest, fkBridgeControlTimeStamp, fkBridgeControlReqResult, fkBridgePortNum, fkBridgeControlStormControlBcast, 
                                fkBridgeControlStormControlDLF, fkBridgeControlStormControlMulticast }
                        STATUS current
                        DESCRIPTION 
                                "Description."
                        ::= { fkBridgeBaseNotification 21 }

                
                -- 1.3.6.1.4.1.10428 9 1.101.3.1.3.22
                fkBridgeMacLearningModeChanged NOTIFICATION-TYPE
                        OBJECTS { fkBridgeControlRequest, fkBridgeControlTimeStamp, fkBridgeControlReqResult, fkBridgeControlMacLearningMode }
                        STATUS current
                        DESCRIPTION 
                                "Description."
                        ::= { fkBridgeBaseNotification 22 }

                
                -- 1.3.6.1.4.1.10428 9 1.101.3.1.3.23
                fkBridgeLagGlobalDistModeChanged NOTIFICATION-TYPE
                        OBJECTS { fkBridgeControlRequest, fkBridgeControlTimeStamp, fkBridgeControlReqResult, fkBridgeControlLagGlobalDistMode }
                        STATUS current
                        DESCRIPTION 
                                "setLagGlobalDistMode"
                        ::= { fkBridgeBaseNotification 23 }

                
                -- 1.3.6.1.4.1.10428 9 1.101.3.1.3.24
                fkBridgeMultiPortLlcfChanged NOTIFICATION-TYPE
                        OBJECTS { fkBridgeControlRequest, fkBridgeControlTimeStamp, fkBridgeControlReqResult, fkBridgeControlMultiPortLlcfPortA, fkBridgeControlMultiPortLlcfPortB, 
                                fkBridgeControlMultiPortLlcfPortC }
                        STATUS current
                        DESCRIPTION 
                                "setMultiPortLlcf "
                        ::= { fkBridgeBaseNotification 24 }

                
                -- 1.3.6.1.4.1.10428 9 1.101.3.1.3.25
                fkBridgeMultiPortLlcfDeleted NOTIFICATION-TYPE
                        OBJECTS { fkBridgeControlRequest, fkBridgeControlTimeStamp, fkBridgeControlReqResult }
                        STATUS current
                        DESCRIPTION 
                                "delMultiPortLlcf "
                        ::= { fkBridgeBaseNotification 25 }

                
                -- 1.3.6.1.4.1.10428 9 1.101.3.1.3.26
                fkBridgeMultiPortLlcfTimerChanged NOTIFICATION-TYPE
                        OBJECTS { fkBridgeControlRequest, fkBridgeControlTimeStamp, fkBridgeControlReqResult, fkBridgeControlMultiPortLlcfTimer }
                        STATUS current
                        DESCRIPTION 
                                "setMultiPortLlcfTimer "
                        ::= { fkBridgeBaseNotification 26 }

                
--                      ::= { fk 4 }
-- 
-- Node definitions
-- 
-- 1.3.6.1.4.1.10428 9 1.9.8.2
                -- 1.3.6.1.4.1.10428 9 1.101.3.2
                fkBridgePort OBJECT IDENTIFIER ::= { fkBridge 2 }

                
--  1.3.6.1.4.1.10428 9 1.9.8.2.1
                -- 1.3.6.1.4.1.10428 9 1.101.3.2.1
                fkBridgePortTable OBJECT-TYPE
                        SYNTAX SEQUENCE OF FkBridgePortEntry
                        MAX-ACCESS not-accessible
                        STATUS current
                        DESCRIPTION
                                "Bridge Port Table"
                        ::= { fkBridgePort 1 }

                
--  1.3.6.1.4.1.10428 9 1.9.8.2.1.1
                -- 1.3.6.1.4.1.10428 9 1.101.3.2.1.1
                fkBridgePortEntry OBJECT-TYPE
                        SYNTAX FkBridgePortEntry
                        MAX-ACCESS not-accessible
                        STATUS current
                        DESCRIPTION
                                "Bridge Port Entry
                                key: fkBridgePortIndex"
                        INDEX { fkBridgePortIndex }
                        ::= { fkBridgePortTable 1 }

                
                FkBridgePortEntry ::=
                        SEQUENCE { 
                                fkBridgePortIndex
                                        INTEGER,
                                fkBridgePortIfIndex
                                        INTEGER,
                                fkBridgePortPVid
                                        INTEGER,
                                fkBridgePortMaxHosts
                                        INTEGER,
                                fkBridgePortCurrentHosts
                                        INTEGER,
                                fkBridgePortMaxLearnPerUnit
                                        INTEGER,
                                fkBridgePortMACFilterPermission
                                        INTEGER,
                                fkBridgePortIngMirrorStatus
                                        INTEGER,
                                fkBridgePortEgMirrorStatus
                                        INTEGER,
                                fkBridgePortBcastThreshold
                                        INTEGER,
                                fkBridgePortMcastThreshold
                                        INTEGER,
                                fkBridgePortDlfThreshold
                                        INTEGER,
                                fkBridgePortQinQStatus
                                        INTEGER,
                                fkBridgePortAdminLinktype
                                        INTEGER,
                                fkBridgePortAdminEdgemode
                                        INTEGER,
                                fkBridgePortOperLinktype
                                        INTEGER,
                                fkBridgePortOperEdgemode
                                        INTEGER,
                                fkBridgePortStpBpduFilter
                                        INTEGER,
                                fkBridgePortPvlanIsolatedStatus
                                        INTEGER,
                                fkBridgePortPvlanPromPorts
                                        OCTET STRING,
                                fkBridgePortDhcpFilterServer
                                        INTEGER,
                                fkBridgePortLoopDetectStatus
                                        INTEGER,
                                fkBridgePortLoopDetectBlock
                                        INTEGER,
                                fkBridgePortLoopDetectPeriod
                                        INTEGER,
                                fkBridgePortLoopDetectTimer
                                        INTEGER,
                                fkBridgePortLoopDetectBlockStatus
                                        INTEGER,
                                fkBridgePortNetBIOSFilter
                                        INTEGER,
                                fkBridgePortPushInnertag
                                        INTEGER,
                                fkBridgePortPopInnertag
                                        INTEGER,
                                fkBridgePortInnertag
                                        INTEGER,
                                fkBridgePortPriority
                                        INTEGER,
                                fkBridgePortInner2outerPri
                                        INTEGER,
                                fkBridgePortInner2outerVid
                                        INTEGER,
                                fkBridgePortLinkUpCnt
                                        INTEGER,
                                fkBridgePortLinkDownCnt
                                        INTEGER,
                                fkBridgePortLinkUpTime
                                        Counter64,
                                fkBridgePortElapsedTimeAfterClearStats
                                        Counter64,
                                fkBridgePortMACLearningStatus
                                        INTEGER,
                                fkBridgePortPortBridgeStatus
                                        INTEGER,
                                fkBridgePortUnknownMcastBlock
                                        INTEGER,
                                fkBridgePortDescription
                                        OCTET STRING,
                                fkBridgePortHoldTime
                                        Integer32,
                                fkBridgePortMacAntiSpoofing
                                        TruthValue,
                                fkBridgePortSwitchType
                                        INTEGER,
                                fkBridgePortSwitchState
                                        INTEGER,
                                fkBridgePortSwitchMode
                                        INTEGER,
                                fkBridgePortSwitchSubMode
                                        INTEGER,
                                fkBridgePortSwitchDefaultVlan
                                        Integer32,
                                fkBridgePortSwitchIngressFilter
                                        INTEGER,
                                fkBridgePortSwitchAccFrameType
                                        BITS,
                                fkBridgePortSwitchNativeVid
                                        Integer32,
                                fkBridgePortSwitchAllowedVlan
                                        OCTET STRING,
                                fkBridgePortSwitchAllowedVlanEtag
                                        OCTET STRING,
                                fkBridgePortSwitchChannelType
                                        INTEGER,
                                fkBridgePortSwitchStaticChannelGroup
                                        OCTET STRING,
                                fkBridgePortSwitchChannelLoadbalance
                                        INTEGER
                         }

--  1.3.6.1.4.1.10428 9 1.9.8.2.1.1.1
                -- 1.3.6.1.4.1.10428 9 1.101.3.2.1.1.1
                fkBridgePortIndex OBJECT-TYPE
                        SYNTAX INTEGER (1..65535)
                        MAX-ACCESS read-only
                        STATUS current
                        DESCRIPTION
                                "Same as ifIndex (for all ifTable entries),
                                additionally aggregation group index values available."
                        ::= { fkBridgePortEntry 1 }

                
--  1.3.6.1.4.1.10428 9 1.9.8.2.1.1.1
                -- 1.3.6.1.4.1.10428 9 1.101.3.2.1.1.2
                fkBridgePortIfIndex OBJECT-TYPE
                        SYNTAX INTEGER (1..4094)
                        MAX-ACCESS read-only
                        STATUS current
                        DESCRIPTION
                                "Bridge Interface Index."
                        ::= { fkBridgePortEntry 2 }

                
--  1.3.6.1.4.1.10428 9 1.9.8.2.1.1.2
                -- 1.3.6.1.4.1.10428 9 1.101.3.2.1.1.3
                fkBridgePortPVid OBJECT-TYPE
                        SYNTAX INTEGER (1..4094)
                        MAX-ACCESS read-only
                        STATUS current
                        DESCRIPTION
                                "The PVID of port. 
                                Taken if no other rule given for VLAN association. 
                                If aggregated: only for group."
                        ::= { fkBridgePortEntry 3 }

                
--  1.3.6.1.4.1.10428 9 1.9.8.2.1.1.3
                -- 1.3.6.1.4.1.10428 9 1.101.3.2.1.1.4
                fkBridgePortMaxHosts OBJECT-TYPE
                        SYNTAX INTEGER (0..2147483647)
                        MAX-ACCESS read-only
                        STATUS current
                        DESCRIPTION
                                "The maximum number of hosts allowed. 
                                Aggregation group available. Value 0 is allowed. 
                                Default value is -1: it means unlimited. "
                        ::= { fkBridgePortEntry 4 }

                
--  1.3.6.1.4.1.10428 9 1.9.8.2.1.1.4
                -- 1.3.6.1.4.1.10428 9 1.101.3.2.1.1.5
                fkBridgePortCurrentHosts OBJECT-TYPE
                        SYNTAX INTEGER (0..65535)
                        MAX-ACCESS read-only
                        STATUS current
                        DESCRIPTION
                                "The number hosts which is allowed to be used. 
                                Aggregation group available."
                        ::= { fkBridgePortEntry 5 }

                
                -- 1.3.6.1.4.1.10428 9 1.101.3.2.1.1.6
                fkBridgePortMaxLearnPerUnit OBJECT-TYPE
                        SYNTAX INTEGER (-1..2147483647)
                        MAX-ACCESS read-only
                        STATUS current
                        DESCRIPTION
                                "Limit maximum number of MAC addresses learning 
                                newly per unit time(one second) on a port.
                                (0: nothing learned, -l: unlimited.)"
                        ::= { fkBridgePortEntry 6 }

                
--  1.3.6.1.4.1.10428 9 1.9.8.2.1.1.5
                -- 1.3.6.1.4.1.10428 9 1.101.3.2.1.1.7
                fkBridgePortMACFilterPermission OBJECT-TYPE
                        SYNTAX INTEGER
                                {
                                deny(0),
                                permit(1)
                                }
                        MAX-ACCESS read-only
                        STATUS current
                        DESCRIPTION
                                "The default permission for mac filtering. 
                                Valid only for physical ports,
                                use values from MFDB Table. "
                        DEFVAL { permit }
                        ::= { fkBridgePortEntry 7 }

                
--  1.3.6.1.4.1.10428 9 1.9.8.2.1.1.6
                -- 1.3.6.1.4.1.10428 9 1.101.3.2.1.1.8
                fkBridgePortIngMirrorStatus OBJECT-TYPE
                        SYNTAX INTEGER
                                {
                                disable(0),
                                enable(1)
                                }
                        MAX-ACCESS read-only
                        STATUS current
                        DESCRIPTION
                                "Mirroring on ingress packets. 
                                Valid only for physical ports. "
                        DEFVAL { disable }
                        ::= { fkBridgePortEntry 8 }

                
--  1.3.6.1.4.1.10428 9 1.9.8.2.1.1.7
                -- 1.3.6.1.4.1.10428 9 1.101.3.2.1.1.9
                fkBridgePortEgMirrorStatus OBJECT-TYPE
                        SYNTAX INTEGER
                                {
                                disable(0),
                                enable(1)
                                }
                        MAX-ACCESS read-only
                        STATUS current
                        DESCRIPTION
                                "Mirroring on egress packets. 
                                Valid only for physical ports. "
                        DEFVAL { disable }
                        ::= { fkBridgePortEntry 9 }

                
--  1.3.6.1.4.1.10428 9 1.9.8.2.1.1.8
                -- 1.3.6.1.4.1.10428 9 1.101.3.2.1.1.10
                fkBridgePortBcastThreshold OBJECT-TYPE
                        SYNTAX INTEGER (0..2097150)
                        MAX-ACCESS read-only
                        STATUS current
                        DESCRIPTION
                                "Broadcast packet rate limit(unit: packets/s),
                                Valid only for physical ports. 
                                Default value is 0: it means BCSC clear-state.
                                Value Range: 0-262142(TX/FX),0-2097150(GBIC)."
                        DEFVAL { 0 }
                        ::= { fkBridgePortEntry 10 }

                
--  1.3.6.1.4.1.10428 9 1.9.8.2.1.1.9
                -- 1.3.6.1.4.1.10428 9 1.101.3.2.1.1.11
                fkBridgePortMcastThreshold OBJECT-TYPE
                        SYNTAX INTEGER (0..2097150)
                        MAX-ACCESS read-only
                        STATUS current
                        DESCRIPTION
                                "Multicast packet rate limit.(unit: packets/s), 
                                Valid only for physical ports. 
                                Default value is 0: it means BCSC clear-state.
                                Value Range: 0-262142(TX/FX),0-2097150(GBIC)."
                        DEFVAL { 0 }
                        ::= { fkBridgePortEntry 11 }

                
--  1.3.6.1.4.1.10428 9 1.9.8.2.1.1.10
                -- 1.3.6.1.4.1.10428 9 1.101.3.2.1.1.12
                fkBridgePortDlfThreshold OBJECT-TYPE
                        SYNTAX INTEGER (0..2097150)
                        MAX-ACCESS read-only
                        STATUS current
                        DESCRIPTION
                                "DLF packet rate limit(unit: packets/s), 
                                Valid only for physical ports.
                                Default value is 0: it means BCSC clear-state.
                                Value Range: 0-262142(TX/FX),0-2097150(GBIC)."
                        DEFVAL { 0 }
                        ::= { fkBridgePortEntry 12 }

                
--  1.3.6.1.4.1.10428 9 1.9.8.2.1.1.11
                -- 1.3.6.1.4.1.10428 9 1.101.3.2.1.1.13
                fkBridgePortQinQStatus OBJECT-TYPE
                        SYNTAX INTEGER
                                {
                                disable(0),
                                enable(1)
                                }
                        MAX-ACCESS read-only
                        STATUS current
                        DESCRIPTION
                                "QinQ Status of the port. 
                                Valid only for physical ports. "
                        DEFVAL { disable }
                        ::= { fkBridgePortEntry 13 }

                
--  1.3.6.1.4.1.10428 9 1.9.8.2.1.1.12
                -- 1.3.6.1.4.1.10428 9 1.101.3.2.1.1.14
                fkBridgePortAdminLinktype OBJECT-TYPE
                        SYNTAX INTEGER
                                {
                                shared(0),
                                pointTopoint(1),
                                automatic(2)
                                }
                        MAX-ACCESS read-only
                        STATUS current
                        DESCRIPTION
                                "The administrative link-type of port on the xSTP."
                        DEFVAL { automatic }
                        ::= { fkBridgePortEntry 14 }

                
--  1.3.6.1.4.1.10428 9 1.9.8.2.1.1.13
                -- 1.3.6.1.4.1.10428 9 1.101.3.2.1.1.15
                fkBridgePortAdminEdgemode OBJECT-TYPE
                        SYNTAX INTEGER
                                {
                                disable(0),
                                enable(1)
                                }
                        MAX-ACCESS read-only
                        STATUS current
                        DESCRIPTION
                                "The administrative edgemode of port on the xSTP."
                        DEFVAL { disable }
                        ::= { fkBridgePortEntry 15 }

                
--  1.3.6.1.4.1.10428 9 1.9.8.2.1.1.14
                -- 1.3.6.1.4.1.10428 9 1.101.3.2.1.1.16
                fkBridgePortOperLinktype OBJECT-TYPE
                        SYNTAX INTEGER
                                {
                                shared(0),
                                pointTopoint(1)
                                }
                        MAX-ACCESS read-only
                        STATUS current
                        DESCRIPTION
                                "The link-type of the port on the xSTP."
                        ::= { fkBridgePortEntry 16 }

                
--  1.3.6.1.4.1.10428 9 1.9.8.2.1.1.15
                -- 1.3.6.1.4.1.10428 9 1.101.3.2.1.1.17
                fkBridgePortOperEdgemode OBJECT-TYPE
                        SYNTAX INTEGER
                                {
                                disabled(0),
                                enabled(1)
                                }
                        MAX-ACCESS read-only
                        STATUS current
                        DESCRIPTION
                                "The edge-mode of the port on the xSTP."
                        ::= { fkBridgePortEntry 17 }

                
                -- 1.3.6.1.4.1.10428 9 1.101.3.2.1.1.18
                fkBridgePortStpBpduFilter OBJECT-TYPE
                        SYNTAX INTEGER
                                {
                                disable(0),
                                enable(1)
                                }
                        MAX-ACCESS read-only
                        STATUS current
                        DESCRIPTION
                                "The stp bpdu-filter of the port on the xSTP. Default value is 0. "
                        ::= { fkBridgePortEntry 18 }

                
                -- 1.3.6.1.4.1.10428 9 1.101.3.2.1.1.19
                fkBridgePortPvlanIsolatedStatus OBJECT-TYPE
                        SYNTAX INTEGER
                                {
                                disable(0),
                                enable(1)
                                }
                        MAX-ACCESS read-only
                        STATUS current
                        DESCRIPTION
                                "Isolated status of this port. Default value is disable(0). "
                        DEFVAL { disable }
                        ::= { fkBridgePortEntry 19 }

                
                -- 1.3.6.1.4.1.10428 9 1.101.3.2.1.1.20
                fkBridgePortPvlanPromPorts OBJECT-TYPE
                        SYNTAX OCTET STRING
                        MAX-ACCESS read-only
                        STATUS current
                        DESCRIPTION
                                "Portlist for promiscuous ports of this port. The OctetString is a list of pairs of octets each identify an sheBridgePortIndex. The least significant byte is the second octet."
                        ::= { fkBridgePortEntry 20 }

                
                -- 1.3.6.1.4.1.10428 9 1.101.3.2.1.1.21
                fkBridgePortDhcpFilterServer OBJECT-TYPE
                        SYNTAX INTEGER
                                {
                                disable(0),
                                enable(1)
                                }
                        MAX-ACCESS read-only
                        STATUS current
                        DESCRIPTION
                                "DHCP filter server status
                                0: disabled
                                1: enabled"
                        ::= { fkBridgePortEntry 21 }

                
                -- 1.3.6.1.4.1.10428 9 1.101.3.2.1.1.22
                fkBridgePortLoopDetectStatus OBJECT-TYPE
                        SYNTAX INTEGER
                                {
                                enable(1),
                                disable(2)
                                }
                        MAX-ACCESS read-only
                        STATUS current
                        DESCRIPTION
                                "The adminStatus of loop-detect per ports."
                        ::= { fkBridgePortEntry 22 }

                
                -- 1.3.6.1.4.1.10428 9 1.101.3.2.1.1.23
                fkBridgePortLoopDetectBlock OBJECT-TYPE
                        SYNTAX INTEGER
                                {
                                enable(1),
                                disable(2)
                                }
                        MAX-ACCESS read-only
                        STATUS current
                        DESCRIPTION
                                "The adminBlock mode of loop-detect per ports.
                                Indicate whether block port or not."
                        ::= { fkBridgePortEntry 23 }

                
                -- 1.3.6.1.4.1.10428 9 1.101.3.2.1.1.24
                fkBridgePortLoopDetectPeriod OBJECT-TYPE
                        SYNTAX INTEGER (1..60)
                        MAX-ACCESS read-only
                        STATUS current
                        DESCRIPTION
                                "The sending period of detection packet."
                        ::= { fkBridgePortEntry 24 }

                
                -- 1.3.6.1.4.1.10428 9 1.101.3.2.1.1.25
                fkBridgePortLoopDetectTimer OBJECT-TYPE
                        SYNTAX INTEGER (0 | 1..86400)
                        MAX-ACCESS read-only
                        STATUS current
                        DESCRIPTION
                                "The Blocked list expire timer."
                        ::= { fkBridgePortEntry 25 }

                
                -- 1.3.6.1.4.1.10428 9 1.101.3.2.1.1.26
                fkBridgePortLoopDetectBlockStatus OBJECT-TYPE
                        SYNTAX INTEGER
                                {
                                block(1),
                                unblock(2)
                                }
                        MAX-ACCESS read-only
                        STATUS current
                        DESCRIPTION
                                "The operStauts of loop-detect per ports."
                        ::= { fkBridgePortEntry 26 }

                
                -- 1.3.6.1.4.1.10428 9 1.101.3.2.1.1.27
                fkBridgePortNetBIOSFilter OBJECT-TYPE
                        SYNTAX INTEGER
                                {
                                disable(0),
                                enable(1)
                                }
                        MAX-ACCESS read-only
                        STATUS current
                        DESCRIPTION
                                "The netBios filter status per ports"
                        ::= { fkBridgePortEntry 27 }

                
                -- 1.3.6.1.4.1.10428 9 1.101.3.2.1.1.28
                fkBridgePortPushInnertag OBJECT-TYPE
                        SYNTAX INTEGER
                                {
                                disable(0),
                                enable(1)
                                }
                        MAX-ACCESS read-only
                        STATUS current
                        DESCRIPTION
                                "The ingress port that push inner-tag"
                        ::= { fkBridgePortEntry 28 }

                
                -- 1.3.6.1.4.1.10428 9 1.101.3.2.1.1.29
                fkBridgePortPopInnertag OBJECT-TYPE
                        SYNTAX INTEGER
                                {
                                disable(0),
                                enable(1)
                                }
                        MAX-ACCESS read-only
                        STATUS current
                        DESCRIPTION
                                "The egress port that pop inner-tag"
                        ::= { fkBridgePortEntry 29 }

                
                -- 1.3.6.1.4.1.10428 9 1.101.3.2.1.1.30
                fkBridgePortInnertag OBJECT-TYPE
                        SYNTAX INTEGER (0..4096)
                        MAX-ACCESS read-only
                        STATUS current
                        DESCRIPTION
                                "The inner-tag value to push for incoming untagged packet"
                        ::= { fkBridgePortEntry 30 }

                
                -- 1.3.6.1.4.1.10428 9 1.101.3.2.1.1.31
                fkBridgePortPriority OBJECT-TYPE
                        SYNTAX INTEGER (0..7)
                        MAX-ACCESS read-only
                        STATUS current
                        DESCRIPTION
                                "The port priority value for incoming untagged packet"
                        ::= { fkBridgePortEntry 31 }

                
                -- 1.3.6.1.4.1.10428 9 1.101.3.2.1.1.32
                fkBridgePortInner2outerPri OBJECT-TYPE
                        SYNTAX INTEGER
                                {
                                disable(0),
                                enable(1)
                                }
                        MAX-ACCESS read-only
                        STATUS current
                        DESCRIPTION
                                "Use inner-tag’s priority as outer-tag’s priority."
                        ::= { fkBridgePortEntry 32 }

                
                -- 1.3.6.1.4.1.10428 9 1.101.3.2.1.1.33
                fkBridgePortInner2outerVid OBJECT-TYPE
                        SYNTAX INTEGER
                                {
                                disable(0),
                                enable(1)
                                }
                        MAX-ACCESS read-only
                        STATUS current
                        DESCRIPTION
                                "Use inner-tag’s vlan-id as outer-tag’s vlan-id."
                        ::= { fkBridgePortEntry 33 }

                
                -- 1.3.6.1.4.1.10428 9 1.101.3.2.1.1.34
                fkBridgePortLinkUpCnt OBJECT-TYPE
                        SYNTAX INTEGER (1..65535)
                        MAX-ACCESS read-only
                        STATUS current
                        DESCRIPTION
                                "The times of link-up event"
                        ::= { fkBridgePortEntry 34 }

                
                -- 1.3.6.1.4.1.10428 9 1.101.3.2.1.1.35
                fkBridgePortLinkDownCnt OBJECT-TYPE
                        SYNTAX INTEGER (1..65535)
                        MAX-ACCESS read-only
                        STATUS current
                        DESCRIPTION
                                "The times of link-down event"
                        ::= { fkBridgePortEntry 35 }

                
                -- 1.3.6.1.4.1.10428 9 1.101.3.2.1.1.36
                fkBridgePortLinkUpTime OBJECT-TYPE
                        SYNTAX Counter64
                        UNITS "1 sec"
                        MAX-ACCESS read-only
                        STATUS current
                        DESCRIPTION
                                "The elapsed time after link is up."
                        ::= { fkBridgePortEntry 36 }

                
                -- 1.3.6.1.4.1.10428 9 1.101.3.2.1.1.37
                fkBridgePortElapsedTimeAfterClearStats OBJECT-TYPE
                        SYNTAX Counter64
                        UNITS "1 sec"
                        MAX-ACCESS read-only
                        STATUS current
                        DESCRIPTION
                                "The elapsed time after clearing statistics."
                        ::= { fkBridgePortEntry 37 }

                
                -- 1.3.6.1.4.1.10428 9 1.101.3.2.1.1.38
                fkBridgePortMACLearningStatus OBJECT-TYPE
                        SYNTAX INTEGER
                                {
                                enable(1),
                                disable(2)
                                }
                        MAX-ACCESS read-only
                        STATUS current
                        DESCRIPTION
                                "If enable, SLF packet is forwarded with mac-learning.
                                Otherwise, SLF packet is forwarded without mac-learning."
                        ::= { fkBridgePortEntry 38 }

                
                -- 1.3.6.1.4.1.10428 9 1.101.3.2.1.1.39
                fkBridgePortPortBridgeStatus OBJECT-TYPE
                        SYNTAX INTEGER
                                {
                                enable(1),
                                disable(2)
                                }
                        MAX-ACCESS read-only
                        STATUS current
                        DESCRIPTION
                                "Port Bridge Feature for transmitting the packet out on the same port of which is received."
                        ::= { fkBridgePortEntry 39 }
-- Port Bridge Feature for transmitting the packet out on the same port of which is received.
                
                -- 1.3.6.1.4.1.10428 9 1.101.3.2.1.1.40
                fkBridgePortUnknownMcastBlock OBJECT-TYPE
                        SYNTAX INTEGER
                                {
                                enable(1),
                                disable(2)
                                }
                        MAX-ACCESS read-only
                        STATUS current
                        DESCRIPTION
                                "Unknown multicast block setting for a port."
                        ::= { fkBridgePortEntry 40 }

                
                -- 1.3.6.1.4.1.10428 9 1.101.3.2.1.1.41
                fkBridgePortDescription OBJECT-TYPE
                        SYNTAX OCTET STRING (SIZE (1..128))
                        MAX-ACCESS read-write
                        STATUS current
                        DESCRIPTION
                                "The port description."
                        ::= { fkBridgePortEntry 41 }

                
                -- 1.3.6.1.4.1.10428 9 1.101.3.2.1.1.42
                fkBridgePortHoldTime OBJECT-TYPE
                        SYNTAX Integer32 (1..65535)
                        MAX-ACCESS read-only
                        STATUS current
                        DESCRIPTION
                                "The hold-time"
                        ::= { fkBridgePortEntry 42 }

                
                -- 1.3.6.1.4.1.10428 9 1.101.3.2.1.1.43
                fkBridgePortMacAntiSpoofing OBJECT-TYPE
                        SYNTAX TruthValue
                        MAX-ACCESS read-only
                        STATUS current
                        DESCRIPTION
                                "The mac anti-spoofing per port."
                        ::= { fkBridgePortEntry 43 }

                
                -- 1.3.6.1.4.1.10428 9 1.101.3.2.1.1.44
                fkBridgePortSwitchType OBJECT-TYPE
                        SYNTAX INTEGER
                                {
                                special(1),
                                inner(2),
                                vlan(3),
                                eth(4),
                                portChannel(5),
                                tunnel(6),
                                unknown(255)
                                }
                        MAX-ACCESS read-only
                        STATUS current
                        DESCRIPTION
                                "Interface type."
                        ::= { fkBridgePortEntry 44 }

                
                -- 1.3.6.1.4.1.10428 9 1.101.3.2.1.1.45
                fkBridgePortSwitchState OBJECT-TYPE
                        SYNTAX INTEGER
                                {
                                switchedPort(1),
                                routedPort(2)
                                }
                        MAX-ACCESS read-only
                        STATUS current
                        DESCRIPTION
                                "The interface mode to switched port or routed port."
                        ::= { fkBridgePortEntry 45 }

                
                -- 1.3.6.1.4.1.10428 9 1.101.3.2.1.1.46
                fkBridgePortSwitchMode OBJECT-TYPE
                        SYNTAX INTEGER
                                {
                                access(1),
                                hybrid(2),
                                trunk(3),
                                ce(4),
                                cn(5),
                                pn(6),
                                pe(7),
                                cnp(8),
                                vip(9),
                                pip(10),
                                cbp(11),
                                invalid(255)
                                }
                        MAX-ACCESS read-only
                        STATUS current
                        DESCRIPTION
                                "The switching mode of L2 interface."
                        ::= { fkBridgePortEntry 46 }

                
                -- 1.3.6.1.4.1.10428 9 1.101.3.2.1.1.47
                fkBridgePortSwitchSubMode OBJECT-TYPE
                        SYNTAX INTEGER
                                {
                                access(1),
                                hybrid(2),
                                trunk(3),
                                ce(4),
                                cn(5),
                                pn(6),
                                pe(7),
                                cnp(8),
                                vip(9),
                                pip(10),
                                cbp(11),
                                invalid(255)
                                }
                        MAX-ACCESS read-only
                        STATUS current
                        DESCRIPTION
                                "The switching sub mode of L2 interface."
                        ::= { fkBridgePortEntry 47 }

                
                -- 1.3.6.1.4.1.10428 9 1.101.3.2.1.1.48
                fkBridgePortSwitchDefaultVlan OBJECT-TYPE
                        SYNTAX Integer32 (1..4094)
                        MAX-ACCESS read-only
                        STATUS current
                        DESCRIPTION
                                "The default VLAN of L2 interface."
                        ::= { fkBridgePortEntry 48 }

                
                -- 1.3.6.1.4.1.10428 9 1.101.3.2.1.1.49
                fkBridgePortSwitchIngressFilter OBJECT-TYPE
                        SYNTAX INTEGER
                                {
                                enable(1),
                                disable(2)
                                }
                        MAX-ACCESS read-only
                        STATUS current
                        DESCRIPTION
                                "Set the ingress filtering for 
the received frames.
                                "
                        ::= { fkBridgePortEntry 49 }

                
                -- 1.3.6.1.4.1.10428 9 1.101.3.2.1.1.50
                fkBridgePortSwitchAccFrameType OBJECT-TYPE
                        SYNTAX BITS
                                {
                                allType(0),
                                tagged(1),
                                untagged(2)
                                }
                        MAX-ACCESS read-only
                        STATUS current
                        DESCRIPTION
                                "Set the Layer 2 interface acceptable frame types. 
                                This processing occurs
after VLAN classification.
vlan-tagged Accept only classified frames 
                                which belong to the port's member set.
Hybridge interface only.
                                "
                        ::= { fkBridgePortEntry 50 }

                
                -- 1.3.6.1.4.1.10428 9 1.101.3.2.1.1.51
                fkBridgePortSwitchNativeVid OBJECT-TYPE
                        SYNTAX Integer32 (1..4094)
                        MAX-ACCESS read-only
                        STATUS current
                        DESCRIPTION
                                "The native VLAN is used for classifying the incoming untagged packets.
                                "
                        ::= { fkBridgePortEntry 51 }

                
                -- 1.3.6.1.4.1.10428 9 1.101.3.2.1.1.52
                fkBridgePortSwitchAllowedVlan OBJECT-TYPE
                        SYNTAX OCTET STRING
                        MAX-ACCESS read-only
                        STATUS current
                        DESCRIPTION
                                "Both tagged and untagged
                                frames will be classified over interfaces."
                        ::= { fkBridgePortEntry 52 }

                
                -- 1.3.6.1.4.1.10428 9 1.101.3.2.1.1.53
                fkBridgePortSwitchAllowedVlanEtag OBJECT-TYPE
                        SYNTAX OCTET STRING
                        MAX-ACCESS read-only
                        STATUS current
                        DESCRIPTION
                                "egress Port string"
                        ::= { fkBridgePortEntry 53 }

                
                -- 1.3.6.1.4.1.10428 9 1.101.3.2.1.1.54
                fkBridgePortSwitchChannelType OBJECT-TYPE
                        SYNTAX INTEGER
                                {
                                none(0),
                                aggregator(1),
                                aggregated(2)
                                }
                        MAX-ACCESS read-only
                        STATUS current
                        DESCRIPTION
                                "Indicate whether port is aggregator or aggregated(member)."
                        ::= { fkBridgePortEntry 54 }

                
                -- 1.3.6.1.4.1.10428 9 1.101.3.2.1.1.55
                fkBridgePortSwitchStaticChannelGroup OBJECT-TYPE
                        SYNTAX OCTET STRING
                        MAX-ACCESS read-only
                        STATUS current
                        DESCRIPTION
                                "Static channel group name"
                        ::= { fkBridgePortEntry 55 }

                
                -- 1.3.6.1.4.1.10428 9 1.101.3.2.1.1.56
                fkBridgePortSwitchChannelLoadbalance OBJECT-TYPE
                        SYNTAX INTEGER
                                {
                                dstMac(1),
                                srcMac(2),
                                srcDstMac(3),
                                srcIp(4),
                                dstIp(5),
                                srcDstIp(6),
                                srcPort(7),
                                dstPort(8),
                                srcDstPort(9)
                                }
                        MAX-ACCESS read-only
                        STATUS current
                        DESCRIPTION
                                "Channel group hash method."
                        ::= { fkBridgePortEntry 56 }

                
--   Node definitions
-- 
-- 1.3.6.1.4.1.10428 9 1.9.8.2.2
                -- 1.3.6.1.4.1.10428 9 1.101.3.2.2
                fkBridgePortControl OBJECT IDENTIFIER ::= { fkBridgePort 2 }

                
--  1.3.6.1.4.1.10428 9 1.9.8.2.2.1
                -- 1.3.6.1.4.1.10428 9 1.101.3.2.2.1
                fkBridgePortControlRequest OBJECT-TYPE
                        SYNTAX INTEGER
                                {
                                setBridgePortPVid(1),
                                setBridgePortMaxHosts(2),
                                setBridgePortMaxLearnPerUnit(3),
                                setBridgePortMACFilterPermission(4),
                                setBridgePortMirrorProfile(5),
                                setBridgePortBcscThresholdProfile(6),
                                setBridgePortQinQStatus(7),
                                setBridgePortLinktype(8),
                                setBridgePortEdgemode(9),
                                setBridgePortStpBpduFilter(10),
                                setBridgePortIsolatedStatus(11),
                                setBridgePortStpBpduGuardErrRcv(12),
                                setBridgePortDhcpFilterServer(13),
                                setBridgePortLoopDetectProfile(14),
                                setBridgePortLoopDetectUnblock(15),
                                setBridgePortNetBIOSFilter(16),
                                setBridgePortPushInnertag(17),
                                setBridgePortPopInnertag(18),
                                setBridgePortInnertag(19),
                                setBridgePortPriority(20),
                                setBridgePortInner2outerPri(21),
                                setBridgePortInner2outerVid(22),
                                setBridgePortMacLearningStatus(23),
                                setBridgePortPortBridgeStatus(24),
                                setBridgePortUnknownMcastBlock(25),
                                setBridgePortDescriptopn(26),
                                setBridgePortHoldTime(27),
                                setBridgePortMacAntiSpoofing(28),
                                setBridgePortSwitchStatus(29),
                                setBridgePortSwitchMode(30),
                                setBridgePortSwitchDefaultVlan(31),
                                setBridgePortSwitchNativeVlan(32),
                                setBridgePortSwitchAccFramType(33),
                                setBridgePortSwitchAddAllowdVlan(34),
                                setBridgePortSwitchRemoveAllowdVlan(35),
                                setBridgePortSwitchStaticChannel(36),
                                setBridgePortSwitchChannelLoadbalance(37)
                                }
                        MAX-ACCESS read-write
                        STATUS current
                        DESCRIPTION
                                "
                                setBridgePortPVid:
                                fkBridgePortControlIndex
                                fkBridgePortControlPVid
                                
                                setBridgePortMaxHosts:
                                fkBridgePortControlIndex
                                fkBridgePortControlMaxHosts
                                
                                setBridgePortMACFilterPermission:
                                fkBridgePortControlIndex
                                fkBridgePortControlMACFilterPermission
                                
                                setBridgePortMirrorProfile:
                                fkBridgePortControlIndex
                                fkBridgePortControlIngMirrorStatus
                                fkBridgePortControlEgMirrorStatus
                                            
                                setBridgePortBcscThresholdProfile:
                                fkBridgePortControlIndex
                                fkBridgePortControlBcastThreshold
                                fkBridgePortControlMcastThreshold
                                fkBridgePortControlDlfThreshold
                                            
                                setBridgePortQinQStatus:
                                fkBridgePortControlIndex
                                fkBridgePortControlQinQStatus
                                            
                                setBridgePortLinktype:
                                fkBridgePortControlIndex
                                fkBridgePortControlAdminLinktype
                                            
                                setBridgePortEdgemode:
                                fkBridgePortControlIndex
                                fkBridgePortControlAdminEdgemode
                                
                                setBridgePortNetBIOSFilter:
                                fkBridgePortControlIndex
                                fkBridgePortControlNetBIOSFilter
                                "
                        ::= { fkBridgePortControl 1 }

                
--  1.3.6.1.4.1.10428 9 1.9.8.2.2.3
                -- 1.3.6.1.4.1.10428 9 1.101.3.2.2.2
                fkBridgePortControlStatus OBJECT-TYPE
                        SYNTAX FkControlStatusType
                        MAX-ACCESS read-only
                        STATUS current
                        DESCRIPTION
                                "The status of a user command."
                        ::= { fkBridgePortControl 2 }

                
--  1.3.6.1.4.1.10428 9 1.9.8.2.2.4
                -- 1.3.6.1.4.1.10428 9 1.101.3.2.2.3
                fkBridgePortControlTimer OBJECT-TYPE
                        SYNTAX Gauge32
                        MAX-ACCESS read-write
                        STATUS current
                        DESCRIPTION
                                "The maximum wait time for the manager for a long running user command."
                        ::= { fkBridgePortControl 3 }

                
--  1.3.6.1.4.1.10428 9 1.9.8.2.2.6
                -- 1.3.6.1.4.1.10428 9 1.101.3.2.2.4
                fkBridgePortControlTimeStamp OBJECT-TYPE
                        SYNTAX TimeTicks
                        MAX-ACCESS read-only
                        STATUS current
                        DESCRIPTION
                                "The time stamp of the last command (end of command)."
                        ::= { fkBridgePortControl 4 }

                
--  1.3.6.1.4.1.10428 9 1.9.8.2.2.5
                -- 1.3.6.1.4.1.10428 9 1.101.3.2.2.5
                fkBridgePortControlReqResult OBJECT-TYPE
                        SYNTAX FkControlRequestResultType
                        MAX-ACCESS read-only
                        STATUS current
                        DESCRIPTION
                                "The result of the last user command."
                        ::= { fkBridgePortControl 5 }

                
--  1.3.6.1.4.1.10428 9 1.9.8.2.2.2
                -- 1.3.6.1.4.1.10428 9 1.101.3.2.2.6
                fkBridgePortControlIndex OBJECT-TYPE
                        SYNTAX INTEGER (1..255)
                        MAX-ACCESS read-write
                        STATUS current
                        DESCRIPTION
                                "fkBridgePortIndex"
                        ::= { fkBridgePortControl 6 }

                
--  1.3.6.1.4.1.10428 9 1.9.8.2.2.7
                -- 1.3.6.1.4.1.10428 9 1.101.3.2.2.7
                fkBridgePortControlPVid OBJECT-TYPE
                        SYNTAX INTEGER (1..4094)
                        MAX-ACCESS read-write
                        STATUS current
                        DESCRIPTION
                                "The PVID of port. 
                                Taken if no other rule given for VLAN association. 
                                If aggregated: only for group."
                        ::= { fkBridgePortControl 7 }

                
--  1.3.6.1.4.1.10428 9 1.9.8.2.2.8
                -- 1.3.6.1.4.1.10428 9 1.101.3.2.2.8
                fkBridgePortControlMaxHosts OBJECT-TYPE
                        SYNTAX INTEGER (-1..2147483647)
                        MAX-ACCESS read-write
                        STATUS current
                        DESCRIPTION
                                "The maximum number of hosts allowed. 
                                Aggregation group available. Value 0 is allowed,
                                Value -1 is used to clear."
                        DEFVAL { -1 }
                        ::= { fkBridgePortControl 8 }

                
                -- 1.3.6.1.4.1.10428 9 1.101.3.2.2.9
                fkBridgePortControlMaxLearnPerUnit OBJECT-TYPE
                        SYNTAX INTEGER (-1..2147483647)
                        MAX-ACCESS read-write
                        STATUS current
                        DESCRIPTION
                                "Limit maximum number of MAC addresses learning 
                                newly per unit time(one second) on a port.
                                (0: nothing learned, -l: unlimited.)"
                        ::= { fkBridgePortControl 9 }

                
--  1.3.6.1.4.1.10428 9 1.9.8.2.2.9
                -- 1.3.6.1.4.1.10428 9 1.101.3.2.2.10
                fkBridgePortControlMACFilterPermission OBJECT-TYPE
                        SYNTAX INTEGER
                                {
                                deny(0),
                                permit(1)
                                }
                        MAX-ACCESS read-write
                        STATUS current
                        DESCRIPTION
                                "The default permission for mac filtering. 
                                Valid only for physical ports, 
                                use values from MFDB  Table."
                        DEFVAL { permit }
                        ::= { fkBridgePortControl 10 }

                
--  1.3.6.1.4.1.10428 9 1.9.8.2.2.10
                -- 1.3.6.1.4.1.10428 9 1.101.3.2.2.11
                fkBridgePortControlIngMirrorStatus OBJECT-TYPE
                        SYNTAX INTEGER
                                {
                                disable(0),
                                enable(1)
                                }
                        MAX-ACCESS read-write
                        STATUS current
                        DESCRIPTION
                                "Mirroring on ingress packets. 
                                Valid only for physical ports. "
                        DEFVAL { disable }
                        ::= { fkBridgePortControl 11 }

                
--  1.3.6.1.4.1.10428 9 1.9.8.2.2.11
                -- 1.3.6.1.4.1.10428 9 1.101.3.2.2.12
                fkBridgePortControlEgMirrorStatus OBJECT-TYPE
                        SYNTAX INTEGER
                                {
                                disable(0),
                                enable(1)
                                }
                        MAX-ACCESS read-write
                        STATUS current
                        DESCRIPTION
                                "Mirroring on egress packets. 
                                Valid only for physical ports. "
                        DEFVAL { disable }
                        ::= { fkBridgePortControl 12 }

                
--  1.3.6.1.4.1.10428 9 1.9.8.2.2.12
                -- 1.3.6.1.4.1.10428 9 1.101.3.2.2.13
                fkBridgePortControlBcastThreshold OBJECT-TYPE
                        SYNTAX INTEGER (0..2097150)
                        MAX-ACCESS read-write
                        STATUS current
                        DESCRIPTION
                                "Broadcast packet rate limit (unit: packets/s), 
                                Valid only for physical ports. Value 0 is used to clear.
                                Value Range: 0-262142(TX/FX),0-2097150(GBIC)."
                        DEFVAL { 0 }
                        ::= { fkBridgePortControl 13 }

                
--  1.3.6.1.4.1.10428 9 1.9.8.2.2.13
                -- 1.3.6.1.4.1.10428 9 1.101.3.2.2.14
                fkBridgePortControlMcastThreshold OBJECT-TYPE
                        SYNTAX INTEGER (0..2097150)
                        MAX-ACCESS read-write
                        STATUS current
                        DESCRIPTION
                                "Multicast packet rate limit (unit: packets/s), 
                                Valid only for physical ports. Value 0 is used to clear.
                                Value Range: 0-262142(TX/FX),0-2097150(GBIC)."
                        DEFVAL { 0 }
                        ::= { fkBridgePortControl 14 }

                
--  1.3.6.1.4.1.10428 9 1.9.8.2.2.14
                -- 1.3.6.1.4.1.10428 9 1.101.3.2.2.15
                fkBridgePortControlDlfThreshold OBJECT-TYPE
                        SYNTAX INTEGER (0..2097150)
                        MAX-ACCESS read-write
                        STATUS current
                        DESCRIPTION
                                "DLF packet rate limit (unit: packets/s), 
                                Valid only for physical ports. Value 0 is used to clear.
                                Value Range: 0-262142(TX/FX),0-2097150(GBIC)."
                        DEFVAL { 0 }
                        ::= { fkBridgePortControl 15 }

                
--  1.3.6.1.4.1.10428 9 1.9.8.2.2.15
                -- 1.3.6.1.4.1.10428 9 1.101.3.2.2.16
                fkBridgePortControlQinQStatus OBJECT-TYPE
                        SYNTAX INTEGER
                                {
                                disable(0),
                                enable(1)
                                }
                        MAX-ACCESS read-write
                        STATUS current
                        DESCRIPTION
                                "QinQ Status of the port. 
                                Valid only for physical ports. "
                        DEFVAL { disable }
                        ::= { fkBridgePortControl 16 }

                
--  1.3.6.1.4.1.10428 9 1.9.8.2.2.16
                -- 1.3.6.1.4.1.10428 9 1.101.3.2.2.17
                fkBridgePortControlAdminLinktype OBJECT-TYPE
                        SYNTAX INTEGER
                                {
                                shared(0),
                                pointTopoint(1),
                                automatic(2)
                                }
                        MAX-ACCESS read-write
                        STATUS current
                        DESCRIPTION
                                "The administrative link-type of port on the xSTP. "
                        DEFVAL { automatic }
                        ::= { fkBridgePortControl 17 }

                
--  1.3.6.1.4.1.10428 9 1.9.8.2.2.17
                -- 1.3.6.1.4.1.10428 9 1.101.3.2.2.18
                fkBridgePortControlAdminEdgemode OBJECT-TYPE
                        SYNTAX INTEGER
                                {
                                disable(0),
                                enable(1)
                                }
                        MAX-ACCESS read-write
                        STATUS current
                        DESCRIPTION
                                "The administrative edgemode of port on the xSTP. "
                        DEFVAL { disable }
                        ::= { fkBridgePortControl 18 }

                
                -- 1.3.6.1.4.1.10428 9 1.101.3.2.2.19
                fkBridgePortControlStpBpduFilter OBJECT-TYPE
                        SYNTAX INTEGER
                                {
                                disable(0),
                                enable(1)
                                }
                        MAX-ACCESS read-write
                        STATUS current
                        DESCRIPTION
                                "The stp bpdu-filter of the port on the xSTP. Default value is 0."
                        DEFVAL { disable }
                        ::= { fkBridgePortControl 19 }

                
                -- 1.3.6.1.4.1.10428 9 1.101.3.2.2.20
                fkBridgePortControlPvlanIsolatedStatus OBJECT-TYPE
                        SYNTAX INTEGER
                                {
                                disable(0),
                                enable(1)
                                }
                        MAX-ACCESS read-write
                        STATUS current
                        DESCRIPTION
                                "Isolated status of this port. Default value is disable(0)."
                        DEFVAL { disable }
                        ::= { fkBridgePortControl 20 }

                
                -- 1.3.6.1.4.1.10428 9 1.101.3.2.2.21
                fkBridgePortControlPvlanPromPort OBJECT-TYPE
                        SYNTAX INTEGER (1..65535)
                        MAX-ACCESS read-write
                        STATUS current
                        DESCRIPTION
                                "Portlist for promiscuous ports of this port. The OctetString is a list of pairs of octets each identify an sheBridgePortIndex. The least significant byte is the second octet."
                        ::= { fkBridgePortControl 21 }

                
                -- 1.3.6.1.4.1.10428 9 1.101.3.2.2.22
                fkBridgePortControlStpBpduGuardErrRcv OBJECT-TYPE
                        SYNTAX TruthValue
                        MAX-ACCESS read-write
                        STATUS current
                        DESCRIPTION
                                "Trigger manual recovery for the port disabled by Bpdu Guard.
                                 false : sustain current state.
                                 true  : trigger recovery."
                        DEFVAL { false }
                        ::= { fkBridgePortControl 22 }

                
                -- 1.3.6.1.4.1.10428 9 1.101.3.2.2.23
                fkBridgePortControlDhcpFilterServer OBJECT-TYPE
                        SYNTAX INTEGER
                                {
                                disable(0),
                                enable(1)
                                }
                        MAX-ACCESS read-write
                        STATUS current
                        DESCRIPTION
                                "DHCP filter server status
                                0: disabled
                                1: enabled"
                        ::= { fkBridgePortControl 23 }

                
                -- 1.3.6.1.4.1.10428 9 1.101.3.2.2.24
                fkBridgePortControlLoopDetectStatus OBJECT-TYPE
                        SYNTAX INTEGER
                                {
                                enable(1),
                                disable(2)
                                }
                        MAX-ACCESS read-write
                        STATUS current
                        DESCRIPTION
                                "The adminStatus of loop-detect per ports."
                        ::= { fkBridgePortControl 24 }

                
                -- 1.3.6.1.4.1.10428 9 1.101.3.2.2.25
                fkBridgePortControlLoopDetectBlock OBJECT-TYPE
                        SYNTAX INTEGER
                                {
                                enable(1),
                                disable(2)
                                }
                        MAX-ACCESS read-only
                        STATUS current
                        DESCRIPTION
                                "The adminBlock mode of loop-detect per ports.
                                Indicate whether block port or not."
                        ::= { fkBridgePortControl 25 }

                
                -- 1.3.6.1.4.1.10428 9 1.101.3.2.2.26
                fkBridgePortControlLoopDetectPeriod OBJECT-TYPE
                        SYNTAX INTEGER (1..60)
                        MAX-ACCESS read-write
                        STATUS current
                        DESCRIPTION
                                "The sending period of detection packet."
                        ::= { fkBridgePortControl 26 }

                
                -- 1.3.6.1.4.1.10428 9 1.101.3.2.2.27
                fkBridgePortControlLoopDetectTimer OBJECT-TYPE
                        SYNTAX INTEGER (0 | 1..86400)
                        MAX-ACCESS read-write
                        STATUS current
                        DESCRIPTION
                                "The Blocked list expire timer."
                        ::= { fkBridgePortControl 27 }

                
                -- 1.3.6.1.4.1.10428 9 1.101.3.2.2.28
                fkBridgePortControlNetBIOSFilter OBJECT-TYPE
                        SYNTAX INTEGER
                                {
                                disable(0),
                                enable(1)
                                }
                        MAX-ACCESS read-write
                        STATUS current
                        DESCRIPTION
                                "The netBios filter status per ports"
                        ::= { fkBridgePortControl 28 }

                
                -- 1.3.6.1.4.1.10428 9 1.101.3.2.2.29
                fkBridgePortControlPushInnertag OBJECT-TYPE
                        SYNTAX INTEGER
                                {
                                disable(0),
                                enable(1)
                                }
                        MAX-ACCESS read-write
                        STATUS current
                        DESCRIPTION
                                "Push inner-tag for incoming untagged packet."
                        ::= { fkBridgePortControl 29 }

                
                -- 1.3.6.1.4.1.10428 9 1.101.3.2.2.30
                fkBridgePortControlPopInnertag OBJECT-TYPE
                        SYNTAX INTEGER
                                {
                                disable(0),
                                enable(1)
                                }
                        MAX-ACCESS read-write
                        STATUS current
                        DESCRIPTION
                                "Pop inner-tag for double tagged packet."
                        ::= { fkBridgePortControl 30 }

                
                -- 1.3.6.1.4.1.10428 9 1.101.3.2.2.31
                fkBridgePortControlInnertag OBJECT-TYPE
                        SYNTAX INTEGER (0..4096)
                        MAX-ACCESS read-write
                        STATUS current
                        DESCRIPTION
                                "Inner-tag value to push for incoming untagged packet."
                        ::= { fkBridgePortControl 31 }

                
                -- 1.3.6.1.4.1.10428 9 1.101.3.2.2.32
                fkBridgePortControlPriority OBJECT-TYPE
                        SYNTAX INTEGER (0..7)
                        MAX-ACCESS read-write
                        STATUS current
                        DESCRIPTION
                                "The priority value per port.
                                Assign priority for untagged packet from port.
                                "
                        ::= { fkBridgePortControl 32 }

                
                -- 1.3.6.1.4.1.10428 9 1.101.3.2.2.33
                fkBridgePortControlInner2outerPri OBJECT-TYPE
                        SYNTAX INTEGER
                                {
                                disable(0),
                                enable(1)
                                }
                        MAX-ACCESS read-write
                        STATUS current
                        DESCRIPTION
                                "If enable, use inner-tag's priority as outer-tag's priority.
                                Otherwise, use outer-tag's priority"
                        ::= { fkBridgePortControl 33 }

                
                -- 1.3.6.1.4.1.10428 9 1.101.3.2.2.34
                fkBridgePortControlInner2outerVid OBJECT-TYPE
                        SYNTAX INTEGER
                                {
                                disable(0),
                                enable(1)
                                }
                        MAX-ACCESS read-write
                        STATUS current
                        DESCRIPTION
                                "If enable, use inner-tag's vlan-id as outer-tag's vlan-id.
                                Otherwise, use outer-tag's vlan-id"
                        ::= { fkBridgePortControl 34 }

                
                -- 1.3.6.1.4.1.10428 9 1.101.3.2.2.35
                fkBridgePortControlMACLearningStatus OBJECT-TYPE
                        SYNTAX INTEGER
                                {
                                enable(1),
                                disable(2)
                                }
                        MAX-ACCESS read-write
                        STATUS current
                        DESCRIPTION
                                "If enable, SLF packet is forwarded with mac-learning.
                                Otherwise, SLF packet is forwarded without mac-learning."
                        ::= { fkBridgePortControl 35 }

                
                -- 1.3.6.1.4.1.10428 9 1.101.3.2.2.36
                fkBridgePortControlPortBridgeStatus OBJECT-TYPE
                        SYNTAX INTEGER
                                {
                                enable(1),
                                disable(2)
                                }
                        MAX-ACCESS read-write
                        STATUS current
                        DESCRIPTION
                                "Port Bridge Feature for transmitting the packet out on the same port of which is received."
                        ::= { fkBridgePortControl 36 }

                
                -- 1.3.6.1.4.1.10428 9 1.101.3.2.2.37
                fkBridgePortControlUnknownMcastBlock OBJECT-TYPE
                        SYNTAX INTEGER
                                {
                                enable(1),
                                disable(2)
                                }
                        MAX-ACCESS read-write
                        STATUS current
                        DESCRIPTION
                                "Unknown multicast block setting for a port."
                        ::= { fkBridgePortControl 37 }

                
                -- 1.3.6.1.4.1.10428 9 1.101.3.2.2.38
                fkBridgePortControlDescription OBJECT-TYPE
                        SYNTAX OCTET STRING (SIZE (1..128))
                        MAX-ACCESS read-write
                        STATUS current
                        DESCRIPTION
                                "The Port Description."
                        ::= { fkBridgePortControl 38 }

                
                -- 1.3.6.1.4.1.10428 9 1.101.3.2.2.39
                fkBridgePortControlHoldTime OBJECT-TYPE
                        SYNTAX Integer32 (1..65535)
                        MAX-ACCESS read-write
                        STATUS current
                        DESCRIPTION
                                "The hold-time"
                        ::= { fkBridgePortControl 39 }

                
                -- 1.3.6.1.4.1.10428 9 1.101.3.2.2.40
                fkBridgePortControlMacAntiSpoofing OBJECT-TYPE
                        SYNTAX TruthValue
                        MAX-ACCESS read-write
                        STATUS current
                        DESCRIPTION
                                "The mac anti-spoofing per port."
                        ::= { fkBridgePortControl 40 }

                
                -- 1.3.6.1.4.1.10428 9 1.101.3.2.2.41
                fkBridgePortControlSwitchStatus OBJECT-TYPE
                        SYNTAX INTEGER
                                {
                                switchedPort(1),
                                routedPort(2)
                                }
                        MAX-ACCESS read-write
                        STATUS current
                        DESCRIPTION
                                "The interface mode to switched port or routed port."
                        ::= { fkBridgePortControl 41 }

                
                -- 1.3.6.1.4.1.10428 9 1.101.3.2.2.42
                fkBridgePortControlSwitchMode OBJECT-TYPE
                        SYNTAX INTEGER
                                {
                                access(1),
                                hybrid(2),
                                trunk(3),
                                ce(4),
                                cn(5),
                                pn(6),
                                pe(7),
                                cnp(8),
                                vip(9),
                                pip(10),
                                cbp(11),
                                invalid(255)
                                }
                        MAX-ACCESS read-write
                        STATUS current
                        DESCRIPTION
                                "The switching mode of L2 interface.
                                "
                        ::= { fkBridgePortControl 42 }

                
                -- 1.3.6.1.4.1.10428 9 1.101.3.2.2.43
                fkBridgePortControlSwitchSubMode OBJECT-TYPE
                        SYNTAX INTEGER
                                {
                                access(1),
                                hybrid(2),
                                trunk(3),
                                ce(4),
                                cn(5),
                                pn(6),
                                pe(7),
                                cnp(8),
                                vip(9),
                                pip(10),
                                cbp(11),
                                invalid(255)
                                }
                        MAX-ACCESS read-write
                        STATUS current
                        DESCRIPTION
                                "The switching sub mode of L2 interface.
                                "
                        ::= { fkBridgePortControl 43 }

                
                -- 1.3.6.1.4.1.10428 9 1.101.3.2.2.44
                fkBridgePortControlSwitchDefaultVlan OBJECT-TYPE
                        SYNTAX Integer32 (1..4094)
                        MAX-ACCESS read-write
                        STATUS current
                        DESCRIPTION
                                "The dafulat VLAN of L2 interface"
                        ::= { fkBridgePortControl 44 }

                
                -- 1.3.6.1.4.1.10428 9 1.101.3.2.2.45
                fkBridgePortControlSwitchIngressFilter OBJECT-TYPE
                        SYNTAX INTEGER
                                {
                                enable(1),
                                disable(2)
                                }
                        MAX-ACCESS read-write
                        STATUS current
                        DESCRIPTION
                                "Set the ingress filtering for 
the received frames
                                "
                        ::= { fkBridgePortControl 45 }

                
                -- 1.3.6.1.4.1.10428 9 1.101.3.2.2.46
                fkBridgePortControlSwitchAccFrameType OBJECT-TYPE
                        SYNTAX BITS
                                {
                                allType(0),
                                tagged(1),
                                unTagged(2)
                                }
                        MAX-ACCESS read-write
                        STATUS current
                        DESCRIPTION
                                "Set the Layer 2 interface acceptable frame types.
                                This processing occurs
after VLAN classification.
vlan-tagged Accept only classified frames 
                                which belong to the port's member set.
Hybridge interface only."
                        ::= { fkBridgePortControl 46 }

                
                -- 1.3.6.1.4.1.10428 9 1.101.3.2.2.47
                fkBridgePortControlSwitchNativeVid OBJECT-TYPE
                        SYNTAX Integer32 (1..4094)
                        MAX-ACCESS read-write
                        STATUS current
                        DESCRIPTION
                                "The native VLAN is used for classifying the incoming untagged packets.
                                "
                        ::= { fkBridgePortControl 47 }

                
                -- 1.3.6.1.4.1.10428 9 1.101.3.2.2.48
                fkBridgePortControlSwitchAllowedVlan OBJECT-TYPE
                        SYNTAX OCTET STRING
                        MAX-ACCESS read-write
                        STATUS current
                        DESCRIPTION
                                "Both tagged and untagged
                                frames will be classified over interfaces."
                        ::= { fkBridgePortControl 48 }

                
                -- 1.3.6.1.4.1.10428 9 1.101.3.2.2.49
                fkBridgePortControlSwitchAllowedVlanEtag OBJECT-TYPE
                        SYNTAX OCTET STRING
                        MAX-ACCESS read-write
                        STATUS current
                        DESCRIPTION
                                "egress Port string"
                        ::= { fkBridgePortControl 49 }

                
                -- 1.3.6.1.4.1.10428 9 1.101.3.2.2.50
                fkBridgePortControlSwitchStaticChannelGroup OBJECT-TYPE
                        SYNTAX OCTET STRING
                        MAX-ACCESS read-write
                        STATUS current
                        DESCRIPTION
                                "Static channel group name"
                        ::= { fkBridgePortControl 50 }

                
                -- 1.3.6.1.4.1.10428 9 1.101.3.2.2.51
                fkBridgePortControlSwitchChannelLoadbalance OBJECT-TYPE
                        SYNTAX INTEGER
                                {
                                dstMac(1),
                                srcMac(2),
                                srcDstMac(3),
                                srcIp(4),
                                dstIp(5),
                                srcDstIp(6),
                                srcPort(7),
                                dstPort(8),
                                srcDstPort(9)
                                }
                        MAX-ACCESS read-write
                        STATUS current
                        DESCRIPTION
                                "Channel group hash method."
                        ::= { fkBridgePortControl 51 }

                
--   Node definitions
-- 
-- 1.3.6.1.4.1.10428 9 1.9.8.2.3
                -- 1.3.6.1.4.1.10428 9 1.101.3.2.3
                fkBridgePortNotification OBJECT IDENTIFIER ::= { fkBridgePort 3 }

                
--  1.3.6.1.4.1.10428 9 1.9.8.2.3.1
                -- 1.3.6.1.4.1.10428 9 1.101.3.2.3.1
                fkBridgePortPVidChanged NOTIFICATION-TYPE
                        OBJECTS { fkBridgePortPVid, fkBridgePortControlRequest, fkBridgePortControlTimeStamp, fkBridgePortControlReqResult }
                        STATUS current
                        DESCRIPTION 
                                "PVid changed"
                        ::= { fkBridgePortNotification 1 }

                
--  1.3.6.1.4.1.10428 9 1.9.8.2.3.2
                -- 1.3.6.1.4.1.10428 9 1.101.3.2.3.2
                fkBridgePortMaxHostsChanged NOTIFICATION-TYPE
                        OBJECTS { fkBridgePortMaxHosts, fkBridgePortControlRequest, fkBridgePortControlTimeStamp, fkBridgePortControlReqResult }
                        STATUS current
                        DESCRIPTION 
                                "MaxHosts changed"
                        ::= { fkBridgePortNotification 2 }

                
                -- 1.3.6.1.4.1.10428 9 1.101.3.2.3.3
                fkBridgePortMaxLearnPerUnitChanged NOTIFICATION-TYPE
                        OBJECTS { fkBridgePortControlRequest, fkBridgePortControlTimeStamp, fkBridgePortControlReqResult, fkBridgePortMaxLearnPerUnit }
                        STATUS current
                        DESCRIPTION 
                                "Description."
                        ::= { fkBridgePortNotification 3 }

                
--  1.3.6.1.4.1.10428 9 1.9.8.2.3.3
                -- 1.3.6.1.4.1.10428 9 1.101.3.2.3.4
                fkBridgePortMACFilterPermissionChanged NOTIFICATION-TYPE
                        OBJECTS { fkBridgePortMACFilterPermission, fkBridgePortControlRequest, fkBridgePortControlTimeStamp, fkBridgePortControlReqResult }
                        STATUS current
                        DESCRIPTION 
                                "MAC filter permission changed"
                        ::= { fkBridgePortNotification 4 }

                
--  1.3.6.1.4.1.10428 9 1.9.8.2.3.4
                -- 1.3.6.1.4.1.10428 9 1.101.3.2.3.5
                fkBridgePortMirrorProfileChanged NOTIFICATION-TYPE
                        OBJECTS { fkBridgePortIngMirrorStatus, fkBridgePortEgMirrorStatus, fkBridgePortControlRequest, fkBridgePortControlTimeStamp, fkBridgePortControlReqResult
                                 }
                        STATUS current
                        DESCRIPTION 
                                "Mirror profile changed"
                        ::= { fkBridgePortNotification 5 }

                
--  1.3.6.1.4.1.10428 9 1.9.8.2.3.5
                -- 1.3.6.1.4.1.10428 9 1.101.3.2.3.6
                fkBridgePortBcscThresholdProfileChanged NOTIFICATION-TYPE
                        OBJECTS { fkBridgePortBcastThreshold, fkBridgePortMcastThreshold, fkBridgePortDlfThreshold, fkBridgePortControlRequest, fkBridgePortControlTimeStamp, 
                                fkBridgePortControlReqResult }
                        STATUS current
                        DESCRIPTION 
                                "BCSC threshold profile changed"
                        ::= { fkBridgePortNotification 6 }

                
--  1.3.6.1.4.1.10428 9 1.9.8.2.3.6
                -- 1.3.6.1.4.1.10428 9 1.101.3.2.3.7
                fkBridgePortQinQStatusChanged NOTIFICATION-TYPE
                        OBJECTS { fkBridgePortQinQStatus, fkBridgePortControlRequest, fkBridgePortControlTimeStamp, fkBridgePortControlReqResult }
                        STATUS current
                        DESCRIPTION 
                                "QinQ status changed"
                        ::= { fkBridgePortNotification 7 }

                
--  1.3.6.1.4.1.10428 9 1.9.8.2.3.7
                -- 1.3.6.1.4.1.10428 9 1.101.3.2.3.8
                fkBridgePortLinktypeChanged NOTIFICATION-TYPE
                        OBJECTS { fkBridgePortAdminLinktype, fkBridgePortControlRequest, fkBridgePortControlTimeStamp, fkBridgePortControlReqResult }
                        STATUS current
                        DESCRIPTION 
                                "Admin link-type changed"
                        ::= { fkBridgePortNotification 8 }

                
--  1.3.6.1.4.1.10428 9 1.9.8.2.3.8
                -- 1.3.6.1.4.1.10428 9 1.101.3.2.3.9
                fkBridgePortEdgemodeChanged NOTIFICATION-TYPE
                        OBJECTS { fkBridgePortAdminEdgemode, fkBridgePortControlRequest, fkBridgePortControlTimeStamp, fkBridgePortControlReqResult }
                        STATUS current
                        DESCRIPTION 
                                "Admin edge-mode changed"
                        ::= { fkBridgePortNotification 9 }

                
                -- 1.3.6.1.4.1.10428 9 1.101.3.2.3.10
                fkBridgePortStpBpduFilterChanged NOTIFICATION-TYPE
                        OBJECTS { fkBridgePortStpBpduFilter, fkBridgePortControlTimeStamp, fkBridgePortControlReqResult, fkBridgePortControlRequest }
                        STATUS current
                        DESCRIPTION 
                                "Description."
                        ::= { fkBridgePortNotification 10 }

                
                -- 1.3.6.1.4.1.10428 9 1.101.3.2.3.11
                fkBridgePortPvlanIsolatedStatusChanged NOTIFICATION-TYPE
                        OBJECTS { fkBridgePortPvlanIsolatedStatus, fkBridgePortPvlanPromPorts, fkBridgePortControlRequest, fkBridgePortControlTimeStamp, fkBridgePortControlReqResult
                                 }
                        STATUS current
                        DESCRIPTION 
                                "Description."
                        ::= { fkBridgePortNotification 11 }

                
                -- 1.3.6.1.4.1.10428 9 1.101.3.2.3.12
                fkBridgePortStpBpduGuardErrRcvChanged NOTIFICATION-TYPE
                        OBJECTS { fkBridgePortControlRequest, fkBridgePortControlTimeStamp, fkBridgePortControlReqResult }
                        STATUS current
                        DESCRIPTION 
                                "Description."
                        ::= { fkBridgePortNotification 12 }

                
                -- 1.3.6.1.4.1.10428 9 1.101.3.2.3.13
                fkBridgePortDhcpFilterServerChanged NOTIFICATION-TYPE
                        OBJECTS { fkBridgePortControlRequest, fkBridgePortControlTimeStamp, fkBridgePortControlReqResult, fkBridgePortDhcpFilterServer }
                        STATUS current
                        DESCRIPTION 
                                "Description."
                        ::= { fkBridgePortNotification 13 }

                
                -- 1.3.6.1.4.1.10428 9 1.101.3.2.3.14
                fkBridgePortLoopDetectProfileChanged NOTIFICATION-TYPE
                        OBJECTS { fkBridgePortControlRequest, fkBridgePortControlTimeStamp, fkBridgePortControlReqResult, fkBridgePortLoopDetectStatus, fkBridgePortLoopDetectBlock, 
                                fkBridgePortLoopDetectPeriod, fkBridgePortLoopDetectTimer }
                        STATUS current
                        DESCRIPTION 
                                "Description."
                        ::= { fkBridgePortNotification 14 }

                
                -- 1.3.6.1.4.1.10428 9 1.101.3.2.3.15
                fkBridgePortLoopDetectUnblock NOTIFICATION-TYPE
                        OBJECTS { fkBridgePortControlRequest, fkBridgePortControlTimeStamp, fkBridgePortControlReqResult, fkBridgePortLoopDetectBlockStatus }
                        STATUS current
                        DESCRIPTION 
                                "Description."
                        ::= { fkBridgePortNotification 15 }

                
                -- 1.3.6.1.4.1.10428 9 1.101.3.2.3.16
                fkBridgePortNetBIOSFilterChanged NOTIFICATION-TYPE
                        OBJECTS { fkBridgePortControlRequest, fkBridgePortControlTimeStamp, fkBridgePortControlReqResult, fkBridgePortNetBIOSFilter }
                        STATUS current
                        DESCRIPTION 
                                "Description."
                        ::= { fkBridgePortNotification 16 }

                
                -- 1.3.6.1.4.1.10428 9 1.101.3.2.3.17
                fkBridgePortPushInnertagChanged NOTIFICATION-TYPE
                        OBJECTS { fkBridgePortControlRequest, fkBridgePortControlReqResult, fkBridgePortControlTimeStamp, fkBridgePortControlIndex, fkBridgePortControlPushInnertag
                                 }
                        STATUS current
                        DESCRIPTION 
                                "setBridgePortPushInnertag"
                        ::= { fkBridgePortNotification 17 }

                
                -- 1.3.6.1.4.1.10428 9 1.101.3.2.3.18
                fkBridgePortPopInnertagChanged NOTIFICATION-TYPE
                        OBJECTS { fkBridgePortControlRequest, fkBridgePortControlReqResult, fkBridgePortControlTimeStamp, fkBridgePortControlIndex, fkBridgePortControlPopInnertag
                                 }
                        STATUS current
                        DESCRIPTION 
                                "setBridgePortPopInnertag"
                        ::= { fkBridgePortNotification 18 }

                
                -- 1.3.6.1.4.1.10428 9 1.101.3.2.3.19
                fkBridgePortInnertagChanged NOTIFICATION-TYPE
                        OBJECTS { fkBridgePortControlRequest, fkBridgePortControlReqResult, fkBridgePortControlTimeStamp, fkBridgePortControlIndex, fkBridgePortControlInnertag
                                 }
                        STATUS current
                        DESCRIPTION 
                                "setBridgePortInnertag"
                        ::= { fkBridgePortNotification 19 }

                
                -- 1.3.6.1.4.1.10428 9 1.101.3.2.3.20
                fkBridgePortPriorityChanged NOTIFICATION-TYPE
                        OBJECTS { fkBridgePortControlRequest, fkBridgePortControlReqResult, fkBridgePortControlTimeStamp, fkBridgePortControlIndex, fkBridgePortControlPriority
                                 }
                        STATUS current
                        DESCRIPTION 
                                "setBridgePortPriority"
                        ::= { fkBridgePortNotification 20 }

                
                -- 1.3.6.1.4.1.10428 9 1.101.3.2.3.21
                fkBridgePortInner2outerPriChanged NOTIFICATION-TYPE
                        OBJECTS { fkBridgePortControlRequest, fkBridgePortControlReqResult, fkBridgePortControlTimeStamp, fkBridgePortControlIndex, fkBridgePortControlInner2outerPri
                                 }
                        STATUS current
                        DESCRIPTION 
                                "setBridgePortInner2outerPri"
                        ::= { fkBridgePortNotification 21 }

                
                -- 1.3.6.1.4.1.10428 9 1.101.3.2.3.22
                fkBridgePortInner2outerVidChanged NOTIFICATION-TYPE
                        OBJECTS { fkBridgePortControlRequest, fkBridgePortControlReqResult, fkBridgePortControlTimeStamp, fkBridgePortControlIndex, fkBridgePortControlInner2outerVid
                                 }
                        STATUS current
                        DESCRIPTION 
                                "setBridgePortInner2outerVid"
                        ::= { fkBridgePortNotification 22 }

                
                -- 1.3.6.1.4.1.10428 9 1.101.3.2.3.23
                fkBridgePortMACLearningStatusChanged NOTIFICATION-TYPE
                        OBJECTS { fkBridgePortControlRequest, fkBridgePortControlReqResult, fkBridgePortControlTimeStamp, fkBridgePortControlIndex, fkBridgePortControlMACLearningStatus
                                 }
                        STATUS current
                        DESCRIPTION 
                                "fkBridgePortMACLearningStatus"
                        ::= { fkBridgePortNotification 23 }

                
                -- 1.3.6.1.4.1.10428 9 1.101.3.2.3.24
                fkBridgePortPortBridgeStatusChanged NOTIFICATION-TYPE
                        OBJECTS { fkBridgePortControlRequest, fkBridgePortControlReqResult, fkBridgePortControlTimeStamp, fkBridgePortControlIndex, fkBridgePortControlPortBridgeStatus
                                 }
                        STATUS current
                        DESCRIPTION 
                                "fkBridgePortPortBridgeStatus"
                        ::= { fkBridgePortNotification 24 }

                
                -- 1.3.6.1.4.1.10428 9 1.101.3.2.3.25
                fkBridgePortUnknownMcastBlockChanged NOTIFICATION-TYPE
                        OBJECTS { fkBridgePortControlRequest, fkBridgePortControlTimeStamp, fkBridgePortControlReqResult, fkBridgePortControlIndex, fkBridgePortControlUnknownMcastBlock
                                 }
                        STATUS current
                        DESCRIPTION 
                                "Description."
                        ::= { fkBridgePortNotification 25 }

                
                -- 1.3.6.1.4.1.10428 9 1.101.3.2.3.26
                fkBridgePortDescriptionChanged NOTIFICATION-TYPE
                        OBJECTS { fkBridgePortControlRequest, fkBridgePortControlTimeStamp, fkBridgePortControlReqResult, fkBridgePortControlIndex, fkBridgePortControlDescription
                                 }
                        STATUS current
                        DESCRIPTION 
                                "Description."
                        ::= { fkBridgePortNotification 26 }

                
                -- 1.3.6.1.4.1.10428 9 1.101.3.2.3.27
                fkBridgePortHoldTimeChanged NOTIFICATION-TYPE
                        OBJECTS { fkBridgePortControlRequest, fkBridgePortControlTimeStamp, fkBridgePortControlReqResult, fkBridgePortControlIndex, fkBridgePortControlHoldTime
                                 }
                        STATUS current
                        DESCRIPTION 
                                "Description."
                        ::= { fkBridgePortNotification 27 }

                
                -- 1.3.6.1.4.1.10428 9 1.101.3.2.3.28
                fkBridgePortMacAntiSpoofChanged NOTIFICATION-TYPE
                        OBJECTS { fkBridgePortControlRequest, fkBridgePortControlTimeStamp, fkBridgePortControlReqResult, fkBridgePortControlIndex, fkBridgePortControlMacAntiSpoofing
                                 }
                        STATUS current
                        DESCRIPTION 
                                "Description."
                        ::= { fkBridgePortNotification 28 }

                
                -- 1.3.6.1.4.1.10428 9 1.101.3.2.3.29
                fkBridgePortSwitchStatusChanged NOTIFICATION-TYPE
                        OBJECTS { fkBridgePortControlRequest, fkBridgePortControlTimeStamp, fkBridgePortControlReqResult, fkBridgePortControlIndex, fkBridgePortControlSwitchStatus
                                 }
                        STATUS current
                        DESCRIPTION 
                                "setBridgePortSwitchStatus"
                        ::= { fkBridgePortNotification 29 }

                
                -- 1.3.6.1.4.1.10428 9 1.101.3.2.3.30
                fkBridgePortSwitchModeChanged NOTIFICATION-TYPE
                        OBJECTS { fkBridgePortControlRequest, fkBridgePortControlTimeStamp, fkBridgePortControlReqResult, fkBridgePortControlIndex, fkBridgePortControlSwitchMode, 
                                fkBridgePortControlSwitchSubMode, fkBridgePortControlSwitchIngressFilter }
                        STATUS current
                        DESCRIPTION 
                                "setBridgePortSwitchMode"
                        ::= { fkBridgePortNotification 30 }

                
                -- 1.3.6.1.4.1.10428 9 1.101.3.2.3.31
                fkBridgePortSwitchDefaultVlanChanged NOTIFICATION-TYPE
                        OBJECTS { fkBridgePortControlRequest, fkBridgePortControlTimeStamp, fkBridgePortControlReqResult, fkBridgePortControlIndex, fkBridgePortControlSwitchDefaultVlan
                                 }
                        STATUS current
                        DESCRIPTION 
                                "setBridgePortSwitchDefaultVlan"
                        ::= { fkBridgePortNotification 31 }

                
                -- 1.3.6.1.4.1.10428 9 1.101.3.2.3.32
                fkBridgePortSwitchNativeVlanChanged NOTIFICATION-TYPE
                        OBJECTS { fkBridgePortControlRequest, fkBridgePortControlTimeStamp, fkBridgePortControlReqResult, fkBridgePortControlIndex, fkBridgePortControlSwitchNativeVid
                                 }
                        STATUS current
                        DESCRIPTION 
                                "setBridgePortSwitchNativeVlan"
                        ::= { fkBridgePortNotification 32 }

                
                -- 1.3.6.1.4.1.10428 9 1.101.3.2.3.33
                fkBridgePortSwitchAccFramTypeChanged NOTIFICATION-TYPE
                        OBJECTS { fkBridgePortControlRequest, fkBridgePortControlTimeStamp, fkBridgePortControlReqResult, fkBridgePortControlIndex, fkBridgePortControlSwitchAccFrameType
                                 }
                        STATUS current
                        DESCRIPTION 
                                "setBridgePortSwitchAccFramType"
                        ::= { fkBridgePortNotification 33 }

                
                -- 1.3.6.1.4.1.10428 9 1.101.3.2.3.34
                fkBridgePortSwitchAllowdVlanAdded NOTIFICATION-TYPE
                        OBJECTS { fkBridgePortControlRequest, fkBridgePortControlTimeStamp, fkBridgePortControlReqResult, fkBridgePortControlIndex, fkBridgePortControlSwitchAllowedVlan, 
                                fkBridgePortControlSwitchAllowedVlanEtag }
                        STATUS current
                        DESCRIPTION 
                                "setBridgePortSwitchAddAllowdVlan"
                        ::= { fkBridgePortNotification 34 }

                
                -- 1.3.6.1.4.1.10428 9 1.101.3.2.3.35
                fkBridgePortSwitchAllowdVlanDeleted NOTIFICATION-TYPE
                        OBJECTS { fkBridgePortControlRequest, fkBridgePortControlTimeStamp, fkBridgePortControlReqResult, fkBridgePortControlIndex, fkBridgePortControlSwitchAllowedVlan, 
                                fkBridgePortControlSwitchAllowedVlanEtag }
                        STATUS current
                        DESCRIPTION 
                                "setBridgePortSwitchRemoveAllowdVlan"
                        ::= { fkBridgePortNotification 35 }

                
                -- 1.3.6.1.4.1.10428 9 1.101.3.2.3.36
                fkBridgePortSwitchStaticChannelChanged NOTIFICATION-TYPE
                        OBJECTS { fkBridgePortControlRequest, fkBridgePortControlTimeStamp, fkBridgePortControlReqResult, fkBridgePortControlIndex, fkBridgePortControlSwitchStaticChannelGroup
                                 }
                        STATUS current
                        DESCRIPTION 
                                "setBridgePortSwitchStaticChannel"
                        ::= { fkBridgePortNotification 36 }

                
                -- 1.3.6.1.4.1.10428 9 1.101.3.2.3.37
                fkBridgePortSwitchChannelLoadbalanceChanged NOTIFICATION-TYPE
                        OBJECTS { fkBridgePortControlRequest, fkBridgePortControlTimeStamp, fkBridgePortControlReqResult, fkBridgePortControlIndex, fkBridgePortControlSwitchChannelLoadbalance
                                 }
                        STATUS current
                        DESCRIPTION 
                                "setBridgePortSwitchChannelLoadbalance"
                        ::= { fkBridgePortNotification 37 }

                
--                      ::= { fk 4 }
-- 
-- Node definitions
-- 
-- 1.3.6.1.4.1.10428 9 1.9.8.3
                -- 1.3.6.1.4.1.10428 9 1.101.3.3
                fkVlan OBJECT IDENTIFIER ::= { fkBridge 3 }

                
--  1.3.6.1.4.1.10428 9 1.9.8.3.1
                -- 1.3.6.1.4.1.10428 9 1.101.3.3.1
                fkVlanTable OBJECT-TYPE
                        SYNTAX SEQUENCE OF FkVlanEntry
                        MAX-ACCESS not-accessible
                        STATUS current
                        DESCRIPTION
                                " fk vlan table"
                        ::= { fkVlan 1 }

                
--  1.3.6.1.4.1.10428 9 1.9.8.3.1.1
                -- 1.3.6.1.4.1.10428 9 1.101.3.3.1.1
                fkVlanEntry OBJECT-TYPE
                        SYNTAX FkVlanEntry
                        MAX-ACCESS not-accessible
                        STATUS current
                        DESCRIPTION
                                " key: fkVlanIndex"
                        INDEX { fkVlanIndex }
                        ::= { fkVlanTable 1 }

                
                FkVlanEntry ::=
                        SEQUENCE { 
                                fkVlanIndex
                                        INTEGER,
                                fkVlanIfIndex
                                        Integer32,
                                fkVlanName
                                        OCTET STRING,
                                fkVlanStatus
                                        INTEGER,
                                fkVlanEgressPorts
                                        OCTET STRING,
                                fkVlanUnTaggedPorts
                                        OCTET STRING,
                                fkVlanCreationTime
                                        TimeTicks,
                                fkVlanAgeingTime
                                        INTEGER,
                                fkVlanTagTxCounter
                                        Counter64,
                                fkVlanDescription
                                        OCTET STRING,
                                fkVlanElineEnable
                                        INTEGER,
                                fkVlanOperStatus
                                        INTEGER,
                                fkVlanMtu
                                        Integer32
                         }

--  1.3.6.1.4.1.10428 9 1.9.8.3.1.1.1
                -- 1.3.6.1.4.1.10428 9 1.101.3.3.1.1.1
                fkVlanIndex OBJECT-TYPE
                        SYNTAX INTEGER (1..4094)
                        MAX-ACCESS read-only
                        STATUS current
                        DESCRIPTION
                                "A vlan-identifier."
                        ::= { fkVlanEntry 1 }

                
                -- 1.3.6.1.4.1.10428 9 1.101.3.3.1.1.2
                fkVlanIfIndex OBJECT-TYPE
                        SYNTAX Integer32
                        MAX-ACCESS read-only
                        STATUS current
                        DESCRIPTION
                                "Same as ifIndex (for appropriated ifTable entries)."
                        ::= { fkVlanEntry 2 }

                
--  1.3.6.1.4.1.10428 9 1.9.8.3.1.1.2
                -- 1.3.6.1.4.1.10428 9 1.101.3.3.1.1.3
                fkVlanName OBJECT-TYPE
                        SYNTAX OCTET STRING
                        MAX-ACCESS read-only
                        STATUS current
                        DESCRIPTION
                                "A descriptional name for that vlan."
                        ::= { fkVlanEntry 3 }

                
--  1.3.6.1.4.1.10428 9 1.9.8.3.1.1.3
                -- 1.3.6.1.4.1.10428 9 1.101.3.3.1.1.4
                fkVlanStatus OBJECT-TYPE
                        SYNTAX INTEGER
                                {
                                static(1),
                                dynamic(2)
                                }
                        MAX-ACCESS read-only
                        STATUS current
                        DESCRIPTION
                                "static, in future gvrp"
                        ::= { fkVlanEntry 4 }

                
--  1.3.6.1.4.1.10428 9 1.9.8.3.1.1.4
                -- 1.3.6.1.4.1.10428 9 1.101.3.3.1.1.5
                fkVlanEgressPorts OBJECT-TYPE
                        SYNTAX OCTET STRING
                        MAX-ACCESS read-only
                        STATUS current
                        DESCRIPTION
                                "Portlist for all member of this VLAN, they will send tagged or untagged frames.
                                The octet string is a list of pairs of octets each identify
                                an fkBridgePortIndex. The least significant byte is the
                                second octet."
                        ::= { fkVlanEntry 5 }

                
--  1.3.6.1.4.1.10428 9 1.9.8.3.1.1.5
                -- 1.3.6.1.4.1.10428 9 1.101.3.3.1.1.6
                fkVlanUnTaggedPorts OBJECT-TYPE
                        SYNTAX OCTET STRING
                        MAX-ACCESS read-only
                        STATUS current
                        DESCRIPTION
                                "Portlist for members of this Vlan they will send only untagged frames.
                                The octet string is a list of pairs of octets each identify
                                an fkBridgePortIndex. The least significant byte is the second
                                octet."
                        ::= { fkVlanEntry 6 }

                
--  1.3.6.1.4.1.10428 9 1.9.8.3.1.1.8
                -- 1.3.6.1.4.1.10428 9 1.101.3.3.1.1.7
                fkVlanCreationTime OBJECT-TYPE
                        SYNTAX TimeTicks
                        MAX-ACCESS read-only
                        STATUS current
                        DESCRIPTION
                                "Only useful in case of gvrp."
                        ::= { fkVlanEntry 7 }

                
                -- 1.3.6.1.4.1.10428 9 1.101.3.3.1.1.8
                fkVlanAgeingTime OBJECT-TYPE
                        SYNTAX INTEGER (-1 | 0 | 10..21474830)
                        MAX-ACCESS read-only
                        STATUS current
                        DESCRIPTION
                                "The ageing time per vlan"
                        ::= { fkVlanEntry 8 }

                
                -- 1.3.6.1.4.1.10428 9 1.101.3.3.1.1.9
                fkVlanTagTxCounter OBJECT-TYPE
                        SYNTAX Counter64
                        MAX-ACCESS read-only
                        STATUS current
                        DESCRIPTION
                                "The VLAN tag tx counter."
                        ::= { fkVlanEntry 9 }

                
                -- 1.3.6.1.4.1.10428 9 1.101.3.3.1.1.10
                fkVlanDescription OBJECT-TYPE
                        SYNTAX OCTET STRING (SIZE (0..32))
                        MAX-ACCESS read-only
                        STATUS current
                        DESCRIPTION
                                "createVlan:
                                (fkVlanControlIndex)
                                fkVlanControlName
                                fkVlanControlMulticastPermision"
                        ::= { fkVlanEntry 10 }

                
                -- 1.3.6.1.4.1.10428 9 1.101.3.3.1.1.11
                fkVlanElineEnable OBJECT-TYPE
                        SYNTAX INTEGER
                                {
                                disable(0),
                                enable(1)
                                }
                        MAX-ACCESS read-only
                        STATUS current
                        DESCRIPTION
                                "Indicate whether E-line service enable or not"
                        ::= { fkVlanEntry 11 }

                
                -- 1.3.6.1.4.1.10428 9 1.101.3.3.1.1.12
                fkVlanOperStatus OBJECT-TYPE
                        SYNTAX INTEGER
                                {
                                invalid(0),
                                inactive(1),
                                active(2)
                                }
                        MAX-ACCESS read-only
                        STATUS current
                        DESCRIPTION
                                "The Vlan operation status."
                        ::= { fkVlanEntry 12 }

                
                -- 1.3.6.1.4.1.10428 9 1.101.3.3.1.1.13
                fkVlanMtu OBJECT-TYPE
                        SYNTAX Integer32
                        MAX-ACCESS read-only
                        STATUS current
                        DESCRIPTION
                                "The Vlan MTU."
                        ::= { fkVlanEntry 13 }

                
--  1.3.6.1.4.1.10428 9 1.9.8.3.2
                -- 1.3.6.1.4.1.10428 9 1.101.3.3.2
                fkVlanControl OBJECT IDENTIFIER ::= { fkVlan 2 }

                
--   Node definitions
-- 
-- 1.3.6.1.4.1.10428 9 1.9.8.3.2.1
                -- 1.3.6.1.4.1.10428 9 1.101.3.3.2.1
                fkVlanControlRequest OBJECT-TYPE
                        SYNTAX INTEGER
                                {
                                createVlan(1),
                                destroyVlan(2),
                                setVlanPortProfile(3),
                                setVlanAgeingTime(4),
                                createVlanRange(5),
                                setVlanDesc(6),
                                createElineVlan(7),
                                setVlanOperStatus(8),
                                setVlanMtu(9)
                                }
                        MAX-ACCESS read-write
                        STATUS current
                        DESCRIPTION
                                "
                                createVlan:
                                (fkVlanControlIndex)
                                fkVlanControlName
                                fkVlanControlMulticastPermision
                                
                                destroyVlan:
                                fkVlanControlIndex
                                
                                setVlanPortProfile:
                                fkVlanControlIndex
                                fkVlanControlEgressPorts
                                fkVlanControlUnTaggedPorts
                                
                                setVlanMulticastPermission:
                                fkVlanControlIndex
                                fkVlanControlMulticastPermission
                                
                                "
                        ::= { fkVlanControl 1 }

                
--  1.3.6.1.4.1.10428 9 1.9.8.3.2.3
                -- 1.3.6.1.4.1.10428 9 1.101.3.3.2.2
                fkVlanControlStatus OBJECT-TYPE
                        SYNTAX FkControlStatusType
                        MAX-ACCESS read-only
                        STATUS current
                        DESCRIPTION
                                "The status of a user command. 
                                "
                        ::= { fkVlanControl 2 }

                
--  1.3.6.1.4.1.10428 9 1.9.8.3.2.4
                -- 1.3.6.1.4.1.10428 9 1.101.3.3.2.3
                fkVlanControlTimer OBJECT-TYPE
                        SYNTAX Gauge32
                        MAX-ACCESS read-write
                        STATUS current
                        DESCRIPTION
                                "The maximum wait time for the manager for a long running user command. 
                                "
                        ::= { fkVlanControl 3 }

                
--  1.3.6.1.4.1.10428 9 1.9.8.3.2.6
                -- 1.3.6.1.4.1.10428 9 1.101.3.3.2.4
                fkVlanControlTimeStamp OBJECT-TYPE
                        SYNTAX TimeTicks
                        MAX-ACCESS read-only
                        STATUS current
                        DESCRIPTION
                                "The time stamp of the last command (end of command)."
                        ::= { fkVlanControl 4 }

                
--  1.3.6.1.4.1.10428 9 1.9.8.3.2.5
                -- 1.3.6.1.4.1.10428 9 1.101.3.3.2.5
                fkVlanControlReqResult OBJECT-TYPE
                        SYNTAX FkControlRequestResultType
                        MAX-ACCESS read-only
                        STATUS current
                        DESCRIPTION
                                "The result of the last user command."
                        ::= { fkVlanControl 5 }

                
--  1.3.6.1.4.1.10428 9 1.9.8.3.2.2
                -- 1.3.6.1.4.1.10428 9 1.101.3.3.2.6
                fkVlanControlIndex OBJECT-TYPE
                        SYNTAX Integer32 (1..4094)
                        MAX-ACCESS read-write
                        STATUS current
                        DESCRIPTION
                                "Vlan's ID
                                "
                        ::= { fkVlanControl 6 }

                
--  1.3.6.1.4.1.10428 9 1.9.8.3.2.7
                -- 1.3.6.1.4.1.10428 9 1.101.3.3.2.7
                fkVlanControlName OBJECT-TYPE
                        SYNTAX OCTET STRING
                        MAX-ACCESS read-write
                        STATUS current
                        DESCRIPTION
                                "Vlan's name."
                        ::= { fkVlanControl 7 }

                
--  1.3.6.1.4.1.10428 9 1.9.8.3.2.8
                -- 1.3.6.1.4.1.10428 9 1.101.3.3.2.8
                fkVlanControlEgressPorts OBJECT-TYPE
                        SYNTAX OCTET STRING
                        MAX-ACCESS read-write
                        STATUS current
                        DESCRIPTION
                                " Portlist for all member of this VLAN, they will send tagged or untagged frames. The OctetString is a list of pairs of octets each identify an sheBridgePortIndex. The least significant byte is the second octet."
                        ::= { fkVlanControl 8 }

                
--  1.3.6.1.4.1.10428 9 1.9.8.3.2.9
                -- 1.3.6.1.4.1.10428 9 1.101.3.3.2.9
                fkVlanControlUnTaggedPorts OBJECT-TYPE
                        SYNTAX OCTET STRING
                        MAX-ACCESS read-write
                        STATUS current
                        DESCRIPTION
                                " Portlist for members of this Vlan they will send only untagged frames. The OctetString is a list of pairs of octets each identify an fkBridgePortIndex. The least significant byte is the second octet."
                        ::= { fkVlanControl 9 }

                
                -- 1.3.6.1.4.1.10428 9 1.101.3.3.2.10
                fkVlanControlAgeingTime OBJECT-TYPE
                        SYNTAX INTEGER (-1 | 0 | 10..21474830)
                        MAX-ACCESS read-write
                        STATUS current
                        DESCRIPTION
                                "The ageing time per vlan
                                (supported only model 5924N)"
                        ::= { fkVlanControl 10 }

                
                -- 1.3.6.1.4.1.10428 9 1.101.3.3.2.11
                fkVlanControlIndexTo OBJECT-TYPE
                        SYNTAX Integer32 (1..4094)
                        MAX-ACCESS read-write
                        STATUS current
                        DESCRIPTION
                                "Vlan's ID
                                "
                        ::= { fkVlanControl 11 }

                
                -- 1.3.6.1.4.1.10428 9 1.101.3.3.2.12
                fkVlanControlDescription OBJECT-TYPE
                        SYNTAX OCTET STRING (SIZE (0..32))
                        MAX-ACCESS read-write
                        STATUS current
                        DESCRIPTION
                                "createVlan:
                                (fkVlanControlIndex)
                                fkVlanControlName
                                fkVlanControlMulticastPermision"
                        ::= { fkVlanControl 12 }

                
                -- 1.3.6.1.4.1.10428 9 1.101.3.3.2.13
                fkVlanControlElineEnable OBJECT-TYPE
                        SYNTAX INTEGER
                                {
                                disable(0),
                                enable(1)
                                }
                        MAX-ACCESS read-write
                        STATUS current
                        DESCRIPTION
                                "Indicate whether E-line service enable or not"
                        ::= { fkVlanControl 13 }

                
                -- 1.3.6.1.4.1.10428 9 1.101.3.3.2.14
                fkVlanControlOperStatus OBJECT-TYPE
                        SYNTAX INTEGER
                                {
                                invalid(0),
                                inactive(1),
                                active(2)
                                }
                        MAX-ACCESS read-write
                        STATUS current
                        DESCRIPTION
                                "The Vlan operation status."
                        ::= { fkVlanControl 14 }

                
                -- 1.3.6.1.4.1.10428 9 1.101.3.3.2.15
                fkVlanControlMtu OBJECT-TYPE
                        SYNTAX Integer32
                        MAX-ACCESS read-write
                        STATUS current
                        DESCRIPTION
                                "The Vlan MTU."
                        ::= { fkVlanControl 15 }

                
--  1.3.6.1.4.1.10428 9 1.9.8.3.3
                -- 1.3.6.1.4.1.10428 9 1.101.3.3.3
                fkVlanNotification OBJECT IDENTIFIER ::= { fkVlan 3 }

                
--  1.3.6.1.4.1.10428 9 1.9.8.3.3.1
                -- 1.3.6.1.4.1.10428 9 1.101.3.3.3.1
                fkVlanCreated NOTIFICATION-TYPE
                        OBJECTS { fkVlanName, fkVlanEgressPorts, fkVlanUnTaggedPorts, fkVlanControlRequest, fkVlanControlTimeStamp, 
                                fkVlanControlReqResult, fkVlanIfIndex, fkVlanStatus }
                        STATUS current
                        DESCRIPTION 
                                "Description."
                        ::= { fkVlanNotification 1 }

                
--  1.3.6.1.4.1.10428 9 1.9.8.3.3.2
                -- 1.3.6.1.4.1.10428 9 1.101.3.3.3.2
                fkVlanDestroyed NOTIFICATION-TYPE
                        OBJECTS { fkVlanControlRequest, fkVlanControlTimeStamp, fkVlanControlReqResult, fkVlanControlIndex }
                        STATUS current
                        DESCRIPTION 
                                " "
                        ::= { fkVlanNotification 2 }

                
--  1.3.6.1.4.1.10428 9 1.9.8.3.3.3
                -- 1.3.6.1.4.1.10428 9 1.101.3.3.3.3
                fkVlanPortProfileChanged NOTIFICATION-TYPE
                        OBJECTS { fkVlanEgressPorts, fkVlanUnTaggedPorts, fkVlanControlRequest, fkVlanControlTimeStamp, fkVlanControlReqResult
                                 }
                        STATUS current
                        DESCRIPTION 
                                " "
                        ::= { fkVlanNotification 3 }

                
                -- 1.3.6.1.4.1.10428 9 1.101.3.3.3.4
                fkVlanAgeingTimeChanged NOTIFICATION-TYPE
                        OBJECTS { fkVlanControlRequest, fkVlanControlTimeStamp, fkVlanControlAgeingTime, fkVlanControlIndex, fkVlanControlReqResult
                                 }
                        STATUS current
                        DESCRIPTION 
                                "Description."
                        ::= { fkVlanNotification 4 }

                
                -- 1.3.6.1.4.1.10428 9 1.101.3.3.3.5
                fkVlanRangeCreated NOTIFICATION-TYPE
                        OBJECTS { fkVlanControlRequest, fkVlanControlTimeStamp, fkVlanControlReqResult, fkVlanControlIndex, fkVlanControlIndexTo
                                 }
                        STATUS current
                        DESCRIPTION 
                                "Description."
                        ::= { fkVlanNotification 5 }

                
                -- 1.3.6.1.4.1.10428 9 1.101.3.3.3.6
                fkVlanDescriptionChanged NOTIFICATION-TYPE
                        OBJECTS { fkVlanControlRequest, fkVlanControlTimeStamp, fkVlanControlReqResult, fkVlanControlIndex, fkVlanControlDescription
                                 }
                        STATUS current
                        DESCRIPTION 
                                "setVlanDesc"
                        ::= { fkVlanNotification 6 }

                
                -- 1.3.6.1.4.1.10428 9 1.101.3.3.3.7
                fkVlanElineVlanCreated NOTIFICATION-TYPE
                        OBJECTS { fkVlanControlRequest, fkVlanControlTimeStamp, fkVlanControlReqResult, fkVlanControlIndex, fkVlanControlElineEnable
                                 }
                        STATUS current
                        DESCRIPTION 
                                "createElineVlan"
                        ::= { fkVlanNotification 7 }

                
                -- 1.3.6.1.4.1.10428 9 1.101.3.3.3.8
                fkVlanOperStatusChagned NOTIFICATION-TYPE
                        OBJECTS { fkVlanControlRequest, fkVlanControlTimeStamp, fkVlanControlReqResult, fkVlanControlIndex, fkVlanControlOperStatus
                                 }
                        STATUS current
                        DESCRIPTION 
                                "setVlanOperStatus"
                        ::= { fkVlanNotification 8 }

                
                -- 1.3.6.1.4.1.10428 9 1.101.3.3.3.9
                fkVlanMtuChagned NOTIFICATION-TYPE
                        OBJECTS { fkVlanControlRequest, fkVlanControlTimeStamp, fkVlanControlReqResult, fkVlanControlIndex, fkVlanControlMtu
                                 }
                        STATUS current
                        DESCRIPTION 
                                "fkVlanMtuChanged"
                        ::= { fkVlanNotification 9 }

                
--   fkVlanMap Group
-- 1.3.6.1.4.1.10428 9 1.9.8.4
                -- 1.3.6.1.4.1.10428 9 1.101.3.4
                fkVlanMap OBJECT IDENTIFIER ::= { fkBridge 4 }

                
--  1.3.6.1.4.1.10428 9 1.9.8.4.1
                -- 1.3.6.1.4.1.10428 9 1.101.3.4.1
                fkVlanMapTable OBJECT-TYPE
                        SYNTAX SEQUENCE OF FkVlanMapEntry
                        MAX-ACCESS not-accessible
                        STATUS current
                        DESCRIPTION
                                "vlan map table."
                        ::= { fkVlanMap 1 }

                
--  1.3.6.1.4.1.10428 9 1.9.8.4.1.1
                -- 1.3.6.1.4.1.10428 9 1.101.3.4.1.1
                fkVlanMapEntry OBJECT-TYPE
                        SYNTAX FkVlanMapEntry
                        MAX-ACCESS not-accessible
                        STATUS current
                        DESCRIPTION
                                " key: fkVlanIndex"
                        INDEX { fkVlanIndex }
                        ::= { fkVlanMapTable 1 }

                
                FkVlanMapEntry ::=
                        SEQUENCE { 
                                fkVlanMapFid
                                        Unsigned32,
                                fkVlanMapStpId
                                        Unsigned32,
                                fkVlanMapErpDomainId
                                        Unsigned32
                         }

--  1.3.6.1.4.1.10428 9 1.9.8.4.1.1.2
                -- 1.3.6.1.4.1.10428 9 1.101.3.4.1.1.1
                fkVlanMapFid OBJECT-TYPE
                        SYNTAX Unsigned32
                        MAX-ACCESS read-only
                        STATUS current
                        DESCRIPTION
                                "Index of the used Filtering Table entry."
                        ::= { fkVlanMapEntry 1 }

                
--  1.3.6.1.4.1.10428 9 1.9.8.4.1.1.3
                -- 1.3.6.1.4.1.10428 9 1.101.3.4.1.1.2
                fkVlanMapStpId OBJECT-TYPE
                        SYNTAX Unsigned32
                        MAX-ACCESS read-only
                        STATUS current
                        DESCRIPTION
                                "Index of the used STP instance."
                        ::= { fkVlanMapEntry 2 }

                
--  1.3.6.1.4.1.10428 9 1.9.8.4.1.1.4
                -- 1.3.6.1.4.1.10428 9 1.101.3.4.1.1.3
                fkVlanMapErpDomainId OBJECT-TYPE
                        SYNTAX Unsigned32
                        MAX-ACCESS read-only
                        STATUS current
                        DESCRIPTION
                                "Index of the used Erp Domain."
                        ::= { fkVlanMapEntry 3 }

                
--  1.3.6.1.4.1.10428 9 1.9.8.4.2
                -- 1.3.6.1.4.1.10428 9 1.101.3.4.2
                fkVlanMapControl OBJECT IDENTIFIER ::= { fkVlanMap 2 }

                
--   Node definitions
-- 
-- 1.3.6.1.4.1.10428 9 1.9.8.4.2.1
                -- 1.3.6.1.4.1.10428 9 1.101.3.4.2.1
                fkVlanMapControlRequest OBJECT-TYPE
                        SYNTAX INTEGER
                                {
                                setVlanMapFid(1),
                                setVlanMapStpId(2),
                                setVlanMapErpDomainId(3)
                                }
                        MAX-ACCESS read-write
                        STATUS current
                        DESCRIPTION
                                "
                                setVlanMapFid:
                                fkVlanMapControlIndex
                                fkVlanMapFid
                                
                                setVlanMapStpId:
                                fkVlanMapControlIndex
                                fkVlanMapStpId
                                
                                setVlanMapErpDomainId:
                                fkVlanMapControlIndex
                                fkVlanMapErpDomainId
                                
                                "
                        ::= { fkVlanMapControl 1 }

                
--  1.3.6.1.4.1.10428 9 1.9.8.4.2.3
                -- 1.3.6.1.4.1.10428 9 1.101.3.4.2.2
                fkVlanMapControlStatus OBJECT-TYPE
                        SYNTAX FkControlStatusType
                        MAX-ACCESS read-only
                        STATUS current
                        DESCRIPTION
                                "The status of a user command. 
                                "
                        ::= { fkVlanMapControl 2 }

                
--  1.3.6.1.4.1.10428 9 1.9.8.4.2.4
                -- 1.3.6.1.4.1.10428 9 1.101.3.4.2.3
                fkVlanMapControlTimer OBJECT-TYPE
                        SYNTAX Gauge32
                        MAX-ACCESS read-write
                        STATUS current
                        DESCRIPTION
                                "The maximum wait time for the manager for a long running user command. 
                                "
                        ::= { fkVlanMapControl 3 }

                
--  1.3.6.1.4.1.10428 9 1.9.8.4.2.6
                -- 1.3.6.1.4.1.10428 9 1.101.3.4.2.4
                fkVlanMapControlTimeStamp OBJECT-TYPE
                        SYNTAX TimeTicks
                        MAX-ACCESS read-only
                        STATUS current
                        DESCRIPTION
                                "The time stamp of the last command (end of command)."
                        ::= { fkVlanMapControl 4 }

                
--  1.3.6.1.4.1.10428 9 1.9.8.4.2.5
                -- 1.3.6.1.4.1.10428 9 1.101.3.4.2.5
                fkVlanMapControlReqResult OBJECT-TYPE
                        SYNTAX FkControlRequestResultType
                        MAX-ACCESS read-only
                        STATUS current
                        DESCRIPTION
                                "The result of the last user command."
                        ::= { fkVlanMapControl 5 }

                
--  1.3.6.1.4.1.10428 9 1.9.8.4.2.2
                -- 1.3.6.1.4.1.10428 9 1.101.3.4.2.6
                fkVlanMapControlIndex OBJECT-TYPE
                        SYNTAX Integer32 (1..4094)
                        MAX-ACCESS read-write
                        STATUS current
                        DESCRIPTION
                                "vlan map index."
                        ::= { fkVlanMapControl 6 }

                
--  1.3.6.1.4.1.10428 9 1.9.8.4.2.7
                -- 1.3.6.1.4.1.10428 9 1.101.3.4.2.7
                fkVlanMapControlFid OBJECT-TYPE
                        SYNTAX Unsigned32
                        MAX-ACCESS read-write
                        STATUS current
                        DESCRIPTION
                                " FDB identifier"
                        ::= { fkVlanMapControl 7 }

                
--  1.3.6.1.4.1.10428 9 1.9.8.4.2.8
                -- 1.3.6.1.4.1.10428 9 1.101.3.4.2.8
                fkVlanMapControlStpId OBJECT-TYPE
                        SYNTAX Unsigned32
                        MAX-ACCESS read-write
                        STATUS current
                        DESCRIPTION
                                " STP Instance Identifier"
                        ::= { fkVlanMapControl 8 }

                
--  1.3.6.1.4.1.10428 9 1.9.8.4.2.9
                -- 1.3.6.1.4.1.10428 9 1.101.3.4.2.9
                fkVlanMapControlErpDomainId OBJECT-TYPE
                        SYNTAX Unsigned32
                        MAX-ACCESS read-write
                        STATUS current
                        DESCRIPTION
                                " The Erp Domain ID."
                        ::= { fkVlanMapControl 9 }

                
--  1.3.6.1.4.1.10428 9 1.9.8.4.3
                -- 1.3.6.1.4.1.10428 9 1.101.3.4.3
                fkVlanMapNotification OBJECT IDENTIFIER ::= { fkVlanMap 3 }

                
--  1.3.6.1.4.1.10428 9 1.9.8.4.3.1
                -- 1.3.6.1.4.1.10428 9 1.101.3.4.3.1
                fkVlanMapFidChanged NOTIFICATION-TYPE
                        OBJECTS { fkVlanMapControlTimeStamp, fkVlanMapControlReqResult, fkVlanMapControlRequest, fkVlanMapFid }
                        STATUS current
                        DESCRIPTION 
                                " "
                        ::= { fkVlanMapNotification 1 }

                
--  1.3.6.1.4.1.10428 9 1.9.8.4.3.2
                -- 1.3.6.1.4.1.10428 9 1.101.3.4.3.2
                fkVlanMapStpIdChanged NOTIFICATION-TYPE
                        OBJECTS { fkVlanMapStpId, fkVlanMapControlRequest, fkVlanMapControlTimeStamp, fkVlanMapControlReqResult }
                        STATUS current
                        DESCRIPTION 
                                " "
                        ::= { fkVlanMapNotification 2 }

                
--  1.3.6.1.4.1.10428 9 1.9.8.4.3.3
                -- 1.3.6.1.4.1.10428 9 1.101.3.4.3.3
                fkVlanMapErpDomainIdChanged NOTIFICATION-TYPE
                        OBJECTS { fkVlanMapErpDomainId, fkVlanMapControlRequest, fkVlanMapControlTimeStamp, fkVlanMapControlReqResult }
                        STATUS current
                        DESCRIPTION 
                                " "
                        ::= { fkVlanMapNotification 3 }

                
-- 
--   Node definitions
-- 
                -- 1.3.6.1.4.1.10428 9 1.101.3.5
                fkStp OBJECT IDENTIFIER ::= { fkBridge 5 }

                
                -- 1.3.6.1.4.1.10428 9 1.101.3.5.1
                fkStpInfo OBJECT IDENTIFIER ::= { fkStp 1 }

                
                -- 1.3.6.1.4.1.10428 9 1.101.3.5.1.1
                fkStpOperationMode OBJECT-TYPE
                        SYNTAX INTEGER
                                {
                                stp(0),
                                rstp(1),
                                mstp(3),
                                pvstp(4),
                                pvrstp(5),
                                pvrstpPlus(6),
                                pvstpPlus(7)
                                }
                        MAX-ACCESS read-only
                        STATUS current
                        DESCRIPTION
                                "The operation mode of running the STP at the switch."
                        ::= { fkStpInfo 1 }

                
                -- 1.3.6.1.4.1.10428 9 1.101.3.5.1.2
                fkStpFormatSelector OBJECT-TYPE
                        SYNTAX INTEGER (0..65535)
                        MAX-ACCESS read-only
                        STATUS current
                        DESCRIPTION
                                "The MST configuration format selector."
                        ::= { fkStpInfo 2 }

                
                -- 1.3.6.1.4.1.10428 9 1.101.3.5.1.3
                fkStpConfigureName OBJECT-TYPE
                        SYNTAX OCTET STRING (SIZE (0..32))
                        MAX-ACCESS read-write
                        STATUS current
                        DESCRIPTION
                                "The MST configuration name of at most 32 characters."
                        ::= { fkStpInfo 3 }

                
                -- 1.3.6.1.4.1.10428 9 1.101.3.5.1.4
                fkStpRevisionLevel OBJECT-TYPE
                        SYNTAX INTEGER (0..65535)
                        MAX-ACCESS read-only
                        STATUS current
                        DESCRIPTION
                                "The MST configuration revision."
                        ::= { fkStpInfo 4 }

                
                -- 1.3.6.1.4.1.10428 9 1.101.3.5.1.5
                fkStpFwdDelay OBJECT-TYPE
                        SYNTAX INTEGER (4..300)
                        MAX-ACCESS read-only
                        STATUS current
                        DESCRIPTION
                                "The STP bridge forward delay."
                        ::= { fkStpInfo 5 }

                
                -- 1.3.6.1.4.1.10428 9 1.101.3.5.1.6
                fkStpHelloTime OBJECT-TYPE
                        SYNTAX INTEGER (1..10)
                        MAX-ACCESS read-only
                        STATUS current
                        DESCRIPTION
                                "The STP bridge hello time."
                        ::= { fkStpInfo 6 }

                
                -- 1.3.6.1.4.1.10428 9 1.101.3.5.1.7
                fkStpMaxAge OBJECT-TYPE
                        SYNTAX INTEGER (6..40)
                        MAX-ACCESS read-only
                        STATUS current
                        DESCRIPTION
                                "The STP bridge max age."
                        ::= { fkStpInfo 7 }

                
                -- 1.3.6.1.4.1.10428 9 1.101.3.5.1.8
                fkStpMaxHops OBJECT-TYPE
                        SYNTAX INTEGER (1..40)
                        MAX-ACCESS read-only
                        STATUS current
                        DESCRIPTION
                                "The MST bridge max hops."
                        ::= { fkStpInfo 8 }

                
                -- 1.3.6.1.4.1.10428 9 1.101.3.5.1.9
                fkStpExtRootBridgeId OBJECT-TYPE
                        SYNTAX OCTET STRING (SIZE (8))
                        MAX-ACCESS read-only
                        STATUS current
                        DESCRIPTION
                                "The MST CST root identifier."
                        ::= { fkStpInfo 9 }

                
                -- 1.3.6.1.4.1.10428 9 1.101.3.5.1.10
                fkStpExtPathcost OBJECT-TYPE
                        SYNTAX Unsigned32
                        MAX-ACCESS read-only
                        STATUS current
                        DESCRIPTION
                                "The MST CST root path cost."
                        ::= { fkStpInfo 10 }

                
                -- 1.3.6.1.4.1.10428 9 1.101.3.5.1.11
                fkStpBpduGuardMode OBJECT-TYPE
                        SYNTAX INTEGER
                                {
                                disable(0),
                                enable(1)
                                }
                        MAX-ACCESS read-only
                        STATUS current
                        DESCRIPTION
                                "Indicates the mode of Bpdu Guard Feature on the switch. 
                                        When the system with Bpdu Guard enabled 
                                        receives a BPDU from any port, that port is 
                                        immediately disabled.    
                                        
                                        disable -- the Bpdu Guard feature is disabled on this
                                                   switch.
                                        
                                        enable -- the Bpdu Guard feature is enabled on this
                                                   switch. 
                                        
                                                   Whether the Bpdu Guard feature is enabled
                                                   or not on this switch depends on the object
                                                   value of fkStpControlBpduGuardMode."
                        DEFVAL { disable }
                        ::= { fkStpInfo 11 }

                
                -- 1.3.6.1.4.1.10428 9 1.101.3.5.1.12
                fkStpBpduGuardAutoRcvMode OBJECT-TYPE
                        SYNTAX INTEGER
                                {
                                disable(0),
                                enable(1)
                                }
                        MAX-ACCESS read-only
                        STATUS current
                        DESCRIPTION
                                "Indicates the automatic recovery mode for the ports disabled by Bpdu Guard.
                                        
                                        disable -- the Bpdu Guard Auto Recovery feature is disabled on this
                                                   switch.
                                        
                                        enable -- the Bpdu Guard Auto Recovery feature is enabled on this
                                                   switch. 
                                        
                                                   Whether the Bpdu Guard Auto Recovery feature is enabled
                                                   or not on this switch depends on the object
                                                   value of fkStpControlBpduGuardAutoRcvMode."
                        DEFVAL { disable }
                        ::= { fkStpInfo 12 }

                
                -- 1.3.6.1.4.1.10428 9 1.101.3.5.1.13
                fkStpBpduGuardAutoRcvTime OBJECT-TYPE
                        SYNTAX INTEGER (10..1000000)
                        MAX-ACCESS read-only
                        STATUS current
                        DESCRIPTION
                                "Indicates the automatic recovery time for the ports disabled by Bpdu Guard.
                                        Unit: second
                                        
                                The Bpdu Guard Auto Recovery time depends on the object value 
                                        of fkStpControlBpduGuardAutoRcvTime."
                        DEFVAL { 300 }
                        ::= { fkStpInfo 13 }

                
                -- 1.3.6.1.4.1.10428 9 1.101.3.5.2
                fkStpControl OBJECT IDENTIFIER ::= { fkStp 2 }

                
                -- 1.3.6.1.4.1.10428 9 1.101.3.5.2.1
                fkStpControlRequest OBJECT-TYPE
                        SYNTAX INTEGER
                                {
                                setStpOperationMode(1),
                                setStpConfigureProfile(2),
                                setStpTimerProfile(3),
                                setStpBpduGuardProfile(4)
                                }
                        MAX-ACCESS read-write
                        STATUS current
                        DESCRIPTION
                                "
                                setStpOperationMode:
                                fkStpControlOperationMode
                                
                                setStpConfigureProfile:
                                fkStpControlConfigureName
                                fkStpControlRevisionLevel
                                
                                setStpTimerProfile
                                fkStpControlFwdDelay
                                fkStpControlHelloTime
                                fkStpControlMaxAge
                                fkStpControlMaxHops
                                "
                        ::= { fkStpControl 1 }

                
                -- 1.3.6.1.4.1.10428 9 1.101.3.5.2.2
                fkStpControlStatus OBJECT-TYPE
                        SYNTAX FkControlStatusType
                        MAX-ACCESS read-only
                        STATUS current
                        DESCRIPTION
                                "The status of a user command. 
                                "
                        ::= { fkStpControl 2 }

                
                -- 1.3.6.1.4.1.10428 9 1.101.3.5.2.3
                fkStpControlTimer OBJECT-TYPE
                        SYNTAX Gauge32
                        MAX-ACCESS read-write
                        STATUS current
                        DESCRIPTION
                                "The maximum wait time for the manager for a long running user command. 
                                "
                        ::= { fkStpControl 3 }

                
                -- 1.3.6.1.4.1.10428 9 1.101.3.5.2.4
                fkStpControlTimeStamp OBJECT-TYPE
                        SYNTAX TimeTicks
                        MAX-ACCESS read-only
                        STATUS current
                        DESCRIPTION
                                "The time stamp of the last command (end of command)."
                        ::= { fkStpControl 4 }

                
                -- 1.3.6.1.4.1.10428 9 1.101.3.5.2.5
                fkStpControlReqResult OBJECT-TYPE
                        SYNTAX FkControlRequestResultType
                        MAX-ACCESS read-only
                        STATUS current
                        DESCRIPTION
                                "The result of the last user command."
                        ::= { fkStpControl 5 }

                
                -- 1.3.6.1.4.1.10428 9 1.101.3.5.2.6
                fkStpControlOperationMode OBJECT-TYPE
                        SYNTAX INTEGER
                                {
                                stp(0),
                                rstp(1),
                                mstp(3),
                                pvstp(4),
                                pvrstp(5),
                                pvrstpPlus(6),
                                pvstpPlus(7)
                                }
                        MAX-ACCESS read-write
                        STATUS current
                        DESCRIPTION
                                " The operation mode of running the STP at the switch."
                        ::= { fkStpControl 6 }

                
                -- 1.3.6.1.4.1.10428 9 1.101.3.5.2.7
                fkStpControlConfigureName OBJECT-TYPE
                        SYNTAX OCTET STRING (SIZE (0..32))
                        MAX-ACCESS read-write
                        STATUS current
                        DESCRIPTION
                                " The MST configuration name of at most 32 characters."
                        ::= { fkStpControl 7 }

                
                -- 1.3.6.1.4.1.10428 9 1.101.3.5.2.8
                fkStpControlRevisionLevel OBJECT-TYPE
                        SYNTAX INTEGER (0..65535)
                        MAX-ACCESS read-write
                        STATUS current
                        DESCRIPTION
                                " The MST configuration revision."
                        ::= { fkStpControl 8 }

                
                -- 1.3.6.1.4.1.10428 9 1.101.3.5.2.9
                fkStpControlFwdDelay OBJECT-TYPE
                        SYNTAX INTEGER (4..30)
                        MAX-ACCESS read-write
                        STATUS current
                        DESCRIPTION
                                " The STP bridge forward delay."
                        ::= { fkStpControl 9 }

                
                -- 1.3.6.1.4.1.10428 9 1.101.3.5.2.10
                fkStpControlHelloTime OBJECT-TYPE
                        SYNTAX INTEGER (1..10)
                        MAX-ACCESS read-write
                        STATUS current
                        DESCRIPTION
                                " The STP bridge hello time."
                        ::= { fkStpControl 10 }

                
                -- 1.3.6.1.4.1.10428 9 1.101.3.5.2.11
                fkStpControlMaxAge OBJECT-TYPE
                        SYNTAX INTEGER (4..60)
                        MAX-ACCESS read-write
                        STATUS current
                        DESCRIPTION
                                " The STP bridge max age."
                        ::= { fkStpControl 11 }

                
                -- 1.3.6.1.4.1.10428 9 1.101.3.5.2.12
                fkStpControlMaxHops OBJECT-TYPE
                        SYNTAX INTEGER (1..40)
                        MAX-ACCESS read-write
                        STATUS current
                        DESCRIPTION
                                " The MST bridge max hops."
                        ::= { fkStpControl 12 }

                
                -- 1.3.6.1.4.1.10428 9 1.101.3.5.2.13
                fkStpControlBpduGuardMode OBJECT-TYPE
                        SYNTAX INTEGER
                                {
                                disable(0),
                                enable(1)
                                }
                        MAX-ACCESS read-write
                        STATUS current
                        DESCRIPTION
                                "Configures the mode of Bpdu Guard Feature on the switch. 
                                        When the system with Bpdu Guard enabled 
                                        receives a BPDU from any port, that port is 
                                        immediately disabled.    
                                        
                                        disable -- the Bpdu Guard feature is disabled on this
                                                   switch.
                                        
                                        enable -- the Bpdu Guard feature is enabled on this
                                                   switch. 
                                "
                        DEFVAL { disable }
                        ::= { fkStpControl 13 }

                
                -- 1.3.6.1.4.1.10428 9 1.101.3.5.2.14
                fkStpControlBpduGuardAutoRcvMode OBJECT-TYPE
                        SYNTAX INTEGER
                                {
                                disable(0),
                                enable(1)
                                }
                        MAX-ACCESS read-write
                        STATUS current
                        DESCRIPTION
                                "Configures the automatic recovery mode for the ports disabled by Bpdu Guard.
                                        
                                        disable -- the Bpdu Guard Auto Recovery feature is disabled on this
                                                   switch.
                                        
                                        enable -- the Bpdu Guard Auto Recovery feature is enabled on this
                                                   switch. "
                        DEFVAL { disable }
                        ::= { fkStpControl 14 }

                
                -- 1.3.6.1.4.1.10428 9 1.101.3.5.2.15
                fkStpControlBpduGuardAutoRcvTime OBJECT-TYPE
                        SYNTAX INTEGER (10..1000000)
                        MAX-ACCESS read-write
                        STATUS current
                        DESCRIPTION
                                "Configures the automatic recovery time for the ports disabled by Bpdu Guard.
                                        Unit: second"
                        DEFVAL { 300 }
                        ::= { fkStpControl 15 }

                
                -- 1.3.6.1.4.1.10428 9 1.101.3.5.3
                fkStpNotification OBJECT IDENTIFIER ::= { fkStp 3 }

                
                -- 1.3.6.1.4.1.10428 9 1.101.3.5.3.1
                fkStpOperationModeChanged NOTIFICATION-TYPE
                        OBJECTS { fkStpControlRequest, fkStpControlReqResult, fkStpControlTimeStamp, fkStpOperationMode }
                        STATUS current
                        DESCRIPTION 
                                " "
                        ::= { fkStpNotification 1 }

                
                -- 1.3.6.1.4.1.10428 9 1.101.3.5.3.2
                fkStpConfigureProfileChanged NOTIFICATION-TYPE
                        OBJECTS { fkStpControlRequest, fkStpControlReqResult, fkStpControlTimeStamp, fkStpRevisionLevel, fkStpConfigureName
                                 }
                        STATUS current
                        DESCRIPTION 
                                " "
                        ::= { fkStpNotification 2 }

                
                -- 1.3.6.1.4.1.10428 9 1.101.3.5.3.3
                fkStpTimerProfileChanged NOTIFICATION-TYPE
                        OBJECTS { fkStpControlRequest, fkStpControlReqResult, fkStpControlTimeStamp, fkStpFwdDelay, fkStpHelloTime, 
                                fkStpMaxAge, fkStpMaxHops }
                        STATUS current
                        DESCRIPTION 
                                " "
                        ::= { fkStpNotification 3 }

                
                -- 1.3.6.1.4.1.10428 9 1.101.3.5.3.4
                fkStpBpduGuardProfileChanged NOTIFICATION-TYPE
                        OBJECTS { fkStpControlRequest, fkStpControlReqResult, fkStpControlTimeStamp, fkStpBpduGuardMode, fkStpBpduGuardAutoRcvMode, 
                                fkStpBpduGuardAutoRcvTime }
                        STATUS current
                        DESCRIPTION 
                                " "
                        ::= { fkStpNotification 4 }

                
                -- 1.3.6.1.4.1.10428 9 1.101.3.6
                fkStpInstance OBJECT IDENTIFIER ::= { fkBridge 6 }

                
                -- 1.3.6.1.4.1.10428 9 1.101.3.6.1
                fkStpInstanceTable OBJECT-TYPE
                        SYNTAX SEQUENCE OF FkStpInstanceEntry
                        MAX-ACCESS not-accessible
                        STATUS current
                        DESCRIPTION
                                " STP instance table."
                        ::= { fkStpInstance 1 }

                
                -- 1.3.6.1.4.1.10428 9 1.101.3.6.1.1
                fkStpInstanceEntry OBJECT-TYPE
                        SYNTAX FkStpInstanceEntry
                        MAX-ACCESS not-accessible
                        STATUS current
                        DESCRIPTION
                                " key: fkStpInstanceIndex"
                        INDEX { fkStpInstanceIndex }
                        ::= { fkStpInstanceTable 1 }

                
                FkStpInstanceEntry ::=
                        SEQUENCE { 
                                fkStpInstanceIndex
                                        INTEGER,
                                fkStpInstanceEnable
                                        INTEGER,
                                fkStpInstancePriority
                                        Integer32,
                                fkStpInstanceRootBridgeId
                                        OCTET STRING,
                                fkStpInstanceRootPathcost
                                        Integer32,
                                fkStpInstanceDesignatedBridgeId
                                        OCTET STRING,
                                fkStpInstanceDesignatedPortId
                                        INTEGER,
                                fkStpInstanceRootPortId
                                        INTEGER,
                                fkStpInstanceFwdDelay
                                        INTEGER,
                                fkStpInstanceHelloTime
                                        INTEGER,
                                fkStpInstanceMaxAge
                                        INTEGER,
                                fkStpInstanceRemainHops
                                        Integer32,
                                fkStpInstanceBrFwdDelay
                                        INTEGER,
                                fkStpInstanceBrHelloTime
                                        INTEGER,
                                fkStpInstanceBrMaxAge
                                        INTEGER
                         }

                -- 1.3.6.1.4.1.10428 9 1.101.3.6.1.1.1
                fkStpInstanceIndex OBJECT-TYPE
                        SYNTAX INTEGER (0..4096)
                        MAX-ACCESS read-only
                        STATUS current
                        DESCRIPTION
                                "The STP instance ID."
                        ::= { fkStpInstanceEntry 1 }

                
                -- 1.3.6.1.4.1.10428 9 1.101.3.6.1.1.2
                fkStpInstanceEnable OBJECT-TYPE
                        SYNTAX INTEGER
                                {
                                enable(0),
                                disable(1)
                                }
                        MAX-ACCESS read-only
                        STATUS current
                        DESCRIPTION
                                "The enabled/disabled status of the pvst."
                        ::= { fkStpInstanceEntry 2 }

                
                -- 1.3.6.1.4.1.10428 9 1.101.3.6.1.1.3
                fkStpInstancePriority OBJECT-TYPE
                        SYNTAX Integer32
                        MAX-ACCESS read-only
                        STATUS current
                        DESCRIPTION
                                "The Setting bridge priority in a specific instance."
                        ::= { fkStpInstanceEntry 3 }

                
                -- 1.3.6.1.4.1.10428 9 1.101.3.6.1.1.4
                fkStpInstanceRootBridgeId OBJECT-TYPE
                        SYNTAX OCTET STRING (SIZE (8))
                        MAX-ACCESS read-only
                        STATUS current
                        DESCRIPTION
                                "The STP designated root bridge identifier in a specific instance. Size: 8."
                        ::= { fkStpInstanceEntry 4 }

                
                -- 1.3.6.1.4.1.10428 9 1.101.3.6.1.1.5
                fkStpInstanceRootPathcost OBJECT-TYPE
                        SYNTAX Integer32
                        MAX-ACCESS read-only
                        STATUS current
                        DESCRIPTION
                                "The STP root path cost in a specific instance."
                        ::= { fkStpInstanceEntry 5 }

                
                -- 1.3.6.1.4.1.10428 9 1.101.3.6.1.1.6
                fkStpInstanceDesignatedBridgeId OBJECT-TYPE
                        SYNTAX OCTET STRING (SIZE (8))
                        MAX-ACCESS read-only
                        STATUS current
                        DESCRIPTION
                                "TThe STP designated bridge identifier."
                        ::= { fkStpInstanceEntry 6 }

                
                -- 1.3.6.1.4.1.10428 9 1.101.3.6.1.1.7
                fkStpInstanceDesignatedPortId OBJECT-TYPE
                        SYNTAX INTEGER (0..256)
                        MAX-ACCESS read-only
                        STATUS current
                        DESCRIPTION
                                "The STP designated port identifier."
                        ::= { fkStpInstanceEntry 7 }

                
                -- 1.3.6.1.4.1.10428 9 1.101.3.6.1.1.8
                fkStpInstanceRootPortId OBJECT-TYPE
                        SYNTAX INTEGER (0..256)
                        MAX-ACCESS read-only
                        STATUS current
                        DESCRIPTION
                                "The port number of the port which offers the lowest
                                cost path from the this STP instance of this bridge
                                to the root bridge."
                        ::= { fkStpInstanceEntry 8 }

                
                -- 1.3.6.1.4.1.10428 9 1.101.3.6.1.1.9
                fkStpInstanceFwdDelay OBJECT-TYPE
                        SYNTAX INTEGER (4..30)
                        MAX-ACCESS read-only
                        STATUS current
                        DESCRIPTION
                                "The current forward delay of the STP Instance."
                        ::= { fkStpInstanceEntry 9 }

                
                -- 1.3.6.1.4.1.10428 9 1.101.3.6.1.1.10
                fkStpInstanceHelloTime OBJECT-TYPE
                        SYNTAX INTEGER (1..10)
                        MAX-ACCESS read-only
                        STATUS current
                        DESCRIPTION
                                "The current hello time of the STP Instance."
                        ::= { fkStpInstanceEntry 10 }

                
                -- 1.3.6.1.4.1.10428 9 1.101.3.6.1.1.11
                fkStpInstanceMaxAge OBJECT-TYPE
                        SYNTAX INTEGER (4..60)
                        MAX-ACCESS read-only
                        STATUS current
                        DESCRIPTION
                                "The current max age of the STP Instance."
                        ::= { fkStpInstanceEntry 11 }

                
                -- 1.3.6.1.4.1.10428 9 1.101.3.6.1.1.12
                fkStpInstanceRemainHops OBJECT-TYPE
                        SYNTAX Integer32
                        MAX-ACCESS read-only
                        STATUS current
                        DESCRIPTION
                                "The current remain hops of the MSTI or pvst."
                        ::= { fkStpInstanceEntry 12 }

                
                -- 1.3.6.1.4.1.10428 9 1.101.3.6.1.1.13
                fkStpInstanceBrFwdDelay OBJECT-TYPE
                        SYNTAX INTEGER (4..30)
                        MAX-ACCESS read-only
                        STATUS current
                        DESCRIPTION
                                "The Setting forward delay of the STP Instance."
                        ::= { fkStpInstanceEntry 13 }

                
                -- 1.3.6.1.4.1.10428 9 1.101.3.6.1.1.14
                fkStpInstanceBrHelloTime OBJECT-TYPE
                        SYNTAX INTEGER (1..10)
                        MAX-ACCESS read-only
                        STATUS current
                        DESCRIPTION
                                "The current hello time of the STP Instance."
                        ::= { fkStpInstanceEntry 14 }

                
                -- 1.3.6.1.4.1.10428 9 1.101.3.6.1.1.15
                fkStpInstanceBrMaxAge OBJECT-TYPE
                        SYNTAX INTEGER (4..60)
                        MAX-ACCESS read-only
                        STATUS current
                        DESCRIPTION
                                "The Setting max age of the STP Instance."
                        ::= { fkStpInstanceEntry 15 }

                
                -- 1.3.6.1.4.1.10428 9 1.101.3.6.2
                fkStpInstanceControl OBJECT IDENTIFIER ::= { fkStpInstance 2 }

                
                -- 1.3.6.1.4.1.10428 9 1.101.3.6.2.1
                fkStpInstanceControlRequest OBJECT-TYPE
                        SYNTAX INTEGER
                                {
                                setStpInstanceEnable(1),
                                setStpInstanceConfigProfile(2)
                                }
                        MAX-ACCESS read-write
                        STATUS current
                        DESCRIPTION
                                "
                                createStpInstance:
                                fkStpInstanceControlIndex
                                fkStpInstanceControlEnable
                                fkStpInstanceControlPriority
                                fkStpInstanceControlBrFwdDelay
                                fkStpInstanceControlBrHelloTime
                                fkStpInstanceControlBrMaxAge
                                
                                destroyStpInstance:
                                fkStpInstanceControlIndex
                                
                                setStpInstanceEnable:
                                fkStpInstanceControlIndex
                                fkStpInstanceControlEnable
                                
                                setStpInstanceConfigProfile:
                                fkStpInstanceControlIndex
                                fkStpInstanceControlPriority
                                fkStpInstanceControlBrFwdDelay
                                fkStpInstanceControlBrHelloTime
                                fkStpInstanceControlBrMaxAge
                                "
                        ::= { fkStpInstanceControl 1 }

                
                -- 1.3.6.1.4.1.10428 9 1.101.3.6.2.2
                fkStpInstanceControlStatus OBJECT-TYPE
                        SYNTAX FkControlStatusType
                        MAX-ACCESS read-only
                        STATUS current
                        DESCRIPTION
                                "The status of a user command. 
                                "
                        ::= { fkStpInstanceControl 2 }

                
                -- 1.3.6.1.4.1.10428 9 1.101.3.6.2.3
                fkStpInstanceControlTimer OBJECT-TYPE
                        SYNTAX Gauge32
                        MAX-ACCESS read-write
                        STATUS current
                        DESCRIPTION
                                "The maximum wait time for the manager for a long running user command. 
                                "
                        ::= { fkStpInstanceControl 3 }

                
                -- 1.3.6.1.4.1.10428 9 1.101.3.6.2.4
                fkStpInstanceControlTimeStamp OBJECT-TYPE
                        SYNTAX TimeTicks
                        MAX-ACCESS read-only
                        STATUS current
                        DESCRIPTION
                                "The time stamp of the last command (end of command)."
                        ::= { fkStpInstanceControl 4 }

                
                -- 1.3.6.1.4.1.10428 9 1.101.3.6.2.5
                fkStpInstanceControlReqResult OBJECT-TYPE
                        SYNTAX FkControlRequestResultType
                        MAX-ACCESS read-only
                        STATUS current
                        DESCRIPTION
                                "The result of the last user command."
                        ::= { fkStpInstanceControl 5 }

                
                -- 1.3.6.1.4.1.10428 9 1.101.3.6.2.6
                fkStpInstanceControlIndex OBJECT-TYPE
                        SYNTAX INTEGER (0..4096)
                        MAX-ACCESS read-write
                        STATUS current
                        DESCRIPTION
                                " fkStpInstanceIndex"
                        ::= { fkStpInstanceControl 6 }

                
                -- 1.3.6.1.4.1.10428 9 1.101.3.6.2.7
                fkStpInstanceControlEnable OBJECT-TYPE
                        SYNTAX INTEGER
                                {
                                disable(0),
                                enable(1)
                                }
                        MAX-ACCESS read-write
                        STATUS current
                        DESCRIPTION
                                " The enabled/disabled status of the pvst."
                        ::= { fkStpInstanceControl 7 }

                
                -- 1.3.6.1.4.1.10428 9 1.101.3.6.2.8
                fkStpInstanceControlPriority OBJECT-TYPE
                        SYNTAX INTEGER (0..16)
                        MAX-ACCESS read-write
                        STATUS current
                        DESCRIPTION
                                "The Setting bridge priority in a specific instance. 
                                The SET priority vaule is multiplied by 4096.
                                (ex. 2 means 8192)"
                        DEFVAL { 8 }
                        ::= { fkStpInstanceControl 8 }

                
                -- 1.3.6.1.4.1.10428 9 1.101.3.6.2.9
                fkStpInstanceControlBrFwdDelay OBJECT-TYPE
                        SYNTAX INTEGER (4..30)
                        MAX-ACCESS read-write
                        STATUS current
                        DESCRIPTION
                                " The Setting forward delay of the MSTI or pvst."
                        DEFVAL { 15 }
                        ::= { fkStpInstanceControl 9 }

                
                -- 1.3.6.1.4.1.10428 9 1.101.3.6.2.10
                fkStpInstanceControlBrHelloTime OBJECT-TYPE
                        SYNTAX INTEGER (1..10)
                        MAX-ACCESS read-write
                        STATUS current
                        DESCRIPTION
                                " The current hello time of the MSTI or pvst."
                        DEFVAL { 2 }
                        ::= { fkStpInstanceControl 10 }

                
                -- 1.3.6.1.4.1.10428 9 1.101.3.6.2.11
                fkStpInstanceControlBrMaxAge OBJECT-TYPE
                        SYNTAX INTEGER (4..60)
                        MAX-ACCESS read-write
                        STATUS current
                        DESCRIPTION
                                " The Setting max age of the MSTI or pvst."
                        DEFVAL { 30 }
                        ::= { fkStpInstanceControl 11 }

                
                -- 1.3.6.1.4.1.10428 9 1.101.3.6.3
                fkStpInstanceNotification OBJECT IDENTIFIER ::= { fkStpInstance 3 }

                
                -- 1.3.6.1.4.1.10428 9 1.101.3.6.3.1
                fkStpInstanceEnableChanged NOTIFICATION-TYPE
                        OBJECTS { fkStpInstanceControlRequest, fkStpInstanceControlReqResult, fkStpInstanceControlIndex, fkStpInstanceControlEnable, fkStpInstanceControlTimeStamp
                                 }
                        STATUS current
                        DESCRIPTION 
                                " "
                        ::= { fkStpInstanceNotification 1 }

                
                -- 1.3.6.1.4.1.10428 9 1.101.3.6.3.2
                fkStpInstanceConfigProfileChanged NOTIFICATION-TYPE
                        OBJECTS { fkStpInstanceControlRequest, fkStpInstanceControlReqResult, fkStpInstanceControlIndex, fkStpInstanceControlPriority, fkStpInstanceControlBrFwdDelay, 
                                fkStpInstanceControlBrHelloTime, fkStpInstanceControlBrMaxAge, fkStpInstanceControlTimeStamp }
                        STATUS current
                        DESCRIPTION 
                                " "
                        ::= { fkStpInstanceNotification 2 }

                
                -- 1.3.6.1.4.1.10428 9 1.101.3.7
                fkStpInstancePort OBJECT IDENTIFIER ::= { fkBridge 7 }

                
                -- 1.3.6.1.4.1.10428 9 1.101.3.7.1
                fkStpInstancePortTable OBJECT-TYPE
                        SYNTAX SEQUENCE OF FkStpInstancePortEntry
                        MAX-ACCESS not-accessible
                        STATUS current
                        DESCRIPTION
                                " STP instance port table"
                        ::= { fkStpInstancePort 1 }

                
                -- 1.3.6.1.4.1.10428 9 1.101.3.7.1.1
                fkStpInstancePortEntry OBJECT-TYPE
                        SYNTAX FkStpInstancePortEntry
                        MAX-ACCESS not-accessible
                        STATUS current
                        DESCRIPTION
                                " key: fkStpInstanceIndex, fkStpInstancePortIndex"
                        INDEX { fkStpInstanceIndex, fkStpInstancePortIndex }
                        ::= { fkStpInstancePortTable 1 }

                
                FkStpInstancePortEntry ::=
                        SEQUENCE { 
                                fkStpInstancePortIndex
                                        InterfaceIndex,
                                fkStpInstancePortPathcost
                                        INTEGER,
                                fkStpInstancePortPriority
                                        INTEGER,
                                fkStpInstancePortRole
                                        INTEGER,
                                fkStpInstancePortState
                                        INTEGER,
                                fkStpInstancePortRootBridgeId
                                        OCTET STRING,
                                fkStpInstancePortRootPathcost
                                        Integer32,
                                fkStpInstancePortDesignateBridgeId
                                        OCTET STRING,
                                fkStpInstancePortDesignatePortId
                                        INTEGER,
                                fkStpInstancePortRootGuardMode
                                        INTEGER
                         }

                -- 1.3.6.1.4.1.10428 9 1.101.3.7.1.1.1
                fkStpInstancePortIndex OBJECT-TYPE
                        SYNTAX InterfaceIndex
                        MAX-ACCESS read-only
                        STATUS current
                        DESCRIPTION
                                "The Port ID."
                        ::= { fkStpInstancePortEntry 1 }

                
                -- 1.3.6.1.4.1.10428 9 1.101.3.7.1.1.2
                fkStpInstancePortPathcost OBJECT-TYPE
                        SYNTAX INTEGER (0..200000000)
                        MAX-ACCESS read-write
                        STATUS current
                        DESCRIPTION
                                "The STP port path cost."
                        ::= { fkStpInstancePortEntry 2 }

                
                -- 1.3.6.1.4.1.10428 9 1.101.3.7.1.1.3
                fkStpInstancePortPriority OBJECT-TYPE
                        SYNTAX INTEGER (0..255)
                        MAX-ACCESS read-only
                        STATUS current
                        DESCRIPTION
                                "The STP port priority."
                        ::= { fkStpInstancePortEntry 3 }

                
                -- 1.3.6.1.4.1.10428 9 1.101.3.7.1.1.4
                fkStpInstancePortRole OBJECT-TYPE
                        SYNTAX INTEGER
                                {
                                disable(0),
                                designated(1),
                                root(2),
                                master(3),
                                alternate(4),
                                backup(5)
                                }
                        MAX-ACCESS read-only
                        STATUS current
                        DESCRIPTION
                                "The current STP Role of the Port."
                        ::= { fkStpInstancePortEntry 4 }

                
                -- 1.3.6.1.4.1.10428 9 1.101.3.7.1.1.5
                fkStpInstancePortState OBJECT-TYPE
                        SYNTAX INTEGER
                                {
                                disabled(0),
                                listening(1),
                                learning(2),
                                forwarding(3),
                                blocking(4)
                                }
                        MAX-ACCESS read-only
                        STATUS current
                        DESCRIPTION
                                "The STP forwarding state of a specific port."
                        ::= { fkStpInstancePortEntry 5 }

                
                -- 1.3.6.1.4.1.10428 9 1.101.3.7.1.1.6
                fkStpInstancePortRootBridgeId OBJECT-TYPE
                        SYNTAX OCTET STRING (SIZE (8))
                        MAX-ACCESS read-only
                        STATUS current
                        DESCRIPTION
                                "The unique Bridge Identifier of the Bridge recorded
                                as the Root in the Configuration BPDUs transmitted
                                by the Designated Bridge for the segment to which
                                the port is attached."
                        ::= { fkStpInstancePortEntry 6 }

                
                -- 1.3.6.1.4.1.10428 9 1.101.3.7.1.1.7
                fkStpInstancePortRootPathcost OBJECT-TYPE
                        SYNTAX Integer32
                        MAX-ACCESS read-only
                        STATUS current
                        DESCRIPTION
                                "The path cost of the Designated Port of the segment
                                connected to this port."
                        ::= { fkStpInstancePortEntry 7 }

                
                -- 1.3.6.1.4.1.10428 9 1.101.3.7.1.1.8
                fkStpInstancePortDesignateBridgeId OBJECT-TYPE
                        SYNTAX OCTET STRING (SIZE (8))
                        MAX-ACCESS read-only
                        STATUS current
                        DESCRIPTION
                                "The Bridge Identifier of the bridge which this port
                                considers to be the Designated Bridge for this
                                port's segment."
                        ::= { fkStpInstancePortEntry 8 }

                
                -- 1.3.6.1.4.1.10428 9 1.101.3.7.1.1.9
                fkStpInstancePortDesignatePortId OBJECT-TYPE
                        SYNTAX INTEGER (0..256)
                        MAX-ACCESS read-only
                        STATUS current
                        DESCRIPTION
                                "The Port Identifier of the port on the Designated
                                Bridge for this port's segment."
                        ::= { fkStpInstancePortEntry 9 }

                
                -- 1.3.6.1.4.1.10428 9 1.101.3.7.1.1.10
                fkStpInstancePortRootGuardMode OBJECT-TYPE
                        SYNTAX INTEGER
                                {
                                disable(0),
                                enable(1)
                                }
                        MAX-ACCESS read-only
                        STATUS current
                        DESCRIPTION
                                "An indication of whether the RootGuard capability is enabled
                                        on this port or not.
                                 This configuration will be applied to the VLAN or MSTP instance
                                        in which this port exists.
                                
                                 Whether the RootGuard capability is enabled or not 
                                        on this switch depends on the object value of 
                                        fkStpInstancePortControlRootGuardMode."
                        DEFVAL { disable }
                        ::= { fkStpInstancePortEntry 10 }

                
                -- 1.3.6.1.4.1.10428 9 1.101.3.7.2
                fkStpInstancePortControl OBJECT IDENTIFIER ::= { fkStpInstancePort 2 }

                
                -- 1.3.6.1.4.1.10428 9 1.101.3.7.2.1
                fkStpInstancePortControlRequest OBJECT-TYPE
                        SYNTAX INTEGER { setStpInstancePortProfile(1) }
                        MAX-ACCESS read-write
                        STATUS current
                        DESCRIPTION
                                "
                                setStpInstancePortProfile:
                                fkStpInstancePortControlIndex
                                fkStpInstancePortControlInstanceId
                                fkStpInstancePortControlPathcost
                                fkStpInstancePortControlPriority
                                "
                        ::= { fkStpInstancePortControl 1 }

                
                -- 1.3.6.1.4.1.10428 9 1.101.3.7.2.2
                fkStpInstancePortControlStatus OBJECT-TYPE
                        SYNTAX FkControlStatusType
                        MAX-ACCESS read-only
                        STATUS current
                        DESCRIPTION
                                "The status of a user command. 
                                "
                        ::= { fkStpInstancePortControl 2 }

                
                -- 1.3.6.1.4.1.10428 9 1.101.3.7.2.3
                fkStpInstancePortControlTimer OBJECT-TYPE
                        SYNTAX Gauge32
                        MAX-ACCESS read-write
                        STATUS current
                        DESCRIPTION
                                "The maximum wait time for the manager for a long running user command. 
                                "
                        ::= { fkStpInstancePortControl 3 }

                
                -- 1.3.6.1.4.1.10428 9 1.101.3.7.2.4
                fkStpInstancePortControlTimeStamp OBJECT-TYPE
                        SYNTAX TimeTicks
                        MAX-ACCESS read-only
                        STATUS current
                        DESCRIPTION
                                "The time stamp of the last command (end of command)."
                        ::= { fkStpInstancePortControl 4 }

                
                -- 1.3.6.1.4.1.10428 9 1.101.3.7.2.5
                fkStpInstancePortControlReqResult OBJECT-TYPE
                        SYNTAX FkControlRequestResultType
                        MAX-ACCESS read-only
                        STATUS current
                        DESCRIPTION
                                "The result of the last user command."
                        ::= { fkStpInstancePortControl 5 }

                
                -- 1.3.6.1.4.1.10428 9 1.101.3.7.2.6
                fkStpInstancePortControlIndex OBJECT-TYPE
                        SYNTAX INTEGER (0..65535)
                        MAX-ACCESS read-write
                        STATUS current
                        DESCRIPTION
                                "fkStpInstancePortIndex"
                        ::= { fkStpInstancePortControl 6 }

                
                -- 1.3.6.1.4.1.10428 9 1.101.3.7.2.7
                fkStpInstancePortControlInstanceId OBJECT-TYPE
                        SYNTAX INTEGER (0..4096)
                        MAX-ACCESS read-write
                        STATUS current
                        DESCRIPTION
                                " fkStpInstanceId"
                        ::= { fkStpInstancePortControl 7 }

                
                -- 1.3.6.1.4.1.10428 9 1.101.3.7.2.8
                fkStpInstancePortControlPathcost OBJECT-TYPE
                        SYNTAX INTEGER (0..200000000)
                        MAX-ACCESS read-write
                        STATUS current
                        DESCRIPTION
                                " The path cost of the Designated Port of the segment
                                connected to this port."
                        ::= { fkStpInstancePortControl 8 }

                
                -- 1.3.6.1.4.1.10428 9 1.101.3.7.2.9
                fkStpInstancePortControlPriority OBJECT-TYPE
                        SYNTAX INTEGER (0..255)
                        MAX-ACCESS read-write
                        STATUS current
                        DESCRIPTION
                                " The STP port priority."
                        DEFVAL { 128 }
                        ::= { fkStpInstancePortControl 9 }

                
                -- 1.3.6.1.4.1.10428 9 1.101.3.7.2.10
                fkStpInstancePortControlRootGuardMode OBJECT-TYPE
                        SYNTAX INTEGER
                                {
                                disable(0),
                                enable(1)
                                }
                        MAX-ACCESS read-write
                        STATUS current
                        DESCRIPTION
                                "Enable or disable RootGuard capability on this port.
                                 This configuration will be applied to the VLAN or MSTP instance
                                        in which this port exists."
                        DEFVAL { disable }
                        ::= { fkStpInstancePortControl 10 }

                
                -- 1.3.6.1.4.1.10428 9 1.101.3.7.3
                fkStpInstancePortNotification OBJECT IDENTIFIER ::= { fkStpInstancePort 3 }

                
                -- 1.3.6.1.4.1.10428 9 1.101.3.7.3.1
                fkStpInstancePortProfileChanged NOTIFICATION-TYPE
                        OBJECTS { fkStpInstancePortControlRequest, fkStpInstancePortControlReqResult, fkStpInstancePortControlTimeStamp, fkStpInstancePortPathcost, fkStpInstancePortPriority, 
                                fkStpInstancePortRootGuardMode }
                        STATUS current
                        DESCRIPTION 
                                " "
                        ::= { fkStpInstancePortNotification 1 }

                
--   fkSubnetVlan Group
-- 1.3.6.1.4.1.10428 9 1.9.8.8
                -- 1.3.6.1.4.1.10428 9 1.101.3.8
                fkSubnetVlan OBJECT IDENTIFIER ::= { fkBridge 8 }

                
--  1.3.6.1.4.1.10428 9 1.9.8.8.1
                -- 1.3.6.1.4.1.10428 9 1.101.3.8.1
                fkSubnetVlanTable OBJECT-TYPE
                        SYNTAX SEQUENCE OF FkSubnetVlanEntry
                        MAX-ACCESS not-accessible
                        STATUS current
                        DESCRIPTION
                                " subnet vlan table."
                        ::= { fkSubnetVlan 1 }

                
--  1.3.6.1.4.1.10428 9 1.9.8.8.1.1
                -- 1.3.6.1.4.1.10428 9 1.101.3.8.1.1
                fkSubnetVlanEntry OBJECT-TYPE
                        SYNTAX FkSubnetVlanEntry
                        MAX-ACCESS not-accessible
                        STATUS current
                        DESCRIPTION
                                " key: fkSubnetVlanIp, fkSubnetVlanMask"
                        INDEX { fkSubnetVlanIp, fkSubnetVlanMask }
                        ::= { fkSubnetVlanTable 1 }

                
                FkSubnetVlanEntry ::=
                        SEQUENCE { 
                                fkSubnetVlanIp
                                        IpAddress,
                                fkSubnetVlanMask
                                        Integer32,
                                fkSubnetVlanVid
                                        Integer32
                         }

--  1.3.6.1.4.1.10428 9 1.9.8.8.1.1.2
                -- 1.3.6.1.4.1.10428 9 1.101.3.8.1.1.1
                fkSubnetVlanIp OBJECT-TYPE
                        SYNTAX IpAddress
                        MAX-ACCESS read-only
                        STATUS current
                        DESCRIPTION
                                "Ip address of Subnet"
                        ::= { fkSubnetVlanEntry 1 }

                
--  1.3.6.1.4.1.10428 9 1.9.8.8.1.1.3
                -- 1.3.6.1.4.1.10428 9 1.101.3.8.1.1.2
                fkSubnetVlanMask OBJECT-TYPE
                        SYNTAX Integer32 (1..32)
                        MAX-ACCESS read-only
                        STATUS current
                        DESCRIPTION
                                "Mask bit."
                        ::= { fkSubnetVlanEntry 2 }

                
--  1.3.6.1.4.1.10428 9 1.9.8.8.1.1.4
                -- 1.3.6.1.4.1.10428 9 1.101.3.8.1.1.3
                fkSubnetVlanVid OBJECT-TYPE
                        SYNTAX Integer32 (1..4094)
                        MAX-ACCESS read-only
                        STATUS current
                        DESCRIPTION
                                "Index of the VLAN."
                        ::= { fkSubnetVlanEntry 3 }

                
--  1.3.6.1.4.1.10428 9 1.9.8.8.2
                -- 1.3.6.1.4.1.10428 9 1.101.3.8.2
                fkSubnetVlanControl OBJECT IDENTIFIER ::= { fkSubnetVlan 2 }

                
--   Node definitions
-- 
-- 1.3.6.1.4.1.10428 9 1.9.8.8.2.1
                -- 1.3.6.1.4.1.10428 9 1.101.3.8.2.1
                fkSubnetVlanControlRequest OBJECT-TYPE
                        SYNTAX INTEGER
                                {
                                createSubnetVlan(1),
                                destorySubnetVlan(2)
                                }
                        MAX-ACCESS read-write
                        STATUS current
                        DESCRIPTION
                                "
                                createSubnetVlan:
                                fkSubnetVlanControlPortIndex
                                fkSubnetVlanControlIp
                                fkSubnetVlanControlMask
                                fkSubnetVlanControlVid
                                
                                destorySubnetVlan:
                                fkSubnetVlanControlPortIndex
                                
                                "
                        ::= { fkSubnetVlanControl 1 }

                
--  1.3.6.1.4.1.10428 9 1.9.8.8.2.3
                -- 1.3.6.1.4.1.10428 9 1.101.3.8.2.2
                fkSubnetVlanControlStatus OBJECT-TYPE
                        SYNTAX FkControlStatusType
                        MAX-ACCESS read-only
                        STATUS current
                        DESCRIPTION
                                "The status of a user command. 
                                "
                        ::= { fkSubnetVlanControl 2 }

                
--  1.3.6.1.4.1.10428 9 1.9.8.8.2.4
                -- 1.3.6.1.4.1.10428 9 1.101.3.8.2.3
                fkSubnetVlanControlTimer OBJECT-TYPE
                        SYNTAX Gauge32
                        MAX-ACCESS read-write
                        STATUS current
                        DESCRIPTION
                                "The maximum wait time for the manager for a long running user command. 
                                "
                        ::= { fkSubnetVlanControl 3 }

                
--  1.3.6.1.4.1.10428 9 1.9.8.8.2.6
                -- 1.3.6.1.4.1.10428 9 1.101.3.8.2.4
                fkSubnetVlanControlTimeStamp OBJECT-TYPE
                        SYNTAX TimeTicks
                        MAX-ACCESS read-only
                        STATUS current
                        DESCRIPTION
                                "The time stamp of the last command (end of command)."
                        ::= { fkSubnetVlanControl 4 }

                
--  1.3.6.1.4.1.10428 9 1.9.8.8.2.5
                -- 1.3.6.1.4.1.10428 9 1.101.3.8.2.5
                fkSubnetVlanControlReqResult OBJECT-TYPE
                        SYNTAX FkControlRequestResultType
                        MAX-ACCESS read-only
                        STATUS current
                        DESCRIPTION
                                "The result of the last user command."
                        ::= { fkSubnetVlanControl 5 }

                
--  1.3.6.1.4.1.10428 9 1.9.8.8.2.7
                -- 1.3.6.1.4.1.10428 9 1.101.3.8.2.6
                fkSubnetVlanControlIp OBJECT-TYPE
                        SYNTAX IpAddress
                        MAX-ACCESS read-write
                        STATUS current
                        DESCRIPTION
                                "IP address"
                        ::= { fkSubnetVlanControl 6 }

                
--  1.3.6.1.4.1.10428 9 1.9.8.8.2.8
                -- 1.3.6.1.4.1.10428 9 1.101.3.8.2.7
                fkSubnetVlanControlMask OBJECT-TYPE
                        SYNTAX Integer32 (1..32)
                        MAX-ACCESS read-write
                        STATUS current
                        DESCRIPTION
                                "Mask bit
                                "
                        ::= { fkSubnetVlanControl 7 }

                
--  1.3.6.1.4.1.10428 9 1.9.8.8.2.9
                -- 1.3.6.1.4.1.10428 9 1.101.3.8.2.8
                fkSubnetVlanControlVid OBJECT-TYPE
                        SYNTAX Integer32 (1..4094)
                        MAX-ACCESS read-write
                        STATUS current
                        DESCRIPTION
                                "Vlan's ID"
                        ::= { fkSubnetVlanControl 8 }

                
--  1.3.6.1.4.1.10428 9 1.9.8.8.3
                -- 1.3.6.1.4.1.10428 9 1.101.3.8.3
                fkSubnetVlanNotification OBJECT IDENTIFIER ::= { fkSubnetVlan 3 }

                
--  1.3.6.1.4.1.10428 9 1.9.8.8.3.1
                -- 1.3.6.1.4.1.10428 9 1.101.3.8.3.1
                fkSubnetVlanCreated NOTIFICATION-TYPE
                        OBJECTS { fkSubnetVlanControlTimeStamp, fkSubnetVlanControlReqResult, fkSubnetVlanControlRequest, fkSubnetVlanVid }
                        STATUS current
                        DESCRIPTION 
                                " "
                        ::= { fkSubnetVlanNotification 1 }

                
--  1.3.6.1.4.1.10428 9 1.9.8.8.3.2
                -- 1.3.6.1.4.1.10428 9 1.101.3.8.3.2
                fkSubnetVlanDestroyed NOTIFICATION-TYPE
                        OBJECTS { fkSubnetVlanControlRequest, fkSubnetVlanControlTimeStamp, fkSubnetVlanControlReqResult, fkSubnetVlanVid }
                        STATUS current
                        DESCRIPTION 
                                " "
                        ::= { fkSubnetVlanNotification 2 }

                
--   fkProtocolVlan Group
-- 1.3.6.1.4.1.10428 9 1.9.8.9
                -- 1.3.6.1.4.1.10428 9 1.101.3.9
                fkProtocolVlan OBJECT IDENTIFIER ::= { fkBridge 9 }

                
--  1.3.6.1.4.1.10428 9 1.9.8.9.1
                -- 1.3.6.1.4.1.10428 9 1.101.3.9.1
                fkProtocolVlanTable OBJECT-TYPE
                        SYNTAX SEQUENCE OF FkProtocolVlanEntry
                        MAX-ACCESS not-accessible
                        STATUS current
                        DESCRIPTION
                                " protocol vlan table."
                        ::= { fkProtocolVlan 1 }

                
--  1.3.6.1.4.1.10428 9 1.9.8.9.1.1
                -- 1.3.6.1.4.1.10428 9 1.101.3.9.1.1
                fkProtocolVlanEntry OBJECT-TYPE
                        SYNTAX FkProtocolVlanEntry
                        MAX-ACCESS not-accessible
                        STATUS current
                        DESCRIPTION
                                " key: fkBridgePortIndex, fkProtocolVlanEtype"
                        INDEX { fkBridgePortIndex, fkProtocolVlanEtype }
                        ::= { fkProtocolVlanTable 1 }

                
                FkProtocolVlanEntry ::=
                        SEQUENCE { 
                                fkProtocolVlanEtype
                                        Unsigned32,
                                fkProtocolVlanVid
                                        Integer32
                         }

--  1.3.6.1.4.1.10428 9 1.9.8.9.1.1.2
                -- 1.3.6.1.4.1.10428 9 1.101.3.9.1.1.1
                fkProtocolVlanEtype OBJECT-TYPE
                        SYNTAX Unsigned32 (1..65535)
                        MAX-ACCESS read-only
                        STATUS current
                        DESCRIPTION
                                "Ethernet type"
                        ::= { fkProtocolVlanEntry 1 }

                
--  1.3.6.1.4.1.10428 9 1.9.8.9.1.1.3
                -- 1.3.6.1.4.1.10428 9 1.101.3.9.1.1.2
                fkProtocolVlanVid OBJECT-TYPE
                        SYNTAX Integer32 (1..4094)
                        MAX-ACCESS read-only
                        STATUS current
                        DESCRIPTION
                                "Index of the VLAN."
                        ::= { fkProtocolVlanEntry 2 }

                
--  1.3.6.1.4.1.10428 9 1.9.8.9.2
                -- 1.3.6.1.4.1.10428 9 1.101.3.9.2
                fkProtocolVlanControl OBJECT IDENTIFIER ::= { fkProtocolVlan 2 }

                
--   Node definitions
-- 
-- 1.3.6.1.4.1.10428 9 1.9.8.9.2.1
                -- 1.3.6.1.4.1.10428 9 1.101.3.9.2.1
                fkProtocolVlanControlRequest OBJECT-TYPE
                        SYNTAX INTEGER
                                {
                                createProtocolVlan(1),
                                destoryProtocolVlan(2)
                                }
                        MAX-ACCESS read-write
                        STATUS current
                        DESCRIPTION
                                "
                                createProtocolVlan:
                                fkProtocolVlanControlPortIndex
                                fkProtocolVlanControlEtype
                                fkProtocolVlanControlVid
                                
                                destoryProtocolVlan:
                                fkProtocolVlanControlPortIndex
                                
                                "
                        ::= { fkProtocolVlanControl 1 }

                
--  1.3.6.1.4.1.10428 9 1.9.8.9.2.3
                -- 1.3.6.1.4.1.10428 9 1.101.3.9.2.2
                fkProtocolVlanControlStatus OBJECT-TYPE
                        SYNTAX FkControlStatusType
                        MAX-ACCESS read-only
                        STATUS current
                        DESCRIPTION
                                "The status of a user command. 
                                "
                        ::= { fkProtocolVlanControl 2 }

                
--  1.3.6.1.4.1.10428 9 1.9.8.9.2.4
                -- 1.3.6.1.4.1.10428 9 1.101.3.9.2.3
                fkProtocolVlanControlTimer OBJECT-TYPE
                        SYNTAX Gauge32
                        MAX-ACCESS read-write
                        STATUS current
                        DESCRIPTION
                                "The maximum wait time for the manager for a long running user command. 
                                "
                        ::= { fkProtocolVlanControl 3 }

                
--  1.3.6.1.4.1.10428 9 1.9.8.9.2.6
                -- 1.3.6.1.4.1.10428 9 1.101.3.9.2.4
                fkProtocolVlanControlTimeStamp OBJECT-TYPE
                        SYNTAX TimeTicks
                        MAX-ACCESS read-only
                        STATUS current
                        DESCRIPTION
                                "The time stamp of the last command (end of command)."
                        ::= { fkProtocolVlanControl 4 }

                
--  1.3.6.1.4.1.10428 9 1.9.8.9.2.5
                -- 1.3.6.1.4.1.10428 9 1.101.3.9.2.5
                fkProtocolVlanControlReqResult OBJECT-TYPE
                        SYNTAX FkControlRequestResultType
                        MAX-ACCESS read-only
                        STATUS current
                        DESCRIPTION
                                "The result of the last user command."
                        ::= { fkProtocolVlanControl 5 }

                
--  1.3.6.1.4.1.10428 9 1.9.8.9.2.2
                -- 1.3.6.1.4.1.10428 9 1.101.3.9.2.6
                fkProtocolVlanControlPortIndex OBJECT-TYPE
                        SYNTAX InterfaceIndex
                        MAX-ACCESS read-write
                        STATUS current
                        DESCRIPTION
                                " fkBridgePortIndex, fkProtocolVlanEtype"
                        ::= { fkProtocolVlanControl 6 }

                
--  1.3.6.1.4.1.10428 9 1.9.8.9.2.7
                -- 1.3.6.1.4.1.10428 9 1.101.3.9.2.7
                fkProtocolVlanControlEtype OBJECT-TYPE
                        SYNTAX Unsigned32
                        MAX-ACCESS read-write
                        STATUS current
                        DESCRIPTION
                                "Ethernet Type"
                        ::= { fkProtocolVlanControl 7 }

                
--  1.3.6.1.4.1.10428 9 1.9.8.9.2.8
                -- 1.3.6.1.4.1.10428 9 1.101.3.9.2.8
                fkProtocolVlanControlVid OBJECT-TYPE
                        SYNTAX Integer32 (1..4094)
                        MAX-ACCESS read-write
                        STATUS current
                        DESCRIPTION
                                " fkProtocolVlanControlVid"
                        ::= { fkProtocolVlanControl 8 }

                
--  1.3.6.1.4.1.10428 9 1.9.8.9.3
                -- 1.3.6.1.4.1.10428 9 1.101.3.9.3
                fkProtocolVlanNotification OBJECT IDENTIFIER ::= { fkProtocolVlan 3 }

                
--  1.3.6.1.4.1.10428 9 1.9.8.9.3.1
                -- 1.3.6.1.4.1.10428 9 1.101.3.9.3.1
                fkProtocolVlanCreated NOTIFICATION-TYPE
                        OBJECTS { fkProtocolVlanVid, fkProtocolVlanControlRequest, fkProtocolVlanControlTimeStamp, fkProtocolVlanControlReqResult }
                        STATUS current
                        DESCRIPTION 
                                " "
                        ::= { fkProtocolVlanNotification 1 }

                
--  1.3.6.1.4.1.10428 9 1.9.8.9.3.2
                -- 1.3.6.1.4.1.10428 9 1.101.3.9.3.2
                fkProtocolVlanDestroyed NOTIFICATION-TYPE
                        OBJECTS { fkProtocolVlanControlRequest, fkProtocolVlanControlTimeStamp, fkProtocolVlanControlReqResult, fkProtocolVlanVid }
                        STATUS current
                        DESCRIPTION 
                                " "
                        ::= { fkProtocolVlanNotification 2 }

                
--  1.3.6.1.4.1.10428 9 1.9.8.10
                -- 1.3.6.1.4.1.10428 9 1.101.3.10
                fkLag OBJECT IDENTIFIER ::= { fkBridge 10 }

                
--  1.3.6.1.4.1.10428 9 1.9.8.10.1
                -- 1.3.6.1.4.1.10428 9 1.101.3.10.1
                fkLagTable OBJECT-TYPE
                        SYNTAX SEQUENCE OF FkLagEntry
                        MAX-ACCESS not-accessible
                        STATUS current
                        DESCRIPTION
                                " lag table."
                        ::= { fkLag 1 }

                
--  1.3.6.1.4.1.10428 9 1.9.8.10.1.1
                -- 1.3.6.1.4.1.10428 9 1.101.3.10.1.1
                fkLagEntry OBJECT-TYPE
                        SYNTAX FkLagEntry
                        MAX-ACCESS not-accessible
                        STATUS current
                        DESCRIPTION
                                " key: fkLagIndex"
                        INDEX { fkLagIndex }
                        ::= { fkLagTable 1 }
-- key: fkLagIndex
                
                FkLagEntry ::=
                        SEQUENCE { 
                                fkLagIndex
                                        Integer32,
                                fkLagPortId
                                        InterfaceIndex,
                                fkLagDistMode
                                        INTEGER,
                                fkLagPortMap
                                        OCTET STRING,
                                fkLagMode
                                        INTEGER,
                                fkLagLeastActive
                                        INTEGER
                         }

--  1.3.6.1.4.1.10428 9 1.9.8.10.1.1.1
                -- 1.3.6.1.4.1.10428 9 1.101.3.10.1.1.1
                fkLagIndex OBJECT-TYPE
                        SYNTAX Integer32 (0..13)
                        MAX-ACCESS read-only
                        STATUS current
                        DESCRIPTION
                                "This value assigned to the aggregation ID."
                        ::= { fkLagEntry 1 }

                
--  1.3.6.1.4.1.10428 9 1.9.8.10.1.1.2
                -- 1.3.6.1.4.1.10428 9 1.101.3.10.1.1.2
                fkLagPortId OBJECT-TYPE
                        SYNTAX InterfaceIndex
                        MAX-ACCESS read-only
                        STATUS current
                        DESCRIPTION
                                "Port ID of aggregation."
                        ::= { fkLagEntry 2 }

                
--  1.3.6.1.4.1.10428 9 1.9.8.10.1.1.3
                -- 1.3.6.1.4.1.10428 9 1.101.3.10.1.1.3
                fkLagDistMode OBJECT-TYPE
                        SYNTAX INTEGER
                                {
                                none(0),
                                srcmac(1),
                                dstmac(2),
                                srcdstmac(3),
                                srcip(4),
                                dstip(5),
                                srcdstip(6),
                                srcdstl4(7),
                                label(80)
                                }
                        MAX-ACCESS read-only
                        STATUS current
                        DESCRIPTION
                                "This value assigned to the distributing 
                                mode of link aggregation."
                        ::= { fkLagEntry 3 }

                
--  1.3.6.1.4.1.10428 9 1.9.8.10.1.1.4
                -- 1.3.6.1.4.1.10428 9 1.101.3.10.1.1.4
                fkLagPortMap OBJECT-TYPE
                        SYNTAX OCTET STRING
                        MAX-ACCESS read-only
                        STATUS current
                        DESCRIPTION
                                "The value assigned to the port list of  the aggregation."
                        ::= { fkLagEntry 4 }

                
--  1.3.6.1.4.1.10428 9 1.9.8.10.1.1.5
                -- 1.3.6.1.4.1.10428 9 1.101.3.10.1.1.5
                fkLagMode OBJECT-TYPE
                        SYNTAX INTEGER
                                {
                                inactive(0),
                                trunk(1),
                                lacp(2)
                                }
                        MAX-ACCESS read-only
                        STATUS current
                        DESCRIPTION
                                "The operation mode of  link aggregation."
                        ::= { fkLagEntry 5 }

                
--  1.3.6.1.4.1.10428 9 1.101.3.10.1.1.6
                -- 1.3.6.1.4.1.10428 9 1.101.3.10.1.1.6
                fkLagLeastActive OBJECT-TYPE
                        SYNTAX INTEGER
                        MAX-ACCESS read-only
                        STATUS current
                        DESCRIPTION
                                "Description."
                        ::= { fkLagEntry 6 }

                
--  1.3.6.1.4.1.10428 9 1.9.8.10.2
                -- 1.3.6.1.4.1.10428 9 1.101.3.10.2
                fkLagControl OBJECT IDENTIFIER ::= { fkLag 2 }

                
--  1.3.6.1.4.1.10428 9 1.9.8.10.2.1
                -- 1.3.6.1.4.1.10428 9 1.101.3.10.2.1
                fkLagControlRequest OBJECT-TYPE
                        SYNTAX INTEGER { setLagProfile(1) }
                        MAX-ACCESS read-write
                        STATUS current
                        DESCRIPTION
                                "The MIB object for the user command.."
                        ::= { fkLagControl 1 }

                
--  1.3.6.1.4.1.10428 9 1.9.8.10.2.2
                -- 1.3.6.1.4.1.10428 9 1.101.3.10.2.2
                fkLagControlStatus OBJECT-TYPE
                        SYNTAX FkControlStatusType
                        MAX-ACCESS read-only
                        STATUS current
                        DESCRIPTION
                                "Describes the status of a user command group, 
                                used for block commands while a command execution in process."
                        ::= { fkLagControl 2 }

                
--  1.3.6.1.4.1.10428 9 1.9.8.10.2.3
                -- 1.3.6.1.4.1.10428 9 1.101.3.10.2.3
                fkLagControlTimer OBJECT-TYPE
                        SYNTAX Gauge32
                        MAX-ACCESS read-write
                        STATUS current
                        DESCRIPTION
                                "Maximum command duration time in case of long running"
                        ::= { fkLagControl 3 }

                
--  1.3.6.1.4.1.10428 9 1.9.8.10.2.5
                -- 1.3.6.1.4.1.10428 9 1.101.3.10.2.4
                fkLagControlTimeStamp OBJECT-TYPE
                        SYNTAX TimeTicks
                        MAX-ACCESS read-only
                        STATUS current
                        DESCRIPTION
                                "Command result attribute"
                        ::= { fkLagControl 4 }

                
--  1.3.6.1.4.1.10428 9 1.9.8.10.2.4
                -- 1.3.6.1.4.1.10428 9 1.101.3.10.2.5
                fkLagControlReqResult OBJECT-TYPE
                        SYNTAX FkControlRequestResultType
                        MAX-ACCESS read-only
                        STATUS current
                        DESCRIPTION
                                "Time stamp attribute set at end of command."
                        ::= { fkLagControl 5 }

                
--  1.3.6.1.4.1.10428 9 1.9.8.10.2.6
                -- 1.3.6.1.4.1.10428 9 1.101.3.10.2.6
                fkLagControlIndex OBJECT-TYPE
                        SYNTAX Integer32
                        MAX-ACCESS read-write
                        STATUS current
                        DESCRIPTION
                                "This value assigned to the aggregation ID."
                        ::= { fkLagControl 6 }

                
--  1.3.6.1.4.1.10428 9 1.9.8.10.2.7
                -- 1.3.6.1.4.1.10428 9 1.101.3.10.2.7
                fkLagControlDistMode OBJECT-TYPE
                        SYNTAX INTEGER
                                {
                                srcmac(1),
                                dstmac(2),
                                srcdstmac(3),
                                srcip(4),
                                dstip(5),
                                srcdstip(6),
                                srcdstl4(7),
                                label(80)
                                }
                        MAX-ACCESS read-write
                        STATUS current
                        DESCRIPTION
                                "This value assigned to the distributing mode of link aggregation."
                        ::= { fkLagControl 7 }

                
--  1.3.6.1.4.1.10428 9 1.9.8.10.2.8
                -- 1.3.6.1.4.1.10428 9 1.101.3.10.2.8
                fkLagControlPortMap OBJECT-TYPE
                        SYNTAX OCTET STRING
                        MAX-ACCESS read-write
                        STATUS current
                        DESCRIPTION
                                "Port ID of aggregation."
                        ::= { fkLagControl 8 }

                
--  1.3.6.1.4.1.10428 9 1.9.8.10.2.9
                -- 1.3.6.1.4.1.10428 9 1.101.3.10.2.9
                fkLagControlMode OBJECT-TYPE
                        SYNTAX INTEGER
                                {
                                trunk(1),
                                lacp(2)
                                }
                        MAX-ACCESS read-write
                        STATUS current
                        DESCRIPTION
                                "The operation mode of  link aggregation."
                        ::= { fkLagControl 9 }

                
--  1.3.6.1.4.1.10428 9 1.101.3.10.2.10
                -- 1.3.6.1.4.1.10428 9 1.101.3.10.2.10
                fkLagControlLeastActive OBJECT-TYPE
                        SYNTAX INTEGER
                        MAX-ACCESS read-write
                        STATUS current
                        DESCRIPTION
                                "Description."
                        ::= { fkLagControl 10 }

                
--  1.3.6.1.4.1.10428 9 1.9.8.10.3
                -- 1.3.6.1.4.1.10428 9 1.101.3.10.3
                fkLagNotification OBJECT IDENTIFIER ::= { fkLag 3 }

                
--  1.3.6.1.4.1.10428 9 1.9.8.10.3.1
                -- 1.3.6.1.4.1.10428 9 1.101.3.10.3.1
                fkLagProfileChanged NOTIFICATION-TYPE
                        OBJECTS { fkLagControlRequest, fkLagControlReqResult, fkLagControlTimeStamp, fkLagLeastActive, fkLagPortMap, 
                                fkLagDistMode, fkLagMode }
                        STATUS current
                        DESCRIPTION 
                                " "
                        ::= { fkLagNotification 1 }

                
--  1.3.6.1.4.1.10428 9 1.9.8.11
                -- 1.3.6.1.4.1.10428 9 1.101.3.11
                fkLagLacp OBJECT IDENTIFIER ::= { fkBridge 11 }

                
--  1.3.6.1.4.1.10428 9 1.9.8.11.1
                -- 1.3.6.1.4.1.10428 9 1.101.3.11.1
                fkLagLacpTable OBJECT-TYPE
                        SYNTAX SEQUENCE OF FkLagLacpEntry
                        MAX-ACCESS not-accessible
                        STATUS current
                        DESCRIPTION
                                " lag LACP table."
                        ::= { fkLagLacp 1 }

                
--  1.3.6.1.4.1.10428 9 1.9.8.11.1.1
                -- 1.3.6.1.4.1.10428 9 1.101.3.11.1.1
                fkLagLacpEntry OBJECT-TYPE
                        SYNTAX FkLagLacpEntry
                        MAX-ACCESS not-accessible
                        STATUS current
                        DESCRIPTION
                                " key: fkLagLacpIndex"
                        INDEX { fkLagLacpIndex }
                        ::= { fkLagLacpTable 1 }

                
                FkLagLacpEntry ::=
                        SEQUENCE { 
                                fkLagLacpIndex
                                        Integer32,
                                fkLagLacpActorAggregatorKey
                                        Integer32,
                                fkLagLacpActorSystemMAC
                                        OCTET STRING,
                                fkLagLacpPartnerSystemMAC
                                        OCTET STRING,
                                fkLagLacpPartnerSystemPriority
                                        Integer32,
                                fkLagLacpPartnerAggregatorKey
                                        Integer32
                         }

--  1.3.6.1.4.1.10428 9 1.9.8.11.1.1.1
                -- 1.3.6.1.4.1.10428 9 1.101.3.11.1.1.1
                fkLagLacpIndex OBJECT-TYPE
                        SYNTAX Integer32 (0..13)
                        MAX-ACCESS read-only
                        STATUS current
                        DESCRIPTION
                                "Location of authentication."
                        ::= { fkLagLacpEntry 1 }

                
--  1.3.6.1.4.1.10428 9 1.9.8.11.1.1.2
                -- 1.3.6.1.4.1.10428 9 1.101.3.11.1.1.2
                fkLagLacpActorAggregatorKey OBJECT-TYPE
                        SYNTAX Integer32 (1..65535)
                        MAX-ACCESS read-only
                        STATUS current
                        DESCRIPTION
                                "The kind of authentication."
                        ::= { fkLagLacpEntry 2 }

                
                -- 1.3.6.1.4.1.10428 9 1.101.3.11.1.1.3
                fkLagLacpActorSystemMAC OBJECT-TYPE
                        SYNTAX OCTET STRING
                        MAX-ACCESS read-write
                        STATUS current
                        DESCRIPTION
                                "The Actor’s System ID, encoded as a MAC address."
                        ::= { fkLagLacpEntry 3 }

                
--  1.3.6.1.4.1.10428 9 1.9.8.11.1.1.3
                -- 1.3.6.1.4.1.10428 9 1.101.3.11.1.1.4
                fkLagLacpPartnerSystemMAC OBJECT-TYPE
                        SYNTAX OCTET STRING
                        MAX-ACCESS read-only
                        STATUS current
                        DESCRIPTION
                                "Enable or disable the corresponding authen method."
                        ::= { fkLagLacpEntry 4 }

                
--  1.3.6.1.4.1.10428 9 1.9.8.11.1.1.4
                -- 1.3.6.1.4.1.10428 9 1.101.3.11.1.1.5
                fkLagLacpPartnerSystemPriority OBJECT-TYPE
                        SYNTAX Integer32 (1..65535)
                        MAX-ACCESS read-only
                        STATUS current
                        DESCRIPTION
                                "The primary priority of the corresponding authen method."
                        ::= { fkLagLacpEntry 5 }

                
--  1.3.6.1.4.1.10428 9 1.9.8.11.1.1.5
                -- 1.3.6.1.4.1.10428 9 1.101.3.11.1.1.6
                fkLagLacpPartnerAggregatorKey OBJECT-TYPE
                        SYNTAX Integer32 (1..65535)
                        MAX-ACCESS read-only
                        STATUS current
                        DESCRIPTION
                                " "
                        ::= { fkLagLacpEntry 6 }

                
                -- 1.3.6.1.4.1.10428 9 1.101.3.11.2
                fkLagLacpStats OBJECT IDENTIFIER ::= { fkLagLacp 2 }

                
                -- 1.3.6.1.4.1.10428 9 1.101.3.11.2.1
                fkLagLacpStatsPduReceived OBJECT-TYPE
                        SYNTAX Counter32
                        MAX-ACCESS read-only
                        STATUS current
                        DESCRIPTION
                                "The received LACP PDUs"
                        ::= { fkLagLacpStats 1 }

                
                -- 1.3.6.1.4.1.10428 9 1.101.3.11.2.2
                fkLagLacpStatsPduReceivedErrrors OBJECT-TYPE
                        SYNTAX Counter32
                        MAX-ACCESS read-only
                        STATUS current
                        DESCRIPTION
                                "The received LACP PDUs"
                        ::= { fkLagLacpStats 2 }

                
                -- 1.3.6.1.4.1.10428 9 1.101.3.11.2.3
                fkLagLacpStatsPduSent OBJECT-TYPE
                        SYNTAX Counter32
                        MAX-ACCESS read-only
                        STATUS current
                        DESCRIPTION
                                "The sent LACP PDUs"
                        ::= { fkLagLacpStats 3 }

                
                -- 1.3.6.1.4.1.10428 9 1.101.3.11.2.4
                fkLagLacpStatsPduSentError OBJECT-TYPE
                        SYNTAX Counter32
                        MAX-ACCESS read-only
                        STATUS current
                        DESCRIPTION
                                "The sent LACP PDUs error"
                        ::= { fkLagLacpStats 4 }

                
                -- 1.3.6.1.4.1.10428 9 1.101.3.11.2.5
                fkLagLacpStatsMarkerReceived OBJECT-TYPE
                        SYNTAX Counter32
                        MAX-ACCESS read-only
                        STATUS current
                        DESCRIPTION
                                "The received LACP Marker"
                        ::= { fkLagLacpStats 5 }

                
                -- 1.3.6.1.4.1.10428 9 1.101.3.11.2.6
                fkLagLacpStatsMarkerSent OBJECT-TYPE
                        SYNTAX Counter32
                        MAX-ACCESS read-only
                        STATUS current
                        DESCRIPTION
                                "The sent LACP Marker"
                        ::= { fkLagLacpStats 6 }

                
                -- 1.3.6.1.4.1.10428 9 1.101.3.11.2.7
                fkLagLacpStatsMarkerSentError OBJECT-TYPE
                        SYNTAX Counter32
                        MAX-ACCESS read-only
                        STATUS current
                        DESCRIPTION
                                "The sent LACP Marker error."
                        ::= { fkLagLacpStats 7 }

                
                -- 1.3.6.1.4.1.10428 9 1.101.3.11.3
                fkLagLacpControl OBJECT IDENTIFIER ::= { fkLagLacp 3 }

                
                -- 1.3.6.1.4.1.10428 9 1.101.3.11.3.1
                fkLagLacpControlRequest OBJECT-TYPE
                        SYNTAX INTEGER { clearLacpStats(1) }
                        MAX-ACCESS read-write
                        STATUS current
                        DESCRIPTION
                                "The request of a user command"
                        ::= { fkLagLacpControl 1 }

                
                -- 1.3.6.1.4.1.10428 9 1.101.3.11.3.2
                fkLagLacpControlStatus OBJECT-TYPE
                        SYNTAX FkControlStatusType
                        MAX-ACCESS read-only
                        STATUS current
                        DESCRIPTION
                                "The status of user command"
                        ::= { fkLagLacpControl 2 }

                
                -- 1.3.6.1.4.1.10428 9 1.101.3.11.3.3
                fkLagLacpControlTimer OBJECT-TYPE
                        SYNTAX Gauge32
                        MAX-ACCESS read-write
                        STATUS current
                        DESCRIPTION
                                "The maximum time for the manager for a long running user command"
                        ::= { fkLagLacpControl 3 }

                
                -- 1.3.6.1.4.1.10428 9 1.101.3.11.3.4
                fkLagLacpControlTimeStamp OBJECT-TYPE
                        SYNTAX TimeTicks
                        MAX-ACCESS read-only
                        STATUS current
                        DESCRIPTION
                                "The time stamp of the last command(end of command)"
                        ::= { fkLagLacpControl 4 }

                
                -- 1.3.6.1.4.1.10428 9 1.101.3.11.3.5
                fkLagLacpControlReqResult OBJECT-TYPE
                        SYNTAX FkControlRequestResultType
                        MAX-ACCESS read-only
                        STATUS current
                        DESCRIPTION
                                "The result of the last user command"
                        ::= { fkLagLacpControl 5 }

                
                -- 1.3.6.1.4.1.10428 9 1.101.3.11.4
                fkLagLacpNotification OBJECT IDENTIFIER ::= { fkLagLacp 4 }

                
                -- 1.3.6.1.4.1.10428 9 1.101.3.11.4.1
                fkLagLacpStatsCleared NOTIFICATION-TYPE
                        OBJECTS { fkLagLacpControlRequest, fkLagLacpControlTimeStamp, fkLagLacpControlReqResult }
                        STATUS current
                        DESCRIPTION 
                                "Description."
                        ::= { fkLagLacpNotification 1 }

                
--  1.3.6.1.4.1.10428 9 1.9.8.12
                -- 1.3.6.1.4.1.10428 9 1.101.3.12
                fkLagLacpPort OBJECT IDENTIFIER ::= { fkBridge 12 }

                
--  1.3.6.1.4.1.10428 9 1.9.8.12.1
                -- 1.3.6.1.4.1.10428 9 1.101.3.12.1
                fkLagLacpPortTable OBJECT-TYPE
                        SYNTAX SEQUENCE OF FkLagLacpPortEntry
                        MAX-ACCESS not-accessible
                        STATUS current
                        DESCRIPTION
                                " lag LACP port table."
                        ::= { fkLagLacpPort 1 }

                
--  1.3.6.1.4.1.10428 9 1.9.8.12.1.1
                -- 1.3.6.1.4.1.10428 9 1.101.3.12.1.1
                fkLagLacpPortEntry OBJECT-TYPE
                        SYNTAX FkLagLacpPortEntry
                        MAX-ACCESS not-accessible
                        STATUS current
                        DESCRIPTION
                                " key: fkLagLacpPortIndex"
                        INDEX { fkLagLacpPortIndex }
                        ::= { fkLagLacpPortTable 1 }

                
                FkLagLacpPortEntry ::=
                        SEQUENCE { 
                                fkLagLacpPortIndex
                                        InterfaceIndex,
                                fkLagLacpPortActivity
                                        INTEGER,
                                fkLagLacpPortActorPriority
                                        INTEGER,
                                fkLagLacpPortActorAggregatorId
                                        Integer32,
                                fkLagLacpPortActorAdminKey
                                        INTEGER,
                                fkLagLacpPortActorAdminState
                                        BITS,
                                fkLagLacpPortActorOperKey
                                        Integer32,
                                fkLagLacpPortActorOperState
                                        BITS,
                                fkLagLacpPortPartnerAdminSystemMAC
                                        OCTET STRING,
                                fkLagLacpPortPartnerAdminSystemPriority
                                        Integer32,
                                fkLagLacpPortPartnerAdminKey
                                        Integer32,
                                fkLagLacpPortPartnerAdminNum
                                        InterfaceIndex,
                                fkLagLacpPortPartnerAdminPriority
                                        Integer32,
                                fkLagLacpPortPartnerAdminState
                                        BITS,
                                fkLagLacpPortPartnerOperSystemMAC
                                        OCTET STRING,
                                fkLagLacpPortPartnerOperSystemPriority
                                        Integer32,
                                fkLagLacpPortPartnerOperKey
                                        Integer32,
                                fkLagLacpPortPartnerOperNum
                                        InterfaceIndex,
                                fkLagLacpPortPartnerOperPriority
                                        Integer32,
                                fkLagLacpPortPartnerOperState
                                        BITS
                         }

--  1.3.6.1.4.1.10428 9 1.9.8.12.1.1.1
                -- 1.3.6.1.4.1.10428 9 1.101.3.12.1.1.1
                fkLagLacpPortIndex OBJECT-TYPE
                        SYNTAX InterfaceIndex
                        MAX-ACCESS read-only
                        STATUS current
                        DESCRIPTION
                                "The IP address of the RADIUS server referred 
                                to in this table entry."
                        ::= { fkLagLacpPortEntry 1 }

                
                -- 1.3.6.1.4.1.10428 9 1.101.3.12.1.1.2
                fkLagLacpPortActivity OBJECT-TYPE
                        SYNTAX INTEGER
                                {
                                disable(0),
                                enable(1)
                                }
                        MAX-ACCESS read-only
                        STATUS current
                        DESCRIPTION
                                "show lacp activity of port"
                        ::= { fkLagLacpPortEntry 2 }

                
--  1.3.6.1.4.1.10428 9 1.9.8.12.1.1.2
                -- 1.3.6.1.4.1.10428 9 1.101.3.12.1.1.3
                fkLagLacpPortActorPriority OBJECT-TYPE
                        SYNTAX INTEGER (1..65535)
                        MAX-ACCESS read-only
                        STATUS current
                        DESCRIPTION
                                "The priority assigned to the port by Actor."
                        ::= { fkLagLacpPortEntry 3 }

                
--  1.3.6.1.4.1.10428 9 1.9.8.12.1.1.3
                -- 1.3.6.1.4.1.10428 9 1.101.3.12.1.1.4
                fkLagLacpPortActorAggregatorId OBJECT-TYPE
                        SYNTAX Integer32
                        MAX-ACCESS read-only
                        STATUS current
                        DESCRIPTION
                                " The aggregator index."
                        ::= { fkLagLacpPortEntry 4 }

                
--  1.3.6.1.4.1.10428 9 1.9.8.12.1.1.4
                -- 1.3.6.1.4.1.10428 9 1.101.3.12.1.1.5
                fkLagLacpPortActorAdminKey OBJECT-TYPE
                        SYNTAX INTEGER (1..65535)
                        MAX-ACCESS read-only
                        STATUS current
                        DESCRIPTION
                                "The administrable Key value assigned to the 
                                port by the Actor."
                        ::= { fkLagLacpPortEntry 5 }

                
--  1.3.6.1.4.1.10428 9 1.9.8.12.1.1.5
                -- 1.3.6.1.4.1.10428 9 1.101.3.12.1.1.6
                fkLagLacpPortActorAdminState OBJECT-TYPE
                        SYNTAX BITS
                                {
                                expired(0),
                                defaulted(1),
                                destributing(2),
                                collecting(3),
                                synchronization(4),
                                aggregation(5),
                                lacpTimeout(6),
                                lacpActivity(7)
                                }
                        MAX-ACCESS read-only
                        STATUS current
                        DESCRIPTION
                                "The Actor's administrable state variables for the port."
                        ::= { fkLagLacpPortEntry 6 }

                
--  1.3.6.1.4.1.10428 9 1.9.8.12.1.1.6
                -- 1.3.6.1.4.1.10428 9 1.101.3.12.1.1.7
                fkLagLacpPortActorOperKey OBJECT-TYPE
                        SYNTAX Integer32 (1..65535)
                        MAX-ACCESS read-only
                        STATUS current
                        DESCRIPTION
                                "The operational Key value assigned to the 
                                port by the Actor."
                        ::= { fkLagLacpPortEntry 7 }

                
--  1.3.6.1.4.1.10428 9 1.9.8.12.1.1.7
                -- 1.3.6.1.4.1.10428 9 1.101.3.12.1.1.8
                fkLagLacpPortActorOperState OBJECT-TYPE
                        SYNTAX BITS
                                {
                                expired(0),
                                defaulted(1),
                                destributing(2),
                                collecting(3),
                                synchronization(4),
                                aggregation(5),
                                lacpTmeout(6),
                                lacpActivity(7)
                                }
                        MAX-ACCESS read-only
                        STATUS current
                        DESCRIPTION
                                "The Actor's operational state variables for the port."
                        ::= { fkLagLacpPortEntry 8 }

                
--  1.3.6.1.4.1.10428 9 1.9.8.12.1.1.8
                -- 1.3.6.1.4.1.10428 9 1.101.3.12.1.1.9
                fkLagLacpPortPartnerAdminSystemMAC OBJECT-TYPE
                        SYNTAX OCTET STRING
                        MAX-ACCESS read-only
                        STATUS current
                        DESCRIPTION
                                "The Partner's Administrable System ID, 
                                encoded as a MAC address."
                        ::= { fkLagLacpPortEntry 9 }

                
--  1.3.6.1.4.1.10428 9 1.9.8.12.1.1.9
                -- 1.3.6.1.4.1.10428 9 1.101.3.12.1.1.10
                fkLagLacpPortPartnerAdminSystemPriority OBJECT-TYPE
                        SYNTAX Integer32 (1..65535)
                        MAX-ACCESS read-only
                        STATUS current
                        DESCRIPTION
                                "The administrable priority assigned to the 
                                Partner System."
                        ::= { fkLagLacpPortEntry 10 }

                
--  1.3.6.1.4.1.10428 9 1.9.8.12.1.1.10
                -- 1.3.6.1.4.1.10428 9 1.101.3.12.1.1.11
                fkLagLacpPortPartnerAdminKey OBJECT-TYPE
                        SYNTAX Integer32 (1..65535)
                        MAX-ACCESS read-only
                        STATUS current
                        DESCRIPTION
                                "The administrable Key value assigned to 
                                the port by the Partner."
                        ::= { fkLagLacpPortEntry 11 }

                
--  1.3.6.1.4.1.10428 9 1.9.8.12.1.1.11
                -- 1.3.6.1.4.1.10428 9 1.101.3.12.1.1.12
                fkLagLacpPortPartnerAdminNum OBJECT-TYPE
                        SYNTAX InterfaceIndex
                        MAX-ACCESS read-only
                        STATUS current
                        DESCRIPTION
                                "The administrable number value assigned 
                                to the port by the Partner."
                        ::= { fkLagLacpPortEntry 12 }

                
--  1.3.6.1.4.1.10428 9 1.9.8.12.1.1.12
                -- 1.3.6.1.4.1.10428 9 1.101.3.12.1.1.13
                fkLagLacpPortPartnerAdminPriority OBJECT-TYPE
                        SYNTAX Integer32 (1..65535)
                        MAX-ACCESS read-only
                        STATUS current
                        DESCRIPTION
                                "The administrable priority assigned to 
                                this port by the Partner."
                        ::= { fkLagLacpPortEntry 13 }

                
--  1.3.6.1.4.1.10428 9 1.9.8.12.1.1.13
                -- 1.3.6.1.4.1.10428 9 1.101.3.12.1.1.14
                fkLagLacpPortPartnerAdminState OBJECT-TYPE
                        SYNTAX BITS
                                {
                                expired(0),
                                defaulted(1),
                                destributing(2),
                                collecting(3),
                                synchronization(4),
                                aggregation(5),
                                lacpTmeout(6),
                                lacpActivity(7)
                                }
                        MAX-ACCESS read-only
                        STATUS current
                        DESCRIPTION
                                "The administrable state assigned to this 
                                port by the Partner."
                        ::= { fkLagLacpPortEntry 14 }

                
--  1.3.6.1.4.1.10428 9 1.9.8.12.1.1.14
                -- 1.3.6.1.4.1.10428 9 1.101.3.12.1.1.15
                fkLagLacpPortPartnerOperSystemMAC OBJECT-TYPE
                        SYNTAX OCTET STRING
                        MAX-ACCESS read-only
                        STATUS current
                        DESCRIPTION
                                "The Partner's operational System ID, 
                                encoded as a MAC address."
                        ::= { fkLagLacpPortEntry 15 }

                
--  1.3.6.1.4.1.10428 9 1.9.8.12.1.1.15
                -- 1.3.6.1.4.1.10428 9 1.101.3.12.1.1.16
                fkLagLacpPortPartnerOperSystemPriority OBJECT-TYPE
                        SYNTAX Integer32 (1..65535)
                        MAX-ACCESS read-only
                        STATUS current
                        DESCRIPTION
                                "The operational priority assigned to 
                                the Partner System."
                        ::= { fkLagLacpPortEntry 16 }

                
--  1.3.6.1.4.1.10428 9 1.9.8.12.1.1.16
                -- 1.3.6.1.4.1.10428 9 1.101.3.12.1.1.17
                fkLagLacpPortPartnerOperKey OBJECT-TYPE
                        SYNTAX Integer32 (1..65535)
                        MAX-ACCESS read-only
                        STATUS current
                        DESCRIPTION
                                "The operational Key value assigned to the 
                                port by the Partner."
                        ::= { fkLagLacpPortEntry 17 }

                
--  1.3.6.1.4.1.10428 9 1.9.8.12.1.1.17
                -- 1.3.6.1.4.1.10428 9 1.101.3.12.1.1.18
                fkLagLacpPortPartnerOperNum OBJECT-TYPE
                        SYNTAX InterfaceIndex
                        MAX-ACCESS read-only
                        STATUS current
                        DESCRIPTION
                                "The operational number value assigned to 
                                the port by the Partner."
                        ::= { fkLagLacpPortEntry 18 }

                
--  1.3.6.1.4.1.10428 9 1.9.8.12.1.1.18
                -- 1.3.6.1.4.1.10428 9 1.101.3.12.1.1.19
                fkLagLacpPortPartnerOperPriority OBJECT-TYPE
                        SYNTAX Integer32 (1..65535)
                        MAX-ACCESS read-only
                        STATUS current
                        DESCRIPTION
                                "The operational priority assigned to 
                                this port by the Partner."
                        ::= { fkLagLacpPortEntry 19 }

                
--  1.3.6.1.4.1.10428 9 1.9.8.12.1.1.19
                -- 1.3.6.1.4.1.10428 9 1.101.3.12.1.1.20
                fkLagLacpPortPartnerOperState OBJECT-TYPE
                        SYNTAX BITS
                                {
                                expired(0),
                                defaulted(1),
                                destributing(2),
                                collecting(3),
                                synchronization(4),
                                aggregation(5),
                                lacpTimeout(6),
                                lacpActivity(7)
                                }
                        MAX-ACCESS read-only
                        STATUS current
                        DESCRIPTION
                                "The operational state assigned to this 
                                port by the Partner."
                        ::= { fkLagLacpPortEntry 20 }

                
--  1.3.6.1.4.1.10428 9 1.9.8.12.2
                -- 1.3.6.1.4.1.10428 9 1.101.3.12.2
                fkLagLacpPortControl OBJECT IDENTIFIER ::= { fkLagLacpPort 2 }

                
--  1.3.6.1.4.1.10428 9 1.9.8.12.2.1
                -- 1.3.6.1.4.1.10428 9 1.101.3.12.2.1
                fkLagLacpPortControlRequest OBJECT-TYPE
                        SYNTAX INTEGER { setLagLacpPortProfile(1) }
                        MAX-ACCESS read-write
                        STATUS current
                        DESCRIPTION
                                "The MIB object for the user command."
                        ::= { fkLagLacpPortControl 1 }

                
--  1.3.6.1.4.1.10428 9 1.9.8.12.2.2
                -- 1.3.6.1.4.1.10428 9 1.101.3.12.2.2
                fkLagLacpPortControlStatus OBJECT-TYPE
                        SYNTAX FkControlStatusType
                        MAX-ACCESS read-only
                        STATUS current
                        DESCRIPTION
                                "Describes the status of a user command group, 
                                used for block commands while a command execution in process."
                        ::= { fkLagLacpPortControl 2 }

                
--  1.3.6.1.4.1.10428 9 1.9.8.12.2.3
                -- 1.3.6.1.4.1.10428 9 1.101.3.12.2.3
                fkLagLacpPortControlTimer OBJECT-TYPE
                        SYNTAX Gauge32
                        MAX-ACCESS read-write
                        STATUS current
                        DESCRIPTION
                                "Maximum command duration time in case of long running"
                        ::= { fkLagLacpPortControl 3 }

                
--  1.3.6.1.4.1.10428 9 1.9.8.12.2.5
                -- 1.3.6.1.4.1.10428 9 1.101.3.12.2.4
                fkLagLacpPortControlTimeStamp OBJECT-TYPE
                        SYNTAX TimeStamp
                        MAX-ACCESS read-only
                        STATUS current
                        DESCRIPTION
                                "Time stamp attribute set at end of command."
                        ::= { fkLagLacpPortControl 4 }

                
--  1.3.6.1.4.1.10428 9 1.9.8.12.2.4
                -- 1.3.6.1.4.1.10428 9 1.101.3.12.2.5
                fkLagLacpPortControlReqResult OBJECT-TYPE
                        SYNTAX FkControlRequestResultType
                        MAX-ACCESS read-only
                        STATUS current
                        DESCRIPTION
                                "Command result attribute."
                        ::= { fkLagLacpPortControl 5 }

                
--  1.3.6.1.4.1.10428 9 1.9.8.12.2.6
                -- 1.3.6.1.4.1.10428 9 1.101.3.12.2.6
                fkLagLacpPortControlIndex OBJECT-TYPE
                        SYNTAX InterfaceIndex
                        MAX-ACCESS read-write
                        STATUS current
                        DESCRIPTION
                                "The IP address of the RADIUS server referred to 
                                in this table entry."
                        ::= { fkLagLacpPortControl 6 }

                
                -- 1.3.6.1.4.1.10428 9 1.101.3.12.2.7
                fkLagLacpPortControlActivity OBJECT-TYPE
                        SYNTAX INTEGER
                                {
                                disable(0),
                                enable(1)
                                }
                        MAX-ACCESS read-write
                        STATUS current
                        DESCRIPTION
                                "show lacp activity of port"
                        ::= { fkLagLacpPortControl 7 }

                
--  1.3.6.1.4.1.10428 9 1.9.8.12.2.7
                -- 1.3.6.1.4.1.10428 9 1.101.3.12.2.8
                fkLagLacpPortControlMode OBJECT-TYPE
                        SYNTAX INTEGER
                                {
                                active(1),
                                passive(2)
                                }
                        MAX-ACCESS read-write
                        STATUS current
                        DESCRIPTION
                                "set LACP_Activity in fkLagLacpPortActorAdminState"
                        ::= { fkLagLacpPortControl 8 }

                
--  1.3.6.1.4.1.10428 9 1.9.8.12.2.8
                -- 1.3.6.1.4.1.10428 9 1.101.3.12.2.9
                fkLagLacpPortControlAdminKey OBJECT-TYPE
                        SYNTAX Integer32 (0..15)
                        MAX-ACCESS read-write
                        STATUS current
                        DESCRIPTION
                                "The administrable Key value assigned to the 
                                port by the Actor."
                        ::= { fkLagLacpPortControl 9 }

                
--  1.3.6.1.4.1.10428 9 1.9.8.12.2.9
                -- 1.3.6.1.4.1.10428 9 1.101.3.12.2.10
                fkLagLacpPortControlAggregation OBJECT-TYPE
                        SYNTAX INTEGER
                                {
                                aggregatable(1),
                                individual(2)
                                }
                        MAX-ACCESS read-write
                        STATUS current
                        DESCRIPTION
                                "set Aggregation in fkLagLacpPortActorAdminState."
                        ::= { fkLagLacpPortControl 10 }

                
--  Radius Server operation mode: if set bit 0, is used 
-- in login, and if set bit 1, is used in 802.1X (dot1x).
-- 1.3.6.1.4.1.10428 9 1.9.8.12.2.10
                -- 1.3.6.1.4.1.10428 9 1.101.3.12.2.11
                fkLagLacpPortControlPriority OBJECT-TYPE
                        SYNTAX Integer32 (1..65535)
                        MAX-ACCESS read-write
                        STATUS current
                        DESCRIPTION
                                "The priority assigned to the port by Actor."
                        ::= { fkLagLacpPortControl 11 }

                
--  1.3.6.1.4.1.10428 9 1.9.8.12.2.11
                -- 1.3.6.1.4.1.10428 9 1.101.3.12.2.12
                fkLagLacpPortControlTimeout OBJECT-TYPE
                        SYNTAX INTEGER
                                {
                                short(1),
                                long(2)
                                }
                        MAX-ACCESS read-write
                        STATUS current
                        DESCRIPTION
                                "set LACP_Timeout in fkLagLacpPortActorAdminState."
                        ::= { fkLagLacpPortControl 12 }

                
--  1.3.6.1.4.1.10428 9 1.9.8.12.3
                -- 1.3.6.1.4.1.10428 9 1.101.3.12.3
                fkLagLacpPortNotification OBJECT IDENTIFIER ::= { fkLagLacpPort 3 }

                
--  1.3.6.1.4.1.10428 9 1.9.8.12.3.1
                -- 1.3.6.1.4.1.10428 9 1.101.3.12.3.1
                fkLagLacpPortProfileChanged NOTIFICATION-TYPE
                        OBJECTS { fkLagLacpPortControlRequest, fkLagLacpPortControlReqResult, fkLagLacpPortControlTimeStamp, fkLagLacpPortActorAdminKey, fkLagLacpPortActorPriority, 
                                fkLagLacpPortActorAdminState }
                        STATUS current
                        DESCRIPTION 
                                " "
                        ::= { fkLagLacpPortNotification 1 }

                
--  1.3.6.1.4.1.10428 9 1.9.8.12.3.2
                -- 1.3.6.1.4.1.10428 9 1.101.3.12.3.2
                fkLagLacpPortAggreChanged NOTIFICATION-TYPE
                        OBJECTS { fkLagLacpPortControlRequest, fkLagLacpPortControlReqResult, fkLagLacpPortControlTimeStamp, fkLagLacpPortActorAggregatorId }
                        STATUS current
                        DESCRIPTION 
                                " "
                        ::= { fkLagLacpPortNotification 2 }

                
--  1.3.6.1.4.1.10428 9 1.9.8.13
                -- 1.3.6.1.4.1.10428 9 1.101.3.13
                fkFdb OBJECT IDENTIFIER ::= { fkBridge 13 }

                
--  1.3.6.1.4.1.10428 9 1.9.8.13.2
                -- 1.3.6.1.4.1.10428 9 1.101.3.13.1
                fkFdbTable OBJECT-TYPE
                        SYNTAX SEQUENCE OF FkFdbEntry
                        MAX-ACCESS not-accessible
                        STATUS current
                        DESCRIPTION
                                "The table of FDB entries."
                        ::= { fkFdb 1 }

                
--  1.3.6.1.4.1.10428 9 1.9.8.13.2.1
                -- 1.3.6.1.4.1.10428 9 1.101.3.13.1.1
                fkFdbEntry OBJECT-TYPE
                        SYNTAX FkFdbEntry
                        MAX-ACCESS not-accessible
                        STATUS current
                        DESCRIPTION
                                "The table entry of FDB table.
                                key: fkFdbEntryFid, fkFdbEntryPort, fkFdbEntryMacAddress"
                        INDEX { fkFdbEntryFid, fkFdbEntryPort, fkFdbEntryMacAddress }
                        ::= { fkFdbTable 1 }

                
                FkFdbEntry ::=
                        SEQUENCE { 
                                fkFdbEntryFid
                                        INTEGER,
                                fkFdbEntryPort
                                        INTEGER,
                                fkFdbEntryMacAddress
                                        OCTET STRING,
                                fkFdbEntryVid
                                        INTEGER,
                                fkFdbEntryMode
                                        INTEGER,
                                fkFdbEntryPermission
                                        INTEGER,
                                fkFdbEntryElapsedTime
                                        Unsigned32
                         }

--  1.3.6.1.4.1.10428 9 1.9.8.13.2.1.1
                -- 1.3.6.1.4.1.10428 9 1.101.3.13.1.1.1
                fkFdbEntryFid OBJECT-TYPE
                        SYNTAX INTEGER (1..4094)
                        MAX-ACCESS read-only
                        STATUS current
                        DESCRIPTION
                                "FDB identify."
                        ::= { fkFdbEntry 1 }

                
--  1.3.6.1.4.1.10428 9 1.9.8.13.2.1.2
                -- 1.3.6.1.4.1.10428 9 1.101.3.13.1.1.2
                fkFdbEntryPort OBJECT-TYPE
                        SYNTAX INTEGER (1..255)
                        MAX-ACCESS read-only
                        STATUS current
                        DESCRIPTION
                                "The port number of the port on which 
                                a frame having a source address equal 
                                to the value of the corresponding instance 
                                of fkoltg1040FdbAddress has been seen."
                        ::= { fkFdbEntry 2 }

                
--  1.3.6.1.4.1.10428 9 1.9.8.13.2.1.3
                -- 1.3.6.1.4.1.10428 9 1.101.3.13.1.1.3
                fkFdbEntryMacAddress OBJECT-TYPE
                        SYNTAX OCTET STRING (SIZE (0..6))
                        MAX-ACCESS read-only
                        STATUS current
                        DESCRIPTION
                                "A unicast MAC address for which the device has
                                forwarding or filtering information."
                        ::= { fkFdbEntry 3 }

                
--  1.3.6.1.4.1.10428 9 1.9.8.13.2.1.5
                -- 1.3.6.1.4.1.10428 9 1.101.3.13.1.1.4
                fkFdbEntryVid OBJECT-TYPE
                        SYNTAX INTEGER (1..4094)
                        MAX-ACCESS read-only
                        STATUS current
                        DESCRIPTION
                                "VLAN ID."
                        ::= { fkFdbEntry 4 }

                
--  1.3.6.1.4.1.10428 9 1.9.8.13.2.1.4
                -- 1.3.6.1.4.1.10428 9 1.101.3.13.1.1.5
                fkFdbEntryMode OBJECT-TYPE
                        SYNTAX INTEGER
                                {
                                local(0),
                                static(1),
                                dynamic(2)
                                }
                        MAX-ACCESS read-only
                        STATUS current
                        DESCRIPTION
                                "FDB Entry's mode.
                                The status of this entry.  The meanings of the values
                                are:
                                    local(0)   - the value of the corresponding instance 
                                                 of fkFdbMacAddress was own.
                                    static(1)  - the value of the corresponding instance 
                                                 of fkFdbMacAddress was specified by management. 
                                    dynamic(2) - the value of the corresponding instance
                                                 of fkFdbMacAddress was learned."
                        ::= { fkFdbEntry 5 }

                
--  1.3.6.1.4.1.10428 9 1.9.8.13.2.1.6
                -- 1.3.6.1.4.1.10428 9 1.101.3.13.1.1.6
                fkFdbEntryPermission OBJECT-TYPE
                        SYNTAX INTEGER
                                {
                                deny(0),
                                permit(1)
                                }
                        MAX-ACCESS read-only
                        STATUS current
                        DESCRIPTION
                                "The permission of fkoltg1040FdbAddress.
                                The meanings of the values are:
                                    deny(0)   - the value of the corresponding instance
                                                of fkoltg1040FdbAddress will be dropped.
                                    permit(1) - the value of the corresponding instance
                                                of fkoltg1040FdbAddress will be flooded.
                                "
                        ::= { fkFdbEntry 6 }

                
--  1.3.6.1.4.1.10428 9 1.9.8.13.2.1.7
                -- 1.3.6.1.4.1.10428 9 1.101.3.13.1.1.7
                fkFdbEntryElapsedTime OBJECT-TYPE
                        SYNTAX Unsigned32
                        MAX-ACCESS read-only
                        STATUS current
                        DESCRIPTION
                                "Elapsed time after registered"
                        ::= { fkFdbEntry 7 }

                
--  1.3.6.1.4.1.10428 9 1.9.8.13.3
                -- 1.3.6.1.4.1.10428 9 1.101.3.13.2
                fkFdbControl OBJECT IDENTIFIER ::= { fkFdb 2 }

                
--  1.3.6.1.4.1.10428 9 1.9.8.13.3.1
                -- 1.3.6.1.4.1.10428 9 1.101.3.13.2.1
                fkFdbEntryControlRequest OBJECT-TYPE
                        SYNTAX INTEGER
                                {
                                createFdbEntry(1),
                                destoryFdbEntry(2),
                                clearFdbTableEntries(3)
                                }
                        MAX-ACCESS read-write
                        STATUS current
                        DESCRIPTION
                                "Control Request."
                        ::= { fkFdbControl 1 }

                
--  1.3.6.1.4.1.10428 9 1.9.8.13.3.2
                -- 1.3.6.1.4.1.10428 9 1.101.3.13.2.2
                fkFdbEntryControlStatus OBJECT-TYPE
                        SYNTAX FkControlStatusType
                        MAX-ACCESS read-only
                        STATUS current
                        DESCRIPTION
                                "Control Status."
                        ::= { fkFdbControl 2 }

                
--  1.3.6.1.4.1.10428 9 1.9.8.13.3.3
                -- 1.3.6.1.4.1.10428 9 1.101.3.13.2.3
                fkFdbEntryControlTimer OBJECT-TYPE
                        SYNTAX Gauge32
                        MAX-ACCESS read-write
                        STATUS current
                        DESCRIPTION
                                "Cotrol Timer."
                        ::= { fkFdbControl 3 }

                
--  1.3.6.1.4.1.10428 9 1.9.8.13.3.5
                -- 1.3.6.1.4.1.10428 9 1.101.3.13.2.4
                fkFdbEntryControlTImeStamp OBJECT-TYPE
                        SYNTAX TimeTicks
                        MAX-ACCESS read-only
                        STATUS current
                        DESCRIPTION
                                " The time stamp of the last command(end of command)"
                        ::= { fkFdbControl 4 }

                
--  1.3.6.1.4.1.10428 9 1.9.8.13.3.4
                -- 1.3.6.1.4.1.10428 9 1.101.3.13.2.5
                fkFdbEntryControlReqResult OBJECT-TYPE
                        SYNTAX FkControlRequestResultType
                        MAX-ACCESS read-only
                        STATUS current
                        DESCRIPTION
                                " The result of the last user command"
                        ::= { fkFdbControl 5 }

                
--  1.3.6.1.4.1.10428 9 1.9.8.13.3.6
                -- 1.3.6.1.4.1.10428 9 1.101.3.13.2.6
                fkFdbEntryControlFid OBJECT-TYPE
                        SYNTAX Integer32 (1..4094)
                        MAX-ACCESS read-write
                        STATUS current
                        DESCRIPTION
                                "FDB identifier."
                        ::= { fkFdbControl 6 }

                
--  1.3.6.1.4.1.10428 9 1.9.8.13.3.7
                -- 1.3.6.1.4.1.10428 9 1.101.3.13.2.7
                fkFdbEntryControlPort OBJECT-TYPE
                        SYNTAX INTEGER (0..255)
                        MAX-ACCESS read-write
                        STATUS current
                        DESCRIPTION
                                "The port number of FDB entry.
                                 0 : any (all) port."
                        ::= { fkFdbControl 7 }

                
--  1.3.6.1.4.1.10428 9 1.9.8.13.3.8
                -- 1.3.6.1.4.1.10428 9 1.101.3.13.2.8
                fkFdbEntryControlMacAddress OBJECT-TYPE
                        SYNTAX OCTET STRING (SIZE (0..6))
                        MAX-ACCESS read-write
                        STATUS current
                        DESCRIPTION
                                "MAC address of FDB entry."
                        ::= { fkFdbControl 8 }

                
--  1.3.6.1.4.1.10428 9 1.9.8.13.4
                -- 1.3.6.1.4.1.10428 9 1.101.3.13.3
                fkFdbNotification OBJECT IDENTIFIER ::= { fkFdb 3 }

                
--  1.3.6.1.4.1.10428 9 1.9.8.13.4.2
                -- 1.3.6.1.4.1.10428 9 1.101.3.13.3.1
                fkFdbEntryCreated NOTIFICATION-TYPE
                        OBJECTS { fkFdbEntryControlRequest, fkFdbEntryControlTImeStamp, fkFdbEntryControlReqResult, fkFdbEntryPermission }
                        STATUS current
                        DESCRIPTION 
                                "Created FDB Entry."
                        ::= { fkFdbNotification 1 }

                
--  1.3.6.1.4.1.10428 9 1.9.8.13.4.3
                -- 1.3.6.1.4.1.10428 9 1.101.3.13.3.2
                fkFdbEntryDestoryed NOTIFICATION-TYPE
                        OBJECTS { fkFdbEntryControlRequest, fkFdbEntryControlTImeStamp, fkFdbEntryControlMacAddress, fkFdbEntryControlReqResult }
                        STATUS current
                        DESCRIPTION 
                                "Destroyed FDB Entry."
                        ::= { fkFdbNotification 2 }

                
                -- 1.3.6.1.4.1.10428 9 1.101.3.13.3.3
                fkFdbTableEntriesCleared NOTIFICATION-TYPE
                        OBJECTS { fkFdbEntryControlRequest, fkFdbEntryControlTImeStamp, fkFdbEntryControlMacAddress, fkFdbEntryControlReqResult }
                        STATUS current
                        DESCRIPTION 
                                "clearFdbTableEntries.
                                 In this notification PDU, key of fkFdbEntryPort 
                                 is fid.port.6.0.0.0.0.0.0.
                                 If port is 0, is cleared on all ports in fid."
                        ::= { fkFdbNotification 3 }

                
--  1.3.6.1.4.1.10428 9 1.9.8.14
                -- 1.3.6.1.4.1.10428 9 1.101.3.14
                fkMfdb OBJECT IDENTIFIER ::= { fkBridge 14 }

                
--  1.3.6.1.4.1.10428 9 1.9.8.14.1
                -- 1.3.6.1.4.1.10428 9 1.101.3.14.1
                fkMfdbTable OBJECT-TYPE
                        SYNTAX SEQUENCE OF FkMfdbEntry
                        MAX-ACCESS not-accessible
                        STATUS current
                        DESCRIPTION
                                "The table of MFDB entries."
                        ::= { fkMfdb 1 }

                
--  1.3.6.1.4.1.10428 9 1.9.8.14.1.1
                -- 1.3.6.1.4.1.10428 9 1.101.3.14.1.1
                fkMfdbEntry OBJECT-TYPE
                        SYNTAX FkMfdbEntry
                        MAX-ACCESS not-accessible
                        STATUS current
                        DESCRIPTION
                                "Information about a specific MAC address that
                                should be forwarding or dropping.
                                key: fkMfdbMacAddress"
                        INDEX { fkMfdbMacAddress }
                        ::= { fkMfdbTable 1 }

                
                FkMfdbEntry ::=
                        SEQUENCE { 
                                fkMfdbMacAddress
                                        OCTET STRING,
                                fkMfdbEntryPermission
                                        INTEGER,
                                fkMfdbVlanIndex
                                        INTEGER,
                                fkMfdbPorts
                                        OCTET STRING
                         }

--  1.3.6.1.4.1.10428 9 1.9.8.14.1.1.1
                -- 1.3.6.1.4.1.10428 9 1.101.3.14.1.1.1
                fkMfdbMacAddress OBJECT-TYPE
                        SYNTAX OCTET STRING (SIZE (0..6))
                        MAX-ACCESS read-only
                        STATUS current
                        DESCRIPTION
                                "A unicast MAC address for which the device has
                                forwarding or filtering information."
                        ::= { fkMfdbEntry 1 }

                
--  1.3.6.1.4.1.10428 9 1.9.8.14.1.1.2
                -- 1.3.6.1.4.1.10428 9 1.101.3.14.1.1.2
                fkMfdbEntryPermission OBJECT-TYPE
                        SYNTAX INTEGER
                                {
                                deny(0),
                                permit(1)
                                }
                        MAX-ACCESS read-only
                        STATUS current
                        DESCRIPTION
                                "The permission of fkMFdbMacAddress.
                                The meanings of the values are: 
                                    deny(0)   - the value of the corresponding instance
                                                of fkMfdbMacAddress will be dropped.
                                    permit(1) - the value of the corresponding instance
                                                of fkMfdbMacAddress will be flooded.
                                "
                        ::= { fkMfdbEntry 2 }

                
                -- 1.3.6.1.4.1.10428 9 1.101.3.14.1.1.3
                fkMfdbVlanIndex OBJECT-TYPE
                        SYNTAX INTEGER (0 | 1..4094)
                        MAX-ACCESS read-only
                        STATUS current
                        DESCRIPTION
                                "vlan index
                                "
                        ::= { fkMfdbEntry 3 }

                
                -- 1.3.6.1.4.1.10428 9 1.101.3.14.1.1.4
                fkMfdbPorts OBJECT-TYPE
                        SYNTAX OCTET STRING (SIZE (0..32))
                        MAX-ACCESS read-write
                        STATUS current
                        DESCRIPTION
                                "Port Map"
                        ::= { fkMfdbEntry 4 }

                
--  1.3.6.1.4.1.10428 9 1.9.8.14.2
                -- 1.3.6.1.4.1.10428 9 1.101.3.14.2
                fkMfdbControl OBJECT IDENTIFIER ::= { fkMfdb 2 }

                
--  1.3.6.1.4.1.10428 9 1.9.8.14.2.1
                -- 1.3.6.1.4.1.10428 9 1.101.3.14.2.1
                fkMfdbControlRequest OBJECT-TYPE
                        SYNTAX INTEGER
                                {
                                createMfdbEntry(1),
                                destoryMfdbEntry(2),
                                setMfdbEntryPermission(3),
                                clearMfdbEntryTable(4)
                                }
                        MAX-ACCESS read-write
                        STATUS current
                        DESCRIPTION
                                " The request of a user command"
                        ::= { fkMfdbControl 1 }

                
--  1.3.6.1.4.1.10428 9 1.9.8.14.2.2
                -- 1.3.6.1.4.1.10428 9 1.101.3.14.2.2
                fkMfdbControlStatus OBJECT-TYPE
                        SYNTAX FkControlStatusType
                        MAX-ACCESS read-only
                        STATUS current
                        DESCRIPTION
                                " The status of user command"
                        ::= { fkMfdbControl 2 }

                
--  1.3.6.1.4.1.10428 9 1.9.8.14.2.3
                -- 1.3.6.1.4.1.10428 9 1.101.3.14.2.3
                fkMfdbControlTimer OBJECT-TYPE
                        SYNTAX Gauge32
                        MAX-ACCESS read-write
                        STATUS current
                        DESCRIPTION
                                " The maximum time for the manager for a long running user command"
                        ::= { fkMfdbControl 3 }

                
--  1.3.6.1.4.1.10428 9 1.9.8.14.2.5
                -- 1.3.6.1.4.1.10428 9 1.101.3.14.2.4
                fkMfdbControlTimeStamp OBJECT-TYPE
                        SYNTAX TimeTicks
                        MAX-ACCESS read-only
                        STATUS current
                        DESCRIPTION
                                " The time stamp of the last command(end of command)"
                        ::= { fkMfdbControl 4 }

                
--  1.3.6.1.4.1.10428 9 1.9.8.14.2.4
                -- 1.3.6.1.4.1.10428 9 1.101.3.14.2.5
                fkMfdbControlReqResult OBJECT-TYPE
                        SYNTAX FkControlRequestResultType
                        MAX-ACCESS read-only
                        STATUS current
                        DESCRIPTION
                                " The result of the last user command"
                        ::= { fkMfdbControl 5 }

                
--  1.3.6.1.4.1.10428 9 1.9.8.14.2.6
                -- 1.3.6.1.4.1.10428 9 1.101.3.14.2.6
                fkMfdbControlMacAddress OBJECT-TYPE
                        SYNTAX OCTET STRING (SIZE (0..6))
                        MAX-ACCESS read-write
                        STATUS current
                        DESCRIPTION
                                "A unicast MAC address for which the device has
                                forwarding or filtering information.
                                  If MAC address is NULL apply mac-filter list 
                                  from file '/etc/mfdb.conf'."
                        ::= { fkMfdbControl 6 }

                
--  1.3.6.1.4.1.10428 9 1.9.8.14.2.7
                -- 1.3.6.1.4.1.10428 9 1.101.3.14.2.7
                fkMfdbControlEntryPermission OBJECT-TYPE
                        SYNTAX INTEGER
                                {
                                deny(0),
                                permit(1)
                                }
                        MAX-ACCESS read-write
                        STATUS current
                        DESCRIPTION
                                "The permission of fkMFdbControlMacAddress."
                        ::= { fkMfdbControl 7 }

                
                -- 1.3.6.1.4.1.10428 9 1.101.3.14.2.8
                fkMfdbControlVlanIndex OBJECT-TYPE
                        SYNTAX INTEGER (0 | 1..4094)
                        MAX-ACCESS read-write
                        STATUS current
                        DESCRIPTION
                                "vlan index
                                The value of 0 is all vlan"
                        ::= { fkMfdbControl 8 }

                
                -- 1.3.6.1.4.1.10428 9 1.101.3.14.2.9
                fkMfdbControlPorts OBJECT-TYPE
                        SYNTAX OCTET STRING (SIZE (0..32))
                        MAX-ACCESS read-write
                        STATUS current
                        DESCRIPTION
                                "Port Map 
                                The value of 0x00 is all port
                                "
                        ::= { fkMfdbControl 9 }

                
--  1.3.6.1.4.1.10428 9 1.9.8.14.3
                -- 1.3.6.1.4.1.10428 9 1.101.3.14.3
                fkMfdbNotification OBJECT IDENTIFIER ::= { fkMfdb 3 }

                
--  1.3.6.1.4.1.10428 9 1.9.8.14.3.1
                -- 1.3.6.1.4.1.10428 9 1.101.3.14.3.1
                fkMfdbEntryCreated NOTIFICATION-TYPE
                        OBJECTS { fkMfdbControlRequest, fkMfdbControlReqResult, fkMfdbControlTimeStamp, fkMfdbEntryPermission }
                        STATUS current
                        DESCRIPTION 
                                "Create new MFDB entry."
                        ::= { fkMfdbNotification 1 }

                
--  1.3.6.1.4.1.10428 9 1.9.8.14.3.2
                -- 1.3.6.1.4.1.10428 9 1.101.3.14.3.2
                fkMfdbEntryDestoryed NOTIFICATION-TYPE
                        OBJECTS { fkMfdbControlRequest, fkMfdbControlReqResult, fkMfdbControlMacAddress, fkMfdbControlTimeStamp }
                        STATUS current
                        DESCRIPTION 
                                "Destroyed MFDB entry."
                        ::= { fkMfdbNotification 2 }

                
--  1.3.6.1.4.1.10428 9 1.9.8.14.3.3
                -- 1.3.6.1.4.1.10428 9 1.101.3.14.3.3
                fkMfdbEntryPermissionChanged NOTIFICATION-TYPE
                        OBJECTS { fkMfdbControlRequest, fkMfdbControlReqResult, fkMfdbControlTimeStamp, fkMfdbEntryPermission }
                        STATUS current
                        DESCRIPTION 
                                "Changed permission of MFDB entry."
                        ::= { fkMfdbNotification 3 }

                
                -- 1.3.6.1.4.1.10428 9 1.101.3.14.3.4
                fkMfdbEntryTableCleared NOTIFICATION-TYPE
                        OBJECTS { fkMfdbControlRequest, fkMfdbControlReqResult, fkMfdbControlTimeStamp }
                        STATUS current
                        DESCRIPTION 
                                "Description."
                        ::= { fkMfdbNotification 4 }

                
                -- 1.3.6.1.4.1.10428 9 1.101.3.15
                fkIgmpConf OBJECT IDENTIFIER ::= { fkBridge 15 }

                
                -- 1.3.6.1.4.1.10428 9 1.101.3.15.1
                fkIgmpConfTable OBJECT-TYPE
                        SYNTAX SEQUENCE OF FkIgmpConfEntry
                        MAX-ACCESS not-accessible
                        STATUS current
                        DESCRIPTION
                                "IGMP configuration table."
                        ::= { fkIgmpConf 1 }

                
                -- 1.3.6.1.4.1.10428 9 1.101.3.15.1.1
                fkIgmpConfEntry OBJECT-TYPE
                        SYNTAX FkIgmpConfEntry
                        MAX-ACCESS not-accessible
                        STATUS current
                        DESCRIPTION
                                "key: fkVlanIndex"
                        INDEX { fkVlanIndex }
                        ::= { fkIgmpConfTable 1 }

                
                FkIgmpConfEntry ::=
                        SEQUENCE { 
                                fkIgmpConfVlanIndex
                                        Integer32,
                                fkIgmpConfEnable
                                        INTEGER,
                                fkIgmpConfMulticastFilter
                                        INTEGER,
                                fkIgmpConfOutmostVlan
                                        INTEGER,
                                fkIgmpConfSnoopEnable
                                        INTEGER,
                                fkIgmpConfSnoopJoinDelay
                                        Integer32,
                                fkIgmpConfSnoopQueryDelay
                                        Integer32,
                                fkIgmpConfSnoopMrouter
                                        Integer32,
                                fkIgmpConfSnoopFastLeave
                                        INTEGER,
                                fkIgmpConfSnoopQuerier
                                        INTEGER
                         }

                -- 1.3.6.1.4.1.10428 9 1.101.3.15.1.1.1
                fkIgmpConfVlanIndex OBJECT-TYPE
                        SYNTAX Integer32 (0..4094)
                        MAX-ACCESS read-only
                        STATUS current
                        DESCRIPTION
                                "fkVlanIndex in fkVlanTable"
                        ::= { fkIgmpConfEntry 1 }

                
                -- 1.3.6.1.4.1.10428 9 1.101.3.15.1.1.2
                fkIgmpConfEnable OBJECT-TYPE
                        SYNTAX INTEGER
                                {
                                disable(0),
                                enable(1)
                                }
                        MAX-ACCESS read-only
                        STATUS current
                        DESCRIPTION
                                "If this flag is true, IGMP multicasting is enabled. (not supported)"
                        ::= { fkIgmpConfEntry 2 }

                
                -- 1.3.6.1.4.1.10428 9 1.101.3.15.1.1.3
                fkIgmpConfMulticastFilter OBJECT-TYPE
                        SYNTAX INTEGER
                                {
                                disable(0),
                                enable(1)
                                }
                        MAX-ACCESS read-only
                        STATUS current
                        DESCRIPTION
                                "If this flag is true, mac address that is unregistered into IGMP table is filtered. (not supported)"
                        ::= { fkIgmpConfEntry 3 }

                
                -- 1.3.6.1.4.1.10428 9 1.101.3.15.1.1.4
                fkIgmpConfOutmostVlan OBJECT-TYPE
                        SYNTAX INTEGER
                                {
                                disable(0),
                                enable(1)
                                }
                        MAX-ACCESS read-only
                        STATUS current
                        DESCRIPTION
                                "Configures outmost VLAN. (not supported)"
                        ::= { fkIgmpConfEntry 4 }

                
                -- 1.3.6.1.4.1.10428 9 1.101.3.15.1.1.5
                fkIgmpConfSnoopEnable OBJECT-TYPE
                        SYNTAX INTEGER
                                {
                                disable(0),
                                enable(1)
                                }
                        MAX-ACCESS read-only
                        STATUS current
                        DESCRIPTION
                                "The IGMP snooping enable/disable flag"
                        ::= { fkIgmpConfEntry 5 }

                
                -- 1.3.6.1.4.1.10428 9 1.101.3.15.1.1.6
                fkIgmpConfSnoopJoinDelay OBJECT-TYPE
                        SYNTAX Integer32 (0..1000)
                        MAX-ACCESS read-only
                        STATUS current
                        DESCRIPTION
                                "After join message is received, the time interval until be registered into multicast group. (not supported)"
                        ::= { fkIgmpConfEntry 6 }

                
                -- 1.3.6.1.4.1.10428 9 1.101.3.15.1.1.7
                fkIgmpConfSnoopQueryDelay OBJECT-TYPE
                        SYNTAX Integer32 (100..900)
                        MAX-ACCESS read-only
                        STATUS current
                        DESCRIPTION
                                "After query message is send, the time interval for response waiting."
                        ::= { fkIgmpConfEntry 7 }

                
                -- 1.3.6.1.4.1.10428 9 1.101.3.15.1.1.8
                fkIgmpConfSnoopMrouter OBJECT-TYPE
                        SYNTAX Integer32
                        MAX-ACCESS read-only
                        STATUS current
                        DESCRIPTION
                                "The index of interface connected with multicast router."
                        ::= { fkIgmpConfEntry 8 }

                
                -- 1.3.6.1.4.1.10428 9 1.101.3.15.1.1.9
                fkIgmpConfSnoopFastLeave OBJECT-TYPE
                        SYNTAX INTEGER
                                {
                                disable(0),
                                enable(1)
                                }
                        MAX-ACCESS read-only
                        STATUS current
                        DESCRIPTION
                                "If this flag is true, immediately this entry is deleted, when leave message is received,"
                        ::= { fkIgmpConfEntry 9 }

                
                -- 1.3.6.1.4.1.10428 9 1.101.3.15.1.1.10
                fkIgmpConfSnoopQuerier OBJECT-TYPE
                        SYNTAX INTEGER
                                {
                                disable(0),
                                enable(1)
                                }
                        MAX-ACCESS read-only
                        STATUS current
                        DESCRIPTION
                                "If this flag is true, perform IGMP snooping querier."
                        ::= { fkIgmpConfEntry 10 }

                
                -- 1.3.6.1.4.1.10428 9 1.101.3.15.2
                fkIgmpConfControl OBJECT IDENTIFIER ::= { fkIgmpConf 2 }

                
                -- 1.3.6.1.4.1.10428 9 1.101.3.15.2.1
                fkIgmpConfControlRequest OBJECT-TYPE
                        SYNTAX FkIgmpConfControlRequestType
                        MAX-ACCESS read-write
                        STATUS current
                        DESCRIPTION
                                "The request of a user command"
                        ::= { fkIgmpConfControl 1 }

                
                -- 1.3.6.1.4.1.10428 9 1.101.3.15.2.2
                fkIgmpConfControlStatus OBJECT-TYPE
                        SYNTAX FkControlStatusType
                        MAX-ACCESS read-only
                        STATUS current
                        DESCRIPTION
                                "The status of user command"
                        ::= { fkIgmpConfControl 2 }

                
                -- 1.3.6.1.4.1.10428 9 1.101.3.15.2.3
                fkIgmpConfControlTimer OBJECT-TYPE
                        SYNTAX Gauge32
                        MAX-ACCESS read-write
                        STATUS current
                        DESCRIPTION
                                "The maximum time for the manager for a long running user command"
                        ::= { fkIgmpConfControl 3 }

                
                -- 1.3.6.1.4.1.10428 9 1.101.3.15.2.4
                fkIgmpConfControlTimeStamp OBJECT-TYPE
                        SYNTAX TimeTicks
                        MAX-ACCESS read-only
                        STATUS current
                        DESCRIPTION
                                "The time stamp of the last command(end of command)"
                        ::= { fkIgmpConfControl 4 }

                
                -- 1.3.6.1.4.1.10428 9 1.101.3.15.2.5
                fkIgmpConfControlReqResult OBJECT-TYPE
                        SYNTAX FkControlRequestResultType
                        MAX-ACCESS read-only
                        STATUS current
                        DESCRIPTION
                                "The result of the last user command"
                        ::= { fkIgmpConfControl 5 }

                
                -- 1.3.6.1.4.1.10428 9 1.101.3.15.2.6
                fkIgmpConfControlVlanIndex OBJECT-TYPE
                        SYNTAX Integer32 (1..4094)
                        MAX-ACCESS read-write
                        STATUS current
                        DESCRIPTION
                                "fkVlanIndex in fkVlanTable"
                        ::= { fkIgmpConfControl 6 }

                
                -- 1.3.6.1.4.1.10428 9 1.101.3.15.2.7
                fkIgmpConfControlEnable OBJECT-TYPE
                        SYNTAX INTEGER
                                {
                                disable(0),
                                enable(1)
                                }
                        MAX-ACCESS read-write
                        STATUS current
                        DESCRIPTION
                                "If this flag is true, IGMP multicasting is enabled."
                        ::= { fkIgmpConfControl 7 }

                
                -- 1.3.6.1.4.1.10428 9 1.101.3.15.2.8
                fkIgmpConfControlMulticastFilter OBJECT-TYPE
                        SYNTAX INTEGER
                                {
                                disable(0),
                                enable(1)
                                }
                        MAX-ACCESS read-write
                        STATUS current
                        DESCRIPTION
                                "If this flag is true, mac address that is unregistered into IGMP table is filtered."
                        ::= { fkIgmpConfControl 8 }

                
                -- 1.3.6.1.4.1.10428 9 1.101.3.15.2.9
                fkIgmpConfControlOutmostVlan OBJECT-TYPE
                        SYNTAX INTEGER
                                {
                                disable(0),
                                enable(1)
                                }
                        MAX-ACCESS read-write
                        STATUS current
                        DESCRIPTION
                                "Configures outmost VLAN. (not supported)"
                        ::= { fkIgmpConfControl 9 }

                
                -- 1.3.6.1.4.1.10428 9 1.101.3.15.2.10
                fkIgmpConfControlSnoopEnable OBJECT-TYPE
                        SYNTAX INTEGER
                                {
                                disable(0),
                                enable(1)
                                }
                        MAX-ACCESS read-write
                        STATUS current
                        DESCRIPTION
                                "The IGMP snooping enable/disable flag"
                        ::= { fkIgmpConfControl 10 }

                
                -- 1.3.6.1.4.1.10428 9 1.101.3.15.2.11
                fkIgmpConfControlSnoopJoinDelay OBJECT-TYPE
                        SYNTAX Integer32 (0..1000)
                        MAX-ACCESS read-write
                        STATUS current
                        DESCRIPTION
                                "After join message is received, the time interval until be registered into multicast group. (not supported)"
                        ::= { fkIgmpConfControl 11 }

                
                -- 1.3.6.1.4.1.10428 9 1.101.3.15.2.12
                fkIgmpConfControlSnoopQueryDelay OBJECT-TYPE
                        SYNTAX Integer32 (100..900)
                        MAX-ACCESS read-write
                        STATUS current
                        DESCRIPTION
                                "After query message is send, the time interval for response waiting."
                        ::= { fkIgmpConfControl 12 }

                
                -- 1.3.6.1.4.1.10428 9 1.101.3.15.2.13
                fkIgmpConfControlSnoopMrouter OBJECT-TYPE
                        SYNTAX Integer32 (1..255)
                        MAX-ACCESS read-write
                        STATUS current
                        DESCRIPTION
                                "The index of interface connected with multicast router."
                        DEFVAL { 1 }
                        ::= { fkIgmpConfControl 13 }

                
                -- 1.3.6.1.4.1.10428 9 1.101.3.15.2.14
                fkIgmpConfControlSnoopFastLeave OBJECT-TYPE
                        SYNTAX INTEGER
                                {
                                disable(0),
                                enable(1)
                                }
                        MAX-ACCESS read-write
                        STATUS current
                        DESCRIPTION
                                "If this flag is true, immediately this entry is deleted, when leave message is received,"
                        ::= { fkIgmpConfControl 14 }

                
                -- 1.3.6.1.4.1.10428 9 1.101.3.15.2.15
                fkIgmpConfControlSnoopQuerier OBJECT-TYPE
                        SYNTAX INTEGER
                                {
                                disable(0),
                                enable(1)
                                }
                        MAX-ACCESS read-write
                        STATUS current
                        DESCRIPTION
                                "If this flag is true, perform IGMP snooping querier."
                        ::= { fkIgmpConfControl 15 }

                
                -- 1.3.6.1.4.1.10428 9 1.101.3.15.3
                fkIgmpConfNotification OBJECT IDENTIFIER ::= { fkIgmpConf 3 }

                
                -- 1.3.6.1.4.1.10428 9 1.101.3.15.3.1
                fkIgmpConfProfileChanged NOTIFICATION-TYPE
                        OBJECTS { fkIgmpConfControlRequest, fkIgmpConfControlReqResult, fkIgmpConfControlTimeStamp, fkIgmpConfSnoopMrouter, fkIgmpConfEnable, 
                                fkIgmpConfMulticastFilter, fkIgmpConfOutmostVlan, fkIgmpConfSnoopEnable, fkIgmpConfSnoopJoinDelay, fkIgmpConfSnoopQueryDelay, 
                                fkIgmpConfSnoopFastLeave, fkIgmpConfSnoopQuerier }
                        STATUS current
                        DESCRIPTION 
                                "Description."
                        ::= { fkIgmpConfNotification 1 }

                
--  1.3.6.1.4.1.10428 9 1.9.8.15
                -- 1.3.6.1.4.1.10428 9 1.101.3.16
                fkIgmpMcast OBJECT IDENTIFIER ::= { fkBridge 16 }

                
--  1.3.6.1.4.1.10428 9 1.9.8.15.1
                -- 1.3.6.1.4.1.10428 9 1.101.3.16.1
                fkIgmpMcastTable OBJECT-TYPE
                        SYNTAX SEQUENCE OF FkIgmpMcastEntry
                        MAX-ACCESS not-accessible
                        STATUS current
                        DESCRIPTION
                                " IGMP multicast table."
                        ::= { fkIgmpMcast 1 }

                
--  1.3.6.1.4.1.10428 9 1.9.8.15.1.1
                -- 1.3.6.1.4.1.10428 9 1.101.3.16.1.1
                fkIgmpMcastEntry OBJECT-TYPE
                        SYNTAX FkIgmpMcastEntry
                        MAX-ACCESS not-accessible
                        STATUS current
                        DESCRIPTION
                                " key: fkVlanIndex, fkIgmpMcastIPAddress, fkIgmpMcastPortIndex"
                        INDEX { fkVlanIndex, fkIgmpMcastIPAddress, fkIgmpMcastPortIndex }
                        ::= { fkIgmpMcastTable 1 }

                
                FkIgmpMcastEntry ::=
                        SEQUENCE { 
                                fkIgmpMcastVlanIndex
                                        Integer32,
                                fkIgmpMcastIPAddress
                                        IpAddress,
                                fkIgmpMcastPortIndex
                                        Integer32,
                                fkIgmpMcastType
                                        INTEGER,
                                fkIgmpMcastExpireTime
                                        Integer32
                         }

                -- 1.3.6.1.4.1.10428 9 1.101.3.16.1.1.1
                fkIgmpMcastVlanIndex OBJECT-TYPE
                        SYNTAX Integer32 (1..4094)
                        MAX-ACCESS read-only
                        STATUS current
                        DESCRIPTION
                                "fkVlanIndex in fkVlanTable"
                        ::= { fkIgmpMcastEntry 1 }

                
--  1.3.6.1.4.1.10428 9 1.9.8.15.1.1.2
                -- 1.3.6.1.4.1.10428 9 1.101.3.16.1.1.2
                fkIgmpMcastIPAddress OBJECT-TYPE
                        SYNTAX IpAddress
                        MAX-ACCESS read-only
                        STATUS current
                        DESCRIPTION
                                "The IP multicast group address for which this entry contains information."
                        ::= { fkIgmpMcastEntry 2 }

                
                -- 1.3.6.1.4.1.10428 9 1.101.3.16.1.1.3
                fkIgmpMcastPortIndex OBJECT-TYPE
                        SYNTAX Integer32 (1..255)
                        MAX-ACCESS read-only
                        STATUS current
                        DESCRIPTION
                                "Port index"
                        ::= { fkIgmpMcastEntry 3 }

                
                -- 1.3.6.1.4.1.10428 9 1.101.3.16.1.1.4
                fkIgmpMcastType OBJECT-TYPE
                        SYNTAX INTEGER
                                {
                                static(0),
                                dynamic(1)
                                }
                        MAX-ACCESS read-only
                        STATUS current
                        DESCRIPTION
                                "indicate either static- or dynamic- IP multicast group address"
                        ::= { fkIgmpMcastEntry 4 }

                
                -- 1.3.6.1.4.1.10428 9 1.101.3.16.1.1.5
                fkIgmpMcastExpireTime OBJECT-TYPE
                        SYNTAX Integer32
                        MAX-ACCESS read-only
                        STATUS current
                        DESCRIPTION
                                "Expiry time of this dynamic multicast table entry."
                        ::= { fkIgmpMcastEntry 5 }

                
--  1.3.6.1.4.1.10428 9 1.9.8.15.2
                -- 1.3.6.1.4.1.10428 9 1.101.3.16.2
                fkIgmpMcastControl OBJECT IDENTIFIER ::= { fkIgmpMcast 2 }

                
--  1.3.6.1.4.1.10428 9 1.9.8.15.2.1
                -- 1.3.6.1.4.1.10428 9 1.101.3.16.2.1
                fkIgmpMcastControlRequest OBJECT-TYPE
                        SYNTAX FkIgmpMcastControlRequestType
                        MAX-ACCESS read-write
                        STATUS current
                        DESCRIPTION
                                " The request of a user command"
                        ::= { fkIgmpMcastControl 1 }

                
--  1.3.6.1.4.1.10428 9 1.9.8.15.2.2
                -- 1.3.6.1.4.1.10428 9 1.101.3.16.2.2
                fkIgmpMcastControlStatus OBJECT-TYPE
                        SYNTAX FkControlStatusType
                        MAX-ACCESS read-only
                        STATUS current
                        DESCRIPTION
                                "The status of user command"
                        ::= { fkIgmpMcastControl 2 }

                
--  1.3.6.1.4.1.10428 9 1.9.8.15.2.3
                -- 1.3.6.1.4.1.10428 9 1.101.3.16.2.3
                fkIgmpMcastControlTimer OBJECT-TYPE
                        SYNTAX Gauge32
                        MAX-ACCESS read-write
                        STATUS current
                        DESCRIPTION
                                " The maximum time for the manager for a long running user command"
                        ::= { fkIgmpMcastControl 3 }

                
--  1.3.6.1.4.1.10428 9 1.9.8.15.2.4
                -- 1.3.6.1.4.1.10428 9 1.101.3.16.2.4
                fkIgmpMcastControlTimeStamp OBJECT-TYPE
                        SYNTAX TimeTicks
                        MAX-ACCESS read-only
                        STATUS current
                        DESCRIPTION
                                " The time stamp of the last command(end of command)"
                        ::= { fkIgmpMcastControl 4 }

                
--  1.3.6.1.4.1.10428 9 1.9.8.15.2.5
                -- 1.3.6.1.4.1.10428 9 1.101.3.16.2.5
                fkIgmpMcastControlReqResult OBJECT-TYPE
                        SYNTAX FkControlRequestResultType
                        MAX-ACCESS read-only
                        STATUS current
                        DESCRIPTION
                                " The result of the last user command"
                        ::= { fkIgmpMcastControl 5 }

                
--  1.3.6.1.4.1.10428 9 1.9.8.15.2.6
                -- 1.3.6.1.4.1.10428 9 1.101.3.16.2.6
                fkIgmpMcastControlVlanIndex OBJECT-TYPE
                        SYNTAX Integer32 (1..4094)
                        MAX-ACCESS read-write
                        STATUS current
                        DESCRIPTION
                                " fkVlanIndex in fkVlanTable"
                        ::= { fkIgmpMcastControl 6 }

                
--  Vlan ID
-- 1.3.6.1.4.1.10428 9 1.9.8.15.2.7
                -- 1.3.6.1.4.1.10428 9 1.101.3.16.2.7
                fkIgmpMcastControlIPAddress OBJECT-TYPE
                        SYNTAX IpAddress
                        MAX-ACCESS read-write
                        STATUS current
                        DESCRIPTION
                                " The multicast group address."
                        ::= { fkIgmpMcastControl 7 }

                
                -- 1.3.6.1.4.1.10428 9 1.101.3.16.2.8
                fkIgmpMcastControlPortIndex OBJECT-TYPE
                        SYNTAX Integer32 (1..255)
                        MAX-ACCESS read-write
                        STATUS current
                        DESCRIPTION
                                "Port index"
                        ::= { fkIgmpMcastControl 8 }

                
--  IP address
-- 1.3.6.1.4.1.10428 9 1.9.8.15.3
                -- 1.3.6.1.4.1.10428 9 1.101.3.16.3
                fkIgmpMcastNotification OBJECT IDENTIFIER ::= { fkIgmpMcast 3 }

                
--  1.3.6.1.4.1.10428 9 1.9.8.15.3.1
                -- 1.3.6.1.4.1.10428 9 1.101.3.16.3.1
                fkIgmpStaticMcastCreated NOTIFICATION-TYPE
                        OBJECTS { fkIgmpMcastControlRequest, fkIgmpMcastControlTimeStamp, fkIgmpMcastControlPortIndex, fkIgmpMcastControlReqResult }
                        STATUS current
                        DESCRIPTION 
                                " "
                        ::= { fkIgmpMcastNotification 1 }

                
--  1.3.6.1.4.1.10428 9 1.9.8.15.3.2
                -- 1.3.6.1.4.1.10428 9 1.101.3.16.3.2
                fkIgmpStaticMcastDestroyed NOTIFICATION-TYPE
                        OBJECTS { fkIgmpMcastControlRequest, fkIgmpMcastControlReqResult, fkIgmpMcastControlPortIndex, fkIgmpMcastControlTimeStamp }
                        STATUS current
                        DESCRIPTION 
                                " "
                        ::= { fkIgmpMcastNotification 2 }

                
                -- 1.3.6.1.4.1.10428 9 1.101.3.16.4
                fkIgmpMcastCounterInfo OBJECT IDENTIFIER ::= { fkIgmpMcast 4 }

                
                -- 1.3.6.1.4.1.10428 9 1.101.3.16.4.1
                fkIgmpMcastCounterInfoGroupCount OBJECT-TYPE
                        SYNTAX Counter32
                        MAX-ACCESS read-only
                        STATUS current
                        DESCRIPTION
                                "Count of IGMP Group entry."
                        ::= { fkIgmpMcastCounterInfo 1 }

                
                -- 1.3.6.1.4.1.10428 9 1.101.3.16.4.2
                fkIgmpMcastCounterInfoSnoopingCount OBJECT-TYPE
                        SYNTAX Counter32
                        MAX-ACCESS read-only
                        STATUS current
                        DESCRIPTION
                                "Count of IGMP Snooping Group entry."
                        ::= { fkIgmpMcastCounterInfo 2 }

                
                -- 1.3.6.1.4.1.10428 9 1.101.3.16.5
                fkMcastMrouteCounterInfo OBJECT IDENTIFIER ::= { fkIgmpMcast 5 }

                
                -- 1.3.6.1.4.1.10428 9 1.101.3.16.5.1
                fkMcastMrouteJoinedCount OBJECT-TYPE
                        SYNTAX Counter32
                        MAX-ACCESS read-only
                        STATUS current
                        DESCRIPTION
                                "The count of Mroute Joined channel"
                        ::= { fkMcastMrouteCounterInfo 1 }

                
--  1.3.6.1.4.1.10428 9 1.9.8.17
                -- 1.3.6.1.4.1.10428 9 1.101.3.17
                fkStackDevice OBJECT IDENTIFIER ::= { fkBridge 17 }

                
--  1.3.6.1.4.1.10428 9 1.9.8.17.1
                -- 1.3.6.1.4.1.10428 9 1.101.3.17.1
                fkStackDeviceTable OBJECT-TYPE
                        SYNTAX SEQUENCE OF FkStackDeviceEntry
                        MAX-ACCESS not-accessible
                        STATUS current
                        DESCRIPTION
                                "Information table of stack master/slave devices."
                        ::= { fkStackDevice 1 }

                
--  1.3.6.1.4.1.10428 9 1.9.8.17.1.1
                -- 1.3.6.1.4.1.10428 9 1.101.3.17.1.1
                fkStackDeviceEntry OBJECT-TYPE
                        SYNTAX FkStackDeviceEntry
                        MAX-ACCESS not-accessible
                        STATUS current
                        DESCRIPTION
                                "Information table entry of stack master/slave devices.
                                key: fkStackDeviceMacAddress"
                        INDEX { fkStackDeviceMacAddress }
                        ::= { fkStackDeviceTable 1 }

                
                FkStackDeviceEntry ::=
                        SEQUENCE { 
                                fkStackDeviceMacAddress
                                        OCTET STRING,
                                fkStackDeviceNodeId
                                        Integer32,
                                fkStackDeviceDescriptor
                                        OCTET STRING,
                                fkStackDeviceMode
                                        INTEGER,
                                fkStackDeviceStatus
                                        INTEGER,
                                fkStackDeviceType
                                        OCTET STRING,
                                fkStackDeviceHostName
                                        OCTET STRING,
                                fkStackDevicePortNum
                                        INTEGER
                         }

--  1.3.6.1.4.1.10428 9 1.9.8.17.1.1.1
                -- 1.3.6.1.4.1.10428 9 1.101.3.17.1.1.1
                fkStackDeviceMacAddress OBJECT-TYPE
                        SYNTAX OCTET STRING (SIZE (0..6))
                        MAX-ACCESS read-only
                        STATUS current
                        DESCRIPTION
                                "MAC address of stack device."
                        ::= { fkStackDeviceEntry 1 }

                
--  1.3.6.1.4.1.10428 9 1.9.8.17.1.1.2
                -- 1.3.6.1.4.1.10428 9 1.101.3.17.1.1.2
                fkStackDeviceNodeId OBJECT-TYPE
                        SYNTAX Integer32
                        MAX-ACCESS read-only
                        STATUS current
                        DESCRIPTION
                                "Index stack device nodes."
                        ::= { fkStackDeviceEntry 2 }

                
--  1.3.6.1.4.1.10428 9 1.9.8.17.1.1.3
                -- 1.3.6.1.4.1.10428 9 1.101.3.17.1.1.3
                fkStackDeviceDescriptor OBJECT-TYPE
                        SYNTAX OCTET STRING (SIZE (0..256))
                        MAX-ACCESS read-only
                        STATUS current
                        DESCRIPTION
                                "Description of stack device."
                        ::= { fkStackDeviceEntry 3 }

                
--  1.3.6.1.4.1.10428 9 1.9.8.17.1.1.4
                -- 1.3.6.1.4.1.10428 9 1.101.3.17.1.1.4
                fkStackDeviceMode OBJECT-TYPE
                        SYNTAX INTEGER
                                {
                                master(1),
                                slave(2)
                                }
                        MAX-ACCESS read-only
                        STATUS current
                        DESCRIPTION
                                "Stack status of device."
                        ::= { fkStackDeviceEntry 4 }

                
--  1.3.6.1.4.1.10428 9 1.9.8.17.1.1.6
                -- 1.3.6.1.4.1.10428 9 1.101.3.17.1.1.5
                fkStackDeviceStatus OBJECT-TYPE
                        SYNTAX INTEGER
                                {
                                inactive(0),
                                active(1)
                                }
                        MAX-ACCESS read-only
                        STATUS current
                        DESCRIPTION
                                "Stack status of stack device."
                        ::= { fkStackDeviceEntry 5 }

                
--  1.3.6.1.4.1.10428 9 1.9.8.17.1.1.7
                -- 1.3.6.1.4.1.10428 9 1.101.3.17.1.1.6
                fkStackDeviceType OBJECT-TYPE
                        SYNTAX OCTET STRING (SIZE (0..16))
                        MAX-ACCESS read-only
                        STATUS current
                        DESCRIPTION
                                "Device type of stack device."
                        ::= { fkStackDeviceEntry 6 }

                
--  1.3.6.1.4.1.10428 9 1.9.8.17.1.1.8
                -- 1.3.6.1.4.1.10428 9 1.101.3.17.1.1.7
                fkStackDeviceHostName OBJECT-TYPE
                        SYNTAX OCTET STRING (SIZE (0..32))
                        MAX-ACCESS read-only
                        STATUS current
                        DESCRIPTION
                                "Hostname of stack device."
                        ::= { fkStackDeviceEntry 7 }

                
--  1.3.6.1.4.1.10428 9 1.9.8.17.1.1.9
                -- 1.3.6.1.4.1.10428 9 1.101.3.17.1.1.8
                fkStackDevicePortNum OBJECT-TYPE
                        SYNTAX INTEGER (0..255)
                        MAX-ACCESS read-only
                        STATUS current
                        DESCRIPTION
                                "Number of stack device's ports."
                        ::= { fkStackDeviceEntry 8 }

                
--  1.3.6.1.4.1.10428 9 1.9.8.17.2
                -- 1.3.6.1.4.1.10428 9 1.101.3.17.2
                fkStackDeviceControl OBJECT IDENTIFIER ::= { fkStackDevice 2 }

                
--  1.3.6.1.4.1.10428 9 1.9.8.17.2.1
                -- 1.3.6.1.4.1.10428 9 1.101.3.17.2.1
                fkStackDeviceControlRequest OBJECT-TYPE
                        SYNTAX INTEGER
                                {
                                createStackSlaveDevice(1),
                                destoryStackSlaveDevice(2)
                                }
                        MAX-ACCESS read-write
                        STATUS current
                        DESCRIPTION
                                " The request of a user command"
                        ::= { fkStackDeviceControl 1 }

                
--  1.3.6.1.4.1.10428 9 1.9.8.17.2.2
                -- 1.3.6.1.4.1.10428 9 1.101.3.17.2.2
                fkStackDeviceControlStatus OBJECT-TYPE
                        SYNTAX FkControlStatusType
                        MAX-ACCESS read-only
                        STATUS current
                        DESCRIPTION
                                " The status of user command"
                        ::= { fkStackDeviceControl 2 }

                
--  1.3.6.1.4.1.10428 9 1.9.8.17.2.3
                -- 1.3.6.1.4.1.10428 9 1.101.3.17.2.3
                fkStackDeviceControlTimer OBJECT-TYPE
                        SYNTAX Gauge32
                        MAX-ACCESS read-write
                        STATUS current
                        DESCRIPTION
                                " The maximum time for the manager for a long running user command"
                        ::= { fkStackDeviceControl 3 }

                
--  1.3.6.1.4.1.10428 9 1.9.8.17.2.5
                -- 1.3.6.1.4.1.10428 9 1.101.3.17.2.4
                fkStackDeviceControlTImeStamp OBJECT-TYPE
                        SYNTAX TimeTicks
                        MAX-ACCESS read-only
                        STATUS current
                        DESCRIPTION
                                " The time stamp of the last command(end of command)"
                        ::= { fkStackDeviceControl 4 }

                
--  1.3.6.1.4.1.10428 9 1.9.8.17.2.4
                -- 1.3.6.1.4.1.10428 9 1.101.3.17.2.5
                fkStackDeviceControlReqResult OBJECT-TYPE
                        SYNTAX FkControlRequestResultType
                        MAX-ACCESS read-only
                        STATUS current
                        DESCRIPTION
                                " The result of the last user command"
                        ::= { fkStackDeviceControl 5 }

                
--  1.3.6.1.4.1.10428 9 1.9.8.17.2.6
                -- 1.3.6.1.4.1.10428 9 1.101.3.17.2.6
                fkStackDeviceControlMacAddress OBJECT-TYPE
                        SYNTAX OCTET STRING (SIZE (0..6))
                        MAX-ACCESS read-write
                        STATUS current
                        DESCRIPTION
                                "MAC address of slave device."
                        ::= { fkStackDeviceControl 6 }

                
--  1.3.6.1.4.1.10428 9 1.9.8.17.2.7
                -- 1.3.6.1.4.1.10428 9 1.101.3.17.2.7
                fkStackDeviceControlDescriptor OBJECT-TYPE
                        SYNTAX OCTET STRING (SIZE (0..256))
                        MAX-ACCESS read-write
                        STATUS current
                        DESCRIPTION
                                "Description of stack slave device."
                        ::= { fkStackDeviceControl 7 }

                
--  1.3.6.1.4.1.10428 9 1.9.8.17.3
                -- 1.3.6.1.4.1.10428 9 1.101.3.17.3
                fkStackDeviceNotification OBJECT IDENTIFIER ::= { fkStackDevice 3 }

                
--  1.3.6.1.4.1.10428 9 1.9.8.17.3.1
                -- 1.3.6.1.4.1.10428 9 1.101.3.17.3.1
                fkStackDeviceCreated NOTIFICATION-TYPE
                        OBJECTS { fkStackDeviceControlRequest, fkStackDeviceControlTImeStamp, fkStackDeviceControlReqResult, fkStackDeviceDescriptor }
                        STATUS current
                        DESCRIPTION 
                                "Added stack slave device to master stack device."
                        ::= { fkStackDeviceNotification 1 }

                
--  1.3.6.1.4.1.10428 9 1.9.8.17.3.2
                -- 1.3.6.1.4.1.10428 9 1.101.3.17.3.2
                fkStackDeviceDestoryed NOTIFICATION-TYPE
                        OBJECTS { fkStackDeviceControlRequest, fkStackDeviceControlTImeStamp, fkStackDeviceControlMacAddress, fkStackDeviceControlReqResult }
                        STATUS current
                        DESCRIPTION 
                                "Deleted stack slave device from master stack device."
                        ::= { fkStackDeviceNotification 2 }

                
                -- 1.3.6.1.4.1.10428 9 1.101.3.18
                fkErpDomain OBJECT IDENTIFIER ::= { fkBridge 18 }

                
                -- 1.3.6.1.4.1.10428 9 1.101.3.18.1
                fkErpDomainTable OBJECT-TYPE
                        SYNTAX SEQUENCE OF FkErpDomainEntry
                        MAX-ACCESS not-accessible
                        STATUS current
                        DESCRIPTION
                                " erp domain table."
                        ::= { fkErpDomain 1 }

                
                -- 1.3.6.1.4.1.10428 9 1.101.3.18.1.1
                fkErpDomainEntry OBJECT-TYPE
                        SYNTAX FkErpDomainEntry
                        MAX-ACCESS not-accessible
                        STATUS current
                        DESCRIPTION
                                " key: fkErpDomainIndex"
                        INDEX { fkErpDomainIndex }
                        ::= { fkErpDomainTable 1 }

                
                FkErpDomainEntry ::=
                        SEQUENCE { 
                                fkErpDomainIndex
                                        INTEGER,
                                fkErpDomainName
                                        OCTET STRING,
                                fkErpDomainPrimaryPort
                                        InterfaceIndex,
                                fkErpDomainSecondaryPort
                                        InterfaceIndex,
                                fkErpDomainBridgeRole
                                        INTEGER,
                                fkErpDomainProtectionActivation
                                        INTEGER,
                                fkErpDomainOperatorRequest
                                        INTEGER,
                                fkErpDomainWaitToRestoreTime
                                        INTEGER,
                                fkErpDomainTestPacketInterval
                                        INTEGER,
                                fkErpDomainLearningDisabledTime
                                        INTEGER,
                                fkErpDomainNodeStatus
                                        INTEGER,
                                fkErpDomainRingStatus
                                        INTEGER,
                                fkErpDomainLotp
                                        INTEGER,
                                fkErpDomainULotp
                                        INTEGER,
                                fkErpDomainMultipleRM
                                        INTEGER,
                                fkErpDomainRMNodeReacheablility
                                        INTEGER,
                                fkErpDomainHoldOffTime
                                        INTEGER,
                                fkErpDomainRingPriority
                                        INTEGER
                         }

                -- 1.3.6.1.4.1.10428 9 1.101.3.18.1.1.1
                fkErpDomainIndex OBJECT-TYPE
                        SYNTAX INTEGER (1..4094)
                        MAX-ACCESS read-only
                        STATUS current
                        DESCRIPTION
                                "An index value that uniquely identifies an ERP domain."
                        ::= { fkErpDomainEntry 1 }

                
                -- 1.3.6.1.4.1.10428 9 1.101.3.18.1.1.2
                fkErpDomainName OBJECT-TYPE
                        SYNTAX OCTET STRING
                        MAX-ACCESS read-only
                        STATUS current
                        DESCRIPTION
                                "Domain name."
                        ::= { fkErpDomainEntry 2 }

                
                -- 1.3.6.1.4.1.10428 9 1.101.3.18.1.1.3
                fkErpDomainPrimaryPort OBJECT-TYPE
                        SYNTAX InterfaceIndex
                        MAX-ACCESS read-write
                        STATUS current
                        DESCRIPTION
                                "Interface index that represents the primary port of the domain."
                        ::= { fkErpDomainEntry 3 }

                
                -- 1.3.6.1.4.1.10428 9 1.101.3.18.1.1.4
                fkErpDomainSecondaryPort OBJECT-TYPE
                        SYNTAX InterfaceIndex
                        MAX-ACCESS read-only
                        STATUS current
                        DESCRIPTION
                                "Interface index that represents the secondary port of the domain."
                        ::= { fkErpDomainEntry 4 }

                
                -- 1.3.6.1.4.1.10428 9 1.101.3.18.1.1.5
                fkErpDomainBridgeRole OBJECT-TYPE
                        SYNTAX INTEGER
                                {
                                normalNode(0),
                                rmNode(1)
                                }
                        MAX-ACCESS read-only
                        STATUS current
                        DESCRIPTION
                                "Mode that the ERP domain may operate in."
                        ::= { fkErpDomainEntry 5 }

                
                -- 1.3.6.1.4.1.10428 9 1.101.3.18.1.1.6
                fkErpDomainProtectionActivation OBJECT-TYPE
                        SYNTAX INTEGER
                                {
                                deactivated(0),
                                activated(1)
                                }
                        MAX-ACCESS read-only
                        STATUS current
                        DESCRIPTION
                                "Protection activation."
                        ::= { fkErpDomainEntry 6 }

                
                -- 1.3.6.1.4.1.10428 9 1.101.3.18.1.1.7
                fkErpDomainOperatorRequest OBJECT-TYPE
                        SYNTAX INTEGER
                                {
                                clear(0),
                                manualToSecondary(1)
                                }
                        MAX-ACCESS read-only
                        STATUS current
                        DESCRIPTION
                                "Operator Request."
                        ::= { fkErpDomainEntry 7 }

                
                -- 1.3.6.1.4.1.10428 9 1.101.3.18.1.1.8
                fkErpDomainWaitToRestoreTime OBJECT-TYPE
                        SYNTAX INTEGER (1..720)
                        MAX-ACCESS read-only
                        STATUS current
                        DESCRIPTION
                                "Time in seconds taken to verify that ring integrity is restored."
                        ::= { fkErpDomainEntry 8 }

                
                -- 1.3.6.1.4.1.10428 9 1.101.3.18.1.1.9
                fkErpDomainTestPacketInterval OBJECT-TYPE
                        SYNTAX INTEGER (10..500)
                        MAX-ACCESS read-only
                        STATUS current
                        DESCRIPTION
                                "Time in mili seconds between consecutive transmissions of test packages."
                        ::= { fkErpDomainEntry 9 }

                
                -- 1.3.6.1.4.1.10428 9 1.101.3.18.1.1.10
                fkErpDomainLearningDisabledTime OBJECT-TYPE
                        SYNTAX INTEGER (0..500)
                        MAX-ACCESS read-only
                        STATUS current
                        DESCRIPTION
                                "Time in mili seconds during which learning is disabled after a FDB flash."
                        ::= { fkErpDomainEntry 10 }

                
                -- 1.3.6.1.4.1.10428 9 1.101.3.18.1.1.11
                fkErpDomainNodeStatus OBJECT-TYPE
                        SYNTAX INTEGER
                                {
                                rmidle(0),
                                primaryProtecting(1),
                                protecting(2),
                                idle(3),
                                failedS(4),
                                failedP(5),
                                preForward(6),
                                isolated(7),
                                deactivated(8),
                                backoff(9)
                                }
                        MAX-ACCESS read-only
                        STATUS current
                        DESCRIPTION
                                "Node status."
                        ::= { fkErpDomainEntry 11 }

                
                -- 1.3.6.1.4.1.10428 9 1.101.3.18.1.1.12
                fkErpDomainRingStatus OBJECT-TYPE
                        SYNTAX INTEGER
                                {
                                normal(0),
                                protecting(1),
                                unknown(2)
                                }
                        MAX-ACCESS read-only
                        STATUS current
                        DESCRIPTION
                                "Actual protection state on the ring."
                        ::= { fkErpDomainEntry 12 }

                
                -- 1.3.6.1.4.1.10428 9 1.101.3.18.1.1.13
                fkErpDomainLotp OBJECT-TYPE
                        SYNTAX INTEGER
                                {
                                clear(0),
                                raised(1)
                                }
                        MAX-ACCESS read-only
                        STATUS current
                        DESCRIPTION
                                "Loss of Test Packet alarm status. Only meaningful in RM node."
                        ::= { fkErpDomainEntry 13 }

                
                -- 1.3.6.1.4.1.10428 9 1.101.3.18.1.1.14
                fkErpDomainULotp OBJECT-TYPE
                        SYNTAX INTEGER
                                {
                                clear(0),
                                raised(1)
                                }
                        MAX-ACCESS read-only
                        STATUS current
                        DESCRIPTION
                                "Unidirectional Detection of  Loss of Test Packet alarm status.
                                Only meaningful in RM node."
                        ::= { fkErpDomainEntry 14 }

                
                -- 1.3.6.1.4.1.10428 9 1.101.3.18.1.1.15
                fkErpDomainMultipleRM OBJECT-TYPE
                        SYNTAX INTEGER
                                {
                                clear(0),
                                raised(1)
                                }
                        MAX-ACCESS read-only
                        STATUS current
                        DESCRIPTION
                                "Multiple Redundancy Manager alarm status. Only meaningful
                                in RM node."
                        ::= { fkErpDomainEntry 15 }

                
                -- 1.3.6.1.4.1.10428 9 1.101.3.18.1.1.16
                fkErpDomainRMNodeReacheablility OBJECT-TYPE
                        SYNTAX INTEGER
                                {
                                clear(0),
                                raised(1)
                                }
                        MAX-ACCESS read-only
                        STATUS current
                        DESCRIPTION
                                "RM Node reacheability alarm status. Only meaningful in
                                normal node."
                        ::= { fkErpDomainEntry 16 }

                
                -- 1.3.6.1.4.1.10428 9 1.101.3.18.1.1.17
                fkErpDomainHoldOffTime OBJECT-TYPE
                        SYNTAX INTEGER (0 | 1..20000)
                        MAX-ACCESS read-only
                        STATUS current
                        DESCRIPTION
                                "The hold off time."
                        ::= { fkErpDomainEntry 17 }

                
                -- 1.3.6.1.4.1.10428 9 1.101.3.18.1.1.18
                fkErpDomainRingPriority OBJECT-TYPE
                        SYNTAX INTEGER (0 | 1..255)
                        MAX-ACCESS read-only
                        STATUS current
                        DESCRIPTION
                                "The ring priority"
                        ::= { fkErpDomainEntry 18 }

                
                -- 1.3.6.1.4.1.10428 9 1.101.3.18.2
                fkErpDomainControl OBJECT IDENTIFIER ::= { fkErpDomain 2 }

                
                -- 1.3.6.1.4.1.10428 9 1.101.3.18.2.1
                fkErpDomainControlRequest OBJECT-TYPE
                        SYNTAX INTEGER
                                {
                                createErpDomain(1),
                                destroyErpDomain(2),
                                setErpDomainProfile(3),
                                setErpProtectionActivation(4),
                                setErpHoldOffTime(5),
                                setErpRingPriority(6),
                                setErpTrap(7)
                                }
                        MAX-ACCESS read-write
                        STATUS current
                        DESCRIPTION
                                "
                                createErpDomain:
                                fkErpDomainControlIndex
                                fkErpDomainControlName
                                fkErpDomainControlPrimaryPort
                                fkErpDomainControlSecondaryPort
                                fkErpDomainControlBridgeRole
                                fkErpDomainControlProtectionActivation
                                fkErpDomainControlOperatorRequest
                                fkErpDomainControlWaitToRestoreTime
                                fkErpDomainControlTestPacketInterval
                                fkErpDomainControlLearningDisabledTime
                                
                                destroyErpDomain:
                                fkErpDomainControlIndex
                                 
                                setErpDomainProfile:
                                fkErpDomainControlIndex 
                                fkErpDomainControlName
                                fkErpDomainControlPrimaryPort
                                fkErpDomainControlSecondaryPort
                                fkErpDomainControlBridgeRole
                                fkErpDomainControlOperatorRequest
                                fkErpDomainControlWaitToRestoreTime
                                fkErpDomainControlTestPacketInterval
                                fkErpDomainControlLearningDisabledTime
                                
                                setErpProtectionActivation:
                                fkErpDomainControlIndex 
                                fkErpDomainControlProtectionActivation
                                "
                        ::= { fkErpDomainControl 1 }

                
                -- 1.3.6.1.4.1.10428 9 1.101.3.18.2.2
                fkErpDomainControlStatus OBJECT-TYPE
                        SYNTAX FkControlStatusType
                        MAX-ACCESS read-only
                        STATUS current
                        DESCRIPTION
                                "The status of a user command. 
                                "
                        ::= { fkErpDomainControl 2 }

                
                -- 1.3.6.1.4.1.10428 9 1.101.3.18.2.3
                fkErpDomainControlTimer OBJECT-TYPE
                        SYNTAX Gauge32
                        MAX-ACCESS read-write
                        STATUS current
                        DESCRIPTION
                                "The maximum wait time for the manager for a long running user command. 
                                "
                        ::= { fkErpDomainControl 3 }

                
                -- 1.3.6.1.4.1.10428 9 1.101.3.18.2.4
                fkErpDomainControlTImeStamp OBJECT-TYPE
                        SYNTAX TimeTicks
                        MAX-ACCESS read-only
                        STATUS current
                        DESCRIPTION
                                "The time stamp of the last command (end of command)."
                        ::= { fkErpDomainControl 4 }

                
                -- 1.3.6.1.4.1.10428 9 1.101.3.18.2.5
                fkErpDomainControlReqResult OBJECT-TYPE
                        SYNTAX FkControlRequestResultType
                        MAX-ACCESS read-only
                        STATUS current
                        DESCRIPTION
                                "The result of the last user command."
                        ::= { fkErpDomainControl 5 }

                
                -- 1.3.6.1.4.1.10428 9 1.101.3.18.2.6
                fkErpDomainControlIndex OBJECT-TYPE
                        SYNTAX Integer32
                        MAX-ACCESS read-write
                        STATUS current
                        DESCRIPTION
                                " An index value that uniquely identifies an ERP domain."
                        ::= { fkErpDomainControl 6 }

                
                -- 1.3.6.1.4.1.10428 9 1.101.3.18.2.7
                fkErpDomainControlName OBJECT-TYPE
                        SYNTAX OCTET STRING
                        MAX-ACCESS read-write
                        STATUS current
                        DESCRIPTION
                                " Domain name."
                        ::= { fkErpDomainControl 7 }

                
                -- 1.3.6.1.4.1.10428 9 1.101.3.18.2.8
                fkErpDomainControlPrimaryPort OBJECT-TYPE
                        SYNTAX InterfaceIndex
                        MAX-ACCESS read-write
                        STATUS current
                        DESCRIPTION
                                " Interface index that represents the primary port of the domain."
                        ::= { fkErpDomainControl 8 }

                
                -- 1.3.6.1.4.1.10428 9 1.101.3.18.2.9
                fkErpDomainControlSecondaryPort OBJECT-TYPE
                        SYNTAX InterfaceIndex
                        MAX-ACCESS read-write
                        STATUS current
                        DESCRIPTION
                                " Interface index that represents the secondary port of the domain."
                        ::= { fkErpDomainControl 9 }

                
                -- 1.3.6.1.4.1.10428 9 1.101.3.18.2.10
                fkErpDomainControlBridgeRole OBJECT-TYPE
                        SYNTAX INTEGER
                                {
                                normalNode(0),
                                rmNode(1)
                                }
                        MAX-ACCESS read-write
                        STATUS current
                        DESCRIPTION
                                " Mode that the ERP domain may operate in."
                        ::= { fkErpDomainControl 10 }

                
                -- 1.3.6.1.4.1.10428 9 1.101.3.18.2.11
                fkErpDomainControlProtectionActivation OBJECT-TYPE
                        SYNTAX INTEGER
                                {
                                deactivated(0),
                                activated(1)
                                }
                        MAX-ACCESS read-write
                        STATUS current
                        DESCRIPTION
                                " Protection activation."
                        ::= { fkErpDomainControl 11 }

                
                -- 1.3.6.1.4.1.10428 9 1.101.3.18.2.12
                fkErpDomainControlOperatorRequest OBJECT-TYPE
                        SYNTAX INTEGER
                                {
                                clear(0),
                                manualToSecondary(1)
                                }
                        MAX-ACCESS read-write
                        STATUS current
                        DESCRIPTION
                                "Operator Request."
                        ::= { fkErpDomainControl 12 }

                
                -- 1.3.6.1.4.1.10428 9 1.101.3.18.2.13
                fkErpDomainControlWaitToRestoreTime OBJECT-TYPE
                        SYNTAX INTEGER (1..720)
                        MAX-ACCESS read-write
                        STATUS current
                        DESCRIPTION
                                " Time in seconds taken to verify that ring integrity is restored."
                        ::= { fkErpDomainControl 13 }

                
                -- 1.3.6.1.4.1.10428 9 1.101.3.18.2.14
                fkErpDomainControlTestPacketInterval OBJECT-TYPE
                        SYNTAX INTEGER (10..500)
                        MAX-ACCESS read-write
                        STATUS current
                        DESCRIPTION
                                " Time in mili seconds between consecutive transmissions of test packages."
                        ::= { fkErpDomainControl 14 }

                
                -- 1.3.6.1.4.1.10428 9 1.101.3.18.2.15
                fkErpDomainControlLearningDisabledTime OBJECT-TYPE
                        SYNTAX INTEGER (0..500)
                        MAX-ACCESS read-write
                        STATUS current
                        DESCRIPTION
                                " Time in mili seconds during which learning is disabled after a FDB flash."
                        ::= { fkErpDomainControl 15 }

                
                -- 1.3.6.1.4.1.10428 9 1.101.3.18.2.16
                fkErpDomainControlHoldOffTime OBJECT-TYPE
                        SYNTAX INTEGER (0 | 1..20000)
                        MAX-ACCESS read-write
                        STATUS current
                        DESCRIPTION
                                "The hold off time."
                        ::= { fkErpDomainControl 16 }

                
                -- 1.3.6.1.4.1.10428 9 1.101.3.18.2.17
                fkErpDomainControlRingPriority OBJECT-TYPE
                        SYNTAX INTEGER (0 | 1..255)
                        MAX-ACCESS read-write
                        STATUS current
                        DESCRIPTION
                                "The ring priority"
                        ::= { fkErpDomainControl 17 }

                
                -- 1.3.6.1.4.1.10428 9 1.101.3.18.2.18
                fkErpDomainControlLotp OBJECT-TYPE
                        SYNTAX INTEGER
                                {
                                clear(0),
                                raised(1)
                                }
                        MAX-ACCESS read-write
                        STATUS current
                        DESCRIPTION
                                "Loss of Test Packet alarm status. Only meaningful in RM node."
                        ::= { fkErpDomainControl 18 }

                
                -- 1.3.6.1.4.1.10428 9 1.101.3.18.2.19
                fkErpDomainControlULotp OBJECT-TYPE
                        SYNTAX INTEGER
                                {
                                clear(0),
                                raised(1)
                                }
                        MAX-ACCESS read-write
                        STATUS current
                        DESCRIPTION
                                "Unidirectional Detection of  Loss of Test Packet alarm status.
                                Only meaningful in RM node."
                        ::= { fkErpDomainControl 19 }

                
                -- 1.3.6.1.4.1.10428 9 1.101.3.18.2.20
                fkErpDomainControlMultipleRM OBJECT-TYPE
                        SYNTAX INTEGER
                                {
                                clear(0),
                                raised(1)
                                }
                        MAX-ACCESS read-write
                        STATUS current
                        DESCRIPTION
                                "Multiple Redundancy Manager alarm status. Only meaningful
                                in RM node.
                                "
                        ::= { fkErpDomainControl 20 }

                
                -- 1.3.6.1.4.1.10428 9 1.101.3.18.2.21
                fkErpDomainControlRMNodeReacheablility OBJECT-TYPE
                        SYNTAX INTEGER
                                {
                                clear(0),
                                raised(1)
                                }
                        MAX-ACCESS read-write
                        STATUS current
                        DESCRIPTION
                                "Multiple Redundancy Manager alarm status. Only meaningful
                                in RM node."
                        ::= { fkErpDomainControl 21 }

                
                -- 1.3.6.1.4.1.10428 9 1.101.3.18.3
                fkErpDomainNotification OBJECT IDENTIFIER ::= { fkErpDomain 3 }

                
                -- 1.3.6.1.4.1.10428 9 1.101.3.18.3.1
                fkErpDomainCreated NOTIFICATION-TYPE
                        OBJECTS { fkErpDomainControlRequest, fkErpDomainControlReqResult, fkErpDomainControlTImeStamp, fkErpDomainName, fkErpDomainPrimaryPort, 
                                fkErpDomainSecondaryPort, fkErpDomainBridgeRole, fkErpDomainProtectionActivation, fkErpDomainOperatorRequest, fkErpDomainWaitToRestoreTime, 
                                fkErpDomainTestPacketInterval, fkErpDomainLearningDisabledTime }
                        STATUS current
                        DESCRIPTION 
                                " "
                        ::= { fkErpDomainNotification 1 }

                
                -- 1.3.6.1.4.1.10428 9 1.101.3.18.3.2
                fkErpDomainDestroyed NOTIFICATION-TYPE
                        OBJECTS { fkErpDomainControlRequest, fkErpDomainControlReqResult, fkErpDomainControlIndex, fkErpDomainControlTImeStamp }
                        STATUS current
                        DESCRIPTION 
                                " "
                        ::= { fkErpDomainNotification 2 }

                
                -- 1.3.6.1.4.1.10428 9 1.101.3.18.3.3
                fkErpDomainProfileChanged NOTIFICATION-TYPE
                        OBJECTS { fkErpDomainControlRequest, fkErpDomainControlReqResult, fkErpDomainControlTImeStamp, fkErpDomainName, fkErpDomainPrimaryPort, 
                                fkErpDomainSecondaryPort, fkErpDomainBridgeRole, fkErpDomainOperatorRequest, fkErpDomainWaitToRestoreTime, fkErpDomainTestPacketInterval, 
                                fkErpDomainLearningDisabledTime }
                        STATUS current
                        DESCRIPTION 
                                " "
                        ::= { fkErpDomainNotification 3 }

                
                -- 1.3.6.1.4.1.10428 9 1.101.3.18.3.4
                fkErpProtectionActivationChanged NOTIFICATION-TYPE
                        OBJECTS { fkErpDomainControlRequest, fkErpDomainControlReqResult, fkErpDomainControlTImeStamp, fkErpDomainProtectionActivation }
                        STATUS current
                        DESCRIPTION 
                                " "
                        ::= { fkErpDomainNotification 4 }

                
                -- 1.3.6.1.4.1.10428 9 1.101.3.18.3.5
                fkErpHoldOffTimeChanged NOTIFICATION-TYPE
                        OBJECTS { fkErpDomainControlRequest, fkErpDomainControlTImeStamp, fkErpDomainControlReqResult, fkErpDomainHoldOffTime }
                        STATUS current
                        DESCRIPTION 
                                "Description."
                        ::= { fkErpDomainNotification 5 }

                
                -- 1.3.6.1.4.1.10428 9 1.101.3.18.3.6
                fkErpRingPriorityChanged NOTIFICATION-TYPE
                        OBJECTS { fkErpDomainControlRequest, fkErpDomainControlTImeStamp, fkErpDomainControlReqResult, fkErpDomainRingPriority }
                        STATUS current
                        DESCRIPTION 
                                "Description."
                        ::= { fkErpDomainNotification 6 }

                
                -- 1.3.6.1.4.1.10428 9 1.101.3.18.3.7
                fkErpTrapChanged NOTIFICATION-TYPE
                        OBJECTS { fkErpDomainControlRequest, fkErpDomainControlTImeStamp, fkErpDomainControlReqResult, fkErpDomainLotp, fkErpDomainULotp, 
                                fkErpDomainMultipleRM, fkErpDomainRMNodeReacheablility }
                        STATUS current
                        DESCRIPTION 
                                "Description."
                        ::= { fkErpDomainNotification 7 }

                
--  1.3.6.1.4.1.10428 9 1.9.8.19
                -- 1.3.6.1.4.1.10428 9 1.101.3.19
                fkLldpPort OBJECT IDENTIFIER ::= { fkBridge 19 }

                
--  1.3.6.1.4.1.10428 9 1.9.8.19.1
                -- 1.3.6.1.4.1.10428 9 1.101.3.19.1
                fkLldpPortTable OBJECT-TYPE
                        SYNTAX SEQUENCE OF FkLldpPortEntry
                        MAX-ACCESS not-accessible
                        STATUS current
                        DESCRIPTION
                                "LLDP port table."
                        ::= { fkLldpPort 1 }

                
--  1.3.6.1.4.1.10428 9 1.9.8.19.1.1
                -- 1.3.6.1.4.1.10428 9 1.101.3.19.1.1
                fkLldpPortEntry OBJECT-TYPE
                        SYNTAX FkLldpPortEntry
                        MAX-ACCESS not-accessible
                        STATUS current
                        DESCRIPTION
                                " key: fkLldpPortIndex"
                        INDEX { fkLldpPortIndex }
                        ::= { fkLldpPortTable 1 }

                
                FkLldpPortEntry ::=
                        SEQUENCE { 
                                fkLldpPortIndex
                                        INTEGER,
                                fkLldpPortActivity
                                        Boolean,
                                fkLldpPortAdminStatus
                                        INTEGER,
                                fkLldpPortNotificationEnable
                                        Boolean,
                                fkLldpPortTLVsTxEnable
                                        BITS,
                                fkLldpPortMgmtTxEnable
                                        Boolean,
                                fkLldpPortMgmtAddress
                                        IpAddress
                         }

--  1.3.6.1.4.1.10428 9 1.9.8.19.1.1.1
                -- 1.3.6.1.4.1.10428 9 1.101.3.19.1.1.1
                fkLldpPortIndex OBJECT-TYPE
                        SYNTAX INTEGER (1..255)
                        MAX-ACCESS read-only
                        STATUS current
                        DESCRIPTION
                                " LLDP port index"
                        ::= { fkLldpPortEntry 1 }

                
                -- 1.3.6.1.4.1.10428 9 1.101.3.19.1.1.2
                fkLldpPortActivity OBJECT-TYPE
                        SYNTAX Boolean
                        MAX-ACCESS read-only
                        STATUS current
                        DESCRIPTION
                                "fkLldpPortActivity"
                        ::= { fkLldpPortEntry 2 }

                
--  1.3.6.1.4.1.10428 9 1.9.8.19.1.1.2
                -- 1.3.6.1.4.1.10428 9 1.101.3.19.1.1.3
                fkLldpPortAdminStatus OBJECT-TYPE
                        SYNTAX INTEGER
                                {
                                txOnly(1),
                                rxOnly(2),
                                txAndRx(3),
                                disabled(4)
                                }
                        MAX-ACCESS read-write
                        STATUS current
                        DESCRIPTION
                                "The administratively desired status of the local LLDP agent."
                        ::= { fkLldpPortEntry 3 }

                
--  It controls, on a per port basis,  whether or not notifications from the agent are enabled.
-- 1.3.6.1.4.1.10428 9 1.9.8.19.1.1.3
                -- 1.3.6.1.4.1.10428 9 1.101.3.19.1.1.4
                fkLldpPortNotificationEnable OBJECT-TYPE
                        SYNTAX Boolean
                        MAX-ACCESS read-write
                        STATUS current
                        DESCRIPTION
                                "It controls, on a per port basis,  whether or not notifications from the agent are enabled. "
                        ::= { fkLldpPortEntry 4 }

                
--  1.3.6.1.4.1.10428 9 1.9.8.19.1.1.4
                -- 1.3.6.1.4.1.10428 9 1.101.3.19.1.1.5
                fkLldpPortTLVsTxEnable OBJECT-TYPE
                        SYNTAX BITS
                                {
                                portDesc(0),
                                sysName(1),
                                sysDesc(2),
                                sysCap(3)
                                }
                        MAX-ACCESS read-write
                        STATUS current
                        DESCRIPTION
                                "Bitmap that includes the basic set of LLDP TLVs whose transmission is allowed on the local LLDP agent by the network management."
                        ::= { fkLldpPortEntry 5 }

                
                -- 1.3.6.1.4.1.10428 9 1.101.3.19.1.1.6
                fkLldpPortMgmtTxEnable OBJECT-TYPE
                        SYNTAX Boolean
                        MAX-ACCESS read-only
                        STATUS current
                        DESCRIPTION
                                "It indicates that the port is either enable or not to transfer management address."
                        ::= { fkLldpPortEntry 6 }

                
                -- 1.3.6.1.4.1.10428 9 1.101.3.19.1.1.7
                fkLldpPortMgmtAddress OBJECT-TYPE
                        SYNTAX IpAddress
                        MAX-ACCESS read-only
                        STATUS current
                        DESCRIPTION
                                "Management address to transfer on the port."
                        ::= { fkLldpPortEntry 7 }

                
--  1.3.6.1.4.1.10428 9 1.9.8.19.2
                -- 1.3.6.1.4.1.10428 9 1.101.3.19.2
                fkLldpPortControl OBJECT IDENTIFIER ::= { fkLldpPort 2 }

                
--  1.3.6.1.4.1.10428 9 1.9.8.19.2.1
                -- 1.3.6.1.4.1.10428 9 1.101.3.19.2.1
                fkLldpPortControlRequest OBJECT-TYPE
                        SYNTAX INTEGER { setLldpPortProfile(1) }
                        MAX-ACCESS read-write
                        STATUS current
                        DESCRIPTION
                                " The request of a user command"
                        ::= { fkLldpPortControl 1 }

                
--  1.3.6.1.4.1.10428 9 1.9.8.19.2.2
                -- 1.3.6.1.4.1.10428 9 1.101.3.19.2.2
                fkLldpPortControlStatus OBJECT-TYPE
                        SYNTAX FkControlStatusType
                        MAX-ACCESS read-only
                        STATUS current
                        DESCRIPTION
                                " The status of user command"
                        ::= { fkLldpPortControl 2 }

                
--  1.3.6.1.4.1.10428 9 1.9.8.19.2.3
                -- 1.3.6.1.4.1.10428 9 1.101.3.19.2.3
                fkLldpPortControlTimer OBJECT-TYPE
                        SYNTAX Gauge32
                        MAX-ACCESS read-write
                        STATUS current
                        DESCRIPTION
                                " The maximum time for the manager for a long running user command"
                        ::= { fkLldpPortControl 3 }

                
--  1.3.6.1.4.1.10428 9 1.9.8.19.2.4
                -- 1.3.6.1.4.1.10428 9 1.101.3.19.2.4
                fkLldpPortControlTimeStamp OBJECT-TYPE
                        SYNTAX TimeTicks
                        MAX-ACCESS read-only
                        STATUS current
                        DESCRIPTION
                                " The time stamp of the last command(end of command)"
                        ::= { fkLldpPortControl 4 }

                
--  1.3.6.1.4.1.10428 9 1.9.8.19.2.5
                -- 1.3.6.1.4.1.10428 9 1.101.3.19.2.5
                fkLldpPortControlReqResult OBJECT-TYPE
                        SYNTAX FkControlRequestResultType
                        MAX-ACCESS read-only
                        STATUS current
                        DESCRIPTION
                                " The result of the last user command"
                        ::= { fkLldpPortControl 5 }

                
                -- 1.3.6.1.4.1.10428 9 1.101.3.19.2.6
                fkLldpPortControlIndex OBJECT-TYPE
                        SYNTAX INTEGER (1..255)
                        MAX-ACCESS read-write
                        STATUS current
                        DESCRIPTION
                                "LLDP port index"
                        ::= { fkLldpPortControl 6 }

                
                -- 1.3.6.1.4.1.10428 9 1.101.3.19.2.7
                fkLldpPortControlActivity OBJECT-TYPE
                        SYNTAX Boolean
                        MAX-ACCESS read-write
                        STATUS current
                        DESCRIPTION
                                "fkLldpPortControlActivity"
                        ::= { fkLldpPortControl 7 }

                
--  1.3.6.1.4.1.10428 9 1.9.8.19.2.6
                -- 1.3.6.1.4.1.10428 9 1.101.3.19.2.8
                fkLldpPortControlAdminstatus OBJECT-TYPE
                        SYNTAX INTEGER
                                {
                                txOnly(1),
                                rxOnly(2),
                                txAndRx(3),
                                disabled(4)
                                }
                        MAX-ACCESS read-write
                        STATUS current
                        DESCRIPTION
                                "The administratively desired status of the local LLDP agent."
                        ::= { fkLldpPortControl 8 }

                
--  1.3.6.1.4.1.10428 9 1.9.8.19.2.7
                -- 1.3.6.1.4.1.10428 9 1.101.3.19.2.9
                fkLldpPortControlNotificationEnable OBJECT-TYPE
                        SYNTAX Boolean
                        MAX-ACCESS read-write
                        STATUS current
                        DESCRIPTION
                                " It controls, on a per port basis, whether or not notifications from the agent are enabled."
                        ::= { fkLldpPortControl 9 }

                
--  1.3.6.1.4.1.10428 9 1.9.8.19.2.8
                -- 1.3.6.1.4.1.10428 9 1.101.3.19.2.10
                fkLldpPortControlTLVsTxEnable OBJECT-TYPE
                        SYNTAX BITS
                                {
                                portDesc(0),
                                sysName(1),
                                sysDesc(2),
                                sysCap(3)
                                }
                        MAX-ACCESS read-write
                        STATUS current
                        DESCRIPTION
                                " Bitmap that includes the basic set of LLDP TLVs whose transmission is allowed on the local LLDP agent by the network management."
                        ::= { fkLldpPortControl 10 }

                
                -- 1.3.6.1.4.1.10428 9 1.101.3.19.2.11
                fkLldpPortControlMgmtTxEnable OBJECT-TYPE
                        SYNTAX Boolean
                        MAX-ACCESS read-write
                        STATUS current
                        DESCRIPTION
                                "It indicates that the port is either enable or not to transfer management address."
                        ::= { fkLldpPortControl 11 }

                
                -- 1.3.6.1.4.1.10428 9 1.101.3.19.2.12
                fkLldpPortControlMgmtAddress OBJECT-TYPE
                        SYNTAX IpAddress
                        MAX-ACCESS read-write
                        STATUS current
                        DESCRIPTION
                                "Management address to transfer on the port."
                        ::= { fkLldpPortControl 12 }

                
--  1.3.6.1.4.1.10428 9 1.9.8.19.3
                -- 1.3.6.1.4.1.10428 9 1.101.3.19.3
                fkLldpPortNotification OBJECT IDENTIFIER ::= { fkLldpPort 3 }

                
--  1.3.6.1.4.1.10428 9 1.9.8.19.3.1
                -- 1.3.6.1.4.1.10428 9 1.101.3.19.3.1
                fkLldpPortProfileChanged NOTIFICATION-TYPE
                        OBJECTS { fkLldpPortActivity, fkLldpPortAdminStatus, fkLldpPortNotificationEnable, fkLldpPortTLVsTxEnable, fkLldpPortMgmtTxEnable, 
                                fkLldpPortMgmtAddress, fkLldpPortControlRequest, fkLldpPortControlTimeStamp, fkLldpPortControlReqResult }
                        STATUS current
                        DESCRIPTION 
                                " "
                        ::= { fkLldpPortNotification 1 }

                
--  1.3.6.1.4.1.10428 9 1.9.8.20
                -- 1.3.6.1.4.1.10428 9 1.101.3.20
                fkLldpRemote OBJECT IDENTIFIER ::= { fkBridge 20 }

                
--  1.3.6.1.4.1.10428 9 1.9.8.20.1
                -- 1.3.6.1.4.1.10428 9 1.101.3.20.1
                fkLldpRemoteTable OBJECT-TYPE
                        SYNTAX SEQUENCE OF FkLldpRemoteEntry
                        MAX-ACCESS not-accessible
                        STATUS current
                        DESCRIPTION
                                " LLDP remote table."
                        ::= { fkLldpRemote 1 }

                
--  1.3.6.1.4.1.10428 9 1.9.8.20.1.1
                -- 1.3.6.1.4.1.10428 9 1.101.3.20.1.1
                fkLldpRemoteEntry OBJECT-TYPE
                        SYNTAX FkLldpRemoteEntry
                        MAX-ACCESS not-accessible
                        STATUS current
                        DESCRIPTION
                                " key: fkLldpPortIndex, fkLldpRemIndex"
                        INDEX { fkLldpPortIndex, fkLldpRemIndex }
                        ::= { fkLldpRemoteTable 1 }

                
                FkLldpRemoteEntry ::=
                        SEQUENCE { 
                                fkLldpRemIndex
                                        Integer32,
                                fkLldpRemTimeMark
                                        TimeTicks,
                                fkLldpRemChassisIdSubtype
                                        INTEGER,
                                fkLldpRemChassisId
                                        OCTET STRING,
                                fkLldpRemPortIdSubtype
                                        INTEGER,
                                fkLldpRemPortId
                                        OCTET STRING,
                                fkLldpRemPortDesc
                                        OCTET STRING,
                                fkLldpRemSysName
                                        OCTET STRING,
                                fkLldpRemSysDesc
                                        OCTET STRING,
                                fkLldpRemSysCapSupported
                                        BITS,
                                fkLldpRemSysCapEnabled
                                        BITS
                         }

--  1.3.6.1.4.1.10428 9 1.9.8.20.1.1.3
                -- 1.3.6.1.4.1.10428 9 1.101.3.20.1.1.1
                fkLldpRemIndex OBJECT-TYPE
                        SYNTAX Integer32 (1..2147483647)
                        MAX-ACCESS read-write
                        STATUS current
                        DESCRIPTION
                                "This object represents an arbitrary local integer value used by this agent to identify a particular connection instance, unique only for the indicated remote system."
                        ::= { fkLldpRemoteEntry 1 }

                
--  1.3.6.1.4.1.10428 9 1.9.8.20.1.1.1
                -- 1.3.6.1.4.1.10428 9 1.101.3.20.1.1.2
                fkLldpRemTimeMark OBJECT-TYPE
                        SYNTAX TimeTicks
                        MAX-ACCESS read-only
                        STATUS current
                        DESCRIPTION
                                "The sysUptime that this entry has been created or modified."
                        ::= { fkLldpRemoteEntry 2 }

                
--  1.3.6.1.4.1.10428 9 1.9.8.20.1.1.4
                -- 1.3.6.1.4.1.10428 9 1.101.3.20.1.1.3
                fkLldpRemChassisIdSubtype OBJECT-TYPE
                        SYNTAX INTEGER
                                {
                                chassisComponent(1),
                                interfaceAlias(2),
                                portComponent(3),
                                macAddress(4),
                                networkAddress(5),
                                interfaceName(6),
                                local(7)
                                }
                        MAX-ACCESS read-only
                        STATUS current
                        DESCRIPTION
                                "The type of encoding used to identify the chassis associatedwith the remote system."
                        ::= { fkLldpRemoteEntry 3 }

                
--  1.3.6.1.4.1.10428 9 1.9.8.20.1.1.5
                -- 1.3.6.1.4.1.10428 9 1.101.3.20.1.1.4
                fkLldpRemChassisId OBJECT-TYPE
                        SYNTAX OCTET STRING (SIZE (1..255))
                        MAX-ACCESS read-write
                        STATUS current
                        DESCRIPTION
                                "The type of encoding used to identify the chassis associatedwith the remote system."
                        ::= { fkLldpRemoteEntry 4 }

                
--  1.3.6.1.4.1.10428 9 1.9.8.20.1.1.6
                -- 1.3.6.1.4.1.10428 9 1.101.3.20.1.1.5
                fkLldpRemPortIdSubtype OBJECT-TYPE
                        SYNTAX INTEGER
                                {
                                interfaceAlias(1),
                                portComponent(2),
                                macAddress(3),
                                networkAddress(4),
                                interfaceName(5),
                                agentCircuitId(6),
                                local(7)
                                }
                        MAX-ACCESS read-write
                        STATUS current
                        DESCRIPTION
                                "The type of port identifier encoding used in the associated'lldpRemPortId' object."
                        ::= { fkLldpRemoteEntry 5 }

                
--  1.3.6.1.4.1.10428 9 1.9.8.20.1.1.7
                -- 1.3.6.1.4.1.10428 9 1.101.3.20.1.1.6
                fkLldpRemPortId OBJECT-TYPE
                        SYNTAX OCTET STRING (SIZE (1..255))
                        MAX-ACCESS read-only
                        STATUS current
                        DESCRIPTION
                                "The string value used to identify the port component associated with the remote system."
                        ::= { fkLldpRemoteEntry 6 }

                
--  1.3.6.1.4.1.10428 9 1.9.8.20.1.1.8
                -- 1.3.6.1.4.1.10428 9 1.101.3.20.1.1.7
                fkLldpRemPortDesc OBJECT-TYPE
                        SYNTAX OCTET STRING (SIZE (0..255))
                        MAX-ACCESS read-only
                        STATUS current
                        DESCRIPTION
                                "The string value used to identify the description of the given port associated with the remote system."
                        ::= { fkLldpRemoteEntry 7 }

                
--  1.3.6.1.4.1.10428 9 1.9.8.20.1.1.9
                -- 1.3.6.1.4.1.10428 9 1.101.3.20.1.1.8
                fkLldpRemSysName OBJECT-TYPE
                        SYNTAX OCTET STRING (SIZE (0..255))
                        MAX-ACCESS read-only
                        STATUS current
                        DESCRIPTION
                                "The string value used to identify the system name of the remote system."
                        ::= { fkLldpRemoteEntry 8 }

                
--  1.3.6.1.4.1.10428 9 1.9.8.20.1.1.10
                -- 1.3.6.1.4.1.10428 9 1.101.3.20.1.1.9
                fkLldpRemSysDesc OBJECT-TYPE
                        SYNTAX OCTET STRING (SIZE (0..255))
                        MAX-ACCESS read-only
                        STATUS current
                        DESCRIPTION
                                "The string value used to identify the system description of the remote system."
                        ::= { fkLldpRemoteEntry 9 }

                
--  1.3.6.1.4.1.10428 9 1.9.8.20.1.1.11
                -- 1.3.6.1.4.1.10428 9 1.101.3.20.1.1.10
                fkLldpRemSysCapSupported OBJECT-TYPE
                        SYNTAX BITS
                                {
                                other(0),
                                repeater(1),
                                bridge(2),
                                wlanAccessPoint(3),
                                router(4),
                                telephone(5),
                                docsisCableDevice(6),
                                stationOnly(7)
                                }
                        MAX-ACCESS read-only
                        STATUS current
                        DESCRIPTION
                                "The bitmap value used to identify which system capabilities are supported on the remote system."
                        ::= { fkLldpRemoteEntry 10 }

                
--  1.3.6.1.4.1.10428 9 1.9.8.20.1.1.12
                -- 1.3.6.1.4.1.10428 9 1.101.3.20.1.1.11
                fkLldpRemSysCapEnabled OBJECT-TYPE
                        SYNTAX BITS
                                {
                                other(0),
                                repeater(1),
                                bridge(2),
                                wlanAccessPoint(3),
                                router(4),
                                telephone(5),
                                docsisCableDevice(6),
                                stationOnly(7)
                                }
                        MAX-ACCESS read-only
                        STATUS current
                        DESCRIPTION
                                "The bitmap value used to identify which system capabilities are enabled on the remote system."
                        ::= { fkLldpRemoteEntry 11 }

                
--  1.3.6.1.4.1.10428 9 1.9.8.20.1
                -- 1.3.6.1.4.1.10428 9 1.101.3.20.2
                fkLldpRemoteManAddrTable OBJECT-TYPE
                        SYNTAX SEQUENCE OF FkLldpRemoteManAddrEntry
                        MAX-ACCESS not-accessible
                        STATUS current
                        DESCRIPTION
                                " LLDP remote table."
                        ::= { fkLldpRemote 2 }

                
--  1.3.6.1.4.1.10428 9 1.9.8.20.1.1
                -- 1.3.6.1.4.1.10428 9 1.101.3.20.2.1
                fkLldpRemoteManAddrEntry OBJECT-TYPE
                        SYNTAX FkLldpRemoteManAddrEntry
                        MAX-ACCESS not-accessible
                        STATUS current
                        DESCRIPTION
                                " key: fkLldpPortIndex, fkLldpRemIndex"
                        INDEX { fkLldpPortIndex, fkLldpRemIndex, fkLldpRemManAddrSubType, fkLldpRemManAddr }
                        ::= { fkLldpRemoteManAddrTable 1 }

                
                FkLldpRemoteManAddrEntry ::=
                        SEQUENCE { 
                                fkLldpRemManAddrSubType
                                        AddressFamilyNumbers,
                                fkLldpRemManAddr
                                        OCTET STRING,
                                fkLldpRemManAddrIfSubType
                                        FkLldpManAddrIfSubType,
                                fkLldpRemManAddrIfId
                                        INTEGER,
                                fkLldpRemAddrOid
                                        OBJECT IDENTIFIER
                         }

--  1.3.6.1.4.1.10428 9 1.9.8.20.1.1.3
                -- 1.3.6.1.4.1.10428 9 1.101.3.20.2.1.1
                fkLldpRemManAddrSubType OBJECT-TYPE
                        SYNTAX AddressFamilyNumbers (0..65535)
                        MAX-ACCESS read-only
                        STATUS current
                        DESCRIPTION
                                "This object represents an arbitrary local integer value used by this agent to identify a particular connection instance, unique only for the indicated remote system."
                        ::= { fkLldpRemoteManAddrEntry 1 }

                
--  1.3.6.1.4.1.10428 9 1.9.8.20.1.1.1
                -- 1.3.6.1.4.1.10428 9 1.101.3.20.2.1.2
                fkLldpRemManAddr OBJECT-TYPE
                        SYNTAX OCTET STRING
                        MAX-ACCESS read-only
                        STATUS current
                        DESCRIPTION
                                "The sysUptime that this entry has been created or modified."
                        ::= { fkLldpRemoteManAddrEntry 2 }

                
--  1.3.6.1.4.1.10428 9 1.9.8.20.1.1.4
                -- 1.3.6.1.4.1.10428 9 1.101.3.20.2.1.3
                fkLldpRemManAddrIfSubType OBJECT-TYPE
                        SYNTAX FkLldpManAddrIfSubType
                        MAX-ACCESS read-only
                        STATUS current
                        DESCRIPTION
                                "The type of encoding used to identify the chassis associatedwith the remote system."
                        ::= { fkLldpRemoteManAddrEntry 3 }

                
--  1.3.6.1.4.1.10428 9 1.9.8.20.1.1.5
                -- 1.3.6.1.4.1.10428 9 1.101.3.20.2.1.4
                fkLldpRemManAddrIfId OBJECT-TYPE
                        SYNTAX INTEGER
                        MAX-ACCESS read-only
                        STATUS current
                        DESCRIPTION
                                "The type of encoding used to identify the chassis associatedwith the remote system."
                        ::= { fkLldpRemoteManAddrEntry 4 }

                
--  1.3.6.1.4.1.10428 9 1.9.8.20.1.1.6
                -- 1.3.6.1.4.1.10428 9 1.101.3.20.2.1.5
                fkLldpRemAddrOid OBJECT-TYPE
                        SYNTAX OBJECT IDENTIFIER
                        MAX-ACCESS read-only
                        STATUS current
                        DESCRIPTION
                                "The type of port identifier encoding used in the associated'lldpRemPortId' object."
                        ::= { fkLldpRemoteManAddrEntry 5 }

                
                -- 1.3.6.1.4.1.10428 9 1.101.3.21
                fkLldpStatistics OBJECT IDENTIFIER ::= { fkBridge 21 }

                
                -- 1.3.6.1.4.1.10428 9 1.101.3.21.1
                fkLldpStatisticsTable OBJECT-TYPE
                        SYNTAX SEQUENCE OF FkLldpStatisticsEntry
                        MAX-ACCESS not-accessible
                        STATUS current
                        DESCRIPTION
                                "LLDP statistics table."
                        ::= { fkLldpStatistics 1 }

                
                -- 1.3.6.1.4.1.10428 9 1.101.3.21.1.1
                fkLldpStatisticsEntry OBJECT-TYPE
                        SYNTAX FkLldpStatisticsEntry
                        MAX-ACCESS not-accessible
                        STATUS current
                        DESCRIPTION
                                "key: fkLldpPortIndex"
                        INDEX { fkLldpPortIndex }
                        ::= { fkLldpStatisticsTable 1 }

                
                FkLldpStatisticsEntry ::=
                        SEQUENCE { 
                                fkLldpStatsTxPortFramesTotal
                                        Integer32,
                                fkLldpStatsRxPortFramesDiscardedTotal
                                        Counter32,
                                fkLldpStatsRxPortFramesErrors
                                        Integer32,
                                fkLldpStatsRxPortFramesTotal
                                        Counter32,
                                fkLldpStatsRxPortTLVsDiscardedTotal
                                        Integer32,
                                fkLldpStatsRxPortTLVsUnrecognizedTotal
                                        Integer32,
                                fkLldpStatsRxPortAgeoutsTotal
                                        Counter32
                         }

                -- 1.3.6.1.4.1.10428 9 1.101.3.21.1.1.1
                fkLldpStatsTxPortFramesTotal OBJECT-TYPE
                        SYNTAX Integer32
                        MAX-ACCESS read-only
                        STATUS current
                        DESCRIPTION
                                "The number of LLDP frames transmitted by this LLDP agent on the indicated port."
                        ::= { fkLldpStatisticsEntry 1 }

                
                -- 1.3.6.1.4.1.10428 9 1.101.3.21.1.1.2
                fkLldpStatsRxPortFramesDiscardedTotal OBJECT-TYPE
                        SYNTAX Counter32
                        MAX-ACCESS read-only
                        STATUS current
                        DESCRIPTION
                                "The number of LLDP frames received by this LLDP agent on  the indicated port, and then discarded for any reason."
                        ::= { fkLldpStatisticsEntry 2 }

                
                -- 1.3.6.1.4.1.10428 9 1.101.3.21.1.1.3
                fkLldpStatsRxPortFramesErrors OBJECT-TYPE
                        SYNTAX Integer32
                        MAX-ACCESS read-only
                        STATUS current
                        DESCRIPTION
                                "The number of invalid LLDP frames received by this LLDPagent on the indicated port, while this LLDP agent is enabled."
                        ::= { fkLldpStatisticsEntry 3 }

                
                -- 1.3.6.1.4.1.10428 9 1.101.3.21.1.1.4
                fkLldpStatsRxPortFramesTotal OBJECT-TYPE
                        SYNTAX Counter32
                        MAX-ACCESS read-only
                        STATUS current
                        DESCRIPTION
                                "The number of valid LLDP frames received by this LLDP agent on the indicated port, while this LLDP agent is enabled."
                        ::= { fkLldpStatisticsEntry 4 }

                
                -- 1.3.6.1.4.1.10428 9 1.101.3.21.1.1.5
                fkLldpStatsRxPortTLVsDiscardedTotal OBJECT-TYPE
                        SYNTAX Integer32
                        MAX-ACCESS read-only
                        STATUS current
                        DESCRIPTION
                                "The number of LLDP TLVs discarded for any reason by this LLDP agent on the indicated port."
                        ::= { fkLldpStatisticsEntry 5 }

                
                -- 1.3.6.1.4.1.10428 9 1.101.3.21.1.1.6
                fkLldpStatsRxPortTLVsUnrecognizedTotal OBJECT-TYPE
                        SYNTAX Integer32
                        MAX-ACCESS read-only
                        STATUS current
                        DESCRIPTION
                                "The number of LLDP TLVs received on the given port that are not recognized by this LLDP agent on the indicated port."
                        ::= { fkLldpStatisticsEntry 6 }

                
                -- 1.3.6.1.4.1.10428 9 1.101.3.21.1.1.7
                fkLldpStatsRxPortAgeoutsTotal OBJECT-TYPE
                        SYNTAX Counter32
                        MAX-ACCESS read-only
                        STATUS current
                        DESCRIPTION
                                "The counter that represents the number of age-outs that occurred on a given port."
                        ::= { fkLldpStatisticsEntry 7 }

                
                -- 1.3.6.1.4.1.10428 9 1.101.3.21.2
                fkLldpStatisticsControl OBJECT IDENTIFIER ::= { fkLldpStatistics 2 }

                
                -- 1.3.6.1.4.1.10428 9 1.101.3.21.2.1
                fkLldpStatsControlRequest OBJECT-TYPE
                        SYNTAX INTEGER { clearLldpStatistics(1) }
                        MAX-ACCESS read-write
                        STATUS current
                        DESCRIPTION
                                "The request of a user command"
                        ::= { fkLldpStatisticsControl 1 }

                
                -- 1.3.6.1.4.1.10428 9 1.101.3.21.2.2
                fkLldpStatsControlStatus OBJECT-TYPE
                        SYNTAX FkControlStatusType
                        MAX-ACCESS read-only
                        STATUS current
                        DESCRIPTION
                                "The status of user command"
                        ::= { fkLldpStatisticsControl 2 }

                
                -- 1.3.6.1.4.1.10428 9 1.101.3.21.2.3
                fkLldpStatsControlTimer OBJECT-TYPE
                        SYNTAX Gauge32
                        MAX-ACCESS read-write
                        STATUS current
                        DESCRIPTION
                                "The maximum time for the manager for a long running user command"
                        ::= { fkLldpStatisticsControl 3 }

                
                -- 1.3.6.1.4.1.10428 9 1.101.3.21.2.4
                fkLldpStatsControlTimeStamp OBJECT-TYPE
                        SYNTAX TimeTicks
                        MAX-ACCESS read-only
                        STATUS current
                        DESCRIPTION
                                "The time stamp of the last command(end of command)"
                        ::= { fkLldpStatisticsControl 4 }

                
                -- 1.3.6.1.4.1.10428 9 1.101.3.21.2.5
                fkLldpStatsControlReqResult OBJECT-TYPE
                        SYNTAX FkControlRequestResultType
                        MAX-ACCESS read-only
                        STATUS current
                        DESCRIPTION
                                "The result of the last user command"
                        ::= { fkLldpStatisticsControl 5 }

                
                -- 1.3.6.1.4.1.10428 9 1.101.3.21.2.6
                fkLldpStatsControlPortIndex OBJECT-TYPE
                        SYNTAX Unsigned32 (1..255)
                        MAX-ACCESS read-write
                        STATUS current
                        DESCRIPTION
                                "LLDP port index in fkLldpPortTable"
                        ::= { fkLldpStatisticsControl 6 }

                
                -- 1.3.6.1.4.1.10428 9 1.101.3.21.3
                fkLldpStatisticsNotification OBJECT IDENTIFIER ::= { fkLldpStatistics 3 }

                
                -- 1.3.6.1.4.1.10428 9 1.101.3.21.3.1
                fkLldpStatisticsCleared NOTIFICATION-TYPE
                        OBJECTS { fkLldpStatsControlRequest, fkLldpStatsControlTimeStamp, fkLldpStatsControlPortIndex, fkLldpStatsControlReqResult }
                        STATUS current
                        DESCRIPTION 
                                "Description."
                        ::= { fkLldpStatisticsNotification 1 }

                
                -- 1.3.6.1.4.1.10428 9 1.101.3.22
                fkBridgePortSecurity OBJECT IDENTIFIER ::= { fkBridge 22 }

                
                -- 1.3.6.1.4.1.10428 9 1.101.3.22.1
                fkBridgePSTable OBJECT-TYPE
                        SYNTAX SEQUENCE OF FkBridgePSEntry
                        MAX-ACCESS not-accessible
                        STATUS current
                        DESCRIPTION
                                "bridge port security table."
                        ::= { fkBridgePortSecurity 1 }

                
                -- 1.3.6.1.4.1.10428 9 1.101.3.22.1.1
                fkBridgePSEntry OBJECT-TYPE
                        SYNTAX FkBridgePSEntry
                        MAX-ACCESS not-accessible
                        STATUS current
                        DESCRIPTION
                                "key: fkBridgePSIndex"
                        INDEX { fkBridgePSIndex }
                        ::= { fkBridgePSTable 1 }

                
                FkBridgePSEntry ::=
                        SEQUENCE { 
                                fkBridgePSIndex
                                        InterfaceIndex,
                                fkBridgePSStatus
                                        INTEGER,
                                fkBridgePSMaxCount
                                        INTEGER,
                                fkBridgePSCurrCount
                                        Unsigned32,
                                fkBridgePSAgingType
                                        INTEGER,
                                fkBridgePSAgingTimer
                                        INTEGER,
                                fkBridgePSAgingStatic
                                        INTEGER,
                                fkBridgePSViolation
                                        INTEGER
                         }

                -- 1.3.6.1.4.1.10428 9 1.101.3.22.1.1.1
                fkBridgePSIndex OBJECT-TYPE
                        SYNTAX InterfaceIndex
                        MAX-ACCESS read-only
                        STATUS current
                        DESCRIPTION
                                "The index of logical port"
                        ::= { fkBridgePSEntry 1 }

                
                -- 1.3.6.1.4.1.10428 9 1.101.3.22.1.1.2
                fkBridgePSStatus OBJECT-TYPE
                        SYNTAX INTEGER
                                {
                                enable(1),
                                disable(2)
                                }
                        MAX-ACCESS read-only
                        STATUS current
                        DESCRIPTION
                                "The status of port security"
                        ::= { fkBridgePSEntry 2 }

                
                -- 1.3.6.1.4.1.10428 9 1.101.3.22.1.1.3
                fkBridgePSMaxCount OBJECT-TYPE
                        SYNTAX INTEGER (-1 | 1..16384)
                        MAX-ACCESS read-only
                        STATUS current
                        DESCRIPTION
                                "The max secure addresses
                                The value of -1 is not used
                                "
                        ::= { fkBridgePSEntry 3 }

                
                -- 1.3.6.1.4.1.10428 9 1.101.3.22.1.1.4
                fkBridgePSCurrCount OBJECT-TYPE
                        SYNTAX Unsigned32
                        MAX-ACCESS read-only
                        STATUS current
                        DESCRIPTION
                                "The current count of port security"
                        ::= { fkBridgePSEntry 4 }

                
                -- 1.3.6.1.4.1.10428 9 1.101.3.22.1.1.5
                fkBridgePSAgingType OBJECT-TYPE
                        SYNTAX INTEGER
                                {
                                absolute(1),
                                inactivity(2)
                                }
                        MAX-ACCESS read-only
                        STATUS current
                        DESCRIPTION
                                "The aging type of port security"
                        ::= { fkBridgePSEntry 5 }

                
                -- 1.3.6.1.4.1.10428 9 1.101.3.22.1.1.6
                fkBridgePSAgingTimer OBJECT-TYPE
                        SYNTAX INTEGER (-1 | 0 | 1..2147483647)
                        UNITS "second"
                        MAX-ACCESS read-only
                        STATUS current
                        DESCRIPTION
                                "The aging time of port security
                                The value of -1 and 0 means that aging time fixed to static and it will be not aging out
                                But The case of 5924N,
                                The value of -1 means that aging time fixed to static and it will be not agint out
                                The value of 0 means that aging out disable. "
                        ::= { fkBridgePSEntry 6 }

                
                -- 1.3.6.1.4.1.10428 9 1.101.3.22.1.1.7
                fkBridgePSAgingStatic OBJECT-TYPE
                        SYNTAX INTEGER
                                {
                                enable(1),
                                disable(2)
                                }
                        MAX-ACCESS read-only
                        STATUS current
                        DESCRIPTION
                                "The enable aging for configured secure addressess"
                        ::= { fkBridgePSEntry 7 }

                
                -- 1.3.6.1.4.1.10428 9 1.101.3.22.1.1.8
                fkBridgePSViolation OBJECT-TYPE
                        SYNTAX INTEGER
                                {
                                shutdown(1),
                                protect(2),
                                restrict(3)
                                }
                        MAX-ACCESS read-only
                        STATUS current
                        DESCRIPTION
                                "The security violation mode of port security "
                        ::= { fkBridgePSEntry 8 }

                
                -- 1.3.6.1.4.1.10428 9 1.101.3.22.2
                fkBridgePSControl OBJECT IDENTIFIER ::= { fkBridgePortSecurity 2 }

                
                -- 1.3.6.1.4.1.10428 9 1.101.3.22.2.1
                fkBridgePSControlRequest OBJECT-TYPE
                        SYNTAX INTEGER
                                {
                                setPSStatus(1),
                                setPSMaxCount(2),
                                setPSProfile(3)
                                }
                        MAX-ACCESS read-write
                        STATUS current
                        DESCRIPTION
                                "The request of a user command"
                        ::= { fkBridgePSControl 1 }

                
                -- 1.3.6.1.4.1.10428 9 1.101.3.22.2.2
                fkBridgePSControlStatus OBJECT-TYPE
                        SYNTAX FkControlStatusType
                        MAX-ACCESS read-only
                        STATUS current
                        DESCRIPTION
                                "The status of user command"
                        ::= { fkBridgePSControl 2 }

                
                -- 1.3.6.1.4.1.10428 9 1.101.3.22.2.3
                fkBridgePSControlTimer OBJECT-TYPE
                        SYNTAX Gauge32
                        MAX-ACCESS read-write
                        STATUS current
                        DESCRIPTION
                                "The maximum time for the manager for a long running user command"
                        ::= { fkBridgePSControl 3 }

                
                -- 1.3.6.1.4.1.10428 9 1.101.3.22.2.4
                fkBridgePSControlTimeStamp OBJECT-TYPE
                        SYNTAX TimeTicks
                        MAX-ACCESS read-only
                        STATUS current
                        DESCRIPTION
                                "The time stamp of the last command(end of command)"
                        ::= { fkBridgePSControl 4 }

                
                -- 1.3.6.1.4.1.10428 9 1.101.3.22.2.5
                fkBridgePSControlReqResult OBJECT-TYPE
                        SYNTAX FkControlRequestResultType
                        MAX-ACCESS read-only
                        STATUS current
                        DESCRIPTION
                                "The result of the last user command"
                        ::= { fkBridgePSControl 5 }

                
                -- 1.3.6.1.4.1.10428 9 1.101.3.22.2.6
                fkBridgePSControlIndex OBJECT-TYPE
                        SYNTAX InterfaceIndex
                        MAX-ACCESS read-write
                        STATUS current
                        DESCRIPTION
                                "The index of logical port"
                        ::= { fkBridgePSControl 6 }

                
                -- 1.3.6.1.4.1.10428 9 1.101.3.22.2.7
                fkBridgePSControlPSStatus OBJECT-TYPE
                        SYNTAX INTEGER
                                {
                                enable(1),
                                disable(2)
                                }
                        MAX-ACCESS read-write
                        STATUS current
                        DESCRIPTION
                                "The status of port security"
                        ::= { fkBridgePSControl 7 }

                
                -- 1.3.6.1.4.1.10428 9 1.101.3.22.2.8
                fkBridgePSControlMaxCount OBJECT-TYPE
                        SYNTAX INTEGER (-1 | 1..16384)
                        MAX-ACCESS read-write
                        STATUS current
                        DESCRIPTION
                                "The max secure addresses
                                The value of -1 is not used
                                "
                        ::= { fkBridgePSControl 8 }

                
                -- 1.3.6.1.4.1.10428 9 1.101.3.22.2.9
                fkBridgePSControlAgingType OBJECT-TYPE
                        SYNTAX INTEGER
                                {
                                absolute(1),
                                inactivity(2)
                                }
                        MAX-ACCESS read-write
                        STATUS current
                        DESCRIPTION
                                "The aging type of port security"
                        ::= { fkBridgePSControl 9 }

                
                -- 1.3.6.1.4.1.10428 9 1.101.3.22.2.10
                fkBridgePSControlAgingTimer OBJECT-TYPE
                        SYNTAX INTEGER (-1 | 0 | 1..2147483647)
                        UNITS "second"
                        MAX-ACCESS read-write
                        STATUS current
                        DESCRIPTION
                                "The aging time of port security
                                The value -1 and 0 means that aging time fixed to static and it will be not aging out"
                        ::= { fkBridgePSControl 10 }

                
                -- 1.3.6.1.4.1.10428 9 1.101.3.22.2.11
                fkBridgePSControlAgingStatic OBJECT-TYPE
                        SYNTAX INTEGER
                                {
                                enable(1),
                                disable(2)
                                }
                        MAX-ACCESS read-write
                        STATUS current
                        DESCRIPTION
                                "The enable aging for configured secure addressess"
                        ::= { fkBridgePSControl 11 }

                
                -- 1.3.6.1.4.1.10428 9 1.101.3.22.2.12
                fkBridgePScontrolViolation OBJECT-TYPE
                        SYNTAX INTEGER
                                {
                                shutdown(1),
                                protect(2),
                                restrict(3)
                                }
                        MAX-ACCESS read-write
                        STATUS current
                        DESCRIPTION
                                "The security violation mode of port security "
                        ::= { fkBridgePSControl 12 }

                
                -- 1.3.6.1.4.1.10428 9 1.101.3.22.3
                fkBridgePSNotification OBJECT IDENTIFIER ::= { fkBridgePortSecurity 3 }

                
                -- 1.3.6.1.4.1.10428 9 1.101.3.22.3.1
                fkBridgePSStatusChanged NOTIFICATION-TYPE
                        OBJECTS { fkBridgePSControlRequest, fkBridgePSControlTimeStamp, fkBridgePSControlReqResult, fkBridgePSControlIndex, fkBridgePSControlPSStatus
                                 }
                        STATUS current
                        DESCRIPTION 
                                "Description."
                        ::= { fkBridgePSNotification 1 }

                
                -- 1.3.6.1.4.1.10428 9 1.101.3.22.3.2
                fkBridgePSMaxCountChanged NOTIFICATION-TYPE
                        OBJECTS { fkBridgePSControlRequest, fkBridgePSControlTimeStamp, fkBridgePSControlReqResult, fkBridgePSControlIndex, fkBridgePSControlMaxCount
                                 }
                        STATUS current
                        DESCRIPTION 
                                "Description."
                        ::= { fkBridgePSNotification 2 }

                
                -- 1.3.6.1.4.1.10428 9 1.101.3.22.3.3
                fkBridgePSProfileChanged NOTIFICATION-TYPE
                        OBJECTS { fkBridgePSControlRequest, fkBridgePSControlTimeStamp, fkBridgePSControlReqResult, fkBridgePSControlIndex, fkBridgePSControlAgingType, 
                                fkBridgePSControlAgingTimer, fkBridgePSControlAgingStatic, fkBridgePScontrolViolation }
                        STATUS current
                        DESCRIPTION 
                                "Description."
                        ::= { fkBridgePSNotification 3 }

                
                -- 1.3.6.1.4.1.10428 9 1.101.3.23
                fkBridgePortSecurityFdb OBJECT IDENTIFIER ::= { fkBridge 23 }

                
                -- 1.3.6.1.4.1.10428 9 1.101.3.23.1
                fkBridgePSFdbTable OBJECT-TYPE
                        SYNTAX SEQUENCE OF FkBridgePSFdbEntry
                        MAX-ACCESS not-accessible
                        STATUS current
                        DESCRIPTION
                                "bridge port security FDB table."
                        ::= { fkBridgePortSecurityFdb 1 }

                
                -- 1.3.6.1.4.1.10428 9 1.101.3.23.1.1
                fkBridgePSFdbEntry OBJECT-TYPE
                        SYNTAX FkBridgePSFdbEntry
                        MAX-ACCESS not-accessible
                        STATUS current
                        DESCRIPTION
                                "key: fkBridgePSFdbPort, fkBridgePSFdbVid, fkBridgePSFdbMacAddress"
                        INDEX { fkBridgePSFdbPort, fkBridgePSFdbVid, fkBridgePSFdbMacAddress }
                        ::= { fkBridgePSFdbTable 1 }

                
                FkBridgePSFdbEntry ::=
                        SEQUENCE { 
                                fkBridgePSFdbPort
                                        INTEGER,
                                fkBridgePSFdbVid
                                        INTEGER,
                                fkBridgePSFdbMacAddress
                                        OCTET STRING,
                                fkBridgePSFdbMode
                                        INTEGER,
                                fkBridgePSFdbElapsedTime
                                        Unsigned32
                         }

                -- 1.3.6.1.4.1.10428 9 1.101.3.23.1.1.1
                fkBridgePSFdbPort OBJECT-TYPE
                        SYNTAX INTEGER (1..512)
                        MAX-ACCESS read-only
                        STATUS current
                        DESCRIPTION
                                "FDB mode configuration.
                                1: dynamic
                                2: static
                                "
                        ::= { fkBridgePSFdbEntry 1 }

                
                -- 1.3.6.1.4.1.10428 9 1.101.3.23.1.1.2
                fkBridgePSFdbVid OBJECT-TYPE
                        SYNTAX INTEGER (1..4094)
                        MAX-ACCESS read-only
                        STATUS current
                        DESCRIPTION
                                "FDB vlan index"
                        ::= { fkBridgePSFdbEntry 2 }

                
                -- 1.3.6.1.4.1.10428 9 1.101.3.23.1.1.3
                fkBridgePSFdbMacAddress OBJECT-TYPE
                        SYNTAX OCTET STRING (SIZE (0..6))
                        MAX-ACCESS read-only
                        STATUS current
                        DESCRIPTION
                                "FDB MAC address"
                        ::= { fkBridgePSFdbEntry 3 }

                
                -- 1.3.6.1.4.1.10428 9 1.101.3.23.1.1.4
                fkBridgePSFdbMode OBJECT-TYPE
                        SYNTAX INTEGER
                                {
                                dynamic(1),
                                static(2)
                                }
                        MAX-ACCESS read-only
                        STATUS current
                        DESCRIPTION
                                "FDB mode configuration.
                                1: dynamic
                                2: static
                                "
                        ::= { fkBridgePSFdbEntry 4 }

                
                -- 1.3.6.1.4.1.10428 9 1.101.3.23.1.1.5
                fkBridgePSFdbElapsedTime OBJECT-TYPE
                        SYNTAX Unsigned32
                        MAX-ACCESS read-only
                        STATUS current
                        DESCRIPTION
                                "FDB elapsed time"
                        ::= { fkBridgePSFdbEntry 5 }

                
                -- 1.3.6.1.4.1.10428 9 1.101.3.23.2
                fkBridgePSFdbControl OBJECT IDENTIFIER ::= { fkBridgePortSecurityFdb 2 }

                
                -- 1.3.6.1.4.1.10428 9 1.101.3.23.2.1
                fkBridgePSFdbControlRequest OBJECT-TYPE
                        SYNTAX INTEGER
                                {
                                createPSFedEntry(1),
                                destroyPSFdbEntry(2),
                                clearPSFdbEntry(3)
                                }
                        MAX-ACCESS read-write
                        STATUS current
                        DESCRIPTION
                                "The request of a user command"
                        ::= { fkBridgePSFdbControl 1 }

                
                -- 1.3.6.1.4.1.10428 9 1.101.3.23.2.2
                fkBridgePSFdbControlStatus OBJECT-TYPE
                        SYNTAX FkControlStatusType
                        MAX-ACCESS read-only
                        STATUS current
                        DESCRIPTION
                                "The status of user command"
                        ::= { fkBridgePSFdbControl 2 }

                
                -- 1.3.6.1.4.1.10428 9 1.101.3.23.2.3
                fkBridgePSFdbControlTimer OBJECT-TYPE
                        SYNTAX Gauge32
                        MAX-ACCESS read-write
                        STATUS current
                        DESCRIPTION
                                "The maximum time for the manager for a long running user command"
                        ::= { fkBridgePSFdbControl 3 }

                
                -- 1.3.6.1.4.1.10428 9 1.101.3.23.2.4
                fkBridgePSFdbControlTimeStamp OBJECT-TYPE
                        SYNTAX TimeTicks
                        MAX-ACCESS read-only
                        STATUS current
                        DESCRIPTION
                                "The time stamp of the last command(end of command)"
                        ::= { fkBridgePSFdbControl 4 }

                
                -- 1.3.6.1.4.1.10428 9 1.101.3.23.2.5
                fkBridgePSFdbControlReqResult OBJECT-TYPE
                        SYNTAX FkControlRequestResultType
                        MAX-ACCESS read-only
                        STATUS current
                        DESCRIPTION
                                "The result of the last user command"
                        ::= { fkBridgePSFdbControl 5 }

                
                -- 1.3.6.1.4.1.10428 9 1.101.3.23.2.6
                fkBridgePSFdbControlPort OBJECT-TYPE
                        SYNTAX INTEGER (1..512)
                        MAX-ACCESS read-write
                        STATUS current
                        DESCRIPTION
                                "FDB port"
                        ::= { fkBridgePSFdbControl 6 }

                
                -- 1.3.6.1.4.1.10428 9 1.101.3.23.2.7
                fkBridgePSFdbControlVid OBJECT-TYPE
                        SYNTAX INTEGER (1..4094)
                        MAX-ACCESS read-write
                        STATUS current
                        DESCRIPTION
                                "FDB vlan index"
                        ::= { fkBridgePSFdbControl 7 }

                
                -- 1.3.6.1.4.1.10428 9 1.101.3.23.2.8
                fkBridgePSFdbControlMacAddress OBJECT-TYPE
                        SYNTAX OCTET STRING (SIZE (0..6))
                        MAX-ACCESS read-write
                        STATUS current
                        DESCRIPTION
                                "FDB MAC address"
                        ::= { fkBridgePSFdbControl 8 }

                
                -- 1.3.6.1.4.1.10428 9 1.101.3.23.3
                fkBridgePSFdbNotification OBJECT IDENTIFIER ::= { fkBridgePortSecurityFdb 3 }

                
                -- 1.3.6.1.4.1.10428 9 1.101.3.23.3.1
                fkBridgePSFdbEntryCreated NOTIFICATION-TYPE
                        OBJECTS { fkBridgePSFdbControlRequest, fkBridgePSFdbControlTimeStamp, fkBridgePSFdbControlReqResult, fkBridgePSFdbControlPort, fkBridgePSFdbControlVid, 
                                fkBridgePSFdbControlMacAddress }
                        STATUS current
                        DESCRIPTION 
                                "Description."
                        ::= { fkBridgePSFdbNotification 1 }

                
                -- 1.3.6.1.4.1.10428 9 1.101.3.23.3.2
                fkBridgePSFdbEntryDestroyed NOTIFICATION-TYPE
                        OBJECTS { fkBridgePSFdbControlRequest, fkBridgePSFdbControlTimeStamp, fkBridgePSFdbControlReqResult, fkBridgePSFdbControlPort, fkBridgePSFdbControlVid, 
                                fkBridgePSFdbControlMacAddress }
                        STATUS current
                        DESCRIPTION 
                                "Description."
                        ::= { fkBridgePSFdbNotification 2 }

                
                -- 1.3.6.1.4.1.10428 9 1.101.3.23.3.3
                fkBridgePSFdbEntryCleared NOTIFICATION-TYPE
                        OBJECTS { fkBridgePSFdbControlRequest, fkBridgePSFdbControlTimeStamp, fkBridgePSFdbControlReqResult, fkBridgePSFdbControlPort, fkBridgePSFdbControlVid, 
                                fkBridgePSFdbControlMacAddress }
                        STATUS current
                        DESCRIPTION 
                                "Description."
                        ::= { fkBridgePSFdbNotification 3 }

                
                -- 1.3.6.1.4.1.10428 9 1.101.3.24
                fkBridgeFloodGuard OBJECT IDENTIFIER ::= { fkBridge 24 }

                
                -- 1.3.6.1.4.1.10428 9 1.101.3.24.1
                fkBridgeFGBase OBJECT IDENTIFIER ::= { fkBridgeFloodGuard 1 }

                
                -- 1.3.6.1.4.1.10428 9 1.101.3.24.1.1
                fkBridgeFGBaseInfo OBJECT IDENTIFIER ::= { fkBridgeFGBase 1 }

                
                -- 1.3.6.1.4.1.10428 9 1.101.3.24.1.1.1
                fkBridgeFGBaseCfgdEnabled OBJECT-TYPE
                        SYNTAX INTEGER
                                {
                                enable(1),
                                disable(2)
                                }
                        MAX-ACCESS read-only
                        STATUS current
                        DESCRIPTION
                                "The CFG enabled
                                1: enable
                                2: disable
                                "
                        ::= { fkBridgeFGBaseInfo 1 }

                
                -- 1.3.6.1.4.1.10428 9 1.101.3.24.1.1.2
                fkBridgeFGBaseMfgdEnabled OBJECT-TYPE
                        SYNTAX INTEGER
                                {
                                enable(1),
                                disable(2)
                                }
                        MAX-ACCESS read-only
                        STATUS current
                        DESCRIPTION
                                "The MFG enabled
                                1: enable
                                2: disable"
                        ::= { fkBridgeFGBaseInfo 2 }

                
                -- 1.3.6.1.4.1.10428 9 1.101.3.24.1.1.3
                fkBridgeFGBaseSfgdEnabled OBJECT-TYPE
                        SYNTAX INTEGER
                                {
                                enable(1),
                                disable(2)
                                }
                        MAX-ACCESS read-only
                        STATUS current
                        DESCRIPTION
                                "The SFG enabled
                                1: enable
                                2: disable"
                        ::= { fkBridgeFGBaseInfo 3 }

                
                -- 1.3.6.1.4.1.10428 9 1.101.3.24.1.2
                fkBridgeFGBaseControl OBJECT IDENTIFIER ::= { fkBridgeFGBase 2 }

                
                -- 1.3.6.1.4.1.10428 9 1.101.3.24.1.2.1
                fkBridgeFGBaseControlRequest OBJECT-TYPE
                        SYNTAX INTEGER
                                {
                                setCfgdEnable(1),
                                setSfgdEnable(2)
                                }
                        MAX-ACCESS read-write
                        STATUS current
                        DESCRIPTION
                                "The request of a user command"
                        ::= { fkBridgeFGBaseControl 1 }

                
                -- 1.3.6.1.4.1.10428 9 1.101.3.24.1.2.2
                fkBridgeFGBaseControlStatus OBJECT-TYPE
                        SYNTAX FkControlStatusType
                        MAX-ACCESS read-only
                        STATUS current
                        DESCRIPTION
                                "The status of user command"
                        ::= { fkBridgeFGBaseControl 2 }

                
                -- 1.3.6.1.4.1.10428 9 1.101.3.24.1.2.3
                fkBridgeFGBaseControlTimer OBJECT-TYPE
                        SYNTAX Gauge32
                        MAX-ACCESS read-write
                        STATUS current
                        DESCRIPTION
                                "The maximum time for the manager for a long running user command"
                        ::= { fkBridgeFGBaseControl 3 }

                
                -- 1.3.6.1.4.1.10428 9 1.101.3.24.1.2.4
                fkBridgeFGBaseControlTimeStamp OBJECT-TYPE
                        SYNTAX TimeTicks
                        MAX-ACCESS read-only
                        STATUS current
                        DESCRIPTION
                                "The time stamp of the last command(end of command)"
                        ::= { fkBridgeFGBaseControl 4 }

                
                -- 1.3.6.1.4.1.10428 9 1.101.3.24.1.2.5
                fkBridgeFGBaseControlReqResult OBJECT-TYPE
                        SYNTAX FkControlRequestResultType
                        MAX-ACCESS read-only
                        STATUS current
                        DESCRIPTION
                                "The result of the last user command"
                        ::= { fkBridgeFGBaseControl 5 }

                
                -- 1.3.6.1.4.1.10428 9 1.101.3.24.1.2.6
                fkBridgeFGBaseControlCfgdEnable OBJECT-TYPE
                        SYNTAX INTEGER
                                {
                                enable(1),
                                disable(2)
                                }
                        MAX-ACCESS read-write
                        STATUS current
                        DESCRIPTION
                                "The CFG enabled
                                1: enable
                                2: disable"
                        ::= { fkBridgeFGBaseControl 6 }

                
                -- 1.3.6.1.4.1.10428 9 1.101.3.24.1.2.7
                fkBridgeFGBaseControlSfgdEnable OBJECT-TYPE
                        SYNTAX INTEGER
                                {
                                enable(1),
                                disable(2)
                                }
                        MAX-ACCESS read-write
                        STATUS current
                        DESCRIPTION
                                "The SFG enabled
                                1: enable
                                2: disable      "
                        ::= { fkBridgeFGBaseControl 7 }

                
                -- 1.3.6.1.4.1.10428 9 1.101.3.24.1.3
                fkBridgeFGBaseNotification OBJECT IDENTIFIER ::= { fkBridgeFGBase 3 }

                
                -- 1.3.6.1.4.1.10428 9 1.101.3.24.1.3.1
                fkBridgeFGBaseCfgdStatusChanged NOTIFICATION-TYPE
                        OBJECTS { fkBridgeFGBaseControlRequest, fkBridgeFGBaseControlTimeStamp, fkBridgeFGBaseControlReqResult, fkBridgeFGBaseControlCfgdEnable }
                        STATUS current
                        DESCRIPTION 
                                "Description."
                        ::= { fkBridgeFGBaseNotification 1 }

                
                -- 1.3.6.1.4.1.10428 9 1.101.3.24.1.3.2
                fkBridgeFGBaseSfgdStatusChanged NOTIFICATION-TYPE
                        OBJECTS { fkBridgeFGBaseControlRequest, fkBridgeFGBaseControlTimeStamp, fkBridgeFGBaseControlReqResult, fkBridgeFGBaseControlSfgdEnable }
                        STATUS current
                        DESCRIPTION 
                                "Description."
                        ::= { fkBridgeFGBaseNotification 2 }

                
                -- 1.3.6.1.4.1.10428 9 1.101.3.24.2
                fkBridgeFGPort OBJECT IDENTIFIER ::= { fkBridgeFloodGuard 2 }

                
                -- 1.3.6.1.4.1.10428 9 1.101.3.24.2.1
                fkBridgeFGPortTable OBJECT-TYPE
                        SYNTAX SEQUENCE OF FkBridgeFGPortEntry
                        MAX-ACCESS not-accessible
                        STATUS current
                        DESCRIPTION
                                "Description."
                        ::= { fkBridgeFGPort 1 }

                
                -- 1.3.6.1.4.1.10428 9 1.101.3.24.2.1.1
                fkBridgeFGPortEntry OBJECT-TYPE
                        SYNTAX FkBridgeFGPortEntry
                        MAX-ACCESS not-accessible
                        STATUS current
                        DESCRIPTION
                                "Description."
                        INDEX { fkBridgePortIndex, fkBridgeFGPortType }
                        ::= { fkBridgeFGPortTable 1 }

                
                FkBridgeFGPortEntry ::=
                        SEQUENCE { 
                                fkBridgeFGPortType
                                        INTEGER,
                                fkBridgeFGPortFrameType
                                        INTEGER,
                                fkBridgeFGPortFrame
                                        INTEGER,
                                fkBridgeFGPortBlocked
                                        INTEGER,
                                fkBridgeFGPortTimer
                                        INTEGER
                         }

                -- 1.3.6.1.4.1.10428 9 1.101.3.24.2.1.1.1
                fkBridgeFGPortType OBJECT-TYPE
                        SYNTAX INTEGER
                                {
                                systemFloodGuard(1),
                                cpuFloodGuard(2),
                                macFloodGuard(3)
                                }
                        MAX-ACCESS read-only
                        STATUS current
                        DESCRIPTION
                                "Flood guard port type
                                1 : systemFloodGuard
                                2 : cpuFloodGuard
                                3 : macFloodGuard"
                        ::= { fkBridgeFGPortEntry 1 }

                
                -- 1.3.6.1.4.1.10428 9 1.101.3.24.2.1.1.2
                fkBridgeFGPortFrameType OBJECT-TYPE
                        SYNTAX INTEGER
                                {
                                none(0),
                                multicast(1),
                                broadcast(2),
                                both(3)
                                }
                        MAX-ACCESS read-only
                        STATUS current
                        DESCRIPTION
                                "Flood guard frame type
                                0 : none
                                1 : multicast
                                2 : broadcast
                                3 : both"
                        ::= { fkBridgeFGPortEntry 2 }

                
                -- 1.3.6.1.4.1.10428 9 1.101.3.24.2.1.1.3
                fkBridgeFGPortFrame OBJECT-TYPE
                        SYNTAX INTEGER (-1 | 1..2147483647)
                        MAX-ACCESS read-only
                        STATUS current
                        DESCRIPTION
                                "Flood guard frame"
                        ::= { fkBridgeFGPortEntry 3 }

                
                -- 1.3.6.1.4.1.10428 9 1.101.3.24.2.1.1.4
                fkBridgeFGPortBlocked OBJECT-TYPE
                        SYNTAX INTEGER
                                {
                                block(1),
                                unblock(2)
                                }
                        MAX-ACCESS read-only
                        STATUS current
                        DESCRIPTION
                                "Flood guard block status
                                1 : block
                                2 : unblock"
                        ::= { fkBridgeFGPortEntry 4 }

                
                -- 1.3.6.1.4.1.10428 9 1.101.3.24.2.1.1.5
                fkBridgeFGPortTimer OBJECT-TYPE
                        SYNTAX INTEGER (-1 | 10..3600)
                        MAX-ACCESS read-only
                        STATUS current
                        DESCRIPTION
                                "Flood guard timer"
                        ::= { fkBridgeFGPortEntry 5 }

                
                -- 1.3.6.1.4.1.10428 9 1.101.3.24.2.2
                fkBridgeFGPortControl OBJECT IDENTIFIER ::= { fkBridgeFGPort 2 }

                
                -- 1.3.6.1.4.1.10428 9 1.101.3.24.2.2.1
                fkBridgeFGPortControlRequest OBJECT-TYPE
                        SYNTAX INTEGER
                                {
                                setFgPortProfile(1),
                                setFgPortUnblock(2)
                                }
                        MAX-ACCESS read-write
                        STATUS current
                        DESCRIPTION
                                "The request of a user command"
                        ::= { fkBridgeFGPortControl 1 }

                
                -- 1.3.6.1.4.1.10428 9 1.101.3.24.2.2.2
                fkBridgeFGPortControlStatus OBJECT-TYPE
                        SYNTAX FkControlStatusType
                        MAX-ACCESS read-only
                        STATUS current
                        DESCRIPTION
                                "The status of user command"
                        ::= { fkBridgeFGPortControl 2 }

                
                -- 1.3.6.1.4.1.10428 9 1.101.3.24.2.2.3
                fkBridgeFGPortControlTimer OBJECT-TYPE
                        SYNTAX Gauge32
                        MAX-ACCESS read-only
                        STATUS current
                        DESCRIPTION
                                "The maximum time for the manager for a long running user command"
                        ::= { fkBridgeFGPortControl 3 }

                
                -- 1.3.6.1.4.1.10428 9 1.101.3.24.2.2.4
                fkBridgeFGPortControlTimeStamp OBJECT-TYPE
                        SYNTAX TimeTicks
                        MAX-ACCESS read-only
                        STATUS current
                        DESCRIPTION
                                "The time stamp of the last command(end of command)"
                        ::= { fkBridgeFGPortControl 4 }

                
                -- 1.3.6.1.4.1.10428 9 1.101.3.24.2.2.5
                fkBridgeFGPortControlReqResult OBJECT-TYPE
                        SYNTAX FkControlRequestResultType
                        MAX-ACCESS read-only
                        STATUS current
                        DESCRIPTION
                                "The result of the last user command"
                        ::= { fkBridgeFGPortControl 5 }

                
                -- 1.3.6.1.4.1.10428 9 1.101.3.24.2.2.6
                fkBridgeFGPortControlIndex OBJECT-TYPE
                        SYNTAX Integer32
                        MAX-ACCESS read-write
                        STATUS current
                        DESCRIPTION
                                "Port index"
                        ::= { fkBridgeFGPortControl 6 }

                
                -- 1.3.6.1.4.1.10428 9 1.101.3.24.2.2.7
                fkBridgeFGPortControlType OBJECT-TYPE
                        SYNTAX INTEGER
                                {
                                systemfloodguard(1),
                                cpufloodguard(2),
                                macfloodguard(3)
                                }
                        MAX-ACCESS read-write
                        STATUS current
                        DESCRIPTION
                                "Flood guard port type
                                1 : systemFloodGuard
                                2 : cpuFloodGuard
                                3 : macFloodGuard"
                        ::= { fkBridgeFGPortControl 7 }

                
                -- 1.3.6.1.4.1.10428 9 1.101.3.24.2.2.8
                fkBridgeFGPortControlFrameType OBJECT-TYPE
                        SYNTAX INTEGER
                                {
                                none(0),
                                multicast(1),
                                broadcast(2),
                                both(3)
                                }
                        MAX-ACCESS read-write
                        STATUS current
                        DESCRIPTION
                                "Flood guard frame type
                                0 : none
                                1 : multicast
                                2 : broadcast
                                3 : both
                                "
                        ::= { fkBridgeFGPortControl 8 }

                
                -- 1.3.6.1.4.1.10428 9 1.101.3.24.2.2.9
                fkBridgeFGPortControlFrame OBJECT-TYPE
                        SYNTAX INTEGER (-1 | 1..2147483647)
                        MAX-ACCESS read-write
                        STATUS current
                        DESCRIPTION
                                "Flood guard frame"
                        ::= { fkBridgeFGPortControl 9 }

                
                -- 1.3.6.1.4.1.10428 9 1.101.3.24.2.2.10
                fkBridgeFGPortControlSetTimer OBJECT-TYPE
                        SYNTAX INTEGER (-1 | 10..3600)
                        MAX-ACCESS read-write
                        STATUS current
                        DESCRIPTION
                                "Flood guard timer"
                        ::= { fkBridgeFGPortControl 10 }

                
                -- 1.3.6.1.4.1.10428 9 1.101.3.24.2.2.11
                fkBridgeFGPortControlBlock OBJECT-TYPE
                        SYNTAX INTEGER
                                {
                                block(1),
                                unblock(2)
                                }
                        MAX-ACCESS read-write
                        STATUS current
                        DESCRIPTION
                                "Flood guard block status
                                1 : block
                                2 : unblock"
                        ::= { fkBridgeFGPortControl 11 }

                
                -- 1.3.6.1.4.1.10428 9 1.101.3.24.2.3
                fkBridgeFGPortNotification OBJECT IDENTIFIER ::= { fkBridgeFGPort 3 }

                
                -- 1.3.6.1.4.1.10428 9 1.101.3.24.2.3.1
                fkBridgeFGPortProfileChanged NOTIFICATION-TYPE
                        OBJECTS { fkBridgeFGPortControlReqResult, fkBridgeFGPortControlTimeStamp, fkBridgeFGPortControlRequest, fkBridgeFGPortControlIndex, fkBridgeFGPortControlType, 
                                fkBridgeFGPortControlFrameType, fkBridgeFGPortControlFrame, fkBridgeFGPortControlSetTimer, fkBridgeFGPortControlBlock }
                        STATUS current
                        DESCRIPTION 
                                "Description."
                        ::= { fkBridgeFGPortNotification 1 }

                
                -- 1.3.6.1.4.1.10428 9 1.101.3.24.2.3.2
                fkBridgeFGPortUnblockChanged NOTIFICATION-TYPE
                        OBJECTS { fkBridgeFGPortControlRequest, fkBridgeFGPortControlTimeStamp, fkBridgeFGPortControlReqResult, fkBridgeFGPortControlIndex, fkBridgeFGPortControlType
                                 }
                        STATUS current
                        DESCRIPTION 
                                "Description."
                        ::= { fkBridgeFGPortNotification 2 }

                
                -- 1.3.6.1.4.1.10428 9 1.101.3.25
                fkBridgeVlanTranslation OBJECT IDENTIFIER ::= { fkBridge 25 }

                
                -- 1.3.6.1.4.1.10428 9 1.101.3.25.1
                fkBridgeVTTable OBJECT-TYPE
                        SYNTAX SEQUENCE OF FkBridgeVTEntry
                        MAX-ACCESS not-accessible
                        STATUS current
                        DESCRIPTION
                                "bridge vlan translation table."
                        ::= { fkBridgeVlanTranslation 1 }

                
                -- 1.3.6.1.4.1.10428 9 1.101.3.25.1.1
                fkBridgeVTEntry OBJECT-TYPE
                        SYNTAX FkBridgeVTEntry
                        MAX-ACCESS not-accessible
                        STATUS current
                        DESCRIPTION
                                "key: fkBridgeVTServiceId, fkBridgeVTSubscriberId"
                        INDEX { fkBridgeVTServiceId, fkBridgeVTSubscriberId }
                        ::= { fkBridgeVTTable 1 }

                
                FkBridgeVTEntry ::=
                        SEQUENCE { 
                                fkBridgeVTServiceId
                                        INTEGER,
                                fkBridgeVTSubscriberId
                                        INTEGER
                         }

                -- 1.3.6.1.4.1.10428 9 1.101.3.25.1.1.1
                fkBridgeVTServiceId OBJECT-TYPE
                        SYNTAX INTEGER (1..4094)
                        MAX-ACCESS read-only
                        STATUS current
                        DESCRIPTION
                                "Service Vlan Id"
                        ::= { fkBridgeVTEntry 1 }

                
                -- 1.3.6.1.4.1.10428 9 1.101.3.25.1.1.2
                fkBridgeVTSubscriberId OBJECT-TYPE
                        SYNTAX INTEGER (1..4094)
                        MAX-ACCESS read-only
                        STATUS current
                        DESCRIPTION
                                "Subscriber Vlan Id"
                        ::= { fkBridgeVTEntry 2 }

                
                -- 1.3.6.1.4.1.10428 9 1.101.3.25.2
                fkBridgeVTRuleTable OBJECT-TYPE
                        SYNTAX SEQUENCE OF FkBridgeVTRuleEntry
                        MAX-ACCESS not-accessible
                        STATUS current
                        DESCRIPTION
                                "bridge vlan translation rule table."
                        ::= { fkBridgeVlanTranslation 2 }

                
                -- 1.3.6.1.4.1.10428 9 1.101.3.25.2.1
                fkBridgeVTRuleEntry OBJECT-TYPE
                        SYNTAX FkBridgeVTRuleEntry
                        MAX-ACCESS not-accessible
                        STATUS current
                        DESCRIPTION
                                "key: fkBridgeVTRuleMac, fkBridgeVTRuleVid"
                        INDEX { fkBridgeVTRuleMac, fkBridgeVTRuleVid }
                        ::= { fkBridgeVTRuleTable 1 }

                
                FkBridgeVTRuleEntry ::=
                        SEQUENCE { 
                                fkBridgeVTRuleMac
                                        MacAddress,
                                fkBridgeVTRuleVid
                                        INTEGER,
                                fkBridgeVTRuleRDirVid
                                        INTEGER,
                                fkBridgeVTRuleRDirPort
                                        Integer32,
                                fkBridgeVTRuleStatus
                                        INTEGER
                         }

                -- 1.3.6.1.4.1.10428 9 1.101.3.25.2.1.1
                fkBridgeVTRuleMac OBJECT-TYPE
                        SYNTAX MacAddress
                        MAX-ACCESS read-only
                        STATUS current
                        DESCRIPTION
                                "fkBridgeVTRuleMac, fkBridgeVTRuleVid"
                        ::= { fkBridgeVTRuleEntry 1 }

                
                -- 1.3.6.1.4.1.10428 9 1.101.3.25.2.1.2
                fkBridgeVTRuleVid OBJECT-TYPE
                        SYNTAX INTEGER (1..4094)
                        MAX-ACCESS read-only
                        STATUS current
                        DESCRIPTION
                                "Original packet Vid"
                        ::= { fkBridgeVTRuleEntry 2 }

                
                -- 1.3.6.1.4.1.10428 9 1.101.3.25.2.1.3
                fkBridgeVTRuleRDirVid OBJECT-TYPE
                        SYNTAX INTEGER (1..4094)
                        MAX-ACCESS read-only
                        STATUS current
                        DESCRIPTION
                                "Output port"
                        ::= { fkBridgeVTRuleEntry 3 }

                
                -- 1.3.6.1.4.1.10428 9 1.101.3.25.2.1.4
                fkBridgeVTRuleRDirPort OBJECT-TYPE
                        SYNTAX Integer32
                        MAX-ACCESS read-only
                        STATUS current
                        DESCRIPTION
                                "Output Vid"
                        ::= { fkBridgeVTRuleEntry 4 }

                
                -- 1.3.6.1.4.1.10428 9 1.101.3.25.2.1.5
                fkBridgeVTRuleStatus OBJECT-TYPE
                        SYNTAX INTEGER
                                {
                                static(1),
                                dynamic(2)
                                }
                        MAX-ACCESS read-only
                        STATUS current
                        DESCRIPTION
                                "Vlan Translation rule status"
                        ::= { fkBridgeVTRuleEntry 5 }

                
                -- 1.3.6.1.4.1.10428 9 1.101.3.25.3
                fkBridgeVTControl OBJECT IDENTIFIER ::= { fkBridgeVlanTranslation 3 }

                
                -- 1.3.6.1.4.1.10428 9 1.101.3.25.3.1
                fkBridgeVTControlRequest OBJECT-TYPE
                        SYNTAX INTEGER
                                {
                                setVT(1),
                                clearVT(2)
                                }
                        MAX-ACCESS read-write
                        STATUS current
                        DESCRIPTION
                                "The request of a user command."
                        ::= { fkBridgeVTControl 1 }

                
                -- 1.3.6.1.4.1.10428 9 1.101.3.25.3.2
                fkBridgeVTControlStatus OBJECT-TYPE
                        SYNTAX FkControlStatusType
                        MAX-ACCESS read-only
                        STATUS current
                        DESCRIPTION
                                "The status of a user command."
                        ::= { fkBridgeVTControl 2 }

                
                -- 1.3.6.1.4.1.10428 9 1.101.3.25.3.3
                fkBridgeVTControlTimer OBJECT-TYPE
                        SYNTAX Gauge32
                        MAX-ACCESS read-write
                        STATUS current
                        DESCRIPTION
                                "The maximum wait time for the manager for a long running user command."
                        ::= { fkBridgeVTControl 3 }

                
                -- 1.3.6.1.4.1.10428 9 1.101.3.25.3.4
                fkBridgeVTControlTimeStamp OBJECT-TYPE
                        SYNTAX TimeTicks
                        MAX-ACCESS read-only
                        STATUS current
                        DESCRIPTION
                                "The time stamp of the last command (end of command)."
                        ::= { fkBridgeVTControl 4 }

                
                -- 1.3.6.1.4.1.10428 9 1.101.3.25.3.5
                fkBridgeVTControlReqResult OBJECT-TYPE
                        SYNTAX FkControlRequestResultType
                        MAX-ACCESS read-only
                        STATUS current
                        DESCRIPTION
                                "The result of the last user command."
                        ::= { fkBridgeVTControl 5 }

                
                -- 1.3.6.1.4.1.10428 9 1.101.3.25.3.6
                fkBridgeVTControlServerId OBJECT-TYPE
                        SYNTAX INTEGER (1..4094)
                        MAX-ACCESS read-write
                        STATUS current
                        DESCRIPTION
                                "Network Interface Index."
                        ::= { fkBridgeVTControl 6 }

                
                -- 1.3.6.1.4.1.10428 9 1.101.3.25.3.7
                fkBridgeVTControlClientId OBJECT-TYPE
                        SYNTAX INTEGER (1..4094)
                        MAX-ACCESS read-write
                        STATUS current
                        DESCRIPTION
                                "Network Interface Index."
                        ::= { fkBridgeVTControl 7 }

                
                -- 1.3.6.1.4.1.10428 9 1.101.3.25.4
                fkBridgeVTNotification OBJECT IDENTIFIER ::= { fkBridgeVlanTranslation 4 }

                
                -- 1.3.6.1.4.1.10428 9 1.101.3.25.4.1
                fkBridgeVTSet NOTIFICATION-TYPE
                        OBJECTS { fkBridgeVTControlRequest, fkBridgeVTControlTimeStamp, fkBridgeVTControlServerId, fkBridgeVTControlClientId, fkBridgeVTControlReqResult
                                 }
                        STATUS current
                        DESCRIPTION 
                                "Description."
                        ::= { fkBridgeVTNotification 1 }

                
                -- 1.3.6.1.4.1.10428 9 1.101.3.25.4.2
                fkBridgeVTClear NOTIFICATION-TYPE
                        OBJECTS { fkBridgeVTControlRequest, fkBridgeVTControlTimeStamp, fkBridgeVTControlServerId, fkBridgeVTControlClientId, fkBridgeVTControlReqResult
                                 }
                        STATUS current
                        DESCRIPTION 
                                "Description."
                        ::= { fkBridgeVTNotification 2 }

                
                -- 1.3.6.1.4.1.10428 9 1.101.3.25.5
                fkBridgeInBoundVTTable OBJECT-TYPE
                        SYNTAX SEQUENCE OF FkBridgeInBoundVTEntry
                        MAX-ACCESS not-accessible
                        STATUS current
                        DESCRIPTION
                                "bridge inbound vlan translation table."
                        ::= { fkBridgeVlanTranslation 5 }

                
                -- 1.3.6.1.4.1.10428 9 1.101.3.25.5.1
                fkBridgeInBoundVTEntry OBJECT-TYPE
                        SYNTAX FkBridgeInBoundVTEntry
                        MAX-ACCESS not-accessible
                        STATUS current
                        DESCRIPTION
                                "key: fkBridgeInBoundVTPortIndex, fkBridgeInBoundVTVlanIndex"
                        INDEX { fkBridgeInBoundVTPortIndex, fkBridgeInBoundVTVlanIndex }
                        ::= { fkBridgeInBoundVTTable 1 }

                
                FkBridgeInBoundVTEntry ::=
                        SEQUENCE { 
                                fkBridgeInBoundVTPortIndex
                                        INTEGER,
                                fkBridgeInBoundVTVlanIndex
                                        Integer32,
                                fkBridgeInBoundVTNewVid
                                        Integer32,
                                fkBridgeInBoundVTOperStatus
                                        INTEGER
                         }

                -- 1.3.6.1.4.1.10428 9 1.101.3.25.5.1.1
                fkBridgeInBoundVTPortIndex OBJECT-TYPE
                        SYNTAX INTEGER (0..512)
                        MAX-ACCESS read-only
                        STATUS current
                        DESCRIPTION
                                "Port Index."
                        ::= { fkBridgeInBoundVTEntry 1 }

                
                -- 1.3.6.1.4.1.10428 9 1.101.3.25.5.1.2
                fkBridgeInBoundVTVlanIndex OBJECT-TYPE
                        SYNTAX Integer32 (0..65535)
                        MAX-ACCESS read-only
                        STATUS current
                        DESCRIPTION
                                "Vlan Index."
                        ::= { fkBridgeInBoundVTEntry 2 }

                
                -- 1.3.6.1.4.1.10428 9 1.101.3.25.5.1.3
                fkBridgeInBoundVTNewVid OBJECT-TYPE
                        SYNTAX Integer32
                        MAX-ACCESS read-only
                        STATUS current
                        DESCRIPTION
                                "New VID."
                        ::= { fkBridgeInBoundVTEntry 3 }

                
                -- 1.3.6.1.4.1.10428 9 1.101.3.25.5.1.4
                fkBridgeInBoundVTOperStatus OBJECT-TYPE
                        SYNTAX INTEGER
                                {
                                on(1),
                                off(2)
                                }
                        MAX-ACCESS read-only
                        STATUS current
                        DESCRIPTION
                                "The operational status of InBound Vlan Translation."
                        ::= { fkBridgeInBoundVTEntry 4 }

                
                -- 1.3.6.1.4.1.10428 9 1.101.3.25.6
                fkBridgeInBoundVTControl OBJECT IDENTIFIER ::= { fkBridgeVlanTranslation 6 }

                
                -- 1.3.6.1.4.1.10428 9 1.101.3.25.6.1
                fkBridgeInBoundVTControlRequest OBJECT-TYPE
                        SYNTAX INTEGER
                                {
                                setInBoundVT(1),
                                clearInBoundVT(2)
                                }
                        MAX-ACCESS read-write
                        STATUS current
                        DESCRIPTION
                                "The request of a user command."
                        ::= { fkBridgeInBoundVTControl 1 }

                
                -- 1.3.6.1.4.1.10428 9 1.101.3.25.6.2
                fkBridgeInBoundVTControlStatus OBJECT-TYPE
                        SYNTAX FkControlStatusType
                        MAX-ACCESS read-only
                        STATUS current
                        DESCRIPTION
                                "The status of a user command."
                        ::= { fkBridgeInBoundVTControl 2 }

                
                -- 1.3.6.1.4.1.10428 9 1.101.3.25.6.3
                fkBridgeInBoundVTControlTimer OBJECT-TYPE
                        SYNTAX Gauge32
                        MAX-ACCESS read-write
                        STATUS current
                        DESCRIPTION
                                "The maximum wait time for the manager for a long running user command."
                        ::= { fkBridgeInBoundVTControl 3 }

                
                -- 1.3.6.1.4.1.10428 9 1.101.3.25.6.4
                fkBridgeInBoundVTControlTimeStamp OBJECT-TYPE
                        SYNTAX TimeTicks
                        MAX-ACCESS read-only
                        STATUS current
                        DESCRIPTION
                                "The time stamp of the last command (end of command)."
                        ::= { fkBridgeInBoundVTControl 4 }

                
                -- 1.3.6.1.4.1.10428 9 1.101.3.25.6.5
                fkBridgeInBoundVTControlReqResult OBJECT-TYPE
                        SYNTAX FkControlRequestResultType
                        MAX-ACCESS read-only
                        STATUS current
                        DESCRIPTION
                                "The result of the last user command."
                        ::= { fkBridgeInBoundVTControl 5 }

                
                -- 1.3.6.1.4.1.10428 9 1.101.3.25.6.6
                fkBridgeInBoundVTControlPortIndex OBJECT-TYPE
                        SYNTAX Integer32
                        MAX-ACCESS read-write
                        STATUS current
                        DESCRIPTION
                                "Port Index."
                        ::= { fkBridgeInBoundVTControl 6 }

                
                -- 1.3.6.1.4.1.10428 9 1.101.3.25.6.7
                fkBridgeInBoundVTControlVlanIndex OBJECT-TYPE
                        SYNTAX Integer32
                        MAX-ACCESS read-write
                        STATUS current
                        DESCRIPTION
                                "Vlan Index."
                        ::= { fkBridgeInBoundVTControl 7 }

                
                -- 1.3.6.1.4.1.10428 9 1.101.3.25.6.8
                fkBridgeInBoundVTControlNewVid OBJECT-TYPE
                        SYNTAX Integer32
                        MAX-ACCESS read-write
                        STATUS current
                        DESCRIPTION
                                "New VID."
                        ::= { fkBridgeInBoundVTControl 8 }

                
                -- 1.3.6.1.4.1.10428 9 1.101.3.25.7
                fkBridgeInBoundVTNotification OBJECT IDENTIFIER ::= { fkBridgeVlanTranslation 7 }

                
                -- 1.3.6.1.4.1.10428 9 1.101.3.25.7.1
                fkBridgeInBoundVTSet NOTIFICATION-TYPE
                        OBJECTS { fkBridgeInBoundVTControlRequest, fkBridgeInBoundVTControlTimeStamp, fkBridgeInBoundVTControlReqResult, fkBridgeInBoundVTControlPortIndex, fkBridgeInBoundVTControlVlanIndex, 
                                fkBridgeInBoundVTControlNewVid }
                        STATUS current
                        DESCRIPTION 
                                "Description."
                        ::= { fkBridgeInBoundVTNotification 1 }

                
                -- 1.3.6.1.4.1.10428 9 1.101.3.25.7.2
                fkBridgeInBoundVTClear NOTIFICATION-TYPE
                        OBJECTS { fkBridgeInBoundVTControlRequest, fkBridgeInBoundVTControlTimeStamp, fkBridgeInBoundVTControlReqResult, fkBridgeInBoundVTControlPortIndex, fkBridgeInBoundVTControlVlanIndex
                                 }
                        STATUS current
                        DESCRIPTION 
                                "Description."
                        ::= { fkBridgeInBoundVTNotification 2 }

                
                -- 1.3.6.1.4.1.10428 9 1.101.3.25.8
                fkBridgeOutBoundVTTable OBJECT-TYPE
                        SYNTAX SEQUENCE OF FkBridgeOutBoundVTEntry
                        MAX-ACCESS not-accessible
                        STATUS current
                        DESCRIPTION
                                "bridge outbound vlan translation table."
                        ::= { fkBridgeVlanTranslation 8 }

                
                -- 1.3.6.1.4.1.10428 9 1.101.3.25.8.1
                fkBridgeOutBoundVTEntry OBJECT-TYPE
                        SYNTAX FkBridgeOutBoundVTEntry
                        MAX-ACCESS not-accessible
                        STATUS current
                        DESCRIPTION
                                "key: fkBridgeOutBoundVTPortIndex, fkBridgeOutBoundVTVlanIndex"
                        INDEX { fkBridgeOutBoundVTPortIndex, fkBridgeOutBoundVTVlanIndex }
                        ::= { fkBridgeOutBoundVTTable 1 }

                
                FkBridgeOutBoundVTEntry ::=
                        SEQUENCE { 
                                fkBridgeOutBoundVTPortIndex
                                        INTEGER,
                                fkBridgeOutBoundVTVlanIndex
                                        Integer32,
                                fkBridgeOutBoundVTNewVid
                                        Integer32,
                                fkBridgeOutBoundVTOperStatus
                                        INTEGER
                         }

                -- 1.3.6.1.4.1.10428 9 1.101.3.25.8.1.1
                fkBridgeOutBoundVTPortIndex OBJECT-TYPE
                        SYNTAX INTEGER (0..512)
                        MAX-ACCESS read-only
                        STATUS current
                        DESCRIPTION
                                "Port Index."
                        ::= { fkBridgeOutBoundVTEntry 1 }

                
                -- 1.3.6.1.4.1.10428 9 1.101.3.25.8.1.2
                fkBridgeOutBoundVTVlanIndex OBJECT-TYPE
                        SYNTAX Integer32 (0..65535)
                        MAX-ACCESS read-only
                        STATUS current
                        DESCRIPTION
                                "Vlan Index."
                        ::= { fkBridgeOutBoundVTEntry 2 }

                
                -- 1.3.6.1.4.1.10428 9 1.101.3.25.8.1.3
                fkBridgeOutBoundVTNewVid OBJECT-TYPE
                        SYNTAX Integer32
                        MAX-ACCESS read-only
                        STATUS current
                        DESCRIPTION
                                "New VID."
                        ::= { fkBridgeOutBoundVTEntry 3 }

                
                -- 1.3.6.1.4.1.10428 9 1.101.3.25.8.1.4
                fkBridgeOutBoundVTOperStatus OBJECT-TYPE
                        SYNTAX INTEGER
                                {
                                on(1),
                                off(2)
                                }
                        MAX-ACCESS read-only
                        STATUS current
                        DESCRIPTION
                                "The operational status of InBound Vlan Translation."
                        ::= { fkBridgeOutBoundVTEntry 4 }

                
                -- 1.3.6.1.4.1.10428 9 1.101.3.25.9
                fkBridgeOutBoundVTControl OBJECT IDENTIFIER ::= { fkBridgeVlanTranslation 9 }

                
                -- 1.3.6.1.4.1.10428 9 1.101.3.25.9.1
                fkBridgeOutBoundVTControlRequest OBJECT-TYPE
                        SYNTAX INTEGER
                                {
                                setOutBoundVT(1),
                                clearOutBoundVT(2)
                                }
                        MAX-ACCESS read-write
                        STATUS current
                        DESCRIPTION
                                "The request of a user command."
                        ::= { fkBridgeOutBoundVTControl 1 }

                
                -- 1.3.6.1.4.1.10428 9 1.101.3.25.9.2
                fkBridgeOutBoundVTControlStatus OBJECT-TYPE
                        SYNTAX FkControlStatusType
                        MAX-ACCESS read-only
                        STATUS current
                        DESCRIPTION
                                "The status of a user command."
                        ::= { fkBridgeOutBoundVTControl 2 }

                
                -- 1.3.6.1.4.1.10428 9 1.101.3.25.9.3
                fkBridgeOutBoundVTControlTimer OBJECT-TYPE
                        SYNTAX Gauge32
                        MAX-ACCESS read-write
                        STATUS current
                        DESCRIPTION
                                "The maximum wait time for the manager for a long running user command."
                        ::= { fkBridgeOutBoundVTControl 3 }

                
                -- 1.3.6.1.4.1.10428 9 1.101.3.25.9.4
                fkBridgeOutBoundVTControlTimeStamp OBJECT-TYPE
                        SYNTAX TimeTicks
                        MAX-ACCESS read-only
                        STATUS current
                        DESCRIPTION
                                "The time stamp of the last command (end of command)."
                        ::= { fkBridgeOutBoundVTControl 4 }

                
                -- 1.3.6.1.4.1.10428 9 1.101.3.25.9.5
                fkBridgeOutBoundVTControlReqResult OBJECT-TYPE
                        SYNTAX FkControlRequestResultType
                        MAX-ACCESS read-only
                        STATUS current
                        DESCRIPTION
                                "The result of the last user command."
                        ::= { fkBridgeOutBoundVTControl 5 }

                
                -- 1.3.6.1.4.1.10428 9 1.101.3.25.9.6
                fkBridgeOutBoundVTControlPortIndex OBJECT-TYPE
                        SYNTAX Integer32
                        MAX-ACCESS read-write
                        STATUS current
                        DESCRIPTION
                                "Port Index."
                        ::= { fkBridgeOutBoundVTControl 6 }

                
                -- 1.3.6.1.4.1.10428 9 1.101.3.25.9.7
                fkBridgeOutBoundVTControlVlanIndex OBJECT-TYPE
                        SYNTAX Integer32
                        MAX-ACCESS read-write
                        STATUS current
                        DESCRIPTION
                                "Vlan Index."
                        ::= { fkBridgeOutBoundVTControl 7 }

                
                -- 1.3.6.1.4.1.10428 9 1.101.3.25.9.8
                fkBridgeOutBoundVTControlNewVid OBJECT-TYPE
                        SYNTAX Integer32
                        MAX-ACCESS read-write
                        STATUS current
                        DESCRIPTION
                                "New VID."
                        ::= { fkBridgeOutBoundVTControl 8 }

                
                -- 1.3.6.1.4.1.10428 9 1.101.3.25.10
                fkBridgeOutBoundVTNotification OBJECT IDENTIFIER ::= { fkBridgeVlanTranslation 10 }

                
                -- 1.3.6.1.4.1.10428 9 1.101.3.25.10.1
                fkBridgeOutBoundVTSet NOTIFICATION-TYPE
                        OBJECTS { fkBridgeOutBoundVTControlRequest, fkBridgeOutBoundVTControlTimeStamp, fkBridgeOutBoundVTControlReqResult, fkBridgeOutBoundVTControlPortIndex, fkBridgeOutBoundVTControlVlanIndex, 
                                fkBridgeOutBoundVTControlNewVid }
                        STATUS current
                        DESCRIPTION 
                                "Description."
                        ::= { fkBridgeOutBoundVTNotification 1 }

                
                -- 1.3.6.1.4.1.10428 9 1.101.3.25.10.2
                fkBridgeOutBoundVTClear NOTIFICATION-TYPE
                        OBJECTS { fkBridgeOutBoundVTControlRequest, fkBridgeOutBoundVTControlTimeStamp, fkBridgeOutBoundVTControlReqResult, fkBridgeOutBoundVTControlPortIndex, fkBridgeOutBoundVTControlVlanIndex
                                 }
                        STATUS current
                        DESCRIPTION 
                                "Description."
                        ::= { fkBridgeOutBoundVTNotification 2 }

                
                -- 1.3.6.1.4.1.10428 9 1.101.3.26
                fkBridgeGarp OBJECT IDENTIFIER ::= { fkBridge 26 }

                
                -- 1.3.6.1.4.1.10428 9 1.101.3.26.1
                fkBridgeGarpBase OBJECT IDENTIFIER ::= { fkBridgeGarp 1 }

                
                -- 1.3.6.1.4.1.10428 9 1.101.3.26.1.1
                fkBridgeGarpBaseInfo OBJECT IDENTIFIER ::= { fkBridgeGarpBase 1 }

                
                -- 1.3.6.1.4.1.10428 9 1.101.3.26.1.1.1
                fkBridgeGvrpStatus OBJECT-TYPE
                        SYNTAX INTEGER
                                {
                                enable(1),
                                disable(2)
                                }
                        MAX-ACCESS read-only
                        STATUS current
                        DESCRIPTION
                                "Global GVRP status"
                        ::= { fkBridgeGarpBaseInfo 1 }

                
                -- 1.3.6.1.4.1.10428 9 1.101.3.26.1.1.2
                fkBridgeGmrpStatus OBJECT-TYPE
                        SYNTAX INTEGER
                                {
                                enable(1),
                                disable(2)
                                }
                        MAX-ACCESS read-only
                        STATUS current
                        DESCRIPTION
                                "Global GMRP status"
                        ::= { fkBridgeGarpBaseInfo 2 }

                
                -- 1.3.6.1.4.1.10428 9 1.101.3.26.1.1.3
                fkBridgeGarpTimerJoin OBJECT-TYPE
                        SYNTAX Integer32
                        MAX-ACCESS read-only
                        STATUS current
                        DESCRIPTION
                                "Global Join Timer"
                        ::= { fkBridgeGarpBaseInfo 3 }

                
                -- 1.3.6.1.4.1.10428 9 1.101.3.26.1.1.4
                fkBridgeGarpTimerLeave OBJECT-TYPE
                        SYNTAX Integer32
                        MAX-ACCESS read-only
                        STATUS current
                        DESCRIPTION
                                "Global Leave Timer"
                        ::= { fkBridgeGarpBaseInfo 4 }

                
                -- 1.3.6.1.4.1.10428 9 1.101.3.26.1.1.5
                fkBridgeGarpTimerLeaveAll OBJECT-TYPE
                        SYNTAX Integer32
                        MAX-ACCESS read-only
                        STATUS current
                        DESCRIPTION
                                "Global LeaveAll Timer"
                        ::= { fkBridgeGarpBaseInfo 5 }

                
                -- 1.3.6.1.4.1.10428 9 1.101.3.26.1.2
                fkBridgeGarpBaseControl OBJECT IDENTIFIER ::= { fkBridgeGarpBase 2 }

                
                -- 1.3.6.1.4.1.10428 9 1.101.3.26.1.2.1
                fkBridgeGarpBaseControlRequest OBJECT-TYPE
                        SYNTAX INTEGER
                                {
                                setGarpStatus(1),
                                setGarpTimer(2)
                                }
                        MAX-ACCESS read-write
                        STATUS current
                        DESCRIPTION
                                "The request of a user command"
                        ::= { fkBridgeGarpBaseControl 1 }

                
                -- 1.3.6.1.4.1.10428 9 1.101.3.26.1.2.2
                fkBridgeGarpBaseControlStatus OBJECT-TYPE
                        SYNTAX FkControlStatusType
                        MAX-ACCESS read-only
                        STATUS current
                        DESCRIPTION
                                "The status of user command"
                        ::= { fkBridgeGarpBaseControl 2 }

                
                -- 1.3.6.1.4.1.10428 9 1.101.3.26.1.2.3
                fkBridgeGarpBaseControlTimer OBJECT-TYPE
                        SYNTAX Gauge32
                        MAX-ACCESS read-write
                        STATUS current
                        DESCRIPTION
                                "The maximum time for the manager for a long running user command"
                        ::= { fkBridgeGarpBaseControl 3 }

                
                -- 1.3.6.1.4.1.10428 9 1.101.3.26.1.2.4
                fkBridgeGarpBaseControlTimeStamp OBJECT-TYPE
                        SYNTAX TimeTicks
                        MAX-ACCESS read-only
                        STATUS current
                        DESCRIPTION
                                "The time stamp of the last command(end of command)"
                        ::= { fkBridgeGarpBaseControl 4 }

                
                -- 1.3.6.1.4.1.10428 9 1.101.3.26.1.2.5
                fkBridgeGarpBaseControlReqResult OBJECT-TYPE
                        SYNTAX FkControlRequestResultType
                        MAX-ACCESS read-only
                        STATUS current
                        DESCRIPTION
                                "The result of the last user command"
                        ::= { fkBridgeGarpBaseControl 5 }

                
                -- 1.3.6.1.4.1.10428 9 1.101.3.26.1.2.6
                fkBridgeGarpBaseControlGvrpStatus OBJECT-TYPE
                        SYNTAX INTEGER
                                {
                                enable(1),
                                disable(2)
                                }
                        MAX-ACCESS read-write
                        STATUS current
                        DESCRIPTION
                                "Global GVRP status"
                        ::= { fkBridgeGarpBaseControl 6 }

                
                -- 1.3.6.1.4.1.10428 9 1.101.3.26.1.2.7
                fkBridgeGarpBaseControlGmrpStatus OBJECT-TYPE
                        SYNTAX INTEGER
                                {
                                enable(1),
                                disable(2)
                                }
                        MAX-ACCESS read-write
                        STATUS current
                        DESCRIPTION
                                "Global GMRP status"
                        ::= { fkBridgeGarpBaseControl 7 }

                
                -- 1.3.6.1.4.1.10428 9 1.101.3.26.1.2.8
                fkBridgeGarpBaseControlTimerJoin OBJECT-TYPE
                        SYNTAX Integer32
                        MAX-ACCESS read-write
                        STATUS current
                        DESCRIPTION
                                "Global Join Timer"
                        ::= { fkBridgeGarpBaseControl 8 }

                
                -- 1.3.6.1.4.1.10428 9 1.101.3.26.1.2.9
                fkBridgeGarpBaseControlTimerLeave OBJECT-TYPE
                        SYNTAX Integer32
                        MAX-ACCESS read-write
                        STATUS current
                        DESCRIPTION
                                "Global Leave Timer"
                        ::= { fkBridgeGarpBaseControl 9 }

                
                -- 1.3.6.1.4.1.10428 9 1.101.3.26.1.2.10
                fkBridgeGarpBaseControlTimerLeaveAll OBJECT-TYPE
                        SYNTAX Integer32
                        MAX-ACCESS read-write
                        STATUS current
                        DESCRIPTION
                                "Global LeaveAll Timer"
                        ::= { fkBridgeGarpBaseControl 10 }

                
                -- 1.3.6.1.4.1.10428 9 1.101.3.26.1.3
                fkBridgeGarpBaseNotification OBJECT IDENTIFIER ::= { fkBridgeGarpBase 3 }

                
                -- 1.3.6.1.4.1.10428 9 1.101.3.26.1.3.1
                fkBridgeGarpStatusChanged NOTIFICATION-TYPE
                        OBJECTS { fkBridgeGarpBaseControlRequest, fkBridgeGarpBaseControlTimeStamp, fkBridgeGarpBaseControlReqResult, fkBridgeGarpBaseControlGvrpStatus, fkBridgeGarpBaseControlGmrpStatus
                                 }
                        STATUS current
                        DESCRIPTION 
                                "Description."
                        ::= { fkBridgeGarpBaseNotification 1 }

                
                -- 1.3.6.1.4.1.10428 9 1.101.3.26.1.3.2
                fkBridgeGarpTimerChanged NOTIFICATION-TYPE
                        OBJECTS { fkBridgeGarpBaseControlRequest, fkBridgeGarpBaseControlTimeStamp, fkBridgeGarpBaseControlReqResult, fkBridgeGarpBaseControlTimerJoin, fkBridgeGarpBaseControlTimerLeave, 
                                fkBridgeGarpBaseControlTimerLeaveAll }
                        STATUS current
                        DESCRIPTION 
                                "Description."
                        ::= { fkBridgeGarpBaseNotification 2 }

                
                -- 1.3.6.1.4.1.10428 9 1.101.3.26.2
                fkBridgeGarpApplication OBJECT IDENTIFIER ::= { fkBridgeGarp 2 }

                
                -- 1.3.6.1.4.1.10428 9 1.101.3.26.2.1
                fkBridgeGarpAppPortTable OBJECT-TYPE
                        SYNTAX SEQUENCE OF FkBridgeGarpAppPortEntry
                        MAX-ACCESS not-accessible
                        STATUS current
                        DESCRIPTION
                                "bridge GARP application port table."
                        ::= { fkBridgeGarpApplication 1 }

                
                -- 1.3.6.1.4.1.10428 9 1.101.3.26.2.1.1
                fkBridgeGarpAppPortEntry OBJECT-TYPE
                        SYNTAX FkBridgeGarpAppPortEntry
                        MAX-ACCESS not-accessible
                        STATUS current
                        DESCRIPTION
                                "key: fkBridgeGarpAppPortIndex, fkBridgeGarpAppPortType"
                        INDEX { fkBridgeGarpAppPortIndex, fkBridgeGarpAppPortType }
                        ::= { fkBridgeGarpAppPortTable 1 }

                
                FkBridgeGarpAppPortEntry ::=
                        SEQUENCE { 
                                fkBridgeGarpAppPortIndex
                                        INTEGER,
                                fkBridgeGarpAppPortType
                                        INTEGER,
                                fkBridgeGarpAppPortStatus
                                        INTEGER,
                                fkBridgeGarpAppPortFailedRegistrations
                                        Integer32,
                                fkBridgeGarpAppPortLastPduOrigin
                                        OCTET STRING,
                                fkBridgeGarpAppPortRegistration
                                        INTEGER,
                                fkBridgeGarpAppPortApplicant
                                        INTEGER,
                                fkBridgeGarpAppPortFwdAll
                                        INTEGER,
                                fkBridgeGarpAppPortTimerJoin
                                        Integer32,
                                fkBridgeGarpAppPortTimerLeave
                                        Integer32,
                                fkBridgeGarpAppPortTimerLeaveAll
                                        Integer32
                         }

                -- 1.3.6.1.4.1.10428 9 1.101.3.26.2.1.1.1
                fkBridgeGarpAppPortIndex OBJECT-TYPE
                        SYNTAX INTEGER (1..65535)
                        MAX-ACCESS read-only
                        STATUS current
                        DESCRIPTION
                                "Port index.  Same as ifindex."
                        ::= { fkBridgeGarpAppPortEntry 1 }

                
                -- 1.3.6.1.4.1.10428 9 1.101.3.26.2.1.1.2
                fkBridgeGarpAppPortType OBJECT-TYPE
                        SYNTAX INTEGER
                                {
                                gvrp(1),
                                gmrp(2)
                                }
                        MAX-ACCESS read-only
                        STATUS current
                        DESCRIPTION
                                "GARP Application Type.
                                Supports GVRP, GMRP 
                                "
                        ::= { fkBridgeGarpAppPortEntry 2 }

                
                -- 1.3.6.1.4.1.10428 9 1.101.3.26.2.1.1.3
                fkBridgeGarpAppPortStatus OBJECT-TYPE
                        SYNTAX INTEGER
                                {
                                enable(1),
                                disable(2)
                                }
                        MAX-ACCESS read-only
                        STATUS current
                        DESCRIPTION
                                "GARP Application port status
                                1 : enable
                                2 : disable"
                        ::= { fkBridgeGarpAppPortEntry 3 }

                
                -- 1.3.6.1.4.1.10428 9 1.101.3.26.2.1.1.4
                fkBridgeGarpAppPortFailedRegistrations OBJECT-TYPE
                        SYNTAX Integer32
                        MAX-ACCESS read-only
                        STATUS current
                        DESCRIPTION
                                "The current value of the Failed Registrations counter maintained for a GARP Attribute type."
                        ::= { fkBridgeGarpAppPortEntry 4 }

                
                -- 1.3.6.1.4.1.10428 9 1.101.3.26.2.1.1.5
                fkBridgeGarpAppPortLastPduOrigin OBJECT-TYPE
                        SYNTAX OCTET STRING (SIZE (1..6))
                        MAX-ACCESS read-only
                        STATUS current
                        DESCRIPTION
                                "MAC Address of the last pdu that caused a state change for a given GARP Attribute."
                        ::= { fkBridgeGarpAppPortEntry 5 }

                
                -- 1.3.6.1.4.1.10428 9 1.101.3.26.2.1.1.6
                fkBridgeGarpAppPortRegistration OBJECT-TYPE
                        SYNTAX INTEGER
                                {
                                nomal(1),
                                fixed(2),
                                forbidden(3)
                                }
                        MAX-ACCESS read-only
                        STATUS current
                        DESCRIPTION
                                "GARP registration mode."
                        ::= { fkBridgeGarpAppPortEntry 6 }

                
                -- 1.3.6.1.4.1.10428 9 1.101.3.26.2.1.1.7
                fkBridgeGarpAppPortApplicant OBJECT-TYPE
                        SYNTAX INTEGER
                                {
                                participant(1),
                                nonParticipant(2)
                                }
                        MAX-ACCESS read-only
                        STATUS current
                        DESCRIPTION
                                "Applicant type
                                1: Transmissible PDU
                                2: Untransmissible PDU
                                "
                        ::= { fkBridgeGarpAppPortEntry 7 }

                
                -- 1.3.6.1.4.1.10428 9 1.101.3.26.2.1.1.8
                fkBridgeGarpAppPortFwdAll OBJECT-TYPE
                        SYNTAX INTEGER
                                {
                                enable(1),
                                disable(2)
                                }
                        MAX-ACCESS read-only
                        STATUS current
                        DESCRIPTION
                                "GMRP forward all registered-groups."
                        ::= { fkBridgeGarpAppPortEntry 8 }

                
                -- 1.3.6.1.4.1.10428 9 1.101.3.26.2.1.1.9
                fkBridgeGarpAppPortTimerJoin OBJECT-TYPE
                        SYNTAX Integer32
                        MAX-ACCESS read-only
                        STATUS current
                        DESCRIPTION
                                "GARP Application port timer join"
                        ::= { fkBridgeGarpAppPortEntry 9 }

                
                -- 1.3.6.1.4.1.10428 9 1.101.3.26.2.1.1.10
                fkBridgeGarpAppPortTimerLeave OBJECT-TYPE
                        SYNTAX Integer32
                        MAX-ACCESS read-only
                        STATUS current
                        DESCRIPTION
                                "GARP Application port timer leave"
                        ::= { fkBridgeGarpAppPortEntry 10 }

                
                -- 1.3.6.1.4.1.10428 9 1.101.3.26.2.1.1.11
                fkBridgeGarpAppPortTimerLeaveAll OBJECT-TYPE
                        SYNTAX Integer32
                        MAX-ACCESS read-only
                        STATUS current
                        DESCRIPTION
                                "GARP Application port timer leave all"
                        ::= { fkBridgeGarpAppPortEntry 11 }

                
                -- 1.3.6.1.4.1.10428 9 1.101.3.26.2.2
                fkBridgeGarpAppPortControl OBJECT IDENTIFIER ::= { fkBridgeGarpApplication 2 }

                
                -- 1.3.6.1.4.1.10428 9 1.101.3.26.2.2.1
                fkBridgeGarpAppPortControlRequest OBJECT-TYPE
                        SYNTAX INTEGER
                                {
                                setGarpAppStatus(1),
                                setGarpAppProfile(2)
                                }
                        MAX-ACCESS read-write
                        STATUS current
                        DESCRIPTION
                                "The request of a user command"
                        ::= { fkBridgeGarpAppPortControl 1 }

                
                -- 1.3.6.1.4.1.10428 9 1.101.3.26.2.2.2
                fkBridgeGarpAppPortControlStatus OBJECT-TYPE
                        SYNTAX FkControlStatusType
                        MAX-ACCESS read-only
                        STATUS current
                        DESCRIPTION
                                "The status of user command"
                        ::= { fkBridgeGarpAppPortControl 2 }

                
                -- 1.3.6.1.4.1.10428 9 1.101.3.26.2.2.3
                fkBridgeGarpAppPortControlTimer OBJECT-TYPE
                        SYNTAX Gauge32
                        MAX-ACCESS read-write
                        STATUS current
                        DESCRIPTION
                                "The maximum time for the manager for a long running user command"
                        ::= { fkBridgeGarpAppPortControl 3 }

                
                -- 1.3.6.1.4.1.10428 9 1.101.3.26.2.2.4
                fkBridgeGarpAppPortControlTimeStamp OBJECT-TYPE
                        SYNTAX TimeTicks
                        MAX-ACCESS read-only
                        STATUS current
                        DESCRIPTION
                                "The time stamp of the last command(end of command)"
                        ::= { fkBridgeGarpAppPortControl 4 }

                
                -- 1.3.6.1.4.1.10428 9 1.101.3.26.2.2.5
                fkBridgeGarpAppPortControlReqResult OBJECT-TYPE
                        SYNTAX FkControlRequestResultType
                        MAX-ACCESS read-only
                        STATUS current
                        DESCRIPTION
                                "The result of the last user command"
                        ::= { fkBridgeGarpAppPortControl 5 }

                
                -- 1.3.6.1.4.1.10428 9 1.101.3.26.2.2.6
                fkBridgeGarpAppPortControlIndex OBJECT-TYPE
                        SYNTAX INTEGER (1..65535)
                        MAX-ACCESS read-write
                        STATUS current
                        DESCRIPTION
                                "Port index.  Same as ifindex."
                        ::= { fkBridgeGarpAppPortControl 6 }

                
                -- 1.3.6.1.4.1.10428 9 1.101.3.26.2.2.7
                fkBridgeGarpAppPortControlType OBJECT-TYPE
                        SYNTAX INTEGER
                                {
                                gvrp(1),
                                gmrp(2)
                                }
                        MAX-ACCESS read-write
                        STATUS current
                        DESCRIPTION
                                "GARP Application Type.
                                Supports GVRP, GMRP"
                        ::= { fkBridgeGarpAppPortControl 7 }

                
                -- 1.3.6.1.4.1.10428 9 1.101.3.26.2.2.8
                fkBridgeGarpAppPortControlPortStatus OBJECT-TYPE
                        SYNTAX INTEGER
                                {
                                enable(1),
                                disable(2)
                                }
                        MAX-ACCESS read-write
                        STATUS current
                        DESCRIPTION
                                "GARP Application port status
                                1 : enable
                                2 : disable
                                "
                        ::= { fkBridgeGarpAppPortControl 8 }

                
                -- 1.3.6.1.4.1.10428 9 1.101.3.26.2.2.9
                fkBridgeGarpAppPortControlRegistration OBJECT-TYPE
                        SYNTAX INTEGER
                                {
                                nomal(1),
                                fixed(2),
                                forbidden(3)
                                }
                        MAX-ACCESS read-write
                        STATUS current
                        DESCRIPTION
                                "The current value of the Failed Registrations counter maintained for a GARP Attribute type."
                        ::= { fkBridgeGarpAppPortControl 9 }

                
                -- 1.3.6.1.4.1.10428 9 1.101.3.26.2.2.10
                fkBridgeGarpAppPortControlApplicant OBJECT-TYPE
                        SYNTAX INTEGER
                                {
                                participant(1),
                                nonPorticipant(2)
                                }
                        MAX-ACCESS read-write
                        STATUS current
                        DESCRIPTION
                                "Applicant type
                                1: Transmissible PDU
                                2: Untransmissible PDU"
                        ::= { fkBridgeGarpAppPortControl 10 }

                
                -- 1.3.6.1.4.1.10428 9 1.101.3.26.2.2.11
                fkBridgeGarpAppPortControlFwdAll OBJECT-TYPE
                        SYNTAX INTEGER
                                {
                                enable(1),
                                disable(2)
                                }
                        MAX-ACCESS read-write
                        STATUS current
                        DESCRIPTION
                                "Applicant type
                                1: Transmissible PDU
                                2: Untransmissible PDU
                                "
                        ::= { fkBridgeGarpAppPortControl 11 }

                
                -- 1.3.6.1.4.1.10428 9 1.101.3.26.2.2.12
                fkBridgeGarpAppPortControlTimerJoin OBJECT-TYPE
                        SYNTAX Integer32
                        MAX-ACCESS read-write
                        STATUS current
                        DESCRIPTION
                                "GARP Application port timer join"
                        ::= { fkBridgeGarpAppPortControl 12 }

                
                -- 1.3.6.1.4.1.10428 9 1.101.3.26.2.2.13
                fkBridgeGarpAppPortControlTimerLeave OBJECT-TYPE
                        SYNTAX Integer32
                        MAX-ACCESS read-write
                        STATUS current
                        DESCRIPTION
                                "GARP Application port timer leave"
                        ::= { fkBridgeGarpAppPortControl 13 }

                
                -- 1.3.6.1.4.1.10428 9 1.101.3.26.2.2.14
                fkBridgeGarpAppPortControlTimerLeaveAll OBJECT-TYPE
                        SYNTAX Integer32
                        MAX-ACCESS read-write
                        STATUS current
                        DESCRIPTION
                                "GARP Application port timer leave all"
                        ::= { fkBridgeGarpAppPortControl 14 }

                
                -- 1.3.6.1.4.1.10428 9 1.101.3.26.2.3
                fkBridgeGarpAppPortNotification OBJECT IDENTIFIER ::= { fkBridgeGarpApplication 3 }

                
                -- 1.3.6.1.4.1.10428 9 1.101.3.26.2.3.1
                fkBridgeGarpAppPortStatusChanged NOTIFICATION-TYPE
                        OBJECTS { fkBridgeGarpAppPortControlRequest, fkBridgeGarpAppPortControlTimeStamp, fkBridgeGarpAppPortControlReqResult, fkBridgeGarpAppPortControlIndex, fkBridgeGarpAppPortControlType, 
                                fkBridgeGarpAppPortControlPortStatus }
                        STATUS current
                        DESCRIPTION 
                                "Description."
                        ::= { fkBridgeGarpAppPortNotification 1 }

                
                -- 1.3.6.1.4.1.10428 9 1.101.3.26.2.3.2
                fkBridgeGarpAppPortProfileChanged NOTIFICATION-TYPE
                        OBJECTS { fkBridgeGarpAppPortControlRequest, fkBridgeGarpAppPortControlTimeStamp, fkBridgeGarpAppPortControlReqResult, fkBridgeGarpAppPortControlIndex, fkBridgeGarpAppPortControlType, 
                                fkBridgeGarpAppPortControlRegistration, fkBridgeGarpAppPortControlApplicant, fkBridgeGarpAppPortControlFwdAll, fkBridgeGarpAppPortControlTimerJoin, fkBridgeGarpAppPortControlTimerLeave, 
                                fkBridgeGarpAppPortControlTimerLeaveAll }
                        STATUS current
                        DESCRIPTION 
                                "Description."
                        ::= { fkBridgeGarpAppPortNotification 2 }

                
                -- 1.3.6.1.4.1.10428 9 1.101.3.26.3
                fkBridgeGarpStats OBJECT IDENTIFIER ::= { fkBridgeGarp 3 }

                
                -- 1.3.6.1.4.1.10428 9 1.101.3.26.3.1
                fkBridgeGarpStatsTable OBJECT-TYPE
                        SYNTAX SEQUENCE OF FkBridgeGarpStatsEntry
                        MAX-ACCESS not-accessible
                        STATUS current
                        DESCRIPTION
                                "bridge GARP stats table"
                        ::= { fkBridgeGarpStats 1 }

                
                -- 1.3.6.1.4.1.10428 9 1.101.3.26.3.1.1
                fkBridgeGarpStatsEntry OBJECT-TYPE
                        SYNTAX FkBridgeGarpStatsEntry
                        MAX-ACCESS not-accessible
                        STATUS current
                        DESCRIPTION
                                "key: fkBridgeGarpAppPortIndex, fkBridgeGarpAppPortType"
                        INDEX { fkBridgeGarpAppPortIndex, fkBridgeGarpAppPortType }
                        ::= { fkBridgeGarpStatsTable 1 }

                
                FkBridgeGarpStatsEntry ::=
                        SEQUENCE { 
                                fkBridgeGarpStatsJoinEmptyReceived
                                        Integer32,
                                fkBridgeGarpStatsJoinInReceived
                                        Integer32,
                                fkBridgeGarpStatsEmptyReceived
                                        Integer32,
                                fkBridgeGarpStatsLeaveInReceived
                                        Integer32,
                                fkBridgeGarpStatsLeaveEmptyReceived
                                        Integer32,
                                fkBridgeGarpStatsLeaveAllReceived
                                        Integer32,
                                fkBridgeGarpStatsJoinEmptyTransmitted
                                        Integer32,
                                fkBridgeGarpStatsJoinInTransmitted
                                        Integer32,
                                fkBridgeGarpStatsEmptyTransmitted
                                        Integer32,
                                fkBridgeGarpStatsLeaveInTransmitted
                                        Integer32,
                                fkBridgeGarpStatsLeaveEmptyTransmitted
                                        Integer32,
                                fkBridgeGarpStatsLeaveAllTransmitted
                                        Integer32
                         }

                -- 1.3.6.1.4.1.10428 9 1.101.3.26.3.1.1.1
                fkBridgeGarpStatsJoinEmptyReceived OBJECT-TYPE
                        SYNTAX Integer32
                        MAX-ACCESS read-only
                        STATUS current
                        DESCRIPTION
                                "GARP stats received:
                                join empty"
                        ::= { fkBridgeGarpStatsEntry 1 }

                
                -- 1.3.6.1.4.1.10428 9 1.101.3.26.3.1.1.2
                fkBridgeGarpStatsJoinInReceived OBJECT-TYPE
                        SYNTAX Integer32
                        MAX-ACCESS read-only
                        STATUS current
                        DESCRIPTION
                                "GARP stats received:
                                Joun in
                                "
                        ::= { fkBridgeGarpStatsEntry 2 }

                
                -- 1.3.6.1.4.1.10428 9 1.101.3.26.3.1.1.3
                fkBridgeGarpStatsEmptyReceived OBJECT-TYPE
                        SYNTAX Integer32
                        MAX-ACCESS read-only
                        STATUS current
                        DESCRIPTION
                                "GARP stats received:
                                empty "
                        ::= { fkBridgeGarpStatsEntry 3 }

                
                -- 1.3.6.1.4.1.10428 9 1.101.3.26.3.1.1.4
                fkBridgeGarpStatsLeaveInReceived OBJECT-TYPE
                        SYNTAX Integer32
                        MAX-ACCESS read-only
                        STATUS current
                        DESCRIPTION
                                "GARP stats received:
                                Leave in"
                        ::= { fkBridgeGarpStatsEntry 4 }

                
                -- 1.3.6.1.4.1.10428 9 1.101.3.26.3.1.1.5
                fkBridgeGarpStatsLeaveEmptyReceived OBJECT-TYPE
                        SYNTAX Integer32
                        MAX-ACCESS read-only
                        STATUS current
                        DESCRIPTION
                                "GARP stats received:
                                Leave empty"
                        ::= { fkBridgeGarpStatsEntry 5 }

                
                -- 1.3.6.1.4.1.10428 9 1.101.3.26.3.1.1.6
                fkBridgeGarpStatsLeaveAllReceived OBJECT-TYPE
                        SYNTAX Integer32
                        MAX-ACCESS read-only
                        STATUS current
                        DESCRIPTION
                                "GARP stats received:
                                Leave all"
                        ::= { fkBridgeGarpStatsEntry 6 }

                
                -- 1.3.6.1.4.1.10428 9 1.101.3.26.3.1.1.7
                fkBridgeGarpStatsJoinEmptyTransmitted OBJECT-TYPE
                        SYNTAX Integer32
                        MAX-ACCESS read-only
                        STATUS current
                        DESCRIPTION
                                "GARP stats transmitted:
                                Join empty"
                        ::= { fkBridgeGarpStatsEntry 7 }

                
                -- 1.3.6.1.4.1.10428 9 1.101.3.26.3.1.1.8
                fkBridgeGarpStatsJoinInTransmitted OBJECT-TYPE
                        SYNTAX Integer32
                        MAX-ACCESS read-only
                        STATUS current
                        DESCRIPTION
                                "GARP stats transmitted:
                                Join in"
                        ::= { fkBridgeGarpStatsEntry 8 }

                
                -- 1.3.6.1.4.1.10428 9 1.101.3.26.3.1.1.9
                fkBridgeGarpStatsEmptyTransmitted OBJECT-TYPE
                        SYNTAX Integer32
                        MAX-ACCESS read-only
                        STATUS current
                        DESCRIPTION
                                "GARP stats transmitted:
                                Empty
                                "
                        ::= { fkBridgeGarpStatsEntry 9 }

                
                -- 1.3.6.1.4.1.10428 9 1.101.3.26.3.1.1.10
                fkBridgeGarpStatsLeaveInTransmitted OBJECT-TYPE
                        SYNTAX Integer32
                        MAX-ACCESS read-only
                        STATUS current
                        DESCRIPTION
                                "GARP stats transmitted:
                                Leave in"
                        ::= { fkBridgeGarpStatsEntry 10 }

                
                -- 1.3.6.1.4.1.10428 9 1.101.3.26.3.1.1.11
                fkBridgeGarpStatsLeaveEmptyTransmitted OBJECT-TYPE
                        SYNTAX Integer32
                        MAX-ACCESS read-only
                        STATUS current
                        DESCRIPTION
                                "GARP stats transmitted;
                                Leave empty"
                        ::= { fkBridgeGarpStatsEntry 11 }

                
                -- 1.3.6.1.4.1.10428 9 1.101.3.26.3.1.1.12
                fkBridgeGarpStatsLeaveAllTransmitted OBJECT-TYPE
                        SYNTAX Integer32
                        MAX-ACCESS read-only
                        STATUS current
                        DESCRIPTION
                                "GARP stats transmitted:
                                Leave all"
                        ::= { fkBridgeGarpStatsEntry 12 }

                
                -- 1.3.6.1.4.1.10428 9 1.101.3.26.3.2
                fkBridgeGarpStatsControl OBJECT IDENTIFIER ::= { fkBridgeGarpStats 2 }

                
                -- 1.3.6.1.4.1.10428 9 1.101.3.26.3.2.1
                fkBridgeGarpStatsControlRequest OBJECT-TYPE
                        SYNTAX INTEGER { clearGarpPktStatistics(1) }
                        MAX-ACCESS read-write
                        STATUS current
                        DESCRIPTION
                                "The request of a user command"
                        ::= { fkBridgeGarpStatsControl 1 }

                
                -- 1.3.6.1.4.1.10428 9 1.101.3.26.3.2.2
                fkBridgeGarpStatstControlStatus OBJECT-TYPE
                        SYNTAX FkControlStatusType
                        MAX-ACCESS read-only
                        STATUS current
                        DESCRIPTION
                                "The status of user command"
                        ::= { fkBridgeGarpStatsControl 2 }

                
                -- 1.3.6.1.4.1.10428 9 1.101.3.26.3.2.3
                fkBridgeGarpStatsControlTimer OBJECT-TYPE
                        SYNTAX Gauge32
                        MAX-ACCESS read-write
                        STATUS current
                        DESCRIPTION
                                "The maximum time for the manager for a long running user command"
                        ::= { fkBridgeGarpStatsControl 3 }

                
                -- 1.3.6.1.4.1.10428 9 1.101.3.26.3.2.4
                fkBridgeGarpStatsControlTimeStamp OBJECT-TYPE
                        SYNTAX TimeTicks
                        MAX-ACCESS read-only
                        STATUS current
                        DESCRIPTION
                                "The time stamp of the last command(end of command)"
                        ::= { fkBridgeGarpStatsControl 4 }

                
                -- 1.3.6.1.4.1.10428 9 1.101.3.26.3.2.5
                fkBridgeGarpStatsControlReqResult OBJECT-TYPE
                        SYNTAX FkControlRequestResultType
                        MAX-ACCESS read-only
                        STATUS current
                        DESCRIPTION
                                "The result of the last user command"
                        ::= { fkBridgeGarpStatsControl 5 }

                
                -- 1.3.6.1.4.1.10428 9 1.101.3.26.3.2.6
                fkBridgeGarpStatsControlIndex OBJECT-TYPE
                        SYNTAX INTEGER (1..65535)
                        MAX-ACCESS read-write
                        STATUS current
                        DESCRIPTION
                                "Port index"
                        ::= { fkBridgeGarpStatsControl 6 }

                
                -- 1.3.6.1.4.1.10428 9 1.101.3.26.3.2.7
                fkBridgeGarpStatsControlType OBJECT-TYPE
                        SYNTAX INTEGER
                                {
                                gvrp(1),
                                gmrp(2)
                                }
                        MAX-ACCESS read-write
                        STATUS current
                        DESCRIPTION
                                "Port type
                                "
                        ::= { fkBridgeGarpStatsControl 7 }

                
                -- 1.3.6.1.4.1.10428 9 1.101.3.26.3.3
                fkBridgeGarpStatsNotification OBJECT IDENTIFIER ::= { fkBridgeGarpStats 3 }

                
                -- 1.3.6.1.4.1.10428 9 1.101.3.26.3.3.1
                fkBridgeGarpStatisticsCleared NOTIFICATION-TYPE
                        OBJECTS { fkBridgeGarpStatsControlRequest, fkBridgeGarpStatsControlTimeStamp, fkBridgeGarpStatsControlReqResult, fkBridgeGarpStatsControlIndex, fkBridgeGarpStatsControlType
                                 }
                        STATUS current
                        DESCRIPTION 
                                "Description."
                        ::= { fkBridgeGarpStatsNotification 1 }

                
                -- 1.3.6.1.4.1.10428 9 1.101.3.26.4
                fkBridgeGmrpStatic OBJECT IDENTIFIER ::= { fkBridgeGarp 4 }

                
                -- 1.3.6.1.4.1.10428 9 1.101.3.26.4.1
                fkBridgeGmrpStaticTable OBJECT-TYPE
                        SYNTAX SEQUENCE OF FkBridgeGmrpStaticEntry
                        MAX-ACCESS not-accessible
                        STATUS current
                        DESCRIPTION
                                "bridge GMRP static table"
                        ::= { fkBridgeGmrpStatic 1 }

                
                -- 1.3.6.1.4.1.10428 9 1.101.3.26.4.1.1
                fkBridgeGmrpStaticEntry OBJECT-TYPE
                        SYNTAX FkBridgeGmrpStaticEntry
                        MAX-ACCESS not-accessible
                        STATUS current
                        DESCRIPTION
                                "key: fkBridgeGmrpStaticVid, fkBridgeGmrpStaticPort, fkBridgeGmrpStaticGmac"
                        INDEX { fkBridgeGmrpStaticVid, fkBridgeGmrpStaticPort, fkBridgeGmrpStaticGmac }
                        ::= { fkBridgeGmrpStaticTable 1 }

                
                FkBridgeGmrpStaticEntry ::=
                        SEQUENCE { 
                                fkBridgeGmrpStaticVid
                                        INTEGER,
                                fkBridgeGmrpStaticPort
                                        INTEGER,
                                fkBridgeGmrpStaticGmac
                                        OCTET STRING
                         }

                -- 1.3.6.1.4.1.10428 9 1.101.3.26.4.1.1.1
                fkBridgeGmrpStaticVid OBJECT-TYPE
                        SYNTAX INTEGER (1..65535)
                        MAX-ACCESS read-only
                        STATUS current
                        DESCRIPTION
                                "VLAN Id"
                        ::= { fkBridgeGmrpStaticEntry 1 }

                
                -- 1.3.6.1.4.1.10428 9 1.101.3.26.4.1.1.2
                fkBridgeGmrpStaticPort OBJECT-TYPE
                        SYNTAX INTEGER (1..65535)
                        MAX-ACCESS read-only
                        STATUS current
                        DESCRIPTION
                                "Port index"
                        ::= { fkBridgeGmrpStaticEntry 2 }

                
                -- 1.3.6.1.4.1.10428 9 1.101.3.26.4.1.1.3
                fkBridgeGmrpStaticGmac OBJECT-TYPE
                        SYNTAX OCTET STRING (SIZE (0..6))
                        MAX-ACCESS read-only
                        STATUS current
                        DESCRIPTION
                                "Group Mac Address"
                        ::= { fkBridgeGmrpStaticEntry 3 }

                
                -- 1.3.6.1.4.1.10428 9 1.101.3.26.4.2
                fkBridgeGmrpStaticControl OBJECT IDENTIFIER ::= { fkBridgeGmrpStatic 2 }

                
                -- 1.3.6.1.4.1.10428 9 1.101.3.26.4.2.1
                fkBridgeGmrpStaticControlRequest OBJECT-TYPE
                        SYNTAX INTEGER
                                {
                                addGmrpStatic(1),
                                delGmrpStatic(2)
                                }
                        MAX-ACCESS read-write
                        STATUS current
                        DESCRIPTION
                                "The request of a user command"
                        ::= { fkBridgeGmrpStaticControl 1 }

                
                -- 1.3.6.1.4.1.10428 9 1.101.3.26.4.2.2
                fkBridgeGmrpStaticControlStatus OBJECT-TYPE
                        SYNTAX FkControlStatusType
                        MAX-ACCESS read-only
                        STATUS current
                        DESCRIPTION
                                "The status of user command"
                        ::= { fkBridgeGmrpStaticControl 2 }

                
                -- 1.3.6.1.4.1.10428 9 1.101.3.26.4.2.3
                fkBridgeGmrpStaticControlTimer OBJECT-TYPE
                        SYNTAX Gauge32
                        MAX-ACCESS read-write
                        STATUS current
                        DESCRIPTION
                                "The maximum time for the manager for a long running user command"
                        ::= { fkBridgeGmrpStaticControl 3 }

                
                -- 1.3.6.1.4.1.10428 9 1.101.3.26.4.2.4
                fkBridgeGmrpStaticControlTimeStamp OBJECT-TYPE
                        SYNTAX TimeTicks
                        MAX-ACCESS read-only
                        STATUS current
                        DESCRIPTION
                                "The time stamp of the last command(end of command)"
                        ::= { fkBridgeGmrpStaticControl 4 }

                
                -- 1.3.6.1.4.1.10428 9 1.101.3.26.4.2.5
                fkBridgeGmrpStaticControlReqResult OBJECT-TYPE
                        SYNTAX FkControlRequestResultType
                        MAX-ACCESS read-only
                        STATUS current
                        DESCRIPTION
                                "The result of the last user command"
                        ::= { fkBridgeGmrpStaticControl 5 }

                
                -- 1.3.6.1.4.1.10428 9 1.101.3.26.4.2.6
                fkBridgeGmrpStaticControlVid OBJECT-TYPE
                        SYNTAX INTEGER (1..65535)
                        MAX-ACCESS read-write
                        STATUS current
                        DESCRIPTION
                                "VLAN Id"
                        ::= { fkBridgeGmrpStaticControl 6 }

                
                -- 1.3.6.1.4.1.10428 9 1.101.3.26.4.2.7
                fkBridgeGmrpStaticControlPort OBJECT-TYPE
                        SYNTAX INTEGER (1..65535)
                        MAX-ACCESS read-write
                        STATUS current
                        DESCRIPTION
                                "Port index"
                        ::= { fkBridgeGmrpStaticControl 7 }

                
                -- 1.3.6.1.4.1.10428 9 1.101.3.26.4.2.8
                fkBridgeGmrpStaticControlGmac OBJECT-TYPE
                        SYNTAX OCTET STRING (SIZE (0..6))
                        MAX-ACCESS read-write
                        STATUS current
                        DESCRIPTION
                                "Group Mac Address"
                        ::= { fkBridgeGmrpStaticControl 8 }

                
                -- 1.3.6.1.4.1.10428 9 1.101.3.26.4.3
                fkBridgeGmrpStaticNotification OBJECT IDENTIFIER ::= { fkBridgeGmrpStatic 3 }

                
                -- 1.3.6.1.4.1.10428 9 1.101.3.26.4.3.1
                fkBridgeGmrpStaticAdded NOTIFICATION-TYPE
                        OBJECTS { fkBridgeGmrpStaticControlRequest, fkBridgeGmrpStaticControlTimeStamp, fkBridgeGmrpStaticControlReqResult, fkBridgeGmrpStaticControlVid, fkBridgeGmrpStaticControlPort, 
                                fkBridgeGmrpStaticControlGmac }
                        STATUS current
                        DESCRIPTION 
                                "Description."
                        ::= { fkBridgeGmrpStaticNotification 1 }

                
                -- 1.3.6.1.4.1.10428 9 1.101.3.26.4.3.2
                fkBridgeGmrpStaticDeleted NOTIFICATION-TYPE
                        OBJECTS { fkBridgeGmrpStaticControlRequest, fkBridgeGmrpStaticControlTimeStamp, fkBridgeGmrpStaticControlReqResult, fkBridgeGmrpStaticControlVid, fkBridgeGmrpStaticControlPort, 
                                fkBridgeGmrpStaticControlGmac }
                        STATUS current
                        DESCRIPTION 
                                "Description."
                        ::= { fkBridgeGmrpStaticNotification 2 }

                
                -- 1.3.6.1.4.1.10428 9 1.101.3.27
                fkVlanTag OBJECT IDENTIFIER ::= { fkBridge 27 }

                
                -- 1.3.6.1.4.1.10428 9 1.101.3.27.1
                fkVlanInboundTag OBJECT IDENTIFIER ::= { fkVlanTag 1 }

                
                -- 1.3.6.1.4.1.10428 9 1.101.3.27.1.1
                fkVlanInboundTagTable OBJECT-TYPE
                        SYNTAX SEQUENCE OF FkVlanInboundTagEntry
                        MAX-ACCESS not-accessible
                        STATUS current
                        DESCRIPTION
                                "vlan inbound tag table."
                        ::= { fkVlanInboundTag 1 }

                
                -- 1.3.6.1.4.1.10428 9 1.101.3.27.1.1.1
                fkVlanInboundTagEntry OBJECT-TYPE
                        SYNTAX FkVlanInboundTagEntry
                        MAX-ACCESS not-accessible
                        STATUS current
                        DESCRIPTION
                                "key: fkVlanInboundTagPortIndex, fkVlanInboundTagVlanIndex"
                        INDEX { fkVlanInboundTagPortIndex, fkVlanInboundTagVlanIndex, fkVlanInboundTagVlanPriority }
                        ::= { fkVlanInboundTagTable 1 }

                
                FkVlanInboundTagEntry ::=
                        SEQUENCE { 
                                fkVlanInboundTagPortIndex
                                        INTEGER,
                                fkVlanInboundTagVlanIndex
                                        INTEGER,
                                fkVlanInboundTagOuterVid
                                        INTEGER,
                                fkVlanInboundTagOperStatus
                                        INTEGER,
                                fkVlanInboundTagVlanPriority
                                        INTEGER,
                                fkVlanInboundTagOuterVlanPriority
                                        INTEGER
                         }

                -- 1.3.6.1.4.1.10428 9 1.101.3.27.1.1.1.1
                fkVlanInboundTagPortIndex OBJECT-TYPE
                        SYNTAX INTEGER (1..65535)
                        MAX-ACCESS read-only
                        STATUS current
                        DESCRIPTION
                                "Bridge Port Index"
                        ::= { fkVlanInboundTagEntry 1 }

                
                -- 1.3.6.1.4.1.10428 9 1.101.3.27.1.1.1.2
                fkVlanInboundTagVlanIndex OBJECT-TYPE
                        SYNTAX INTEGER (1..4094)
                        MAX-ACCESS read-only
                        STATUS current
                        DESCRIPTION
                                "Vlan Index of inner-tag"
                        ::= { fkVlanInboundTagEntry 2 }

                
                -- 1.3.6.1.4.1.10428 9 1.101.3.27.1.1.1.3
                fkVlanInboundTagOuterVid OBJECT-TYPE
                        SYNTAX INTEGER (1..4094)
                        MAX-ACCESS read-only
                        STATUS current
                        DESCRIPTION
                                "The Outer Vlan-ID to tag for incoming packet with vlan index"
                        ::= { fkVlanInboundTagEntry 3 }

                
                -- 1.3.6.1.4.1.10428 9 1.101.3.27.1.1.1.4
                fkVlanInboundTagOperStatus OBJECT-TYPE
                        SYNTAX INTEGER
                                {
                                on(1),
                                off(2)
                                }
                        MAX-ACCESS read-only
                        STATUS current
                        DESCRIPTION
                                "The Operational Status of Outer Vlan-ID to tag for incoming packet with vlan index."
                        ::= { fkVlanInboundTagEntry 4 }

                
                -- 1.3.6.1.4.1.10428 9 1.101.3.27.1.1.1.5
                fkVlanInboundTagVlanPriority OBJECT-TYPE
                        SYNTAX INTEGER
                                {
                                cos0(0),
                                cos1(1),
                                cos2(2),
                                cos3(3),
                                cos4(4),
                                cos5(5),
                                cos6(6),
                                cos7(7),
                                cosAny(8)
                                }
                        MAX-ACCESS read-only
                        STATUS current
                        DESCRIPTION
                                "Vlan Priority of inner-tag"
                        ::= { fkVlanInboundTagEntry 5 }

                
                -- 1.3.6.1.4.1.10428 9 1.101.3.27.1.1.1.6
                fkVlanInboundTagOuterVlanPriority OBJECT-TYPE
                        SYNTAX INTEGER
                                {
                                cos0(0),
                                cos1(1),
                                cos2(2),
                                cos3(3),
                                cos4(4),
                                cos5(5),
                                cos6(6),
                                cos7(7)
                                }
                        MAX-ACCESS read-only
                        STATUS current
                        DESCRIPTION
                                "The Outer Vlan-Pri to tag for incoming packet with vlan index"
                        ::= { fkVlanInboundTagEntry 6 }

                
                -- 1.3.6.1.4.1.10428 9 1.101.3.27.1.2
                fkVlanInboundTagControl OBJECT IDENTIFIER ::= { fkVlanInboundTag 2 }

                
                -- 1.3.6.1.4.1.10428 9 1.101.3.27.1.2.1
                fkVlanInboundTagControlRequest OBJECT-TYPE
                        SYNTAX INTEGER
                                {
                                setInboundVid(1),
                                clearInboundVid(2)
                                }
                        MAX-ACCESS read-write
                        STATUS current
                        DESCRIPTION
                                "The request of a user command"
                        ::= { fkVlanInboundTagControl 1 }

                
                -- 1.3.6.1.4.1.10428 9 1.101.3.27.1.2.2
                fkVlanInboundTagControlStatus OBJECT-TYPE
                        SYNTAX FkControlStatusType
                        MAX-ACCESS read-only
                        STATUS current
                        DESCRIPTION
                                "The status of user command"
                        ::= { fkVlanInboundTagControl 2 }

                
                -- 1.3.6.1.4.1.10428 9 1.101.3.27.1.2.3
                fkVlanInboundTagControlTimer OBJECT-TYPE
                        SYNTAX Gauge32
                        MAX-ACCESS read-write
                        STATUS current
                        DESCRIPTION
                                "The maximum time for the manager for a long running user command"
                        ::= { fkVlanInboundTagControl 3 }

                
                -- 1.3.6.1.4.1.10428 9 1.101.3.27.1.2.4
                fkVlanInboundTagControlTimeStamp OBJECT-TYPE
                        SYNTAX TimeTicks
                        MAX-ACCESS read-only
                        STATUS current
                        DESCRIPTION
                                "The time stamp of the last command(end of command)"
                        ::= { fkVlanInboundTagControl 4 }

                
                -- 1.3.6.1.4.1.10428 9 1.101.3.27.1.2.5
                fkVlanInboundTagControlReqResult OBJECT-TYPE
                        SYNTAX FkControlRequestResultType
                        MAX-ACCESS read-only
                        STATUS current
                        DESCRIPTION
                                "The result of the last user command"
                        ::= { fkVlanInboundTagControl 5 }

                
                -- 1.3.6.1.4.1.10428 9 1.101.3.27.1.2.6
                fkVlanInboundTagControlPortIndex OBJECT-TYPE
                        SYNTAX INTEGER (1..65535)
                        MAX-ACCESS read-write
                        STATUS current
                        DESCRIPTION
                                "fkVlanInboundTagPortIndex"
                        ::= { fkVlanInboundTagControl 6 }

                
                -- 1.3.6.1.4.1.10428 9 1.101.3.27.1.2.7
                fkVlanInboundTagControlVlanIndex OBJECT-TYPE
                        SYNTAX INTEGER (1..4094)
                        MAX-ACCESS read-write
                        STATUS current
                        DESCRIPTION
                                "fkVlanInboundTagVlanIndex"
                        ::= { fkVlanInboundTagControl 7 }

                
                -- 1.3.6.1.4.1.10428 9 1.101.3.27.1.2.8
                fkVlanInboundTagControlOuterVid OBJECT-TYPE
                        SYNTAX INTEGER (0..4094)
                        MAX-ACCESS read-write
                        STATUS current
                        DESCRIPTION
                                "The Vlan-ID for outer-tag
                                0 : clear
                                "
                        ::= { fkVlanInboundTagControl 8 }

                
                -- 1.3.6.1.4.1.10428 9 1.101.3.27.1.2.9
                fkVlanInboundTagControlVlanPriority OBJECT-TYPE
                        SYNTAX INTEGER
                                {
                                cos0(0),
                                cos1(1),
                                cos2(2),
                                cos3(3),
                                cos4(4),
                                cos5(5),
                                cos6(6),
                                cos7(7),
                                cosAny(8)
                                }
                        MAX-ACCESS read-write
                        STATUS current
                        DESCRIPTION
                                "Vlan Priority of inner-tag"
                        ::= { fkVlanInboundTagControl 9 }

                
                -- 1.3.6.1.4.1.10428 9 1.101.3.27.1.2.10
                fkVlanInboundTagControlOuterVlanPriority OBJECT-TYPE
                        SYNTAX INTEGER
                                {
                                cos0(0),
                                cos1(1),
                                cos2(2),
                                cos3(3),
                                cos4(4),
                                cos5(5),
                                cos6(6),
                                cos7(7)
                                }
                        MAX-ACCESS read-write
                        STATUS current
                        DESCRIPTION
                                "The Outer Vlan-Pri to tag for incoming packet with vlan index"
                        ::= { fkVlanInboundTagControl 10 }

                
                -- 1.3.6.1.4.1.10428 9 1.101.3.27.1.3
                fkVlanInboundTagNotification OBJECT IDENTIFIER ::= { fkVlanInboundTag 3 }

                
                -- 1.3.6.1.4.1.10428 9 1.101.3.27.1.3.1
                fkVlanInboundTagChanged NOTIFICATION-TYPE
                        OBJECTS { fkVlanInboundTagControlRequest, fkVlanInboundTagControlReqResult, fkVlanInboundTagControlTimeStamp, fkVlanInboundTagControlPortIndex, fkVlanInboundTagControlVlanIndex, 
                                fkVlanInboundTagControlOuterVid, fkVlanInboundTagControlVlanPriority, fkVlanInboundTagControlOuterVlanPriority }
                        STATUS current
                        DESCRIPTION 
                                "setInboundVid"
                        ::= { fkVlanInboundTagNotification 1 }

                
                -- 1.3.6.1.4.1.10428 9 1.101.3.27.1.3.2
                fkVlanInboundTagCleared NOTIFICATION-TYPE
                        OBJECTS { fkVlanInboundTagControlRequest, fkVlanInboundTagControlTimeStamp, fkVlanInboundTagControlReqResult, fkVlanInboundTagControlPortIndex, fkVlanInboundTagControlVlanIndex, 
                                fkVlanInboundTagControlVlanPriority }
                        STATUS current
                        DESCRIPTION 
                                "Description."
                        ::= { fkVlanInboundTagNotification 2 }

                
                -- 1.3.6.1.4.1.10428 9 1.101.3.27.2
                fkVlanOutboundTag OBJECT IDENTIFIER ::= { fkVlanTag 2 }

                
                -- 1.3.6.1.4.1.10428 9 1.101.3.27.2.1
                fkVlanOutboundTagTable OBJECT-TYPE
                        SYNTAX SEQUENCE OF FkVlanOutboundTagEntry
                        MAX-ACCESS not-accessible
                        STATUS current
                        DESCRIPTION
                                "vlan outbound tag table."
                        ::= { fkVlanOutboundTag 1 }

                
                -- 1.3.6.1.4.1.10428 9 1.101.3.27.2.1.1
                fkVlanOutboundTagEntry OBJECT-TYPE
                        SYNTAX FkVlanOutboundTagEntry
                        MAX-ACCESS not-accessible
                        STATUS current
                        DESCRIPTION
                                "key: fkVlanOutboundTagPortIndex, fkVlanOutboundTagVlanIndex"
                        INDEX { fkVlanOutboundTagPortIndex, fkVlanOutboundTagVlanIndex }
                        ::= { fkVlanOutboundTagTable 1 }

                
                FkVlanOutboundTagEntry ::=
                        SEQUENCE { 
                                fkVlanOutboundTagPortIndex
                                        INTEGER,
                                fkVlanOutboundTagVlanIndex
                                        INTEGER,
                                fkVlanOutboundTagOperStatus
                                        INTEGER
                         }

                -- 1.3.6.1.4.1.10428 9 1.101.3.27.2.1.1.1
                fkVlanOutboundTagPortIndex OBJECT-TYPE
                        SYNTAX INTEGER (1..65535)
                        MAX-ACCESS read-only
                        STATUS current
                        DESCRIPTION
                                "Bridge Port Index for egress port"
                        ::= { fkVlanOutboundTagEntry 1 }

                
                -- 1.3.6.1.4.1.10428 9 1.101.3.27.2.1.1.2
                fkVlanOutboundTagVlanIndex OBJECT-TYPE
                        SYNTAX INTEGER (1..4094)
                        MAX-ACCESS read-only
                        STATUS current
                        DESCRIPTION
                                "Vlan index of outer-tag"
                        ::= { fkVlanOutboundTagEntry 2 }

                
                -- 1.3.6.1.4.1.10428 9 1.101.3.27.2.1.1.3
                fkVlanOutboundTagOperStatus OBJECT-TYPE
                        SYNTAX INTEGER
                                {
                                on(1),
                                off(2)
                                }
                        MAX-ACCESS read-only
                        STATUS current
                        DESCRIPTION
                                "The Operational Status of Outer Vlan-ID to tag for outgoing packet with vlan index."
                        ::= { fkVlanOutboundTagEntry 3 }

                
                -- 1.3.6.1.4.1.10428 9 1.101.3.27.2.2
                fkVlanOutboundTagControl OBJECT IDENTIFIER ::= { fkVlanOutboundTag 2 }

                
                -- 1.3.6.1.4.1.10428 9 1.101.3.27.2.2.1
                fkVlanOutboundTagControlRequest OBJECT-TYPE
                        SYNTAX INTEGER
                                {
                                setOutboundtag(1),
                                clearOutboundtag(2)
                                }
                        MAX-ACCESS read-write
                        STATUS current
                        DESCRIPTION
                                "The request of a user command"
                        ::= { fkVlanOutboundTagControl 1 }

                
                -- 1.3.6.1.4.1.10428 9 1.101.3.27.2.2.2
                fkVlanOutboundTagControlStatus OBJECT-TYPE
                        SYNTAX FkControlStatusType
                        MAX-ACCESS read-only
                        STATUS current
                        DESCRIPTION
                                "The status of user command"
                        ::= { fkVlanOutboundTagControl 2 }

                
                -- 1.3.6.1.4.1.10428 9 1.101.3.27.2.2.3
                fkVlanOutboundTagControlTimer OBJECT-TYPE
                        SYNTAX Gauge32
                        MAX-ACCESS read-write
                        STATUS current
                        DESCRIPTION
                                "The maximum time for the manager for a long running user command"
                        ::= { fkVlanOutboundTagControl 3 }

                
                -- 1.3.6.1.4.1.10428 9 1.101.3.27.2.2.4
                fkVlanOutboundTagControlTimeStamp OBJECT-TYPE
                        SYNTAX TimeTicks
                        MAX-ACCESS read-only
                        STATUS current
                        DESCRIPTION
                                "The time stamp of the last command(end of command)"
                        ::= { fkVlanOutboundTagControl 4 }

                
                -- 1.3.6.1.4.1.10428 9 1.101.3.27.2.2.5
                fkVlanOutboundTagControlReqResult OBJECT-TYPE
                        SYNTAX FkControlRequestResultType
                        MAX-ACCESS read-only
                        STATUS current
                        DESCRIPTION
                                "The result of the last user command"
                        ::= { fkVlanOutboundTagControl 5 }

                
                -- 1.3.6.1.4.1.10428 9 1.101.3.27.2.2.6
                fkVlanOutboundTagControlPortIndex OBJECT-TYPE
                        SYNTAX INTEGER (1..65535)
                        MAX-ACCESS read-write
                        STATUS current
                        DESCRIPTION
                                "fkVlanOutboundTagPortIndex"
                        ::= { fkVlanOutboundTagControl 6 }

                
                -- 1.3.6.1.4.1.10428 9 1.101.3.27.2.2.7
                fkVlanOutboundTagControlOuterVid OBJECT-TYPE
                        SYNTAX INTEGER (1..4094)
                        MAX-ACCESS read-write
                        STATUS current
                        DESCRIPTION
                                "The outer-tag vid of packet to go out on the egress port"
                        ::= { fkVlanOutboundTagControl 7 }

                
                -- 1.3.6.1.4.1.10428 9 1.101.3.27.2.3
                fkVlanOutboundTagNotification OBJECT IDENTIFIER ::= { fkVlanOutboundTag 3 }

                
                -- 1.3.6.1.4.1.10428 9 1.101.3.27.2.3.1
                fkVlanOutboundTagSet NOTIFICATION-TYPE
                        OBJECTS { fkVlanOutboundTagControlRequest, fkVlanOutboundTagControlReqResult, fkVlanOutboundTagControlTimeStamp, fkVlanOutboundTagControlPortIndex, fkVlanOutboundTagControlOuterVid
                                 }
                        STATUS current
                        DESCRIPTION 
                                "setOutboundtag"
                        ::= { fkVlanOutboundTagNotification 1 }

                
                -- 1.3.6.1.4.1.10428 9 1.101.3.27.2.3.2
                fkVlanOutboundTagClear NOTIFICATION-TYPE
                        OBJECTS { fkVlanOutboundTagControlRequest, fkVlanOutboundTagControlReqResult, fkVlanOutboundTagControlTimeStamp, fkVlanOutboundTagControlPortIndex, fkVlanOutboundTagControlOuterVid
                                 }
                        STATUS current
                        DESCRIPTION 
                                "clearOutboundtag"
                        ::= { fkVlanOutboundTagNotification 2 }

                
                -- 1.3.6.1.4.1.10428 9 1.101.3.27.3
                fkVlanRangeInboundTag OBJECT IDENTIFIER ::= { fkVlanTag 3 }

                
                -- 1.3.6.1.4.1.10428 9 1.101.3.27.3.1
                fkVlanRangeInboundTagTable OBJECT-TYPE
                        SYNTAX SEQUENCE OF FkVlanRangeInboundTagEntry
                        MAX-ACCESS not-accessible
                        STATUS current
                        DESCRIPTION
                                "vlan range inbound tag table."
                        ::= { fkVlanRangeInboundTag 1 }

                
                -- 1.3.6.1.4.1.10428 9 1.101.3.27.3.1.1
                fkVlanRangeInboundTagEntry OBJECT-TYPE
                        SYNTAX FkVlanRangeInboundTagEntry
                        MAX-ACCESS not-accessible
                        STATUS current
                        DESCRIPTION
                                "key: fkVlanRangeInboundTagPortIndex, fkVlanRangeInboundTagMinVlanIndex, fkVlanRangeInboundTagMaxVlanIndex"
                        INDEX { fkVlanRangeInboundTagPortIndex, fkVlanRangeInboundTagMinVlanIndex, fkVlanRangeInboundTagMaxVlanIndex }
                        ::= { fkVlanRangeInboundTagTable 1 }

                
                FkVlanRangeInboundTagEntry ::=
                        SEQUENCE { 
                                fkVlanRangeInboundTagPortIndex
                                        Integer32,
                                fkVlanRangeInboundTagMinVlanIndex
                                        Integer32,
                                fkVlanRangeInboundTagMaxVlanIndex
                                        Integer32,
                                fkVlanRangeInboundTagOuterVid
                                        Integer32,
                                fkVlanRangeInboundTagOperStatus
                                        INTEGER
                         }

                -- 1.3.6.1.4.1.10428 9 1.101.3.27.3.1.1.1
                fkVlanRangeInboundTagPortIndex OBJECT-TYPE
                        SYNTAX Integer32 (1..512)
                        MAX-ACCESS read-only
                        STATUS current
                        DESCRIPTION
                                "Bridge Port Index."
                        ::= { fkVlanRangeInboundTagEntry 1 }

                
                -- 1.3.6.1.4.1.10428 9 1.101.3.27.3.1.1.2
                fkVlanRangeInboundTagMinVlanIndex OBJECT-TYPE
                        SYNTAX Integer32 (1..65535)
                        MAX-ACCESS read-only
                        STATUS current
                        DESCRIPTION
                                "Min Vlan Index of inner-tag."
                        ::= { fkVlanRangeInboundTagEntry 2 }

                
                -- 1.3.6.1.4.1.10428 9 1.101.3.27.3.1.1.3
                fkVlanRangeInboundTagMaxVlanIndex OBJECT-TYPE
                        SYNTAX Integer32 (1..65535)
                        MAX-ACCESS read-only
                        STATUS current
                        DESCRIPTION
                                "Max Vlan Index of inner-tag."
                        ::= { fkVlanRangeInboundTagEntry 3 }

                
                -- 1.3.6.1.4.1.10428 9 1.101.3.27.3.1.1.4
                fkVlanRangeInboundTagOuterVid OBJECT-TYPE
                        SYNTAX Integer32 (1..65535)
                        MAX-ACCESS read-only
                        STATUS current
                        DESCRIPTION
                                "The Outer Vlan-ID to tag for incoming packet with vlan index."
                        ::= { fkVlanRangeInboundTagEntry 4 }

                
                -- 1.3.6.1.4.1.10428 9 1.101.3.27.3.1.1.5
                fkVlanRangeInboundTagOperStatus OBJECT-TYPE
                        SYNTAX INTEGER
                                {
                                on(1),
                                off(2)
                                }
                        MAX-ACCESS read-only
                        STATUS current
                        DESCRIPTION
                                "The Operational Status of Outer Vlan-ID to tag for incoming packet with vlan index."
                        ::= { fkVlanRangeInboundTagEntry 5 }

                
                -- 1.3.6.1.4.1.10428 9 1.101.3.27.3.2
                fkVlanRangeInboundTagControl OBJECT IDENTIFIER ::= { fkVlanRangeInboundTag 2 }

                
                -- 1.3.6.1.4.1.10428 9 1.101.3.27.3.2.1
                fkVlanRangeInboundTagControlRequest OBJECT-TYPE
                        SYNTAX INTEGER
                                {
                                setRangeInboundVid(1),
                                clearRangeInboundVid(2)
                                }
                        MAX-ACCESS read-write
                        STATUS current
                        DESCRIPTION
                                "The request of a user command."
                        ::= { fkVlanRangeInboundTagControl 1 }

                
                -- 1.3.6.1.4.1.10428 9 1.101.3.27.3.2.2
                fkVlanRangeInboundTagControlStatus OBJECT-TYPE
                        SYNTAX FkControlStatusType
                        MAX-ACCESS read-only
                        STATUS current
                        DESCRIPTION
                                "The status of a user command."
                        ::= { fkVlanRangeInboundTagControl 2 }

                
                -- 1.3.6.1.4.1.10428 9 1.101.3.27.3.2.3
                fkVlanRangeInboundTagControlTimer OBJECT-TYPE
                        SYNTAX Gauge32
                        MAX-ACCESS read-write
                        STATUS current
                        DESCRIPTION
                                "The maximum wait time for the manager for a long running user command."
                        ::= { fkVlanRangeInboundTagControl 3 }

                
                -- 1.3.6.1.4.1.10428 9 1.101.3.27.3.2.4
                fkVlanRangeInboundTagControlTimeStamp OBJECT-TYPE
                        SYNTAX TimeTicks
                        MAX-ACCESS read-only
                        STATUS current
                        DESCRIPTION
                                "The time stamp of the last command (end of command)."
                        ::= { fkVlanRangeInboundTagControl 4 }

                
                -- 1.3.6.1.4.1.10428 9 1.101.3.27.3.2.5
                fkVlanRangeInboundTagControlReqResult OBJECT-TYPE
                        SYNTAX FkControlRequestResultType
                        MAX-ACCESS read-only
                        STATUS current
                        DESCRIPTION
                                "The result of the last user command."
                        ::= { fkVlanRangeInboundTagControl 5 }

                
                -- 1.3.6.1.4.1.10428 9 1.101.3.27.3.2.6
                fkVlanRangeInboundTagControlPortIndex OBJECT-TYPE
                        SYNTAX Integer32 (1..512)
                        MAX-ACCESS read-write
                        STATUS current
                        DESCRIPTION
                                "Bridge Port Index."
                        ::= { fkVlanRangeInboundTagControl 6 }

                
                -- 1.3.6.1.4.1.10428 9 1.101.3.27.3.2.7
                fkVlanRangeInboundTagControlMinVlanIndex OBJECT-TYPE
                        SYNTAX Integer32 (1..65535)
                        MAX-ACCESS read-write
                        STATUS current
                        DESCRIPTION
                                "Min vlan Index of inner-tag."
                        ::= { fkVlanRangeInboundTagControl 7 }

                
                -- 1.3.6.1.4.1.10428 9 1.101.3.27.3.2.8
                fkVlanRangeInboundTagControlMaxVlanIndex OBJECT-TYPE
                        SYNTAX Integer32 (1..65535)
                        MAX-ACCESS read-write
                        STATUS current
                        DESCRIPTION
                                "Max vlan Index of inner-tag."
                        ::= { fkVlanRangeInboundTagControl 8 }

                
                -- 1.3.6.1.4.1.10428 9 1.101.3.27.3.2.9
                fkVlanRangeInboundTagControlOuterVid OBJECT-TYPE
                        SYNTAX Integer32 (1..65535)
                        MAX-ACCESS read-write
                        STATUS current
                        DESCRIPTION
                                "The Outer Vlan-ID to tag for incoming packet with vlan index."
                        ::= { fkVlanRangeInboundTagControl 9 }

                
                -- 1.3.6.1.4.1.10428 9 1.101.3.27.3.3
                fkVlanRangeInboundTagNotification OBJECT IDENTIFIER ::= { fkVlanRangeInboundTag 3 }

                
                -- 1.3.6.1.4.1.10428 9 1.101.3.27.3.3.1
                fkVlanRangeInboundTagChanged NOTIFICATION-TYPE
                        OBJECTS { fkVlanRangeInboundTagControlRequest, fkVlanRangeInboundTagControlTimeStamp, fkVlanRangeInboundTagControlReqResult, fkVlanRangeInboundTagControlPortIndex, fkVlanRangeInboundTagControlMinVlanIndex, 
                                fkVlanRangeInboundTagControlMaxVlanIndex, fkVlanRangeInboundTagControlOuterVid }
                        STATUS current
                        DESCRIPTION 
                                "Description."
                        ::= { fkVlanRangeInboundTagNotification 1 }

                
                -- 1.3.6.1.4.1.10428 9 1.101.3.27.3.3.2
                fkVlanRangeInboundTagCleared NOTIFICATION-TYPE
                        OBJECTS { fkVlanRangeInboundTagControlRequest, fkVlanRangeInboundTagControlTimeStamp, fkVlanRangeInboundTagControlReqResult, fkVlanRangeInboundTagControlPortIndex, fkVlanRangeInboundTagControlMinVlanIndex, 
                                fkVlanRangeInboundTagControlMaxVlanIndex }
                        STATUS current
                        DESCRIPTION 
                                "Description."
                        ::= { fkVlanRangeInboundTagNotification 2 }

                
                -- 1.3.6.1.4.1.10428 9 1.101.3.27.4
                fkVlanProtoId OBJECT IDENTIFIER ::= { fkVlanTag 4 }

                
                -- 1.3.6.1.4.1.10428 9 1.101.3.27.4.1
                fkVlanProtoIdTable OBJECT-TYPE
                        SYNTAX SEQUENCE OF FkVlanProtoIdEntry
                        MAX-ACCESS not-accessible
                        STATUS current
                        DESCRIPTION
                                "vlan proto id table"
                        ::= { fkVlanProtoId 1 }

                
                -- 1.3.6.1.4.1.10428 9 1.101.3.27.4.1.1
                fkVlanProtoIdEntry OBJECT-TYPE
                        SYNTAX FkVlanProtoIdEntry
                        MAX-ACCESS not-accessible
                        STATUS current
                        DESCRIPTION
                                "key: fkVlanProtoIdVid"
                        INDEX { fkVlanProtoIdVid }
                        ::= { fkVlanProtoIdTable 1 }

                
                FkVlanProtoIdEntry ::=
                        SEQUENCE { 
                                fkVlanProtoIdVid
                                        Integer32,
                                fkVlanProtoIdOuterProtoId
                                        INTEGER
                         }

                -- 1.3.6.1.4.1.10428 9 1.101.3.27.4.1.1.1
                fkVlanProtoIdVid OBJECT-TYPE
                        SYNTAX Integer32 (0..65535)
                        MAX-ACCESS read-only
                        STATUS current
                        DESCRIPTION
                                "The Vlan ID."
                        ::= { fkVlanProtoIdEntry 1 }

                
                -- 1.3.6.1.4.1.10428 9 1.101.3.27.4.1.1.2
                fkVlanProtoIdOuterProtoId OBJECT-TYPE
                        SYNTAX INTEGER
                                {
                                dtag8100(33024),
                                dtag9100(37120)
                                }
                        MAX-ACCESS read-only
                        STATUS current
                        DESCRIPTION
                                "programmable outer Double Tag Protocol Identifier."
                        ::= { fkVlanProtoIdEntry 2 }

                
                -- 1.3.6.1.4.1.10428 9 1.101.3.27.4.2
                fkVlanProtoIdControl OBJECT IDENTIFIER ::= { fkVlanProtoId 2 }

                
                -- 1.3.6.1.4.1.10428 9 1.101.3.27.4.2.1
                fkVlanProtoIdControlRequest OBJECT-TYPE
                        SYNTAX INTEGER { setVlanProtoIdOuterTpid(1) }
                        MAX-ACCESS read-write
                        STATUS current
                        DESCRIPTION
                                "The request of a user command"
                        ::= { fkVlanProtoIdControl 1 }

                
                -- 1.3.6.1.4.1.10428 9 1.101.3.27.4.2.2
                fkVlanProtoIdControlStatus OBJECT-TYPE
                        SYNTAX FkControlStatusType
                        MAX-ACCESS read-only
                        STATUS current
                        DESCRIPTION
                                "The status of user command"
                        ::= { fkVlanProtoIdControl 2 }

                
                -- 1.3.6.1.4.1.10428 9 1.101.3.27.4.2.3
                fkVlanProtoIdControlTimer OBJECT-TYPE
                        SYNTAX Gauge32
                        MAX-ACCESS read-write
                        STATUS current
                        DESCRIPTION
                                "The maximum time for the manager for a long running user command"
                        ::= { fkVlanProtoIdControl 3 }

                
                -- 1.3.6.1.4.1.10428 9 1.101.3.27.4.2.4
                fkVlanProtoIdControlTimeStamp OBJECT-TYPE
                        SYNTAX TimeTicks
                        MAX-ACCESS read-only
                        STATUS current
                        DESCRIPTION
                                "The time stamp of the last command(end of command)"
                        ::= { fkVlanProtoIdControl 4 }

                
                -- 1.3.6.1.4.1.10428 9 1.101.3.27.4.2.5
                fkVlanProtoIdControlReqResult OBJECT-TYPE
                        SYNTAX FkControlRequestResultType
                        MAX-ACCESS read-only
                        STATUS current
                        DESCRIPTION
                                "The result of the last user command"
                        ::= { fkVlanProtoIdControl 5 }

                
                -- 1.3.6.1.4.1.10428 9 1.101.3.27.4.2.6
                fkVlanProtoIdControlVid OBJECT-TYPE
                        SYNTAX Integer32
                        MAX-ACCESS read-write
                        STATUS current
                        DESCRIPTION
                                "The Vlan Index."
                        ::= { fkVlanProtoIdControl 6 }

                
                -- 1.3.6.1.4.1.10428 9 1.101.3.27.4.2.7
                fkVlanProtoIdControlOuterProtoId OBJECT-TYPE
                        SYNTAX Integer32
                        MAX-ACCESS read-write
                        STATUS current
                        DESCRIPTION
                                "The programmable outer Double Tag Protocol Identifier"
                        ::= { fkVlanProtoIdControl 7 }

                
                -- 1.3.6.1.4.1.10428 9 1.101.3.27.4.3
                fkVlanProtoIdNotification OBJECT IDENTIFIER ::= { fkVlanProtoId 3 }

                
                -- 1.3.6.1.4.1.10428 9 1.101.3.27.4.3.1
                fkVlanProtoIdOuterProtoIdChanged NOTIFICATION-TYPE
                        OBJECTS { fkVlanProtoIdControlRequest, fkVlanProtoIdControlTimeStamp, fkVlanProtoIdControlReqResult, fkVlanProtoIdControlVid, fkVlanProtoIdControlOuterProtoId
                                 }
                        STATUS current
                        DESCRIPTION 
                                "Description."
                        ::= { fkVlanProtoIdNotification 1 }

                
                -- 1.3.6.1.4.1.10428 9 1.101.3.28
                fkVlanMapping OBJECT IDENTIFIER ::= { fkBridge 28 }

                
                -- 1.3.6.1.4.1.10428 9 1.101.3.28.1
                fkVlanMappingTable OBJECT-TYPE
                        SYNTAX SEQUENCE OF FkVlanMappingEntry
                        MAX-ACCESS not-accessible
                        STATUS current
                        DESCRIPTION
                                "vlan mapping table"
                        ::= { fkVlanMapping 1 }

                
                -- 1.3.6.1.4.1.10428 9 1.101.3.28.1.1
                fkVlanMappingEntry OBJECT-TYPE
                        SYNTAX FkVlanMappingEntry
                        MAX-ACCESS not-accessible
                        STATUS current
                        DESCRIPTION
                                "key: fkVlanMappingIndex"
                        INDEX { fkVlanMappingIndex }
                        ::= { fkVlanMappingTable 1 }

                
                FkVlanMappingEntry ::=
                        SEQUENCE { 
                                fkVlanMappingIndex
                                        INTEGER,
                                fkVlanMappingPortId
                                        INTEGER,
                                fkVlanMappingOriVlanId
                                        INTEGER,
                                fkVlanMappingTransVlanId
                                        INTEGER,
                                fkVlanMappingMode
                                        INTEGER,
                                fkVlanMappingMatchCos
                                        Integer32,
                                fkVlanMappingMatchDscp
                                        Integer32,
                                fkVlanMappingMatchEthType
                                        INTEGER,
                                fkVlanMappingMatchIPPrecedence
                                        Integer32,
                                fkVlanMappingMatchTos
                                        Integer32,
                                fkVlanMappingRateLimit
                                        INTEGER,
                                fkVlanMappingCos
                                        Integer32,
                                fkVlanMappingDscp
                                        Integer32
                         }

                -- 1.3.6.1.4.1.10428 9 1.101.3.28.1.1.1
                fkVlanMappingIndex OBJECT-TYPE
                        SYNTAX INTEGER (1..65535)
                        MAX-ACCESS read-only
                        STATUS current
                        DESCRIPTION
                                "The Vlan index"
                        ::= { fkVlanMappingEntry 1 }

                
                -- 1.3.6.1.4.1.10428 9 1.101.3.28.1.1.2
                fkVlanMappingPortId OBJECT-TYPE
                        SYNTAX INTEGER (1..65535)
                        MAX-ACCESS read-only
                        STATUS current
                        DESCRIPTION
                                "The port index."
                        ::= { fkVlanMappingEntry 2 }

                
                -- 1.3.6.1.4.1.10428 9 1.101.3.28.1.1.3
                fkVlanMappingOriVlanId OBJECT-TYPE
                        SYNTAX INTEGER (1..4094)
                        MAX-ACCESS read-only
                        STATUS current
                        DESCRIPTION
                                "The original vlan index."
                        ::= { fkVlanMappingEntry 3 }

                
                -- 1.3.6.1.4.1.10428 9 1.101.3.28.1.1.4
                fkVlanMappingTransVlanId OBJECT-TYPE
                        SYNTAX INTEGER (1..4094)
                        MAX-ACCESS read-only
                        STATUS current
                        DESCRIPTION
                                "The translation vlan index"
                        ::= { fkVlanMappingEntry 4 }

                
                -- 1.3.6.1.4.1.10428 9 1.101.3.28.1.1.5
                fkVlanMappingMode OBJECT-TYPE
                        SYNTAX INTEGER
                                {
                                default(0),
                                cos(1),
                                dscp(2),
                                matchCos(3),
                                matchDscp(4),
                                matchEthType(5),
                                matchIpPrecedence(6),
                                matchTos(7),
                                rateLimit(8)
                                }
                        MAX-ACCESS read-only
                        STATUS current
                        DESCRIPTION
                                "The vlan mapping mode configuration"
                        ::= { fkVlanMappingEntry 5 }

                
                -- 1.3.6.1.4.1.10428 9 1.101.3.28.1.1.6
                fkVlanMappingMatchCos OBJECT-TYPE
                        SYNTAX Integer32 (-1 | 0..7)
                        MAX-ACCESS read-only
                        STATUS current
                        DESCRIPTION
                                "The match CoS value"
                        ::= { fkVlanMappingEntry 6 }

                
                -- 1.3.6.1.4.1.10428 9 1.101.3.28.1.1.7
                fkVlanMappingMatchDscp OBJECT-TYPE
                        SYNTAX Integer32 (-1 | 0..63)
                        MAX-ACCESS read-only
                        STATUS current
                        DESCRIPTION
                                "The match DSCP value"
                        ::= { fkVlanMappingEntry 7 }

                
                -- 1.3.6.1.4.1.10428 9 1.101.3.28.1.1.8
                fkVlanMappingMatchEthType OBJECT-TYPE
                        SYNTAX INTEGER (-1 | 1..65535)
                        MAX-ACCESS read-only
                        STATUS current
                        DESCRIPTION
                                "The match Ethernet type value"
                        ::= { fkVlanMappingEntry 8 }

                
                -- 1.3.6.1.4.1.10428 9 1.101.3.28.1.1.9
                fkVlanMappingMatchIPPrecedence OBJECT-TYPE
                        SYNTAX Integer32 (-1 | 0..7)
                        MAX-ACCESS read-only
                        STATUS current
                        DESCRIPTION
                                "The Match IP precedence value"
                        ::= { fkVlanMappingEntry 9 }

                
                -- 1.3.6.1.4.1.10428 9 1.101.3.28.1.1.10
                fkVlanMappingMatchTos OBJECT-TYPE
                        SYNTAX Integer32 (-1 | 0..255)
                        MAX-ACCESS read-only
                        STATUS current
                        DESCRIPTION
                                "The match ToS value"
                        ::= { fkVlanMappingEntry 10 }

                
                -- 1.3.6.1.4.1.10428 9 1.101.3.28.1.1.11
                fkVlanMappingRateLimit OBJECT-TYPE
                        SYNTAX INTEGER (-1 | 1..65535)
                        MAX-ACCESS read-only
                        STATUS current
                        DESCRIPTION
                                "The rate limit value"
                        ::= { fkVlanMappingEntry 11 }

                
                -- 1.3.6.1.4.1.10428 9 1.101.3.28.1.1.12
                fkVlanMappingCos OBJECT-TYPE
                        SYNTAX Integer32 (-1 | 0..7)
                        MAX-ACCESS read-only
                        STATUS current
                        DESCRIPTION
                                "The CoS value"
                        ::= { fkVlanMappingEntry 12 }

                
                -- 1.3.6.1.4.1.10428 9 1.101.3.28.1.1.13
                fkVlanMappingDscp OBJECT-TYPE
                        SYNTAX Integer32 (-1 | 0..63)
                        MAX-ACCESS read-only
                        STATUS current
                        DESCRIPTION
                                "The DSCP value"
                        ::= { fkVlanMappingEntry 13 }

                
                -- 1.3.6.1.4.1.10428 9 1.101.3.28.2
                fkVlanMappingControl OBJECT IDENTIFIER ::= { fkVlanMapping 2 }

                
                -- 1.3.6.1.4.1.10428 9 1.101.3.28.2.1
                fkVlanMappingControlRequest OBJECT-TYPE
                        SYNTAX INTEGER
                                {
                                addVlanMapping(1),
                                delVlanMapping(2)
                                }
                        MAX-ACCESS read-write
                        STATUS current
                        DESCRIPTION
                                "The request of a user command"
                        ::= { fkVlanMappingControl 1 }

                
                -- 1.3.6.1.4.1.10428 9 1.101.3.28.2.2
                fkVlanMappingControlStatus OBJECT-TYPE
                        SYNTAX FkControlStatusType
                        MAX-ACCESS read-write
                        STATUS current
                        DESCRIPTION
                                "The status of user command"
                        ::= { fkVlanMappingControl 2 }

                
                -- 1.3.6.1.4.1.10428 9 1.101.3.28.2.3
                fkVlanMappingControlTimer OBJECT-TYPE
                        SYNTAX Gauge32
                        MAX-ACCESS read-write
                        STATUS current
                        DESCRIPTION
                                "The maximum time for the manager for a long running user command"
                        ::= { fkVlanMappingControl 3 }

                
                -- 1.3.6.1.4.1.10428 9 1.101.3.28.2.4
                fkVlanMappingControlTimeStamp OBJECT-TYPE
                        SYNTAX TimeTicks
                        MAX-ACCESS read-write
                        STATUS current
                        DESCRIPTION
                                "The time stamp of the last command(end of command)"
                        ::= { fkVlanMappingControl 4 }

                
                -- 1.3.6.1.4.1.10428 9 1.101.3.28.2.5
                fkVlanMappingControlReqResult OBJECT-TYPE
                        SYNTAX FkControlRequestResultType
                        MAX-ACCESS read-write
                        STATUS current
                        DESCRIPTION
                                "The result of the last user command"
                        ::= { fkVlanMappingControl 5 }

                
                -- 1.3.6.1.4.1.10428 9 1.101.3.28.2.6
                fkVlanMappingControlIndex OBJECT-TYPE
                        SYNTAX INTEGER (1..65535)
                        MAX-ACCESS read-write
                        STATUS current
                        DESCRIPTION
                                "The Vlan index"
                        ::= { fkVlanMappingControl 6 }

                
                -- 1.3.6.1.4.1.10428 9 1.101.3.28.2.7
                fkVlanMappingControlPortId OBJECT-TYPE
                        SYNTAX INTEGER (1..65535)
                        MAX-ACCESS read-write
                        STATUS current
                        DESCRIPTION
                                "The port index."
                        ::= { fkVlanMappingControl 7 }

                
                -- 1.3.6.1.4.1.10428 9 1.101.3.28.2.8
                fkVlanMappingControlOriVlanId OBJECT-TYPE
                        SYNTAX INTEGER (1..4094)
                        MAX-ACCESS read-write
                        STATUS current
                        DESCRIPTION
                                "The original vlan index."
                        ::= { fkVlanMappingControl 8 }

                
                -- 1.3.6.1.4.1.10428 9 1.101.3.28.2.9
                fkVlanMappingControlTransVlanID OBJECT-TYPE
                        SYNTAX INTEGER (1..4094)
                        MAX-ACCESS read-write
                        STATUS current
                        DESCRIPTION
                                "The translation vlan index"
                        ::= { fkVlanMappingControl 9 }

                
                -- 1.3.6.1.4.1.10428 9 1.101.3.28.2.10
                fkVlanMappingControlMode OBJECT-TYPE
                        SYNTAX INTEGER
                                {
                                default(0),
                                cos(1),
                                dscp(2),
                                matchCos(3),
                                matchDscp(4),
                                matchEthType(5),
                                matchIpPrecedence(6),
                                matchTos(7),
                                rateLimit(8)
                                }
                        MAX-ACCESS read-write
                        STATUS current
                        DESCRIPTION
                                "The vlan mapping mode configuration"
                        ::= { fkVlanMappingControl 10 }

                
                -- 1.3.6.1.4.1.10428 9 1.101.3.28.2.11
                fkVlanMappingControlMatchCos OBJECT-TYPE
                        SYNTAX Integer32 (-1 | 0..7)
                        MAX-ACCESS read-write
                        STATUS current
                        DESCRIPTION
                                "The match CoS value"
                        ::= { fkVlanMappingControl 11 }

                
                -- 1.3.6.1.4.1.10428 9 1.101.3.28.2.12
                fkVlanMappingControlMatchDscp OBJECT-TYPE
                        SYNTAX Integer32 (-1 | 0..63)
                        MAX-ACCESS read-write
                        STATUS current
                        DESCRIPTION
                                "The match DSCP value"
                        ::= { fkVlanMappingControl 12 }

                
                -- 1.3.6.1.4.1.10428 9 1.101.3.28.2.13
                fkVlanMappingControlMatchEthType OBJECT-TYPE
                        SYNTAX INTEGER (-1 | 1..65535)
                        MAX-ACCESS read-write
                        STATUS current
                        DESCRIPTION
                                "The match Ethernet type value"
                        ::= { fkVlanMappingControl 13 }

                
                -- 1.3.6.1.4.1.10428 9 1.101.3.28.2.14
                fkVlanMappingControlMatchIPPrecedence OBJECT-TYPE
                        SYNTAX Integer32 (-1 | 0..7)
                        MAX-ACCESS read-write
                        STATUS current
                        DESCRIPTION
                                "The Match IP precedence value"
                        ::= { fkVlanMappingControl 14 }

                
                -- 1.3.6.1.4.1.10428 9 1.101.3.28.2.15
                fkVlanMappingControlMatchTos OBJECT-TYPE
                        SYNTAX Integer32 (-1 | 0..255)
                        MAX-ACCESS read-write
                        STATUS current
                        DESCRIPTION
                                "The match ToS value"
                        ::= { fkVlanMappingControl 15 }

                
                -- 1.3.6.1.4.1.10428 9 1.101.3.28.2.16
                fkVlanMappingControlRateLimit OBJECT-TYPE
                        SYNTAX INTEGER (-1 | 1..65535)
                        MAX-ACCESS read-write
                        STATUS current
                        DESCRIPTION
                                "The rate limit value"
                        ::= { fkVlanMappingControl 16 }

                
                -- 1.3.6.1.4.1.10428 9 1.101.3.28.2.17
                fkVlanMappingControlCos OBJECT-TYPE
                        SYNTAX Integer32 (-1 | 0..7)
                        MAX-ACCESS read-write
                        STATUS current
                        DESCRIPTION
                                "The CoS value"
                        ::= { fkVlanMappingControl 17 }

                
                -- 1.3.6.1.4.1.10428 9 1.101.3.28.2.18
                fkVlanMappingControlDscp OBJECT-TYPE
                        SYNTAX Integer32 (-1 | 0..255)
                        MAX-ACCESS read-write
                        STATUS current
                        DESCRIPTION
                                "The DSCP value"
                        ::= { fkVlanMappingControl 18 }

                
                -- 1.3.6.1.4.1.10428 9 1.101.3.28.3
                fkVlanMappingNotification OBJECT IDENTIFIER ::= { fkVlanMapping 3 }

                
                -- 1.3.6.1.4.1.10428 9 1.101.3.28.3.1
                fkVlanMappingCreated NOTIFICATION-TYPE
                        OBJECTS { fkVlanMappingControlRequest, fkVlanMappingControlTimeStamp, fkVlanMappingControlReqResult, fkVlanMappingControlPortId, fkVlanMappingControlOriVlanId, 
                                fkVlanMappingControlTransVlanID, fkVlanMappingControlMode, fkVlanMappingControlMatchCos, fkVlanMappingControlMatchDscp, fkVlanMappingControlMatchEthType, 
                                fkVlanMappingControlMatchIPPrecedence, fkVlanMappingControlMatchTos, fkVlanMappingControlRateLimit, fkVlanMappingControlCos, fkVlanMappingControlDscp
                                 }
                        STATUS current
                        DESCRIPTION 
                                "Description."
                        ::= { fkVlanMappingNotification 1 }

                
                -- 1.3.6.1.4.1.10428 9 1.101.3.28.3.2
                fkVlanMappingDeleted NOTIFICATION-TYPE
                        OBJECTS { fkVlanMappingControlRequest, fkVlanMappingControlTimeStamp, fkVlanMappingControlIndex, fkVlanMappingControlReqResult }
                        STATUS current
                        DESCRIPTION 
                                "Description."
                        ::= { fkVlanMappingNotification 2 }

                
                -- 1.3.6.1.4.1.10428 9 1.101.3.29
                fkPowerInline OBJECT IDENTIFIER ::= { fkBridge 29 }

                
                -- 1.3.6.1.4.1.10428 9 1.101.3.29.1
                fkPowerInlineTable OBJECT-TYPE
                        SYNTAX SEQUENCE OF FkPowerInlineEntry
                        MAX-ACCESS not-accessible
                        STATUS current
                        DESCRIPTION
                                "The poe snmp main table"
                        ::= { fkPowerInline 1 }

                
                -- 1.3.6.1.4.1.10428 9 1.101.3.29.1.1
                fkPowerInlineEntry OBJECT-TYPE
                        SYNTAX FkPowerInlineEntry
                        MAX-ACCESS not-accessible
                        STATUS current
                        DESCRIPTION
                                "The poe snmp entry table"
                        INDEX { fkPowerInlinePortIndex }
                        ::= { fkPowerInlineTable 1 }

                
                FkPowerInlineEntry ::=
                        SEQUENCE { 
                                fkPowerInlinePortIndex
                                        INTEGER,
                                fkPowerInlineAdminStatus
                                        INTEGER,
                                fkPowerInlinePortStatus
                                        INTEGER,
                                fkPowerInlineDetectionStatus
                                        INTEGER,
                                fkPowerInlinePortClass
                                        INTEGER,
                                fkPowerInlinePortMaxPow
                                        INTEGER,
                                fkPowerInlinePortLegacy
                                        INTEGER,
                                fkPowerInlinePortPriority
                                        INTEGER,
                                fkPowerInlinePortPower
                                        OCTET STRING,
                                fkPowerInlinePortCurrent
                                        OCTET STRING,
                                fkPowerInlinePortVoltage
                                        OCTET STRING,
                                fkPowerInlinePortTemperture
                                        OCTET STRING
                         }

                -- 1.3.6.1.4.1.10428 9 1.101.3.29.1.1.1
                fkPowerInlinePortIndex OBJECT-TYPE
                        SYNTAX INTEGER (1..65535)
                        MAX-ACCESS read-only
                        STATUS current
                        DESCRIPTION
                                "The number of poe port."
                        ::= { fkPowerInlineEntry 1 }

                
                -- 1.3.6.1.4.1.10428 9 1.101.3.29.1.1.2
                fkPowerInlineAdminStatus OBJECT-TYPE
                        SYNTAX INTEGER
                                {
                                auto(1),
                                static(2),
                                null(3)
                                }
                        MAX-ACCESS read-only
                        STATUS current
                        DESCRIPTION
                                "The poe port Admin status"
                        ::= { fkPowerInlineEntry 2 }

                
                -- 1.3.6.1.4.1.10428 9 1.101.3.29.1.1.3
                fkPowerInlinePortStatus OBJECT-TYPE
                        SYNTAX INTEGER
                                {
                                enable(1),
                                disable(2)
                                }
                        MAX-ACCESS read-only
                        STATUS current
                        DESCRIPTION
                                "The poe port operate status"
                        ::= { fkPowerInlineEntry 3 }

                
                -- 1.3.6.1.4.1.10428 9 1.101.3.29.1.1.4
                fkPowerInlineDetectionStatus OBJECT-TYPE
                        SYNTAX INTEGER
                                {
                                disable(1),
                                searching(2),
                                delivingPower(3),
                                test(4),
                                fault(5),
                                overloadFault(6),
                                requestPower(7)
                                }
                        MAX-ACCESS read-only
                        STATUS current
                        DESCRIPTION
                                "The poe port detection status"
                        ::= { fkPowerInlineEntry 4 }

                
                -- 1.3.6.1.4.1.10428 9 1.101.3.29.1.1.5
                fkPowerInlinePortClass OBJECT-TYPE
                        SYNTAX INTEGER
                                {
                                class0(1),
                                class1(2),
                                class2(3),
                                class3(4)
                                }
                        MAX-ACCESS read-only
                        STATUS current
                        DESCRIPTION
                                "The poe port class type."
                        ::= { fkPowerInlineEntry 5 }

                
                -- 1.3.6.1.4.1.10428 9 1.101.3.29.1.1.6
                fkPowerInlinePortMaxPow OBJECT-TYPE
                        SYNTAX INTEGER (3000..30000)
                        MAX-ACCESS read-only
                        STATUS current
                        DESCRIPTION
                                "The max power value."
                        ::= { fkPowerInlineEntry 6 }

                
                -- 1.3.6.1.4.1.10428 9 1.101.3.29.1.1.7
                fkPowerInlinePortLegacy OBJECT-TYPE
                        SYNTAX INTEGER
                                {
                                enable(1),
                                disable(2)
                                }
                        MAX-ACCESS read-only
                        STATUS current
                        DESCRIPTION
                                "The poe port legacy mode."
                        ::= { fkPowerInlineEntry 7 }

                
                -- 1.3.6.1.4.1.10428 9 1.101.3.29.1.1.8
                fkPowerInlinePortPriority OBJECT-TYPE
                        SYNTAX INTEGER
                                {
                                low(1),
                                medium(2),
                                high(3)
                                }
                        MAX-ACCESS read-only
                        STATUS current
                        DESCRIPTION
                                "The poe port priority level."
                        ::= { fkPowerInlineEntry 8 }

                
                -- 1.3.6.1.4.1.10428 9 1.101.3.29.1.1.9
                fkPowerInlinePortPower OBJECT-TYPE
                        SYNTAX OCTET STRING (SIZE (1..8))
                        MAX-ACCESS read-only
                        STATUS current
                        DESCRIPTION
                                "The poe port detected power."
                        ::= { fkPowerInlineEntry 9 }

                
                -- 1.3.6.1.4.1.10428 9 1.101.3.29.1.1.10
                fkPowerInlinePortCurrent OBJECT-TYPE
                        SYNTAX OCTET STRING (SIZE (1..8))
                        MAX-ACCESS read-only
                        STATUS current
                        DESCRIPTION
                                "The poe port detected current."
                        ::= { fkPowerInlineEntry 10 }

                
                -- 1.3.6.1.4.1.10428 9 1.101.3.29.1.1.11
                fkPowerInlinePortVoltage OBJECT-TYPE
                        SYNTAX OCTET STRING (SIZE (1..8))
                        MAX-ACCESS read-only
                        STATUS current
                        DESCRIPTION
                                "The poe port detected voltage."
                        ::= { fkPowerInlineEntry 11 }

                
                -- 1.3.6.1.4.1.10428 9 1.101.3.29.1.1.12
                fkPowerInlinePortTemperture OBJECT-TYPE
                        SYNTAX OCTET STRING (SIZE (1..8))
                        MAX-ACCESS read-only
                        STATUS current
                        DESCRIPTION
                                "The poe port detected temperture."
                        ::= { fkPowerInlineEntry 12 }

                
                -- 1.3.6.1.4.1.10428 9 1.101.3.29.2
                fkPowerInlineControl OBJECT IDENTIFIER ::= { fkPowerInline 2 }
-- The poe snmp control table
                
                -- 1.3.6.1.4.1.10428 9 1.101.3.29.2.1
                fkPowerInlineControlRequest OBJECT-TYPE
                        SYNTAX INTEGER
                                {
                                setPowerInlineEnable(1),
                                setPowerInlineDisable(2),
                                setPowerInlineReset(3),
                                setPowerInlineLegacy(4),
                                setPowerInlinePriority(5),
                                setPowerInlineClass(6),
                                setPowerInlinePower(7)
                                }
                        MAX-ACCESS read-write
                        STATUS current
                        DESCRIPTION
                                "The poe control request type"
                        ::= { fkPowerInlineControl 1 }

                
                -- 1.3.6.1.4.1.10428 9 1.101.3.29.2.2
                fkPowerInlineControlStatus OBJECT-TYPE
                        SYNTAX FkControlStatusType
                        MAX-ACCESS read-only
                        STATUS current
                        DESCRIPTION
                                "The poe control status type"
                        ::= { fkPowerInlineControl 2 }

                
                -- 1.3.6.1.4.1.10428 9 1.101.3.29.2.3
                fkPowerInlineControlTimer OBJECT-TYPE
                        SYNTAX Gauge32
                        MAX-ACCESS read-write
                        STATUS current
                        DESCRIPTION
                                "The poe control flag"
                        ::= { fkPowerInlineControl 3 }

                
                -- 1.3.6.1.4.1.10428 9 1.101.3.29.2.4
                fkPowerInlineControlTimeStamp OBJECT-TYPE
                        SYNTAX TimeTicks
                        MAX-ACCESS read-only
                        STATUS current
                        DESCRIPTION
                                "The poe control timestamp"
                        ::= { fkPowerInlineControl 4 }

                
                -- 1.3.6.1.4.1.10428 9 1.101.3.29.2.5
                fkPowerInlineControlReqResult OBJECT-TYPE
                        SYNTAX FkControlRequestResultType
                        MAX-ACCESS read-only
                        STATUS current
                        DESCRIPTION
                                "Result of the last command."
                        ::= { fkPowerInlineControl 5 }

                
                -- 1.3.6.1.4.1.10428 9 1.101.3.29.2.6
                fkPowerInlineControlPortIndex OBJECT-TYPE
                        SYNTAX INTEGER (1..65535)
                        MAX-ACCESS read-write
                        STATUS current
                        DESCRIPTION
                                "The Index of poe port."
                        ::= { fkPowerInlineControl 6 }

                
                -- 1.3.6.1.4.1.10428 9 1.101.3.29.2.7
                fkPowerInlineControlAdminStatus OBJECT-TYPE
                        SYNTAX INTEGER
                                {
                                auto(1),
                                static(2),
                                null(3)
                                }
                        MAX-ACCESS read-write
                        STATUS current
                        DESCRIPTION
                                "The poe port admin status"
                        ::= { fkPowerInlineControl 7 }

                
                -- 1.3.6.1.4.1.10428 9 1.101.3.29.2.8
                fkPowerInlineControlPortStatus OBJECT-TYPE
                        SYNTAX INTEGER
                                {
                                enable(1),
                                disable(2)
                                }
                        MAX-ACCESS read-write
                        STATUS current
                        DESCRIPTION
                                "The poe port operate status."
                        ::= { fkPowerInlineControl 8 }

                
                -- 1.3.6.1.4.1.10428 9 1.101.3.29.2.9
                fkPowerInlineControlPortClass OBJECT-TYPE
                        SYNTAX INTEGER
                                {
                                class0(1),
                                class1(2),
                                class2(3),
                                class3(4)
                                }
                        MAX-ACCESS read-write
                        STATUS current
                        DESCRIPTION
                                "The poe port class type."
                        ::= { fkPowerInlineControl 9 }

                
                -- 1.3.6.1.4.1.10428 9 1.101.3.29.2.10
                fkPowerInlineControlPortMaxPower OBJECT-TYPE
                        SYNTAX INTEGER (3000..30000)
                        MAX-ACCESS read-write
                        STATUS current
                        DESCRIPTION
                                "The max power value."
                        ::= { fkPowerInlineControl 10 }

                
                -- 1.3.6.1.4.1.10428 9 1.101.3.29.2.11
                fkPowerInlineControlPortLegacy OBJECT-TYPE
                        SYNTAX INTEGER
                                {
                                enable(1),
                                disable(2)
                                }
                        MAX-ACCESS read-write
                        STATUS current
                        DESCRIPTION
                                "The poe port legacy mode."
                        ::= { fkPowerInlineControl 11 }

                
                -- 1.3.6.1.4.1.10428 9 1.101.3.29.2.12
                fkPowerInlineControlPriority OBJECT-TYPE
                        SYNTAX INTEGER
                                {
                                low(1),
                                medium(2),
                                high(3)
                                }
                        MAX-ACCESS read-write
                        STATUS current
                        DESCRIPTION
                                "The poe port priority level."
                        ::= { fkPowerInlineControl 12 }

                
                -- 1.3.6.1.4.1.10428 9 1.101.3.29.3
                fkPowerInlineNotification OBJECT IDENTIFIER ::= { fkPowerInline 3 }
-- The poe snmp notify table
                
                -- 1.3.6.1.4.1.10428 9 1.101.3.29.3.1
                fkPowerInlineEnableChanged NOTIFICATION-TYPE
                        OBJECTS { fkPowerInlineControlRequest, fkPowerInlineControlTimeStamp, fkPowerInlineControlReqResult, fkPowerInlineControlPortIndex, fkPowerInlineControlPortStatus, 
                                fkPowerInlineControlPortClass, fkPowerInlineControlPortMaxPower, fkPowerInlineControlPortLegacy, fkPowerInlineControlPriority }
                        STATUS current
                        DESCRIPTION 
                                "setPowerInlineEnable"
                        ::= { fkPowerInlineNotification 1 }

                
                -- 1.3.6.1.4.1.10428 9 1.101.3.29.3.2
                fkPowerInlineDisableChanged NOTIFICATION-TYPE
                        OBJECTS { fkPowerInlineControlRequest, fkPowerInlineControlTimeStamp, fkPowerInlineControlReqResult, fkPowerInlineControlPortIndex, fkPowerInlineControlPortStatus
                                 }
                        STATUS current
                        DESCRIPTION 
                                "setPowerInlineDisable"
                        ::= { fkPowerInlineNotification 2 }

                
                -- 1.3.6.1.4.1.10428 9 1.101.3.29.3.3
                fkPowerInlineResetChanged NOTIFICATION-TYPE
                        OBJECTS { fkPowerInlineControlRequest, fkPowerInlineControlTimeStamp, fkPowerInlineControlReqResult, fkPowerInlineControlPortIndex, fkPowerInlineControlPortStatus, 
                                fkPowerInlineControlPortClass, fkPowerInlineControlPortMaxPower, fkPowerInlineControlPortLegacy, fkPowerInlineControlPriority }
                        STATUS current
                        DESCRIPTION 
                                "setPowerInlineReset"
                        ::= { fkPowerInlineNotification 3 }

                
                -- 1.3.6.1.4.1.10428 9 1.101.3.29.3.4
                fkPowerInlineLegacyChanged NOTIFICATION-TYPE
                        OBJECTS { fkPowerInlineControlRequest, fkPowerInlineControlTimeStamp, fkPowerInlineControlReqResult, fkPowerInlineControlPortIndex, fkPowerInlineControlPortStatus, 
                                fkPowerInlineControlPortLegacy }
                        STATUS current
                        DESCRIPTION 
                                "setPowerInlineLegacy"
                        ::= { fkPowerInlineNotification 4 }

                
                -- 1.3.6.1.4.1.10428 9 1.101.3.29.3.5
                fkPowerInlinePriorityChanged NOTIFICATION-TYPE
                        OBJECTS { fkPowerInlineControlRequest, fkPowerInlineControlTimeStamp, fkPowerInlineControlReqResult, fkPowerInlineControlPortIndex, fkPowerInlineControlPortStatus, 
                                fkPowerInlineControlPriority }
                        STATUS current
                        DESCRIPTION 
                                "setPowerInlinePriority"
                        ::= { fkPowerInlineNotification 5 }

                
                -- 1.3.6.1.4.1.10428 9 1.101.3.29.3.6
                fkPowerInlineClassChanged NOTIFICATION-TYPE
                        OBJECTS { fkPowerInlineControlRequest, fkPowerInlineControlTimeStamp, fkPowerInlineControlReqResult, fkPowerInlineControlPortIndex, fkPowerInlineControlPortStatus, 
                                fkPowerInlineControlPortClass }
                        STATUS current
                        DESCRIPTION 
                                "setPowerInlineClass"
                        ::= { fkPowerInlineNotification 6 }

                
                -- 1.3.6.1.4.1.10428 9 1.101.3.29.3.7
                fkPowerInlinePowerChanged NOTIFICATION-TYPE
                        OBJECTS { fkPowerInlineControlRequest, fkPowerInlineControlTimeStamp, fkPowerInlineControlReqResult, fkPowerInlineControlPortIndex, fkPowerInlineControlPortStatus, 
                                fkPowerInlineControlPortClass, fkPowerInlineControlPortMaxPower, fkPowerInlineControlPortLegacy }
                        STATUS current
                        DESCRIPTION 
                                "setPowerInlinePower"
                        ::= { fkPowerInlineNotification 7 }

                
                -- 1.3.6.1.4.1.10428 9 1.101.3.30
                fkBridgeGroup OBJECT-GROUP
                        OBJECTS { fkBridgeMacAddress, fkBridgePortNum, fkBridgeLagMaxId, fkBridgeLacpActivity, fkBridgeLacpPriority, 
                                fkBridgeVlanSupportMode, fkBridgeVlanMaxNum, fkBridgeDoubleTagProtoId, fkBridgeMirrorMode, fkBridgeMirrorMonitorPortId, 
                                fkBridgeMirroredIngressPorts, fkBridgeMirroredEgressPorts, fkBridgeMaxLearnPerUnit, fkBridgeFdbAgeingTime, fkBridgeFdbMaxEntries, 
                                fkBridgeFdbCurrentEntries, fkBridgeStackMode, fkBridgeStackDeviceName, fkBridgeStackNodeId, fkBridgeLldpMessageTxInterval, 
                                fkBridgeLldpTxHoldMultiplier, fkBridgeLldpReinitDelay, fkBridgeLldpTxDelay, fkBridgeLldpNotificationInterval, fkBridgeLldpStatsRemTablesLastChangeTime, 
                                fkBridgeLldpStatsRemTablesInserts, fkBridgeLldpStatsRemTablesDeletes, fkBridgeLldpStatsRemTablesDrops, fkBridgeLldpStatsRemTablesAgeouts, fkBridgeLldpLocalChassisIdSubtype, 
                                fkBridgeLldpLocalChassisId, fkBridgeLldpLocalSysName, fkBridgeLldpLocalSysDes, fkBridgeLldpLocalSysCapSupported, fkBridgeLldpLocalSysCapEnabled, 
                                fkBridgeStpActivity, fkBridgeStpSelfLoop, fkBridgePvlanOnePromPortEnable, fkBridgeTcpSyncookie, fkBridgeTcpIgnoreRstUnknown, 
                                fkBridgeControlRequest, fkBridgeControlStatus, fkBridgeControlTimer, fkBridgeControlTimeStamp, fkBridgeControlReqResult, 
                                fkBridgeControlLacpActivity, fkBridgeControlLacpPriority, fkBridgeControlDoubleTagProtoId, fkBridgeControlMirrorMode, fkBridgeControlMirrorMonitorPortId, 
                                fkBridgeControlMaxLearnPerUnit, fkBridgeControlFdbAgeingTime, fkBridgeControlStackMode, fkBridgeControlStackDeviceName, fkBridgeControlLldpMessageTxInterval, 
                                fkBridgeControlLldpTxHoldMultiplier, fkBridgeControlLldpReinitDelay, fkBridgeControlLldpTxDelay, fkBridgeControlLldpNotificationInterval, fkBridgeControlStpActivity, 
                                fkBridgeControlStpSelfLoop, fkBridgeControlTcpSyncookie, fkBridgeControlTcpIgnoreRstUnknown, fkBridgePortIndex, fkBridgePortIfIndex, 
                                fkBridgePortPVid, fkBridgePortMaxHosts, fkBridgePortCurrentHosts, fkBridgePortMaxLearnPerUnit, fkBridgePortMACFilterPermission, 
                                fkBridgePortIngMirrorStatus, fkBridgePortEgMirrorStatus, fkBridgePortBcastThreshold, fkBridgePortMcastThreshold, fkBridgePortDlfThreshold, 
                                fkBridgePortQinQStatus, fkBridgePortAdminLinktype, fkBridgePortAdminEdgemode, fkBridgePortOperLinktype, fkBridgePortOperEdgemode, 
                                fkBridgePortStpBpduFilter, fkBridgePortPvlanIsolatedStatus, fkBridgePortPvlanPromPorts, fkBridgePortControlRequest, fkBridgePortControlStatus, 
                                fkBridgePortControlTimer, fkBridgePortControlTimeStamp, fkBridgePortControlReqResult, fkBridgePortControlIndex, fkBridgePortControlPVid, 
                                fkBridgePortControlMaxHosts, fkBridgePortControlMaxLearnPerUnit, fkBridgePortControlMACFilterPermission, fkBridgePortControlIngMirrorStatus, fkBridgePortControlEgMirrorStatus, 
                                fkBridgePortControlBcastThreshold, fkBridgePortControlMcastThreshold, fkBridgePortControlDlfThreshold, fkBridgePortControlQinQStatus, fkBridgePortControlAdminLinktype, 
                                fkBridgePortControlAdminEdgemode, fkBridgePortControlStpBpduFilter, fkBridgePortControlPvlanIsolatedStatus, fkBridgePortControlPvlanPromPort, fkBridgePortControlStpBpduGuardErrRcv, 
                                fkVlanIndex, fkVlanIfIndex, fkVlanName, fkVlanStatus, fkVlanEgressPorts, 
                                fkVlanUnTaggedPorts, fkVlanCreationTime, fkVlanAgeingTime, fkVlanControlRequest, fkVlanControlStatus, 
                                fkVlanControlTimer, fkVlanControlTimeStamp, fkVlanControlReqResult, fkVlanControlIndex, fkVlanControlName, 
                                fkVlanControlEgressPorts, fkVlanControlUnTaggedPorts, fkVlanControlAgeingTime, fkVlanMapFid, fkVlanMapStpId, 
                                fkVlanMapErpDomainId, fkVlanMapControlRequest, fkVlanMapControlStatus, fkVlanMapControlTimer, fkVlanMapControlTimeStamp, 
                                fkVlanMapControlReqResult, fkVlanMapControlIndex, fkVlanMapControlFid, fkVlanMapControlStpId, fkVlanMapControlErpDomainId, 
                                fkStpOperationMode, fkStpFormatSelector, fkStpConfigureName, fkStpRevisionLevel, fkStpFwdDelay, 
                                fkStpHelloTime, fkStpMaxAge, fkStpMaxHops, fkStpExtRootBridgeId, fkStpExtPathcost, 
                                fkStpBpduGuardMode, fkStpBpduGuardAutoRcvMode, fkStpBpduGuardAutoRcvTime, fkStpControlRequest, fkStpControlStatus, 
                                fkStpControlTimer, fkStpControlTimeStamp, fkStpControlReqResult, fkStpControlOperationMode, fkStpControlConfigureName, 
                                fkStpControlRevisionLevel, fkStpControlFwdDelay, fkStpControlHelloTime, fkStpControlMaxAge, fkStpControlMaxHops, 
                                fkStpControlBpduGuardMode, fkStpControlBpduGuardAutoRcvMode, fkStpControlBpduGuardAutoRcvTime, fkStpInstanceIndex, fkStpInstanceEnable, 
                                fkStpInstancePriority, fkStpInstanceRootBridgeId, fkStpInstanceRootPathcost, fkStpInstanceDesignatedBridgeId, fkStpInstanceDesignatedPortId, 
                                fkStpInstanceRootPortId, fkStpInstanceFwdDelay, fkStpInstanceHelloTime, fkStpInstanceMaxAge, fkStpInstanceRemainHops, 
                                fkStpInstanceBrFwdDelay, fkStpInstanceBrHelloTime, fkStpInstanceBrMaxAge, fkStpInstanceControlRequest, fkStpInstanceControlStatus, 
                                fkStpInstanceControlTimer, fkStpInstanceControlTimeStamp, fkStpInstanceControlReqResult, fkStpInstanceControlIndex, fkStpInstanceControlEnable, 
                                fkStpInstanceControlPriority, fkStpInstanceControlBrFwdDelay, fkStpInstanceControlBrHelloTime, fkStpInstanceControlBrMaxAge, fkStpInstancePortIndex, 
                                fkStpInstancePortPathcost, fkStpInstancePortPriority, fkStpInstancePortRole, fkStpInstancePortState, fkStpInstancePortRootBridgeId, 
                                fkStpInstancePortRootPathcost, fkStpInstancePortDesignateBridgeId, fkStpInstancePortDesignatePortId, fkStpInstancePortRootGuardMode, fkStpInstancePortControlRequest, 
                                fkStpInstancePortControlStatus, fkStpInstancePortControlTimer, fkStpInstancePortControlTimeStamp, fkStpInstancePortControlReqResult, fkStpInstancePortControlIndex, 
                                fkStpInstancePortControlInstanceId, fkStpInstancePortControlPathcost, fkStpInstancePortControlPriority, fkStpInstancePortControlRootGuardMode, fkSubnetVlanIp, 
                                fkSubnetVlanMask, fkSubnetVlanVid, fkSubnetVlanControlRequest, fkSubnetVlanControlStatus, fkSubnetVlanControlTimer, 
                                fkSubnetVlanControlTimeStamp, fkSubnetVlanControlReqResult, fkSubnetVlanControlIp, fkSubnetVlanControlMask, fkSubnetVlanControlVid, 
                                fkProtocolVlanEtype, fkProtocolVlanVid, fkProtocolVlanControlRequest, fkProtocolVlanControlStatus, fkProtocolVlanControlTimer, 
                                fkProtocolVlanControlTimeStamp, fkProtocolVlanControlReqResult, fkProtocolVlanControlPortIndex, fkProtocolVlanControlEtype, fkProtocolVlanControlVid, 
                                fkLagIndex, fkLagPortId, fkLagDistMode, fkLagPortMap, fkLagMode, 
                                fkLagControlRequest, fkLagControlStatus, fkLagControlTimer, fkLagControlTimeStamp, fkLagControlReqResult, 
                                fkLagControlIndex, fkLagControlDistMode, fkLagControlPortMap, fkLagControlMode, fkLagLacpIndex, 
                                fkLagLacpActorAggregatorKey, fkLagLacpActorSystemMAC, fkLagLacpPartnerSystemMAC, fkLagLacpPartnerSystemPriority, fkLagLacpPartnerAggregatorKey, 
                                fkLagLacpPortIndex, fkLagLacpPortActivity, fkLagLacpPortActorPriority, fkLagLacpPortActorAggregatorId, fkLagLacpPortActorAdminKey, 
                                fkLagLacpPortActorAdminState, fkLagLacpPortActorOperKey, fkLagLacpPortActorOperState, fkLagLacpPortPartnerAdminSystemMAC, fkLagLacpPortPartnerAdminSystemPriority, 
                                fkLagLacpPortPartnerAdminKey, fkLagLacpPortPartnerAdminNum, fkLagLacpPortPartnerAdminPriority, fkLagLacpPortPartnerAdminState, fkLagLacpPortPartnerOperSystemMAC, 
                                fkLagLacpPortPartnerOperSystemPriority, fkLagLacpPortPartnerOperKey, fkLagLacpPortPartnerOperNum, fkLagLacpPortPartnerOperPriority, fkLagLacpPortPartnerOperState, 
                                fkLagLacpPortControlRequest, fkLagLacpPortControlStatus, fkLagLacpPortControlTimer, fkLagLacpPortControlTimeStamp, fkLagLacpPortControlReqResult, 
                                fkLagLacpPortControlIndex, fkLagLacpPortControlActivity, fkLagLacpPortControlMode, fkLagLacpPortControlAdminKey, fkLagLacpPortControlAggregation, 
                                fkLagLacpPortControlPriority, fkLagLacpPortControlTimeout, fkFdbEntryFid, fkFdbEntryPort, fkFdbEntryMacAddress, 
                                fkFdbEntryVid, fkFdbEntryMode, fkFdbEntryPermission, fkFdbEntryElapsedTime, fkFdbEntryControlRequest, 
                                fkFdbEntryControlStatus, fkFdbEntryControlTimer, fkFdbEntryControlTImeStamp, fkFdbEntryControlReqResult, fkFdbEntryControlFid, 
                                fkFdbEntryControlPort, fkFdbEntryControlMacAddress, fkMfdbMacAddress, fkMfdbEntryPermission, fkMfdbVlanIndex, 
                                fkMfdbPorts, fkMfdbControlRequest, fkMfdbControlStatus, fkMfdbControlTimer, fkMfdbControlTimeStamp, 
                                fkMfdbControlReqResult, fkMfdbControlMacAddress, fkMfdbControlEntryPermission, fkMfdbControlVlanIndex, fkMfdbControlPorts, 
                                fkIgmpConfVlanIndex, fkIgmpConfEnable, fkIgmpConfMulticastFilter, fkIgmpConfOutmostVlan, fkIgmpConfSnoopEnable, 
                                fkIgmpConfSnoopJoinDelay, fkIgmpConfSnoopQueryDelay, fkIgmpConfSnoopMrouter, fkIgmpConfSnoopFastLeave, fkIgmpConfSnoopQuerier, 
                                fkIgmpConfControlRequest, fkIgmpConfControlStatus, fkIgmpConfControlTimer, fkIgmpConfControlReqResult, fkIgmpConfControlTimeStamp, 
                                fkIgmpConfControlVlanIndex, fkIgmpConfControlEnable, fkIgmpConfControlMulticastFilter, fkIgmpConfControlOutmostVlan, fkIgmpConfControlSnoopEnable, 
                                fkIgmpConfControlSnoopJoinDelay, fkIgmpConfControlSnoopQueryDelay, fkIgmpConfControlSnoopMrouter, fkIgmpConfControlSnoopFastLeave, fkIgmpConfControlSnoopQuerier, 
                                fkIgmpMcastVlanIndex, fkIgmpMcastIPAddress, fkIgmpMcastPortIndex, fkIgmpMcastType, fkIgmpMcastExpireTime, 
                                fkIgmpMcastControlRequest, fkIgmpMcastControlStatus, fkIgmpMcastControlTimer, fkIgmpMcastControlTimeStamp, fkIgmpMcastControlReqResult, 
                                fkIgmpMcastControlVlanIndex, fkIgmpMcastControlIPAddress, fkIgmpMcastControlPortIndex, fkStackDeviceMacAddress, fkStackDeviceNodeId, 
                                fkStackDeviceDescriptor, fkStackDeviceMode, fkStackDeviceStatus, fkStackDeviceType, fkStackDeviceHostName, 
                                fkStackDevicePortNum, fkStackDeviceControlRequest, fkStackDeviceControlStatus, fkStackDeviceControlTimer, fkStackDeviceControlTImeStamp, 
                                fkStackDeviceControlReqResult, fkStackDeviceControlMacAddress, fkStackDeviceControlDescriptor, fkErpDomainIndex, fkErpDomainName, 
                                fkErpDomainPrimaryPort, fkErpDomainSecondaryPort, fkErpDomainBridgeRole, fkErpDomainProtectionActivation, fkErpDomainOperatorRequest, 
                                fkErpDomainWaitToRestoreTime, fkErpDomainTestPacketInterval, fkErpDomainLearningDisabledTime, fkErpDomainNodeStatus, fkErpDomainRingStatus, 
                                fkErpDomainLotp, fkErpDomainULotp, fkErpDomainMultipleRM, fkErpDomainRMNodeReacheablility, fkErpDomainControlRequest, 
                                fkErpDomainControlStatus, fkErpDomainControlTimer, fkErpDomainControlTImeStamp, fkErpDomainControlReqResult, fkErpDomainControlIndex, 
                                fkErpDomainControlName, fkErpDomainControlPrimaryPort, fkErpDomainControlSecondaryPort, fkErpDomainControlBridgeRole, fkErpDomainControlProtectionActivation, 
                                fkErpDomainControlOperatorRequest, fkErpDomainControlWaitToRestoreTime, fkErpDomainControlTestPacketInterval, fkErpDomainControlLearningDisabledTime, fkLldpPortIndex, 
                                fkLldpPortActivity, fkLldpPortAdminStatus, fkLldpPortNotificationEnable, fkLldpPortTLVsTxEnable, fkLldpPortMgmtTxEnable, 
                                fkLldpPortMgmtAddress, fkLldpPortControlRequest, fkLldpPortControlStatus, fkLldpPortControlTimer, fkLldpPortControlTimeStamp, 
                                fkLldpPortControlReqResult, fkLldpPortControlIndex, fkLldpPortControlActivity, fkLldpPortControlAdminstatus, fkLldpPortControlNotificationEnable, 
                                fkLldpPortControlTLVsTxEnable, fkLldpPortControlMgmtTxEnable, fkLldpPortControlMgmtAddress, fkLldpRemIndex, fkLldpRemTimeMark, 
                                fkLldpRemChassisIdSubtype, fkLldpRemChassisId, fkLldpRemPortIdSubtype, fkLldpRemPortId, fkLldpRemPortDesc, 
                                fkLldpRemSysName, fkLldpRemSysDesc, fkLldpRemSysCapSupported, fkLldpRemSysCapEnabled, fkLldpStatsTxPortFramesTotal, 
                                fkLldpStatsRxPortFramesDiscardedTotal, fkLldpStatsRxPortFramesErrors, fkLldpStatsRxPortFramesTotal, fkLldpStatsRxPortTLVsDiscardedTotal, fkLldpStatsRxPortTLVsUnrecognizedTotal, 
                                fkLldpStatsRxPortAgeoutsTotal, fkLldpStatsControlRequest, fkLldpStatsControlStatus, fkLldpStatsControlTimer, fkLldpStatsControlTimeStamp, 
                                fkLldpStatsControlReqResult, fkLldpStatsControlPortIndex, fkBridgePSIndex, fkBridgePSStatus, fkBridgePSMaxCount, 
                                fkBridgePSCurrCount, fkBridgePSAgingType, fkBridgePSAgingTimer, fkBridgePSAgingStatic, fkBridgePSViolation, 
                                fkBridgePSControlRequest, fkBridgePSControlStatus, fkBridgePSControlTimer, fkBridgePSControlTimeStamp, fkBridgePSControlReqResult, 
                                fkBridgePSControlIndex, fkBridgePSControlPSStatus, fkBridgePSControlMaxCount, fkBridgePSControlAgingType, fkBridgePSControlAgingTimer, 
                                fkBridgePSControlAgingStatic, fkBridgePScontrolViolation, fkBridgePSFdbPort, fkBridgePSFdbVid, fkBridgePSFdbMacAddress, 
                                fkBridgePSFdbMode, fkBridgePSFdbElapsedTime, fkBridgePSFdbControlRequest, fkBridgePSFdbControlStatus, fkBridgePSFdbControlTimer, 
                                fkBridgePSFdbControlTimeStamp, fkBridgePSFdbControlReqResult, fkBridgePSFdbControlPort, fkBridgePSFdbControlVid, fkErpDomainControlRingPriority, 
                                fkErpDomainHoldOffTime, fkErpDomainRingPriority, fkErpDomainControlHoldOffTime, fkErpDomainControlLotp, fkErpDomainControlULotp, 
                                fkErpDomainControlMultipleRM, fkErpDomainControlRMNodeReacheablility, fkBridgeFGBaseControlRequest, fkBridgeFGBaseSfgdEnabled, fkBridgeFGBaseMfgdEnabled, 
                                fkBridgeFGBaseCfgdEnabled, fkBridgePSFdbControlMacAddress, fkBridgePortDhcpFilterServer, fkBridgePortControlDhcpFilterServer, fkBridgeFGBaseControlStatus, 
                                fkBridgeFGBaseControlTimer, fkBridgeFGBaseControlTimeStamp, fkBridgeFGBaseControlReqResult, fkBridgeFGBaseControlCfgdEnable, fkBridgeFGBaseControlSfgdEnable, 
                                fkBridgeFGPortControlRequest, fkBridgeFGPortControlStatus, fkBridgeFGPortControlTimer, fkBridgeFGPortControlTimeStamp, fkBridgeFGPortControlReqResult, 
                                fkBridgeFGPortControlIndex, fkBridgeFGPortType, fkBridgeFGPortFrame, fkBridgeFGPortBlocked, fkBridgeFGPortTimer, 
                                fkBridgeFGPortControlFrame, fkBridgeFGPortFrameType, fkBridgeFGPortControlBlock, fkBridgeAutoInterfaceActivation, fkBridgeControlAutoInterfaceActivation, 
                                fkBridgeLoopDetectStatus, fkBridgeLoopDetectPacketType, fkBridgeControlLoopDetectStatus, fkBridgeControlLoopDetectPacketType, fkBridgePortLoopDetectStatus, 
                                fkBridgePortLoopDetectBlock, fkBridgePortLoopDetectPeriod, fkBridgePortLoopDetectTimer, fkBridgePortLoopDetectBlockStatus, fkBridgePortControlLoopDetectStatus, 
                                fkBridgePortControlLoopDetectBlock, fkBridgePortControlLoopDetectPeriod, fkBridgePortControlLoopDetectTimer, fkBridgePvlanPromSelectMode, fkBridgePvlanPromiscuousPorts, 
                                fkBridgeControlPvlanPromSelectMode, fkBridgeControlPvlanPromiscuousPorts, fkBridgeVTServiceId, fkBridgeVTSubscriberId, fkBridgeVTRuleMac, 
                                fkBridgeVTRuleVid, fkBridgeVTRuleRDirVid, fkBridgeVTRuleRDirPort, fkBridgeVTRuleStatus, fkBridgeVTControlRequest, 
                                fkBridgeVTControlStatus, fkBridgeVTControlTimer, fkBridgeVTControlTimeStamp, fkBridgeVTControlServerId, fkBridgeVTControlClientId, 
                                fkBridgeGvrpStatus, fkBridgeGmrpStatus, fkBridgeGarpTimerJoin, fkBridgeGarpTimerLeave, fkBridgeGarpTimerLeaveAll, 
                                fkBridgeGarpBaseControlRequest, fkBridgeGarpBaseControlStatus, fkBridgeGarpBaseControlTimer, fkBridgeGarpBaseControlTimeStamp, fkBridgeGarpBaseControlReqResult, 
                                fkBridgeGarpBaseControlGvrpStatus, fkBridgeGarpBaseControlGmrpStatus, fkBridgeGarpBaseControlTimerJoin, fkBridgeGarpBaseControlTimerLeave, fkBridgeGarpBaseControlTimerLeaveAll, 
                                fkBridgeGarpAppPortIndex, fkBridgeGarpAppPortType, fkBridgeGarpAppPortStatus, fkBridgeGarpAppPortFailedRegistrations, fkBridgeGarpAppPortLastPduOrigin, 
                                fkBridgeGarpAppPortRegistration, fkBridgeGarpAppPortApplicant, fkBridgeGarpAppPortFwdAll, fkBridgeGarpAppPortTimerJoin, fkBridgeGarpAppPortTimerLeave, 
                                fkBridgeGarpAppPortTimerLeaveAll, fkBridgeGarpAppPortControlRequest, fkBridgeGarpAppPortControlStatus, fkBridgeGarpAppPortControlTimer, fkBridgeGarpAppPortControlTimeStamp, 
                                fkBridgeGarpAppPortControlReqResult, fkBridgeGarpAppPortControlIndex, fkBridgeGarpAppPortControlType, fkBridgeGarpAppPortControlPortStatus, fkBridgeGarpAppPortControlRegistration, 
                                fkBridgeGarpAppPortControlApplicant, fkBridgeGarpAppPortControlFwdAll, fkBridgeGarpAppPortControlTimerJoin, fkBridgeGarpAppPortControlTimerLeave, fkBridgeGarpAppPortControlTimerLeaveAll, 
                                fkBridgeGarpStatsJoinEmptyReceived, fkBridgeGarpStatsJoinInReceived, fkBridgeGarpStatsLeaveInReceived, fkBridgeGarpStatsLeaveEmptyReceived, fkBridgeGarpStatsLeaveAllReceived, 
                                fkBridgeGarpStatsJoinInTransmitted, fkBridgeGarpStatsEmptyTransmitted, fkBridgeGarpStatsLeaveInTransmitted, fkBridgeGarpStatsLeaveEmptyTransmitted, fkBridgeGarpStatsControlRequest, 
                                fkBridgeGarpStatstControlStatus, fkBridgeGarpStatsControlTimer, fkBridgeGarpStatsControlTimeStamp, fkBridgeGarpStatsControlReqResult, fkBridgeGarpStatsControlIndex, 
                                fkBridgeGarpStatsControlType, fkBridgeGmrpStaticVid, fkBridgeGmrpStaticPort, fkBridgeGmrpStaticGmac, fkBridgeGmrpStaticControlRequest, 
                                fkBridgeGmrpStaticControlStatus, fkBridgeGmrpStaticControlTimer, fkBridgeGmrpStaticControlTimeStamp, fkBridgeGmrpStaticControlReqResult, fkBridgeGmrpStaticControlVid, 
                                fkBridgeGmrpStaticControlPort, fkBridgeGmrpStaticControlGmac, fkBridgePortNetBIOSFilter, fkBridgePortControlNetBIOSFilter, fkBridgePortPopInnertag, 
                                fkBridgePortInnertag, fkBridgePortPriority, fkBridgePortControlPushInnertag, fkBridgePortControlPopInnertag, fkBridgePortControlInnertag, 
                                fkBridgePortControlPriority, fkBridgePortPushInnertag, fkVlanInboundTagPortIndex, fkVlanInboundTagVlanIndex, fkVlanInboundTagOuterVid, 
                                fkVlanInboundTagControlRequest, fkVlanInboundTagControlStatus, fkVlanInboundTagControlTimer, fkVlanInboundTagControlTimeStamp, fkVlanInboundTagControlReqResult, 
                                fkVlanInboundTagControlPortIndex, fkVlanInboundTagControlVlanIndex, fkVlanInboundTagControlOuterVid, fkVlanOutboundTagPortIndex, fkVlanOutboundTagControlRequest, 
                                fkVlanOutboundTagControlStatus, fkVlanOutboundTagControlTimer, fkVlanOutboundTagControlTimeStamp, fkVlanOutboundTagControlReqResult, fkVlanOutboundTagControlPortIndex, 
                                fkVlanOutboundTagControlOuterVid, fkVlanOutboundTagVlanIndex, fkBridgePortInner2outerVid, fkBridgePortInner2outerPri, fkBridgeFGPortControlFrameType, 
                                fkBridgeFGPortControlType, fkBridgeFGPortControlSetTimer, fkBridgeGarpStatsEmptyReceived, fkBridgeGarpStatsJoinEmptyTransmitted, fkIgmpMcastCounterInfoGroupCount, 
                                fkIgmpMcastCounterInfoSnoopingCount, fkMcastMrouteJoinedCount, fkBridgePortLinkUpCnt, fkBridgePortLinkDownCnt, fkBridgePortLinkUpTime, 
                                fkBridgePortElapsedTimeAfterClearStats, fkVlanTagTxCounter, fkBridgePortMACLearningStatus, fkBridgePortPortBridgeStatus, fkBridgePortControlMACLearningStatus, 
                                fkBridgePortControlPortBridgeStatus, fkBridgeInBoundVTPortIndex, fkBridgeInBoundVTNewVid, fkBridgeInBoundVTControlRequest, fkBridgeInBoundVTControlStatus, 
                                fkBridgeInBoundVTControlTimer, fkBridgeInBoundVTControlTimeStamp, fkBridgeInBoundVTControlReqResult, fkBridgeInBoundVTControlPortIndex, fkBridgeInBoundVTControlNewVid, 
                                fkBridgeGarpStatsLeaveAllTransmitted, fkBridgePortControlInner2outerPri, fkBridgeInBoundVTVlanIndex, fkBridgeInBoundVTOperStatus, fkBridgeInBoundVTControlVlanIndex, 
                                fkVlanInboundTagOperStatus, fkVlanOutboundTagOperStatus, fkVlanRangeInboundTagOperStatus, fkVlanControlIndexTo, fkBridgeUnknownMcastBlockAllPorts, 
                                fkBridgeControlUnknownMcastBlockAllPorts, fkBridgePortUnknownMcastBlock, fkBridgePortControlUnknownMcastBlock, fkBridgeEcmpHashType, fkBridgeControlEcmpHashType, 
                                fkBridgeTcpSynguard, fkBridgeControlTcpSynguard, fkBridgePortDescription, fkBridgePortHoldTime, fkBridgePortControlDescription, 
                                fkBridgePortControlHoldTime, fkLagLacpStatsPduReceived, fkLagLacpStatsPduReceivedErrrors, fkLagLacpStatsPduSent, fkLagLacpStatsPduSentError, 
                                fkLagLacpStatsMarkerReceived, fkLagLacpStatsMarkerSent, fkLagLacpStatsMarkerSentError, fkLagLacpControlRequest, fkLagLacpControlStatus, 
                                fkLagLacpControlTimer, fkLagLacpControlTimeStamp, fkLagLacpControlReqResult, fkBridgeOuterTagProtoId, fkBridgeControlOuterTagProtoId, 
                                fkBridgeOutBoundVTPortIndex, fkBridgeOutBoundVTVlanIndex, fkBridgeOutBoundVTNewVid, fkBridgeOutBoundVTOperStatus, fkBridgeOutBoundVTControlRequest, 
                                fkBridgeOutBoundVTControlStatus, fkBridgeOutBoundVTControlTimer, fkBridgeOutBoundVTControlTimeStamp, fkBridgeOutBoundVTControlReqResult, fkBridgeOutBoundVTControlPortIndex, 
                                fkBridgeOutBoundVTControlVlanIndex, fkBridgeOutBoundVTControlNewVid, fkBridgeMacAntiSpoofing, fkBridgeMacReplace, fkBridgeControlMacAntiSpoofing, 
                                fkBridgeControlMacReplace, fkBridgePortMacAntiSpoofing, fkBridgePortControlMacAntiSpoofing, fkVlanProtoIdVid, fkVlanProtoIdOuterProtoId, 
                                fkVlanProtoIdControlRequest, fkVlanProtoIdControlStatus, fkVlanProtoIdControlTimer, fkVlanProtoIdControlTimeStamp, fkVlanProtoIdControlReqResult, 
                                fkVlanProtoIdControlVid, fkVlanProtoIdControlOuterProtoId, fkBridgeStormControlBcast, fkBridgeStormControlDLF, fkBridgeStormControlMulticast, 
                                fkBridgeControlStormControlBcast, fkBridgeControlStormControlDLF, fkBridgeControlStormControlMulticast, fkVlanMappingIndex, fkVlanMappingPortId, 
                                fkVlanMappingOriVlanId, fkVlanMappingTransVlanId, fkVlanMappingMode, fkVlanMappingMatchCos, fkVlanMappingMatchDscp, 
                                fkVlanMappingMatchEthType, fkVlanMappingMatchIPPrecedence, fkVlanMappingMatchTos, fkVlanMappingRateLimit, fkVlanMappingCos, 
                                fkVlanMappingDscp, fkVlanMappingControlRequest, fkVlanMappingControlStatus, fkVlanMappingControlTimer, fkVlanMappingControlTimeStamp, 
                                fkVlanMappingControlReqResult, fkVlanMappingControlPortId, fkVlanMappingControlOriVlanId, fkVlanMappingControlTransVlanID, fkVlanMappingControlMode, 
                                fkVlanMappingControlMatchCos, fkVlanMappingControlMatchDscp, fkVlanMappingControlMatchEthType, fkVlanMappingControlMatchIPPrecedence, fkVlanMappingControlMatchTos, 
                                fkVlanMappingControlRateLimit, fkVlanMappingControlCos, fkVlanMappingControlDscp, fkVlanMappingControlIndex, fkBridgeMacLearningMode, 
                                fkBridgeControlMacLearningMode, fkLldpRemManAddrSubType, fkLldpRemManAddr, fkLldpRemManAddrIfSubType, fkLldpRemManAddrIfId, 
                                fkLldpRemAddrOid, fkBridgeLagGlobalDistMode, fkBridgeControlLagGlobalDistMode, fkVlanDescription, fkVlanControlDescription, 
                                fkVlanElineEnable, fkVlanControlElineEnable, fkBridgePortSwitchType, fkBridgePortSwitchState, fkBridgePortSwitchMode, 
                                fkBridgePortSwitchSubMode, fkBridgePortSwitchDefaultVlan, fkBridgePortSwitchIngressFilter, fkBridgePortSwitchAccFrameType, fkBridgePortSwitchNativeVid, 
                                fkBridgePortSwitchAllowedVlan, fkBridgePortSwitchAllowedVlanEtag, fkBridgePortControlSwitchStatus, fkBridgePortControlSwitchMode, fkBridgePortControlSwitchSubMode, 
                                fkBridgePortControlSwitchDefaultVlan, fkBridgePortControlSwitchIngressFilter, fkBridgePortControlSwitchAccFrameType, fkBridgePortControlSwitchNativeVid, fkBridgePortControlSwitchAllowedVlan, 
                                fkBridgePortControlSwitchAllowedVlanEtag, fkBridgePortControlInner2outerVid, fkBridgeInnerTagProtoId, fkBridgeControlInnerTagProtoId, fkBridgeVTControlReqResult, 
                                fkVlanRangeInboundTagPortIndex, fkVlanRangeInboundTagMinVlanIndex, fkVlanRangeInboundTagMaxVlanIndex, fkVlanRangeInboundTagOuterVid, fkVlanRangeInboundTagControlRequest, 
                                fkVlanRangeInboundTagControlStatus, fkVlanRangeInboundTagControlTimer, fkVlanRangeInboundTagControlTimeStamp, fkVlanRangeInboundTagControlReqResult, fkVlanRangeInboundTagControlPortIndex, 
                                fkVlanRangeInboundTagControlMinVlanIndex, fkVlanRangeInboundTagControlMaxVlanIndex, fkBridgeMultiPortLlcfPortAStatus, fkBridgeMultiPortLlcfPortBStatus, fkVlanRangeInboundTagControlOuterVid, 
                                fkBridgeMultiPortLlcfPortA, fkBridgeMultiPortLlcfPortB, fkBridgeMultiPortLlcfTimer, fkBridgeControlMultiPortLlcfPortA, fkBridgeControlMultiPortLlcfPortB, 
                                fkBridgeControlMultiPortLlcfPortC, fkVlanOperStatus, fkVlanMtu, fkVlanControlOperStatus, fkVlanControlMtu, 
                                fkBridgePortSwitchChannelType, fkBridgePortSwitchStaticChannelGroup, fkBridgePortSwitchChannelLoadbalance, fkBridgePortControlSwitchStaticChannelGroup, fkBridgePortControlSwitchChannelLoadbalance, 
                                fkVlanInboundTagVlanPriority, fkVlanInboundTagOuterVlanPriority, fkVlanInboundTagControlVlanPriority, fkVlanInboundTagControlOuterVlanPriority, fkPowerInlinePortIndex, 
                                fkPowerInlineAdminStatus, fkPowerInlinePortStatus, fkPowerInlineDetectionStatus, fkPowerInlinePortClass, fkPowerInlinePortMaxPow, 
                                fkPowerInlinePortLegacy, fkPowerInlinePortPriority, fkPowerInlinePortPower, fkPowerInlinePortCurrent, fkPowerInlinePortVoltage, 
                                fkPowerInlinePortTemperture, fkPowerInlineControlRequest, fkPowerInlineControlStatus, fkPowerInlineControlTimer, fkPowerInlineControlTimeStamp, 
                                fkPowerInlineControlReqResult, fkPowerInlineControlPortIndex, fkPowerInlineControlPortStatus, fkPowerInlineControlPortClass, fkPowerInlineControlPortMaxPower, 
                                fkPowerInlineControlPortLegacy, fkPowerInlineControlPriority, fkPowerInlineControlAdminStatus, fkLagLeastActive, fkLagControlLeastActive, 
                                fkBridgeControlMultiPortLlcfTimer, fkBridgeMultiPortLlcfUpPortC, fkBridgeMultiPortLlcfDownPortC, fkBridgeMultiPortLlcfUpPortCStatus, fkBridgeMultiPortLlcfDownPortCStatus
                                 }
                        STATUS current
                        DESCRIPTION 
                                "Description."
                        ::= { fkBridge 30 }

                
                -- 1.3.6.1.4.1.10428 9 1.101.3.31
                fkBridgeNotificationGroup NOTIFICATION-GROUP
                        NOTIFICATIONS { fkBridgeLacpProfileChanged, fkBridgeDoubleTagProtoIdChanged, fkBridgeMirrorProfileChanged, fkBridgeMaxLearnPerUnitChanged, fkBridgeFdbAgeingTimeChanged, 
                                fkBridgeStackProfileChanged, fkBridgeLldpProfileChanged, fkBridgeTcpSyncookieChanged, fkBridgeTcpIgnoreRstUnknownChanged, fkBridgePortPVidChanged, 
                                fkBridgePortMaxHostsChanged, fkBridgePortMaxLearnPerUnitChanged, fkBridgePortMACFilterPermissionChanged, fkBridgePortMirrorProfileChanged, fkBridgePortBcscThresholdProfileChanged, 
                                fkBridgePortQinQStatusChanged, fkBridgePortLinktypeChanged, fkBridgePortEdgemodeChanged, fkBridgePortStpBpduFilterChanged, fkBridgePortPvlanIsolatedStatusChanged, 
                                fkVlanCreated, fkVlanDestroyed, fkVlanPortProfileChanged, fkVlanAgeingTimeChanged, fkVlanMapFidChanged, 
                                fkVlanMapStpIdChanged, fkVlanMapErpDomainIdChanged, fkStpOperationModeChanged, fkStpConfigureProfileChanged, fkStpTimerProfileChanged, 
                                fkStpBpduGuardProfileChanged, fkStpInstanceEnableChanged, fkStpInstanceConfigProfileChanged, fkStpInstancePortProfileChanged, fkSubnetVlanCreated, 
                                fkSubnetVlanDestroyed, fkProtocolVlanCreated, fkProtocolVlanDestroyed, fkLagProfileChanged, fkLagLacpPortProfileChanged, 
                                fkLagLacpPortAggreChanged, fkFdbEntryCreated, fkFdbEntryDestoryed, fkFdbTableEntriesCleared, fkMfdbEntryCreated, 
                                fkMfdbEntryDestoryed, fkMfdbEntryPermissionChanged, fkMfdbEntryTableCleared, fkIgmpConfProfileChanged, fkIgmpStaticMcastCreated, 
                                fkIgmpStaticMcastDestroyed, fkStackDeviceCreated, fkStackDeviceDestoryed, fkErpDomainCreated, fkErpDomainDestroyed, 
                                fkErpDomainProfileChanged, fkErpProtectionActivationChanged, fkLldpPortProfileChanged, fkLldpStatisticsCleared, fkBridgePSStatusChanged, 
                                fkBridgePSMaxCountChanged, fkBridgePSProfileChanged, fkBridgePSFdbEntryCreated, fkBridgePSFdbEntryDestroyed, fkBridgePortStpBpduGuardErrRcvChanged, 
                                fkErpHoldOffTimeChanged, fkErpRingPriorityChanged, fkErpTrapChanged, fkBridgeFGBaseCfgdStatusChanged, fkBridgeAutoInterfaceActivationChanged, 
                                fkBridgeFGPortUnblockChanged, fkBridgeFGPortProfileChanged, fkBridgeLoopDetectProfileChanged, fkBridgePortLoopDetectProfileChanged, fkBridgePortLoopDetectUnblock, 
                                fkBridgePvlanPormSelectModeChanged, fkBridgeVTSet, fkBridgeVTClear, fkBridgeGarpStatusChanged, fkBridgeGarpTimerChanged, 
                                fkBridgeGarpAppPortStatusChanged, fkBridgeGarpAppPortProfileChanged, fkBridgeGarpStatisticsCleared, fkBridgeGmrpStaticAdded, fkBridgeGmrpStaticDeleted, 
                                fkBridgePortNetBIOSFilterChanged, fkBridgePortPriorityChanged, fkBridgePortInnertagChanged, fkBridgePortPopInnertagChanged, fkBridgePortPushInnertagChanged, 
                                fkVlanInboundTagChanged, fkVlanOutboundTagSet, fkVlanOutboundTagClear, fkBridgePortInner2outerVidChanged, fkBridgePortInner2outerPriChanged, 
                                fkBridgePSFdbEntryCleared, fkBridgePortDhcpFilterServerChanged, fkBridgePortMACLearningStatusChanged, fkBridgePortPortBridgeStatusChanged, fkBridgeInBoundVTSet, 
                                fkBridgeInBoundVTClear, fkBridgeInnerTagProtoIdChanged, fkVlanInboundTagCleared, fkVlanRangeInboundTagChanged, fkVlanRangeInboundTagCleared, 
                                fkVlanRangeCreated, fkBridgeUnknownMcastBlockAllPortsChanged, fkBridgePortUnknownMcastBlockChanged, fkBridgeEcmpHashTypeChanged, fkBridgeTcpSynguardChanged, 
                                fkBridgePortDescriptionChanged, fkBridgePortHoldTimeChanged, fkLagLacpStatsCleared, fkBridgeOuterTagProtoIdChanged, fkBridgeOutBoundVTSet, 
                                fkBridgeOutBoundVTClear, fkBridgeMacAntiSpoofingChanged, fkBridgeMacReplaceChanged, fkBridgePortMacAntiSpoofChanged, fkVlanProtoIdOuterProtoIdChanged, 
                                fkBridgeStormControlChanged, fkVlanMappingCreated, fkVlanMappingDeleted, fkBridgeMacLearningModeChanged, fkBridgeLagGlobalDistModeChanged, 
                                fkVlanDescriptionChanged, fkVlanElineVlanCreated, fkBridgePortSwitchStatusChanged, fkBridgePortSwitchModeChanged, fkBridgePortSwitchDefaultVlanChanged, 
                                fkBridgePortSwitchNativeVlanChanged, fkBridgePortSwitchAccFramTypeChanged, fkBridgePortSwitchAllowdVlanAdded, fkBridgePortSwitchAllowdVlanDeleted, fkVlanOperStatusChagned, 
                                fkVlanMtuChagned, fkBridgePortSwitchStaticChannelChanged, fkBridgePortSwitchChannelLoadbalanceChanged, fkPowerInlineEnableChanged, fkPowerInlineDisableChanged, 
                                fkPowerInlineResetChanged, fkPowerInlineLegacyChanged, fkPowerInlinePriorityChanged, fkPowerInlineClassChanged, fkPowerInlinePowerChanged, 
                                fkBridgeFGBaseSfgdStatusChanged, fkBridgeStpProfileChanged, fkBridgeMultiPortLlcfChanged, fkBridgeMultiPortLlcfDeleted, fkBridgeMultiPortLlcfTimerChanged
                                 }
                        STATUS current
                        DESCRIPTION 
                                "Description."
                        ::= { fkBridge 31 }

                
        
        END

--
-- fk-bridge-mib.mib
--
