--
-- fk-rmon-mib.mib
-- MIB generated by MG-SOFT Visual MIB Builder Version 6.0  Build 88
-- Thursday, December 27, 2012 at 17:52:11
--

--  FK-RMON-MIB.my
-- MIB generated by MG-SOFT Visual MIB Builder Version 3.0 Build 285
-- Monday, January 22, 2007 at 16:52:34
-- 

	FK-RMON-MIB DEFINITIONS ::= BEGIN
 
		IMPORTS
			fkMgmt			
				FROM FKOLTG1040-SMI			
			FkControlStatusType, FkControlRequestResultType			
				FROM FK-TC-MIB			
			OBJECT-GROUP, NOTIFICATION-GROUP			
				FROM SNMPv2-CONF			
			TimeTicks, Integer32, Gauge32, Counter32, OBJECT-TYPE, 
			MODULE-IDENTITY, NOTIFICATION-TYPE			
				FROM SNMPv2-SMI			
			DisplayString			
				FROM SNMPv2-TC;
	
	
--  			fk			
-- FROM AN-MIB			
-- 
-- 1.3.6.1.4.1.10428 9 1.101.9
-- December 08, 2004 at 09:03 GMT
-- December 08, 2004 at 08:40 GMT
		-- 1.3.6.1.4.1.10428 9 1.101.9
		fkRmon MODULE-IDENTITY 
			LAST-UPDATED "200412080903Z"		-- December 08, 2004 at 09:03 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 9 }

		
	
--
-- Type definitions
--
	
--  Type definitions
-- 
-- ::= { fk 14 }
-- textual conventions
		OwnerString ::= OCTET STRING (SIZE (0..255))

--   This data type is used to model an administratively
-- assigned name of the owner of a resource. This
-- information is taken from the NVT ASCII character
-- set.  It is suggested that this name contain one or
-- more of the following: IP address, management station
-- name, network manager's name, location, or phone
-- number.
-- In some cases the agent itself will be the owner of
-- an entry.  In these cases, this string shall be set
-- to a string starting with 'monitor'.
-- 
-- SNMP access control is articulated entirely in terms
-- of the contents of MIB views; access to a particular
-- SNMP object instance depends only upon its presence
-- or absence in a particular MIB view and never upon
-- its value or the value of related object instances.
-- Thus, objects of this type afford resolution of
-- resource contention only among cooperating managers;
-- they realize no access control function with respect
-- to uncooperative parties.
-- 
-- By convention, objects with this syntax are declared as
-- having
-- 
--      SIZE (0..127)
		FkEntryStatus ::= INTEGER
			{
			valid(1),
			createRequest(2),
			underCreation(3)
			}

	
	
--
-- Node definitions
--
	
--  Node definitions
-- 
-- 1.3.6.1.4.1.10428 9 1.101.9.1
		-- 1.3.6.1.4.1.10428 9 1.101.9.1
		fkHistory OBJECT IDENTIFIER ::= { fkRmon 1 }

		
--   The fkHistory Control Group
-- Implementation of the History Control group is optional.
-- 
-- The fkHistory control group controls the periodic statistical
-- sampling of data from various types of networks.  The
-- historyControlTable stores configuration entries that each
-- define an interface, polling period, and other parameters.
-- Once samples are taken, their data is stored in an entry
-- in a media-specific table.  Each such entry defines one
-- sample, and is associated with the historyControlEntry that
-- caused the sample to be taken.  Each counter in the
-- etherHistoryEntry counts the same event as its
-- similarly-named counterpart in the etherStatsEntry,
-- except that each value here is a cumulative sum during a
-- sampling period.
-- 
-- If the probe keeps track of the time of day, it should
-- start the first sample of the history at a time such that
-- when the next hour of the day begins, a sample is
-- started at that instant.  This tends to make more
-- user-friendly reports, and enables comparison of reports
-- from different probes that have relatively accurate time
-- of day.
-- 
-- The probe is encouraged to add two history control entries
-- per monitored interface upon initialization that describe
-- a short term and a long term polling period.  Suggested
-- parameters are 30 seconds for the short term polling period
-- and 30 minutes for the long term period.
-- 1.3.6.1.4.1.10428 9 1.101.9.1.1
		-- 1.3.6.1.4.1.10428 9 1.101.9.1.1
		fkHistoryTable OBJECT-TYPE
			SYNTAX SEQUENCE OF FkHistoryEntry
			MAX-ACCESS not-accessible
			STATUS current
			DESCRIPTION
				"A list of history control entries."
			::= { fkHistory 1 }

		
--  1.3.6.1.4.1.10428 9 1.101.9.1.1.1
		-- 1.3.6.1.4.1.10428 9 1.101.9.1.1.1
		fkHistoryEntry OBJECT-TYPE
			SYNTAX FkHistoryEntry
			MAX-ACCESS not-accessible
			STATUS current
			DESCRIPTION
				"A list of parameters that set up a periodic sampling
				of statistics.  As an example, an instance of the
				fkHistoryControlInterval object might be named
				fkHistoryControlInterval.2"
			INDEX { fkHistoryIndex }
			::= { fkHistoryTable 1 }

		
		FkHistoryEntry ::=
			SEQUENCE { 
				fkHistoryIndex
					INTEGER,
				fkHistoryDataSource
					OBJECT IDENTIFIER,
				fkHistoryBucketsRequested
					INTEGER,
				fkHistoryBucketsGranted
					INTEGER,
				fkHistoryInterval
					INTEGER,
				fkHistoryOwner
					OwnerString,
				fkHistoryStatus
					FkEntryStatus
			 }

--  1.3.6.1.4.1.10428 9 1.101.9.1.1.1.1
		-- 1.3.6.1.4.1.10428 9 1.101.9.1.1.1.1
		fkHistoryIndex OBJECT-TYPE
			SYNTAX INTEGER (1..65535)
			MAX-ACCESS read-only
			STATUS current
			DESCRIPTION
				"An index that uniquely identifies an entry in the
				historyControl table.  Each such entry defines a
				set of samples at a particular interval for an
				interface on the device."
			::= { fkHistoryEntry 1 }

		
--  1.3.6.1.4.1.10428 9 1.101.9.1.1.1.2
		-- 1.3.6.1.4.1.10428 9 1.101.9.1.1.1.2
		fkHistoryDataSource OBJECT-TYPE
			SYNTAX OBJECT IDENTIFIER
			MAX-ACCESS read-only
			STATUS current
			DESCRIPTION
				"This object identifies the source of the data for
				which historical data was collected and
				placed in a media-specific table on behalf of this
				historyControlEntry.  This source can be any
				interface on this device.  In order to identify
				a particular interface, this object shall identify
				the instance of the ifIndex object, defined
				in  RFC 1213 and RFC 1573 [4,6], for the desired
				interface.  For example, if an entry were to receive
				data from interface #1, this object would be set
				to ifIndex.1.
				
				The statistics in this group reflect all packets
				on the local network segment attached to the
				identified interface.
				
				An agent may or may not be able to tell if fundamental
				changes to the media of the interface have occurred
				and necessitate an invalidation of this entry.  For
				example, a hot-pluggable ethernet card could be
				pulled out and replaced by a token-ring card.  In
				such a case, if the agent has such knowledge of the
				change, it is recommended that it invalidate this
				entry.
				
				This object may not be modified if the associated
				historyControlStatus object is equal to valid(1)."
			::= { fkHistoryEntry 2 }

		
--  1.3.6.1.4.1.10428 9 1.101.9.1.1.1.3
		-- 1.3.6.1.4.1.10428 9 1.101.9.1.1.1.3
		fkHistoryBucketsRequested OBJECT-TYPE
			SYNTAX INTEGER (1..65535)
			MAX-ACCESS read-only
			STATUS current
			DESCRIPTION
				"The requested number of discrete time intervals
				over which data is to be saved in the part of the
				media-specific table associated with this
				historyControlEntry.
				
				When this object is created or modified, the probe
				should set historyControlBucketsGranted as closely to
				this object as is possible for the particular probe
				implementation and available resources."
			DEFVAL { 50 }
			::= { fkHistoryEntry 3 }

		
--  1.3.6.1.4.1.10428 9 1.101.9.1.1.1.4
		-- 1.3.6.1.4.1.10428 9 1.101.9.1.1.1.4
		fkHistoryBucketsGranted OBJECT-TYPE
			SYNTAX INTEGER (1..100)
			MAX-ACCESS read-only
			STATUS current
			DESCRIPTION
				"The number of discrete sampling intervals
				over which data shall be saved in the part of
				the media-specific table associated with this
				historyControlEntry.
				
				When the associated historyControlBucketsRequested
				object is created or modified, the probe
				should set this object as closely to the requested
				value as is possible for the particular
				probe implementation and available resources.  The
				probe must not lower this value except as a result
				of a modification to the associated
				historyControlBucketsRequested object.
				
				There will be times when the actual number of
				buckets associated with this entry is less than
				the value of this object.  In this case, at the
				end of each sampling interval, a new bucket will
				be added to the media-specific table.
				
				When the number of buckets reaches the value of
				this object and a new bucket is to be added to the
				media-specific table, the oldest bucket associated
				with this historyControlEntry shall be deleted by
				the agent so that the new bucket can be added.
				
				When the value of this object changes to a value less
				than the current value, entries are deleted
				from the media-specific table associated with this
				historyControlEntry.  Enough of the oldest of these
				entries shall be deleted by the agent so that their
				number remains less than or equal to the new value of
				this object.
				
				When the value of this object changes to a value
				greater than the current value, the number of
				associated media- specific entries may be allowed to
				grow."
			::= { fkHistoryEntry 4 }

		
--  1.3.6.1.4.1.10428 9 1.101.9.1.1.1.5
		-- 1.3.6.1.4.1.10428 9 1.101.9.1.1.1.5
		fkHistoryInterval OBJECT-TYPE
			SYNTAX INTEGER (1..3600)
			MAX-ACCESS read-only
			STATUS current
			DESCRIPTION
				"The interval in seconds over which the data is
				sampled for each bucket in the part of the
				media-specific table associated with this
				historyControlEntry.  This interval can
				be set to any number of seconds between 1 and
				3600 (1 hour).
				
				Because the counters in a bucket may overflow at their
				maximum value with no indication, a prudent manager
				will take into account the possibility of overflow
				in any of the associated counters.  It is important
				to consider the minimum time in which any counter
				could overflow on a particular media type and set
				the historyControlInterval object to a value less
				than this interval.  This is typically most
				important for the 'octets' counter in any
				media-specific table.  For example, on an Ethernet
				network, the etherHistoryOctets counter could
				overflow in about one hour at the Ethernet's maximum
				utilization.
				
				This object may not be modified if the associated
				historyControlStatus object is equal to valid(1)."
			DEFVAL { 1800 }
			::= { fkHistoryEntry 5 }

		
--  1.3.6.1.4.1.10428 9 1.101.9.1.1.1.6
		-- 1.3.6.1.4.1.10428 9 1.101.9.1.1.1.6
		fkHistoryOwner OBJECT-TYPE
			SYNTAX OwnerString
			MAX-ACCESS read-only
			STATUS current
			DESCRIPTION
				"The entity that configured this entry and is
				therefore using the resources assigned to it."
			::= { fkHistoryEntry 6 }

		
--  1.3.6.1.4.1.10428 9 1.101.9.1.1.1.7
		-- 1.3.6.1.4.1.10428 9 1.101.9.1.1.1.7
		fkHistoryStatus OBJECT-TYPE
			SYNTAX FkEntryStatus
			MAX-ACCESS read-only
			STATUS current
			DESCRIPTION
				"The status of this historyControl entry.
				
				Each instance of the media-specific table associated
				with this historyControlEntry will be deleted by the
				agent if this historyControlEntry is not equal to
				valid(1)."
			::= { fkHistoryEntry 7 }

		
--  1.3.6.1.4.1.10428 9 1.101.9.1.2
		-- 1.3.6.1.4.1.10428 9 1.101.9.1.2
		fkHistoryControl OBJECT IDENTIFIER ::= { fkHistory 2 }

		
--   Node definitions
-- 
-- 1.3.6.1.4.1.10428 9 1.101.9.1.2.1
		-- 1.3.6.1.4.1.10428 9 1.101.9.1.2.1
		fkHistoryControlRequest OBJECT-TYPE
			SYNTAX INTEGER
				{
				createHistory(1),
				destroyHistory(2),
				setHistoryProfile(3)
				}
			MAX-ACCESS read-write
			STATUS current
			DESCRIPTION
				"
				createHistory:
				fkHistoryControlIndex
				fkHistoryControlDataSource
				fkHistoryControlBucketsRequested
				fkHistoryControlInterval
				fkHistoryControlOwner
				fkHistoryControlSts
				
				destroyHistory:
				fkHistoryControlIndex
				
				setHistoryProfile:
				fkHistoryControlIndex
				fkHistoryControlDataSource
				fkHistoryControlBucketsRequested
				fkHistoryControlInterval
				fkHistoryControlOwner
				fkHistoryControlSts
				
				"
			::= { fkHistoryControl 1 }

		
--  1.3.6.1.4.1.10428 9 1.101.9.1.2.2
		-- 1.3.6.1.4.1.10428 9 1.101.9.1.2.2
		fkHistoryControlStatus OBJECT-TYPE
			SYNTAX FkControlStatusType
			MAX-ACCESS read-only
			STATUS current
			DESCRIPTION
				"The status of a user command. 
				"
			::= { fkHistoryControl 2 }

		
--  1.3.6.1.4.1.10428 9 1.101.9.1.2.3
		-- 1.3.6.1.4.1.10428 9 1.101.9.1.2.3
		fkHistoryControlTimer OBJECT-TYPE
			SYNTAX Gauge32
			MAX-ACCESS read-write
			STATUS current
			DESCRIPTION
				"The maximum wait time for the manager for a long running user command. 
				"
			::= { fkHistoryControl 3 }

		
--  1.3.6.1.4.1.10428 9 1.101.9.1.2.4
		-- 1.3.6.1.4.1.10428 9 1.101.9.1.2.4
		fkHistoryControlTimeStamp OBJECT-TYPE
			SYNTAX TimeTicks
			MAX-ACCESS read-only
			STATUS current
			DESCRIPTION
				"The time stamp of the last command (end of command)."
			::= { fkHistoryControl 4 }

		
--  1.3.6.1.4.1.10428 9 1.101.9.1.2.5
		-- 1.3.6.1.4.1.10428 9 1.101.9.1.2.5
		fkHistoryControlReqResult OBJECT-TYPE
			SYNTAX FkControlRequestResultType
			MAX-ACCESS read-only
			STATUS current
			DESCRIPTION
				"The result of the last user command."
			::= { fkHistoryControl 5 }

		
--  1.3.6.1.4.1.10428 9 1.101.9.1.2.6
		-- 1.3.6.1.4.1.10428 9 1.101.9.1.2.6
		fkHistoryControlIndex OBJECT-TYPE
			SYNTAX INTEGER (1..65535)
			MAX-ACCESS read-write
			STATUS current
			DESCRIPTION
				"Description."
			::= { fkHistoryControl 6 }

		
--  1.3.6.1.4.1.10428 9 1.101.9.1.2.7
		-- 1.3.6.1.4.1.10428 9 1.101.9.1.2.7
		fkHistoryControlDataSource OBJECT-TYPE
			SYNTAX OBJECT IDENTIFIER
			MAX-ACCESS read-write
			STATUS current
			DESCRIPTION
				"This object identifies the source of the data for
				which historical data was collected and
				placed in a media-specific table on behalf of this
				historyControlEntry.  This source can be any
				interface on this device.  In order to identify
				a particular interface, this object shall identify
				the instance of the ifIndex object, defined
				in  RFC 1213 and RFC 1573 [4,6], for the desired
				interface.  For example, if an entry were to receive
				data from interface #1, this object would be set
				to ifIndex.1.
				
				The statistics in this group reflect all packets
				on the local network segment attached to the
				identified interface.
				
				An agent may or may not be able to tell if fundamental
				changes to the media of the interface have occurred
				and necessitate an invalidation of this entry.  For
				example, a hot-pluggable ethernet card could be
				pulled out and replaced by a token-ring card.  In
				such a case, if the agent has such knowledge of the
				change, it is recommended that it invalidate this
				entry.
				
				This object may not be modified if the associated
				historyControlStatus object is equal to valid(1)."
			::= { fkHistoryControl 7 }

		
--  1.3.6.1.4.1.10428 9 1.101.9.1.2.8
		-- 1.3.6.1.4.1.10428 9 1.101.9.1.2.8
		fkHistoryControlBucketsRequested OBJECT-TYPE
			SYNTAX INTEGER (1..100)
			MAX-ACCESS read-write
			STATUS current
			DESCRIPTION
				"The requested number of discrete time intervals
				over which data is to be saved in the part of the
				media-specific table associated with this
				historyControlEntry.
				
				When this object is created or modified, the probe
				should set historyControlBucketsGranted as closely to
				this object as is possible for the particular probe
				implementation and available resources."
			DEFVAL { 50 }
			::= { fkHistoryControl 8 }

		
--  1.3.6.1.4.1.10428 9 1.101.9.1.2.9
		-- 1.3.6.1.4.1.10428 9 1.101.9.1.2.9
		fkHistoryControlInterval OBJECT-TYPE
			SYNTAX INTEGER (1..3600)
			MAX-ACCESS read-write
			STATUS current
			DESCRIPTION
				"The interval in seconds over which the data is
				sampled for each bucket in the part of the
				media-specific table associated with this
				historyControlEntry.  This interval can
				be set to any number of seconds between 1 and
				3600 (1 hour).
				
				Because the counters in a bucket may overflow at their
				maximum value with no indication, a prudent manager
				will take into account the possibility of overflow
				in any of the associated counters.  It is important
				to consider the minimum time in which any counter
				could overflow on a particular media type and set
				the historyControlInterval object to a value less
				than this interval.  This is typically most
				important for the 'octets' counter in any
				media-specific table.  For example, on an Ethernet
				network, the etherHistoryOctets counter could
				overflow in about one hour at the Ethernet's maximum
				utilization.
				
				This object may not be modified if the associated
				historyControlStatus object is equal to valid(1)."
			DEFVAL { 1800 }
			::= { fkHistoryControl 9 }

		
--  1.3.6.1.4.1.10428 9 1.101.9.1.2.10
		-- 1.3.6.1.4.1.10428 9 1.101.9.1.2.10
		fkHistoryControlOwner OBJECT-TYPE
			SYNTAX OwnerString
			MAX-ACCESS read-write
			STATUS current
			DESCRIPTION
				"The entity that configured this entry and is
				therefore using the resources assigned to it."
			::= { fkHistoryControl 10 }

		
--  1.3.6.1.4.1.10428 9 1.101.9.1.2.11
		-- 1.3.6.1.4.1.10428 9 1.101.9.1.2.11
		fkHistoryControlSts OBJECT-TYPE
			SYNTAX FkEntryStatus
			MAX-ACCESS read-write
			STATUS current
			DESCRIPTION
				"The status of this historyControl entry.
				
				Each instance of the media-specific table associated
				with this historyControlEntry will be deleted by the
				agent if this historyControlEntry is not equal to
				valid(1)."
			::= { fkHistoryControl 11 }

		
--  1.3.6.1.4.1.10428 9 1.101.9.1.3
		-- 1.3.6.1.4.1.10428 9 1.101.9.1.3
		fkHistoryNotification OBJECT IDENTIFIER ::= { fkHistory 3 }

		
--  1.3.6.1.4.1.10428 9 1.101.9.1.3.1
		-- 1.3.6.1.4.1.10428 9 1.101.9.1.3.1
		fkHistoryCreated NOTIFICATION-TYPE
			OBJECTS { fkHistoryDataSource, fkHistoryBucketsRequested, fkHistoryInterval, fkHistoryOwner, fkHistoryStatus, 
				fkHistoryControlRequest, fkHistoryControlTimeStamp, fkHistoryControlReqResult }
			STATUS current
			DESCRIPTION 
				"Description."
			::= { fkHistoryNotification 1 }

		
--  1.3.6.1.4.1.10428 9 1.101.9.1.3.2
		-- 1.3.6.1.4.1.10428 9 1.101.9.1.3.2
		fkHistoryDestroyed NOTIFICATION-TYPE
			OBJECTS { fkHistoryIndex, fkHistoryControlRequest, fkHistoryControlTimeStamp, fkHistoryControlReqResult }
			STATUS current
			DESCRIPTION 
				"Description."
			::= { fkHistoryNotification 2 }

		
--  1.3.6.1.4.1.10428 9 1.101.9.1.3.3
		-- 1.3.6.1.4.1.10428 9 1.101.9.1.3.3
		fkHistoryProfileChanged NOTIFICATION-TYPE
			OBJECTS { fkHistoryDataSource, fkHistoryBucketsRequested, fkHistoryInterval, fkHistoryOwner, fkHistoryStatus, 
				fkHistoryControlRequest, fkHistoryControlTimeStamp, fkHistoryControlReqResult }
			STATUS current
			DESCRIPTION 
				"Description."
			::= { fkHistoryNotification 3 }

		
--  1.3.6.1.4.1.10428 9 1.101.9.2
		-- 1.3.6.1.4.1.10428 9 1.101.9.2
		fkAlarm OBJECT IDENTIFIER ::= { fkRmon 2 }

		
--   The fkAlarm Group
-- Implementation of the Alarm group is optional.
-- 
-- The fkAlarm Group requires the implementation of the Event
-- group.
-- 
-- The fkAlarm group periodically takes
-- statistical samples from variables in the probe and
-- compares them to thresholds that have been
-- configured.  The alarm table stores configuration
-- entries that each define a variable, polling period,
-- and threshold parameters.  If a sample is found to
-- cross the threshold values, an event is generated.
-- Only variables that resolve to an ASN.1 primitive
-- type of INTEGER (INTEGER, Counter, Gauge, or
-- TimeTicks) may be monitored in this way.
-- 
-- This function has a hysteresis mechanism to limit
-- the generation of events.  This mechanism generates
-- one event as a threshold is crossed in the
-- appropriate direction.  No more events are generated
-- for that threshold until the opposite threshold is
-- crossed.
-- 
-- In the case of a sampling a deltaValue, a probe may
-- implement this mechanism with more precision if it
-- takes a delta sample twice per period, each time
-- comparing the sum of the latest two samples to the
-- threshold.  This allows the detection of threshold
-- crossings that span the sampling boundary.  Note
-- that this does not require any special configuration
-- of the threshold value.  It is suggested that probes
-- implement this more precise algorithm.
-- 1.3.6.1.4.1.10428 9 1.101.9.2.1
		-- 1.3.6.1.4.1.10428 9 1.101.9.2.1
		fkAlarmTable OBJECT-TYPE
			SYNTAX SEQUENCE OF FkAlarmEntry
			MAX-ACCESS not-accessible
			STATUS current
			DESCRIPTION
				"A list of alarm entries."
			::= { fkAlarm 1 }

		
--  1.3.6.1.4.1.10428 9 1.101.9.2.1.1
		-- 1.3.6.1.4.1.10428 9 1.101.9.2.1.1
		fkAlarmEntry OBJECT-TYPE
			SYNTAX FkAlarmEntry
			MAX-ACCESS not-accessible
			STATUS current
			DESCRIPTION
				"A list of parameters that set up a periodic checking
				for alarm conditions.  For example, an instance of the
				fkAlarmValue object might be named fkAlarmValue.8"
			INDEX { fkAlarmIndex }
			::= { fkAlarmTable 1 }

		
		FkAlarmEntry ::=
			SEQUENCE { 
				fkAlarmIndex
					INTEGER,
				fkAlarmInterval
					Integer32,
				fkAlarmVariable
					OBJECT IDENTIFIER,
				fkAlarmSampleType
					INTEGER,
				fkAlarmValue
					Integer32,
				fkAlarmStartupAlarm
					INTEGER,
				fkAlarmRisingThreshold
					Integer32,
				fkAlarmFallingThreshold
					Integer32,
				fkAlarmRisingEventIndex
					INTEGER,
				fkAlarmFallingEventIndex
					INTEGER,
				fkAlarmOwner
					OwnerString,
				fkAlarmStatus
					FkEntryStatus
			 }

--  1.3.6.1.4.1.10428 9 1.101.9.2.1.1.1
		-- 1.3.6.1.4.1.10428 9 1.101.9.2.1.1.1
		fkAlarmIndex OBJECT-TYPE
			SYNTAX INTEGER (1..65535)
			MAX-ACCESS read-only
			STATUS current
			DESCRIPTION
				"An index that uniquely identifies an entry in the
				alarm table.  Each such entry defines a
				diagnostic sample at a particular interval
				for an object on the device."
			::= { fkAlarmEntry 1 }

		
--  1.3.6.1.4.1.10428 9 1.101.9.2.1.1.2
		-- 1.3.6.1.4.1.10428 9 1.101.9.2.1.1.2
		fkAlarmInterval OBJECT-TYPE
			SYNTAX Integer32
			MAX-ACCESS read-only
			STATUS current
			DESCRIPTION
				"The interval in seconds over which the data is
				sampled and compared with the rising and falling
				thresholds.  When setting this variable, care
				should be taken in the case of deltaValue
				sampling - the interval should be set short enough
				that the sampled variable is very unlikely to
				increase or decrease by more than 2^31 - 1 during
				a single sampling interval.
				
				This object may not be modified if the associated
				alarmStatus object is equal to valid(1)."
			::= { fkAlarmEntry 2 }

		
--  1.3.6.1.4.1.10428 9 1.101.9.2.1.1.3
		-- 1.3.6.1.4.1.10428 9 1.101.9.2.1.1.3
		fkAlarmVariable OBJECT-TYPE
			SYNTAX OBJECT IDENTIFIER
			MAX-ACCESS read-only
			STATUS current
			DESCRIPTION
				"The object identifier of the particular variable to
				be sampled.  Only variables that resolve to an ASN.1
				primitive type of INTEGER (INTEGER, Counter, Gauge,
				or TimeTicks) may be sampled.
				
				Because SNMP access control is articulated entirely
				in terms of the contents of MIB views, no access
				control mechanism exists that can restrict the value
				of this object to identify only those objects that
				exist in a particular MIB view.  Because there is
				thus no acceptable means of restricting the read
				access that could be obtained through the alarm
				mechanism, the probe must only grant write access to
				this object in those views that have read access to
				all objects on the probe.
				
				During a set operation, if the supplied variable
				name is not available in the selected MIB view, a
				badValue error must be returned.  If at any time the
				variable name of an establifkd alarmEntry is no
				longer available in the selected MIB view, the probe
				must change the status of this alarmEntry to
				invalid(4).
				
				This object may not be modified if the associated
				alarmStatus object is equal to valid(1)."
			::= { fkAlarmEntry 3 }

		
--  1.3.6.1.4.1.10428 9 1.101.9.2.1.1.4
		-- 1.3.6.1.4.1.10428 9 1.101.9.2.1.1.4
		fkAlarmSampleType OBJECT-TYPE
			SYNTAX INTEGER
				{
				absoluteValue(1),
				deltaValue(2)
				}
			MAX-ACCESS read-only
			STATUS current
			DESCRIPTION
				"The method of sampling the selected variable and
				calculating the value to be compared against the
				thresholds.  If the value of this object is
				absoluteValue(1), the value of the selected variable
				will be compared directly with the thresholds at the
				end of the sampling interval.  If the value of this
				object is deltaValue(2), the value of the selected
				variable at the last sample will be subtracted from
				the current value, and the difference compared with
				the thresholds.
				
				This object may not be modified if the associated
				alarmStatus object is equal to valid(1)."
			::= { fkAlarmEntry 4 }

		
--  1.3.6.1.4.1.10428 9 1.101.9.2.1.1.5
		-- 1.3.6.1.4.1.10428 9 1.101.9.2.1.1.5
		fkAlarmValue OBJECT-TYPE
			SYNTAX Integer32
			MAX-ACCESS read-only
			STATUS current
			DESCRIPTION
				"The value of the statistic during the last sampling
				period.  For example, if the sample type is
				deltaValue, this value will be the difference
				between the samples at the beginning and end of the
				period.  If the sample type is absoluteValue, this
				value will be the sampled value at the end of the
				period.
				
				This is the value that is compared with the rising and
				falling thresholds.
				
				The value during the current sampling period is not
				made available until the period is completed and will
				remain available until the next period completes."
			::= { fkAlarmEntry 5 }

		
--  1.3.6.1.4.1.10428 9 1.101.9.2.1.1.6
		-- 1.3.6.1.4.1.10428 9 1.101.9.2.1.1.6
		fkAlarmStartupAlarm OBJECT-TYPE
			SYNTAX INTEGER
				{
				risingAlarm(1),
				fallingAlarm(2),
				risingOrFallingAlarm(3)
				}
			MAX-ACCESS read-only
			STATUS current
			DESCRIPTION
				"The alarm that may be sent when this entry is first
				set to valid.  If the first sample after this entry
				becomes valid is greater than or equal to the
				risingThreshold and alarmStartupAlarm is equal to
				risingAlarm(1) or risingOrFallingAlarm(3), then a
				single rising alarm will be generated.  If the first
				sample after this entry becomes valid is less than
				or equal to the fallingThreshold and
				alarmStartupAlarm is equal to fallingAlarm(2) or
				risingOrFallingAlarm(3), then a single falling alarm
				will be generated.
				
				This object may not be modified if the associated
				alarmStatus object is equal to valid(1)."
			::= { fkAlarmEntry 6 }

		
--  1.3.6.1.4.1.10428 9 1.101.9.2.1.1.7
		-- 1.3.6.1.4.1.10428 9 1.101.9.2.1.1.7
		fkAlarmRisingThreshold OBJECT-TYPE
			SYNTAX Integer32
			MAX-ACCESS read-only
			STATUS current
			DESCRIPTION
				"A threshold for the sampled statistic.  When the
				current sampled value is greater than or equal to
				this threshold, and the value at the last sampling
				interval was less than this threshold, a single
				event will be generated.  A single event will also
				be generated if the first sample after this entry
				becomes valid is greater than or equal to this
				threshold and the associated alarmStartupAlarm is
				equal to risingAlarm(1) or risingOrFallingAlarm(3).
				
				After a rising event is generated, another such event
				will not be generated until the sampled value
				falls below this threshold and reaches the
				alarmFallingThreshold.
				
				This object may not be modified if the associated
				alarmStatus object is equal to valid(1)."
			::= { fkAlarmEntry 7 }

		
--  1.3.6.1.4.1.10428 9 1.101.9.2.1.1.8
		-- 1.3.6.1.4.1.10428 9 1.101.9.2.1.1.8
		fkAlarmFallingThreshold OBJECT-TYPE
			SYNTAX Integer32
			MAX-ACCESS read-only
			STATUS current
			DESCRIPTION
				"A threshold for the sampled statistic.  When the
				current sampled value is less than or equal to this
				threshold, and the value at the last sampling
				interval was greater than this threshold, a single
				event will be generated.  A single event will also
				be generated if the first sample after this entry
				becomes valid is less than or equal to this
				threshold and the associated alarmStartupAlarm is
				equal to fallingAlarm(2) or risingOrFallingAlarm(3).
				
				After a falling event is generated, another such event
				will not be generated until the sampled value
				rises above this threshold and reaches the
				alarmRisingThreshold.
				
				This object may not be modified if the associated
				fkAlarmStatus object is equal to valid(1)."
			::= { fkAlarmEntry 8 }

		
--  1.3.6.1.4.1.10428 9 1.101.9.2.1.1.9
		-- 1.3.6.1.4.1.10428 9 1.101.9.2.1.1.9
		fkAlarmRisingEventIndex OBJECT-TYPE
			SYNTAX INTEGER (0..65535)
			MAX-ACCESS read-only
			STATUS current
			DESCRIPTION
				"The index of the eventEntry that is
				used when a rising threshold is crossed.  The
				eventEntry identified by a particular value of
				this index is the same as identified by the same value
				of the eventIndex object.  If there is no
				corresponding entry in the eventTable, then
				no association exists.  In particular, if this value
				is zero, no associated event will be generated, as
				zero is not a valid event index.
				
				This object may not be modified if the associated
				fkAlarmStatus object is equal to valid(1)."
			::= { fkAlarmEntry 9 }

		
--  1.3.6.1.4.1.10428 9 1.101.9.2.1.1.10
		-- 1.3.6.1.4.1.10428 9 1.101.9.2.1.1.10
		fkAlarmFallingEventIndex OBJECT-TYPE
			SYNTAX INTEGER (0..65535)
			MAX-ACCESS read-only
			STATUS current
			DESCRIPTION
				"The index of the eventEntry that is
				used when a falling threshold is crossed.  The
				eventEntry identified by a particular value of
				this index is the same as identified by the same value
				of the eventIndex object.  If there is no
				corresponding entry in the eventTable, then
				no association exists.  In particular, if this value
				is zero, no associated event will be generated, as
				zero is not a valid event index.
				
				This object may not be modified if the associated
				fkAlarmStatus object is equal to valid(1)."
			::= { fkAlarmEntry 10 }

		
--  1.3.6.1.4.1.10428 9 1.101.9.2.1.1.11
		-- 1.3.6.1.4.1.10428 9 1.101.9.2.1.1.11
		fkAlarmOwner OBJECT-TYPE
			SYNTAX OwnerString
			MAX-ACCESS read-only
			STATUS current
			DESCRIPTION
				"The entity that configured this entry and is
				therefore using the resources assigned to it."
			::= { fkAlarmEntry 11 }

		
--  1.3.6.1.4.1.10428 9 1.101.9.2.1.1.12
		-- 1.3.6.1.4.1.10428 9 1.101.9.2.1.1.12
		fkAlarmStatus OBJECT-TYPE
			SYNTAX FkEntryStatus
			MAX-ACCESS read-only
			STATUS current
			DESCRIPTION
				"The status of this alarm entry."
			::= { fkAlarmEntry 12 }

		
--  1.3.6.1.4.1.10428 9 1.101.9.2.2
		-- 1.3.6.1.4.1.10428 9 1.101.9.2.2
		fkAlarmControl OBJECT IDENTIFIER ::= { fkAlarm 2 }

		
--   Node definitions
-- 
-- 1.3.6.1.4.1.10428 9 1.101.9.2.2.1
		-- 1.3.6.1.4.1.10428 9 1.101.9.2.2.1
		fkAlarmControlRequest OBJECT-TYPE
			SYNTAX INTEGER
				{
				createAlarm(1),
				destroyAlarm(2),
				setAlarmProfile(3)
				}
			MAX-ACCESS read-write
			STATUS current
			DESCRIPTION
				"
				createAlarm:
				(fkAlarmControlIndex)
				fkAlarmInterval
				fkAlarmControlVariable
				fkAlarmControlSampleType
				fkAlarmControlStartupAlarm
				fkAlarmControlRisingThreshold
				fkAlarmControlFallingThreshold
				fkAlarmControlRisingEventIndex
				fkAlarmControlFallingEventIndex
				fkAlarmControlOwner
				fkAlarmControlSts
				
				destroyAlarm:
				fkAlarmControlIndex
				
				setAlarmProfile:
				fkAlarmControlIndex
				fkAlarmControlInterval
				fkAlarmControlVariable
				fkAlarmControlSampleType
				fkAlarmControlStartupAlarm
				fkAlarmControlRisingThreshold
				fkAlarmControlFallingThreshold
				fkAlarmControlRisingEventIndex
				fkAlarmControlFallingEventIndex
				fkAlarmControlOwner
				fkAlarmControlSts
				
				"
			::= { fkAlarmControl 1 }

		
--  1.3.6.1.4.1.10428 9 1.101.9.2.2.2
		-- 1.3.6.1.4.1.10428 9 1.101.9.2.2.2
		fkAlarmControlStatus OBJECT-TYPE
			SYNTAX FkControlStatusType
			MAX-ACCESS read-only
			STATUS current
			DESCRIPTION
				"The status of a user command. 
				"
			::= { fkAlarmControl 2 }

		
--  1.3.6.1.4.1.10428 9 1.101.9.2.2.3
		-- 1.3.6.1.4.1.10428 9 1.101.9.2.2.3
		fkAlarmControlTimer OBJECT-TYPE
			SYNTAX Gauge32
			MAX-ACCESS read-write
			STATUS current
			DESCRIPTION
				"The maximum wait time for the manager for a long running user command. 
				"
			::= { fkAlarmControl 3 }

		
--  1.3.6.1.4.1.10428 9 1.101.9.2.2.4
		-- 1.3.6.1.4.1.10428 9 1.101.9.2.2.4
		fkAlarmControlTimeStamp OBJECT-TYPE
			SYNTAX TimeTicks
			MAX-ACCESS read-only
			STATUS current
			DESCRIPTION
				"The time stamp of the last command (end of command)."
			::= { fkAlarmControl 4 }

		
--  1.3.6.1.4.1.10428 9 1.101.9.2.2.5
		-- 1.3.6.1.4.1.10428 9 1.101.9.2.2.5
		fkAlarmControlReqResult OBJECT-TYPE
			SYNTAX FkControlRequestResultType
			MAX-ACCESS read-only
			STATUS current
			DESCRIPTION
				"The result of the last user command."
			::= { fkAlarmControl 5 }

		
--  1.3.6.1.4.1.10428 9 1.101.9.2.2.6
		-- 1.3.6.1.4.1.10428 9 1.101.9.2.2.6
		fkAlarmControlIndex OBJECT-TYPE
			SYNTAX INTEGER (1..65535)
			MAX-ACCESS read-write
			STATUS current
			DESCRIPTION
				"Description."
			::= { fkAlarmControl 6 }

		
--  1.3.6.1.4.1.10428 9 1.101.9.2.2.7
		-- 1.3.6.1.4.1.10428 9 1.101.9.2.2.7
		fkAlarmControlInterval OBJECT-TYPE
			SYNTAX Integer32
			MAX-ACCESS read-write
			STATUS current
			DESCRIPTION
				"The interval in seconds over which the data is
				sampled and compared with the rising and falling
				thresholds.  When setting this variable, care
				should be taken in the case of deltaValue
				sampling - the interval should be set short enough
				that the sampled variable is very unlikely to
				increase or decrease by more than 2^31 - 1 during
				a single sampling interval.
				
				This object may not be modified if the associated
				alarmStatus object is equal to valid(1)."
			::= { fkAlarmControl 7 }

		
--  1.3.6.1.4.1.10428 9 1.101.9.2.2.8
		-- 1.3.6.1.4.1.10428 9 1.101.9.2.2.8
		fkAlarmControlVariable OBJECT-TYPE
			SYNTAX OBJECT IDENTIFIER
			MAX-ACCESS read-write
			STATUS current
			DESCRIPTION
				"The object identifier of the particular variable to
				be sampled.  Only variables that resolve to an ASN.1
				primitive type of INTEGER (INTEGER, Counter, Gauge,
				or TimeTicks) may be sampled.
				
				Because SNMP access control is articulated entirely
				in terms of the contents of MIB views, no access
				control mechanism exists that can restrict the value
				of this object to identify only those objects that
				exist in a particular MIB view.  Because there is
				thus no acceptable means of restricting the read
				access that could be obtained through the alarm
				mechanism, the probe must only grant write access to
				this object in those views that have read access to
				all objects on the probe.
				
				During a set operation, if the supplied variable
				name is not available in the selected MIB view, a
				badValue error must be returned.  If at any time the
				variable name of an establifkd alarmEntry is no
				longer available in the selected MIB view, the probe
				must change the status of this alarmEntry to
				invalid(4).
				
				This object may not be modified if the associated
				alarmStatus object is equal to valid(1)."
			::= { fkAlarmControl 8 }

		
--  1.3.6.1.4.1.10428 9 1.101.9.2.2.9
		-- 1.3.6.1.4.1.10428 9 1.101.9.2.2.9
		fkAlarmControlSampleType OBJECT-TYPE
			SYNTAX INTEGER
				{
				absoluteValue(1),
				deltaValue(2)
				}
			MAX-ACCESS read-write
			STATUS current
			DESCRIPTION
				"The method of sampling the selected variable and
				calculating the value to be compared against the
				thresholds.  If the value of this object is
				absoluteValue(1), the value of the selected variable
				will be compared directly with the thresholds at the
				end of the sampling interval.  If the value of this
				object is deltaValue(2), the value of the selected
				variable at the last sample will be subtracted from
				the current value, and the difference compared with
				the thresholds.
				
				This object may not be modified if the associated
				alarmStatus object is equal to valid(1)."
			::= { fkAlarmControl 9 }

		
--  1.3.6.1.4.1.10428 9 1.101.9.2.2.10
		-- 1.3.6.1.4.1.10428 9 1.101.9.2.2.10
		fkAlarmControlStartupAlarm OBJECT-TYPE
			SYNTAX INTEGER
				{
				risingAlarm(1),
				fallingAlarm(2),
				risingOrFallingAlarm(3)
				}
			MAX-ACCESS read-write
			STATUS current
			DESCRIPTION
				"The alarm that may be sent when this entry is first
				set to valid.  If the first sample after this entry
				becomes valid is greater than or equal to the
				risingThreshold and alarmStartupAlarm is equal to
				risingAlarm(1) or risingOrFallingAlarm(3), then a
				single rising alarm will be generated.  If the first
				sample after this entry becomes valid is less than
				or equal to the fallingThreshold and
				alarmStartupAlarm is equal to fallingAlarm(2) or
				risingOrFallingAlarm(3), then a single falling alarm
				will be generated.
				
				This object may not be modified if the associated
				alarmStatus object is equal to valid(1)."
			::= { fkAlarmControl 10 }

		
--  1.3.6.1.4.1.10428 9 1.101.9.2.2.11
		-- 1.3.6.1.4.1.10428 9 1.101.9.2.2.11
		fkAlarmControlRisingThreshold OBJECT-TYPE
			SYNTAX Integer32
			MAX-ACCESS read-write
			STATUS current
			DESCRIPTION
				"A threshold for the sampled statistic.  When the
				current sampled value is greater than or equal to
				this threshold, and the value at the last sampling
				interval was less than this threshold, a single
				event will be generated.  A single event will also
				be generated if the first sample after this entry
				becomes valid is greater than or equal to this
				threshold and the associated alarmStartupAlarm is
				equal to risingAlarm(1) or risingOrFallingAlarm(3).
				
				After a rising event is generated, another such event
				will not be generated until the sampled value
				falls below this threshold and reaches the
				alarmFallingThreshold.
				
				This object may not be modified if the associated
				alarmStatus object is equal to valid(1)."
			::= { fkAlarmControl 11 }

		
--  1.3.6.1.4.1.10428 9 1.101.9.2.2.12
		-- 1.3.6.1.4.1.10428 9 1.101.9.2.2.12
		fkAlarmControlFallingThreshold OBJECT-TYPE
			SYNTAX Integer32
			MAX-ACCESS read-write
			STATUS current
			DESCRIPTION
				"A threshold for the sampled statistic.  When the
				current sampled value is less than or equal to this
				threshold, and the value at the last sampling
				interval was greater than this threshold, a single
				event will be generated.  A single event will also
				be generated if the first sample after this entry
				becomes valid is less than or equal to this
				threshold and the associated alarmStartupAlarm is
				equal to fallingAlarm(2) or risingOrFallingAlarm(3).
				
				After a falling event is generated, another such event
				will not be generated until the sampled value
				rises above this threshold and reaches the
				alarmRisingThreshold.
				
				This object may not be modified if the associated
				fkAlarmStatus object is equal to valid(1)."
			::= { fkAlarmControl 12 }

		
--  1.3.6.1.4.1.10428 9 1.101.9.2.2.13
		-- 1.3.6.1.4.1.10428 9 1.101.9.2.2.13
		fkAlarmControlRisingEventIndex OBJECT-TYPE
			SYNTAX INTEGER (0..65535)
			MAX-ACCESS read-write
			STATUS current
			DESCRIPTION
				"The index of the eventEntry that is
				used when a rising threshold is crossed.  The
				eventEntry identified by a particular value of
				this index is the same as identified by the same value
				of the eventIndex object.  If there is no
				corresponding entry in the eventTable, then
				no association exists.  In particular, if this value
				is zero, no associated event will be generated, as
				zero is not a valid event index.
				
				This object may not be modified if the associated
				fkAlarmStatus object is equal to valid(1)."
			::= { fkAlarmControl 13 }

		
--  1.3.6.1.4.1.10428 9 1.101.9.2.2.14
		-- 1.3.6.1.4.1.10428 9 1.101.9.2.2.14
		fkAlarmControlFallingEventIndex OBJECT-TYPE
			SYNTAX INTEGER (0..65535)
			MAX-ACCESS read-write
			STATUS current
			DESCRIPTION
				"The index of the eventEntry that is
				used when a falling threshold is crossed.  The
				eventEntry identified by a particular value of
				this index is the same as identified by the same value
				of the eventIndex object.  If there is no
				corresponding entry in the eventTable, then
				no association exists.  In particular, if this value
				is zero, no associated event will be generated, as
				zero is not a valid event index.
				
				This object may not be modified if the associated
				fkAlarmStatus object is equal to valid(1)."
			::= { fkAlarmControl 14 }

		
--  1.3.6.1.4.1.10428 9 1.101.9.2.2.15
		-- 1.3.6.1.4.1.10428 9 1.101.9.2.2.15
		fkAlarmControlOwner OBJECT-TYPE
			SYNTAX OwnerString
			MAX-ACCESS read-write
			STATUS current
			DESCRIPTION
				"The entity that configured this entry and is
				therefore using the resources assigned to it."
			::= { fkAlarmControl 15 }

		
--  1.3.6.1.4.1.10428 9 1.101.9.2.2.16
		-- 1.3.6.1.4.1.10428 9 1.101.9.2.2.16
		fkAlarmControlSts OBJECT-TYPE
			SYNTAX FkEntryStatus
			MAX-ACCESS read-write
			STATUS current
			DESCRIPTION
				"The status of this alarm entry."
			::= { fkAlarmControl 16 }

		
--  1.3.6.1.4.1.10428 9 1.101.9.2.3
		-- 1.3.6.1.4.1.10428 9 1.101.9.2.3
		fkAlarmNotification OBJECT IDENTIFIER ::= { fkAlarm 3 }

		
--  1.3.6.1.4.1.10428 9 1.101.9.2.3.1
		-- 1.3.6.1.4.1.10428 9 1.101.9.2.3.1
		fkAlarmCreated NOTIFICATION-TYPE
			OBJECTS { fkAlarmInterval, fkAlarmVariable, fkAlarmSampleType, fkAlarmStartupAlarm, fkAlarmRisingThreshold, 
				fkAlarmFallingThreshold, fkAlarmRisingEventIndex, fkAlarmFallingEventIndex, fkAlarmOwner, fkAlarmStatus, 
				fkAlarmControlRequest, fkAlarmControlTimeStamp, fkAlarmControlReqResult }
			STATUS current
			DESCRIPTION 
				"Description."
			::= { fkAlarmNotification 1 }

		
--  1.3.6.1.4.1.10428 9 1.101.9.2.3.2
		-- 1.3.6.1.4.1.10428 9 1.101.9.2.3.2
		fkAlarmDestroyed NOTIFICATION-TYPE
			OBJECTS { fkAlarmIndex, fkAlarmControlRequest, fkAlarmControlTimeStamp, fkAlarmControlReqResult }
			STATUS current
			DESCRIPTION 
				"Description."
			::= { fkAlarmNotification 2 }

		
--  1.3.6.1.4.1.10428 9 1.101.9.2.3.3
		-- 1.3.6.1.4.1.10428 9 1.101.9.2.3.3
		fkAlarmProfileChanged NOTIFICATION-TYPE
			OBJECTS { fkAlarmControlRequest, fkAlarmControlTimeStamp, fkAlarmControlReqResult, fkAlarmInterval, fkAlarmVariable, 
				fkAlarmSampleType, fkAlarmStartupAlarm, fkAlarmRisingThreshold, fkAlarmFallingThreshold, fkAlarmRisingEventIndex, 
				fkAlarmFallingEventIndex, fkAlarmOwner, fkAlarmStatus }
			STATUS current
			DESCRIPTION 
				"Description."
			::= { fkAlarmNotification 3 }

		
--   The status of a table entry.
-- 
-- Setting this object to the value invalid(4) has the
-- effect of invalidating the corresponding entry.
-- That is, it effectively disassociates the mapping
-- identified with said entry.
-- It is an implementation-specific matter as to whether
-- the agent removes an invalidated entry from the table.
-- Accordingly, management stations must be prepared to
-- receive tabular information from agents that
-- corresponds to entries currently not in use.  Proper
-- interpretation of such entries requires examination
-- of the relevant EntryStatus object.
-- 
-- An existing instance of this object cannot be set to
-- createRequest(2).  This object may only be set to
-- createRequest(2) when this instance is created.  When
-- this object is created, the agent may wish to create
-- supplemental object instances with default values
-- to complete a conceptual row in this table.  Because
-- the creation of these default objects is entirely at
-- the option of the agent, the manager must not assume
-- that any will be created, but may make use of any that
-- are created. Immediately after completing the create
-- operation, the agent must set this object to
-- underCreation(3).
-- 
-- When in the underCreation(3) state, an entry is
-- allowed to exist in a possibly incomplete, possibly
-- inconsistent state, usually to allow it to be
-- modified in mutiple PDUs.  When in this state, an
-- entry is not fully active.  Entries shall exist in
-- the underCreation(3) state until the management
-- station is finifkd configuring the entry and sets
-- this object to valid(1) or aborts, setting this
-- object to invalid(4).  If the agent determines that
-- an entry has been in the underCreation(3) state for
-- an abnormally long time, it may decide that the
-- management station has crafkd.  If the agent makes
-- this decision, it may set this object to invalid(4)
-- to reclaim the entry.  A prudent agent will
-- understand that the management station may need to
-- wait for human input and will allow for that
-- possibility in its determination of this abnormally
-- long period.
-- 
-- An entry in the valid(1) state is fully configured and
-- consistent and fully represents the configuration or
-- operation such a row is intended to represent.  For
-- example, it could be a statistical function that is
-- configured and active, or a filter that is available
-- in the list of filters processed by the packet capture
-- process.
-- 
-- A manager is restricted to changing the state of an
-- entry in the following ways:
-- 
--                       create   under
--      To:       valid  Request  Creation  invalid
-- From:
-- valid             OK       NO        OK       OK
-- createRequest    N/A      N/A       N/A      N/A
-- underCreation     OK       NO        OK       OK
-- invalid           NO       NO        NO       OK
-- nonExistent       NO       OK        NO       OK
-- 
-- In the table above, it is not applicable to move the
-- state from the createRequest state to any other
-- state because the manager will never find the
-- variable in that state.  The nonExistent state is
-- not a value of the enumeration, rather it means that
-- the entryStatus variable does not exist at all.
-- 
-- An agent may allow an entryStatus variable to change
-- state in additional ways, so long as the semantics
-- of the states are followed.  This allowance is made
-- to ease the implementation of the agent and is made
-- despite the fact that managers should never
-- excercise these additional state transitions.
-- 1.3.6.1.4.1.10428 9 1.101.9.3
		-- 1.3.6.1.4.1.10428 9 1.101.9.3
		fkEvent OBJECT IDENTIFIER ::= { fkRmon 3 }

		
--   The fkEvent Group
-- Implementation of the Event group is optional.
-- 
-- The Event group controls the generation and notification
-- of events from this device.  Each entry in the eventTable
-- describes the parameters of the event that can be
-- triggered. Each event entry is fired by an associated
-- condition located elsewhere in the MIB.  An event entry
-- may also be associated- with a function elsewhere in the
-- MIB that will be executed when the event is generated.  For
-- example, a channel may be turned on or off by the firing
-- of an event.
-- 
-- Each eventEntry may optionally specify that a log entry
-- be created on its behalf whenever the event occurs.
-- Each entry may also specify that notification should
-- occur by way of SNMP trap messages.  In this case, the
-- community for the trap message is given in the associated
-- eventCommunity object.  The enterprise and specific trap
-- fields of the trap are determined by the condition that
-- triggered the event.  Two traps are defined: risingAlarm
-- and fallingAlarm.  If the eventTable is triggered by a
-- condition specified elsewhere, the enterprise and
-- specific trap fields must be specified for traps
-- generated for that condition.
-- 1.3.6.1.4.1.10428 9 1.101.9.3.1
		-- 1.3.6.1.4.1.10428 9 1.101.9.3.1
		fkEventTable OBJECT-TYPE
			SYNTAX SEQUENCE OF FkEventEntry
			MAX-ACCESS not-accessible
			STATUS current
			DESCRIPTION
				"A list of events to be generated."
			::= { fkEvent 1 }

		
--  1.3.6.1.4.1.10428 9 1.101.9.3.1.1
		-- 1.3.6.1.4.1.10428 9 1.101.9.3.1.1
		fkEventEntry OBJECT-TYPE
			SYNTAX FkEventEntry
			MAX-ACCESS not-accessible
			STATUS current
			DESCRIPTION
				"A set of parameters that describe an event to be
				generated when certain conditions are met.  As an
				example, an instance of the fkEventLastTimeSent object
				might be named fkEventLastTimeSent.6"
			INDEX { fkEventIndex }
			::= { fkEventTable 1 }

		
		FkEventEntry ::=
			SEQUENCE { 
				fkEventIndex
					INTEGER,
				fkEventDescription
					DisplayString,
				fkEventType
					INTEGER,
				fkEventCommunity
					OCTET STRING,
				fkEventLastTimeSent
					TimeTicks,
				fkEventOwner
					OwnerString,
				fkEventStatus
					FkEntryStatus
			 }

--  1.3.6.1.4.1.10428 9 1.101.9.3.1.1.1
		-- 1.3.6.1.4.1.10428 9 1.101.9.3.1.1.1
		fkEventIndex OBJECT-TYPE
			SYNTAX INTEGER (1..65535)
			MAX-ACCESS read-only
			STATUS current
			DESCRIPTION
				"An index that uniquely identifies an entry in the
				event table.  Each such entry defines one event that
				is to be generated when the appropriate conditions
				occur."
			::= { fkEventEntry 1 }

		
--  1.3.6.1.4.1.10428 9 1.101.9.3.1.1.2
		-- 1.3.6.1.4.1.10428 9 1.101.9.3.1.1.2
		fkEventDescription OBJECT-TYPE
			SYNTAX DisplayString (SIZE (0..127))
			MAX-ACCESS read-only
			STATUS current
			DESCRIPTION
				"A comment describing this event entry."
			::= { fkEventEntry 2 }

		
--   send an SNMP trap
-- 1.3.6.1.4.1.10428 9 1.101.9.3.1.1.3
		-- 1.3.6.1.4.1.10428 9 1.101.9.3.1.1.3
		fkEventType OBJECT-TYPE
			SYNTAX INTEGER
				{
				none(1),
				log(2),
				snmpTrap(3),
				logAndTrap(4)
				}
			MAX-ACCESS read-only
			STATUS current
			DESCRIPTION
				"The type of notification that the probe will make
				about this event.  In the case of log, an entry is
				made in the log table for each event.  In the case of
				snmp-trap, an SNMP trap is sent to one or more
				management stations."
			::= { fkEventEntry 3 }

		
--  1.3.6.1.4.1.10428 9 1.101.9.3.1.1.4
		-- 1.3.6.1.4.1.10428 9 1.101.9.3.1.1.4
		fkEventCommunity OBJECT-TYPE
			SYNTAX OCTET STRING (SIZE (0..127))
			MAX-ACCESS read-only
			STATUS current
			DESCRIPTION
				"If an SNMP trap is to be sent, it will be sent to
				the SNMP community specified by this octet string.
				In the future this table will be extended to include
				the party security mechanism.  This object shall be
				set to a string of length zero if it is intended that
				that mechanism be used to specify the destination of
				the trap."
			::= { fkEventEntry 4 }

		
--  1.3.6.1.4.1.10428 9 1.101.9.3.1.1.5
		-- 1.3.6.1.4.1.10428 9 1.101.9.3.1.1.5
		fkEventLastTimeSent OBJECT-TYPE
			SYNTAX TimeTicks
			MAX-ACCESS read-only
			STATUS current
			DESCRIPTION
				"The value of sysUpTime at the time this event
				entry last generated an event.  If this entry has
				not generated any events, this value will be
				zero."
			::= { fkEventEntry 5 }

		
--  1.3.6.1.4.1.10428 9 1.101.9.3.1.1.6
		-- 1.3.6.1.4.1.10428 9 1.101.9.3.1.1.6
		fkEventOwner OBJECT-TYPE
			SYNTAX OwnerString
			MAX-ACCESS read-only
			STATUS current
			DESCRIPTION
				"The entity that configured this entry and is
				therefore using the resources assigned to it.
				
				If this object contains a string starting with
				'monitor' and has associated entries in the log
				table, all connected management stations should
				retrieve those log entries, as they may have
				significance to all management stations connected to
				this device"
			::= { fkEventEntry 6 }

		
--  1.3.6.1.4.1.10428 9 1.101.9.3.1.1.7
		-- 1.3.6.1.4.1.10428 9 1.101.9.3.1.1.7
		fkEventStatus OBJECT-TYPE
			SYNTAX FkEntryStatus
			MAX-ACCESS read-only
			STATUS current
			DESCRIPTION
				"The status of this event entry.
				
				If this object is not equal to valid(1), all
				associated log entries shall be deleted by the
				agent."
			::= { fkEventEntry 7 }

		
--  1.3.6.1.4.1.10428 9 1.101.9.3.2
		-- 1.3.6.1.4.1.10428 9 1.101.9.3.2
		fkEventControl OBJECT IDENTIFIER ::= { fkEvent 2 }

		
--   Node definitions
-- 
-- 1.3.6.1.4.1.10428 9 1.101.9.3.2.1
		-- 1.3.6.1.4.1.10428 9 1.101.9.3.2.1
		fkEventControlRequest OBJECT-TYPE
			SYNTAX INTEGER
				{
				createEvent(1),
				destroyEvent(2),
				setEventProfile(3)
				}
			MAX-ACCESS read-write
			STATUS current
			DESCRIPTION
				"
				createEvent:
				(fkEventControlIndex)
				fkEventControlDescription
				fkEventControlType
				fkEventControlCommunity
				fkEventControlOwner
				fkEventControlSts
				
				destroyEvent:
				fkEventControlIndex
				
				setEventProfile:
				fkEventControlIndex
				fkEventControlDescription
				fkEventControlType
				fkEventControlCommunity
				fkEventControlOwner
				fkEventControlSts
				
				"
			::= { fkEventControl 1 }

		
--  1.3.6.1.4.1.10428 9 1.101.9.3.2.2
		-- 1.3.6.1.4.1.10428 9 1.101.9.3.2.2
		fkEventControlStatus OBJECT-TYPE
			SYNTAX FkControlStatusType
			MAX-ACCESS read-only
			STATUS current
			DESCRIPTION
				"The status of a user command. 
				"
			::= { fkEventControl 2 }

		
--  1.3.6.1.4.1.10428 9 1.101.9.3.2.3
		-- 1.3.6.1.4.1.10428 9 1.101.9.3.2.3
		fkEventControlTimer OBJECT-TYPE
			SYNTAX Gauge32
			MAX-ACCESS read-write
			STATUS current
			DESCRIPTION
				"The maximum wait time for the manager for a long running user command. 
				"
			::= { fkEventControl 3 }

		
--  1.3.6.1.4.1.10428 9 1.101.9.3.2.4
		-- 1.3.6.1.4.1.10428 9 1.101.9.3.2.4
		fkEventControlTimeStamp OBJECT-TYPE
			SYNTAX TimeTicks
			MAX-ACCESS read-only
			STATUS current
			DESCRIPTION
				"The time stamp of the last command (end of command)."
			::= { fkEventControl 4 }

		
--  1.3.6.1.4.1.10428 9 1.101.9.3.2.5
		-- 1.3.6.1.4.1.10428 9 1.101.9.3.2.5
		fkEventControlReqResult OBJECT-TYPE
			SYNTAX FkControlRequestResultType
			MAX-ACCESS read-only
			STATUS current
			DESCRIPTION
				"The result of the last user command."
			::= { fkEventControl 5 }

		
--  1.3.6.1.4.1.10428 9 1.101.9.3.2.6
		-- 1.3.6.1.4.1.10428 9 1.101.9.3.2.6
		fkEventControlIndex OBJECT-TYPE
			SYNTAX Integer32 (1..65535)
			MAX-ACCESS read-write
			STATUS current
			DESCRIPTION
				"Description."
			::= { fkEventControl 6 }

		
--  1.3.6.1.4.1.10428 9 1.101.9.3.2.7
		-- 1.3.6.1.4.1.10428 9 1.101.9.3.2.7
		fkEventControlDescription OBJECT-TYPE
			SYNTAX DisplayString (SIZE (0..127))
			MAX-ACCESS read-write
			STATUS current
			DESCRIPTION
				"A comment describing this event entry."
			::= { fkEventControl 7 }

		
--   send an SNMP trap
-- 1.3.6.1.4.1.10428 9 1.101.9.3.2.8
		-- 1.3.6.1.4.1.10428 9 1.101.9.3.2.8
		fkEventControlType OBJECT-TYPE
			SYNTAX INTEGER
				{
				none(1),
				log(2),
				snmpTrap(3),
				logAndTrap(4)
				}
			MAX-ACCESS read-write
			STATUS current
			DESCRIPTION
				"The type of notification that the probe will make
				about this event.  In the case of log, an entry is
				made in the log table for each event.  In the case of
				snmp-trap, an SNMP trap is sent to one or more
				management stations."
			::= { fkEventControl 8 }

		
--  1.3.6.1.4.1.10428 9 1.101.9.3.2.9
		-- 1.3.6.1.4.1.10428 9 1.101.9.3.2.9
		fkEventControlCommunity OBJECT-TYPE
			SYNTAX OCTET STRING (SIZE (0..127))
			MAX-ACCESS read-write
			STATUS current
			DESCRIPTION
				"If an SNMP trap is to be sent, it will be sent to
				the SNMP community specified by this octet string.
				In the future this table will be extended to include
				the party security mechanism.  This object shall be
				set to a string of length zero if it is intended that
				that mechanism be used to specify the destination of
				the trap."
			::= { fkEventControl 9 }

		
--  1.3.6.1.4.1.10428 9 1.101.9.3.2.10
		-- 1.3.6.1.4.1.10428 9 1.101.9.3.2.10
		fkEventControlOwner OBJECT-TYPE
			SYNTAX OwnerString
			MAX-ACCESS read-write
			STATUS current
			DESCRIPTION
				"The entity that configured this entry and is
				therefore using the resources assigned to it.
				
				If this object contains a string starting with
				'monitor' and has associated entries in the log
				table, all connected management stations should
				retrieve those log entries, as they may have
				significance to all management stations connected to
				this device"
			::= { fkEventControl 10 }

		
--  1.3.6.1.4.1.10428 9 1.101.9.3.2.11
		-- 1.3.6.1.4.1.10428 9 1.101.9.3.2.11
		fkEventControlSts OBJECT-TYPE
			SYNTAX FkEntryStatus
			MAX-ACCESS read-write
			STATUS current
			DESCRIPTION
				"The status of this event entry.
				
				If this object is not equal to valid(1), all
				associated log entries shall be deleted by the
				agent."
			::= { fkEventControl 11 }

		
--  1.3.6.1.4.1.10428 9 1.101.9.3.3
		-- 1.3.6.1.4.1.10428 9 1.101.9.3.3
		fkEventNotification OBJECT IDENTIFIER ::= { fkEvent 3 }

		
--  1.3.6.1.4.1.10428 9 1.101.9.3.3.1
		-- 1.3.6.1.4.1.10428 9 1.101.9.3.3.1
		fkEventCreated NOTIFICATION-TYPE
			OBJECTS { fkEventDescription, fkEventType, fkEventCommunity, fkEventOwner, fkEventStatus, 
				fkEventControlRequest, fkEventControlTimeStamp, fkEventControlReqResult }
			STATUS current
			DESCRIPTION 
				"Description."
			::= { fkEventNotification 1 }

		
--  1.3.6.1.4.1.10428 9 1.101.9.3.3.2
		-- 1.3.6.1.4.1.10428 9 1.101.9.3.3.2
		fkEventDestroyed NOTIFICATION-TYPE
			OBJECTS { fkEventIndex, fkEventControlRequest, fkEventControlTimeStamp, fkEventControlReqResult }
			STATUS current
			DESCRIPTION 
				"Description."
			::= { fkEventNotification 2 }

		
--  1.3.6.1.4.1.10428 9 1.101.9.3.3.3
		-- 1.3.6.1.4.1.10428 9 1.101.9.3.3.3
		fkEventProfileChanged NOTIFICATION-TYPE
			OBJECTS { fkEventDescription, fkEventType, fkEventCommunity, fkEventOwner, fkEventStatus, 
				fkEventControlRequest, fkEventControlTimeStamp, fkEventControlReqResult }
			STATUS current
			DESCRIPTION 
				"Description."
			::= { fkEventNotification 3 }

		
--  1.3.6.1.4.1.10428 9 1.101.9.4
		-- 1.3.6.1.4.1.10428 9 1.101.9.4
		fkStatistics OBJECT IDENTIFIER ::= { fkRmon 4 }

		
--  1.3.6.1.4.1.10428 9 1.101.9.4.1
		-- 1.3.6.1.4.1.10428 9 1.101.9.4.1
		fkEtherStats OBJECT IDENTIFIER ::= { fkStatistics 1 }

		
--  1.3.6.1.4.1.10428 9 1.101.9.4.1.1
		-- 1.3.6.1.4.1.10428 9 1.101.9.4.1.1
		fkEtherStatsTable OBJECT-TYPE
			SYNTAX SEQUENCE OF FkEtherStatsEntry
			MAX-ACCESS not-accessible
			STATUS current
			DESCRIPTION
				"Description."
			::= { fkEtherStats 1 }

		
--  1.3.6.1.4.1.10428 9 1.101.9.4.1.1.1
		-- 1.3.6.1.4.1.10428 9 1.101.9.4.1.1.1
		fkEtherStatsEntry OBJECT-TYPE
			SYNTAX FkEtherStatsEntry
			MAX-ACCESS not-accessible
			STATUS current
			DESCRIPTION
				"Description."
			INDEX { fkEtherStatsIndex }
			::= { fkEtherStatsTable 1 }

		
		FkEtherStatsEntry ::=
			SEQUENCE { 
				fkEtherStatsIndex
					INTEGER,
				fkEtherStatsDataSource
					OBJECT IDENTIFIER,
				fkEtherStatsDropEvents
					Counter32,
				fkEtherStatsOctets
					Counter32,
				fkEtherStatsPkts
					Counter32,
				fkEtherStatsBroadcastPkts
					Counter32,
				fkEtherStatsMulticastPkts
					Counter32,
				fkEtherStatsCRCAlignErrors
					Counter32,
				fkEtherStatsUndersizePkts
					Counter32,
				fkEtherStatsOversizePkts
					Counter32,
				fkEtherStatsFragments
					Counter32,
				fkEtherStatsJabbers
					Counter32,
				fkEtherStatsCollisions
					Counter32,
				fkEtherStatsPkts64Octets
					Counter32,
				fkEtherStatsPkts65to127Octets
					Counter32,
				fkEtherStatsPkts128to255Octets
					Counter32,
				fkEtherStatsPkts256to511Octets
					Counter32,
				fkEtherStatsPkts512to1023Octets
					Counter32,
				fkEtherStatsPkts1024to1518Octets
					Counter32,
				fkEtherStatsOwner
					OCTET STRING,
				fkEtherStatsStatus
					FkEntryStatus,
				fkEtherStatsClearedTime
					TimeTicks
			 }

--  1.3.6.1.4.1.10428 9 1.101.9.4.1.1.1.1
		-- 1.3.6.1.4.1.10428 9 1.101.9.4.1.1.1.1
		fkEtherStatsIndex OBJECT-TYPE
			SYNTAX INTEGER (1..65535)
			MAX-ACCESS read-only
			STATUS current
			DESCRIPTION
				"The value of this object uniquely identifies this fkEtherStats entry"
			::= { fkEtherStatsEntry 1 }

		
--  1.3.6.1.4.1.10428 9 1.101.9.4.1.1.1.2
		-- 1.3.6.1.4.1.10428 9 1.101.9.4.1.1.1.2
		fkEtherStatsDataSource OBJECT-TYPE
			SYNTAX OBJECT IDENTIFIER
			MAX-ACCESS read-only
			STATUS current
			DESCRIPTION
				"This object identifies the source of the data that
				this fkEtherStats entry is configured to analyze.  This
				source can be any ethernet interface on this device.
				In order to identify a particular interface, this
				object shall identify the instance of the ifIndex
				object, defined in RFC 1213 and RFC 1573 [4,6], for
				the desired interface.  For example, if an entry
				were to receive data from interface #1, this object
				would be set to ifIndex.1.
				 	
				The statistics in this group reflect all packets
				on the local network segment attached to the
				identified interface.
				 	
				An agent may or may not be able to tell if
				fundamental changes to the media of the interface
				have occurred and necessitate an invalidation of
				this entry.  For example, a hot-pluggable ethernet
				card could be pulled out and replaced by a
				token-ring card.  In such a case, if the agent has
				such knowledge of the change, it is recommended that
				it invalidate this entry.
				 	
				This object may not be modified if the associated
				fkEtherStatsStatus object is equal to valid(1)."
			::= { fkEtherStatsEntry 2 }

		
--  1.3.6.1.4.1.10428 9 1.101.9.4.1.1.1.3
		-- 1.3.6.1.4.1.10428 9 1.101.9.4.1.1.1.3
		fkEtherStatsDropEvents OBJECT-TYPE
			SYNTAX Counter32
			MAX-ACCESS read-only
			STATUS current
			DESCRIPTION
				"The total number of events in which packets
				were dropped by the probe due to lack of resources.
				Note that this number is not necessarily the number of
				packets dropped; it is just the number of times this
				condition has been detected."
			::= { fkEtherStatsEntry 3 }

		
--  1.3.6.1.4.1.10428 9 1.101.9.4.1.1.1.4
		-- 1.3.6.1.4.1.10428 9 1.101.9.4.1.1.1.4
		fkEtherStatsOctets OBJECT-TYPE
			SYNTAX Counter32
			MAX-ACCESS read-only
			STATUS current
			DESCRIPTION
				"The total number of octets of data (including
				those in bad packets) received on the
				network (excluding framing bits but including
				FCS octets).
				 	
				This object can be used as a reasonable estimate of
				ethernet utilization.  If greater precision is
				desired, the etherStatsPkts and etherStatsOctets
				objects should be sampled before and after a common
				interval.  The differences in the sampled values are
				Pkts and Octets, respectively, and the number of
				seconds in the interval is Interval.  These values
				are used to calculate the Utilization as follows:
				 	
				              Pkts * (9.6 + 6.4) + (Octets * .8)
				Utilization = -------------------------------------
				                   Interval * 10,000
				 	
				The result of this equation is the value Utilization
				which is the percent utilization of the ethernet
				segment on a scale of 0 to 100 percent.
				"
			::= { fkEtherStatsEntry 4 }

		
--  1.3.6.1.4.1.10428 9 1.101.9.4.1.1.1.5
		-- 1.3.6.1.4.1.10428 9 1.101.9.4.1.1.1.5
		fkEtherStatsPkts OBJECT-TYPE
			SYNTAX Counter32
			MAX-ACCESS read-only
			STATUS current
			DESCRIPTION
				"The total number of packets (including bad packets,
				broadcast packets, and multicast packets) received."
			::= { fkEtherStatsEntry 5 }

		
--  1.3.6.1.4.1.10428 9 1.101.9.4.1.1.1.6
		-- 1.3.6.1.4.1.10428 9 1.101.9.4.1.1.1.6
		fkEtherStatsBroadcastPkts OBJECT-TYPE
			SYNTAX Counter32
			MAX-ACCESS read-only
			STATUS current
			DESCRIPTION
				"The total number of good packets received that were
				directed to the broadcast address.  Note that this
				does not include multicast packets."
			::= { fkEtherStatsEntry 6 }

		
--  1.3.6.1.4.1.10428 9 1.101.9.4.1.1.1.7
		-- 1.3.6.1.4.1.10428 9 1.101.9.4.1.1.1.7
		fkEtherStatsMulticastPkts OBJECT-TYPE
			SYNTAX Counter32
			MAX-ACCESS read-only
			STATUS current
			DESCRIPTION
				"The total number of good packets received that were
				directed to a multicast address.  Note that this
				number does not include packets directed to the
				broadcast address.
				"
			::= { fkEtherStatsEntry 7 }

		
--  1.3.6.1.4.1.10428 9 1.101.9.4.1.1.1.8
		-- 1.3.6.1.4.1.10428 9 1.101.9.4.1.1.1.8
		fkEtherStatsCRCAlignErrors OBJECT-TYPE
			SYNTAX Counter32
			MAX-ACCESS read-only
			STATUS current
			DESCRIPTION
				"The total number of packets received that
				had a length (excluding framing bits, but
				including FCS octets) of between 64 and 1518
				octets, inclusive, but but had either a bad
				Frame Check Sequence (FCS) with an integral
				number of octets (FCS Error) or a bad FCS with
				a non-integral number of octets (Alignment Error).
				"
			::= { fkEtherStatsEntry 8 }

		
--  1.3.6.1.4.1.10428 9 1.101.9.4.1.1.1.9
		-- 1.3.6.1.4.1.10428 9 1.101.9.4.1.1.1.9
		fkEtherStatsUndersizePkts OBJECT-TYPE
			SYNTAX Counter32
			MAX-ACCESS read-only
			STATUS current
			DESCRIPTION
				"The total number of packets received that were
				less than 64 octets long (excluding framing bits,
				but including FCS octets) and were otherwise well
				formed.
				"
			::= { fkEtherStatsEntry 9 }

		
--  1.3.6.1.4.1.10428 9 1.101.9.4.1.1.1.10
		-- 1.3.6.1.4.1.10428 9 1.101.9.4.1.1.1.10
		fkEtherStatsOversizePkts OBJECT-TYPE
			SYNTAX Counter32
			MAX-ACCESS read-only
			STATUS current
			DESCRIPTION
				"The total number of packets received that were
				longer than 1518 octets (excluding framing bits,
				but including FCS octets) and were otherwise
				well formed.
				"
			::= { fkEtherStatsEntry 10 }

		
--  1.3.6.1.4.1.10428 9 1.101.9.4.1.1.1.11
		-- 1.3.6.1.4.1.10428 9 1.101.9.4.1.1.1.11
		fkEtherStatsFragments OBJECT-TYPE
			SYNTAX Counter32
			MAX-ACCESS read-only
			STATUS current
			DESCRIPTION
				"The total number of packets received that were less
				than 64 octets in length (excluding framing bits but
				including FCS octets) and had either a bad Frame
				Check Sequence (FCS) with an integral number of
				octets (FCS Error) or a bad FCS with a non-integral
				number of octets (Alignment Error).
				"
			::= { fkEtherStatsEntry 11 }

		
--  1.3.6.1.4.1.10428 9 1.101.9.4.1.1.1.12
		-- 1.3.6.1.4.1.10428 9 1.101.9.4.1.1.1.12
		fkEtherStatsJabbers OBJECT-TYPE
			SYNTAX Counter32
			MAX-ACCESS read-only
			STATUS current
			DESCRIPTION
				"The total number of packets received that were
				longer than 1518 octets (excluding framing bits,
				but including FCS octets), and had either a bad
				Frame Check Sequence (FCS) with an integral number
				of octets (FCS Error) or a bad FCS with a
				non-integral number of octets (Alignment Error).
				"
			::= { fkEtherStatsEntry 12 }

		
--  1.3.6.1.4.1.10428 9 1.101.9.4.1.1.1.13
		-- 1.3.6.1.4.1.10428 9 1.101.9.4.1.1.1.13
		fkEtherStatsCollisions OBJECT-TYPE
			SYNTAX Counter32
			MAX-ACCESS read-only
			STATUS current
			DESCRIPTION
				"The best estimate of the total number of collisions
				on this Ethernet segment.
				 	
				The value returned will depend on the location of
				the RMON probe. Section 8.2.1.3 (10BASE-5) and
				section 10.3.1.3 (10BASE-2) of IEEE standard 802.3
				states that a station must detect a collision, in
				the receive mode, if three or more stations are
				transmitting simultaneously.  A repeater port must
				detect a collision when two or more stations are
				transmitting simultaneously.  Thus a probe placed on
				a repeater port could record more collisions than a
				probe connected to a station on the same segment
				would.
				 	
				Probe location plays a much smaller role when 
				considering 10BASE-T.  14.2.1.4 (10BASE-T) of IEEE
				standard 802.3 defines a collision as the
				simultaneous presence of signals on the DO and RD
				circuits (transmitting and receiving at the same
				time).  A 10BASE-T station can only detect
				collisions when it is transmitting.  Thus probes
				placed on a station and a repeater, should report
				the same number of collisions.
				 	
				Note also that an RMON probe inside a repeater
				should ideally report collisions between the
				repeater and one or more other hosts (transmit
				collisions as defined by IEEE 802.3k) plus receiver
				collisions observed on any coax segments to which
				the repeater is connected.
				"
			::= { fkEtherStatsEntry 13 }

		
--  1.3.6.1.4.1.10428 9 1.101.9.4.1.1.1.14
		-- 1.3.6.1.4.1.10428 9 1.101.9.4.1.1.1.14
		fkEtherStatsPkts64Octets OBJECT-TYPE
			SYNTAX Counter32
			MAX-ACCESS read-only
			STATUS current
			DESCRIPTION
				"The total number of packets (including bad
				packets) received that were 64 octets in length
				(excluding framing bits but including FCS octets).
				"
			::= { fkEtherStatsEntry 14 }

		
--  1.3.6.1.4.1.10428 9 1.101.9.4.1.1.1.15
		-- 1.3.6.1.4.1.10428 9 1.101.9.4.1.1.1.15
		fkEtherStatsPkts65to127Octets OBJECT-TYPE
			SYNTAX Counter32
			MAX-ACCESS read-only
			STATUS current
			DESCRIPTION
				"The total number of packets (including bad
				packets) received that were between
				65 and 127 octets in length inclusive
				(excluding framing bits but including FCS octets)."
			::= { fkEtherStatsEntry 15 }

		
--  1.3.6.1.4.1.10428 9 1.101.9.4.1.1.1.16
		-- 1.3.6.1.4.1.10428 9 1.101.9.4.1.1.1.16
		fkEtherStatsPkts128to255Octets OBJECT-TYPE
			SYNTAX Counter32
			MAX-ACCESS read-only
			STATUS current
			DESCRIPTION
				"The total number of packets (including bad
				packets) received that were between
				128 and 255 octets in length inclusive
				(excluding framing bits but including FCS octets)."
			::= { fkEtherStatsEntry 16 }

		
--  1.3.6.1.4.1.10428 9 1.101.9.4.1.1.1.17
		-- 1.3.6.1.4.1.10428 9 1.101.9.4.1.1.1.17
		fkEtherStatsPkts256to511Octets OBJECT-TYPE
			SYNTAX Counter32
			MAX-ACCESS read-only
			STATUS current
			DESCRIPTION
				"The total number of packets (including bad
				packets) received that were between
				256 and 511 octets in length inclusive
				(excluding framing bits but including FCS octets)."
			::= { fkEtherStatsEntry 17 }

		
--  1.3.6.1.4.1.10428 9 1.101.9.4.1.1.1.18
		-- 1.3.6.1.4.1.10428 9 1.101.9.4.1.1.1.18
		fkEtherStatsPkts512to1023Octets OBJECT-TYPE
			SYNTAX Counter32
			MAX-ACCESS read-only
			STATUS current
			DESCRIPTION
				"The total number of packets (including bad
				packets) received that were between
				512 and 1023 octets in length inclusive
				(excluding framing bits but including FCS octets)."
			::= { fkEtherStatsEntry 18 }

		
--  1.3.6.1.4.1.10428 9 1.101.9.4.1.1.1.19
		-- 1.3.6.1.4.1.10428 9 1.101.9.4.1.1.1.19
		fkEtherStatsPkts1024to1518Octets OBJECT-TYPE
			SYNTAX Counter32
			MAX-ACCESS read-only
			STATUS current
			DESCRIPTION
				"The total number of packets (including bad
				packets) received that were between
				1024 and 1518 octets in length inclusive
				(excluding framing bits but including FCS octets)."
			::= { fkEtherStatsEntry 19 }

		
--  1.3.6.1.4.1.10428 9 1.101.9.4.1.1.1.20
		-- 1.3.6.1.4.1.10428 9 1.101.9.4.1.1.1.20
		fkEtherStatsOwner OBJECT-TYPE
			SYNTAX OCTET STRING
			MAX-ACCESS read-only
			STATUS current
			DESCRIPTION
				"The entity that configured this entry and is
				therefore using the resources assigned to it.
				"
			::= { fkEtherStatsEntry 20 }

		
--  1.3.6.1.4.1.10428 9 1.101.9.4.1.1.1.21
		-- 1.3.6.1.4.1.10428 9 1.101.9.4.1.1.1.21
		fkEtherStatsStatus OBJECT-TYPE
			SYNTAX FkEntryStatus
			MAX-ACCESS read-only
			STATUS current
			DESCRIPTION
				"The status of this etherStats entry.
				"
			::= { fkEtherStatsEntry 21 }

		
--  1.3.6.1.4.1.10428 9 1.101.9.4.1.1.1.22
		-- 1.3.6.1.4.1.10428 9 1.101.9.4.1.1.1.22
		fkEtherStatsClearedTime OBJECT-TYPE
			SYNTAX TimeTicks
			MAX-ACCESS read-only
			STATUS current
			DESCRIPTION
				"Description."
			::= { fkEtherStatsEntry 22 }

		
		-- 1.3.6.1.4.1.10428 9 1.101.9.5
		fkRmonSimple OBJECT IDENTIFIER ::= { fkRmon 5 }

		
		-- 1.3.6.1.4.1.10428 9 1.101.9.5.1
		fkRmonSimpleTable OBJECT-TYPE
			SYNTAX SEQUENCE OF FkRmonSimpleEntry
			MAX-ACCESS not-accessible
			STATUS current
			DESCRIPTION
				"Description."
			::= { fkRmonSimple 1 }

		
		-- 1.3.6.1.4.1.10428 9 1.101.9.5.1.1
		fkRmonSimpleEntry OBJECT-TYPE
			SYNTAX FkRmonSimpleEntry
			MAX-ACCESS not-accessible
			STATUS current
			DESCRIPTION
				"Description."
			INDEX { fkRmonSimplePortIndex, fkRmonSimpleSampleVariable }
			::= { fkRmonSimpleTable 1 }

		
		FkRmonSimpleEntry ::=
			SEQUENCE { 
				fkRmonSimplePortIndex
					Integer32,
				fkRmonSimpleSampleVariable
					INTEGER,
				fkRmonSimpleSampleInterval
					Integer32,
				fkRmonSimpleRisingThreshold
					Integer32,
				fkRmonSimpleFallingThreshold
					Integer32
			 }

		-- 1.3.6.1.4.1.10428 9 1.101.9.5.1.1.1
		fkRmonSimplePortIndex OBJECT-TYPE
			SYNTAX Integer32 (1..65535)
			MAX-ACCESS read-only
			STATUS current
			DESCRIPTION
				"The port index."
			::= { fkRmonSimpleEntry 1 }

		
		-- 1.3.6.1.4.1.10428 9 1.101.9.5.1.1.2
		fkRmonSimpleSampleVariable OBJECT-TYPE
			SYNTAX INTEGER
				{
				crcAlignError(1),
				jabber(2),
				oversizePackets(3),
				undersizePackets(4),
				fragments(5),
				dropEvents(6)
				}
			MAX-ACCESS read-only
			STATUS current
			DESCRIPTION
				"The sample variable type."
			::= { fkRmonSimpleEntry 2 }

		
		-- 1.3.6.1.4.1.10428 9 1.101.9.5.1.1.3
		fkRmonSimpleSampleInterval OBJECT-TYPE
			SYNTAX Integer32
			MAX-ACCESS read-only
			STATUS current
			DESCRIPTION
				"The sample interval."
			::= { fkRmonSimpleEntry 3 }

		
		-- 1.3.6.1.4.1.10428 9 1.101.9.5.1.1.4
		fkRmonSimpleRisingThreshold OBJECT-TYPE
			SYNTAX Integer32
			MAX-ACCESS read-only
			STATUS current
			DESCRIPTION
				"The rising threshold."
			::= { fkRmonSimpleEntry 4 }

		
		-- 1.3.6.1.4.1.10428 9 1.101.9.5.1.1.5
		fkRmonSimpleFallingThreshold OBJECT-TYPE
			SYNTAX Integer32
			MAX-ACCESS read-only
			STATUS current
			DESCRIPTION
				"The falling threshold."
			::= { fkRmonSimpleEntry 5 }

		
--  1.3.6.1.4.1.10428 9 1.101.9.3.2
		-- 1.3.6.1.4.1.10428 9 1.101.9.5.2
		fkRmonSimpleControl OBJECT IDENTIFIER ::= { fkRmonSimple 2 }

		
--   Node definitions
-- 
-- 1.3.6.1.4.1.10428 9 1.101.9.3.2.1
		-- 1.3.6.1.4.1.10428 9 1.101.9.5.2.1
		fkRmonSimpleControlRequest OBJECT-TYPE
			SYNTAX INTEGER
				{
				createRmonSimple(1),
				delRmonSimple(2)
				}
			MAX-ACCESS read-write
			STATUS current
			DESCRIPTION			" "
			::= { fkRmonSimpleControl 1 }

		
--  1.3.6.1.4.1.10428 9 1.101.9.3.2.2
		-- 1.3.6.1.4.1.10428 9 1.101.9.5.2.2
		fkRmonSimpleControlStatus OBJECT-TYPE
			SYNTAX FkControlStatusType
			MAX-ACCESS read-only
			STATUS current
			DESCRIPTION
				"The status of a user command. 
				"
			::= { fkRmonSimpleControl 2 }

		
--  1.3.6.1.4.1.10428 9 1.101.9.3.2.3
		-- 1.3.6.1.4.1.10428 9 1.101.9.5.2.3
		fkRmonSimpleControlTimer OBJECT-TYPE
			SYNTAX Gauge32
			MAX-ACCESS read-write
			STATUS current
			DESCRIPTION
				"The maximum wait time for the manager for a long running user command. 
				"
			::= { fkRmonSimpleControl 3 }

		
--  1.3.6.1.4.1.10428 9 1.101.9.3.2.4
		-- 1.3.6.1.4.1.10428 9 1.101.9.5.2.4
		fkRmonSimpleControlTimeStamp OBJECT-TYPE
			SYNTAX TimeTicks
			MAX-ACCESS read-only
			STATUS current
			DESCRIPTION
				"The time stamp of the last command (end of command)."
			::= { fkRmonSimpleControl 4 }

		
--  1.3.6.1.4.1.10428 9 1.101.9.3.2.5
		-- 1.3.6.1.4.1.10428 9 1.101.9.5.2.5
		fkRmonSimpleControlReqResult OBJECT-TYPE
			SYNTAX FkControlRequestResultType
			MAX-ACCESS read-only
			STATUS current
			DESCRIPTION
				"The result of the last user command."
			::= { fkRmonSimpleControl 5 }

		
--  1.3.6.1.4.1.10428 9 1.101.9.3.2.6
		-- 1.3.6.1.4.1.10428 9 1.101.9.5.2.6
		fkRmonSimpleControlPortIndex OBJECT-TYPE
			SYNTAX Integer32 (1..65535)
			MAX-ACCESS read-write
			STATUS current
			DESCRIPTION
				"The port index."
			::= { fkRmonSimpleControl 6 }

		
--  1.3.6.1.4.1.10428 9 1.101.9.3.2.7
		-- 1.3.6.1.4.1.10428 9 1.101.9.5.2.7
		fkRmonSimpleControlSampleVariable OBJECT-TYPE
			SYNTAX INTEGER
				{
				crcAlignError(1),
				jabber(2),
				oversizePackets(3),
				undersizePackets(4),
				fragments(5),
				dropEvents(6)
				}
			MAX-ACCESS read-write
			STATUS current
			DESCRIPTION
				"The sample variable type."
			::= { fkRmonSimpleControl 7 }

		
		-- 1.3.6.1.4.1.10428 9 1.101.9.5.2.8
		fkRmonSimpleControlSampleInterval OBJECT-TYPE
			SYNTAX Integer32
			MAX-ACCESS read-write
			STATUS current
			DESCRIPTION
				"The sample interval."
			::= { fkRmonSimpleControl 8 }

		
--   send an SNMP trap
-- 1.3.6.1.4.1.10428 9 1.101.9.3.2.8
		-- 1.3.6.1.4.1.10428 9 1.101.9.5.2.9
		fkRmonSimpleControlRisingThreshold OBJECT-TYPE
			SYNTAX Integer32
			MAX-ACCESS read-write
			STATUS current
			DESCRIPTION
				"The rising threshold."
			::= { fkRmonSimpleControl 9 }

		
--  1.3.6.1.4.1.10428 9 1.101.9.3.2.9
		-- 1.3.6.1.4.1.10428 9 1.101.9.5.2.10
		fkRmonSimpleControlFallingThreshold OBJECT-TYPE
			SYNTAX Integer32
			MAX-ACCESS read-write
			STATUS current
			DESCRIPTION
				"The falling threshold."
			::= { fkRmonSimpleControl 10 }

		
		-- 1.3.6.1.4.1.10428 9 1.101.9.5.3
		fkRmonSimpleNotification OBJECT IDENTIFIER ::= { fkRmonSimple 3 }

		
		-- 1.3.6.1.4.1.10428 9 1.101.9.5.3.1
		fkRmonSimpleCreated NOTIFICATION-TYPE
			OBJECTS { fkRmonSimpleControlRequest, fkRmonSimpleControlTimeStamp, fkRmonSimpleControlReqResult, fkRmonSimpleControlPortIndex, fkRmonSimpleControlSampleVariable, 
				fkRmonSimpleControlSampleInterval, fkRmonSimpleControlRisingThreshold, fkRmonSimpleControlFallingThreshold }
			STATUS current
			DESCRIPTION 
				"createRmonSimple"
			::= { fkRmonSimpleNotification 1 }

		
		-- 1.3.6.1.4.1.10428 9 1.101.9.5.3.2
		fkRmonSimpleDeleted NOTIFICATION-TYPE
			OBJECTS { fkRmonSimpleControlRequest, fkRmonSimpleControlTimeStamp, fkRmonSimpleControlReqResult, fkRmonSimpleControlPortIndex, fkRmonSimpleControlSampleVariable
				 }
			STATUS current
			DESCRIPTION 
				"delRmonSimple"
			::= { fkRmonSimpleNotification 2 }

		
--  1.3.6.1.4.1.10428 9 1.101.9.5
		-- 1.3.6.1.4.1.10428 9 1.101.9.6
		fkRmonGroup OBJECT-GROUP
			OBJECTS { fkHistoryIndex, fkHistoryDataSource, fkHistoryBucketsRequested, fkHistoryBucketsGranted, fkHistoryInterval, 
				fkHistoryOwner, fkHistoryStatus, fkHistoryControlRequest, fkHistoryControlStatus, fkHistoryControlTimer, 
				fkHistoryControlTimeStamp, fkHistoryControlReqResult, fkHistoryControlIndex, fkHistoryControlDataSource, fkHistoryControlBucketsRequested, 
				fkHistoryControlInterval, fkHistoryControlOwner, fkHistoryControlSts, fkAlarmIndex, fkAlarmInterval, 
				fkAlarmVariable, fkAlarmSampleType, fkAlarmValue, fkAlarmStartupAlarm, fkAlarmRisingThreshold, 
				fkAlarmFallingThreshold, fkAlarmRisingEventIndex, fkAlarmFallingEventIndex, fkAlarmOwner, fkAlarmStatus, 
				fkAlarmControlRequest, fkAlarmControlStatus, fkAlarmControlTimer, fkAlarmControlTimeStamp, fkAlarmControlReqResult, 
				fkAlarmControlIndex, fkAlarmControlInterval, fkAlarmControlVariable, fkAlarmControlSampleType, fkAlarmControlStartupAlarm, 
				fkAlarmControlRisingThreshold, fkAlarmControlFallingThreshold, fkAlarmControlRisingEventIndex, fkAlarmControlFallingEventIndex, fkAlarmControlOwner, 
				fkAlarmControlSts, fkEventIndex, fkEventDescription, fkEventType, fkEventCommunity, 
				fkEventLastTimeSent, fkEventOwner, fkEventStatus, fkEventControlRequest, fkEventControlStatus, 
				fkEventControlTimer, fkEventControlTimeStamp, fkEventControlReqResult, fkEventControlIndex, fkEventControlDescription, 
				fkEventControlType, fkEventControlCommunity, fkEventControlOwner, fkEventControlSts, fkEtherStatsIndex, 
				fkEtherStatsDataSource, fkEtherStatsDropEvents, fkEtherStatsOctets, fkEtherStatsPkts, fkEtherStatsBroadcastPkts, 
				fkEtherStatsMulticastPkts, fkEtherStatsCRCAlignErrors, fkEtherStatsUndersizePkts, fkEtherStatsOversizePkts, fkEtherStatsFragments, 
				fkEtherStatsJabbers, fkEtherStatsCollisions, fkEtherStatsPkts64Octets, fkEtherStatsPkts65to127Octets, fkEtherStatsPkts128to255Octets, 
				fkEtherStatsPkts256to511Octets, fkEtherStatsPkts512to1023Octets, fkEtherStatsPkts1024to1518Octets, fkEtherStatsOwner, fkEtherStatsStatus, 
				fkEtherStatsClearedTime, fkRmonSimplePortIndex, fkRmonSimpleSampleVariable, fkRmonSimpleSampleInterval, fkRmonSimpleRisingThreshold, 
				fkRmonSimpleFallingThreshold, fkRmonSimpleControlRequest, fkRmonSimpleControlStatus, fkRmonSimpleControlTimer, fkRmonSimpleControlTimeStamp, 
				fkRmonSimpleControlReqResult, fkRmonSimpleControlPortIndex, fkRmonSimpleControlSampleVariable, fkRmonSimpleControlRisingThreshold, fkRmonSimpleControlFallingThreshold, 
				fkRmonSimpleControlSampleInterval }
			STATUS current
			DESCRIPTION 
				"Description."
			::= { fkRmon 6 }

		
--  1.3.6.1.4.1.10428 9 1.101.9.6
		-- 1.3.6.1.4.1.10428 9 1.101.9.7
		fkRmonNotificationGroup NOTIFICATION-GROUP
			NOTIFICATIONS { fkHistoryCreated, fkHistoryDestroyed, fkHistoryProfileChanged, fkAlarmCreated, fkAlarmDestroyed, 
				fkAlarmProfileChanged, fkEventCreated, fkEventDestroyed, fkEventProfileChanged, fkRmonSimpleDeleted, 
				fkRmonSimpleCreated }
			STATUS current
			DESCRIPTION 
				"Description."
			::= { fkRmon 7 }

		
	
	END

--
-- fk-rmon-mib.mib
--
