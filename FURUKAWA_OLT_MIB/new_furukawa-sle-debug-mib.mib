--
-- FK-DEBUG-MIB.my
-- MIB generated by MG-SOFT Visual MIB Builder Version 3.0 Build 285
-- Monday, January 22, 2007 at 17:04:05
--

	FK-DEBUG-MIB DEFINITIONS ::= BEGIN
 
		IMPORTS
			fkMgmt			
				FROM FKOLTG1040-SMI			
			FkControlStatusType, FkControlRequestResultType			
				FROM FK-TC-MIB			
			OBJECT-GROUP, NOTIFICATION-GROUP			
				FROM SNMPv2-CONF			
			TimeTicks, Gauge32, BITS, OBJECT-TYPE, MODULE-IDENTITY, 
			NOTIFICATION-TYPE			
				FROM SNMPv2-SMI;
	
	
-- 			fk			
-- FROM AN-MIB			
-- 
		-- 1.3.6.1.4.1.10428 9 1.101.99
		fkDebug MODULE-IDENTITY 
			LAST-UPDATED "200412080903Z"		-- December 08, 2004 at 09:03 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 99 }

		
	
--
-- Type definitions
--
	
-- 			::= { fk 14 }
-- textual conventions
		OwnerString ::= OCTET STRING (SIZE (0..255))

	
	
--
-- Node definitions
--
	
--  Node definitions
-- 
		-- 1.3.6.1.4.1.10428 9 1.101.99.1
		fkDebugBase OBJECT IDENTIFIER::= { fkDebug 1 }

		
		-- 1.3.6.1.4.1.10428 9 1.101.99.1.1
		fkDebugStatus OBJECT IDENTIFIER::= { fkDebugBase 1 }

		
		-- 1.3.6.1.4.1.10428 9 1.101.99.1.1.1
		fkDebugDhcpStatus OBJECT-TYPE
			SYNTAX BITS
				{
				debugFilter(0),
				debugLease(1),
				debugPacket(2),
				debugServices(3)
				}
			MAX-ACCESS read-only
			STATUS current
			DESCRIPTION
				"The  debug option setting of dhcp daemon.
				debugFilter(0),
				debugLease(1),
				debugPacket(2),
				debugServices(3),
				
				The above value is denotes by 'or'.
				"
			::= { fkDebugStatus 1 }

		
		-- 1.3.6.1.4.1.10428 9 1.101.99.1.1.2
		fkDebugIgmpStatus OBJECT-TYPE
			SYNTAX BITS
				{
				debugDecode(0),
				debugEncode(1),
				debugEvents(2),
				debugFsm(3),
				debugTib(4)
				}
			MAX-ACCESS read-only
			STATUS current
			DESCRIPTION
				"The  debug option setting of Igmp daemon.
				debugDecode(0),
				debugEncode(1),
				debugEvents(2),
				debugFsm(3),
				debugTib(4)
				
				The above value is denotes by 'or'.
				"
			::= { fkDebugStatus 2 }

		
		-- 1.3.6.1.4.1.10428 9 1.101.99.1.1.3
		fkDebugIgmpSnoopStatus OBJECT-TYPE
			SYNTAX BITS { debugTcn(0) }
			MAX-ACCESS read-only
			STATUS current
			DESCRIPTION
				"The  debug option setting of Igmp Snoop function.
				debugTcn(0)
				
				The above value is denotes by 'or'."
			::= { fkDebugStatus 3 }

		
		-- 1.3.6.1.4.1.10428 9 1.101.99.1.1.4
		fkDebugNsmStatus OBJECT-TYPE
			SYNTAX BITS
				{
				debugEvents(0),
				debugKernel(1),
				debugPacketDetail(2),
				debugPacketRecv(3),
				debugPacketSend(4)
				}
			MAX-ACCESS read-only
			STATUS current
			DESCRIPTION
				"The  debug option setting of Nsm function.
				debugEvents(0),
				debugKernel(1),
				debugPacketDetail(2),
				debugPacketRecv(3),
				debugPacketSend(4)
				
				The above value is denotes by 'or'."
			::= { fkDebugStatus 4 }

		
		-- 1.3.6.1.4.1.10428 9 1.101.99.1.1.5
		fkDebugNsmMcastStatus OBJECT-TYPE
			SYNTAX BITS
				{
				debugMcastFibMsg(0),
				debugMcastMrt(1),
				debugMcastRegister(2),
				debugMcastStats(3),
				debugMcastVif(4)
				}
			MAX-ACCESS read-only
			STATUS current
			DESCRIPTION
				"The  debug option setting of Nsm Mcast function.
				debugMcastFibMsg(0),
				debugMcastMrt(1),
				debugMcastRegister(2),
				debugMcastStats(3),
				debugMcastVif(4)
				
				The above value is denotes by 'or'."
			::= { fkDebugStatus 5 }

		
		-- 1.3.6.1.4.1.10428 9 1.101.99.1.1.6
		fkDebugBgpStatus OBJECT-TYPE
			SYNTAX BITS
				{
				debugNormal(0),
				debugDampening(1),
				debugEvents(2),
				debugFilters(3),
				debugFsm(4),
				debugKeepalives(5),
				debugNsm(6),
				debugUpdatesIn(7),
				debugUpdatesOut(8)
				}
			MAX-ACCESS read-only
			STATUS current
			DESCRIPTION
				"The  debug option setting of Bgp deamon.
				debugNormal(0),
				debugDampening(1),
				debugEvents(2),
				debugFilters(3),
				debugFsm(4),
				debugKeepalives(5),
				debugNsm(6),
				debugUpdatesIn(7),
				debugUpdatesOut(8)
				
				The above value is denotes by 'or'."
			::= { fkDebugStatus 6 }

		
		-- 1.3.6.1.4.1.10428 9 1.101.99.1.1.7
		fkDebugOspfStatus OBJECT-TYPE
			SYNTAX BITS
				{
				debugEventAbr(0),
				debugEventAsbr(1),
				debugEventLsa(2),
				debugEventNssa(3),
				debugEventOs(4),
				debugEventRouter(5),
				debugEventVlink(6),
				debugIfsmEvent(7),
				debugIfsmStatus(8),
				debugIfsmTimers(9),
				debugLsaFlooding(10),
				debugLsaGenerate(11),
				debugLsaInstall(12),
				debugLsaMaxage(13),
				debugLsaRefrash(14),
				debugNfsmEvents(15),
				debugNfsmStatus(16),
				debugNfsmTimers(17),
				debugNsmInterface(18),
				debugNsmRedistribute(19),
				debugRouteAse(20),
				debugRouteIa(21),
				debugRouteInstall(22),
				debugRouteSpf(23),
				debugPacketDDDetail(24),
				debugPacketDDRecv(25),
				debugPacketDDSend(26),
				debugPacketHelloDetail(27),
				debugPacketHelloRecv(28),
				debugPacketHelloSend(29),
				debugPacketLsAckDetail(30),
				debugPacketLsAckRecv(31),
				debugPacketLsAckSend(32),
				debugPacketLsRequestDetail(33),
				debugPacketLsRequestRecv(34),
				debugPacketLsRequestSend(35),
				debugPacketLsUpdateDetail(36),
				debugPacketLsUpdateRecv(37),
				debugPacketLsUpdateSend(38)
				}
			MAX-ACCESS read-only
			STATUS current
			DESCRIPTION
				"The  debug option setting of Ospf deamon.
				debugEventAbr(0),
				debugEventAsbr(1),
				debugEventLsa(2),
				debugEventNssa(3),
				debugEventOs(4),
				debugEventRouter(5),
				debugEventVlink(6),
				debugIfsmEvent(7),
				debugIfsmStatus(8),
				debugIfsmTimers(9),
				debugLsaFlooding(10),
				debugLsaGenerate(11),
				debugLsaInstall(12),
				debugLsaMaxage(13),
				debugLsaRefrash(14),
				debugNfsmEvents(15),
				debugNfsmStatus(16),
				debugNfsmTimers(17),
				debugNsmInterface(18),
				debugNsmRedistribute(19),
				debugRouteAse(20),
				debugRouteIa(21),
				debugRouteInstall(22),
				debugRouteSpf(23),
				debugPacketDDDetail(24),
				debugPacketDDRecv(25),
				debugPacketDDSend(26),
				debugPacketHelloDetail(27),
				debugPacketHelloRecv(28),
				debugPacketHelloSend(29),
				debugPacketLsAckDetail(30),
				debugPacketLsAckRecv(31),
				debugPacketLsAckSend(32),
				debugPacketLsRequestDetail(33),
				debugPacketLsRequestRecv(34),
				debugPacketLsRequestSend(35),
				debugPacketLsUpdateDetail(36),
				debugPacketLsUpdateRecv(37),
				debugPacketLsUpdateSend(38)
				
				Thee above value is denotes by 'or'."
			::= { fkDebugStatus 7 }

		
		-- 1.3.6.1.4.1.10428 9 1.101.99.1.1.8
		fkDebugPimStatus OBJECT-TYPE
			SYNTAX BITS
				{
				debugEvent(0),
				debugMfc(1),
				debugMib(2),
				debugNexthop(3),
				debugNsm(4),
				debugPacketIn(5),
				debugPacketOut(6),
				debugState(7),
				debugTimerAssertAt(8),
				debugTimerBsr(9),
				debugTimerBsrBst(10),
				debugTimerBsrCrp(11),
				debugTimerHello(12),
				debugTimerHelloHt(13),
				debugTimerHelloNlt(14),
				debugTimerHelloTht(15),
				debugTimerJoinprune(16),
				debugTimerJoinpruneEt(17),
				debugTimerJoinpruneJt(18),
				debugTimerJoinpruneKat(19),
				debugTimerJoinpruneOt(20),
				debugTimerJoinprunePpt(21),
				debugTimerRegister(22)
				}
			MAX-ACCESS read-only
			STATUS current
			DESCRIPTION
				"The  debug option setting of Pim deamon.
				debugEvent(0),
				debugMfc(1),
				debugMib(2),
				debugNexthop(3),
				debugNsm(4),
				debugPacketIn(5),
				debugPacketOut(6),
				debugState(7),
				debugTimerAssertAt(8),
				debugTimerBsr(9),
				debugTimerBsrBst(10),
				debugTimerBsrCrp(11),
				debugTimerHello(12),
				debugTimerHelloHt(13),
				debugTimerHelloNlt(14),
				debugTimerHelloTht(15),
				debugTimerJoinprune(16),
				debugTimerJoinpruneEt(17),
				debugTimerJoinpruneJt(18),
				debugTimerJoinpruneKat(19),
				debugTimerJoinpruneOt(20),
				debugTimerJoinprunePpt(21),
				debugTimerRegister(22)
				
				The above value is denotes by 'or'."
			::= { fkDebugStatus 8 }

		
		-- 1.3.6.1.4.1.10428 9 1.101.99.1.1.9
		fkDebugRipStatus OBJECT-TYPE
			SYNTAX BITS
				{
				debugEvents(0),
				debugNsm(1),
				debugPacketDetail(2),
				debugPacketRecv(3),
				debugPacketSend(4)
				}
			MAX-ACCESS read-only
			STATUS current
			DESCRIPTION
				"The  debug option setting of Rip deamon.
				debugEvents(0),
				debugNsm(1),
				debugPacketDetail(2),
				debugPacketRecv(3),
				debugPacketSend(4)
				
				The above value is denotes by 'or'."
			::= { fkDebugStatus 9 }

		
		-- 1.3.6.1.4.1.10428 9 1.101.99.1.2
		fkDebugStatusControl OBJECT IDENTIFIER::= { fkDebugBase 2 }

		
		-- 1.3.6.1.4.1.10428 9 1.101.99.1.2.1
		fkDebugControlRequest OBJECT-TYPE
			SYNTAX INTEGER
				{
				setDhcpDebugStatus(1),
				setIgmpDebugStatus(2),
				setIgmpSnoopDebugStats(3),
				setNsmDebugStatus(4),
				setNsmMcastDebugStatus(5),
				setBgpDebugStatus(6),
				setOspfDebugStatus(7),
				setPimDebugStatus(8),
				setRipDebugStatus(9)
				}
			MAX-ACCESS read-write
			STATUS current
			DESCRIPTION
				"
				.
				"
			::= { fkDebugStatusControl 1 }

		
		-- 1.3.6.1.4.1.10428 9 1.101.99.1.2.2
		fkDebugControlStatus OBJECT-TYPE
			SYNTAX FkControlStatusType
			MAX-ACCESS read-only
			STATUS current
			DESCRIPTION
				"The status of a user command. 
				"
			::= { fkDebugStatusControl 2 }

		
		-- 1.3.6.1.4.1.10428 9 1.101.99.1.2.3
		fkDebugControlTimer OBJECT-TYPE
			SYNTAX Gauge32
			MAX-ACCESS read-write
			STATUS current
			DESCRIPTION
				"The maximum wait time for the manager for a long running user command. 
				"
			::= { fkDebugStatusControl 3 }

		
		-- 1.3.6.1.4.1.10428 9 1.101.99.1.2.4
		fkDebugControlTimeStamp OBJECT-TYPE
			SYNTAX TimeTicks
			MAX-ACCESS read-only
			STATUS current
			DESCRIPTION
				"The time stamp of the last command (end of command)."
			::= { fkDebugStatusControl 4 }

		
		-- 1.3.6.1.4.1.10428 9 1.101.99.1.2.5
		fkDebugControlReqResult OBJECT-TYPE
			SYNTAX FkControlRequestResultType
			MAX-ACCESS read-only
			STATUS current
			DESCRIPTION
				"The result of the last user command."
			::= { fkDebugStatusControl 5 }

		
		-- 1.3.6.1.4.1.10428 9 1.101.99.1.2.6
		fkDebugControlDhcpStatus OBJECT-TYPE
			SYNTAX BITS
				{
				debugFilter(0),
				debugLease(1),
				debugPacket(2),
				debugServices(3)
				}
			MAX-ACCESS read-write
			STATUS current
			DESCRIPTION
				"Description."
			::= { fkDebugStatusControl 6 }

		
		-- 1.3.6.1.4.1.10428 9 1.101.99.1.2.7
		fkDebugControlIgmpStatus OBJECT-TYPE
			SYNTAX BITS
				{
				debugDecode(0),
				debugEncode(1),
				debugEvents(2),
				debugFsm(3),
				debugTib(4)
				}
			MAX-ACCESS read-write
			STATUS current
			DESCRIPTION
				"Description."
			::= { fkDebugStatusControl 7 }

		
		-- 1.3.6.1.4.1.10428 9 1.101.99.1.2.8
		fkDebugControlIgmpSnoopStatus OBJECT-TYPE
			SYNTAX BITS { debugTcn(0) }
			MAX-ACCESS read-write
			STATUS current
			DESCRIPTION
				"Description."
			::= { fkDebugStatusControl 8 }

		
		-- 1.3.6.1.4.1.10428 9 1.101.99.1.2.9
		fkDebugControlNsmStatus OBJECT-TYPE
			SYNTAX BITS
				{
				debugEvents(0),
				debugKernel(1),
				debugPacketDetail(2),
				debugPacketRecv(3),
				debugPacketSend(4)
				}
			MAX-ACCESS read-write
			STATUS current
			DESCRIPTION
				"Description."
			::= { fkDebugStatusControl 9 }

		
		-- 1.3.6.1.4.1.10428 9 1.101.99.1.2.10
		fkDebugControlNsmMcastStatus OBJECT-TYPE
			SYNTAX BITS
				{
				debugMcastFibMsg(0),
				debugMcastMrt(1),
				debugMcastRegister(2),
				debugMcastStats(3),
				debugMcastVif(4)
				}
			MAX-ACCESS read-write
			STATUS current
			DESCRIPTION
				"Description."
			::= { fkDebugStatusControl 10 }

		
		-- 1.3.6.1.4.1.10428 9 1.101.99.1.2.11
		fkDebugControlBgpStatus OBJECT-TYPE
			SYNTAX BITS
				{
				debugNormal(0),
				debugDampening(1),
				debugEvents(2),
				debugFilters(3),
				debugFsm(4),
				debugKeepalives(5),
				debugNsm(6),
				debugUpdatesIn(7),
				debugUpdatesOut(8)
				}
			MAX-ACCESS read-write
			STATUS current
			DESCRIPTION
				"Description."
			::= { fkDebugStatusControl 11 }

		
		-- 1.3.6.1.4.1.10428 9 1.101.99.1.2.12
		fkDebugControlOspfStatus OBJECT-TYPE
			SYNTAX BITS
				{
				debugEventAbr(0),
				debugEventAsbr(1),
				debugEventLsa(2),
				debugEventNssa(3),
				debugEventOs(4),
				debugEventRouter(5),
				debugEventVlink(6),
				debugIfsmEvent(7),
				debugIfsmStatus(8),
				debugIfsmTimers(9),
				debugLsaFlooding(10),
				debugLsaGenerate(11),
				debugLsaInstall(12),
				debugLsaMaxage(13),
				debugLsaRefrash(14),
				debugNfsmEvents(15),
				debugNfsmStatus(16),
				debugNfsmTimers(17),
				debugNsmInterface(18),
				debugNsmRedistribute(19),
				debugRouteAse(20),
				debugRouteIa(21),
				debugRouteInstall(22),
				debugRouteSpf(23),
				debugPacketDDDetail(24),
				debugPacketDDRecv(25),
				debugPacketDDSend(26),
				debugPacketHelloDetail(27),
				debugPacketHelloRecv(28),
				debugPacketHelloSend(29),
				debugPacketLsAckDetail(30),
				debugPacketLsAckRecv(31),
				debugPacketLsAckSend(32),
				debugPacketLsRequestDetail(33),
				debugPacketLsRequestRecv(34),
				debugPacketLsRequestSend(35),
				debugPacketLsUpdateDetail(36),
				debugPacketLsUpdateRecv(37),
				debugPacketLsUpdateSend(38)
				}
			MAX-ACCESS read-write
			STATUS current
			DESCRIPTION
				"Description."
			::= { fkDebugStatusControl 12 }

		
		-- 1.3.6.1.4.1.10428 9 1.101.99.1.2.13
		fkDebugControlPimStatus OBJECT-TYPE
			SYNTAX BITS
				{
				debugEvent(0),
				debugMfc(1),
				debugMib(2),
				debugNexthop(3),
				debugNsm(4),
				debugPacketIn(5),
				debugPacketOut(6),
				debugState(7),
				debugTimerAssertAt(8),
				debugTimerBsr(9),
				debugTimerBsrBst(10),
				debugTimerBsrCrp(11),
				debugTimerHello(12),
				debugTimerHelloHt(13),
				debugTimerHelloNlt(14),
				debugTimerHelloTht(15),
				debugTimerJoinprune(16),
				debugTimerJoinpruneEt(17),
				debugTimerJoinpruneJt(18),
				debugTimerJoinpruneKat(19),
				debugTimerJoinpruneOt(20),
				debugTimerJoinprunePpt(21),
				debugTimerRegister(22)
				}
			MAX-ACCESS read-write
			STATUS current
			DESCRIPTION
				"Description."
			::= { fkDebugStatusControl 13 }

		
		-- 1.3.6.1.4.1.10428 9 1.101.99.1.2.14
		fkDebugControlRipStatus OBJECT-TYPE
			SYNTAX BITS
				{
				debugEvents(0),
				debugNsm(1),
				debugPacketDetail(2),
				debugPacketRecv(3),
				debugPacketSend(4)
				}
			MAX-ACCESS read-write
			STATUS current
			DESCRIPTION
				"Description."
			::= { fkDebugStatusControl 14 }

		
		-- 1.3.6.1.4.1.10428 9 1.101.99.1.3
		fkDebugStatusNotification OBJECT IDENTIFIER::= { fkDebugBase 3 }

		
		-- 1.3.6.1.4.1.10428 9 1.101.99.1.3.1
		fkDebugDhcpStatusChanged NOTIFICATION-TYPE
			OBJECTS { fkDebugControlRequest, fkDebugControlTimeStamp, fkDebugControlReqResult, fkDebugDhcpStatus }
			STATUS current
			DESCRIPTION 
				"Description."
			::= { fkDebugStatusNotification 1 }

		
		-- 1.3.6.1.4.1.10428 9 1.101.99.1.3.2
		fkDebugIgmpStatusChanged NOTIFICATION-TYPE
			OBJECTS { fkDebugControlRequest, fkDebugControlTimeStamp, fkDebugControlReqResult, fkDebugIgmpStatus }
			STATUS current
			DESCRIPTION 
				"Description."
			::= { fkDebugStatusNotification 2 }

		
		-- 1.3.6.1.4.1.10428 9 1.101.99.1.3.3
		fkDebugIgmpSnoopStatusChanged NOTIFICATION-TYPE
			OBJECTS { fkDebugControlRequest, fkDebugControlTimeStamp, fkDebugControlReqResult, fkDebugIgmpSnoopStatus }
			STATUS current
			DESCRIPTION 
				"Description."
			::= { fkDebugStatusNotification 3 }

		
		-- 1.3.6.1.4.1.10428 9 1.101.99.1.3.4
		fkDebugNsmStatusChanged NOTIFICATION-TYPE
			OBJECTS { fkDebugControlRequest, fkDebugControlTimeStamp, fkDebugControlReqResult, fkDebugNsmStatus }
			STATUS current
			DESCRIPTION 
				"Description."
			::= { fkDebugStatusNotification 4 }

		
		-- 1.3.6.1.4.1.10428 9 1.101.99.1.3.5
		fkDebugNsmMcastStatusChanged NOTIFICATION-TYPE
			OBJECTS { fkDebugControlRequest, fkDebugControlTimeStamp, fkDebugControlReqResult, fkDebugNsmMcastStatus }
			STATUS current
			DESCRIPTION 
				"Description."
			::= { fkDebugStatusNotification 5 }

		
		-- 1.3.6.1.4.1.10428 9 1.101.99.1.3.6
		fkDebugBgpStatusChanged NOTIFICATION-TYPE
			OBJECTS { fkDebugControlRequest, fkDebugControlTimeStamp, fkDebugControlReqResult, fkDebugBgpStatus }
			STATUS current
			DESCRIPTION 
				"Description."
			::= { fkDebugStatusNotification 6 }

		
		-- 1.3.6.1.4.1.10428 9 1.101.99.1.3.7
		fkDebugOspfStatusChanged NOTIFICATION-TYPE
			OBJECTS { fkDebugControlRequest, fkDebugControlTimeStamp, fkDebugControlReqResult, fkDebugOspfStatus }
			STATUS current
			DESCRIPTION 
				"Description."
			::= { fkDebugStatusNotification 7 }

		
		-- 1.3.6.1.4.1.10428 9 1.101.99.1.3.8
		fkDebugPimStatusChanged NOTIFICATION-TYPE
			OBJECTS { fkDebugControlRequest, fkDebugControlTimeStamp, fkDebugControlReqResult, fkDebugPimStatus }
			STATUS current
			DESCRIPTION 
				"Description."
			::= { fkDebugStatusNotification 8 }

		
		-- 1.3.6.1.4.1.10428 9 1.101.99.1.3.9
		fkDebugRipStatusChanged NOTIFICATION-TYPE
			OBJECTS { fkDebugControlRequest, fkDebugControlTimeStamp, fkDebugControlReqResult, fkDebugRipStatus }
			STATUS current
			DESCRIPTION 
				"Description."
			::= { fkDebugStatusNotification 9 }

		
		-- 1.3.6.1.4.1.10428 9 1.101.99.2
		fkDebugGroup OBJECT-GROUP
			OBJECTS { fkDebugDhcpStatus, fkDebugIgmpStatus, fkDebugIgmpSnoopStatus, fkDebugNsmStatus, fkDebugNsmMcastStatus, 
				fkDebugBgpStatus, fkDebugOspfStatus, fkDebugPimStatus, fkDebugRipStatus, fkDebugControlRequest, 
				fkDebugControlStatus, fkDebugControlTimer, fkDebugControlTimeStamp, fkDebugControlReqResult, fkDebugControlDhcpStatus, 
				fkDebugControlIgmpStatus, fkDebugControlIgmpSnoopStatus, fkDebugControlNsmStatus, fkDebugControlNsmMcastStatus, fkDebugControlBgpStatus, 
				fkDebugControlOspfStatus, fkDebugControlPimStatus, fkDebugControlRipStatus }
			STATUS current
			DESCRIPTION 
				"Description."
			::= { fkDebug 2 }

		
		-- 1.3.6.1.4.1.10428 9 1.101.99.3
		fkDebugNotificationGroup NOTIFICATION-GROUP
			NOTIFICATIONS { fkDebugDhcpStatusChanged, fkDebugIgmpStatusChanged, fkDebugIgmpSnoopStatusChanged, fkDebugNsmStatusChanged, fkDebugNsmMcastStatusChanged, 
				fkDebugBgpStatusChanged, fkDebugOspfStatusChanged, fkDebugPimStatusChanged, fkDebugRipStatusChanged }
			STATUS current
			DESCRIPTION 
				"Description."
			::= { fkDebug 3 }

		
	
	END

--
-- FK-DEBUG-MIB.my
--
