--
-- fk-pppoe-mib.mib
-- MIB generated by MG-SOFT Visual MIB Builder Version 6.0  Build 88
-- Wednesday, April 13, 2011 at 19:19:02
--

	FK-PPPOE-MIB DEFINITIONS ::= BEGIN
 
		IMPORTS
			fkMgmt			
				FROM FKOLTG1040-SMI			
			FkControlStatusType, FkControlRequestResultType			
				FROM FK-TC-MIB			
			OBJECT-GROUP, NOTIFICATION-GROUP			
				FROM SNMPv2-CONF			
			TimeTicks, Gauge32, OBJECT-TYPE, MODULE-IDENTITY, NOTIFICATION-TYPE			
				FROM SNMPv2-SMI;
	
	
		-- 1.3.6.1.4.1.10428 9 1.101.24
		fkPppoe MODULE-IDENTITY 
			LAST-UPDATED "201104081633Z"		-- April 08, 2011 at 16:33 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 24 }

		
	
	
--
-- Node definitions
--
	
		-- 1.3.6.1.4.1.10428 9 1.101.24.1
		fkPppoeBase OBJECT IDENTIFIER ::= { fkPppoe 1 }

		
		-- 1.3.6.1.4.1.10428 9 1.101.24.2
		fkPppoeIntermediateAgent OBJECT IDENTIFIER ::= { fkPppoe 2 }

		
		-- 1.3.6.1.4.1.10428 9 1.101.24.2.1
		fkPpppoeIABaseInfo OBJECT IDENTIFIER ::= { fkPppoeIntermediateAgent 1 }

		
		-- 1.3.6.1.4.1.10428 9 1.101.24.2.1.1
		fkPpppoeIAEnableStatus OBJECT-TYPE
			SYNTAX INTEGER
				{
				enable(1),
				disable(2)
				}
			MAX-ACCESS read-only
			STATUS current
			DESCRIPTION
				"Enable/Disable Intermediate Agent on the switch"
			::= { fkPpppoeIABaseInfo 1 }

		
		-- 1.3.6.1.4.1.10428 9 1.101.24.2.1.2
		fkPpppoeIAAccessNode OBJECT-TYPE
			SYNTAX OCTET STRING
			MAX-ACCESS read-only
			STATUS current
			DESCRIPTION
				"Format Type : Access Node Identifier of the switch"
			::= { fkPpppoeIABaseInfo 2 }

		
		-- 1.3.6.1.4.1.10428 9 1.101.24.2.1.3
		fkPpppoeIACircuitId OBJECT-TYPE
			SYNTAX OCTET STRING
			MAX-ACCESS read-only
			STATUS current
			DESCRIPTION
				"Format Type : Circuit ID"
			::= { fkPpppoeIABaseInfo 3 }

		
		-- 1.3.6.1.4.1.10428 9 1.101.24.2.1.4
		fkPpppoeIARemoteId OBJECT-TYPE
			SYNTAX OCTET STRING
			MAX-ACCESS read-only
			STATUS current
			DESCRIPTION
				"Format Type : Remote ID"
			::= { fkPpppoeIABaseInfo 4 }

		
		-- 1.3.6.1.4.1.10428 9 1.101.24.2.2
		fkPpppoeIAControl OBJECT IDENTIFIER ::= { fkPppoeIntermediateAgent 2 }

		
		-- 1.3.6.1.4.1.10428 9 1.101.24.2.2.1
		fkPpppoeIAControlRequest OBJECT-TYPE
			SYNTAX INTEGER
				{
				setIntermediateAgentEnableStatus(1),
				setFormatTypeAccessnodeId(2),
				setFormatTypeCircuitId(3),
				setFormatTypeRemoteId(4)
				}
			MAX-ACCESS read-write
			STATUS current
			DESCRIPTION
				"The request of a user command."
			::= { fkPpppoeIAControl 1 }

		
		-- 1.3.6.1.4.1.10428 9 1.101.24.2.2.2
		fkPpppoeIAControlStatus OBJECT-TYPE
			SYNTAX FkControlStatusType
			MAX-ACCESS read-write
			STATUS current
			DESCRIPTION
				"The status of a user command."
			::= { fkPpppoeIAControl 2 }

		
		-- 1.3.6.1.4.1.10428 9 1.101.24.2.2.3
		fkPpppoeIAControlTimer OBJECT-TYPE
			SYNTAX Gauge32
			MAX-ACCESS read-write
			STATUS current
			DESCRIPTION
				"The maximum wait Time for the manager for a long running user command."
			::= { fkPpppoeIAControl 3 }

		
		-- 1.3.6.1.4.1.10428 9 1.101.24.2.2.4
		fkPpppoeIAControlTimeStamp OBJECT-TYPE
			SYNTAX TimeTicks
			MAX-ACCESS read-write
			STATUS current
			DESCRIPTION
				"The Time stamp of the last command (end of command)"
			::= { fkPpppoeIAControl 4 }

		
		-- 1.3.6.1.4.1.10428 9 1.101.24.2.2.5
		fkPpppoeIAControlReqResult OBJECT-TYPE
			SYNTAX FkControlRequestResultType
			MAX-ACCESS read-write
			STATUS current
			DESCRIPTION
				"The result of the last user command."
			::= { fkPpppoeIAControl 5 }

		
		-- 1.3.6.1.4.1.10428 9 1.101.24.2.2.6
		fkPpppoeIAControlEnableStatus OBJECT-TYPE
			SYNTAX INTEGER
				{
				enable(1),
				disable(2)
				}
			MAX-ACCESS read-write
			STATUS current
			DESCRIPTION
				"Enable/Disable Intermediate Agent on the switch"
			::= { fkPpppoeIAControl 6 }

		
		-- 1.3.6.1.4.1.10428 9 1.101.24.2.2.7
		fkPpppoeIAControlAccessNode OBJECT-TYPE
			SYNTAX OCTET STRING
			MAX-ACCESS read-only
			STATUS current
			DESCRIPTION
				"Format Type : Access Node Identifier of the switch"
			::= { fkPpppoeIAControl 7 }

		
		-- 1.3.6.1.4.1.10428 9 1.101.24.2.2.8
		fkPpppoeIAControlCircuitId OBJECT-TYPE
			SYNTAX OCTET STRING
			MAX-ACCESS read-only
			STATUS current
			DESCRIPTION
				"Format Type : Circuit ID"
			::= { fkPpppoeIAControl 8 }

		
		-- 1.3.6.1.4.1.10428 9 1.101.24.2.2.9
		fkPpppoeIAControlRemoteId OBJECT-TYPE
			SYNTAX OCTET STRING
			MAX-ACCESS read-only
			STATUS current
			DESCRIPTION
				"Format Type : Remote ID"
			::= { fkPpppoeIAControl 9 }

		
		-- 1.3.6.1.4.1.10428 9 1.101.24.2.3
		fkPpppoeIANotification OBJECT IDENTIFIER ::= { fkPppoeIntermediateAgent 3 }

		
		-- 1.3.6.1.4.1.10428 9 1.101.24.2.3.1
		fkPpppoeIAEnableStatuschanged NOTIFICATION-TYPE
			OBJECTS { fkPpppoeIAControlRequest, fkPpppoeIAControlTimeStamp, fkPpppoeIAControlEnableStatus }
			STATUS current
			DESCRIPTION 
				"Enable/Disable Intermediate Agent on the switch"
			::= { fkPpppoeIANotification 1 }

		
		-- 1.3.6.1.4.1.10428 9 1.101.24.2.3.2
		fkPpppoeIAAccessnodeIdChanged NOTIFICATION-TYPE
			OBJECTS { fkPpppoeIAControlRequest, fkPpppoeIAControlTimeStamp, fkPpppoeIAControlAccessNode }
			STATUS current
			DESCRIPTION 
				"Format Type : Access Node Identifier of the switch"
			::= { fkPpppoeIANotification 2 }

		
		-- 1.3.6.1.4.1.10428 9 1.101.24.2.3.3
		fkPpppoeIACircuitIdChanged NOTIFICATION-TYPE
			OBJECTS { fkPpppoeIAControlRequest, fkPpppoeIAControlTimeStamp, fkPpppoeIAControlCircuitId }
			STATUS current
			DESCRIPTION 
				"Format Type : Circuit ID"
			::= { fkPpppoeIANotification 3 }

		
		-- 1.3.6.1.4.1.10428 9 1.101.24.2.3.4
		fkPpppoeIARemoteIdChanged NOTIFICATION-TYPE
			OBJECTS { fkPpppoeIAControlRequest, fkPpppoeIAControlTimeStamp, fkPpppoeIAControlRemoteId }
			STATUS current
			DESCRIPTION 
				"Format Type : Remote ID"
			::= { fkPpppoeIANotification 4 }

		
		-- 1.3.6.1.4.1.10428 9 1.101.24.3
		fkPppoeGroup OBJECT-GROUP
			OBJECTS { fkPpppoeIAEnableStatus, fkPpppoeIAAccessNode, fkPpppoeIACircuitId, fkPpppoeIARemoteId, fkPpppoeIAControlRequest, 
				fkPpppoeIAControlStatus, fkPpppoeIAControlTimer, fkPpppoeIAControlTimeStamp, fkPpppoeIAControlReqResult, fkPpppoeIAControlEnableStatus, 
				fkPpppoeIAControlAccessNode, fkPpppoeIAControlCircuitId, fkPpppoeIAControlRemoteId }
			STATUS current
			DESCRIPTION 
				"Description."
			::= { fkPppoe 3 }

		
		-- 1.3.6.1.4.1.10428 9 1.101.24.4
		fkPppoeNotificationGroup NOTIFICATION-GROUP
			NOTIFICATIONS { fkPpppoeIAEnableStatuschanged, fkPpppoeIAAccessnodeIdChanged, fkPpppoeIACircuitIdChanged, fkPpppoeIARemoteIdChanged }
			STATUS current
			DESCRIPTION 
				"Description."
			::= { fkPppoe 4 }

		
	
	END

--
-- fk-pppoe-mib.mib
--
