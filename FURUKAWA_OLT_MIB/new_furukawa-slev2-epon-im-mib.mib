--
-- FKV2-EPON-IM-MIB.my
-- MIB generated by MG-SOFT Visual MIB Builder Version 6.0  Build 88
-- Thursday, October 25, 2007 at 17:42:26
--

	FKV2-EPON-IM-MIB DEFINITIONS ::= BEGIN
 
		IMPORTS
			fkV2Mgmt			
				FROM FKOLTG1040-SMI			
			FkControlStatusType, FkControlRequestResultType			
				FROM FK-TC-MIB			
			OBJECT-GROUP, NOTIFICATION-GROUP			
				FROM SNMPv2-CONF			
			TimeTicks, Integer32, Gauge32, Counter32, Counter64, 
			OBJECT-TYPE, MODULE-IDENTITY, NOTIFICATION-TYPE			
				FROM SNMPv2-SMI;
	
	
--   1.3.6.1.4.1.10428 9 1.102.15
-- 1.3.6.1.4.1.10428 9 1.102.15
-- October 24, 2006 at 11:42 GMT
		-- 1.3.6.1.4.1.10428 9 1.102.15
		fkV2EponIM MODULE-IDENTITY 
			LAST-UPDATED "200610241142Z"		-- October 24, 2006 at 11:42 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkV2Mgmt 15 }

		
	
--
-- Type definitions
--
	
--  Type definitions
-- 
		EponOnuState ::= INTEGER
			{
			disable(0),
			enable(1)
			}

--   Type definitions
-- 
		EponPortType ::= INTEGER
			{
			nni(1),
			mgmt(2),
			uni(3),
			pon(4),
			aggr(5),
			llid(6)
			}

		EponOnuLinkStatus ::= INTEGER
			{
			down(0),
			up(1)
			}

		EponOnuStatus ::= INTEGER
			{
			registered(1),
			deregistered(2),
			discovered(3),
			lost(4)
			}

	
	
--
-- Node definitions
--
	
--  Node definitions
-- 
-- 
-- TAG : Onu 
--  
-- 1.3.6.1.4.1.10428 9 1.102.15.1
		-- 1.3.6.1.4.1.10428 9 1.102.15.1
		fkV2EponIMOnu OBJECT IDENTIFIER ::= { fkV2EponIM 1 }

		
--  1.3.6.1.4.1.10428 9 1.102.15.1.1
		-- 1.3.6.1.4.1.10428 9 1.102.15.1.1
		fkV2EponIMOnuBase OBJECT IDENTIFIER ::= { fkV2EponIMOnu 1 }

		
--  1.3.6.1.4.1.10428 9 1.102.15.1.1.1
		-- 1.3.6.1.4.1.10428 9 1.102.15.1.1.1
		fkV2EponIMOnuInfo OBJECT IDENTIFIER ::= { fkV2EponIMOnuBase 1 }

		
--  1.3.6.1.4.1.10428 9 1.102.15.1.1.1.1
		-- 1.3.6.1.4.1.10428 9 1.102.15.1.1.1.1
		fkV2EponIMOnuConfigMask OBJECT-TYPE
			SYNTAX Integer32
			MAX-ACCESS read-only
			STATUS current
			DESCRIPTION
				"mask to indicate valid fields"
			::= { fkV2EponIMOnuInfo 1 }

		
--  1.3.6.1.4.1.10428 9 1.102.15.1.1.1.2
		-- 1.3.6.1.4.1.10428 9 1.102.15.1.1.1.2
		fkV2EponIMOnuConfigData OBJECT-TYPE
			SYNTAX OCTET STRING
			MAX-ACCESS read-only
			STATUS current
			DESCRIPTION
				"eeprom startup config data"
			::= { fkV2EponIMOnuInfo 2 }

		
--  1.3.6.1.4.1.10428 9 1.102.15.1.1.1.3
		-- 1.3.6.1.4.1.10428 9 1.102.15.1.1.1.3
		fkV2EponIMOnuRegistered OBJECT-TYPE
			SYNTAX EponOnuState
			MAX-ACCESS read-only
			STATUS current
			DESCRIPTION
				"status of the ONU port"
			::= { fkV2EponIMOnuInfo 3 }

		
--  1.3.6.1.4.1.10428 9 1.102.15.1.1.1.4
		-- 1.3.6.1.4.1.10428 9 1.102.15.1.1.1.4
		fkV2EponIMOnuAuthenticated OBJECT-TYPE
			SYNTAX EponOnuState
			MAX-ACCESS read-only
			STATUS current
			DESCRIPTION
				"status of the ONU port authentication"
			::= { fkV2EponIMOnuInfo 4 }

		
--  1.3.6.1.4.1.10428 9 1.102.15.1.1.1.5
		-- 1.3.6.1.4.1.10428 9 1.102.15.1.1.1.5
		fkV2EponIMOnuImageVersion OBJECT-TYPE
			SYNTAX OCTET STRING
			MAX-ACCESS read-only
			STATUS current
			DESCRIPTION
				"ONU software version"
			::= { fkV2EponIMOnuInfo 5 }

		
--  1.3.6.1.4.1.10428 9 1.102.15.1.1.1.6
		-- 1.3.6.1.4.1.10428 9 1.102.15.1.1.1.6
		fkV2EponIMOnuLoadVersion OBJECT-TYPE
			SYNTAX OCTET STRING
			MAX-ACCESS read-only
			STATUS current
			DESCRIPTION
				"ONU loader version"
			::= { fkV2EponIMOnuInfo 6 }

		
--  1.3.6.1.4.1.10428 9 1.102.15.1.1.1.7
		-- 1.3.6.1.4.1.10428 9 1.102.15.1.1.1.7
		fkV2EponIMOnuChipVersion OBJECT-TYPE
			SYNTAX OCTET STRING
			MAX-ACCESS read-only
			STATUS current
			DESCRIPTION
				"chip version"
			::= { fkV2EponIMOnuInfo 7 }

		
--  1.3.6.1.4.1.10428 9 1.102.15.1.1.1.8
		-- 1.3.6.1.4.1.10428 9 1.102.15.1.1.1.8
		fkV2EponIMOnuSerialNumber OBJECT-TYPE
			SYNTAX OCTET STRING
			MAX-ACCESS read-only
			STATUS current
			DESCRIPTION
				"ONU serial number"
			::= { fkV2EponIMOnuInfo 8 }

		
--  1.3.6.1.4.1.10428 9 1.102.15.1.1.1.9
		-- 1.3.6.1.4.1.10428 9 1.102.15.1.1.1.9
		fkV2EponIMOnuRxOpticPower OBJECT-TYPE
			SYNTAX OCTET STRING
			MAX-ACCESS read-only
			STATUS current
			DESCRIPTION
				"value of the ONU rx optical power, UNIT : dBm"
			::= { fkV2EponIMOnuInfo 9 }

		
--  1.3.6.1.4.1.10428 9 1.102.15.1.1.1.10
		-- 1.3.6.1.4.1.10428 9 1.102.15.1.1.1.10
		fkV2EponIMRegInfoOltId OBJECT-TYPE
			SYNTAX Integer32
			MAX-ACCESS read-only
			STATUS current
			DESCRIPTION
				"the OLT id from which the registration comes"
			::= { fkV2EponIMOnuInfo 10 }

		
--  1.3.6.1.4.1.10428 9 1.102.15.1.1.1.11
		-- 1.3.6.1.4.1.10428 9 1.102.15.1.1.1.11
		fkV2EponIMRegInfoOltLlidPort OBJECT-TYPE
			SYNTAX INTEGER (1..512)
			MAX-ACCESS read-only
			STATUS current
			DESCRIPTION
				"the OLT LLID based logical port at which the ONU is registered"
			::= { fkV2EponIMOnuInfo 11 }

		
--  1.3.6.1.4.1.10428 9 1.102.15.1.1.1.12
		-- 1.3.6.1.4.1.10428 9 1.102.15.1.1.1.12
		fkV2EponIMRegInfoOltPonPort OBJECT-TYPE
			SYNTAX Integer32
			MAX-ACCESS read-only
			STATUS current
			DESCRIPTION
				"the OLT PON port at which the ONU is registered"
			::= { fkV2EponIMOnuInfo 12 }

		
--  1.3.6.1.4.1.10428 9 1.102.15.1.1.1.13
		-- 1.3.6.1.4.1.10428 9 1.102.15.1.1.1.13
		fkV2EponIMRegInfoOnuMacAddress OBJECT-TYPE
			SYNTAX OCTET STRING
			MAX-ACCESS read-only
			STATUS current
			DESCRIPTION
				"the ONU MAC address"
			::= { fkV2EponIMOnuInfo 13 }

		
--  1.3.6.1.4.1.10428 9 1.102.15.1.1.1.14
		-- 1.3.6.1.4.1.10428 9 1.102.15.1.1.1.14
		fkV2EponIMRegInfoOnuLlid OBJECT-TYPE
			SYNTAX Integer32
			MAX-ACCESS read-only
			STATUS current
			DESCRIPTION
				"the logical link ID"
			::= { fkV2EponIMOnuInfo 14 }

		
--  1.3.6.1.4.1.10428 9 1.102.15.1.1.1.15
		-- 1.3.6.1.4.1.10428 9 1.102.15.1.1.1.15
		fkV2EponIMOnuId OBJECT-TYPE
			SYNTAX OCTET STRING
			MAX-ACCESS read-only
			STATUS current
			DESCRIPTION
				"ONU authentication user name"
			::= { fkV2EponIMOnuInfo 15 }

		
--  1.3.6.1.4.1.10428 9 1.102.15.1.1.1.16
		-- 1.3.6.1.4.1.10428 9 1.102.15.1.1.1.16
		fkV2EponIMOnuSecret OBJECT-TYPE
			SYNTAX OCTET STRING
			MAX-ACCESS read-only
			STATUS current
			DESCRIPTION
				"ONU authentication password"
			::= { fkV2EponIMOnuInfo 16 }

		
--  1.3.6.1.4.1.10428 9 1.102.15.1.1.1.17
		-- 1.3.6.1.4.1.10428 9 1.102.15.1.1.1.17
		fkV2EponIMOnuVendorCode OBJECT-TYPE
			SYNTAX Integer32
			MAX-ACCESS read-only
			STATUS current
			DESCRIPTION
				"vendor code"
			::= { fkV2EponIMOnuInfo 17 }

		
--  1.3.6.1.4.1.10428 9 1.102.15.1.1.1.18
		-- 1.3.6.1.4.1.10428 9 1.102.15.1.1.1.18
		fkV2EponIMOnuAuthTimer OBJECT-TYPE
			SYNTAX INTEGER (1..6000)
			MAX-ACCESS read-only
			STATUS current
			DESCRIPTION
				"ONU Auth timer"
			::= { fkV2EponIMOnuInfo 18 }

		
--  1.3.6.1.4.1.10428 9 1.102.15.1.1.1.19
		-- 1.3.6.1.4.1.10428 9 1.102.15.1.1.1.19
		fkV2EponIMOnuAuthTimeoutTimer OBJECT-TYPE
			SYNTAX INTEGER (1..15360)
			MAX-ACCESS read-only
			STATUS current
			DESCRIPTION
				"ONU Timeout timer"
			::= { fkV2EponIMOnuInfo 19 }

		
--  1.3.6.1.4.1.10428 9 1.102.15.1.1.1.20
		-- 1.3.6.1.4.1.10428 9 1.102.15.1.1.1.20
		fkV2EponIMOnuAuthRejectTimer OBJECT-TYPE
			SYNTAX INTEGER (1..15360)
			MAX-ACCESS read-only
			STATUS current
			DESCRIPTION
				"ONU Reject timer"
			::= { fkV2EponIMOnuInfo 20 }

		
		-- 1.3.6.1.4.1.10428 9 1.102.15.1.1.1.21
		fkV2EponIMOnuAutoUpgrade OBJECT-TYPE
			SYNTAX EponOnuState
			MAX-ACCESS read-only
			STATUS current
			DESCRIPTION
				"Description."
			::= { fkV2EponIMOnuInfo 21 }

		
		-- 1.3.6.1.4.1.10428 9 1.102.15.1.1.1.22
		fkV2EponIMOnuForceOpticPowerOff OBJECT-TYPE
			SYNTAX EponOnuState
			MAX-ACCESS read-only
			STATUS current
			DESCRIPTION
				"Description."
			::= { fkV2EponIMOnuInfo 22 }

		
		-- 1.3.6.1.4.1.10428 9 1.102.15.1.1.1.23
		fkV2EponIMOnuOpticButtonPushed OBJECT-TYPE
			SYNTAX EponOnuState
			MAX-ACCESS read-only
			STATUS current
			DESCRIPTION
				"Description."
			::= { fkV2EponIMOnuInfo 23 }

		
--  1.3.6.1.4.1.10428 9 1.102.15.1.1.2
		-- 1.3.6.1.4.1.10428 9 1.102.15.1.1.2
		fkV2EponIMOnuControl OBJECT IDENTIFIER ::= { fkV2EponIMOnuBase 2 }

		
--  1.3.6.1.4.1.10428 9 1.102.15.1.1.2.1
		-- 1.3.6.1.4.1.10428 9 1.102.15.1.1.2.1
		fkV2EponIMOnuControlRequest OBJECT-TYPE
			SYNTAX INTEGER
				{
				setOnuSecret(1),
				setOnuVendorCode(2),
				setOnuAuthTimer(3),
				setOnuConfigApply(4),
				setOnuAutoUpgrade(5),
				setOnuForcePowerOff(6),
				setOnuReset(7)
				}
			MAX-ACCESS read-write
			STATUS current
			DESCRIPTION
				"."
			::= { fkV2EponIMOnuControl 1 }

		
--  1.3.6.1.4.1.10428 9 1.102.15.1.1.2.2
		-- 1.3.6.1.4.1.10428 9 1.102.15.1.1.2.2
		fkV2EponIMOnuControlStatus OBJECT-TYPE
			SYNTAX FkControlStatusType
			MAX-ACCESS read-only
			STATUS current
			DESCRIPTION
				".
				"
			::= { fkV2EponIMOnuControl 2 }

		
--  1.3.6.1.4.1.10428 9 1.102.15.1.1.2.3
		-- 1.3.6.1.4.1.10428 9 1.102.15.1.1.2.3
		fkV2EponIMOnuControlTimer OBJECT-TYPE
			SYNTAX Gauge32
			MAX-ACCESS read-write
			STATUS current
			DESCRIPTION
				".
				"
			::= { fkV2EponIMOnuControl 3 }

		
--  1.3.6.1.4.1.10428 9 1.102.15.1.1.2.4
		-- 1.3.6.1.4.1.10428 9 1.102.15.1.1.2.4
		fkV2EponIMOnuControlTimeStamp OBJECT-TYPE
			SYNTAX TimeTicks
			MAX-ACCESS read-only
			STATUS current
			DESCRIPTION
				".."
			::= { fkV2EponIMOnuControl 4 }

		
--  1.3.6.1.4.1.10428 9 1.102.15.1.1.2.5
		-- 1.3.6.1.4.1.10428 9 1.102.15.1.1.2.5
		fkV2EponIMOnuControlReqResult OBJECT-TYPE
			SYNTAX FkControlRequestResultType
			MAX-ACCESS read-only
			STATUS current
			DESCRIPTION
				"."
			::= { fkV2EponIMOnuControl 5 }

		
--  1.3.6.1.4.1.10428 9 1.102.15.1.1.2.6
		-- 1.3.6.1.4.1.10428 9 1.102.15.1.1.2.6
		fkV2EponIMOnuControlSecret OBJECT-TYPE
			SYNTAX OCTET STRING (SIZE (1..16))
			MAX-ACCESS read-write
			STATUS current
			DESCRIPTION
				"."
			::= { fkV2EponIMOnuControl 6 }

		
--  1.3.6.1.4.1.10428 9 1.102.15.1.1.2.7
		-- 1.3.6.1.4.1.10428 9 1.102.15.1.1.2.7
		fkV2EponIMOnuControlOnuVendorCode OBJECT-TYPE
			SYNTAX INTEGER (0..255)
			MAX-ACCESS read-write
			STATUS current
			DESCRIPTION
				"."
			::= { fkV2EponIMOnuControl 7 }

		
--  1.3.6.1.4.1.10428 9 1.102.15.1.1.2.8
		-- 1.3.6.1.4.1.10428 9 1.102.15.1.1.2.8
		fkV2EponIMOnuControlAuthTimer OBJECT-TYPE
			SYNTAX INTEGER (1..6000)
			MAX-ACCESS read-write
			STATUS current
			DESCRIPTION
				"."
			::= { fkV2EponIMOnuControl 8 }

		
--  1.3.6.1.4.1.10428 9 1.102.15.1.1.2.9
		-- 1.3.6.1.4.1.10428 9 1.102.15.1.1.2.9
		fkV2EponIMOnuControlAuthTimeoutTimer OBJECT-TYPE
			SYNTAX INTEGER (1..15360)
			MAX-ACCESS read-write
			STATUS current
			DESCRIPTION
				"."
			::= { fkV2EponIMOnuControl 9 }

		
--  1.3.6.1.4.1.10428 9 1.102.15.1.1.2.10
		-- 1.3.6.1.4.1.10428 9 1.102.15.1.1.2.10
		fkV2EponIMOnuControlAuthRejectTimer OBJECT-TYPE
			SYNTAX INTEGER (1..15360)
			MAX-ACCESS read-write
			STATUS current
			DESCRIPTION
				"."
			::= { fkV2EponIMOnuControl 10 }

		
		-- 1.3.6.1.4.1.10428 9 1.102.15.1.1.2.11
		fkV2EponIMOnuControlAutoUpgrade OBJECT-TYPE
			SYNTAX EponOnuState
			MAX-ACCESS read-write
			STATUS current
			DESCRIPTION
				"Description."
			::= { fkV2EponIMOnuControl 11 }

		
		-- 1.3.6.1.4.1.10428 9 1.102.15.1.1.2.12
		fkV2EponIMOnuControlForceOpticPowerOff OBJECT-TYPE
			SYNTAX EponOnuState
			MAX-ACCESS read-write
			STATUS current
			DESCRIPTION
				"Description."
			::= { fkV2EponIMOnuControl 12 }

		
--  1.3.6.1.4.1.10428 9 1.102.15.1.1.3
		-- 1.3.6.1.4.1.10428 9 1.102.15.1.1.3
		fkV2EponIMOnuNotification OBJECT IDENTIFIER ::= { fkV2EponIMOnuBase 3 }

		
--  1.3.6.1.4.1.10428 9 1.102.15.1.1.3.1
		-- 1.3.6.1.4.1.10428 9 1.102.15.1.1.3.1
		fkV2EponIMOnuSecretChanged NOTIFICATION-TYPE
			OBJECTS { fkV2EponIMOnuControlRequest, fkV2EponIMOnuControlTimeStamp, fkV2EponIMOnuControlReqResult, fkV2EponIMOnuSecret }
			STATUS current
			DESCRIPTION 
				"Description."
			::= { fkV2EponIMOnuNotification 1 }

		
--  1.3.6.1.4.1.10428 9 1.102.15.1.1.3.2
		-- 1.3.6.1.4.1.10428 9 1.102.15.1.1.3.2
		fkV2EponIMOnuVendorCodeChanged NOTIFICATION-TYPE
			OBJECTS { fkV2EponIMOnuControlRequest, fkV2EponIMOnuControlTimeStamp, fkV2EponIMOnuControlReqResult, fkV2EponIMOnuVendorCode }
			STATUS current
			DESCRIPTION 
				"Description."
			::= { fkV2EponIMOnuNotification 2 }

		
--  1.3.6.1.4.1.10428 9 1.102.15.1.1.3.3
		-- 1.3.6.1.4.1.10428 9 1.102.15.1.1.3.3
		fkV2EponIMOnuAuthTimerChanged NOTIFICATION-TYPE
			OBJECTS { fkV2EponIMOnuControlRequest, fkV2EponIMOnuControlTimeStamp, fkV2EponIMOnuControlReqResult, fkV2EponIMOnuAuthTimer, fkV2EponIMOnuAuthTimeoutTimer, 
				fkV2EponIMOnuAuthRejectTimer }
			STATUS current
			DESCRIPTION 
				"Description."
			::= { fkV2EponIMOnuNotification 3 }

		
--  1.3.6.1.4.1.10428 9 1.102.15.1.1.3.4
		-- 1.3.6.1.4.1.10428 9 1.102.15.1.1.3.4
		fkV2EponIMOnuConfigApplySetted NOTIFICATION-TYPE
			OBJECTS { fkV2EponIMOnuControlRequest, fkV2EponIMOnuControlTimeStamp, fkV2EponIMOnuControlReqResult }
			STATUS current
			DESCRIPTION 
				"Description."
			::= { fkV2EponIMOnuNotification 4 }

		
		-- 1.3.6.1.4.1.10428 9 1.102.15.1.1.3.5
		fkV2EponIMOnuAutoUpgradeChanged NOTIFICATION-TYPE
			OBJECTS { fkV2EponIMOnuControlRequest, fkV2EponIMOnuControlTimeStamp, fkV2EponIMOnuControlReqResult, fkV2EponIMOnuControlAuthRejectTimer }
			STATUS current
			DESCRIPTION 
				"Description."
			::= { fkV2EponIMOnuNotification 5 }

		
		-- 1.3.6.1.4.1.10428 9 1.102.15.1.1.3.6
		fkV2EponIMOnuForcePowerOffChanged NOTIFICATION-TYPE
			OBJECTS { fkV2EponIMOnuControlRequest, fkV2EponIMOnuControlTimeStamp, fkV2EponIMOnuControlReqResult, fkV2EponIMOnuForceOpticPowerOff }
			STATUS current
			DESCRIPTION 
				"Description."
			::= { fkV2EponIMOnuNotification 6 }

		
		-- 1.3.6.1.4.1.10428 9 1.102.15.1.1.3.7
		fkV2EponIMOnuReset NOTIFICATION-TYPE
			OBJECTS { fkV2EponIMOnuControlRequest, fkV2EponIMOnuControlTimeStamp, fkV2EponIMOnuControlReqResult }
			STATUS current
			DESCRIPTION 
				"Description."
			::= { fkV2EponIMOnuNotification 7 }

		
--  1.3.6.1.4.1.10428 9 1.102.15.1.2
		-- 1.3.6.1.4.1.10428 9 1.102.15.1.2
		fkV2EponIMOnuFW OBJECT IDENTIFIER ::= { fkV2EponIMOnu 2 }

		
		-- 1.3.6.1.4.1.10428 9 1.102.15.1.2.1
		fkV2EponIMOnuFWTable OBJECT-TYPE
			SYNTAX SEQUENCE OF FkV2EponIMOnuFWEntry
			MAX-ACCESS not-accessible
			STATUS current
			DESCRIPTION
				"Description."
			::= { fkV2EponIMOnuFW 1 }

		
		-- 1.3.6.1.4.1.10428 9 1.102.15.1.2.1.1
		fkV2EponIMOnuFWEntry OBJECT-TYPE
			SYNTAX FkV2EponIMOnuFWEntry
			MAX-ACCESS not-accessible
			STATUS current
			DESCRIPTION
				"Description."
			INDEX { fkV2EponIMOnuFWName }
			::= { fkV2EponIMOnuFWTable 1 }

		
		FkV2EponIMOnuFWEntry ::=
			SEQUENCE { 
				fkV2EponIMOnuFWName
					OCTET STRING
			 }

--  1.3.6.1.4.1.10428 9 1.102.15.1.2.1.1.1
		-- 1.3.6.1.4.1.10428 9 1.102.15.1.2.1.1.1
		fkV2EponIMOnuFWName OBJECT-TYPE
			SYNTAX OCTET STRING
			MAX-ACCESS read-only
			STATUS current
			DESCRIPTION
				"firmware name"
			::= { fkV2EponIMOnuFWEntry 1 }

		
--  1.3.6.1.4.1.10428 9 1.102.15.1.2.2
		-- 1.3.6.1.4.1.10428 9 1.102.15.1.2.2
		fkV2EponIMOnuFWControl OBJECT IDENTIFIER ::= { fkV2EponIMOnuFW 2 }

		
--  1.3.6.1.4.1.10428 9 1.102.15.1.2.2.1
		-- 1.3.6.1.4.1.10428 9 1.102.15.1.2.2.1
		fkV2EponIMOnuFWControlRequest OBJECT-TYPE
			SYNTAX INTEGER
				{
				copyFirmware(1),
				destroyFirmware(2),
				updateFirmware(3),
				commitFirmware(4)
				}
			MAX-ACCESS read-write
			STATUS current
			DESCRIPTION
				"."
			::= { fkV2EponIMOnuFWControl 1 }

		
--  1.3.6.1.4.1.10428 9 1.102.15.1.2.2.2
		-- 1.3.6.1.4.1.10428 9 1.102.15.1.2.2.2
		fkV2EponIMOnuFWControlStatus OBJECT-TYPE
			SYNTAX FkControlStatusType
			MAX-ACCESS read-only
			STATUS current
			DESCRIPTION
				"."
			::= { fkV2EponIMOnuFWControl 2 }

		
--  1.3.6.1.4.1.10428 9 1.102.15.1.2.2.3
		-- 1.3.6.1.4.1.10428 9 1.102.15.1.2.2.3
		fkV2EponIMOnuFWControlTimer OBJECT-TYPE
			SYNTAX Gauge32
			MAX-ACCESS read-write
			STATUS current
			DESCRIPTION
				"."
			::= { fkV2EponIMOnuFWControl 3 }

		
--  1.3.6.1.4.1.10428 9 1.102.15.1.2.2.4
		-- 1.3.6.1.4.1.10428 9 1.102.15.1.2.2.4
		fkV2EponIMOnuFWControlTimeStamp OBJECT-TYPE
			SYNTAX TimeTicks
			MAX-ACCESS read-only
			STATUS current
			DESCRIPTION
				"."
			::= { fkV2EponIMOnuFWControl 4 }

		
--  1.3.6.1.4.1.10428 9 1.102.15.1.2.2.5
		-- 1.3.6.1.4.1.10428 9 1.102.15.1.2.2.5
		fkV2EponIMOnuFWControlReqResult OBJECT-TYPE
			SYNTAX FkControlRequestResultType
			MAX-ACCESS read-only
			STATUS current
			DESCRIPTION
				"."
			::= { fkV2EponIMOnuFWControl 5 }

		
--  1.3.6.1.4.1.10428 9 1.102.15.1.2.2.6
		-- 1.3.6.1.4.1.10428 9 1.102.15.1.2.2.6
		fkV2EponIMOnuFWControlServerIp OBJECT-TYPE
			SYNTAX OCTET STRING
			MAX-ACCESS read-write
			STATUS current
			DESCRIPTION
				"Description."
			::= { fkV2EponIMOnuFWControl 6 }

		
--  1.3.6.1.4.1.10428 9 1.102.15.1.2.2.7
		-- 1.3.6.1.4.1.10428 9 1.102.15.1.2.2.7
		fkV2EponIMOnuFWControlUpDownFlag OBJECT-TYPE
			SYNTAX INTEGER
				{
				upload(1),
				download(2)
				}
			MAX-ACCESS read-write
			STATUS current
			DESCRIPTION
				"Description."
			::= { fkV2EponIMOnuFWControl 7 }

		
--  1.3.6.1.4.1.10428 9 1.102.15.1.2.2.8
		-- 1.3.6.1.4.1.10428 9 1.102.15.1.2.2.8
		fkV2EponIMOnuFWControlUserId OBJECT-TYPE
			SYNTAX OCTET STRING
			MAX-ACCESS read-write
			STATUS current
			DESCRIPTION
				"Description."
			::= { fkV2EponIMOnuFWControl 8 }

		
--  1.3.6.1.4.1.10428 9 1.102.15.1.2.2.9
		-- 1.3.6.1.4.1.10428 9 1.102.15.1.2.2.9
		fkV2EponIMOnuFWControlPassword OBJECT-TYPE
			SYNTAX OCTET STRING
			MAX-ACCESS read-write
			STATUS current
			DESCRIPTION
				"Description."
			::= { fkV2EponIMOnuFWControl 9 }

		
--  1.3.6.1.4.1.10428 9 1.102.15.1.2.2.10
		-- 1.3.6.1.4.1.10428 9 1.102.15.1.2.2.10
		fkV2EponIMOnuFWControlFileName OBJECT-TYPE
			SYNTAX OCTET STRING
			MAX-ACCESS read-write
			STATUS current
			DESCRIPTION
				"Description."
			::= { fkV2EponIMOnuFWControl 10 }

		
--  1.3.6.1.4.1.10428 9 1.102.15.1.2.2.11
		-- 1.3.6.1.4.1.10428 9 1.102.15.1.2.2.11
		fkV2EponIMOnuFWControlUpdateCommitTime OBJECT-TYPE
			SYNTAX INTEGER (60..86400)
			MAX-ACCESS read-write
			STATUS current
			DESCRIPTION
				"Description."
			::= { fkV2EponIMOnuFWControl 11 }

		
--  1.3.6.1.4.1.10428 9 1.102.15.1.2.3
		-- 1.3.6.1.4.1.10428 9 1.102.15.1.2.3
		fkV2EponIMOnuFWNotification OBJECT IDENTIFIER ::= { fkV2EponIMOnuFW 3 }

		
--  1.3.6.1.4.1.10428 9 1.102.15.1.2.3.1
		-- 1.3.6.1.4.1.10428 9 1.102.15.1.2.3.1
		fkV2EponIMOnuFWFirmwareCpSetted NOTIFICATION-TYPE
			OBJECTS { fkV2EponIMOnuFWControlRequest, fkV2EponIMOnuFWControlTimeStamp, fkV2EponIMOnuFWControlReqResult, fkV2EponIMOnuFWControlServerIp, fkV2EponIMOnuFWControlUpDownFlag, 
				fkV2EponIMOnuFWControlUserId, fkV2EponIMOnuFWControlPassword }
			STATUS current
			DESCRIPTION 
				"Description."
			::= { fkV2EponIMOnuFWNotification 1 }

		
--  1.3.6.1.4.1.10428 9 1.102.15.1.2.3.2
		-- 1.3.6.1.4.1.10428 9 1.102.15.1.2.3.2
		fkV2EponIMOnuFWFirmwareDestroyed NOTIFICATION-TYPE
			OBJECTS { fkV2EponIMOnuFWControlRequest, fkV2EponIMOnuFWControlTimeStamp, fkV2EponIMOnuFWControlReqResult, fkV2EponIMOnuFWControlFileName }
			STATUS current
			DESCRIPTION 
				"Description."
			::= { fkV2EponIMOnuFWNotification 2 }

		
--  1.3.6.1.4.1.10428 9 1.102.15.1.2.3.3
		-- 1.3.6.1.4.1.10428 9 1.102.15.1.2.3.3
		fkV2EponIMOnuFWFirmwareUpgradeSetted NOTIFICATION-TYPE
			OBJECTS { fkV2EponIMOnuFWControlRequest, fkV2EponIMOnuFWControlTimeStamp, fkV2EponIMOnuFWControlReqResult, fkV2EponIMOnuFWControlUpdateCommitTime, fkV2EponIMOnuFWControlFileName
				 }
			STATUS current
			DESCRIPTION 
				"Description."
			::= { fkV2EponIMOnuFWNotification 3 }

		
--  1.3.6.1.4.1.10428 9 1.102.15.1.2.3.4
		-- 1.3.6.1.4.1.10428 9 1.102.15.1.2.3.4
		fkV2EponIMOnuFWFirmwareCommitSetted NOTIFICATION-TYPE
			OBJECTS { fkV2EponIMOnuFWControlRequest, fkV2EponIMOnuFWControlTimeStamp, fkV2EponIMOnuFWControlReqResult }
			STATUS current
			DESCRIPTION 
				"Description."
			::= { fkV2EponIMOnuFWNotification 4 }

		
--   TAG : OnuBridge 
-- 
-- 1.3.6.1.4.1.10428 9 1.102.15.2
		-- 1.3.6.1.4.1.10428 9 1.102.15.2
		fkV2EponIMOnuBridge OBJECT IDENTIFIER ::= { fkV2EponIM 2 }

		
--  1.3.6.1.4.1.10428 9 1.102.15.2.1
		-- 1.3.6.1.4.1.10428 9 1.102.15.2.1
		fkV2EponIMOnuPort OBJECT IDENTIFIER ::= { fkV2EponIMOnuBridge 1 }

		
		-- 1.3.6.1.4.1.10428 9 1.102.15.2.1.1
		fkV2EponIMOnuPortTable OBJECT-TYPE
			SYNTAX SEQUENCE OF FkV2EponIMOnuPortEntry
			MAX-ACCESS not-accessible
			STATUS current
			DESCRIPTION
				"Description."
			::= { fkV2EponIMOnuPort 1 }

		
		-- 1.3.6.1.4.1.10428 9 1.102.15.2.1.1.1
		fkV2EponIMOnuPortEntry OBJECT-TYPE
			SYNTAX FkV2EponIMOnuPortEntry
			MAX-ACCESS not-accessible
			STATUS current
			DESCRIPTION
				"Description."
			INDEX { fkV2EponIMOnuPortIndex }
			::= { fkV2EponIMOnuPortTable 1 }

		
		FkV2EponIMOnuPortEntry ::=
			SEQUENCE { 
				fkV2EponIMOnuPortIndex
					INTEGER,
				fkV2EponIMOnuPortId
					Integer32,
				fkV2EponIMOnuPortType
					EponPortType,
				fkV2EponIMOnuPortAdminStatus
					EponOnuLinkStatus,
				fkV2EponIMOnuPortOperStatus
					EponOnuLinkStatus,
				fkV2EponIMOnuPortLinkupTime
					OCTET STRING,
				fkV2EponIMOnuPortUpTime
					TimeTicks,
				fkV2EponIMOnuPortFECtxEnable
					EponOnuState,
				fkV2EponIMOnuPortFECrxEnable
					EponOnuState,
				fkV2EponIMOnuPortLaserAlwaysOn
					EponOnuState,
				fkV2EponIMOnuPortDropInMcastTraffic
					EponOnuState,
				fkV2EponIMOnuPortDropInBcastTraffic
					EponOnuState,
				fkV2EponIMOnuPortBlockDataTraffic
					EponOnuState
			 }

--  1.3.6.1.4.1.10428 9 1.102.15.2.1.1.1.1
		-- 1.3.6.1.4.1.10428 9 1.102.15.2.1.1.1.1
		fkV2EponIMOnuPortIndex OBJECT-TYPE
			SYNTAX INTEGER (1..512)
			MAX-ACCESS read-only
			STATUS current
			DESCRIPTION
				"."
			::= { fkV2EponIMOnuPortEntry 1 }

		
--  1.3.6.1.4.1.10428 9 1.102.15.2.1.1.1.2
		-- 1.3.6.1.4.1.10428 9 1.102.15.2.1.1.1.2
		fkV2EponIMOnuPortId OBJECT-TYPE
			SYNTAX Integer32
			MAX-ACCESS read-only
			STATUS current
			DESCRIPTION
				"."
			::= { fkV2EponIMOnuPortEntry 2 }

		
--  1.3.6.1.4.1.10428 9 1.102.15.2.1.1.1.3
		-- 1.3.6.1.4.1.10428 9 1.102.15.2.1.1.1.3
		fkV2EponIMOnuPortType OBJECT-TYPE
			SYNTAX EponPortType
			MAX-ACCESS read-only
			STATUS current
			DESCRIPTION
				"."
			::= { fkV2EponIMOnuPortEntry 3 }

		
--  1.3.6.1.4.1.10428 9 1.102.15.2.1.1.1.4
		-- 1.3.6.1.4.1.10428 9 1.102.15.2.1.1.1.4
		fkV2EponIMOnuPortAdminStatus OBJECT-TYPE
			SYNTAX EponOnuLinkStatus
			MAX-ACCESS read-only
			STATUS current
			DESCRIPTION
				"."
			::= { fkV2EponIMOnuPortEntry 4 }

		
--  1.3.6.1.4.1.10428 9 1.102.15.2.1.1.1.5
		-- 1.3.6.1.4.1.10428 9 1.102.15.2.1.1.1.5
		fkV2EponIMOnuPortOperStatus OBJECT-TYPE
			SYNTAX EponOnuLinkStatus
			MAX-ACCESS read-only
			STATUS current
			DESCRIPTION
				"."
			::= { fkV2EponIMOnuPortEntry 5 }

		
--  1.3.6.1.4.1.10428 9 1.102.15.2.1.1.1.6
		-- 1.3.6.1.4.1.10428 9 1.102.15.2.1.1.1.6
		fkV2EponIMOnuPortLinkupTime OBJECT-TYPE
			SYNTAX OCTET STRING
			MAX-ACCESS read-only
			STATUS current
			DESCRIPTION
				"."
			::= { fkV2EponIMOnuPortEntry 6 }

		
--  1.3.6.1.4.1.10428 9 1.102.15.2.1.1.1.7
		-- 1.3.6.1.4.1.10428 9 1.102.15.2.1.1.1.7
		fkV2EponIMOnuPortUpTime OBJECT-TYPE
			SYNTAX TimeTicks
			MAX-ACCESS read-only
			STATUS current
			DESCRIPTION
				"."
			::= { fkV2EponIMOnuPortEntry 7 }

		
		-- 1.3.6.1.4.1.10428 9 1.102.15.2.1.1.1.8
		fkV2EponIMOnuPortFECtxEnable OBJECT-TYPE
			SYNTAX EponOnuState
			MAX-ACCESS read-only
			STATUS current
			DESCRIPTION
				"Description."
			::= { fkV2EponIMOnuPortEntry 8 }

		
		-- 1.3.6.1.4.1.10428 9 1.102.15.2.1.1.1.9
		fkV2EponIMOnuPortFECrxEnable OBJECT-TYPE
			SYNTAX EponOnuState
			MAX-ACCESS read-only
			STATUS current
			DESCRIPTION
				"Description."
			::= { fkV2EponIMOnuPortEntry 9 }

		
		-- 1.3.6.1.4.1.10428 9 1.102.15.2.1.1.1.10
		fkV2EponIMOnuPortLaserAlwaysOn OBJECT-TYPE
			SYNTAX EponOnuState
			MAX-ACCESS read-only
			STATUS current
			DESCRIPTION
				"Description."
			::= { fkV2EponIMOnuPortEntry 10 }

		
		-- 1.3.6.1.4.1.10428 9 1.102.15.2.1.1.1.11
		fkV2EponIMOnuPortDropInMcastTraffic OBJECT-TYPE
			SYNTAX EponOnuState
			MAX-ACCESS read-only
			STATUS current
			DESCRIPTION
				"Description."
			::= { fkV2EponIMOnuPortEntry 11 }

		
		-- 1.3.6.1.4.1.10428 9 1.102.15.2.1.1.1.12
		fkV2EponIMOnuPortDropInBcastTraffic OBJECT-TYPE
			SYNTAX EponOnuState
			MAX-ACCESS read-only
			STATUS current
			DESCRIPTION
				"Description."
			::= { fkV2EponIMOnuPortEntry 12 }

		
		-- 1.3.6.1.4.1.10428 9 1.102.15.2.1.1.1.13
		fkV2EponIMOnuPortBlockDataTraffic OBJECT-TYPE
			SYNTAX EponOnuState
			MAX-ACCESS read-write
			STATUS current
			DESCRIPTION
				"Description."
			::= { fkV2EponIMOnuPortEntry 13 }

		
--  1.3.6.1.4.1.10428 9 1.102.15.2.1.2
		-- 1.3.6.1.4.1.10428 9 1.102.15.2.1.2
		fkV2EponIMOnuPortControl OBJECT IDENTIFIER ::= { fkV2EponIMOnuPort 2 }

		
--  1.3.6.1.4.1.10428 9 1.102.15.2.1.2.1
		-- 1.3.6.1.4.1.10428 9 1.102.15.2.1.2.1
		fkV2EponIMOnuPortControlRequest OBJECT-TYPE
			SYNTAX INTEGER { changeAdminStatus(1) }
			MAX-ACCESS read-write
			STATUS current
			DESCRIPTION
				"."
			::= { fkV2EponIMOnuPortControl 1 }

		
--  1.3.6.1.4.1.10428 9 1.102.15.2.1.2.2
		-- 1.3.6.1.4.1.10428 9 1.102.15.2.1.2.2
		fkV2EponIMOnuPortControlStatus OBJECT-TYPE
			SYNTAX FkControlStatusType
			MAX-ACCESS read-only
			STATUS current
			DESCRIPTION
				"."
			::= { fkV2EponIMOnuPortControl 2 }

		
--  1.3.6.1.4.1.10428 9 1.102.15.2.1.2.3
		-- 1.3.6.1.4.1.10428 9 1.102.15.2.1.2.3
		fkV2EponIMOnuPortControlTimer OBJECT-TYPE
			SYNTAX Gauge32
			MAX-ACCESS read-write
			STATUS current
			DESCRIPTION
				"."
			::= { fkV2EponIMOnuPortControl 3 }

		
--  1.3.6.1.4.1.10428 9 1.102.15.2.1.2.4
		-- 1.3.6.1.4.1.10428 9 1.102.15.2.1.2.4
		fkV2EponIMOnuPortControlTimeStamp OBJECT-TYPE
			SYNTAX TimeTicks
			MAX-ACCESS read-only
			STATUS current
			DESCRIPTION
				"."
			::= { fkV2EponIMOnuPortControl 4 }

		
--  1.3.6.1.4.1.10428 9 1.102.15.2.1.2.5
		-- 1.3.6.1.4.1.10428 9 1.102.15.2.1.2.5
		fkV2EponIMOnuPortControlReqResult OBJECT-TYPE
			SYNTAX FkControlRequestResultType
			MAX-ACCESS read-only
			STATUS current
			DESCRIPTION
				"."
			::= { fkV2EponIMOnuPortControl 5 }

		
--  1.3.6.1.4.1.10428 9 1.102.15.2.1.2.6
		-- 1.3.6.1.4.1.10428 9 1.102.15.2.1.2.6
		fkV2EponIMOnuPortControlAdminState OBJECT-TYPE
			SYNTAX EponOnuState
			MAX-ACCESS read-write
			STATUS current
			DESCRIPTION
				"Description."
			::= { fkV2EponIMOnuPortControl 6 }

		
--  1.3.6.1.4.1.10428 9 1.102.15.2.1.3
		-- 1.3.6.1.4.1.10428 9 1.102.15.2.1.3
		fkV2EponIMOnuPortNotification OBJECT IDENTIFIER ::= { fkV2EponIMOnuPort 3 }

		
--  1.3.6.1.4.1.10428 9 1.102.15.2.1.3.1
		-- 1.3.6.1.4.1.10428 9 1.102.15.2.1.3.1
		fkV2EponIMOnuPortAdminStateChanged NOTIFICATION-TYPE
			OBJECTS { fkV2EponIMOnuPortControlRequest, fkV2EponIMOnuPortControlTimeStamp, fkV2EponIMOnuPortControlReqResult, fkV2EponIMOnuPortAdminStatus }
			STATUS current
			DESCRIPTION 
				"Description."
			::= { fkV2EponIMOnuPortNotification 1 }

		
--  1.3.6.1.4.1.10428 9 1.102.15.2.2
		-- 1.3.6.1.4.1.10428 9 1.102.15.2.2
		fkV2EponIMOnuBridgeBase OBJECT IDENTIFIER ::= { fkV2EponIMOnuBridge 2 }

		
--  1.3.6.1.4.1.10428 9 1.102.15.2.2.1
		-- 1.3.6.1.4.1.10428 9 1.102.15.2.2.1
		fkV2EponIMOnuBridgeInfo OBJECT IDENTIFIER ::= { fkV2EponIMOnuBridgeBase 1 }

		
--  1.3.6.1.4.1.10428 9 1.102.15.2.2.1.1
		-- 1.3.6.1.4.1.10428 9 1.102.15.2.2.1.1
		fkV2EponIMOnuRxFlowCtrl OBJECT-TYPE
			SYNTAX EponOnuState
			MAX-ACCESS read-only
			STATUS current
			DESCRIPTION
				"."
			::= { fkV2EponIMOnuBridgeInfo 1 }

		
--  1.3.6.1.4.1.10428 9 1.102.15.2.2.1.2
		-- 1.3.6.1.4.1.10428 9 1.102.15.2.2.1.2
		fkV2EponIMOnuTxFlowCtrl OBJECT-TYPE
			SYNTAX EponOnuState
			MAX-ACCESS read-only
			STATUS current
			DESCRIPTION
				"."
			::= { fkV2EponIMOnuBridgeInfo 2 }

		
--  1.3.6.1.4.1.10428 9 1.102.15.2.2.1.3
		-- 1.3.6.1.4.1.10428 9 1.102.15.2.2.1.3
		fkV2EponIMOnuFlowCtrlLowThreshold OBJECT-TYPE
			SYNTAX INTEGER (0..100)
			MAX-ACCESS read-only
			STATUS current
			DESCRIPTION
				"."
			::= { fkV2EponIMOnuBridgeInfo 3 }

		
--  1.3.6.1.4.1.10428 9 1.102.15.2.2.1.4
		-- 1.3.6.1.4.1.10428 9 1.102.15.2.2.1.4
		fkV2EponIMOnuFlowCtrlHighThreshold OBJECT-TYPE
			SYNTAX INTEGER (0..100)
			MAX-ACCESS read-only
			STATUS current
			DESCRIPTION
				"."
			::= { fkV2EponIMOnuBridgeInfo 4 }

		
--  1.3.6.1.4.1.10428 9 1.102.15.2.2.2
		-- 1.3.6.1.4.1.10428 9 1.102.15.2.2.2
		fkV2EponIMOnuBridgeControl OBJECT IDENTIFIER ::= { fkV2EponIMOnuBridgeBase 2 }

		
--  1.3.6.1.4.1.10428 9 1.102.15.2.2.2.1
		-- 1.3.6.1.4.1.10428 9 1.102.15.2.2.2.1
		fkV2EponIMOnuBridgeControlRequest OBJECT-TYPE
			SYNTAX INTEGER { setFlowControl(1) }
			MAX-ACCESS read-write
			STATUS current
			DESCRIPTION
				"."
			::= { fkV2EponIMOnuBridgeControl 1 }

		
--  1.3.6.1.4.1.10428 9 1.102.15.2.2.2.2
		-- 1.3.6.1.4.1.10428 9 1.102.15.2.2.2.2
		fkV2EponIMOnuBridgeControlStatus OBJECT-TYPE
			SYNTAX FkControlStatusType
			MAX-ACCESS read-only
			STATUS current
			DESCRIPTION
				".
				"
			::= { fkV2EponIMOnuBridgeControl 2 }

		
--  1.3.6.1.4.1.10428 9 1.102.15.2.2.2.3
		-- 1.3.6.1.4.1.10428 9 1.102.15.2.2.2.3
		fkV2EponIMOnuBridgeControlTimer OBJECT-TYPE
			SYNTAX Gauge32
			MAX-ACCESS read-write
			STATUS current
			DESCRIPTION
				".
				"
			::= { fkV2EponIMOnuBridgeControl 3 }

		
--  1.3.6.1.4.1.10428 9 1.102.15.2.2.2.4
		-- 1.3.6.1.4.1.10428 9 1.102.15.2.2.2.4
		fkV2EponIMOnuBridgeControlTimeStamp OBJECT-TYPE
			SYNTAX TimeTicks
			MAX-ACCESS read-only
			STATUS current
			DESCRIPTION
				".."
			::= { fkV2EponIMOnuBridgeControl 4 }

		
--  1.3.6.1.4.1.10428 9 1.102.15.2.2.2.5
		-- 1.3.6.1.4.1.10428 9 1.102.15.2.2.2.5
		fkV2EponIMOnuBridgeControlReqResult OBJECT-TYPE
			SYNTAX FkControlRequestResultType
			MAX-ACCESS read-only
			STATUS current
			DESCRIPTION
				"."
			::= { fkV2EponIMOnuBridgeControl 5 }

		
--  1.3.6.1.4.1.10428 9 1.102.15.2.2.2.6
		-- 1.3.6.1.4.1.10428 9 1.102.15.2.2.2.6
		fkV2EponIMOnuBridgeControlRxFlowCtrl OBJECT-TYPE
			SYNTAX EponOnuState
			MAX-ACCESS read-write
			STATUS current
			DESCRIPTION
				"."
			::= { fkV2EponIMOnuBridgeControl 6 }

		
--  1.3.6.1.4.1.10428 9 1.102.15.2.2.2.7
		-- 1.3.6.1.4.1.10428 9 1.102.15.2.2.2.7
		fkV2EponIMOnuBridgeControlTxFlowCtrl OBJECT-TYPE
			SYNTAX EponOnuState
			MAX-ACCESS read-write
			STATUS current
			DESCRIPTION
				"."
			::= { fkV2EponIMOnuBridgeControl 7 }

		
--  1.3.6.1.4.1.10428 9 1.102.15.2.2.2.8
		-- 1.3.6.1.4.1.10428 9 1.102.15.2.2.2.8
		fkV2EponIMOnuBridgeControlFlowCtrlLowThreshold OBJECT-TYPE
			SYNTAX INTEGER (0..100)
			MAX-ACCESS read-write
			STATUS current
			DESCRIPTION
				"."
			::= { fkV2EponIMOnuBridgeControl 8 }

		
--  1.3.6.1.4.1.10428 9 1.102.15.2.2.2.9
		-- 1.3.6.1.4.1.10428 9 1.102.15.2.2.2.9
		fkV2EponIMOnuBridgeControlFlowCtrlHighThreshold OBJECT-TYPE
			SYNTAX INTEGER (0..100)
			MAX-ACCESS read-write
			STATUS current
			DESCRIPTION
				"."
			::= { fkV2EponIMOnuBridgeControl 9 }

		
--  1.3.6.1.4.1.10428 9 1.102.15.2.2.3
		-- 1.3.6.1.4.1.10428 9 1.102.15.2.2.3
		fkV2EponIMOnuBridgeNotification OBJECT IDENTIFIER ::= { fkV2EponIMOnuBridgeBase 3 }

		
--  1.3.6.1.4.1.10428 9 1.102.15.2.2.3.1
		-- 1.3.6.1.4.1.10428 9 1.102.15.2.2.3.1
		fkV2EponIMOnuBridgeFlowCtrlChagned NOTIFICATION-TYPE
			OBJECTS { fkV2EponIMOnuBridgeControlRequest, fkV2EponIMOnuBridgeControlTimeStamp, fkV2EponIMOnuBridgeControlReqResult, fkV2EponIMOnuRxFlowCtrl, fkV2EponIMOnuTxFlowCtrl, 
				fkV2EponIMOnuFlowCtrlLowThreshold, fkV2EponIMOnuFlowCtrlHighThreshold }
			STATUS current
			DESCRIPTION 
				"Description."
			::= { fkV2EponIMOnuBridgeNotification 1 }

		
--    
-- TAG : OnuStats 
--  
-- 1.3.6.1.4.1.10428 9 1.102.15.3
		-- 1.3.6.1.4.1.10428 9 1.102.15.3
		fkV2EponIMOnuStats OBJECT IDENTIFIER ::= { fkV2EponIM 3 }

		
--  1.3.6.1.4.1.10428 9 1.102.15.3.1
		-- 1.3.6.1.4.1.10428 9 1.102.15.3.1
		fkV2EponIMOnuPortStats OBJECT IDENTIFIER ::= { fkV2EponIMOnuStats 1 }

		
		-- 1.3.6.1.4.1.10428 9 1.102.15.3.1.1
		fkV2EponIMOnuPortIfStatsTable OBJECT-TYPE
			SYNTAX SEQUENCE OF FkV2EponIMOnuPortIfStatsEntry
			MAX-ACCESS not-accessible
			STATUS current
			DESCRIPTION
				"Description."
			::= { fkV2EponIMOnuPortStats 1 }

		
		-- 1.3.6.1.4.1.10428 9 1.102.15.3.1.1.1
		fkV2EponIMOnuPortIfStatsEntry OBJECT-TYPE
			SYNTAX FkV2EponIMOnuPortIfStatsEntry
			MAX-ACCESS not-accessible
			STATUS current
			DESCRIPTION
				"Description."
			INDEX { fkV2EponIMOnuPortIndex }
			::= { fkV2EponIMOnuPortIfStatsTable 1 }

		
		FkV2EponIMOnuPortIfStatsEntry ::=
			SEQUENCE { 
				fkV2EponIMOnuPortIfInOctets
					Counter64,
				fkV2EponIMOnuPortIfInUnicast
					Counter64,
				fkV2EponIMOnuPortIfInMulticast
					Counter64,
				fkV2EponIMOnuPortIfInBroadcast
					Counter64,
				fkV2EponIMOnuPortIfInDiscards
					Counter64,
				fkV2EponIMOnuPortIfInErrors
					Counter64,
				fkV2EponIMOnuPortIfInUnknownProtos
					Counter64,
				fkV2EponIMOnuPortIfOutOctets
					Counter64,
				fkV2EponIMOnuPortIfOutUnicast
					Counter64,
				fkV2EponIMOnuPortIfOutMulticast
					Counter64,
				fkV2EponIMOnuPortIfOutBroadcast
					Counter64,
				fkV2EponIMOnuPortIfOutDiscards
					Counter64,
				fkV2EponIMOnuPortIfOutErrors
					Counter64
			 }

--  1.3.6.1.4.1.10428 9 1.102.15.3.1.1.1.1
		-- 1.3.6.1.4.1.10428 9 1.102.15.3.1.1.1.1
		fkV2EponIMOnuPortIfInOctets OBJECT-TYPE
			SYNTAX Counter64
			MAX-ACCESS read-only
			STATUS current
			DESCRIPTION
				"."
			::= { fkV2EponIMOnuPortIfStatsEntry 1 }

		
--  1.3.6.1.4.1.10428 9 1.102.15.3.1.1.1.2
		-- 1.3.6.1.4.1.10428 9 1.102.15.3.1.1.1.2
		fkV2EponIMOnuPortIfInUnicast OBJECT-TYPE
			SYNTAX Counter64
			MAX-ACCESS read-only
			STATUS current
			DESCRIPTION
				"."
			::= { fkV2EponIMOnuPortIfStatsEntry 2 }

		
--  1.3.6.1.4.1.10428 9 1.102.15.3.1.1.1.3
		-- 1.3.6.1.4.1.10428 9 1.102.15.3.1.1.1.3
		fkV2EponIMOnuPortIfInMulticast OBJECT-TYPE
			SYNTAX Counter64
			MAX-ACCESS read-only
			STATUS current
			DESCRIPTION
				"."
			::= { fkV2EponIMOnuPortIfStatsEntry 3 }

		
--  1.3.6.1.4.1.10428 9 1.102.15.3.1.1.1.4
		-- 1.3.6.1.4.1.10428 9 1.102.15.3.1.1.1.4
		fkV2EponIMOnuPortIfInBroadcast OBJECT-TYPE
			SYNTAX Counter64
			MAX-ACCESS read-only
			STATUS current
			DESCRIPTION
				"."
			::= { fkV2EponIMOnuPortIfStatsEntry 4 }

		
--  1.3.6.1.4.1.10428 9 1.102.15.3.1.1.1.5
		-- 1.3.6.1.4.1.10428 9 1.102.15.3.1.1.1.5
		fkV2EponIMOnuPortIfInDiscards OBJECT-TYPE
			SYNTAX Counter64
			MAX-ACCESS read-only
			STATUS current
			DESCRIPTION
				"."
			::= { fkV2EponIMOnuPortIfStatsEntry 5 }

		
--  1.3.6.1.4.1.10428 9 1.102.15.3.1.1.1.6
		-- 1.3.6.1.4.1.10428 9 1.102.15.3.1.1.1.6
		fkV2EponIMOnuPortIfInErrors OBJECT-TYPE
			SYNTAX Counter64
			MAX-ACCESS read-only
			STATUS current
			DESCRIPTION
				"."
			::= { fkV2EponIMOnuPortIfStatsEntry 6 }

		
--  1.3.6.1.4.1.10428 9 1.102.15.3.1.1.1.7
		-- 1.3.6.1.4.1.10428 9 1.102.15.3.1.1.1.7
		fkV2EponIMOnuPortIfInUnknownProtos OBJECT-TYPE
			SYNTAX Counter64
			MAX-ACCESS read-only
			STATUS current
			DESCRIPTION
				"."
			::= { fkV2EponIMOnuPortIfStatsEntry 7 }

		
--  1.3.6.1.4.1.10428 9 1.102.15.3.1.1.1.8
		-- 1.3.6.1.4.1.10428 9 1.102.15.3.1.1.1.8
		fkV2EponIMOnuPortIfOutOctets OBJECT-TYPE
			SYNTAX Counter64
			MAX-ACCESS read-only
			STATUS current
			DESCRIPTION
				"."
			::= { fkV2EponIMOnuPortIfStatsEntry 8 }

		
--  1.3.6.1.4.1.10428 9 1.102.15.3.1.1.1.9
		-- 1.3.6.1.4.1.10428 9 1.102.15.3.1.1.1.9
		fkV2EponIMOnuPortIfOutUnicast OBJECT-TYPE
			SYNTAX Counter64
			MAX-ACCESS read-only
			STATUS current
			DESCRIPTION
				"."
			::= { fkV2EponIMOnuPortIfStatsEntry 9 }

		
--  1.3.6.1.4.1.10428 9 1.102.15.3.1.1.1.10
		-- 1.3.6.1.4.1.10428 9 1.102.15.3.1.1.1.10
		fkV2EponIMOnuPortIfOutMulticast OBJECT-TYPE
			SYNTAX Counter64
			MAX-ACCESS read-only
			STATUS current
			DESCRIPTION
				"."
			::= { fkV2EponIMOnuPortIfStatsEntry 10 }

		
--  1.3.6.1.4.1.10428 9 1.102.15.3.1.1.1.11
		-- 1.3.6.1.4.1.10428 9 1.102.15.3.1.1.1.11
		fkV2EponIMOnuPortIfOutBroadcast OBJECT-TYPE
			SYNTAX Counter64
			MAX-ACCESS read-only
			STATUS current
			DESCRIPTION
				"."
			::= { fkV2EponIMOnuPortIfStatsEntry 11 }

		
--  1.3.6.1.4.1.10428 9 1.102.15.3.1.1.1.12
		-- 1.3.6.1.4.1.10428 9 1.102.15.3.1.1.1.12
		fkV2EponIMOnuPortIfOutDiscards OBJECT-TYPE
			SYNTAX Counter64
			MAX-ACCESS read-only
			STATUS current
			DESCRIPTION
				"."
			::= { fkV2EponIMOnuPortIfStatsEntry 12 }

		
--  1.3.6.1.4.1.10428 9 1.102.15.3.1.1.1.13
		-- 1.3.6.1.4.1.10428 9 1.102.15.3.1.1.1.13
		fkV2EponIMOnuPortIfOutErrors OBJECT-TYPE
			SYNTAX Counter64
			MAX-ACCESS read-only
			STATUS current
			DESCRIPTION
				"."
			::= { fkV2EponIMOnuPortIfStatsEntry 13 }

		
		-- 1.3.6.1.4.1.10428 9 1.102.15.3.1.2
		fkV2EponIMOnuPortEtherStatsTable OBJECT-TYPE
			SYNTAX SEQUENCE OF FkV2EponIMOnuPortEtherStatsEntry
			MAX-ACCESS not-accessible
			STATUS current
			DESCRIPTION
				"Description."
			::= { fkV2EponIMOnuPortStats 2 }

		
		-- 1.3.6.1.4.1.10428 9 1.102.15.3.1.2.1
		fkV2EponIMOnuPortEtherStatsEntry OBJECT-TYPE
			SYNTAX FkV2EponIMOnuPortEtherStatsEntry
			MAX-ACCESS not-accessible
			STATUS current
			DESCRIPTION
				"Description."
			INDEX { fkV2EponIMOnuPortIndex }
			::= { fkV2EponIMOnuPortEtherStatsTable 1 }

		
		FkV2EponIMOnuPortEtherStatsEntry ::=
			SEQUENCE { 
				fkV2EponIMOnuPortEtherAlignmentErrors
					Counter64,
				fkV2EponIMOnuPortEtherFcsErrors
					Counter64,
				fkV2EponIMOnuPortEtherSingleCollision
					Counter32,
				fkV2EponIMOnuPortEtherMultipleCollision
					Counter32,
				fkV2EponIMOnuPortEtherSqeTestErrors
					Counter32,
				fkV2EponIMOnuPortEtherDeferredTransmissions
					Counter32,
				fkV2EponIMOnuPortEtherLateCollisions
					Counter32,
				fkV2EponIMOnuPortEtherExcessiveCollisions
					Counter32,
				fkV2EponIMOnuPortEtherInternalMacTxErrors
					Counter64,
				fkV2EponIMOnuPortEtherCarrierSenseErrors
					Counter32,
				fkV2EponIMOnuPortEtherFrameTooLongs
					Counter64,
				fkV2EponIMOnuPortEtherInternalMacRxErrors
					Counter64,
				fkV2EponIMOnuPortEtherSymbolErrors
					Counter64,
				fkV2EponIMOnuPortEtherInUnknownOpcode
					Counter64,
				fkV2EponIMOnuPortEtherInPauseFrames
					Counter64,
				fkV2EponIMOnuPortEtherOutPauseFrames
					Counter64
			 }

--  1.3.6.1.4.1.10428 9 1.102.15.3.1.2.1.1
		-- 1.3.6.1.4.1.10428 9 1.102.15.3.1.2.1.1
		fkV2EponIMOnuPortEtherAlignmentErrors OBJECT-TYPE
			SYNTAX Counter64
			MAX-ACCESS read-only
			STATUS current
			DESCRIPTION
				"."
			::= { fkV2EponIMOnuPortEtherStatsEntry 1 }

		
--  1.3.6.1.4.1.10428 9 1.102.15.3.1.2.1.2
		-- 1.3.6.1.4.1.10428 9 1.102.15.3.1.2.1.2
		fkV2EponIMOnuPortEtherFcsErrors OBJECT-TYPE
			SYNTAX Counter64
			MAX-ACCESS read-only
			STATUS current
			DESCRIPTION
				"."
			::= { fkV2EponIMOnuPortEtherStatsEntry 2 }

		
--  1.3.6.1.4.1.10428 9 1.102.15.3.1.2.1.3
		-- 1.3.6.1.4.1.10428 9 1.102.15.3.1.2.1.3
		fkV2EponIMOnuPortEtherSingleCollision OBJECT-TYPE
			SYNTAX Counter32
			MAX-ACCESS read-only
			STATUS current
			DESCRIPTION
				"."
			::= { fkV2EponIMOnuPortEtherStatsEntry 3 }

		
--  1.3.6.1.4.1.10428 9 1.102.15.3.1.2.1.4
		-- 1.3.6.1.4.1.10428 9 1.102.15.3.1.2.1.4
		fkV2EponIMOnuPortEtherMultipleCollision OBJECT-TYPE
			SYNTAX Counter32
			MAX-ACCESS read-only
			STATUS current
			DESCRIPTION
				"."
			::= { fkV2EponIMOnuPortEtherStatsEntry 4 }

		
--  1.3.6.1.4.1.10428 9 1.102.15.3.1.2.1.5
		-- 1.3.6.1.4.1.10428 9 1.102.15.3.1.2.1.5
		fkV2EponIMOnuPortEtherSqeTestErrors OBJECT-TYPE
			SYNTAX Counter32
			MAX-ACCESS read-only
			STATUS current
			DESCRIPTION
				"."
			::= { fkV2EponIMOnuPortEtherStatsEntry 5 }

		
--  1.3.6.1.4.1.10428 9 1.102.15.3.1.2.1.6
		-- 1.3.6.1.4.1.10428 9 1.102.15.3.1.2.1.6
		fkV2EponIMOnuPortEtherDeferredTransmissions OBJECT-TYPE
			SYNTAX Counter32
			MAX-ACCESS read-only
			STATUS current
			DESCRIPTION
				"."
			::= { fkV2EponIMOnuPortEtherStatsEntry 6 }

		
--  1.3.6.1.4.1.10428 9 1.102.15.3.1.2.1.7
		-- 1.3.6.1.4.1.10428 9 1.102.15.3.1.2.1.7
		fkV2EponIMOnuPortEtherLateCollisions OBJECT-TYPE
			SYNTAX Counter32
			MAX-ACCESS read-only
			STATUS current
			DESCRIPTION
				"."
			::= { fkV2EponIMOnuPortEtherStatsEntry 7 }

		
--  1.3.6.1.4.1.10428 9 1.102.15.3.1.2.1.8
		-- 1.3.6.1.4.1.10428 9 1.102.15.3.1.2.1.8
		fkV2EponIMOnuPortEtherExcessiveCollisions OBJECT-TYPE
			SYNTAX Counter32
			MAX-ACCESS read-only
			STATUS current
			DESCRIPTION
				"."
			::= { fkV2EponIMOnuPortEtherStatsEntry 8 }

		
--  1.3.6.1.4.1.10428 9 1.102.15.3.1.2.1.9
		-- 1.3.6.1.4.1.10428 9 1.102.15.3.1.2.1.9
		fkV2EponIMOnuPortEtherInternalMacTxErrors OBJECT-TYPE
			SYNTAX Counter64
			MAX-ACCESS read-only
			STATUS current
			DESCRIPTION
				"."
			::= { fkV2EponIMOnuPortEtherStatsEntry 9 }

		
--  1.3.6.1.4.1.10428 9 1.102.15.3.1.2.1.10
		-- 1.3.6.1.4.1.10428 9 1.102.15.3.1.2.1.10
		fkV2EponIMOnuPortEtherCarrierSenseErrors OBJECT-TYPE
			SYNTAX Counter32
			MAX-ACCESS read-only
			STATUS current
			DESCRIPTION
				"."
			::= { fkV2EponIMOnuPortEtherStatsEntry 10 }

		
--  1.3.6.1.4.1.10428 9 1.102.15.3.1.2.1.11
		-- 1.3.6.1.4.1.10428 9 1.102.15.3.1.2.1.11
		fkV2EponIMOnuPortEtherFrameTooLongs OBJECT-TYPE
			SYNTAX Counter64
			MAX-ACCESS read-only
			STATUS current
			DESCRIPTION
				"."
			::= { fkV2EponIMOnuPortEtherStatsEntry 11 }

		
--  1.3.6.1.4.1.10428 9 1.102.15.3.1.2.1.12
		-- 1.3.6.1.4.1.10428 9 1.102.15.3.1.2.1.12
		fkV2EponIMOnuPortEtherInternalMacRxErrors OBJECT-TYPE
			SYNTAX Counter64
			MAX-ACCESS read-only
			STATUS current
			DESCRIPTION
				"."
			::= { fkV2EponIMOnuPortEtherStatsEntry 12 }

		
--  1.3.6.1.4.1.10428 9 1.102.15.3.1.2.1.13
		-- 1.3.6.1.4.1.10428 9 1.102.15.3.1.2.1.13
		fkV2EponIMOnuPortEtherSymbolErrors OBJECT-TYPE
			SYNTAX Counter64
			MAX-ACCESS read-only
			STATUS current
			DESCRIPTION
				"."
			::= { fkV2EponIMOnuPortEtherStatsEntry 13 }

		
--  1.3.6.1.4.1.10428 9 1.102.15.3.1.2.1.14
		-- 1.3.6.1.4.1.10428 9 1.102.15.3.1.2.1.14
		fkV2EponIMOnuPortEtherInUnknownOpcode OBJECT-TYPE
			SYNTAX Counter64
			MAX-ACCESS read-only
			STATUS current
			DESCRIPTION
				"."
			::= { fkV2EponIMOnuPortEtherStatsEntry 14 }

		
--  1.3.6.1.4.1.10428 9 1.102.15.3.1.2.1.15
		-- 1.3.6.1.4.1.10428 9 1.102.15.3.1.2.1.15
		fkV2EponIMOnuPortEtherInPauseFrames OBJECT-TYPE
			SYNTAX Counter64
			MAX-ACCESS read-only
			STATUS current
			DESCRIPTION
				"."
			::= { fkV2EponIMOnuPortEtherStatsEntry 15 }

		
--  1.3.6.1.4.1.10428 9 1.102.15.3.1.2.1.16
		-- 1.3.6.1.4.1.10428 9 1.102.15.3.1.2.1.16
		fkV2EponIMOnuPortEtherOutPauseFrames OBJECT-TYPE
			SYNTAX Counter64
			MAX-ACCESS read-only
			STATUS current
			DESCRIPTION
				"."
			::= { fkV2EponIMOnuPortEtherStatsEntry 16 }

		
		-- 1.3.6.1.4.1.10428 9 1.102.15.3.1.3
		fkV2EponIMOnuPortEponStatsTable OBJECT-TYPE
			SYNTAX SEQUENCE OF FkV2EponIMOnuPortEponStatsEntry
			MAX-ACCESS not-accessible
			STATUS current
			DESCRIPTION
				"Description."
			::= { fkV2EponIMOnuPortStats 3 }

		
		-- 1.3.6.1.4.1.10428 9 1.102.15.3.1.3.1
		fkV2EponIMOnuPortEponStatsEntry OBJECT-TYPE
			SYNTAX FkV2EponIMOnuPortEponStatsEntry
			MAX-ACCESS not-accessible
			STATUS current
			DESCRIPTION
				"Description."
			INDEX { fkV2EponIMOnuPortIndex }
			::= { fkV2EponIMOnuPortEponStatsTable 1 }

		
		FkV2EponIMOnuPortEponStatsEntry ::=
			SEQUENCE { 
				fkV2EponIMOnuPortEponMacCtrlFrameRx
					Counter32,
				fkV2EponIMOnuPortEponDiscWindowsSent
					Counter32,
				fkV2EponIMOnuPortEponDiscTimeout
					Counter32,
				fkV2EponIMOnuPortEponTxRegRequest
					Counter32,
				fkV2EponIMOnuPortEponRxReqRequest
					Counter32,
				fkV2EponIMOnuPortEponTxReqAck
					Counter32,
				fkV2EponIMOnuPortEponRxReqAck
					Counter32,
				fkV2EponIMOnuPortEponTxReport
					Counter32,
				fkV2EponIMOnuPortEponRxReport
					Counter32,
				fkV2EponIMOnuPortEponTxGate
					Counter32,
				fkV2EponIMOnuPortEponRxGate
					Counter32,
				fkV2EponIMOnuPortEponTxRegister
					Counter32,
				fkV2EponIMOnuPortEponRxRegister
					Counter32,
				fkV2EponIMOnuPortEponRxNotSupported
					Counter32,
				fkV2EponIMOnuPortEponSldErrors
					Counter32,
				fkV2EponIMOnuPortEponCrc8Errors
					Counter32,
				fkV2EponIMOnuPortEponBadLlid
					Counter32,
				fkV2EponIMOnuPortEponGoodLlid
					Counter32,
				fkV2EponIMOnuPortEponOnuPonCastLlid
					Counter32,
				fkV2EponIMOnuPortEponOltPonCastLlid
					Counter32,
				fkV2EponIMOnuPortEponBcastLlidNotOnuId
					Counter32,
				fkV2EponIMOnuPortEponOnuLlidNotBcast
					Counter32,
				fkV2EponIMOnuPortEponBcastLlidPlusOnuId
					Counter32,
				fkV2EponIMOnuPortEponNotBcastLlidNotOnuId
					Counter32,
				fkV2EponIMOnuPortEponPcsCodingViolation
					Counter32,
				fkV2EponIMOnuPortEponFecCorrectedBlocks
					Counter32,
				fkV2EponIMOnuPortEponFecUnCorrectedBlocks
					Counter32,
				fkV2EponIMOnuPortEponBufferHeadCodingViolation
					Counter32
			 }

--  1.3.6.1.4.1.10428 9 1.102.15.3.1.3.1.1
		-- 1.3.6.1.4.1.10428 9 1.102.15.3.1.3.1.1
		fkV2EponIMOnuPortEponMacCtrlFrameRx OBJECT-TYPE
			SYNTAX Counter32
			MAX-ACCESS read-only
			STATUS current
			DESCRIPTION
				"."
			::= { fkV2EponIMOnuPortEponStatsEntry 1 }

		
--  1.3.6.1.4.1.10428 9 1.102.15.3.1.3.1.2
		-- 1.3.6.1.4.1.10428 9 1.102.15.3.1.3.1.2
		fkV2EponIMOnuPortEponDiscWindowsSent OBJECT-TYPE
			SYNTAX Counter32
			MAX-ACCESS read-only
			STATUS current
			DESCRIPTION
				"."
			::= { fkV2EponIMOnuPortEponStatsEntry 2 }

		
--  1.3.6.1.4.1.10428 9 1.102.15.3.1.3.1.3
		-- 1.3.6.1.4.1.10428 9 1.102.15.3.1.3.1.3
		fkV2EponIMOnuPortEponDiscTimeout OBJECT-TYPE
			SYNTAX Counter32
			MAX-ACCESS read-only
			STATUS current
			DESCRIPTION
				"."
			::= { fkV2EponIMOnuPortEponStatsEntry 3 }

		
--  1.3.6.1.4.1.10428 9 1.102.15.3.1.3.1.4
		-- 1.3.6.1.4.1.10428 9 1.102.15.3.1.3.1.4
		fkV2EponIMOnuPortEponTxRegRequest OBJECT-TYPE
			SYNTAX Counter32
			MAX-ACCESS read-only
			STATUS current
			DESCRIPTION
				"."
			::= { fkV2EponIMOnuPortEponStatsEntry 4 }

		
--  1.3.6.1.4.1.10428 9 1.102.15.3.1.3.1.5
		-- 1.3.6.1.4.1.10428 9 1.102.15.3.1.3.1.5
		fkV2EponIMOnuPortEponRxReqRequest OBJECT-TYPE
			SYNTAX Counter32
			MAX-ACCESS read-only
			STATUS current
			DESCRIPTION
				"."
			::= { fkV2EponIMOnuPortEponStatsEntry 5 }

		
--  1.3.6.1.4.1.10428 9 1.102.15.3.1.3.1.6
		-- 1.3.6.1.4.1.10428 9 1.102.15.3.1.3.1.6
		fkV2EponIMOnuPortEponTxReqAck OBJECT-TYPE
			SYNTAX Counter32
			MAX-ACCESS read-only
			STATUS current
			DESCRIPTION
				"."
			::= { fkV2EponIMOnuPortEponStatsEntry 6 }

		
--  1.3.6.1.4.1.10428 9 1.102.15.3.1.3.1.7
		-- 1.3.6.1.4.1.10428 9 1.102.15.3.1.3.1.7
		fkV2EponIMOnuPortEponRxReqAck OBJECT-TYPE
			SYNTAX Counter32
			MAX-ACCESS read-only
			STATUS current
			DESCRIPTION
				"."
			::= { fkV2EponIMOnuPortEponStatsEntry 7 }

		
--  1.3.6.1.4.1.10428 9 1.102.15.3.1.3.1.8
		-- 1.3.6.1.4.1.10428 9 1.102.15.3.1.3.1.8
		fkV2EponIMOnuPortEponTxReport OBJECT-TYPE
			SYNTAX Counter32
			MAX-ACCESS read-only
			STATUS current
			DESCRIPTION
				"."
			::= { fkV2EponIMOnuPortEponStatsEntry 8 }

		
--  1.3.6.1.4.1.10428 9 1.102.15.3.1.3.1.9
		-- 1.3.6.1.4.1.10428 9 1.102.15.3.1.3.1.9
		fkV2EponIMOnuPortEponRxReport OBJECT-TYPE
			SYNTAX Counter32
			MAX-ACCESS read-only
			STATUS current
			DESCRIPTION
				"."
			::= { fkV2EponIMOnuPortEponStatsEntry 9 }

		
--  1.3.6.1.4.1.10428 9 1.102.15.3.1.3.1.10
		-- 1.3.6.1.4.1.10428 9 1.102.15.3.1.3.1.10
		fkV2EponIMOnuPortEponTxGate OBJECT-TYPE
			SYNTAX Counter32
			MAX-ACCESS read-only
			STATUS current
			DESCRIPTION
				"."
			::= { fkV2EponIMOnuPortEponStatsEntry 10 }

		
--  1.3.6.1.4.1.10428 9 1.102.15.3.1.3.1.11
		-- 1.3.6.1.4.1.10428 9 1.102.15.3.1.3.1.11
		fkV2EponIMOnuPortEponRxGate OBJECT-TYPE
			SYNTAX Counter32
			MAX-ACCESS read-only
			STATUS current
			DESCRIPTION
				"."
			::= { fkV2EponIMOnuPortEponStatsEntry 11 }

		
--  1.3.6.1.4.1.10428 9 1.102.15.3.1.3.1.12
		-- 1.3.6.1.4.1.10428 9 1.102.15.3.1.3.1.12
		fkV2EponIMOnuPortEponTxRegister OBJECT-TYPE
			SYNTAX Counter32
			MAX-ACCESS read-only
			STATUS current
			DESCRIPTION
				"."
			::= { fkV2EponIMOnuPortEponStatsEntry 12 }

		
--  1.3.6.1.4.1.10428 9 1.102.15.3.1.3.1.13
		-- 1.3.6.1.4.1.10428 9 1.102.15.3.1.3.1.13
		fkV2EponIMOnuPortEponRxRegister OBJECT-TYPE
			SYNTAX Counter32
			MAX-ACCESS read-only
			STATUS current
			DESCRIPTION
				"."
			::= { fkV2EponIMOnuPortEponStatsEntry 13 }

		
--  1.3.6.1.4.1.10428 9 1.102.15.3.1.3.1.14
		-- 1.3.6.1.4.1.10428 9 1.102.15.3.1.3.1.14
		fkV2EponIMOnuPortEponRxNotSupported OBJECT-TYPE
			SYNTAX Counter32
			MAX-ACCESS read-only
			STATUS current
			DESCRIPTION
				"."
			::= { fkV2EponIMOnuPortEponStatsEntry 14 }

		
--  1.3.6.1.4.1.10428 9 1.102.15.3.1.3.1.15
		-- 1.3.6.1.4.1.10428 9 1.102.15.3.1.3.1.15
		fkV2EponIMOnuPortEponSldErrors OBJECT-TYPE
			SYNTAX Counter32
			MAX-ACCESS read-only
			STATUS current
			DESCRIPTION
				"."
			::= { fkV2EponIMOnuPortEponStatsEntry 15 }

		
--  1.3.6.1.4.1.10428 9 1.102.15.3.1.3.1.16
		-- 1.3.6.1.4.1.10428 9 1.102.15.3.1.3.1.16
		fkV2EponIMOnuPortEponCrc8Errors OBJECT-TYPE
			SYNTAX Counter32
			MAX-ACCESS read-only
			STATUS current
			DESCRIPTION
				"."
			::= { fkV2EponIMOnuPortEponStatsEntry 16 }

		
--  1.3.6.1.4.1.10428 9 1.102.15.3.1.3.1.17
		-- 1.3.6.1.4.1.10428 9 1.102.15.3.1.3.1.17
		fkV2EponIMOnuPortEponBadLlid OBJECT-TYPE
			SYNTAX Counter32
			MAX-ACCESS read-only
			STATUS current
			DESCRIPTION
				"."
			::= { fkV2EponIMOnuPortEponStatsEntry 17 }

		
--  1.3.6.1.4.1.10428 9 1.102.15.3.1.3.1.18
		-- 1.3.6.1.4.1.10428 9 1.102.15.3.1.3.1.18
		fkV2EponIMOnuPortEponGoodLlid OBJECT-TYPE
			SYNTAX Counter32
			MAX-ACCESS read-only
			STATUS current
			DESCRIPTION
				"."
			::= { fkV2EponIMOnuPortEponStatsEntry 18 }

		
--  1.3.6.1.4.1.10428 9 1.102.15.3.1.3.1.19
		-- 1.3.6.1.4.1.10428 9 1.102.15.3.1.3.1.19
		fkV2EponIMOnuPortEponOnuPonCastLlid OBJECT-TYPE
			SYNTAX Counter32
			MAX-ACCESS read-only
			STATUS current
			DESCRIPTION
				"."
			::= { fkV2EponIMOnuPortEponStatsEntry 19 }

		
--  1.3.6.1.4.1.10428 9 1.102.15.3.1.3.1.20
		-- 1.3.6.1.4.1.10428 9 1.102.15.3.1.3.1.20
		fkV2EponIMOnuPortEponOltPonCastLlid OBJECT-TYPE
			SYNTAX Counter32
			MAX-ACCESS read-only
			STATUS current
			DESCRIPTION
				"."
			::= { fkV2EponIMOnuPortEponStatsEntry 20 }

		
--  1.3.6.1.4.1.10428 9 1.102.15.3.1.3.1.21
		-- 1.3.6.1.4.1.10428 9 1.102.15.3.1.3.1.21
		fkV2EponIMOnuPortEponBcastLlidNotOnuId OBJECT-TYPE
			SYNTAX Counter32
			MAX-ACCESS read-only
			STATUS current
			DESCRIPTION
				"."
			::= { fkV2EponIMOnuPortEponStatsEntry 21 }

		
--  1.3.6.1.4.1.10428 9 1.102.15.3.1.3.1.22
		-- 1.3.6.1.4.1.10428 9 1.102.15.3.1.3.1.22
		fkV2EponIMOnuPortEponOnuLlidNotBcast OBJECT-TYPE
			SYNTAX Counter32
			MAX-ACCESS read-only
			STATUS current
			DESCRIPTION
				"."
			::= { fkV2EponIMOnuPortEponStatsEntry 22 }

		
--  1.3.6.1.4.1.10428 9 1.102.15.3.1.3.1.23
		-- 1.3.6.1.4.1.10428 9 1.102.15.3.1.3.1.23
		fkV2EponIMOnuPortEponBcastLlidPlusOnuId OBJECT-TYPE
			SYNTAX Counter32
			MAX-ACCESS read-only
			STATUS current
			DESCRIPTION
				"."
			::= { fkV2EponIMOnuPortEponStatsEntry 23 }

		
--  1.3.6.1.4.1.10428 9 1.102.15.3.1.3.1.24
		-- 1.3.6.1.4.1.10428 9 1.102.15.3.1.3.1.24
		fkV2EponIMOnuPortEponNotBcastLlidNotOnuId OBJECT-TYPE
			SYNTAX Counter32
			MAX-ACCESS read-only
			STATUS current
			DESCRIPTION
				"."
			::= { fkV2EponIMOnuPortEponStatsEntry 24 }

		
--  1.3.6.1.4.1.10428 9 1.102.15.3.1.3.1.25
		-- 1.3.6.1.4.1.10428 9 1.102.15.3.1.3.1.25
		fkV2EponIMOnuPortEponPcsCodingViolation OBJECT-TYPE
			SYNTAX Counter32
			MAX-ACCESS read-only
			STATUS current
			DESCRIPTION
				"."
			::= { fkV2EponIMOnuPortEponStatsEntry 25 }

		
--  1.3.6.1.4.1.10428 9 1.102.15.3.1.3.1.26
		-- 1.3.6.1.4.1.10428 9 1.102.15.3.1.3.1.26
		fkV2EponIMOnuPortEponFecCorrectedBlocks OBJECT-TYPE
			SYNTAX Counter32
			MAX-ACCESS read-only
			STATUS current
			DESCRIPTION
				"."
			::= { fkV2EponIMOnuPortEponStatsEntry 26 }

		
--  1.3.6.1.4.1.10428 9 1.102.15.3.1.3.1.27
		-- 1.3.6.1.4.1.10428 9 1.102.15.3.1.3.1.27
		fkV2EponIMOnuPortEponFecUnCorrectedBlocks OBJECT-TYPE
			SYNTAX Counter32
			MAX-ACCESS read-only
			STATUS current
			DESCRIPTION
				"."
			::= { fkV2EponIMOnuPortEponStatsEntry 27 }

		
--  1.3.6.1.4.1.10428 9 1.102.15.3.1.3.1.28
		-- 1.3.6.1.4.1.10428 9 1.102.15.3.1.3.1.28
		fkV2EponIMOnuPortEponBufferHeadCodingViolation OBJECT-TYPE
			SYNTAX Counter32
			MAX-ACCESS read-only
			STATUS current
			DESCRIPTION
				"."
			::= { fkV2EponIMOnuPortEponStatsEntry 28 }

		
--  1.3.6.1.4.1.10428 9 1.102.15.3.1.4
		-- 1.3.6.1.4.1.10428 9 1.102.15.3.1.4
		fkV2EponIMOnuPortStatsControl OBJECT IDENTIFIER ::= { fkV2EponIMOnuPortStats 4 }

		
--  1.3.6.1.4.1.10428 9 1.102.15.3.1.4.1
		-- 1.3.6.1.4.1.10428 9 1.102.15.3.1.4.1
		fkV2EponIMOnuPortStatsControlRequest OBJECT-TYPE
			SYNTAX INTEGER { clearPortStats(1) }
			MAX-ACCESS read-write
			STATUS current
			DESCRIPTION
				"."
			::= { fkV2EponIMOnuPortStatsControl 1 }

		
--  1.3.6.1.4.1.10428 9 1.102.15.3.1.4.2
		-- 1.3.6.1.4.1.10428 9 1.102.15.3.1.4.2
		fkV2EponIMOnuPortStatsControlStatus OBJECT-TYPE
			SYNTAX FkControlStatusType
			MAX-ACCESS read-only
			STATUS current
			DESCRIPTION
				"."
			::= { fkV2EponIMOnuPortStatsControl 2 }

		
--  1.3.6.1.4.1.10428 9 1.102.15.3.1.4.3
		-- 1.3.6.1.4.1.10428 9 1.102.15.3.1.4.3
		fkV2EponIMOnuPortStatsControlTimer OBJECT-TYPE
			SYNTAX Gauge32
			MAX-ACCESS read-write
			STATUS current
			DESCRIPTION
				"."
			::= { fkV2EponIMOnuPortStatsControl 3 }

		
--  1.3.6.1.4.1.10428 9 1.102.15.3.1.4.4
		-- 1.3.6.1.4.1.10428 9 1.102.15.3.1.4.4
		fkV2EponIMOnuPortStatsControlTimeStamp OBJECT-TYPE
			SYNTAX TimeTicks
			MAX-ACCESS read-only
			STATUS current
			DESCRIPTION
				"."
			::= { fkV2EponIMOnuPortStatsControl 4 }

		
--  1.3.6.1.4.1.10428 9 1.102.15.3.1.4.5
		-- 1.3.6.1.4.1.10428 9 1.102.15.3.1.4.5
		fkV2EponIMOnuPortStatsControlReqResult OBJECT-TYPE
			SYNTAX FkControlRequestResultType
			MAX-ACCESS read-only
			STATUS current
			DESCRIPTION
				"."
			::= { fkV2EponIMOnuPortStatsControl 5 }

		
--  1.3.6.1.4.1.10428 9 1.102.15.3.1.4.6
		-- 1.3.6.1.4.1.10428 9 1.102.15.3.1.4.6
		fkV2EponIMOnuPortStatsControlPortIndex OBJECT-TYPE
			SYNTAX Integer32
			MAX-ACCESS read-write
			STATUS current
			DESCRIPTION
				"Description."
			::= { fkV2EponIMOnuPortStatsControl 6 }

		
--  1.3.6.1.4.1.10428 9 1.102.15.3.1.5
		-- 1.3.6.1.4.1.10428 9 1.102.15.3.1.5
		fkV2EponIMOnuPortStatsNotification OBJECT IDENTIFIER ::= { fkV2EponIMOnuPortStats 5 }

		
--  1.3.6.1.4.1.10428 9 1.102.15.3.1.5.1
		-- 1.3.6.1.4.1.10428 9 1.102.15.3.1.5.1
		fkV2EponIMOnuPortStatsCleared NOTIFICATION-TYPE
			OBJECTS { fkV2EponIMOnuPortStatsControlRequest, fkV2EponIMOnuPortStatsControlTimeStamp, fkV2EponIMOnuPortStatsControlReqResult, fkV2EponIMOnuPortStatsControlPortIndex }
			STATUS current
			DESCRIPTION 
				"Description."
			::= { fkV2EponIMOnuPortStatsNotification 1 }

		
--  1.3.6.1.4.1.10428 9 1.102.15.3.2
		-- 1.3.6.1.4.1.10428 9 1.102.15.3.2
		fkV2EponIMOnuLlidStats OBJECT IDENTIFIER ::= { fkV2EponIMOnuStats 2 }

		
--  1.3.6.1.4.1.10428 9 1.102.15.3.2.1
		-- 1.3.6.1.4.1.10428 9 1.102.15.3.2.1
		fkV2EponIMOnuLlidIfStats OBJECT IDENTIFIER ::= { fkV2EponIMOnuLlidStats 1 }

		
--  1.3.6.1.4.1.10428 9 1.102.15.3.2.1.1
		-- 1.3.6.1.4.1.10428 9 1.102.15.3.2.1.1
		fkV2EponIMOnuLlidIfInOctets OBJECT-TYPE
			SYNTAX Counter64
			MAX-ACCESS read-only
			STATUS current
			DESCRIPTION
				"."
			::= { fkV2EponIMOnuLlidIfStats 1 }

		
--  1.3.6.1.4.1.10428 9 1.102.15.3.2.1.2
		-- 1.3.6.1.4.1.10428 9 1.102.15.3.2.1.2
		fkV2EponIMOnuLlidIfInUnicast OBJECT-TYPE
			SYNTAX Counter64
			MAX-ACCESS read-only
			STATUS current
			DESCRIPTION
				"."
			::= { fkV2EponIMOnuLlidIfStats 2 }

		
--  1.3.6.1.4.1.10428 9 1.102.15.3.2.1.3
		-- 1.3.6.1.4.1.10428 9 1.102.15.3.2.1.3
		fkV2EponIMOnuLlidIfInMulticast OBJECT-TYPE
			SYNTAX Counter64
			MAX-ACCESS read-only
			STATUS current
			DESCRIPTION
				"."
			::= { fkV2EponIMOnuLlidIfStats 3 }

		
--  1.3.6.1.4.1.10428 9 1.102.15.3.2.1.4
		-- 1.3.6.1.4.1.10428 9 1.102.15.3.2.1.4
		fkV2EponIMOnuLlidIfInBroadcast OBJECT-TYPE
			SYNTAX Counter64
			MAX-ACCESS read-only
			STATUS current
			DESCRIPTION
				"."
			::= { fkV2EponIMOnuLlidIfStats 4 }

		
--  1.3.6.1.4.1.10428 9 1.102.15.3.2.1.5
		-- 1.3.6.1.4.1.10428 9 1.102.15.3.2.1.5
		fkV2EponIMOnuLlidIfInDiscards OBJECT-TYPE
			SYNTAX Counter64
			MAX-ACCESS read-only
			STATUS current
			DESCRIPTION
				"."
			::= { fkV2EponIMOnuLlidIfStats 5 }

		
--  1.3.6.1.4.1.10428 9 1.102.15.3.2.1.6
		-- 1.3.6.1.4.1.10428 9 1.102.15.3.2.1.6
		fkV2EponIMOnuLlidIfInErrors OBJECT-TYPE
			SYNTAX Counter64
			MAX-ACCESS read-only
			STATUS current
			DESCRIPTION
				"."
			::= { fkV2EponIMOnuLlidIfStats 6 }

		
--  1.3.6.1.4.1.10428 9 1.102.15.3.2.1.7
		-- 1.3.6.1.4.1.10428 9 1.102.15.3.2.1.7
		fkV2EponIMOnuLlidIfInUnknownProtos OBJECT-TYPE
			SYNTAX Counter64
			MAX-ACCESS read-only
			STATUS current
			DESCRIPTION
				"."
			::= { fkV2EponIMOnuLlidIfStats 7 }

		
--  1.3.6.1.4.1.10428 9 1.102.15.3.2.1.8
		-- 1.3.6.1.4.1.10428 9 1.102.15.3.2.1.8
		fkV2EponIMOnuLlidIfOutOctets OBJECT-TYPE
			SYNTAX Counter64
			MAX-ACCESS read-only
			STATUS current
			DESCRIPTION
				"."
			::= { fkV2EponIMOnuLlidIfStats 8 }

		
--  1.3.6.1.4.1.10428 9 1.102.15.3.2.1.9
		-- 1.3.6.1.4.1.10428 9 1.102.15.3.2.1.9
		fkV2EponIMOnuLlidIfOutUnicast OBJECT-TYPE
			SYNTAX Counter64
			MAX-ACCESS read-only
			STATUS current
			DESCRIPTION
				"."
			::= { fkV2EponIMOnuLlidIfStats 9 }

		
--  1.3.6.1.4.1.10428 9 1.102.15.3.2.1.10
		-- 1.3.6.1.4.1.10428 9 1.102.15.3.2.1.10
		fkV2EponIMOnuLlidIfOutMulticast OBJECT-TYPE
			SYNTAX Counter64
			MAX-ACCESS read-only
			STATUS current
			DESCRIPTION
				"."
			::= { fkV2EponIMOnuLlidIfStats 10 }

		
--  1.3.6.1.4.1.10428 9 1.102.15.3.2.1.11
		-- 1.3.6.1.4.1.10428 9 1.102.15.3.2.1.11
		fkV2EponIMOnuLlidIfOutBroadcast OBJECT-TYPE
			SYNTAX Counter64
			MAX-ACCESS read-only
			STATUS current
			DESCRIPTION
				"."
			::= { fkV2EponIMOnuLlidIfStats 11 }

		
--  1.3.6.1.4.1.10428 9 1.102.15.3.2.1.12
		-- 1.3.6.1.4.1.10428 9 1.102.15.3.2.1.12
		fkV2EponIMOnuLlidIfOutDiscards OBJECT-TYPE
			SYNTAX Counter64
			MAX-ACCESS read-only
			STATUS current
			DESCRIPTION
				"."
			::= { fkV2EponIMOnuLlidIfStats 12 }

		
--  1.3.6.1.4.1.10428 9 1.102.15.3.2.1.13
		-- 1.3.6.1.4.1.10428 9 1.102.15.3.2.1.13
		fkV2EponIMOnuLlidIfOutErrors OBJECT-TYPE
			SYNTAX Counter64
			MAX-ACCESS read-only
			STATUS current
			DESCRIPTION
				"."
			::= { fkV2EponIMOnuLlidIfStats 13 }

		
--  1.3.6.1.4.1.10428 9 1.102.15.3.2.2
		-- 1.3.6.1.4.1.10428 9 1.102.15.3.2.2
		fkV2EponIMOnuLlidEponStats OBJECT IDENTIFIER ::= { fkV2EponIMOnuLlidStats 2 }

		
--  1.3.6.1.4.1.10428 9 1.102.15.3.2.2.1
		-- 1.3.6.1.4.1.10428 9 1.102.15.3.2.2.1
		fkV2EponIMOnuLlidEponMacCtrlFrameRx OBJECT-TYPE
			SYNTAX Counter32
			MAX-ACCESS read-only
			STATUS current
			DESCRIPTION
				"."
			::= { fkV2EponIMOnuLlidEponStats 1 }

		
--  1.3.6.1.4.1.10428 9 1.102.15.3.2.2.2
		-- 1.3.6.1.4.1.10428 9 1.102.15.3.2.2.2
		fkV2EponIMOnuLlidEponDiscWindowsSent OBJECT-TYPE
			SYNTAX Counter32
			MAX-ACCESS read-only
			STATUS current
			DESCRIPTION
				"."
			::= { fkV2EponIMOnuLlidEponStats 2 }

		
--  1.3.6.1.4.1.10428 9 1.102.15.3.2.2.3
		-- 1.3.6.1.4.1.10428 9 1.102.15.3.2.2.3
		fkV2EponIMOnuLlidEponDiscTimeout OBJECT-TYPE
			SYNTAX Counter32
			MAX-ACCESS read-only
			STATUS current
			DESCRIPTION
				"."
			::= { fkV2EponIMOnuLlidEponStats 3 }

		
--  1.3.6.1.4.1.10428 9 1.102.15.3.2.2.4
		-- 1.3.6.1.4.1.10428 9 1.102.15.3.2.2.4
		fkV2EponIMOnuLlidEponTxRegRequest OBJECT-TYPE
			SYNTAX Counter32
			MAX-ACCESS read-only
			STATUS current
			DESCRIPTION
				"."
			::= { fkV2EponIMOnuLlidEponStats 4 }

		
--  1.3.6.1.4.1.10428 9 1.102.15.3.2.2.5
		-- 1.3.6.1.4.1.10428 9 1.102.15.3.2.2.5
		fkV2EponIMOnuLlidEponRxReqRequest OBJECT-TYPE
			SYNTAX Counter32
			MAX-ACCESS read-only
			STATUS current
			DESCRIPTION
				"."
			::= { fkV2EponIMOnuLlidEponStats 5 }

		
--  1.3.6.1.4.1.10428 9 1.102.15.3.2.2.6
		-- 1.3.6.1.4.1.10428 9 1.102.15.3.2.2.6
		fkV2EponIMOnuLlidEponTxReqAck OBJECT-TYPE
			SYNTAX Counter32
			MAX-ACCESS read-only
			STATUS current
			DESCRIPTION
				"."
			::= { fkV2EponIMOnuLlidEponStats 6 }

		
--  1.3.6.1.4.1.10428 9 1.102.15.3.2.2.7
		-- 1.3.6.1.4.1.10428 9 1.102.15.3.2.2.7
		fkV2EponIMOnuLlidEponRxReqAck OBJECT-TYPE
			SYNTAX Counter32
			MAX-ACCESS read-only
			STATUS current
			DESCRIPTION
				"."
			::= { fkV2EponIMOnuLlidEponStats 7 }

		
--  1.3.6.1.4.1.10428 9 1.102.15.3.2.2.8
		-- 1.3.6.1.4.1.10428 9 1.102.15.3.2.2.8
		fkV2EponIMOnuLlidEponTxReport OBJECT-TYPE
			SYNTAX Counter32
			MAX-ACCESS read-only
			STATUS current
			DESCRIPTION
				"."
			::= { fkV2EponIMOnuLlidEponStats 8 }

		
--  1.3.6.1.4.1.10428 9 1.102.15.3.2.2.9
		-- 1.3.6.1.4.1.10428 9 1.102.15.3.2.2.9
		fkV2EponIMOnuLlidEponRxReport OBJECT-TYPE
			SYNTAX Counter32
			MAX-ACCESS read-only
			STATUS current
			DESCRIPTION
				"."
			::= { fkV2EponIMOnuLlidEponStats 9 }

		
--  1.3.6.1.4.1.10428 9 1.102.15.3.2.2.10
		-- 1.3.6.1.4.1.10428 9 1.102.15.3.2.2.10
		fkV2EponIMOnuLlidEponTxGate OBJECT-TYPE
			SYNTAX Counter32
			MAX-ACCESS read-only
			STATUS current
			DESCRIPTION
				"."
			::= { fkV2EponIMOnuLlidEponStats 10 }

		
--  1.3.6.1.4.1.10428 9 1.102.15.3.2.2.11
		-- 1.3.6.1.4.1.10428 9 1.102.15.3.2.2.11
		fkV2EponIMOnuLlidEponRxGate OBJECT-TYPE
			SYNTAX Counter32
			MAX-ACCESS read-only
			STATUS current
			DESCRIPTION
				"."
			::= { fkV2EponIMOnuLlidEponStats 11 }

		
--  1.3.6.1.4.1.10428 9 1.102.15.3.2.2.12
		-- 1.3.6.1.4.1.10428 9 1.102.15.3.2.2.12
		fkV2EponIMOnuLlidEponTxRegister OBJECT-TYPE
			SYNTAX Counter32
			MAX-ACCESS read-only
			STATUS current
			DESCRIPTION
				"."
			::= { fkV2EponIMOnuLlidEponStats 12 }

		
--  1.3.6.1.4.1.10428 9 1.102.15.3.2.2.13
		-- 1.3.6.1.4.1.10428 9 1.102.15.3.2.2.13
		fkV2EponIMOnuLlidEponRxRegister OBJECT-TYPE
			SYNTAX Counter32
			MAX-ACCESS read-only
			STATUS current
			DESCRIPTION
				"."
			::= { fkV2EponIMOnuLlidEponStats 13 }

		
--  1.3.6.1.4.1.10428 9 1.102.15.3.2.2.14
		-- 1.3.6.1.4.1.10428 9 1.102.15.3.2.2.14
		fkV2EponIMOnuLlidEponRxNotSupported OBJECT-TYPE
			SYNTAX Counter32
			MAX-ACCESS read-only
			STATUS current
			DESCRIPTION
				"."
			::= { fkV2EponIMOnuLlidEponStats 14 }

		
--  1.3.6.1.4.1.10428 9 1.102.15.3.2.2.15
		-- 1.3.6.1.4.1.10428 9 1.102.15.3.2.2.15
		fkV2EponIMOnuLlidEponSldErrors OBJECT-TYPE
			SYNTAX Counter32
			MAX-ACCESS read-only
			STATUS current
			DESCRIPTION
				"."
			::= { fkV2EponIMOnuLlidEponStats 15 }

		
--  1.3.6.1.4.1.10428 9 1.102.15.3.2.2.16
		-- 1.3.6.1.4.1.10428 9 1.102.15.3.2.2.16
		fkV2EponIMOnuLlidEponCrc8Errors OBJECT-TYPE
			SYNTAX Counter32
			MAX-ACCESS read-only
			STATUS current
			DESCRIPTION
				"."
			::= { fkV2EponIMOnuLlidEponStats 16 }

		
--  1.3.6.1.4.1.10428 9 1.102.15.3.2.2.17
		-- 1.3.6.1.4.1.10428 9 1.102.15.3.2.2.17
		fkV2EponIMOnuLlidEponBadLlid OBJECT-TYPE
			SYNTAX Counter32
			MAX-ACCESS read-only
			STATUS current
			DESCRIPTION
				"."
			::= { fkV2EponIMOnuLlidEponStats 17 }

		
--  1.3.6.1.4.1.10428 9 1.102.15.3.2.2.18
		-- 1.3.6.1.4.1.10428 9 1.102.15.3.2.2.18
		fkV2EponIMOnuLlidEponGoodLlid OBJECT-TYPE
			SYNTAX Counter32
			MAX-ACCESS read-only
			STATUS current
			DESCRIPTION
				"."
			::= { fkV2EponIMOnuLlidEponStats 18 }

		
--  1.3.6.1.4.1.10428 9 1.102.15.3.2.2.19
		-- 1.3.6.1.4.1.10428 9 1.102.15.3.2.2.19
		fkV2EponIMOnuLlidEponOnuPonCastLlid OBJECT-TYPE
			SYNTAX Counter32
			MAX-ACCESS read-only
			STATUS current
			DESCRIPTION
				"."
			::= { fkV2EponIMOnuLlidEponStats 19 }

		
--  1.3.6.1.4.1.10428 9 1.102.15.3.2.2.20
		-- 1.3.6.1.4.1.10428 9 1.102.15.3.2.2.20
		fkV2EponIMOnuLlidEponOltPonCastLlid OBJECT-TYPE
			SYNTAX Counter32
			MAX-ACCESS read-only
			STATUS current
			DESCRIPTION
				"."
			::= { fkV2EponIMOnuLlidEponStats 20 }

		
--  1.3.6.1.4.1.10428 9 1.102.15.3.2.2.21
		-- 1.3.6.1.4.1.10428 9 1.102.15.3.2.2.21
		fkV2EponIMOnuLlidEponBcastLlidNotOnuId OBJECT-TYPE
			SYNTAX Counter32
			MAX-ACCESS read-only
			STATUS current
			DESCRIPTION
				"."
			::= { fkV2EponIMOnuLlidEponStats 21 }

		
--  1.3.6.1.4.1.10428 9 1.102.15.3.2.2.22
		-- 1.3.6.1.4.1.10428 9 1.102.15.3.2.2.22
		fkV2EponIMOnuLlidEponOnuLlidNotBcast OBJECT-TYPE
			SYNTAX Counter32
			MAX-ACCESS read-only
			STATUS current
			DESCRIPTION
				"."
			::= { fkV2EponIMOnuLlidEponStats 22 }

		
--  1.3.6.1.4.1.10428 9 1.102.15.3.2.2.23
		-- 1.3.6.1.4.1.10428 9 1.102.15.3.2.2.23
		fkV2EponIMOnuLlidEponBcastLlidPlusOnuId OBJECT-TYPE
			SYNTAX Counter32
			MAX-ACCESS read-only
			STATUS current
			DESCRIPTION
				"."
			::= { fkV2EponIMOnuLlidEponStats 23 }

		
--  1.3.6.1.4.1.10428 9 1.102.15.3.2.2.24
		-- 1.3.6.1.4.1.10428 9 1.102.15.3.2.2.24
		fkV2EponIMOnuLlidEponNotBcastLlidNotOnuId OBJECT-TYPE
			SYNTAX Counter32
			MAX-ACCESS read-only
			STATUS current
			DESCRIPTION
				"."
			::= { fkV2EponIMOnuLlidEponStats 24 }

		
--  1.3.6.1.4.1.10428 9 1.102.15.3.2.2.25
		-- 1.3.6.1.4.1.10428 9 1.102.15.3.2.2.25
		fkV2EponIMOnuLlidEponPcsCodingViolation OBJECT-TYPE
			SYNTAX Counter32
			MAX-ACCESS read-only
			STATUS current
			DESCRIPTION
				"."
			::= { fkV2EponIMOnuLlidEponStats 25 }

		
--  1.3.6.1.4.1.10428 9 1.102.15.3.2.2.26
		-- 1.3.6.1.4.1.10428 9 1.102.15.3.2.2.26
		fkV2EponIMOnuLlidEponFecCorrectedBlocks OBJECT-TYPE
			SYNTAX Counter32
			MAX-ACCESS read-only
			STATUS current
			DESCRIPTION
				"."
			::= { fkV2EponIMOnuLlidEponStats 26 }

		
--  1.3.6.1.4.1.10428 9 1.102.15.3.2.2.27
		-- 1.3.6.1.4.1.10428 9 1.102.15.3.2.2.27
		fkV2EponIMOnuLlidEponFecUnCorrectedBlocks OBJECT-TYPE
			SYNTAX Counter32
			MAX-ACCESS read-only
			STATUS current
			DESCRIPTION
				"."
			::= { fkV2EponIMOnuLlidEponStats 27 }

		
--  1.3.6.1.4.1.10428 9 1.102.15.3.2.2.28
		-- 1.3.6.1.4.1.10428 9 1.102.15.3.2.2.28
		fkV2EponIMOnuLlidEponBufferHeadCodingViolation OBJECT-TYPE
			SYNTAX Counter32
			MAX-ACCESS read-only
			STATUS current
			DESCRIPTION
				"."
			::= { fkV2EponIMOnuLlidEponStats 28 }

		
--  1.3.6.1.4.1.10428 9 1.102.15.3.2.3
		-- 1.3.6.1.4.1.10428 9 1.102.15.3.2.3
		fkV2EponIMOnuLlidStatsControl OBJECT IDENTIFIER ::= { fkV2EponIMOnuLlidStats 3 }

		
--  1.3.6.1.4.1.10428 9 1.102.15.3.2.3.1
		-- 1.3.6.1.4.1.10428 9 1.102.15.3.2.3.1
		fkV2EponIMOnuLlidStatsControlRequest OBJECT-TYPE
			SYNTAX INTEGER { clearPortStats(1) }
			MAX-ACCESS read-write
			STATUS current
			DESCRIPTION
				"."
			::= { fkV2EponIMOnuLlidStatsControl 1 }

		
--  1.3.6.1.4.1.10428 9 1.102.15.3.2.3.2
		-- 1.3.6.1.4.1.10428 9 1.102.15.3.2.3.2
		fkV2EponIMOnuLlidStatsControlStatus OBJECT-TYPE
			SYNTAX FkControlStatusType
			MAX-ACCESS read-only
			STATUS current
			DESCRIPTION
				"."
			::= { fkV2EponIMOnuLlidStatsControl 2 }

		
--  1.3.6.1.4.1.10428 9 1.102.15.3.2.3.3
		-- 1.3.6.1.4.1.10428 9 1.102.15.3.2.3.3
		fkV2EponIMOnuLlidStatsControlTimer OBJECT-TYPE
			SYNTAX Gauge32
			MAX-ACCESS read-write
			STATUS current
			DESCRIPTION
				"."
			::= { fkV2EponIMOnuLlidStatsControl 3 }

		
--  1.3.6.1.4.1.10428 9 1.102.15.3.2.3.4
		-- 1.3.6.1.4.1.10428 9 1.102.15.3.2.3.4
		fkV2EponIMOnuLlidStatsControlTimeStamp OBJECT-TYPE
			SYNTAX TimeTicks
			MAX-ACCESS read-only
			STATUS current
			DESCRIPTION
				"."
			::= { fkV2EponIMOnuLlidStatsControl 4 }

		
--  1.3.6.1.4.1.10428 9 1.102.15.3.2.3.5
		-- 1.3.6.1.4.1.10428 9 1.102.15.3.2.3.5
		fkV2EponIMOnuLlidStatsControlReqResult OBJECT-TYPE
			SYNTAX FkControlRequestResultType
			MAX-ACCESS read-only
			STATUS current
			DESCRIPTION
				"."
			::= { fkV2EponIMOnuLlidStatsControl 5 }

		
--  1.3.6.1.4.1.10428 9 1.102.15.3.2.4
		-- 1.3.6.1.4.1.10428 9 1.102.15.3.2.4
		fkV2EponIMOnuLlidStatsNotification OBJECT IDENTIFIER ::= { fkV2EponIMOnuLlidStats 4 }

		
--  1.3.6.1.4.1.10428 9 1.102.15.3.2.4.1
		-- 1.3.6.1.4.1.10428 9 1.102.15.3.2.4.1
		fkV2EponIMOnuLlidStatsCleared NOTIFICATION-TYPE
			OBJECTS { fkV2EponIMOnuLlidStatsControlRequest, fkV2EponIMOnuLlidStatsControlTimeStamp, fkV2EponIMOnuLlidStatsControlReqResult }
			STATUS current
			DESCRIPTION 
				"Description."
			::= { fkV2EponIMOnuLlidStatsNotification 1 }

		
		-- 1.3.6.1.4.1.10428 9 1.102.15.4
		fkV2EponIMAlarm OBJECT IDENTIFIER ::= { fkV2EponIM 4 }

		
		-- 1.3.6.1.4.1.10428 9 1.102.15.4.1
		fkV2EponIMAlarmTable OBJECT-TYPE
			SYNTAX SEQUENCE OF FkV2EponIMAlarmEntry
			MAX-ACCESS not-accessible
			STATUS current
			DESCRIPTION
				"Description."
			::= { fkV2EponIMAlarm 1 }

		
		-- 1.3.6.1.4.1.10428 9 1.102.15.4.1.1
		fkV2EponIMAlarmEntry OBJECT-TYPE
			SYNTAX FkV2EponIMAlarmEntry
			MAX-ACCESS not-accessible
			STATUS current
			DESCRIPTION
				"Description."
			INDEX { fkV2EponIMAlarmOnuPortIndex, fkV2EponIMAlarmOnuAlarmIndex }
			::= { fkV2EponIMAlarmTable 1 }

		
		FkV2EponIMAlarmEntry ::=
			SEQUENCE { 
				fkV2EponIMAlarmOnuPortIndex
					INTEGER,
				fkV2EponIMAlarmOnuAlarmIndex
					INTEGER,
				fkV2EponIMAlarmOnuAlarmStatus
					EponOnuState,
				fkV2EponIMAlarmOnuWindow
					Integer32,
				fkV2EponIMAlarmOnuThreshold
					Integer32
			 }

		-- 1.3.6.1.4.1.10428 9 1.102.15.4.1.1.1
		fkV2EponIMAlarmOnuPortIndex OBJECT-TYPE
			SYNTAX INTEGER
				{
				pon(1),
				uni(2),
				llid(3)
				}
			MAX-ACCESS read-only
			STATUS current
			DESCRIPTION
				"ONU port, which is valid only for port specific alarms."
			::= { fkV2EponIMAlarmEntry 1 }

		
		-- 1.3.6.1.4.1.10428 9 1.102.15.4.1.1.2
		fkV2EponIMAlarmOnuAlarmIndex OBJECT-TYPE
			SYNTAX INTEGER
				{
				errFramePeriod(1),
				errFrame(2),
				errFrameSecond(3)
				}
			MAX-ACCESS read-only
			STATUS current
			DESCRIPTION
				"Alarm type.
				err_frame_period - errored frame period alarm is raised when a threshold number of errored frame occur in the specified window time period.
				err_frame - errored frame alarm is raised when a threshold number of errored frames occur among the specified number of frames.
				err_frame_second - errored frame seconds summary alarm is raised when a threshold number of errored frames occur in the specified window time period.
				                   this alarm type is a summary of the errored frame period alarm.
				"
			::= { fkV2EponIMAlarmEntry 2 }

		
		-- 1.3.6.1.4.1.10428 9 1.102.15.4.1.1.3
		fkV2EponIMAlarmOnuAlarmStatus OBJECT-TYPE
			SYNTAX EponOnuState
			MAX-ACCESS read-only
			STATUS current
			DESCRIPTION
				"whether to enable alarm or not."
			::= { fkV2EponIMAlarmEntry 3 }

		
		-- 1.3.6.1.4.1.10428 9 1.102.15.4.1.1.4
		fkV2EponIMAlarmOnuWindow OBJECT-TYPE
			SYNTAX Integer32
			MAX-ACCESS read-only
			STATUS current
			DESCRIPTION
				"the window during which the alarm threshold is measured."
			::= { fkV2EponIMAlarmEntry 4 }

		
		-- 1.3.6.1.4.1.10428 9 1.102.15.4.1.1.5
		fkV2EponIMAlarmOnuThreshold OBJECT-TYPE
			SYNTAX Integer32
			MAX-ACCESS read-only
			STATUS current
			DESCRIPTION
				"the threshold valud leading to the alarm.
				"
			::= { fkV2EponIMAlarmEntry 5 }

		
		-- 1.3.6.1.4.1.10428 9 1.102.15.4.2
		fkV2EponIMAlarmControl OBJECT IDENTIFIER ::= { fkV2EponIMAlarm 2 }

		
		-- 1.3.6.1.4.1.10428 9 1.102.15.4.2.1
		fkV2EponIMAlarmControlRequest OBJECT-TYPE
			SYNTAX INTEGER { setEponIMAlarmProfileChanged(1) }
			MAX-ACCESS read-write
			STATUS current
			DESCRIPTION
				"Description."
			::= { fkV2EponIMAlarmControl 1 }

		
		-- 1.3.6.1.4.1.10428 9 1.102.15.4.2.2
		fkV2EponIMAlarmControlStatus OBJECT-TYPE
			SYNTAX FkControlStatusType
			MAX-ACCESS read-only
			STATUS current
			DESCRIPTION
				"Description."
			::= { fkV2EponIMAlarmControl 2 }

		
		-- 1.3.6.1.4.1.10428 9 1.102.15.4.2.3
		fkV2EponIMAlarmControlTimer OBJECT-TYPE
			SYNTAX Gauge32
			MAX-ACCESS read-write
			STATUS current
			DESCRIPTION
				"Description."
			::= { fkV2EponIMAlarmControl 3 }

		
		-- 1.3.6.1.4.1.10428 9 1.102.15.4.2.4
		fkV2EponIMAlarmControlTimeStamp OBJECT-TYPE
			SYNTAX TimeTicks
			MAX-ACCESS read-only
			STATUS current
			DESCRIPTION
				"Description."
			::= { fkV2EponIMAlarmControl 4 }

		
		-- 1.3.6.1.4.1.10428 9 1.102.15.4.2.5
		fkV2EponIMAlarmControlReqResult OBJECT-TYPE
			SYNTAX FkControlRequestResultType
			MAX-ACCESS read-only
			STATUS current
			DESCRIPTION
				"Description."
			::= { fkV2EponIMAlarmControl 5 }

		
		-- 1.3.6.1.4.1.10428 9 1.102.15.4.2.6
		fkV2EponIMAlarmControlOnuPortIndex OBJECT-TYPE
			SYNTAX INTEGER
				{
				pon(1),
				uni(2),
				llid(3)
				}
			MAX-ACCESS read-write
			STATUS current
			DESCRIPTION
				"ONU port, which is valid only for port specific alarms."
			::= { fkV2EponIMAlarmControl 6 }

		
		-- 1.3.6.1.4.1.10428 9 1.102.15.4.2.7
		fkV2EponIMAlarmControlOnuAlarmIndex OBJECT-TYPE
			SYNTAX INTEGER
				{
				errFramePeriod(1),
				errFrame(2),
				errFrameSecond(3)
				}
			MAX-ACCESS read-write
			STATUS current
			DESCRIPTION
				"Alarm type.
				err_frame_period - errored frame period alarm is raised when a threshold number of errored frame occur in the specified window time period.
				err_frame - errored frame alarm is raised when a threshold number of errored frames occur among the specified number of frames.
				err_frame_second - errored frame seconds summary alarm is raised when a threshold number of errored frames occur in the specified window time period.
				                   this alarm type is a summary of the errored frame period alarm.
				"
			::= { fkV2EponIMAlarmControl 7 }

		
		-- 1.3.6.1.4.1.10428 9 1.102.15.4.2.8
		fkV2EponIMAlarmControlOnuAlarmStatus OBJECT-TYPE
			SYNTAX EponOnuState
			MAX-ACCESS read-write
			STATUS current
			DESCRIPTION
				"whether to enable alarm or not."
			::= { fkV2EponIMAlarmControl 8 }

		
		-- 1.3.6.1.4.1.10428 9 1.102.15.4.2.9
		fkV2EponIMAlarmControlWindow OBJECT-TYPE
			SYNTAX Integer32
			MAX-ACCESS read-write
			STATUS current
			DESCRIPTION
				"the window during which the alarm threshold is measured."
			::= { fkV2EponIMAlarmControl 9 }

		
		-- 1.3.6.1.4.1.10428 9 1.102.15.4.2.10
		fkV2EponIMAlarmControlThreshold OBJECT-TYPE
			SYNTAX Integer32
			MAX-ACCESS read-write
			STATUS current
			DESCRIPTION
				"the threshold valud leading to the alarm."
			::= { fkV2EponIMAlarmControl 10 }

		
		-- 1.3.6.1.4.1.10428 9 1.102.15.4.4
		fkV2EponIMAlarmNotification OBJECT IDENTIFIER ::= { fkV2EponIMAlarm 4 }

		
		-- 1.3.6.1.4.1.10428 9 1.102.15.4.4.1
		fkV2EponIMAlarmProfileChanged NOTIFICATION-TYPE
			OBJECTS { fkV2EponIMAlarmControlRequest, fkV2EponIMAlarmControlTimeStamp, fkV2EponIMAlarmControlReqResult, fkV2EponIMAlarmOnuAlarmStatus, fkV2EponIMAlarmOnuWindow, 
				fkV2EponIMAlarmOnuThreshold }
			STATUS current
			DESCRIPTION 
				"Description."
			::= { fkV2EponIMAlarmNotification 1 }

		
--  1.3.6.1.4.1.10428 9 1.102.15.4
		-- 1.3.6.1.4.1.10428 9 1.102.15.5
		fkV2EponIMGroup OBJECT-GROUP
			OBJECTS { fkV2EponIMOnuConfigMask, fkV2EponIMOnuConfigData, fkV2EponIMOnuRegistered, fkV2EponIMOnuAuthenticated, fkV2EponIMOnuImageVersion, 
				fkV2EponIMOnuLoadVersion, fkV2EponIMOnuChipVersion, fkV2EponIMOnuSerialNumber, fkV2EponIMOnuRxOpticPower, fkV2EponIMRegInfoOltId, 
				fkV2EponIMRegInfoOltLlidPort, fkV2EponIMRegInfoOltPonPort, fkV2EponIMRegInfoOnuMacAddress, fkV2EponIMRegInfoOnuLlid, fkV2EponIMOnuId, 
				fkV2EponIMOnuSecret, fkV2EponIMOnuVendorCode, fkV2EponIMOnuAuthTimer, fkV2EponIMOnuAuthTimeoutTimer, fkV2EponIMOnuAuthRejectTimer, 
				fkV2EponIMOnuControlRequest, fkV2EponIMOnuControlStatus, fkV2EponIMOnuControlTimer, fkV2EponIMOnuControlTimeStamp, fkV2EponIMOnuControlReqResult, 
				fkV2EponIMOnuControlSecret, fkV2EponIMOnuControlOnuVendorCode, fkV2EponIMOnuControlAuthTimer, fkV2EponIMOnuControlAuthTimeoutTimer, fkV2EponIMOnuControlAuthRejectTimer, 
				fkV2EponIMOnuFWName, fkV2EponIMOnuFWControlRequest, fkV2EponIMOnuFWControlStatus, fkV2EponIMOnuFWControlTimer, fkV2EponIMOnuFWControlTimeStamp, 
				fkV2EponIMOnuFWControlReqResult, fkV2EponIMOnuFWControlServerIp, fkV2EponIMOnuFWControlUpDownFlag, fkV2EponIMOnuFWControlUserId, fkV2EponIMOnuFWControlPassword, 
				fkV2EponIMOnuFWControlFileName, fkV2EponIMOnuFWControlUpdateCommitTime, fkV2EponIMOnuPortIndex, fkV2EponIMOnuPortId, fkV2EponIMOnuPortType, 
				fkV2EponIMOnuPortAdminStatus, fkV2EponIMOnuPortOperStatus, fkV2EponIMOnuPortLinkupTime, fkV2EponIMOnuPortUpTime, fkV2EponIMOnuPortControlRequest, 
				fkV2EponIMOnuPortControlStatus, fkV2EponIMOnuPortControlTimer, fkV2EponIMOnuPortControlTimeStamp, fkV2EponIMOnuPortControlReqResult, fkV2EponIMOnuPortControlAdminState, 
				fkV2EponIMOnuRxFlowCtrl, fkV2EponIMOnuTxFlowCtrl, fkV2EponIMOnuFlowCtrlLowThreshold, fkV2EponIMOnuFlowCtrlHighThreshold, fkV2EponIMOnuBridgeControlRequest, 
				fkV2EponIMOnuBridgeControlStatus, fkV2EponIMOnuBridgeControlTimer, fkV2EponIMOnuBridgeControlTimeStamp, fkV2EponIMOnuBridgeControlReqResult, fkV2EponIMOnuBridgeControlRxFlowCtrl, 
				fkV2EponIMOnuBridgeControlTxFlowCtrl, fkV2EponIMOnuBridgeControlFlowCtrlLowThreshold, fkV2EponIMOnuBridgeControlFlowCtrlHighThreshold, fkV2EponIMOnuPortIfInOctets, fkV2EponIMOnuPortIfInUnicast, 
				fkV2EponIMOnuPortIfInMulticast, fkV2EponIMOnuPortIfInBroadcast, fkV2EponIMOnuPortIfInDiscards, fkV2EponIMOnuPortIfInErrors, fkV2EponIMOnuPortIfInUnknownProtos, 
				fkV2EponIMOnuPortIfOutOctets, fkV2EponIMOnuPortIfOutUnicast, fkV2EponIMOnuPortIfOutMulticast, fkV2EponIMOnuPortIfOutBroadcast, fkV2EponIMOnuPortIfOutDiscards, 
				fkV2EponIMOnuPortIfOutErrors, fkV2EponIMOnuPortEtherAlignmentErrors, fkV2EponIMOnuPortEtherFcsErrors, fkV2EponIMOnuPortEtherSingleCollision, fkV2EponIMOnuPortEtherMultipleCollision, 
				fkV2EponIMOnuPortEtherSqeTestErrors, fkV2EponIMOnuPortEtherDeferredTransmissions, fkV2EponIMOnuPortEtherLateCollisions, fkV2EponIMOnuPortEtherExcessiveCollisions, fkV2EponIMOnuPortEtherInternalMacTxErrors, 
				fkV2EponIMOnuPortEtherCarrierSenseErrors, fkV2EponIMOnuPortEtherFrameTooLongs, fkV2EponIMOnuPortEtherInternalMacRxErrors, fkV2EponIMOnuPortEtherSymbolErrors, fkV2EponIMOnuPortEtherInUnknownOpcode, 
				fkV2EponIMOnuPortEtherInPauseFrames, fkV2EponIMOnuPortEtherOutPauseFrames, fkV2EponIMOnuPortEponMacCtrlFrameRx, fkV2EponIMOnuPortEponDiscWindowsSent, fkV2EponIMOnuPortEponDiscTimeout, 
				fkV2EponIMOnuPortEponTxRegRequest, fkV2EponIMOnuPortEponRxReqRequest, fkV2EponIMOnuPortEponTxReqAck, fkV2EponIMOnuPortEponRxReqAck, fkV2EponIMOnuPortEponTxReport, 
				fkV2EponIMOnuPortEponRxReport, fkV2EponIMOnuPortEponTxGate, fkV2EponIMOnuPortEponRxGate, fkV2EponIMOnuPortEponTxRegister, fkV2EponIMOnuPortEponRxRegister, 
				fkV2EponIMOnuPortEponRxNotSupported, fkV2EponIMOnuPortEponSldErrors, fkV2EponIMOnuPortEponCrc8Errors, fkV2EponIMOnuPortEponBadLlid, fkV2EponIMOnuPortEponGoodLlid, 
				fkV2EponIMOnuPortEponOnuPonCastLlid, fkV2EponIMOnuPortEponOltPonCastLlid, fkV2EponIMOnuPortEponBcastLlidNotOnuId, fkV2EponIMOnuPortEponOnuLlidNotBcast, fkV2EponIMOnuPortEponBcastLlidPlusOnuId, 
				fkV2EponIMOnuPortEponNotBcastLlidNotOnuId, fkV2EponIMOnuPortEponPcsCodingViolation, fkV2EponIMOnuPortEponFecCorrectedBlocks, fkV2EponIMOnuPortEponFecUnCorrectedBlocks, fkV2EponIMOnuPortEponBufferHeadCodingViolation, 
				fkV2EponIMOnuPortStatsControlRequest, fkV2EponIMOnuPortStatsControlStatus, fkV2EponIMOnuPortStatsControlTimer, fkV2EponIMOnuPortStatsControlTimeStamp, fkV2EponIMOnuPortStatsControlReqResult, 
				fkV2EponIMOnuPortStatsControlPortIndex, fkV2EponIMOnuLlidIfInOctets, fkV2EponIMOnuLlidIfInUnicast, fkV2EponIMOnuLlidIfInMulticast, fkV2EponIMOnuLlidIfInBroadcast, 
				fkV2EponIMOnuLlidIfInDiscards, fkV2EponIMOnuLlidIfInErrors, fkV2EponIMOnuLlidIfInUnknownProtos, fkV2EponIMOnuLlidIfOutOctets, fkV2EponIMOnuLlidIfOutUnicast, 
				fkV2EponIMOnuLlidIfOutMulticast, fkV2EponIMOnuLlidIfOutBroadcast, fkV2EponIMOnuLlidIfOutDiscards, fkV2EponIMOnuLlidIfOutErrors, fkV2EponIMOnuLlidEponMacCtrlFrameRx, 
				fkV2EponIMOnuLlidEponDiscWindowsSent, fkV2EponIMOnuLlidEponDiscTimeout, fkV2EponIMOnuLlidEponTxRegRequest, fkV2EponIMOnuLlidEponRxReqRequest, fkV2EponIMOnuLlidEponTxReqAck, 
				fkV2EponIMOnuLlidEponRxReqAck, fkV2EponIMOnuLlidEponTxReport, fkV2EponIMOnuLlidEponRxReport, fkV2EponIMOnuLlidEponTxGate, fkV2EponIMOnuLlidEponRxGate, 
				fkV2EponIMOnuLlidEponTxRegister, fkV2EponIMOnuLlidEponRxRegister, fkV2EponIMOnuLlidEponRxNotSupported, fkV2EponIMOnuLlidEponSldErrors, fkV2EponIMOnuLlidEponCrc8Errors, 
				fkV2EponIMOnuLlidEponBadLlid, fkV2EponIMOnuLlidEponGoodLlid, fkV2EponIMOnuLlidEponOnuPonCastLlid, fkV2EponIMOnuLlidEponOltPonCastLlid, fkV2EponIMOnuLlidEponBcastLlidNotOnuId, 
				fkV2EponIMOnuLlidEponOnuLlidNotBcast, fkV2EponIMOnuLlidEponBcastLlidPlusOnuId, fkV2EponIMOnuLlidEponNotBcastLlidNotOnuId, fkV2EponIMOnuLlidEponPcsCodingViolation, fkV2EponIMOnuLlidEponFecCorrectedBlocks, 
				fkV2EponIMOnuLlidEponFecUnCorrectedBlocks, fkV2EponIMOnuLlidEponBufferHeadCodingViolation, fkV2EponIMOnuLlidStatsControlRequest, fkV2EponIMOnuLlidStatsControlStatus, fkV2EponIMOnuLlidStatsControlTimer, 
				fkV2EponIMOnuLlidStatsControlTimeStamp, fkV2EponIMOnuLlidStatsControlReqResult, fkV2EponIMAlarmOnuPortIndex, fkV2EponIMAlarmOnuAlarmIndex, fkV2EponIMAlarmOnuAlarmStatus, 
				fkV2EponIMAlarmOnuWindow, fkV2EponIMAlarmOnuThreshold, fkV2EponIMAlarmControlRequest, fkV2EponIMAlarmControlStatus, fkV2EponIMAlarmControlTimer, 
				fkV2EponIMAlarmControlTimeStamp, fkV2EponIMAlarmControlReqResult, fkV2EponIMAlarmControlOnuPortIndex, fkV2EponIMAlarmControlOnuAlarmIndex, fkV2EponIMAlarmControlOnuAlarmStatus, 
				fkV2EponIMAlarmControlWindow, fkV2EponIMOnuControlForceOpticPowerOff, fkV2EponIMOnuForceOpticPowerOff, fkV2EponIMOnuPortFECtxEnable, fkV2EponIMOnuPortFECrxEnable, 
				fkV2EponIMOnuPortLaserAlwaysOn, fkV2EponIMOnuPortDropInMcastTraffic, fkV2EponIMOnuPortDropInBcastTraffic, fkV2EponIMOnuPortBlockDataTraffic, fkV2EponIMOnuOpticButtonPushed, 
				fkV2EponIMAlarmControlThreshold, fkV2EponIMOnuAutoUpgrade, fkV2EponIMOnuControlAutoUpgrade }
			STATUS current
			DESCRIPTION 
				"Description."
			::= { fkV2EponIM 5 }

		
--  1.3.6.1.4.1.10428 9 1.102.15.5
		-- 1.3.6.1.4.1.10428 9 1.102.15.6
		fkV2EponIMNotificationGroup NOTIFICATION-GROUP
			NOTIFICATIONS { fkV2EponIMOnuSecretChanged, fkV2EponIMOnuVendorCodeChanged, fkV2EponIMOnuAuthTimerChanged, fkV2EponIMOnuConfigApplySetted, fkV2EponIMOnuFWFirmwareCpSetted, 
				fkV2EponIMOnuFWFirmwareDestroyed, fkV2EponIMOnuFWFirmwareUpgradeSetted, fkV2EponIMOnuFWFirmwareCommitSetted, fkV2EponIMOnuPortAdminStateChanged, fkV2EponIMOnuBridgeFlowCtrlChagned, 
				fkV2EponIMOnuPortStatsCleared, fkV2EponIMOnuLlidStatsCleared, fkV2EponIMOnuForcePowerOffChanged, fkV2EponIMAlarmProfileChanged, fkV2EponIMOnuAutoUpgradeChanged, 
				fkV2EponIMOnuReset }
			STATUS current
			DESCRIPTION 
				"Description."
			::= { fkV2EponIM 6 }

		
	
	END

--
-- FKV2-EPON-IM-MIB.my
--
