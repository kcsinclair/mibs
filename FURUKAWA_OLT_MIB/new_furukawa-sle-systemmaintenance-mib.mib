--
-- fk-systemmaintenance-mib.mib
-- MIB generated by MG-SOFT Visual MIB Builder Version 6.0  Build 88
-- Tuesday, March 26, 2013 at 17:39:29
--

        FK-SYSTEMMAINTENANCE-MIB DEFINITIONS ::= BEGIN
 
                IMPORTS
                        fkMgmt                  
                                FROM FKOLTG1040-SMI                     
                        FkPermissionType, FkControlStatusType, FkControlRequestResultType                       
                                FROM FK-TC-MIB                  
                        OBJECT-GROUP, NOTIFICATION-GROUP                        
                                FROM SNMPv2-CONF                        
                        TimeTicks, IpAddress, Integer32, Unsigned32, Gauge32, 
                        Counter64, OBJECT-TYPE, MODULE-IDENTITY, NOTIFICATION-TYPE                        
                                FROM SNMPv2-SMI                 
                        MacAddress                      
                                FROM SNMPv2-TC;
        
        
                -- 1.3.6.1.4.1.10428 9 1.101.1
                fkSystemMaintenance MODULE-IDENTITY 
                        LAST-UPDATED "200412101054Z"            -- December 10, 2004 at 10:54 GMT
                        ORGANIZATION 
                                "Furukawa Industrial S.A."
                        CONTACT-INFO 
                                "Furukawa Industrial S.A. Produtos Eletricos
        Rua Hasdrubal Bellegard, 820 - CIC
        CEP 81460-120 - Curitiba - Parana - Brasil
        CSC 0800-41-2100
        E-mail: fisa@furukawa.com.br"
                        DESCRIPTION 
                                "The MIB module for Furukawa GPON OLT FK-OLT-G1040."
                        ::= { fkMgmt 1 }

                
        
--
-- Type definitions
--
        
                EnableFlag ::= INTEGER
                        {
                        enable(1),
                        disable(2)
                        }

                FkDefAutoCliScheduleResult ::= INTEGER
                        {
                        success(1),
                        fail(2)
                        }

                FkDefAutoCliScheduleType ::= INTEGER
                        {
                        periodic(1),
                        at(2),
                        daily(3),
                        immediate(4)
                        }

                FkDefAutoCliScheduleTransferType ::= INTEGER
                        {
                        ftp(1),
                        tftp(2),
                        memory(3),
                        none(4)
                        }

        
        
--
-- Node definitions
--
        
                -- 1.3.6.1.4.1.10428 9 1.101.1.1
                fkSystemBase OBJECT IDENTIFIER ::= { fkSystemMaintenance 1 }

                
                -- 1.3.6.1.4.1.10428 9 1.101.1.1.1
                fkSystemBaseInfo OBJECT IDENTIFIER ::= { fkSystemBase 1 }

                
                -- 1.3.6.1.4.1.10428 9 1.101.1.1.1.1
                fkSystemModelName OBJECT-TYPE
                        SYNTAX OCTET STRING
                        MAX-ACCESS read-only
                        STATUS current
                        DESCRIPTION
                                "Description"
                        ::= { fkSystemBaseInfo 1 }

                
                -- 1.3.6.1.4.1.10428 9 1.101.1.1.1.2
                fkSystemSerialNumber OBJECT-TYPE
                        SYNTAX OCTET STRING
                        MAX-ACCESS read-only
                        STATUS current
                        DESCRIPTION
                                "Description"
                        ::= { fkSystemBaseInfo 2 }

                
                -- 1.3.6.1.4.1.10428 9 1.101.1.1.1.3
                fkSystemHWVersion OBJECT-TYPE
                        SYNTAX OCTET STRING
                        MAX-ACCESS read-only
                        STATUS current
                        DESCRIPTION
                                "Description"
                        ::= { fkSystemBaseInfo 3 }

                
                -- 1.3.6.1.4.1.10428 9 1.101.1.1.1.4
                fkSystemBLVersion OBJECT-TYPE
                        SYNTAX OCTET STRING
                        MAX-ACCESS read-only
                        STATUS current
                        DESCRIPTION
                                "Description"
                        ::= { fkSystemBaseInfo 4 }

                
                -- 1.3.6.1.4.1.10428 9 1.101.1.1.1.5
                fkSystemSWCompatibility OBJECT-TYPE
                        SYNTAX OCTET STRING
                        MAX-ACCESS read-only
                        STATUS current
                        DESCRIPTION
                                "Description"
                        ::= { fkSystemBaseInfo 5 }

                
                -- 1.3.6.1.4.1.10428 9 1.101.1.1.1.6
                fkSystemOSVersion OBJECT-TYPE
                        SYNTAX OCTET STRING
                        MAX-ACCESS read-only
                        STATUS current
                        DESCRIPTION
                                "Description"
                        ::= { fkSystemBaseInfo 6 }

                
                -- 1.3.6.1.4.1.10428 9 1.101.1.1.1.7
                fkSystemMacAddress OBJECT-TYPE
                        SYNTAX MacAddress
                        MAX-ACCESS read-only
                        STATUS current
                        DESCRIPTION
                                "Description"
                        ::= { fkSystemBaseInfo 7 }

                
                -- 1.3.6.1.4.1.10428 9 1.101.1.1.1.8
                fkSystemHostName OBJECT-TYPE
                        SYNTAX OCTET STRING
                        MAX-ACCESS read-only
                        STATUS current
                        DESCRIPTION
                                "Description"
                        ::= { fkSystemBaseInfo 8 }

                
                -- 1.3.6.1.4.1.10428 9 1.101.1.1.1.9
                fkSystemCPULoadAll OBJECT-TYPE
                        SYNTAX OCTET STRING
                        MAX-ACCESS read-only
                        STATUS current
                        DESCRIPTION
                                "Description"
                        ::= { fkSystemBaseInfo 9 }

                
                -- 1.3.6.1.4.1.10428 9 1.101.1.1.1.10
                fkSystemCPULoadInterrupt OBJECT-TYPE
                        SYNTAX OCTET STRING
                        MAX-ACCESS read-only
                        STATUS current
                        DESCRIPTION
                                "Description"
                        ::= { fkSystemBaseInfo 10 }

                
                -- 1.3.6.1.4.1.10428 9 1.101.1.1.1.11
                fkSystemCPUThreshold OBJECT-TYPE
                        SYNTAX INTEGER (20..100)
                        MAX-ACCESS read-only
                        STATUS current
                        DESCRIPTION
                                "Description"
                        ::= { fkSystemBaseInfo 11 }

                
                -- 1.3.6.1.4.1.10428 9 1.101.1.1.1.12
                fkSystemCPUInterval OBJECT-TYPE
                        SYNTAX INTEGER (5 | 60 | 600)
                        MAX-ACCESS read-only
                        STATUS current
                        DESCRIPTION
                                "Description"
                        ::= { fkSystemBaseInfo 12 }

                
                -- 1.3.6.1.4.1.10428 9 1.101.1.1.1.13
                fkSystemMemoryTotal OBJECT-TYPE
                        SYNTAX Unsigned32
                        MAX-ACCESS read-only
                        STATUS current
                        DESCRIPTION
                                "Description"
                        ::= { fkSystemBaseInfo 13 }

                
                -- 1.3.6.1.4.1.10428 9 1.101.1.1.1.14
                fkSystemMemoryFree OBJECT-TYPE
                        SYNTAX Unsigned32
                        MAX-ACCESS read-only
                        STATUS current
                        DESCRIPTION
                                "Description"
                        ::= { fkSystemBaseInfo 14 }

                
                -- 1.3.6.1.4.1.10428 9 1.101.1.1.1.15
                fkSystemMemoryShared OBJECT-TYPE
                        SYNTAX Unsigned32
                        MAX-ACCESS read-only
                        STATUS current
                        DESCRIPTION
                                "Description"
                        ::= { fkSystemBaseInfo 15 }

                
                -- 1.3.6.1.4.1.10428 9 1.101.1.1.1.16
                fkSystemMemoryBuffers OBJECT-TYPE
                        SYNTAX Unsigned32
                        MAX-ACCESS read-only
                        STATUS current
                        DESCRIPTION
                                "Description"
                        ::= { fkSystemBaseInfo 16 }

                
                -- 1.3.6.1.4.1.10428 9 1.101.1.1.1.17
                fkSystemMemoryCached OBJECT-TYPE
                        SYNTAX Unsigned32
                        MAX-ACCESS read-only
                        STATUS current
                        DESCRIPTION
                                "Description"
                        ::= { fkSystemBaseInfo 17 }

                
                -- 1.3.6.1.4.1.10428 9 1.101.1.1.1.18
                fkSystemMemorySwapTotal OBJECT-TYPE
                        SYNTAX Unsigned32
                        MAX-ACCESS read-only
                        STATUS current
                        DESCRIPTION
                                "Description"
                        ::= { fkSystemBaseInfo 18 }

                
                -- 1.3.6.1.4.1.10428 9 1.101.1.1.1.19
                fkSystemMemorySwapFree OBJECT-TYPE
                        SYNTAX Unsigned32
                        MAX-ACCESS read-only
                        STATUS current
                        DESCRIPTION
                                "Description"
                        ::= { fkSystemBaseInfo 19 }

                
                -- 1.3.6.1.4.1.10428 9 1.101.1.1.1.20
                fkSystemDefaultOS OBJECT-TYPE
                        SYNTAX INTEGER
                                {
                                noDualOS(0),
                                os1(1),
                                os2(2)
                                }
                        MAX-ACCESS read-only
                        STATUS current
                        DESCRIPTION
                                "Description"
                        ::= { fkSystemBaseInfo 20 }

                
                -- 1.3.6.1.4.1.10428 9 1.101.1.1.1.21
                fkSystemOS1Version OBJECT-TYPE
                        SYNTAX OCTET STRING
                        MAX-ACCESS read-only
                        STATUS current
                        DESCRIPTION
                                "Description"
                        ::= { fkSystemBaseInfo 21 }

                
                -- 1.3.6.1.4.1.10428 9 1.101.1.1.1.22
                fkSystemOS1Size OBJECT-TYPE
                        SYNTAX Unsigned32
                        MAX-ACCESS read-only
                        STATUS current
                        DESCRIPTION
                                "Description"
                        ::= { fkSystemBaseInfo 22 }

                
                -- 1.3.6.1.4.1.10428 9 1.101.1.1.1.23
                fkSystemOS1BuildNumber OBJECT-TYPE
                        SYNTAX OCTET STRING
                        MAX-ACCESS read-only
                        STATUS current
                        DESCRIPTION
                                "Description"
                        ::= { fkSystemBaseInfo 23 }

                
                -- 1.3.6.1.4.1.10428 9 1.101.1.1.1.24
                fkSystemOS2Version OBJECT-TYPE
                        SYNTAX OCTET STRING
                        MAX-ACCESS read-only
                        STATUS current
                        DESCRIPTION
                                "Description"
                        ::= { fkSystemBaseInfo 24 }

                
                -- 1.3.6.1.4.1.10428 9 1.101.1.1.1.25
                fkSystemOS2Size OBJECT-TYPE
                        SYNTAX Unsigned32
                        MAX-ACCESS read-only
                        STATUS current
                        DESCRIPTION
                                "Description"
                        ::= { fkSystemBaseInfo 25 }

                
                -- 1.3.6.1.4.1.10428 9 1.101.1.1.1.26
                fkSystemOS2BuildNumber OBJECT-TYPE
                        SYNTAX OCTET STRING
                        MAX-ACCESS read-only
                        STATUS current
                        DESCRIPTION
                                "Description"
                        ::= { fkSystemBaseInfo 26 }

                
                -- 1.3.6.1.4.1.10428 9 1.101.1.1.1.27
                fkSystemFlashTotalSize OBJECT-TYPE
                        SYNTAX Unsigned32
                        MAX-ACCESS read-only
                        STATUS current
                        DESCRIPTION
                                "Description"
                        ::= { fkSystemBaseInfo 27 }

                
                -- 1.3.6.1.4.1.10428 9 1.101.1.1.1.28
                fkSystemFlashOSSize OBJECT-TYPE
                        SYNTAX Unsigned32
                        MAX-ACCESS read-only
                        STATUS current
                        DESCRIPTION
                                "Description"
                        ::= { fkSystemBaseInfo 28 }

                
                -- 1.3.6.1.4.1.10428 9 1.101.1.1.1.29
                fkSystemFlashConfigSize OBJECT-TYPE
                        SYNTAX Unsigned32
                        MAX-ACCESS read-only
                        STATUS current
                        DESCRIPTION
                                "Description"
                        ::= { fkSystemBaseInfo 29 }

                
                -- 1.3.6.1.4.1.10428 9 1.101.1.1.1.30
                fkSystemFlashOSUsedSize OBJECT-TYPE
                        SYNTAX Unsigned32
                        MAX-ACCESS read-only
                        STATUS current
                        DESCRIPTION
                                "Description"
                        ::= { fkSystemBaseInfo 30 }

                
                -- 1.3.6.1.4.1.10428 9 1.101.1.1.1.31
                fkSystemFlashConfigUsedSize OBJECT-TYPE
                        SYNTAX Unsigned32
                        MAX-ACCESS read-only
                        STATUS current
                        DESCRIPTION
                                "Description"
                        ::= { fkSystemBaseInfo 31 }

                
                -- 1.3.6.1.4.1.10428 9 1.101.1.1.1.32
                fkSystemClock OBJECT-TYPE
                        SYNTAX OCTET STRING
                        MAX-ACCESS read-only
                        STATUS current
                        DESCRIPTION
                                "Description"
                        ::= { fkSystemBaseInfo 32 }

                
                -- 1.3.6.1.4.1.10428 9 1.101.1.1.1.33
                fkSystemTimezone OBJECT-TYPE
                        SYNTAX OCTET STRING
                        MAX-ACCESS read-only
                        STATUS current
                        DESCRIPTION
                                "Description"
                        ::= { fkSystemBaseInfo 33 }

                
                -- 1.3.6.1.4.1.10428 9 1.101.1.1.1.34
                fkSystemDNSDomainName OBJECT-TYPE
                        SYNTAX OCTET STRING
                        MAX-ACCESS read-only
                        STATUS current
                        DESCRIPTION
                                "Description"
                        ::= { fkSystemBaseInfo 34 }

                
                -- 1.3.6.1.4.1.10428 9 1.101.1.1.1.35
                fkSystemInitBanner OBJECT-TYPE
                        SYNTAX OCTET STRING
                        MAX-ACCESS read-only
                        STATUS current
                        DESCRIPTION
                                "Description"
                        ::= { fkSystemBaseInfo 35 }

                
                -- 1.3.6.1.4.1.10428 9 1.101.1.1.1.36
                fkSystemSuccessBanner OBJECT-TYPE
                        SYNTAX OCTET STRING
                        MAX-ACCESS read-only
                        STATUS current
                        DESCRIPTION
                                "Description"
                        ::= { fkSystemBaseInfo 36 }

                
                -- 1.3.6.1.4.1.10428 9 1.101.1.1.1.37
                fkSystemFailBanner OBJECT-TYPE
                        SYNTAX OCTET STRING
                        MAX-ACCESS read-only
                        STATUS current
                        DESCRIPTION
                                "Description"
                        ::= { fkSystemBaseInfo 37 }

                
                -- 1.3.6.1.4.1.10428 9 1.101.1.1.1.38
                fkSystemSyslogState OBJECT-TYPE
                        SYNTAX INTEGER
                                {
                                notAvailable(-2),
                                stop(0),
                                start(1)
                                }
                        MAX-ACCESS read-only
                        STATUS current
                        DESCRIPTION
                                "Description"
                        ::= { fkSystemBaseInfo 38 }

                
                -- 1.3.6.1.4.1.10428 9 1.101.1.1.1.39
                fkSystemSyslogVolatileNumber OBJECT-TYPE
                        SYNTAX Integer32
                        MAX-ACCESS read-only
                        STATUS current
                        DESCRIPTION
                                "Description"
                        ::= { fkSystemBaseInfo 39 }

                
                -- 1.3.6.1.4.1.10428 9 1.101.1.1.1.40
                fkSystemSyslogNonVolatileNumber OBJECT-TYPE
                        SYNTAX Integer32
                        MAX-ACCESS read-only
                        STATUS current
                        DESCRIPTION
                                "Description"
                        ::= { fkSystemBaseInfo 40 }

                
                -- 1.3.6.1.4.1.10428 9 1.101.1.1.1.41
                fkSystemSyslogBindAddress OBJECT-TYPE
                        SYNTAX IpAddress
                        MAX-ACCESS read-only
                        STATUS current
                        DESCRIPTION
                                "Description"
                        ::= { fkSystemBaseInfo 41 }

                
                -- 1.3.6.1.4.1.10428 9 1.101.1.1.1.42
                fkSystemSyslogLocalCode OBJECT-TYPE
                        SYNTAX INTEGER (-1 | 0..7)
                        MAX-ACCESS read-only
                        STATUS current
                        DESCRIPTION
                                "Description"
                        ::= { fkSystemBaseInfo 42 }

                
                -- 1.3.6.1.4.1.10428 9 1.101.1.1.1.43
                fkSystemSSHState OBJECT-TYPE
                        SYNTAX INTEGER
                                {
                                disable(0),
                                enable(1)
                                }
                        MAX-ACCESS read-only
                        STATUS current
                        DESCRIPTION
                                "Description"
                        ::= { fkSystemBaseInfo 43 }

                
                -- 1.3.6.1.4.1.10428 9 1.101.1.1.1.44
                fkSystemNTPState OBJECT-TYPE
                        SYNTAX INTEGER
                                {
                                disable(0),
                                ntp(1),
                                sntp(2)
                                }
                        MAX-ACCESS read-only
                        STATUS current
                        DESCRIPTION
                                "Description"
                        ::= { fkSystemBaseInfo 44 }

                
                -- 1.3.6.1.4.1.10428 9 1.101.1.1.1.45
                fkSystemBackupInterval OBJECT-TYPE
                        SYNTAX Integer32
                        MAX-ACCESS read-only
                        STATUS current
                        DESCRIPTION
                                "Description."
                        ::= { fkSystemBaseInfo 45 }

                
                -- 1.3.6.1.4.1.10428 9 1.101.1.1.1.46
                fkSystemDhcpActivity OBJECT-TYPE
                        SYNTAX INTEGER
                                {
                                disable(0),
                                enable(1)
                                }
                        MAX-ACCESS read-only
                        STATUS current
                        DESCRIPTION
                                "The activity of DHCP daemon."
                        ::= { fkSystemBaseInfo 46 }

                
                -- 1.3.6.1.4.1.10428 9 1.101.1.1.1.47
                fkSystemDefaultTTL OBJECT-TYPE
                        SYNTAX INTEGER (32..255)
                        MAX-ACCESS read-only
                        STATUS current
                        DESCRIPTION
                                "The default ttl."
                        ::= { fkSystemBaseInfo 47 }

                
                -- 1.3.6.1.4.1.10428 9 1.101.1.1.1.48
                fkSystemSyslogVolatileSize OBJECT-TYPE
                        SYNTAX Integer32
                        MAX-ACCESS read-only
                        STATUS current
                        DESCRIPTION
                                "Description."
                        ::= { fkSystemBaseInfo 48 }

                
                -- 1.3.6.1.4.1.10428 9 1.101.1.1.1.49
                fkSystemSyslogBindInterfaceName OBJECT-TYPE
                        SYNTAX OCTET STRING
                        MAX-ACCESS read-only
                        STATUS current
                        DESCRIPTION
                                "Description."
                        ::= { fkSystemBaseInfo 49 }

                
                -- 1.3.6.1.4.1.10428 9 1.101.1.1.1.50
                fkSystemSessionTime OBJECT-TYPE
                        SYNTAX INTEGER (60..3600)
                        MAX-ACCESS read-only
                        STATUS current
                        DESCRIPTION
                                "Description."
                        ::= { fkSystemBaseInfo 50 }

                
                -- 1.3.6.1.4.1.10428 9 1.101.1.1.1.51
                fkSystemExecTimeout OBJECT-TYPE
                        SYNTAX INTEGER (0..2147519)
                        MAX-ACCESS read-only
                        STATUS current
                        DESCRIPTION
                                "Description."
                        ::= { fkSystemBaseInfo 51 }

                
                -- 1.3.6.1.4.1.10428 9 1.101.1.1.1.52
                fkSystemWatchdogStatus OBJECT-TYPE
                        SYNTAX INTEGER
                                {
                                enable(1),
                                disable(2)
                                }
                        MAX-ACCESS read-only
                        STATUS current
                        DESCRIPTION
                                "Description."
                        ::= { fkSystemBaseInfo 52 }

                
                -- 1.3.6.1.4.1.10428 9 1.101.1.1.1.53
                fkSystemNtpBindInterface OBJECT-TYPE
                        SYNTAX OCTET STRING
                        MAX-ACCESS read-only
                        STATUS current
                        DESCRIPTION
                                "Description."
                        ::= { fkSystemBaseInfo 53 }

                
                -- 1.3.6.1.4.1.10428 9 1.101.1.1.1.54
                fkSystemFtpBindInterface OBJECT-TYPE
                        SYNTAX OCTET STRING
                        MAX-ACCESS read-only
                        STATUS current
                        DESCRIPTION
                                "Description."
                        ::= { fkSystemBaseInfo 54 }

                
                -- 1.3.6.1.4.1.10428 9 1.101.1.1.1.55
                fkSystemRedundancyPort OBJECT-TYPE
                        SYNTAX INTEGER (1..24)
                        MAX-ACCESS read-only
                        STATUS current
                        DESCRIPTION
                                "Description."
                        ::= { fkSystemBaseInfo 55 }

                
                -- 1.3.6.1.4.1.10428 9 1.101.1.1.1.56
                fkSystemSyslogVolatileMaxLine OBJECT-TYPE
                        SYNTAX INTEGER (0 | 8..16384)
                        MAX-ACCESS read-only
                        STATUS current
                        DESCRIPTION
                                "The max lines of volatile.
                                Exclusive to fkSystemSyslogVolatileSize.
                                (Supported only model 5924N)
                                "
                        ::= { fkSystemBaseInfo 56 }

                
                -- 1.3.6.1.4.1.10428 9 1.101.1.1.1.57
                fkSystemBootInfo OBJECT-TYPE
                        SYNTAX OCTET STRING
                        MAX-ACCESS read-only
                        STATUS current
                        DESCRIPTION
                                "The information of last boot..
                                (Supported only model 5924N)
                                "
                        ::= { fkSystemBaseInfo 57 }

                
                -- 1.3.6.1.4.1.10428 9 1.101.1.1.1.58
                fkSystemTempHighThreshold OBJECT-TYPE
                        SYNTAX Integer32
                        MAX-ACCESS read-only
                        STATUS current
                        DESCRIPTION
                                "Description."
                        ::= { fkSystemBaseInfo 58 }

                
                -- 1.3.6.1.4.1.10428 9 1.101.1.1.1.59
                fkSystemTempLowThreshold OBJECT-TYPE
                        SYNTAX Integer32
                        MAX-ACCESS read-only
                        STATUS current
                        DESCRIPTION
                                "Description."
                        ::= { fkSystemBaseInfo 59 }

                
                -- 1.3.6.1.4.1.10428 9 1.101.1.1.1.60
                fkSystemMemThreshold OBJECT-TYPE
                        SYNTAX INTEGER (20..100)
                        MAX-ACCESS read-only
                        STATUS current
                        DESCRIPTION
                                "Description."
                        ::= { fkSystemBaseInfo 60 }

                
                -- 1.3.6.1.4.1.10428 9 1.101.1.1.1.61
                fkSystemLowCPUThreshold OBJECT-TYPE
                        SYNTAX INTEGER (20..100)
                        MAX-ACCESS read-only
                        STATUS current
                        DESCRIPTION
                                "Description."
                        ::= { fkSystemBaseInfo 61 }

                
                -- 1.3.6.1.4.1.10428 9 1.101.1.1.1.62
                fkSystemLowCPUInterval OBJECT-TYPE
                        SYNTAX INTEGER (5 | 60 | 600)
                        MAX-ACCESS read-only
                        STATUS current
                        DESCRIPTION
                                "Description."
                        ::= { fkSystemBaseInfo 62 }

                
                -- 1.3.6.1.4.1.10428 9 1.101.1.1.1.63
                fkSystemRunningOS OBJECT-TYPE
                        SYNTAX INTEGER
                                {
                                noDualOS(0),
                                os1(1),
                                os2(2)
                                }
                        MAX-ACCESS read-only
                        STATUS current
                        DESCRIPTION
                                "Description."
                        ::= { fkSystemBaseInfo 63 }

                
                -- 1.3.6.1.4.1.10428 9 1.101.1.1.1.64
                fkSystemNtpBindAddress OBJECT-TYPE
                        SYNTAX IpAddress
                        MAX-ACCESS read-only
                        STATUS current
                        DESCRIPTION
                                "The NTP client binding address."
                        DEFVAL { ''h }
                        ::= { fkSystemBaseInfo 64 }

                
                -- 1.3.6.1.4.1.10428 9 1.101.1.1.1.65
                fkSystemEnablePasswdType OBJECT-TYPE
                        SYNTAX INTEGER
                                {
                                plain(1),
                                encrypt(2)
                                }
                        MAX-ACCESS read-write
                        STATUS current
                        DESCRIPTION
                                "The type of enable password of command shell.
                                plain : no encryption.
                                encrypt : encryption"
                        DEFVAL { plain }
                        ::= { fkSystemBaseInfo 65 }

                
                -- 1.3.6.1.4.1.10428 9 1.101.1.1.1.66
                fkSystemEnablePasswd OBJECT-TYPE
                        SYNTAX OCTET STRING (SIZE (0..64))
                        MAX-ACCESS read-write
                        STATUS current
                        DESCRIPTION
                                "The enable password of command shell."
                        ::= { fkSystemBaseInfo 66 }

                
                -- 1.3.6.1.4.1.10428 9 1.101.1.1.1.67
                fkSystemServicePasswdEncryption OBJECT-TYPE
                        SYNTAX INTEGER
                                {
                                enable(1),
                                disable(2)
                                }
                        MAX-ACCESS read-write
                        STATUS current
                        DESCRIPTION
                                "The encrypt system passwords"
                        DEFVAL { disable }
                        ::= { fkSystemBaseInfo 67 }

                
                -- 1.3.6.1.4.1.10428 9 1.101.1.1.1.68
                fkSystemUptime64 OBJECT-TYPE
                        SYNTAX Counter64
                        MAX-ACCESS read-write
                        STATUS current
                        DESCRIPTION
                                "The time counter from system up. It is large version of sysUpTime."
                        ::= { fkSystemBaseInfo 68 }

                
                -- 1.3.6.1.4.1.10428 9 1.101.1.1.1.69
                fkSystemNtpPollnterval OBJECT-TYPE
                        SYNTAX Integer32 (6..20)
                        MAX-ACCESS read-only
                        STATUS current
                        DESCRIPTION
                                "The NTP request polling-interval"
                        ::= { fkSystemBaseInfo 69 }

                
--   1.3.6.1.4.1.10428 9 1.101.1.1.1.70
-- 1.3.6.1.4.1.10428 9 1.101.1.1.1.70
                -- 1.3.6.1.4.1.10428 9 1.101.1.1.1.70
                fkSystemCPUDuration OBJECT-TYPE
                        SYNTAX INTEGER (5..300)
                        MAX-ACCESS read-only
                        STATUS current
                        DESCRIPTION
                                "The threshold sampling duration."
                        ::= { fkSystemBaseInfo 70 }

                
--   1.3.6.1.4.1.10428 9 1.101.1.1.1.71
-- 1.3.6.1.4.1.10428 9 1.101.1.1.1.71
                -- 1.3.6.1.4.1.10428 9 1.101.1.1.1.71
                fkSystemLowCPUDuration OBJECT-TYPE
                        SYNTAX INTEGER (5..300)
                        MAX-ACCESS read-only
                        STATUS current
                        DESCRIPTION
                                "The threshold sampling duration."
                        ::= { fkSystemBaseInfo 71 }

                
                -- 1.3.6.1.4.1.10428 9 1.101.1.1.1.72
                fkSystemBarcode OBJECT-TYPE
                        SYNTAX OCTET STRING
                        MAX-ACCESS read-only
                        STATUS current
                        DESCRIPTION
                                "The System Barcode. (only for specific vender)"
                        ::= { fkSystemBaseInfo 72 }

                
                -- 1.3.6.1.4.1.10428 9 1.101.1.1.1.73
                fkSystemEnhancedFeature OBJECT-TYPE
                        SYNTAX INTEGER
                                {
                                enable(1),
                                disable(2)
                                }
                        MAX-ACCESS read-only
                        STATUS current
                        DESCRIPTION
                                "System enhanced feature enable/disable."
                        ::= { fkSystemBaseInfo 73 }

                
                -- 1.3.6.1.4.1.10428 9 1.101.1.1.1.74
                fkSystemGetBranchModel OBJECT-TYPE
                        SYNTAX INTEGER
                                {
                                other(0),
                                nsn(1)
                                }
                        MAX-ACCESS read-only
                        STATUS current
                        DESCRIPTION
                                "The distinction of branch model."
                        ::= { fkSystemBaseInfo 74 }

                
                -- 1.3.6.1.4.1.10428 9 1.101.1.1.1.75
                fkSystemTargetId OBJECT-TYPE
                        SYNTAX OCTET STRING
                        MAX-ACCESS read-only
                        STATUS current
                        DESCRIPTION
                                "The system target ID."
                        ::= { fkSystemBaseInfo 75 }

                
                -- 1.3.6.1.4.1.10428 9 1.101.1.1.1.76
                fkSystemNodeName OBJECT-TYPE
                        SYNTAX OCTET STRING
                        MAX-ACCESS read-only
                        STATUS current
                        DESCRIPTION
                                "The system node name."
                        ::= { fkSystemBaseInfo 76 }

                
                -- 1.3.6.1.4.1.10428 9 1.101.1.1.1.77
                fkSystemNetworkName OBJECT-TYPE
                        SYNTAX OCTET STRING
                        MAX-ACCESS read-only
                        STATUS current
                        DESCRIPTION
                                "The system network name."
                        ::= { fkSystemBaseInfo 77 }

                
                -- 1.3.6.1.4.1.10428 9 1.101.1.1.1.78
                fkSystemShelfId OBJECT-TYPE
                        SYNTAX OCTET STRING
                        MAX-ACCESS read-only
                        STATUS current
                        DESCRIPTION
                                "The system shelf ID."
                        ::= { fkSystemBaseInfo 78 }

                
                -- 1.3.6.1.4.1.10428 9 1.101.1.1.1.79
                fkSystemSlotId OBJECT-TYPE
                        SYNTAX OCTET STRING
                        MAX-ACCESS read-only
                        STATUS current
                        DESCRIPTION
                                "The system slot ID."
                        ::= { fkSystemBaseInfo 79 }

                
                -- 1.3.6.1.4.1.10428 9 1.101.1.1.2
                fkSystemBaseControl OBJECT IDENTIFIER ::= { fkSystemBase 2 }

                
                -- 1.3.6.1.4.1.10428 9 1.101.1.1.2.1
                fkSystemControlRequest OBJECT-TYPE
                        SYNTAX INTEGER
                                {
                                setSystemBaseSystemInfoProfile(1),
                                setSystemBaseCPUThresholdProfile(2),
                                fkSystemBaseDefaultOS(3),
                                setSystemBaseRTCProfile(4),
                                setSystemBaseDNSDomainName(5),
                                setSystemBaseBannerProfile(6),
                                setSystemBaseSyslogProfile(7),
                                setSystemBaseSSHState(8),
                                setSystemBaseNTPState(9),
                                setSystemBaseOSUpgradeProfile(10),
                                setSystemBaseBackup(11),
                                setSystemBaseBackupInterval(12),
                                setSystemBaseReload(13),
                                setSystemDhcpActivity(14),
                                setSystemBasePonFwDownloadProfile(15),
                                setSystemDefaultTTL(16),
                                setSystemBaseSyslogBindIfName(17),
                                clearSystemBaseSyslogBindIfName(18),
                                setSystemConfigPortMove(19),
                                setSystemConfigPortCopy(20),
                                setSystemConfigPortClear(21),
                                setSystemControlSessionTime(22),
                                setSystemControlExecTimeout(23),
                                setSystemWatchdogStatus(24),
                                clearSystemOs(25),
                                setNtpBindInterface(26),
                                setFtpBindInterface(27),
                                setSystemBaseRedundancyPort(28),
                                clearRedundancy(29),
                                setSystemBaseTempThreshold(30),
                                setSystemBaseMemThreshold(31),
                                setSystemBaseReloadBoth(32),
                                setSystemBaseBootloaderUpgradeProfile(33),
                                setNtpBindAddress(34),
                                setEnablePasswd(35),
                                setEnableSerivceEncryption(36),
                                restoreSystemPasswd(37),
                                setNtpPollInterval(38),
                                setRestoreFactory(39)
                                }
                        MAX-ACCESS read-write
                        STATUS current
                        DESCRIPTION
                                "Description"
                        ::= { fkSystemBaseControl 1 }

                
                -- 1.3.6.1.4.1.10428 9 1.101.1.1.2.2
                fkSystemControlStatus OBJECT-TYPE
                        SYNTAX FkControlStatusType
                        MAX-ACCESS read-only
                        STATUS current
                        DESCRIPTION
                                "Description"
                        ::= { fkSystemBaseControl 2 }

                
                -- 1.3.6.1.4.1.10428 9 1.101.1.1.2.3
                fkSystemControlTimer OBJECT-TYPE
                        SYNTAX Gauge32
                        MAX-ACCESS read-write
                        STATUS current
                        DESCRIPTION
                                "Description"
                        ::= { fkSystemBaseControl 3 }

                
                -- 1.3.6.1.4.1.10428 9 1.101.1.1.2.4
                fkSystemControlTimeStamp OBJECT-TYPE
                        SYNTAX TimeTicks
                        MAX-ACCESS read-only
                        STATUS current
                        DESCRIPTION
                                "Description"
                        ::= { fkSystemBaseControl 4 }

                
                -- 1.3.6.1.4.1.10428 9 1.101.1.1.2.5
                fkSystemControlReqResult OBJECT-TYPE
                        SYNTAX FkControlRequestResultType
                        MAX-ACCESS read-only
                        STATUS current
                        DESCRIPTION
                                "Description"
                        ::= { fkSystemBaseControl 5 }

                
                -- 1.3.6.1.4.1.10428 9 1.101.1.1.2.6
                fkSystemControlHostName OBJECT-TYPE
                        SYNTAX OCTET STRING
                        MAX-ACCESS read-write
                        STATUS current
                        DESCRIPTION
                                "Description"
                        ::= { fkSystemBaseControl 6 }

                
                -- 1.3.6.1.4.1.10428 9 1.101.1.1.2.7
                fkSystemControlCPUThreshold OBJECT-TYPE
                        SYNTAX INTEGER (20..100)
                        MAX-ACCESS read-write
                        STATUS current
                        DESCRIPTION
                                "Description"
                        ::= { fkSystemBaseControl 7 }

                
                -- 1.3.6.1.4.1.10428 9 1.101.1.1.2.8
                fkSystemControlCPUInterval OBJECT-TYPE
                        SYNTAX INTEGER (5 | 60 | 600)
                        MAX-ACCESS read-write
                        STATUS current
                        DESCRIPTION
                                "Description"
                        ::= { fkSystemBaseControl 8 }

                
                -- 1.3.6.1.4.1.10428 9 1.101.1.1.2.9
                fkSystemControlDefaultOS OBJECT-TYPE
                        SYNTAX INTEGER
                                {
                                os1(1),
                                os2(2)
                                }
                        MAX-ACCESS read-write
                        STATUS current
                        DESCRIPTION
                                "Description"
                        ::= { fkSystemBaseControl 9 }

                
                -- 1.3.6.1.4.1.10428 9 1.101.1.1.2.10
                fkSystemControlClock OBJECT-TYPE
                        SYNTAX OCTET STRING
                        MAX-ACCESS read-write
                        STATUS current
                        DESCRIPTION
                                "Description"
                        ::= { fkSystemBaseControl 10 }

                
                -- 1.3.6.1.4.1.10428 9 1.101.1.1.2.11
                fkSystemControlTimezone OBJECT-TYPE
                        SYNTAX OCTET STRING
                        MAX-ACCESS read-write
                        STATUS current
                        DESCRIPTION
                                "Description"
                        ::= { fkSystemBaseControl 11 }

                
                -- 1.3.6.1.4.1.10428 9 1.101.1.1.2.12
                fkSystemControlDNSDomainName OBJECT-TYPE
                        SYNTAX OCTET STRING
                        MAX-ACCESS read-write
                        STATUS current
                        DESCRIPTION
                                "Description"
                        ::= { fkSystemBaseControl 12 }

                
                -- 1.3.6.1.4.1.10428 9 1.101.1.1.2.13
                fkSystemControlInitBanner OBJECT-TYPE
                        SYNTAX OCTET STRING
                        MAX-ACCESS read-write
                        STATUS current
                        DESCRIPTION
                                "Description"
                        ::= { fkSystemBaseControl 13 }

                
                -- 1.3.6.1.4.1.10428 9 1.101.1.1.2.14
                fkSystemControlSuccessBanner OBJECT-TYPE
                        SYNTAX OCTET STRING
                        MAX-ACCESS read-write
                        STATUS current
                        DESCRIPTION
                                "Description"
                        ::= { fkSystemBaseControl 14 }

                
                -- 1.3.6.1.4.1.10428 9 1.101.1.1.2.15
                fkSystemControlFailBanner OBJECT-TYPE
                        SYNTAX OCTET STRING
                        MAX-ACCESS read-write
                        STATUS current
                        DESCRIPTION
                                "Description"
                        ::= { fkSystemBaseControl 15 }

                
                -- 1.3.6.1.4.1.10428 9 1.101.1.1.2.16
                fkSystemControlSyslogState OBJECT-TYPE
                        SYNTAX INTEGER
                                {
                                notAvailable(-2),
                                stop(0),
                                start(1)
                                }
                        MAX-ACCESS read-write
                        STATUS current
                        DESCRIPTION
                                "Description"
                        ::= { fkSystemBaseControl 16 }

                
                -- 1.3.6.1.4.1.10428 9 1.101.1.1.2.17
                fkSystemControlSyslogVolatileNumber OBJECT-TYPE
                        SYNTAX INTEGER
                                {
                                notAvailable(-2),
                                clearLocalVolatileHistory(0)
                                }
                        MAX-ACCESS read-write
                        STATUS current
                        DESCRIPTION
                                "Description"
                        ::= { fkSystemBaseControl 17 }

                
                -- 1.3.6.1.4.1.10428 9 1.101.1.1.2.18
                fkSystemControlSyslogNonVolatileNumber OBJECT-TYPE
                        SYNTAX INTEGER
                                {
                                notAvailable(-2),
                                clearLocalNonVolatileHistory(0)
                                }
                        MAX-ACCESS read-write
                        STATUS current
                        DESCRIPTION
                                "Description"
                        ::= { fkSystemBaseControl 18 }

                
                -- 1.3.6.1.4.1.10428 9 1.101.1.1.2.19
                fkSystemControlSyslogBindAddress OBJECT-TYPE
                        SYNTAX IpAddress
                        MAX-ACCESS read-write
                        STATUS current
                        DESCRIPTION
                                "Description"
                        ::= { fkSystemBaseControl 19 }

                
                -- 1.3.6.1.4.1.10428 9 1.101.1.1.2.20
                fkSystemControlSyslogLocalCode OBJECT-TYPE
                        SYNTAX INTEGER (-1 | 0..7)
                        MAX-ACCESS read-write
                        STATUS current
                        DESCRIPTION
                                "Description"
                        ::= { fkSystemBaseControl 20 }

                
                -- 1.3.6.1.4.1.10428 9 1.101.1.1.2.21
                fkSystemControlSSHState OBJECT-TYPE
                        SYNTAX INTEGER
                                {
                                disable(0),
                                enable(1)
                                }
                        MAX-ACCESS read-write
                        STATUS current
                        DESCRIPTION
                                "Description"
                        ::= { fkSystemBaseControl 21 }

                
                -- 1.3.6.1.4.1.10428 9 1.101.1.1.2.22
                fkSystemControlNTPState OBJECT-TYPE
                        SYNTAX INTEGER
                                {
                                disable(0),
                                ntp(1),
                                sntp(2)
                                }
                        MAX-ACCESS read-write
                        STATUS current
                        DESCRIPTION
                                "Description"
                        ::= { fkSystemBaseControl 22 }

                
                -- 1.3.6.1.4.1.10428 9 1.101.1.1.2.23
                fkSystemControlOSUpgradeNumber OBJECT-TYPE
                        SYNTAX INTEGER
                                {
                                os1(1),
                                os2(2)
                                }
                        MAX-ACCESS read-write
                        STATUS current
                        DESCRIPTION
                                "Description"
                        ::= { fkSystemBaseControl 23 }

                
                -- 1.3.6.1.4.1.10428 9 1.101.1.1.2.24
                fkSystemControlServerAddress OBJECT-TYPE
                        SYNTAX IpAddress
                        MAX-ACCESS read-write
                        STATUS current
                        DESCRIPTION
                                "Description"
                        ::= { fkSystemBaseControl 24 }

                
                -- 1.3.6.1.4.1.10428 9 1.101.1.1.2.25
                fkSystemControlUpDownFlag OBJECT-TYPE
                        SYNTAX INTEGER
                                {
                                upload(0),
                                download(1)
                                }
                        MAX-ACCESS read-write
                        STATUS current
                        DESCRIPTION
                                "Description"
                        ::= { fkSystemBaseControl 25 }

                
                -- 1.3.6.1.4.1.10428 9 1.101.1.1.2.26
                fkSystemControlUserID OBJECT-TYPE
                        SYNTAX OCTET STRING
                        MAX-ACCESS read-write
                        STATUS current
                        DESCRIPTION
                                "Description"
                        ::= { fkSystemBaseControl 26 }

                
                -- 1.3.6.1.4.1.10428 9 1.101.1.1.2.27
                fkSystemControlPassword OBJECT-TYPE
                        SYNTAX OCTET STRING
                        MAX-ACCESS read-write
                        STATUS current
                        DESCRIPTION
                                "Description"
                        ::= { fkSystemBaseControl 27 }

                
                -- 1.3.6.1.4.1.10428 9 1.101.1.1.2.28
                fkSystemControlFileName OBJECT-TYPE
                        SYNTAX OCTET STRING
                        MAX-ACCESS read-write
                        STATUS current
                        DESCRIPTION
                                "Description"
                        ::= { fkSystemBaseControl 28 }

                
                -- 1.3.6.1.4.1.10428 9 1.101.1.1.2.29
                fkSystemControlBackupFlag OBJECT-TYPE
                        SYNTAX INTEGER
                                {
                                writeMemory(1),
                                restoreFactoryDefault(2)
                                }
                        MAX-ACCESS read-write
                        STATUS current
                        DESCRIPTION
                                "Description"
                        ::= { fkSystemBaseControl 29 }

                
                -- 1.3.6.1.4.1.10428 9 1.101.1.1.2.30
                fkSystemControlReloadOS OBJECT-TYPE
                        SYNTAX INTEGER
                                {
                                notAvailable(0),
                                os1(1),
                                os2(2)
                                }
                        MAX-ACCESS read-write
                        STATUS current
                        DESCRIPTION
                                "Description."
                        ::= { fkSystemBaseControl 30 }

                
                -- 1.3.6.1.4.1.10428 9 1.101.1.1.2.31
                fkSystemControlBackupInterval OBJECT-TYPE
                        SYNTAX Integer32
                        MAX-ACCESS read-write
                        STATUS current
                        DESCRIPTION
                                "Description."
                        ::= { fkSystemBaseControl 31 }

                
                -- 1.3.6.1.4.1.10428 9 1.101.1.1.2.32
                fkSystemControlDhcpActivity OBJECT-TYPE
                        SYNTAX INTEGER
                                {
                                disable(0),
                                enable(1)
                                }
                        MAX-ACCESS read-write
                        STATUS current
                        DESCRIPTION
                                "The activity of DHCP daemon."
                        ::= { fkSystemBaseControl 32 }

                
                -- 1.3.6.1.4.1.10428 9 1.101.1.1.2.33
                fkSystemControlDefaultTTL OBJECT-TYPE
                        SYNTAX INTEGER (32..255)
                        MAX-ACCESS read-write
                        STATUS current
                        DESCRIPTION
                                "The default ttl."
                        ::= { fkSystemBaseControl 33 }

                
                -- 1.3.6.1.4.1.10428 9 1.101.1.1.2.34
                fkSystemControlSyslogVolatileSize OBJECT-TYPE
                        SYNTAX INTEGER (1..2048)
                        MAX-ACCESS read-write
                        STATUS current
                        DESCRIPTION
                                "Description."
                        ::= { fkSystemBaseControl 34 }

                
                -- 1.3.6.1.4.1.10428 9 1.101.1.1.2.35
                fkSystemControlSyslogBindInterfaceName OBJECT-TYPE
                        SYNTAX OCTET STRING
                        MAX-ACCESS read-write
                        STATUS current
                        DESCRIPTION
                                "Description."
                        ::= { fkSystemBaseControl 35 }

                
                -- 1.3.6.1.4.1.10428 9 1.101.1.1.2.36
                fkSystemControlSrcPort OBJECT-TYPE
                        SYNTAX INTEGER (1..255)
                        MAX-ACCESS read-write
                        STATUS current
                        DESCRIPTION
                                "The source bridge port
                                "
                        ::= { fkSystemBaseControl 36 }

                
                -- 1.3.6.1.4.1.10428 9 1.101.1.1.2.37
                fkSystemControlDstPort OBJECT-TYPE
                        SYNTAX INTEGER (1..255)
                        MAX-ACCESS read-write
                        STATUS current
                        DESCRIPTION
                                "The destination bridge port"
                        ::= { fkSystemBaseControl 37 }

                
                -- 1.3.6.1.4.1.10428 9 1.101.1.1.2.38
                fkSystemControlSessionTime OBJECT-TYPE
                        SYNTAX INTEGER (60..600)
                        MAX-ACCESS read-write
                        STATUS current
                        DESCRIPTION
                                "Description."
                        ::= { fkSystemBaseControl 38 }

                
                -- 1.3.6.1.4.1.10428 9 1.101.1.1.2.39
                fkSystemControlExecTimeout OBJECT-TYPE
                        SYNTAX INTEGER (0..2147519)
                        MAX-ACCESS read-write
                        STATUS current
                        DESCRIPTION
                                "Description."
                        ::= { fkSystemBaseControl 39 }

                
                -- 1.3.6.1.4.1.10428 9 1.101.1.1.2.40
                fkSystemControlWatchdogStatus OBJECT-TYPE
                        SYNTAX INTEGER
                                {
                                enable(1),
                                disable(2)
                                }
                        MAX-ACCESS read-write
                        STATUS current
                        DESCRIPTION
                                "Description."
                        ::= { fkSystemBaseControl 40 }

                
                -- 1.3.6.1.4.1.10428 9 1.101.1.1.2.41
                fkSystemControlClearOs OBJECT-TYPE
                        SYNTAX Integer32
                        MAX-ACCESS read-write
                        STATUS current
                        DESCRIPTION
                                "Description."
                        ::= { fkSystemBaseControl 41 }

                
                -- 1.3.6.1.4.1.10428 9 1.101.1.1.2.42
                fkSystemControlNtpBindInterface OBJECT-TYPE
                        SYNTAX OCTET STRING
                        MAX-ACCESS read-write
                        STATUS current
                        DESCRIPTION
                                "Description."
                        ::= { fkSystemBaseControl 42 }

                
                -- 1.3.6.1.4.1.10428 9 1.101.1.1.2.43
                fkSystemControlFtpBindInterface OBJECT-TYPE
                        SYNTAX OCTET STRING
                        MAX-ACCESS read-write
                        STATUS current
                        DESCRIPTION
                                "Description."
                        ::= { fkSystemBaseControl 43 }

                
                -- 1.3.6.1.4.1.10428 9 1.101.1.1.2.44
                fkSystemControlSyslogVolMaxLine OBJECT-TYPE
                        SYNTAX INTEGER (8..16384)
                        MAX-ACCESS read-write
                        STATUS current
                        DESCRIPTION
                                "Syslog volatile max line.
                                (Supported only model 5924N)"
                        ::= { fkSystemBaseControl 44 }

                
                -- 1.3.6.1.4.1.10428 9 1.101.1.1.2.45
                fkSystemControlTempHighThreshold OBJECT-TYPE
                        SYNTAX Integer32
                        MAX-ACCESS read-write
                        STATUS current
                        DESCRIPTION
                                "Description."
                        ::= { fkSystemBaseControl 45 }

                
                -- 1.3.6.1.4.1.10428 9 1.101.1.1.2.46
                fkSystemControlTempLowThreshold OBJECT-TYPE
                        SYNTAX Integer32
                        MAX-ACCESS read-write
                        STATUS current
                        DESCRIPTION
                                "Description."
                        ::= { fkSystemBaseControl 46 }

                
                -- 1.3.6.1.4.1.10428 9 1.101.1.1.2.47
                fkSystemControlMemThreshold OBJECT-TYPE
                        SYNTAX INTEGER (20..100)
                        MAX-ACCESS read-write
                        STATUS current
                        DESCRIPTION
                                "Description."
                        ::= { fkSystemBaseControl 47 }

                
                -- 1.3.6.1.4.1.10428 9 1.101.1.1.2.48
                fkSystemControlLowCPUThreshold OBJECT-TYPE
                        SYNTAX INTEGER (20..100)
                        MAX-ACCESS read-write
                        STATUS current
                        DESCRIPTION
                                "Description."
                        ::= { fkSystemBaseControl 48 }

                
                -- 1.3.6.1.4.1.10428 9 1.101.1.1.2.49
                fkSystemControlLowCPUInterval OBJECT-TYPE
                        SYNTAX INTEGER (5 | 60 | 600)
                        MAX-ACCESS read-write
                        STATUS current
                        DESCRIPTION
                                "Description."
                        ::= { fkSystemBaseControl 49 }

                
                -- 1.3.6.1.4.1.10428 9 1.101.1.1.2.50
                fkSystemControlNtpBindAddress OBJECT-TYPE
                        SYNTAX IpAddress
                        MAX-ACCESS read-write
                        STATUS current
                        DESCRIPTION
                                "The NTP client binding address."
                        ::= { fkSystemBaseControl 50 }

                
                -- 1.3.6.1.4.1.10428 9 1.101.1.1.2.51
                fkSystemControlEnablePasswdType OBJECT-TYPE
                        SYNTAX INTEGER
                                {
                                plain(1),
                                encrypt(2)
                                }
                        MAX-ACCESS read-write
                        STATUS current
                        DESCRIPTION
                                "The type of enable password of command shell.
                                plain : no encryption.
                                encrypt : encryption"
                        DEFVAL { encrypt }
                        ::= { fkSystemBaseControl 51 }

                
                -- 1.3.6.1.4.1.10428 9 1.101.1.1.2.52
                fkSystemControlEnablePasswd OBJECT-TYPE
                        SYNTAX OCTET STRING (SIZE (0..64))
                        MAX-ACCESS read-write
                        STATUS current
                        DESCRIPTION
                                "The enable password of command shell."
                        ::= { fkSystemBaseControl 52 }

                
                -- 1.3.6.1.4.1.10428 9 1.101.1.1.2.53
                fkSystemControlServicePasswdEncryption OBJECT-TYPE
                        SYNTAX INTEGER
                                {
                                enable(1),
                                disable(2)
                                }
                        MAX-ACCESS read-write
                        STATUS current
                        DESCRIPTION
                                "The encrypt system passwords"
                        DEFVAL { disable }
                        ::= { fkSystemBaseControl 53 }

                
                -- 1.3.6.1.4.1.10428 9 1.101.1.1.2.54
                fkSystemControlNtpPollInterval OBJECT-TYPE
                        SYNTAX Integer32 (6..20)
                        MAX-ACCESS read-write
                        STATUS current
                        DESCRIPTION
                                "The NTP request polling-interval"
                        ::= { fkSystemBaseControl 54 }

                
--  1.3.6.1.4.1.10428 9 1.101.1.1.2.55
                -- 1.3.6.1.4.1.10428 9 1.101.1.1.2.55
                fkSystemControlCPUDuration OBJECT-TYPE
                        SYNTAX INTEGER (5..300)
                        MAX-ACCESS read-write
                        STATUS current
                        DESCRIPTION
                                "The threshold sampling duration."
                        ::= { fkSystemBaseControl 55 }

                
--  1.3.6.1.4.1.10428 9 1.101.1.1.2.56
                -- 1.3.6.1.4.1.10428 9 1.101.1.1.2.56
                fkSystemControlLowCPUDuration OBJECT-TYPE
                        SYNTAX INTEGER (5..300)
                        MAX-ACCESS read-write
                        STATUS current
                        DESCRIPTION
                                "The threshold sampling duration."
                        ::= { fkSystemBaseControl 56 }

                
                -- 1.3.6.1.4.1.10428 9 1.101.1.1.3
                fkSystemBaseNotification OBJECT IDENTIFIER ::= { fkSystemBase 3 }

                
                -- 1.3.6.1.4.1.10428 9 1.101.1.1.3.1
                fkSystemSystemInfoProfileChanged NOTIFICATION-TYPE
                        OBJECTS { fkSystemControlRequest, fkSystemControlTimeStamp, fkSystemControlReqResult, fkSystemHostName }
                        STATUS current
                        DESCRIPTION 
                                "Description"
                        ::= { fkSystemBaseNotification 1 }

                
                -- 1.3.6.1.4.1.10428 9 1.101.1.1.3.2
                fkSystemCPUThresholdProfileChanged NOTIFICATION-TYPE
                        OBJECTS { fkSystemControlRequest, fkSystemControlTimeStamp, fkSystemControlReqResult, fkSystemCPUThreshold, fkSystemCPUInterval, 
                                fkSystemLowCPUThreshold, fkSystemLowCPUInterval }
                        STATUS current
                        DESCRIPTION 
                                "Description"
                        ::= { fkSystemBaseNotification 2 }

                
                -- 1.3.6.1.4.1.10428 9 1.101.1.1.3.3
                fkSystemDefaultOSChanged NOTIFICATION-TYPE
                        OBJECTS { fkSystemControlRequest, fkSystemControlTimeStamp, fkSystemControlReqResult, fkSystemDefaultOS }
                        STATUS current
                        DESCRIPTION 
                                "Description"
                        ::= { fkSystemBaseNotification 3 }

                
                -- 1.3.6.1.4.1.10428 9 1.101.1.1.3.4
                fkSystemRTCProfileChanged NOTIFICATION-TYPE
                        OBJECTS { fkSystemControlRequest, fkSystemControlTimeStamp, fkSystemControlReqResult, fkSystemClock, fkSystemTimezone
                                 }
                        STATUS current
                        DESCRIPTION 
                                "Description"
                        ::= { fkSystemBaseNotification 4 }

                
                -- 1.3.6.1.4.1.10428 9 1.101.1.1.3.5
                fkSystemDNSDomainNameChanged NOTIFICATION-TYPE
                        OBJECTS { fkSystemControlRequest, fkSystemControlTimeStamp, fkSystemControlReqResult, fkSystemDNSDomainName }
                        STATUS current
                        DESCRIPTION 
                                "Description"
                        ::= { fkSystemBaseNotification 5 }

                
                -- 1.3.6.1.4.1.10428 9 1.101.1.1.3.6
                fkSystemBannerProfileChanged NOTIFICATION-TYPE
                        OBJECTS { fkSystemControlRequest, fkSystemControlTimeStamp, fkSystemControlReqResult, fkSystemInitBanner, fkSystemSuccessBanner, 
                                fkSystemFailBanner }
                        STATUS current
                        DESCRIPTION 
                                "Description"
                        ::= { fkSystemBaseNotification 6 }

                
                -- 1.3.6.1.4.1.10428 9 1.101.1.1.3.7
                fkSystemSyslogProfileChanged NOTIFICATION-TYPE
                        OBJECTS { fkSystemControlRequest, fkSystemControlTimeStamp, fkSystemSyslogVolatileSize, fkSystemSyslogVolatileMaxLine, fkSystemControlReqResult, 
                                fkSystemSyslogState, fkSystemSyslogVolatileNumber, fkSystemSyslogNonVolatileNumber, fkSystemSyslogBindAddress, fkSystemSyslogLocalCode
                                 }
                        STATUS current
                        DESCRIPTION 
                                "Description"
                        ::= { fkSystemBaseNotification 7 }

                
                -- 1.3.6.1.4.1.10428 9 1.101.1.1.3.8
                fkSystemSSHStateChanged NOTIFICATION-TYPE
                        OBJECTS { fkSystemControlRequest, fkSystemControlTimeStamp, fkSystemControlReqResult, fkSystemSSHState }
                        STATUS current
                        DESCRIPTION 
                                "Description"
                        ::= { fkSystemBaseNotification 8 }

                
                -- 1.3.6.1.4.1.10428 9 1.101.1.1.3.9
                fkSystemNTPStateChanged NOTIFICATION-TYPE
                        OBJECTS { fkSystemControlRequest, fkSystemControlTimeStamp, fkSystemControlReqResult, fkSystemNTPState }
                        STATUS current
                        DESCRIPTION 
                                "Description"
                        ::= { fkSystemBaseNotification 9 }

                
                -- 1.3.6.1.4.1.10428 9 1.101.1.1.3.10
                fkSystemOSProfileChanged NOTIFICATION-TYPE
                        OBJECTS { fkSystemControlRequest, fkSystemControlTimeStamp, fkSystemControlReqResult, fkSystemControlOSUpgradeNumber }
                        STATUS current
                        DESCRIPTION 
                                "Description"
                        ::= { fkSystemBaseNotification 10 }

                
                -- 1.3.6.1.4.1.10428 9 1.101.1.1.3.11
                fkSystemBackupChanged NOTIFICATION-TYPE
                        OBJECTS { fkSystemControlRequest, fkSystemControlTimeStamp, fkSystemControlReqResult, fkSystemControlBackupFlag }
                        STATUS current
                        DESCRIPTION 
                                "Description"
                        ::= { fkSystemBaseNotification 11 }

                
                -- 1.3.6.1.4.1.10428 9 1.101.1.1.3.12
                fkSystemBackupIntervalChanged NOTIFICATION-TYPE
                        OBJECTS { fkSystemControlRequest, fkSystemControlReqResult, fkSystemControlTimeStamp, fkSystemBackupInterval }
                        STATUS current
                        DESCRIPTION 
                                "Description."
                        ::= { fkSystemBaseNotification 12 }

                
                -- 1.3.6.1.4.1.10428 9 1.101.1.1.3.13
                fkSystemDhcpActivityChanged NOTIFICATION-TYPE
                        OBJECTS { fkSystemControlRequest, fkSystemControlTimeStamp, fkSystemControlReqResult, fkSystemDhcpActivity }
                        STATUS current
                        DESCRIPTION 
                                "Description."
                        ::= { fkSystemBaseNotification 13 }

                
                -- 1.3.6.1.4.1.10428 9 1.101.1.1.3.14
                fkSystemDefaultTTLChanged NOTIFICATION-TYPE
                        OBJECTS { fkSystemControlRequest, fkSystemControlTimeStamp, fkSystemControlReqResult, fkSystemDefaultTTL }
                        STATUS current
                        DESCRIPTION 
                                "Description."
                        ::= { fkSystemBaseNotification 14 }

                
                -- 1.3.6.1.4.1.10428 9 1.101.1.1.3.15
                fkSystemSyslogBindInterfaceNameChanged NOTIFICATION-TYPE
                        OBJECTS { fkSystemControlRequest, fkSystemControlTimeStamp, fkSystemControlReqResult, fkSystemSyslogState, fkSystemSyslogBindInterfaceName
                                 }
                        STATUS current
                        DESCRIPTION 
                                "Description."
                        ::= { fkSystemBaseNotification 15 }

                
                -- 1.3.6.1.4.1.10428 9 1.101.1.1.3.16
                fkSystemSyslogBindInterfaceNameCleared NOTIFICATION-TYPE
                        OBJECTS { fkSystemControlRequest, fkSystemControlTimeStamp, fkSystemControlReqResult }
                        STATUS current
                        DESCRIPTION 
                                "Description."
                        ::= { fkSystemBaseNotification 16 }

                
                -- 1.3.6.1.4.1.10428 9 1.101.1.1.3.17
                fkSystemConfigPortMoved NOTIFICATION-TYPE
                        OBJECTS { fkSystemControlRequest, fkSystemControlTimeStamp, fkSystemControlReqResult, fkSystemControlSrcPort, fkSystemControlDstPort
                                 }
                        STATUS current
                        DESCRIPTION 
                                "Description."
                        ::= { fkSystemBaseNotification 17 }

                
                -- 1.3.6.1.4.1.10428 9 1.101.1.1.3.18
                fkSystemConfigPortCopied NOTIFICATION-TYPE
                        OBJECTS { fkSystemControlRequest, fkSystemControlTimeStamp, fkSystemControlReqResult, fkSystemControlSrcPort, fkSystemControlDstPort
                                 }
                        STATUS current
                        DESCRIPTION 
                                "Description."
                        ::= { fkSystemBaseNotification 18 }

                
                -- 1.3.6.1.4.1.10428 9 1.101.1.1.3.19
                fkSystemConfigPortCleared NOTIFICATION-TYPE
                        OBJECTS { fkSystemControlRequest, fkSystemControlTimeStamp, fkSystemControlReqResult, fkSystemControlSrcPort, fkSystemControlDstPort
                                 }
                        STATUS current
                        DESCRIPTION 
                                "Description."
                        ::= { fkSystemBaseNotification 19 }

                
                -- 1.3.6.1.4.1.10428 9 1.101.1.1.3.20
                fkSystemSessionTimeChanged NOTIFICATION-TYPE
                        OBJECTS { fkSystemControlRequest, fkSystemControlTimeStamp, fkSystemControlReqResult, fkSystemSessionTime }
                        STATUS current
                        DESCRIPTION 
                                "Description."
                        ::= { fkSystemBaseNotification 20 }

                
                -- 1.3.6.1.4.1.10428 9 1.101.1.1.3.21
                fkSystemExecTimeoutChanged NOTIFICATION-TYPE
                        OBJECTS { fkSystemControlRequest, fkSystemControlTimeStamp, fkSystemControlReqResult, fkSystemExecTimeout }
                        STATUS current
                        DESCRIPTION 
                                "Description."
                        ::= { fkSystemBaseNotification 21 }

                
                -- 1.3.6.1.4.1.10428 9 1.101.1.1.3.22
                fkSystemWatchdogStatusChanged NOTIFICATION-TYPE
                        OBJECTS { fkSystemControlRequest, fkSystemControlTimeStamp, fkSystemControlReqResult, fkSystemWatchdogStatus }
                        STATUS current
                        DESCRIPTION 
                                "Description."
                        ::= { fkSystemBaseNotification 22 }

                
                -- 1.3.6.1.4.1.10428 9 1.101.1.1.3.23
                fkSystemNosDestroyed NOTIFICATION-TYPE
                        OBJECTS { fkSystemControlRequest, fkSystemControlTimeStamp, fkSystemControlReqResult, fkSystemControlClearOs }
                        STATUS current
                        DESCRIPTION 
                                "Description."
                        ::= { fkSystemBaseNotification 23 }

                
                -- 1.3.6.1.4.1.10428 9 1.101.1.1.3.24
                fkSystemNtpBindInterfaceChanged NOTIFICATION-TYPE
                        OBJECTS { fkSystemControlRequest, fkSystemControlTimeStamp, fkSystemControlReqResult, fkSystemNtpBindInterface }
                        STATUS current
                        DESCRIPTION 
                                "Description."
                        ::= { fkSystemBaseNotification 24 }

                
                -- 1.3.6.1.4.1.10428 9 1.101.1.1.3.25
                fkSystemFtpBindInterfaceChanged NOTIFICATION-TYPE
                        OBJECTS { fkSystemControlRequest, fkSystemControlTimeStamp, fkSystemControlReqResult, fkSystemFtpBindInterface }
                        STATUS current
                        DESCRIPTION 
                                "Description."
                        ::= { fkSystemBaseNotification 25 }

                
                -- 1.3.6.1.4.1.10428 9 1.101.1.1.3.26
                fkSystemRedundancyPortChanged NOTIFICATION-TYPE
                        OBJECTS { fkSystemControlRequest, fkSystemControlTimeStamp, fkSystemControlReqResult, fkSystemControlSrcPort }
                        STATUS current
                        DESCRIPTION 
                                "Description."
                        ::= { fkSystemBaseNotification 26 }

                
                -- 1.3.6.1.4.1.10428 9 1.101.1.1.3.27
                fkRedundancyPortCleared NOTIFICATION-TYPE
                        OBJECTS { fkSystemControlRequest, fkSystemControlTimeStamp, fkSystemControlReqResult }
                        STATUS current
                        DESCRIPTION 
                                "Description."
                        ::= { fkSystemBaseNotification 27 }

                
                -- 1.3.6.1.4.1.10428 9 1.101.1.1.3.28
                fkSystemTempThresholdChanged NOTIFICATION-TYPE
                        OBJECTS { fkSystemControlRequest, fkSystemControlTimeStamp, fkSystemControlReqResult, fkSystemControlTempHighThreshold, fkSystemControlTempLowThreshold
                                 }
                        STATUS current
                        DESCRIPTION 
                                "Description."
                        ::= { fkSystemBaseNotification 28 }

                
                -- 1.3.6.1.4.1.10428 9 1.101.1.1.3.29
                fkSystemMemThresholdChanged NOTIFICATION-TYPE
                        OBJECTS { fkSystemControlRequest, fkSystemControlTimeStamp, fkSystemControlReqResult, fkSystemControlMemThreshold }
                        STATUS current
                        DESCRIPTION 
                                "Description."
                        ::= { fkSystemBaseNotification 29 }

                
                -- 1.3.6.1.4.1.10428 9 1.101.1.1.3.30
                fkSystemBootloaderProfileChanged NOTIFICATION-TYPE
                        OBJECTS { fkSystemControlRequest, fkSystemControlTimeStamp, fkSystemControlReqResult }
                        STATUS current
                        DESCRIPTION 
                                "Description"
                        ::= { fkSystemBaseNotification 30 }

                
                -- 1.3.6.1.4.1.10428 9 1.101.1.1.3.31
                fkSystemNtpBindAddressChanged NOTIFICATION-TYPE
                        OBJECTS { fkSystemControlRequest, fkSystemControlTimeStamp, fkSystemControlReqResult, fkSystemControlNtpBindAddress }
                        STATUS current
                        DESCRIPTION 
                                "Description."
                        ::= { fkSystemBaseNotification 31 }

                
                -- 1.3.6.1.4.1.10428 9 1.101.1.1.3.32
                fkSystemEnablePasswdChanged NOTIFICATION-TYPE
                        OBJECTS { fkSystemControlRequest, fkSystemControlTimeStamp, fkSystemControlReqResult, fkSystemControlEnablePasswdType, fkSystemControlEnablePasswd
                                 }
                        STATUS current
                        DESCRIPTION 
                                "Description."
                        ::= { fkSystemBaseNotification 32 }

                
                -- 1.3.6.1.4.1.10428 9 1.101.1.1.3.33
                fkSystemEnableServicePasswdEncryptionChanged NOTIFICATION-TYPE
                        OBJECTS { fkSystemControlRequest, fkSystemControlTimeStamp, fkSystemControlReqResult, fkSystemControlServicePasswdEncryption }
                        STATUS current
                        DESCRIPTION 
                                "Encrypt system passwords"
                        ::= { fkSystemBaseNotification 33 }

                
                -- 1.3.6.1.4.1.10428 9 1.101.1.1.3.34
                fkSystemPasswdRestored NOTIFICATION-TYPE
                        OBJECTS { fkSystemControlRequest, fkSystemControlTimeStamp, fkSystemControlReqResult }
                        STATUS current
                        DESCRIPTION 
                                "Description."
                        ::= { fkSystemBaseNotification 34 }

                
                -- 1.3.6.1.4.1.10428 9 1.101.1.1.3.35
                fkSystemNtpPollIntervalChanged NOTIFICATION-TYPE
                        OBJECTS { fkSystemControlRequest, fkSystemControlTimeStamp, fkSystemControlReqResult, fkSystemNtpPollnterval }
                        STATUS current
                        DESCRIPTION 
                                "Description."
                        ::= { fkSystemBaseNotification 35 }

                
                -- 1.3.6.1.4.1.10428 9 1.101.1.1.3.36
                fkSystemRestoreFactoryChanged NOTIFICATION-TYPE
                        OBJECTS { fkSystemControlRequest, fkSystemControlTimeStamp, fkSystemControlReqResult }
                        STATUS current
                        DESCRIPTION 
                                "The command of restory factory."
                        ::= { fkSystemBaseNotification 36 }

                
                -- 1.3.6.1.4.1.10428 9 1.101.1.1.4
                fkSystemBaseSlotInfo OBJECT IDENTIFIER ::= { fkSystemBase 4 }

                
                -- 1.3.6.1.4.1.10428 9 1.101.1.1.4.1
                fkSystemBaseSlotInfoTable OBJECT-TYPE
                        SYNTAX SEQUENCE OF FkSystemBaseSlotInfoEntry
                        MAX-ACCESS not-accessible
                        STATUS current
                        DESCRIPTION
                                "Description."
                        ::= { fkSystemBaseSlotInfo 1 }

                
                -- 1.3.6.1.4.1.10428 9 1.101.1.1.4.1.1
                fkSystemBaseSlotInfoEntry OBJECT-TYPE
                        SYNTAX FkSystemBaseSlotInfoEntry
                        MAX-ACCESS not-accessible
                        STATUS current
                        DESCRIPTION
                                "Description."
                        INDEX { fkSystemSlotIndex }
                        ::= { fkSystemBaseSlotInfoTable 1 }

                
                FkSystemBaseSlotInfoEntry ::=
                        SEQUENCE { 
                                fkSystemSlotIndex
                                        Integer32,
                                fkSystemSlotUptime
                                        TimeTicks,
                                fkSystemSlotModelName
                                        OCTET STRING,
                                fkSystemSlotSerialNumber
                                        OCTET STRING,
                                fkSystemSlotHWVersion
                                        OCTET STRING,
                                fkSystemSlotBLVersion
                                        OCTET STRING,
                                fkSystemSlotSWCompatibility
                                        OCTET STRING,
                                fkSystemSlotOSVersion
                                        OCTET STRING,
                                fkSystemSlotMacAddress
                                        OCTET STRING,
                                fkSystemSlotCPULoadAll
                                        OCTET STRING,
                                fkSystemSlotCPULoadInterrupt
                                        OCTET STRING,
                                fkSystemSlotMemoryTotal
                                        Unsigned32,
                                fkSystemSlotMemoryFree
                                        Unsigned32,
                                fkSystemSlotMemoryShared
                                        Unsigned32,
                                fkSystemSlotMemoryBuffers
                                        Unsigned32,
                                fkSystemSlotMemoryCached
                                        Unsigned32,
                                fkSystemSlotMemorySwapTotal
                                        Unsigned32,
                                fkSystemSlotMemorySwapFree
                                        Unsigned32,
                                fkSystemSlotBootReason
                                        INTEGER,
                                fkSystemSlotBootTime
                                        Unsigned32,
                                fkSystemSlotVoltage
                                        Unsigned32
                         }

                -- 1.3.6.1.4.1.10428 9 1.101.1.1.4.1.1.1
                fkSystemSlotIndex OBJECT-TYPE
                        SYNTAX Integer32 (0..64)
                        MAX-ACCESS read-only
                        STATUS current
                        DESCRIPTION
                                "Description."
                        ::= { fkSystemBaseSlotInfoEntry 1 }

                
                -- 1.3.6.1.4.1.10428 9 1.101.1.1.4.1.1.2
                fkSystemSlotUptime OBJECT-TYPE
                        SYNTAX TimeTicks
                        MAX-ACCESS read-only
                        STATUS current
                        DESCRIPTION
                                "Description."
                        ::= { fkSystemBaseSlotInfoEntry 2 }

                
                -- 1.3.6.1.4.1.10428 9 1.101.1.1.4.1.1.3
                fkSystemSlotModelName OBJECT-TYPE
                        SYNTAX OCTET STRING
                        MAX-ACCESS read-only
                        STATUS current
                        DESCRIPTION
                                "Description."
                        ::= { fkSystemBaseSlotInfoEntry 3 }

                
                -- 1.3.6.1.4.1.10428 9 1.101.1.1.4.1.1.4
                fkSystemSlotSerialNumber OBJECT-TYPE
                        SYNTAX OCTET STRING
                        MAX-ACCESS read-only
                        STATUS current
                        DESCRIPTION
                                "Description."
                        ::= { fkSystemBaseSlotInfoEntry 4 }

                
                -- 1.3.6.1.4.1.10428 9 1.101.1.1.4.1.1.5
                fkSystemSlotHWVersion OBJECT-TYPE
                        SYNTAX OCTET STRING
                        MAX-ACCESS read-only
                        STATUS current
                        DESCRIPTION
                                "Description."
                        ::= { fkSystemBaseSlotInfoEntry 5 }

                
                -- 1.3.6.1.4.1.10428 9 1.101.1.1.4.1.1.6
                fkSystemSlotBLVersion OBJECT-TYPE
                        SYNTAX OCTET STRING
                        MAX-ACCESS read-only
                        STATUS current
                        DESCRIPTION
                                "Description."
                        ::= { fkSystemBaseSlotInfoEntry 6 }

                
                -- 1.3.6.1.4.1.10428 9 1.101.1.1.4.1.1.7
                fkSystemSlotSWCompatibility OBJECT-TYPE
                        SYNTAX OCTET STRING
                        MAX-ACCESS read-only
                        STATUS current
                        DESCRIPTION
                                "Description."
                        ::= { fkSystemBaseSlotInfoEntry 7 }

                
                -- 1.3.6.1.4.1.10428 9 1.101.1.1.4.1.1.8
                fkSystemSlotOSVersion OBJECT-TYPE
                        SYNTAX OCTET STRING
                        MAX-ACCESS read-only
                        STATUS current
                        DESCRIPTION
                                "Description."
                        ::= { fkSystemBaseSlotInfoEntry 8 }

                
                -- 1.3.6.1.4.1.10428 9 1.101.1.1.4.1.1.9
                fkSystemSlotMacAddress OBJECT-TYPE
                        SYNTAX OCTET STRING
                        MAX-ACCESS read-only
                        STATUS current
                        DESCRIPTION
                                "Description."
                        ::= { fkSystemBaseSlotInfoEntry 9 }

                
                -- 1.3.6.1.4.1.10428 9 1.101.1.1.4.1.1.10
                fkSystemSlotCPULoadAll OBJECT-TYPE
                        SYNTAX OCTET STRING
                        MAX-ACCESS read-only
                        STATUS current
                        DESCRIPTION
                                "Description."
                        ::= { fkSystemBaseSlotInfoEntry 10 }

                
                -- 1.3.6.1.4.1.10428 9 1.101.1.1.4.1.1.11
                fkSystemSlotCPULoadInterrupt OBJECT-TYPE
                        SYNTAX OCTET STRING
                        MAX-ACCESS read-only
                        STATUS current
                        DESCRIPTION
                                "Description."
                        ::= { fkSystemBaseSlotInfoEntry 11 }

                
                -- 1.3.6.1.4.1.10428 9 1.101.1.1.4.1.1.12
                fkSystemSlotMemoryTotal OBJECT-TYPE
                        SYNTAX Unsigned32
                        MAX-ACCESS read-only
                        STATUS current
                        DESCRIPTION
                                "Description."
                        ::= { fkSystemBaseSlotInfoEntry 12 }

                
                -- 1.3.6.1.4.1.10428 9 1.101.1.1.4.1.1.13
                fkSystemSlotMemoryFree OBJECT-TYPE
                        SYNTAX Unsigned32
                        MAX-ACCESS read-only
                        STATUS current
                        DESCRIPTION
                                "Description."
                        ::= { fkSystemBaseSlotInfoEntry 13 }

                
                -- 1.3.6.1.4.1.10428 9 1.101.1.1.4.1.1.14
                fkSystemSlotMemoryShared OBJECT-TYPE
                        SYNTAX Unsigned32
                        MAX-ACCESS read-only
                        STATUS current
                        DESCRIPTION
                                "Description."
                        ::= { fkSystemBaseSlotInfoEntry 14 }

                
                -- 1.3.6.1.4.1.10428 9 1.101.1.1.4.1.1.15
                fkSystemSlotMemoryBuffers OBJECT-TYPE
                        SYNTAX Unsigned32
                        MAX-ACCESS read-only
                        STATUS current
                        DESCRIPTION
                                "Description."
                        ::= { fkSystemBaseSlotInfoEntry 15 }

                
                -- 1.3.6.1.4.1.10428 9 1.101.1.1.4.1.1.16
                fkSystemSlotMemoryCached OBJECT-TYPE
                        SYNTAX Unsigned32
                        MAX-ACCESS read-only
                        STATUS current
                        DESCRIPTION
                                "Description."
                        ::= { fkSystemBaseSlotInfoEntry 16 }

                
                -- 1.3.6.1.4.1.10428 9 1.101.1.1.4.1.1.17
                fkSystemSlotMemorySwapTotal OBJECT-TYPE
                        SYNTAX Unsigned32
                        MAX-ACCESS read-only
                        STATUS current
                        DESCRIPTION
                                "Description."
                        ::= { fkSystemBaseSlotInfoEntry 17 }

                
                -- 1.3.6.1.4.1.10428 9 1.101.1.1.4.1.1.18
                fkSystemSlotMemorySwapFree OBJECT-TYPE
                        SYNTAX Unsigned32
                        MAX-ACCESS read-only
                        STATUS current
                        DESCRIPTION
                                "Description."
                        ::= { fkSystemBaseSlotInfoEntry 18 }

                
                -- 1.3.6.1.4.1.10428 9 1.101.1.1.4.1.1.19
                fkSystemSlotBootReason OBJECT-TYPE
                        SYNTAX INTEGER
                                {
                                error(0),
                                powerboot(1),
                                panic(2),
                                swreboot(3),
                                lowmemory(4),
                                watchdog(5),
                                swWatchdog(9),
                                swrebootBySfu(11)
                                }
                        MAX-ACCESS read-only
                        STATUS current
                        DESCRIPTION
                                "Description."
                        ::= { fkSystemBaseSlotInfoEntry 19 }

                
                -- 1.3.6.1.4.1.10428 9 1.101.1.1.4.1.1.20
                fkSystemSlotBootTime OBJECT-TYPE
                        SYNTAX Unsigned32
                        UNITS "1 second"
                        MAX-ACCESS read-only
                        STATUS current
                        DESCRIPTION
                                "Description."
                        ::= { fkSystemBaseSlotInfoEntry 20 }

                
                -- 1.3.6.1.4.1.10428 9 1.101.1.1.4.1.1.21
                fkSystemSlotVoltage OBJECT-TYPE
                        SYNTAX Unsigned32
                        UNITS "0.1 v"
                        MAX-ACCESS read-only
                        STATUS current
                        DESCRIPTION
                                "Description."
                        ::= { fkSystemBaseSlotInfoEntry 21 }

                
                -- 1.3.6.1.4.1.10428 9 1.101.1.2
                fkDNSServer OBJECT IDENTIFIER ::= { fkSystemMaintenance 2 }

                
                -- 1.3.6.1.4.1.10428 9 1.101.1.2.1
                fkDNSServerTable OBJECT-TYPE
                        SYNTAX SEQUENCE OF FkDNSServerEntry
                        MAX-ACCESS not-accessible
                        STATUS current
                        DESCRIPTION
                                "Description."
                        ::= { fkDNSServer 1 }

                
                -- 1.3.6.1.4.1.10428 9 1.101.1.2.1.1
                fkDNSServerEntry OBJECT-TYPE
                        SYNTAX FkDNSServerEntry
                        MAX-ACCESS not-accessible
                        STATUS current
                        DESCRIPTION
                                "Description."
                        INDEX { fkDNSServerIndex }
                        ::= { fkDNSServerTable 1 }

                
                FkDNSServerEntry ::=
                        SEQUENCE { 
                                fkDNSServerIndex
                                        Integer32,
                                fkDNSServerName
                                        IpAddress
                         }

                -- 1.3.6.1.4.1.10428 9 1.101.1.2.1.1.1
                fkDNSServerIndex OBJECT-TYPE
                        SYNTAX Integer32 (1..65535)
                        MAX-ACCESS read-write
                        STATUS current
                        DESCRIPTION
                                "DNS server index"
                        ::= { fkDNSServerEntry 1 }

                
                -- 1.3.6.1.4.1.10428 9 1.101.1.2.1.1.2
                fkDNSServerName OBJECT-TYPE
                        SYNTAX IpAddress
                        MAX-ACCESS read-only
                        STATUS current
                        DESCRIPTION
                                "Registered DNS server name"
                        ::= { fkDNSServerEntry 2 }

                
                -- 1.3.6.1.4.1.10428 9 1.101.1.2.2
                fkDNSServerControl OBJECT IDENTIFIER ::= { fkDNSServer 2 }

                
                -- 1.3.6.1.4.1.10428 9 1.101.1.2.2.1
                fkDNSServerControlRequest OBJECT-TYPE
                        SYNTAX INTEGER
                                {
                                createDNSServer(1),
                                destroyDNSServer(2)
                                }
                        MAX-ACCESS read-write
                        STATUS current
                        DESCRIPTION
                                "Description"
                        ::= { fkDNSServerControl 1 }

                
                -- 1.3.6.1.4.1.10428 9 1.101.1.2.2.2
                fkDNSServerControlStatus OBJECT-TYPE
                        SYNTAX FkControlStatusType
                        MAX-ACCESS read-only
                        STATUS current
                        DESCRIPTION
                                "Description"
                        ::= { fkDNSServerControl 2 }

                
                -- 1.3.6.1.4.1.10428 9 1.101.1.2.2.3
                fkDNSServerControlTimer OBJECT-TYPE
                        SYNTAX Gauge32
                        MAX-ACCESS read-write
                        STATUS current
                        DESCRIPTION
                                "Description"
                        ::= { fkDNSServerControl 3 }

                
                -- 1.3.6.1.4.1.10428 9 1.101.1.2.2.4
                fkDNSServerControlTImeStamp OBJECT-TYPE
                        SYNTAX TimeTicks
                        MAX-ACCESS read-only
                        STATUS current
                        DESCRIPTION
                                "Description"
                        ::= { fkDNSServerControl 4 }

                
                -- 1.3.6.1.4.1.10428 9 1.101.1.2.2.5
                fkDNSServerControlReqResult OBJECT-TYPE
                        SYNTAX FkControlRequestResultType
                        MAX-ACCESS read-only
                        STATUS current
                        DESCRIPTION
                                "Description"
                        ::= { fkDNSServerControl 5 }

                
                -- 1.3.6.1.4.1.10428 9 1.101.1.2.2.6
                fkDNSServerControlIndex OBJECT-TYPE
                        SYNTAX Integer32
                        MAX-ACCESS read-write
                        STATUS current
                        DESCRIPTION
                                "This is corresponded to fkDNSServerIndex."
                        ::= { fkDNSServerControl 6 }

                
                -- 1.3.6.1.4.1.10428 9 1.101.1.2.2.7
                fkDNSServerControlName OBJECT-TYPE
                        SYNTAX IpAddress
                        MAX-ACCESS read-write
                        STATUS current
                        DESCRIPTION
                                "This is corresponded to fkDNSServerName."
                        ::= { fkDNSServerControl 7 }

                
                -- 1.3.6.1.4.1.10428 9 1.101.1.2.3
                fkDNSServerNotification OBJECT IDENTIFIER ::= { fkDNSServer 3 }

                
                -- 1.3.6.1.4.1.10428 9 1.101.1.2.3.1
                fkDNSServerCreated NOTIFICATION-TYPE
                        OBJECTS { fkDNSServerControlRequest, fkDNSServerControlReqResult, fkDNSServerControlTImeStamp, fkDNSServerName }
                        STATUS current
                        DESCRIPTION 
                                "Description"
                        ::= { fkDNSServerNotification 1 }

                
                -- 1.3.6.1.4.1.10428 9 1.101.1.2.3.2
                fkDNSServerDestroyed NOTIFICATION-TYPE
                        OBJECTS { fkDNSServerControlRequest, fkDNSServerControlReqResult, fkDNSServerControlTImeStamp, fkDNSServerControlIndex }
                        STATUS current
                        DESCRIPTION 
                                "Description"
                        ::= { fkDNSServerNotification 2 }

                
                -- 1.3.6.1.4.1.10428 9 1.101.1.3
                fkLogin OBJECT IDENTIFIER ::= { fkSystemMaintenance 3 }

                
                -- 1.3.6.1.4.1.10428 9 1.101.1.3.1
                fkLoginTable OBJECT-TYPE
                        SYNTAX SEQUENCE OF FkLoginEntry
                        MAX-ACCESS not-accessible
                        STATUS current
                        DESCRIPTION
                                "Description."
                        ::= { fkLogin 1 }

                
                -- 1.3.6.1.4.1.10428 9 1.101.1.3.1.1
                fkLoginEntry OBJECT-TYPE
                        SYNTAX FkLoginEntry
                        MAX-ACCESS not-accessible
                        STATUS current
                        DESCRIPTION
                                "Description."
                        INDEX { fkLoginIndex }
                        ::= { fkLoginTable 1 }

                
                FkLoginEntry ::=
                        SEQUENCE { 
                                fkLoginIndex
                                        Integer32,
                                fkLoginUser
                                        OCTET STRING,
                                fkLoginTTY
                                        OCTET STRING,
                                fkLoginRemote
                                        OCTET STRING,
                                fkLoginTime
                                        OCTET STRING
                         }

                -- 1.3.6.1.4.1.10428 9 1.101.1.3.1.1.1
                fkLoginIndex OBJECT-TYPE
                        SYNTAX Integer32 (1..65536)
                        MAX-ACCESS read-only
                        STATUS current
                        DESCRIPTION
                                "Logined user's index"
                        ::= { fkLoginEntry 1 }

                
                -- 1.3.6.1.4.1.10428 9 1.101.1.3.1.1.2
                fkLoginUser OBJECT-TYPE
                        SYNTAX OCTET STRING
                        MAX-ACCESS read-only
                        STATUS current
                        DESCRIPTION
                                "Logined user name"
                        ::= { fkLoginEntry 2 }

                
                -- 1.3.6.1.4.1.10428 9 1.101.1.3.1.1.3
                fkLoginTTY OBJECT-TYPE
                        SYNTAX OCTET STRING
                        MAX-ACCESS read-only
                        STATUS current
                        DESCRIPTION
                                "The login user's terminal"
                        ::= { fkLoginEntry 3 }

                
                -- 1.3.6.1.4.1.10428 9 1.101.1.3.1.1.4
                fkLoginRemote OBJECT-TYPE
                        SYNTAX OCTET STRING
                        MAX-ACCESS read-only
                        STATUS current
                        DESCRIPTION
                                "Remote host"
                        ::= { fkLoginEntry 4 }

                
                -- 1.3.6.1.4.1.10428 9 1.101.1.3.1.1.5
                fkLoginTime OBJECT-TYPE
                        SYNTAX OCTET STRING
                        MAX-ACCESS read-only
                        STATUS current
                        DESCRIPTION
                                "Logined time."
                        ::= { fkLoginEntry 5 }

                
                -- 1.3.6.1.4.1.10428 9 1.101.1.4
                fkBackup OBJECT IDENTIFIER ::= { fkSystemMaintenance 4 }

                
                -- 1.3.6.1.4.1.10428 9 1.101.1.4.1
                fkBackupTable OBJECT-TYPE
                        SYNTAX SEQUENCE OF FkBackupEntry
                        MAX-ACCESS not-accessible
                        STATUS current
                        DESCRIPTION
                                "Description."
                        ::= { fkBackup 1 }

                
                -- 1.3.6.1.4.1.10428 9 1.101.1.4.1.1
                fkBackupEntry OBJECT-TYPE
                        SYNTAX FkBackupEntry
                        MAX-ACCESS not-accessible
                        STATUS current
                        DESCRIPTION
                                "Description."
                        INDEX { fkBackupConfigFile }
                        ::= { fkBackupTable 1 }

                
                FkBackupEntry ::=
                        SEQUENCE { 
                                fkBackupConfigFile
                                        OCTET STRING
                         }

                -- 1.3.6.1.4.1.10428 9 1.101.1.4.1.1.1
                fkBackupConfigFile OBJECT-TYPE
                        SYNTAX OCTET STRING
                        MAX-ACCESS read-only
                        STATUS current
                        DESCRIPTION
                                "Copied configuration file name'running-config' is reserved config name."
                        ::= { fkBackupEntry 1 }

                
                -- 1.3.6.1.4.1.10428 9 1.101.1.4.2
                fkBackupControl OBJECT IDENTIFIER ::= { fkBackup 2 }

                
                -- 1.3.6.1.4.1.10428 9 1.101.1.4.2.1
                fkBackupControlRequest OBJECT-TYPE
                        SYNTAX INTEGER
                                {
                                createBackup(1),
                                destroyBackup(2),
                                setBackupToRemote(3),
                                setBackupConfigBySftp(4),
                                setBackupConfigByScp(5),
                                setBackupKeyBySftp(6),
                                setBackupKeyByScp(7)
                                }
                        MAX-ACCESS read-write
                        STATUS current
                        DESCRIPTION
                                "Description"
                        ::= { fkBackupControl 1 }

                
                -- 1.3.6.1.4.1.10428 9 1.101.1.4.2.2
                fkBackupControlStatus OBJECT-TYPE
                        SYNTAX FkControlStatusType
                        MAX-ACCESS read-only
                        STATUS current
                        DESCRIPTION
                                "Description"
                        ::= { fkBackupControl 2 }

                
                -- 1.3.6.1.4.1.10428 9 1.101.1.4.2.3
                fkBackupControlTimer OBJECT-TYPE
                        SYNTAX Gauge32
                        MAX-ACCESS read-write
                        STATUS current
                        DESCRIPTION
                                "Description"
                        ::= { fkBackupControl 3 }

                
                -- 1.3.6.1.4.1.10428 9 1.101.1.4.2.4
                fkBackupControlTimeStamp OBJECT-TYPE
                        SYNTAX TimeTicks
                        MAX-ACCESS read-only
                        STATUS current
                        DESCRIPTION
                                "Description"
                        ::= { fkBackupControl 4 }

                
                -- 1.3.6.1.4.1.10428 9 1.101.1.4.2.5
                fkBackupControlReqResult OBJECT-TYPE
                        SYNTAX FkControlRequestResultType
                        MAX-ACCESS read-only
                        STATUS current
                        DESCRIPTION
                                "Description"
                        ::= { fkBackupControl 5 }

                
                -- 1.3.6.1.4.1.10428 9 1.101.1.4.2.6
                fkBackupControlCreateMode OBJECT-TYPE
                        SYNTAX INTEGER
                                {
                                backupFromRunning(1),
                                backupFromLocal(2),
                                backupFromRemote(3)
                                }
                        MAX-ACCESS read-write
                        STATUS current
                        DESCRIPTION
                                "Description"
                        ::= { fkBackupControl 6 }

                
                -- 1.3.6.1.4.1.10428 9 1.101.1.4.2.7
                fkBackupControlServerIP OBJECT-TYPE
                        SYNTAX IpAddress
                        MAX-ACCESS read-write
                        STATUS current
                        DESCRIPTION
                                "FTP or TFTP server's address."
                        ::= { fkBackupControl 7 }

                
                -- 1.3.6.1.4.1.10428 9 1.101.1.4.2.8
                fkBackupControlUserID OBJECT-TYPE
                        SYNTAX OCTET STRING
                        MAX-ACCESS read-write
                        STATUS current
                        DESCRIPTION
                                "User's ID of the FTP server.If this is empty string, means that the FTP server is the TFTP server."
                        ::= { fkBackupControl 8 }

                
                -- 1.3.6.1.4.1.10428 9 1.101.1.4.2.9
                fkBackupControlPassword OBJECT-TYPE
                        SYNTAX OCTET STRING
                        MAX-ACCESS read-write
                        STATUS current
                        DESCRIPTION
                                "User's password of the FTP server."
                        ::= { fkBackupControl 9 }

                
                -- 1.3.6.1.4.1.10428 9 1.101.1.4.2.10
                fkBackupControlSrcConfigFile OBJECT-TYPE
                        SYNTAX OCTET STRING
                        MAX-ACCESS read-write
                        STATUS current
                        DESCRIPTION
                                "'running-config' is reserved config name."
                        ::= { fkBackupControl 10 }

                
                -- 1.3.6.1.4.1.10428 9 1.101.1.4.2.11
                fkBackupControlDstConfigFile OBJECT-TYPE
                        SYNTAX OCTET STRING
                        MAX-ACCESS read-write
                        STATUS current
                        DESCRIPTION
                                "Descroption."
                        ::= { fkBackupControl 11 }

                
                -- 1.3.6.1.4.1.10428 9 1.101.1.4.3
                fkBackupNotification OBJECT IDENTIFIER ::= { fkBackup 3 }

                
                -- 1.3.6.1.4.1.10428 9 1.101.1.4.3.1
                fkBackupCreated NOTIFICATION-TYPE
                        OBJECTS { fkBackupControlRequest, fkBackupControlReqResult, fkBackupControlTimeStamp, fkBackupControlSrcConfigFile }
                        STATUS current
                        DESCRIPTION 
                                "Description"
                        ::= { fkBackupNotification 1 }

                
                -- 1.3.6.1.4.1.10428 9 1.101.1.4.3.2
                fkBackupDestroyed NOTIFICATION-TYPE
                        OBJECTS { fkBackupControlRequest, fkBackupControlReqResult, fkBackupControlTimeStamp, fkBackupControlSrcConfigFile }
                        STATUS current
                        DESCRIPTION 
                                "Description"
                        ::= { fkBackupNotification 2 }

                
                -- 1.3.6.1.4.1.10428 9 1.101.1.4.3.3
                fkBackupChanged NOTIFICATION-TYPE
                        OBJECTS { fkBackupControlRequest, fkBackupControlTimeStamp, fkBackupControlReqResult, fkBackupControlSrcConfigFile }
                        STATUS current
                        DESCRIPTION 
                                "Description"
                        ::= { fkBackupNotification 3 }

                
                -- 1.3.6.1.4.1.10428 9 1.101.1.4.3.4
                fkBackupConfigBySftpChanged NOTIFICATION-TYPE
                        OBJECTS { fkBackupControlRequest, fkBackupControlTimeStamp, fkBackupControlReqResult, fkBackupControlSrcConfigFile }
                        STATUS current
                        DESCRIPTION 
                                "Description"
                        ::= { fkBackupNotification 4 }

                
                -- 1.3.6.1.4.1.10428 9 1.101.1.4.3.5
                fkBackupConfigByScpChanged NOTIFICATION-TYPE
                        OBJECTS { fkBackupControlRequest, fkBackupControlTimeStamp, fkBackupControlReqResult, fkBackupControlSrcConfigFile }
                        STATUS current
                        DESCRIPTION 
                                "Description"
                        ::= { fkBackupNotification 5 }

                
                -- 1.3.6.1.4.1.10428 9 1.101.1.4.3.6
                fkBackupKeyBySftpChanged NOTIFICATION-TYPE
                        OBJECTS { fkBackupControlRequest, fkBackupControlTimeStamp, fkBackupControlReqResult, fkBackupControlSrcConfigFile }
                        STATUS current
                        DESCRIPTION 
                                "Description"
                        ::= { fkBackupNotification 6 }

                
                -- 1.3.6.1.4.1.10428 9 1.101.1.4.3.7
                fkBackupKeyByScpChanged NOTIFICATION-TYPE
                        OBJECTS { fkBackupControlRequest, fkBackupControlTimeStamp, fkBackupControlReqResult, fkBackupControlSrcConfigFile }
                        STATUS current
                        DESCRIPTION 
                                "Description"
                        ::= { fkBackupNotification 7 }

                
                -- 1.3.6.1.4.1.10428 9 1.101.1.5
                fkProcess OBJECT IDENTIFIER ::= { fkSystemMaintenance 5 }

                
                -- 1.3.6.1.4.1.10428 9 1.101.1.5.1
                fkProcessTable OBJECT-TYPE
                        SYNTAX SEQUENCE OF FkProcessEntry
                        MAX-ACCESS not-accessible
                        STATUS current
                        DESCRIPTION
                                "Description."
                        ::= { fkProcess 1 }

                
                -- 1.3.6.1.4.1.10428 9 1.101.1.5.1.1
                fkProcessEntry OBJECT-TYPE
                        SYNTAX FkProcessEntry
                        MAX-ACCESS not-accessible
                        STATUS current
                        DESCRIPTION
                                "Description."
                        INDEX { fkProcessID }
                        ::= { fkProcessTable 1 }

                
                FkProcessEntry ::=
                        SEQUENCE { 
                                fkProcessID
                                        Integer32,
                                fkProcessUser
                                        OCTET STRING,
                                fkProcessCPU
                                        Integer32,
                                fkProcessMemory
                                        Integer32,
                                fkProcessVSZ
                                        Integer32,
                                fkProcessRSS
                                        Integer32,
                                fkProcessTerminal
                                        OCTET STRING,
                                fkProcessStatus
                                        OCTET STRING,
                                fkProcessStartTime
                                        OCTET STRING,
                                fkProcessUsedTime
                                        OCTET STRING,
                                fkProcessCommand
                                        OCTET STRING
                         }

                -- 1.3.6.1.4.1.10428 9 1.101.1.5.1.1.1
                fkProcessID OBJECT-TYPE
                        SYNTAX Integer32 (1..65535)
                        MAX-ACCESS read-write
                        STATUS current
                        DESCRIPTION
                                "Process ID"
                        ::= { fkProcessEntry 1 }

                
                -- 1.3.6.1.4.1.10428 9 1.101.1.5.1.1.2
                fkProcessUser OBJECT-TYPE
                        SYNTAX OCTET STRING
                        MAX-ACCESS read-only
                        STATUS current
                        DESCRIPTION
                                "Owner name of the process"
                        ::= { fkProcessEntry 2 }

                
                -- 1.3.6.1.4.1.10428 9 1.101.1.5.1.1.3
                fkProcessCPU OBJECT-TYPE
                        SYNTAX Integer32
                        MAX-ACCESS read-only
                        STATUS current
                        DESCRIPTION
                                "Percent CPU usage (unit : 0.1%)"
                        ::= { fkProcessEntry 3 }

                
                -- 1.3.6.1.4.1.10428 9 1.101.1.5.1.1.4
                fkProcessMemory OBJECT-TYPE
                        SYNTAX Integer32
                        MAX-ACCESS read-only
                        STATUS current
                        DESCRIPTION
                                "Percent real memory usage (unit : 0.1%)"
                        ::= { fkProcessEntry 4 }

                
                -- 1.3.6.1.4.1.10428 9 1.101.1.5.1.1.5
                fkProcessVSZ OBJECT-TYPE
                        SYNTAX Integer32
                        MAX-ACCESS read-only
                        STATUS current
                        DESCRIPTION
                                "Virtual address size for the process"
                        ::= { fkProcessEntry 5 }

                
                -- 1.3.6.1.4.1.10428 9 1.101.1.5.1.1.6
                fkProcessRSS OBJECT-TYPE
                        SYNTAX Integer32
                        MAX-ACCESS read-only
                        STATUS current
                        DESCRIPTION
                                "Residnet set size of the process"
                        ::= { fkProcessEntry 6 }

                
                -- 1.3.6.1.4.1.10428 9 1.101.1.5.1.1.7
                fkProcessTerminal OBJECT-TYPE
                        SYNTAX OCTET STRING
                        MAX-ACCESS read-only
                        STATUS current
                        DESCRIPTION
                                "Terminal for the process"
                        ::= { fkProcessEntry 7 }

                
                -- 1.3.6.1.4.1.10428 9 1.101.1.5.1.1.8
                fkProcessStatus OBJECT-TYPE
                        SYNTAX OCTET STRING
                        MAX-ACCESS read-only
                        STATUS current
                        DESCRIPTION
                                "Symbolic process status"
                        ::= { fkProcessEntry 8 }

                
                -- 1.3.6.1.4.1.10428 9 1.101.1.5.1.1.9
                fkProcessStartTime OBJECT-TYPE
                        SYNTAX OCTET STRING
                        MAX-ACCESS read-only
                        STATUS current
                        DESCRIPTION
                                "Start time of the process"
                        ::= { fkProcessEntry 9 }

                
                -- 1.3.6.1.4.1.10428 9 1.101.1.5.1.1.10
                fkProcessUsedTime OBJECT-TYPE
                        SYNTAX OCTET STRING
                        MAX-ACCESS read-only
                        STATUS current
                        DESCRIPTION
                                "Current CPU time used"
                        ::= { fkProcessEntry 10 }

                
                -- 1.3.6.1.4.1.10428 9 1.101.1.5.1.1.11
                fkProcessCommand OBJECT-TYPE
                        SYNTAX OCTET STRING
                        MAX-ACCESS read-only
                        STATUS current
                        DESCRIPTION
                                "Command for the process"
                        ::= { fkProcessEntry 11 }

                
                -- 1.3.6.1.4.1.10428 9 1.101.1.6
                fkNTP OBJECT IDENTIFIER ::= { fkSystemMaintenance 6 }

                
                -- 1.3.6.1.4.1.10428 9 1.101.1.6.1
                fkNTPServerTable OBJECT-TYPE
                        SYNTAX SEQUENCE OF FkNTPServerEntry
                        MAX-ACCESS not-accessible
                        STATUS current
                        DESCRIPTION
                                "The NTP Server table."
                        ::= { fkNTP 1 }

                
                -- 1.3.6.1.4.1.10428 9 1.101.1.6.1.1
                fkNTPServerEntry OBJECT-TYPE
                        SYNTAX FkNTPServerEntry
                        MAX-ACCESS not-accessible
                        STATUS current
                        DESCRIPTION
                                "Description."
                        INDEX { fkNTPServerName }
                        ::= { fkNTPServerTable 1 }

                
                FkNTPServerEntry ::=
                        SEQUENCE { 
                                fkNTPServerName
                                        OCTET STRING
                         }

                -- 1.3.6.1.4.1.10428 9 1.101.1.6.1.1.1
                fkNTPServerName OBJECT-TYPE
                        SYNTAX OCTET STRING (SIZE (0..256))
                        MAX-ACCESS read-only
                        STATUS current
                        DESCRIPTION
                                "The NTP server name."
                        ::= { fkNTPServerEntry 1 }

                
                -- 1.3.6.1.4.1.10428 9 1.101.1.6.2
                fkNTPServerControl OBJECT IDENTIFIER ::= { fkNTP 2 }

                
                -- 1.3.6.1.4.1.10428 9 1.101.1.6.2.1
                fkNTPServerControlRequest OBJECT-TYPE
                        SYNTAX INTEGER
                                {
                                createNTPServer(1),
                                destoryNTPServer(2)
                                }
                        MAX-ACCESS read-write
                        STATUS current
                        DESCRIPTION
                                "Description."
                        ::= { fkNTPServerControl 1 }

                
                -- 1.3.6.1.4.1.10428 9 1.101.1.6.2.2
                fkNTPServerControlStatus OBJECT-TYPE
                        SYNTAX FkControlStatusType
                        MAX-ACCESS read-only
                        STATUS current
                        DESCRIPTION
                                "Description."
                        ::= { fkNTPServerControl 2 }

                
                -- 1.3.6.1.4.1.10428 9 1.101.1.6.2.3
                fkNTPServerControlTimer OBJECT-TYPE
                        SYNTAX Gauge32
                        MAX-ACCESS read-write
                        STATUS current
                        DESCRIPTION
                                "Description."
                        ::= { fkNTPServerControl 3 }

                
                -- 1.3.6.1.4.1.10428 9 1.101.1.6.2.4
                fkNTPServerControlTImeStamp OBJECT-TYPE
                        SYNTAX TimeTicks
                        MAX-ACCESS read-only
                        STATUS current
                        DESCRIPTION
                                "Description."
                        ::= { fkNTPServerControl 4 }

                
                -- 1.3.6.1.4.1.10428 9 1.101.1.6.2.5
                fkNTPServerControlReqResult OBJECT-TYPE
                        SYNTAX FkControlRequestResultType
                        MAX-ACCESS read-only
                        STATUS current
                        DESCRIPTION
                                "Description."
                        ::= { fkNTPServerControl 5 }

                
                -- 1.3.6.1.4.1.10428 9 1.101.1.6.2.6
                fkNTPServerControlName OBJECT-TYPE
                        SYNTAX OCTET STRING (SIZE (0..256))
                        MAX-ACCESS read-write
                        STATUS current
                        DESCRIPTION
                                "The NTP server name."
                        ::= { fkNTPServerControl 6 }

                
                -- 1.3.6.1.4.1.10428 9 1.101.1.6.3
                fkNTPServerNotification OBJECT IDENTIFIER ::= { fkNTP 3 }

                
                -- 1.3.6.1.4.1.10428 9 1.101.1.6.3.1
                fkNTPServerCreated NOTIFICATION-TYPE
                        OBJECTS { fkNTPServerControlRequest, fkNTPServerControlTImeStamp, fkNTPServerControlReqResult, fkNTPServerName }
                        STATUS current
                        DESCRIPTION 
                                "Created NTP Server table entry."
                        ::= { fkNTPServerNotification 1 }

                
                -- 1.3.6.1.4.1.10428 9 1.101.1.6.3.2
                fkNTPServerDestroyed NOTIFICATION-TYPE
                        OBJECTS { fkNTPServerControlRequest, fkNTPServerControlReqResult, fkNTPServerControlTImeStamp, fkNTPServerControlName }
                        STATUS current
                        DESCRIPTION 
                                "Destroyed NTP Server table entry."
                        ::= { fkNTPServerNotification 2 }

                
                -- 1.3.6.1.4.1.10428 9 1.101.1.7
                fkSyslogConf OBJECT IDENTIFIER ::= { fkSystemMaintenance 7 }

                
                -- 1.3.6.1.4.1.10428 9 1.101.1.7.1
                fkSyslogConfTable OBJECT-TYPE
                        SYNTAX SEQUENCE OF FkSyslogConfEntry
                        MAX-ACCESS not-accessible
                        STATUS current
                        DESCRIPTION
                                "Description."
                        ::= { fkSyslogConf 1 }

                
                -- 1.3.6.1.4.1.10428 9 1.101.1.7.1.1
                fkSyslogConfEntry OBJECT-TYPE
                        SYNTAX FkSyslogConfEntry
                        MAX-ACCESS not-accessible
                        STATUS current
                        DESCRIPTION
                                "Description."
                        INDEX { fkSyslogConfIndex }
                        ::= { fkSyslogConfTable 1 }

                
                FkSyslogConfEntry ::=
                        SEQUENCE { 
                                fkSyslogConfIndex
                                        Integer32,
                                fkSyslogConfMode
                                        INTEGER,
                                fkSyslogConfFacility
                                        INTEGER,
                                fkSyslogConfSeverity
                                        INTEGER,
                                fkSyslogConfTarget
                                        INTEGER,
                                fkSyslogConfStorage
                                        INTEGER,
                                fkSyslogConfTargetAddress
                                        IpAddress
                         }

                -- 1.3.6.1.4.1.10428 9 1.101.1.7.1.1.1
                fkSyslogConfIndex OBJECT-TYPE
                        SYNTAX Integer32 (1..255)
                        MAX-ACCESS read-only
                        STATUS current
                        DESCRIPTION
                                "Message index"
                        ::= { fkSyslogConfEntry 1 }

                
                -- 1.3.6.1.4.1.10428 9 1.101.1.7.1.1.2
                fkSyslogConfMode OBJECT-TYPE
                        SYNTAX INTEGER
                                {
                                general(0),
                                priority(1)
                                }
                        MAX-ACCESS read-only
                        STATUS current
                        DESCRIPTION
                                "Name of the facility that generated message."
                        ::= { fkSyslogConfEntry 2 }

                
                -- 1.3.6.1.4.1.10428 9 1.101.1.7.1.1.3
                fkSyslogConfFacility OBJECT-TYPE
                        SYNTAX INTEGER
                                {
                                auth(0),
                                authpriv(1),
                                kern(2),
                                local0(3),
                                local1(4),
                                local2(5),
                                local3(6),
                                local4(7),
                                local5(8),
                                local6(9),
                                local7(10),
                                syslog(11),
                                user(12),
                                nomap(99)
                                }
                        MAX-ACCESS read-only
                        STATUS current
                        DESCRIPTION
                                "Name of the facility that generated message.
                                16~23: local"
                        ::= { fkSyslogConfEntry 3 }

                
                -- 1.3.6.1.4.1.10428 9 1.101.1.7.1.1.4
                fkSyslogConfSeverity OBJECT-TYPE
                        SYNTAX INTEGER
                                {
                                emergency(0),
                                alert(1),
                                critical(2),
                                error(3),
                                warning(4),
                                notice(5),
                                info(6),
                                debug(7),
                                other(99)
                                }
                        MAX-ACCESS read-only
                        STATUS current
                        DESCRIPTION
                                "The severity of the message"
                        ::= { fkSyslogConfEntry 4 }

                
                -- 1.3.6.1.4.1.10428 9 1.101.1.7.1.1.5
                fkSyslogConfTarget OBJECT-TYPE
                        SYNTAX INTEGER
                                {
                                local(1),
                                consol(2),
                                remote(3)
                                }
                        MAX-ACCESS read-only
                        STATUS current
                        DESCRIPTION
                                "Target type"
                        ::= { fkSyslogConfEntry 5 }

                
                -- 1.3.6.1.4.1.10428 9 1.101.1.7.1.1.6
                fkSyslogConfStorage OBJECT-TYPE
                        SYNTAX INTEGER
                                {
                                notAvailable(-1),
                                volatile(0),
                                nonvolatile(1)
                                }
                        MAX-ACCESS read-only
                        STATUS current
                        DESCRIPTION
                                "Description."
                        ::= { fkSyslogConfEntry 6 }

                
                -- 1.3.6.1.4.1.10428 9 1.101.1.7.1.1.7
                fkSyslogConfTargetAddress OBJECT-TYPE
                        SYNTAX IpAddress
                        MAX-ACCESS read-only
                        STATUS current
                        DESCRIPTION
                                "Description."
                        ::= { fkSyslogConfEntry 7 }

                
                -- 1.3.6.1.4.1.10428 9 1.101.1.7.2
                fkSyslogConfControl OBJECT IDENTIFIER ::= { fkSyslogConf 2 }

                
                -- 1.3.6.1.4.1.10428 9 1.101.1.7.2.1
                fkSyslogConfControlRequest OBJECT-TYPE
                        SYNTAX INTEGER
                                {
                                createSyslogConf(1),
                                destroySyslogConf(2)
                                }
                        MAX-ACCESS read-write
                        STATUS current
                        DESCRIPTION
                                "Description."
                        ::= { fkSyslogConfControl 1 }

                
                -- 1.3.6.1.4.1.10428 9 1.101.1.7.2.2
                fkSyslogConfControlStatus OBJECT-TYPE
                        SYNTAX Integer32
                        MAX-ACCESS read-only
                        STATUS current
                        DESCRIPTION
                                "Description."
                        ::= { fkSyslogConfControl 2 }

                
                -- 1.3.6.1.4.1.10428 9 1.101.1.7.2.3
                fkSyslogConfControlTimer OBJECT-TYPE
                        SYNTAX Gauge32
                        MAX-ACCESS read-write
                        STATUS current
                        DESCRIPTION
                                "Description."
                        ::= { fkSyslogConfControl 3 }

                
                -- 1.3.6.1.4.1.10428 9 1.101.1.7.2.4
                fkSyslogConfControlTimeStamp OBJECT-TYPE
                        SYNTAX TimeTicks
                        MAX-ACCESS read-only
                        STATUS current
                        DESCRIPTION
                                "Description."
                        ::= { fkSyslogConfControl 4 }

                
                -- 1.3.6.1.4.1.10428 9 1.101.1.7.2.5
                fkSyslogConfControlReqResult OBJECT-TYPE
                        SYNTAX Integer32
                        MAX-ACCESS read-only
                        STATUS current
                        DESCRIPTION
                                "Description."
                        ::= { fkSyslogConfControl 5 }

                
                -- 1.3.6.1.4.1.10428 9 1.101.1.7.2.6
                fkSyslogConfControlIndex OBJECT-TYPE
                        SYNTAX Integer32
                        MAX-ACCESS read-write
                        STATUS current
                        DESCRIPTION
                                "Description."
                        ::= { fkSyslogConfControl 6 }

                
                -- 1.3.6.1.4.1.10428 9 1.101.1.7.2.7
                fkSyslogConfControlMode OBJECT-TYPE
                        SYNTAX INTEGER
                                {
                                general(0),
                                priority(1)
                                }
                        MAX-ACCESS read-write
                        STATUS current
                        DESCRIPTION
                                "Description."
                        ::= { fkSyslogConfControl 7 }

                
                -- 1.3.6.1.4.1.10428 9 1.101.1.7.2.8
                fkSyslogConfControlSeverity OBJECT-TYPE
                        SYNTAX INTEGER
                                {
                                emergency(0),
                                alert(1),
                                critical(2),
                                error(3),
                                warning(4),
                                notice(5),
                                info(6),
                                debug(7),
                                other(99)
                                }
                        MAX-ACCESS read-write
                        STATUS current
                        DESCRIPTION
                                "Description."
                        ::= { fkSyslogConfControl 8 }

                
                -- 1.3.6.1.4.1.10428 9 1.101.1.7.2.9
                fkSyslogConfControlFacility OBJECT-TYPE
                        SYNTAX INTEGER
                                {
                                auth(0),
                                authpriv(1),
                                kern(2),
                                local0(3),
                                local1(4),
                                local2(5),
                                local3(6),
                                local4(7),
                                local5(8),
                                local6(9),
                                local7(10),
                                syslog(11),
                                user(12),
                                nomap(99)
                                }
                        MAX-ACCESS read-write
                        STATUS current
                        DESCRIPTION
                                "Description."
                        ::= { fkSyslogConfControl 9 }

                
                -- 1.3.6.1.4.1.10428 9 1.101.1.7.2.10
                fkSyslogConfControlTarget OBJECT-TYPE
                        SYNTAX INTEGER
                                {
                                local(1),
                                consol(2),
                                remote(3)
                                }
                        MAX-ACCESS read-write
                        STATUS current
                        DESCRIPTION
                                "Target type"
                        ::= { fkSyslogConfControl 10 }

                
                -- 1.3.6.1.4.1.10428 9 1.101.1.7.2.11
                fkSyslogConfControlStorage OBJECT-TYPE
                        SYNTAX INTEGER
                                {
                                notAvailable(-1),
                                volatile(0),
                                nonvolatile(1)
                                }
                        MAX-ACCESS read-write
                        STATUS current
                        DESCRIPTION
                                "Description"
                        ::= { fkSyslogConfControl 11 }

                
                -- 1.3.6.1.4.1.10428 9 1.101.1.7.2.12
                fkSyslogConfControlTargetAddress OBJECT-TYPE
                        SYNTAX IpAddress
                        MAX-ACCESS read-write
                        STATUS current
                        DESCRIPTION
                                "Description"
                        ::= { fkSyslogConfControl 12 }

                
                -- 1.3.6.1.4.1.10428 9 1.101.1.7.3
                fkSyslogConfNotification OBJECT IDENTIFIER ::= { fkSyslogConf 3 }

                
                -- 1.3.6.1.4.1.10428 9 1.101.1.7.3.1
                fkSyslogConfCreated NOTIFICATION-TYPE
                        OBJECTS { fkSyslogConfControlRequest, fkSyslogConfControlReqResult, fkSyslogConfControlTimeStamp, fkSyslogConfMode, fkSyslogConfFacility, 
                                fkSyslogConfSeverity, fkSyslogConfTarget, fkSyslogConfStorage, fkSyslogConfTargetAddress }
                        STATUS current
                        DESCRIPTION 
                                "Description."
                        ::= { fkSyslogConfNotification 1 }

                
                -- 1.3.6.1.4.1.10428 9 1.101.1.7.3.2
                fkSyslogConfDestroyed NOTIFICATION-TYPE
                        OBJECTS { fkSyslogConfControlRequest, fkSyslogConfControlReqResult, fkSyslogConfControlTimeStamp, fkSyslogConfControlIndex }
                        STATUS current
                        DESCRIPTION 
                                "Description."
                        ::= { fkSyslogConfNotification 2 }

                
                -- 1.3.6.1.4.1.10428 9 1.101.1.8
                fkSyslogHistVol OBJECT IDENTIFIER ::= { fkSystemMaintenance 8 }

                
                -- 1.3.6.1.4.1.10428 9 1.101.1.8.1
                fkSyslogHistVolTable OBJECT-TYPE
                        SYNTAX SEQUENCE OF FkSyslogHistVolEntry
                        MAX-ACCESS not-accessible
                        STATUS current
                        DESCRIPTION
                                "Description."
                        ::= { fkSyslogHistVol 1 }

                
                -- 1.3.6.1.4.1.10428 9 1.101.1.8.1.1
                fkSyslogHistVolEntry OBJECT-TYPE
                        SYNTAX FkSyslogHistVolEntry
                        MAX-ACCESS not-accessible
                        STATUS current
                        DESCRIPTION
                                "Description."
                        INDEX { fkSyslogHistVolIndex }
                        ::= { fkSyslogHistVolTable 1 }

                
                FkSyslogHistVolEntry ::=
                        SEQUENCE { 
                                fkSyslogHistVolIndex
                                        Integer32,
                                fkSyslogHistVolMsgText
                                        OCTET STRING,
                                fkSyslogHistVolTime
                                        TimeTicks
                         }

                -- 1.3.6.1.4.1.10428 9 1.101.1.8.1.1.1
                fkSyslogHistVolIndex OBJECT-TYPE
                        SYNTAX Integer32 (1..65535)
                        MAX-ACCESS read-only
                        STATUS current
                        DESCRIPTION
                                "Description."
                        ::= { fkSyslogHistVolEntry 1 }

                
                -- 1.3.6.1.4.1.10428 9 1.101.1.8.1.1.2
                fkSyslogHistVolMsgText OBJECT-TYPE
                        SYNTAX OCTET STRING
                        MAX-ACCESS read-only
                        STATUS current
                        DESCRIPTION
                                "Description."
                        ::= { fkSyslogHistVolEntry 2 }

                
                -- 1.3.6.1.4.1.10428 9 1.101.1.8.1.1.3
                fkSyslogHistVolTime OBJECT-TYPE
                        SYNTAX TimeTicks
                        MAX-ACCESS read-only
                        STATUS current
                        DESCRIPTION
                                "Description."
                        ::= { fkSyslogHistVolEntry 3 }

                
                -- 1.3.6.1.4.1.10428 9 1.101.1.9
                fkSyslogHistNVol OBJECT IDENTIFIER ::= { fkSystemMaintenance 9 }

                
                -- 1.3.6.1.4.1.10428 9 1.101.1.9.1
                fkSyslogHistNVolTable OBJECT-TYPE
                        SYNTAX SEQUENCE OF FkSyslogHistNVolEntry
                        MAX-ACCESS not-accessible
                        STATUS current
                        DESCRIPTION
                                "Description."
                        ::= { fkSyslogHistNVol 1 }

                
                -- 1.3.6.1.4.1.10428 9 1.101.1.9.1.1
                fkSyslogHistNVolEntry OBJECT-TYPE
                        SYNTAX FkSyslogHistNVolEntry
                        MAX-ACCESS not-accessible
                        STATUS current
                        DESCRIPTION
                                "Description."
                        INDEX { fkSyslogHistNVolIndex }
                        ::= { fkSyslogHistNVolTable 1 }

                
                FkSyslogHistNVolEntry ::=
                        SEQUENCE { 
                                fkSyslogHistNVolIndex
                                        Integer32,
                                fkSyslogHistNVolMsgText
                                        OCTET STRING,
                                fkSyslogHistNVolTime
                                        TimeTicks
                         }

                -- 1.3.6.1.4.1.10428 9 1.101.1.9.1.1.1
                fkSyslogHistNVolIndex OBJECT-TYPE
                        SYNTAX Integer32 (1..65535)
                        MAX-ACCESS read-only
                        STATUS current
                        DESCRIPTION
                                "Description."
                        ::= { fkSyslogHistNVolEntry 1 }

                
                -- 1.3.6.1.4.1.10428 9 1.101.1.9.1.1.2
                fkSyslogHistNVolMsgText OBJECT-TYPE
                        SYNTAX OCTET STRING
                        MAX-ACCESS read-only
                        STATUS current
                        DESCRIPTION
                                "The text of the message."
                        ::= { fkSyslogHistNVolEntry 2 }

                
                -- 1.3.6.1.4.1.10428 9 1.101.1.9.1.1.3
                fkSyslogHistNVolTime OBJECT-TYPE
                        SYNTAX TimeTicks
                        MAX-ACCESS read-only
                        STATUS current
                        DESCRIPTION
                                "The value of sysUpTime when this message was generated"
                        ::= { fkSyslogHistNVolEntry 3 }

                
                -- 1.3.6.1.4.1.10428 9 1.101.1.10
                fkSSHRemote OBJECT IDENTIFIER ::= { fkSystemMaintenance 10 }

                
                -- 1.3.6.1.4.1.10428 9 1.101.1.10.1
                fkSSHRemoteTable OBJECT-TYPE
                        SYNTAX SEQUENCE OF FkSSHRemoteEntry
                        MAX-ACCESS not-accessible
                        STATUS current
                        DESCRIPTION
                                "The table of remote connection's to this SSH Server."
                        ::= { fkSSHRemote 1 }

                
                -- 1.3.6.1.4.1.10428 9 1.101.1.10.1.1
                fkSSHRemoteEntry OBJECT-TYPE
                        SYNTAX FkSSHRemoteEntry
                        MAX-ACCESS not-accessible
                        STATUS current
                        DESCRIPTION
                                "Remote SSH connection entries."
                        INDEX { fkSSHRemoteIndex }
                        ::= { fkSSHRemoteTable 1 }

                
                FkSSHRemoteEntry ::=
                        SEQUENCE { 
                                fkSSHRemoteIndex
                                        INTEGER,
                                fkSSHRemoteUser
                                        OCTET STRING,
                                fkSSHRemoteHost
                                        IpAddress,
                                fkSSHRemoteTime
                                        OCTET STRING
                         }

                -- 1.3.6.1.4.1.10428 9 1.101.1.10.1.1.1
                fkSSHRemoteIndex OBJECT-TYPE
                        SYNTAX INTEGER (1..65535)
                        MAX-ACCESS read-only
                        STATUS current
                        DESCRIPTION
                                "Proccess ID of remote SSH Client connected to SSH Server."
                        ::= { fkSSHRemoteEntry 1 }

                
                -- 1.3.6.1.4.1.10428 9 1.101.1.10.1.1.2
                fkSSHRemoteUser OBJECT-TYPE
                        SYNTAX OCTET STRING (SIZE (0..256))
                        MAX-ACCESS read-only
                        STATUS current
                        DESCRIPTION
                                "Remote user ID connected to SSH Server."
                        ::= { fkSSHRemoteEntry 2 }

                
                -- 1.3.6.1.4.1.10428 9 1.101.1.10.1.1.3
                fkSSHRemoteHost OBJECT-TYPE
                        SYNTAX IpAddress
                        MAX-ACCESS read-only
                        STATUS current
                        DESCRIPTION
                                "Remote host IP address connected to SSH Server."
                        ::= { fkSSHRemoteEntry 3 }

                
                -- 1.3.6.1.4.1.10428 9 1.101.1.10.1.1.4
                fkSSHRemoteTime OBJECT-TYPE
                        SYNTAX OCTET STRING (SIZE (0..32))
                        MAX-ACCESS read-only
                        STATUS current
                        DESCRIPTION
                                "Connection time to SSH Server of this remote user."
                        ::= { fkSSHRemoteEntry 4 }

                
                -- 1.3.6.1.4.1.10428 9 1.101.1.10.2
                fkSSHRemoteControl OBJECT IDENTIFIER ::= { fkSSHRemote 2 }

                
                -- 1.3.6.1.4.1.10428 9 1.101.1.10.2.1
                fkSSHRemoteControlRequest OBJECT-TYPE
                        SYNTAX INTEGER { destorySshRemoteConnection(1) }
                        MAX-ACCESS read-write
                        STATUS current
                        DESCRIPTION
                                "Control Request."
                        ::= { fkSSHRemoteControl 1 }

                
                -- 1.3.6.1.4.1.10428 9 1.101.1.10.2.2
                fkSSHRemoteControlStatus OBJECT-TYPE
                        SYNTAX FkControlStatusType
                        MAX-ACCESS read-only
                        STATUS current
                        DESCRIPTION
                                "Control Status."
                        ::= { fkSSHRemoteControl 2 }

                
                -- 1.3.6.1.4.1.10428 9 1.101.1.10.2.3
                fkSSHRemoteControlTimer OBJECT-TYPE
                        SYNTAX Gauge32
                        MAX-ACCESS read-write
                        STATUS current
                        DESCRIPTION
                                "Description."
                        ::= { fkSSHRemoteControl 3 }

                
                -- 1.3.6.1.4.1.10428 9 1.101.1.10.2.4
                fkSSHRemoteControlTImeStamp OBJECT-TYPE
                        SYNTAX TimeTicks
                        MAX-ACCESS read-only
                        STATUS current
                        DESCRIPTION
                                "Description."
                        ::= { fkSSHRemoteControl 4 }

                
                -- 1.3.6.1.4.1.10428 9 1.101.1.10.2.5
                fkSSHRemoteControlReqResult OBJECT-TYPE
                        SYNTAX FkControlRequestResultType
                        MAX-ACCESS read-only
                        STATUS current
                        DESCRIPTION
                                "Description."
                        ::= { fkSSHRemoteControl 5 }

                
                -- 1.3.6.1.4.1.10428 9 1.101.1.10.2.6
                fkSSHRemoteControlIndex OBJECT-TYPE
                        SYNTAX INTEGER (1..65535)
                        MAX-ACCESS read-write
                        STATUS current
                        DESCRIPTION
                                "Proccess ID of remote SSH Client connected to SSH Server."
                        ::= { fkSSHRemoteControl 6 }

                
                -- 1.3.6.1.4.1.10428 9 1.101.1.10.3
                fkSSHRemoteNotification OBJECT IDENTIFIER ::= { fkSSHRemote 3 }

                
                -- 1.3.6.1.4.1.10428 9 1.101.1.10.3.1
                fkSSHRemoteConnectiondestoryed NOTIFICATION-TYPE
                        OBJECTS { fkSSHRemoteControlRequest, fkSSHRemoteControlReqResult, fkSSHRemoteControlTImeStamp, fkSSHRemoteControlIndex }
                        STATUS current
                        DESCRIPTION 
                                "Destroyed the remote connection to this SSH Server."
                        ::= { fkSSHRemoteNotification 1 }

                
                -- 1.3.6.1.4.1.10428 9 1.101.1.11
                fkAutoCli OBJECT IDENTIFIER ::= { fkSystemMaintenance 11 }

                
                -- 1.3.6.1.4.1.10428 9 1.101.1.11.1
                fkAutoCliInfo OBJECT IDENTIFIER ::= { fkAutoCli 1 }

                
                -- 1.3.6.1.4.1.10428 9 1.101.1.11.1.1
                fkAutoCliBase OBJECT IDENTIFIER ::= { fkAutoCliInfo 1 }

                
                -- 1.3.6.1.4.1.10428 9 1.101.1.11.1.1.1
                fkAutoCliConfStatus OBJECT-TYPE
                        SYNTAX EnableFlag
                        MAX-ACCESS read-only
                        STATUS current
                        DESCRIPTION
                                "The administrative state of AutoCli Scheduler"
                        ::= { fkAutoCliBase 1 }

                
                -- 1.3.6.1.4.1.10428 9 1.101.1.11.1.1.2
                fkAutoCliMemoryMaxSize OBJECT-TYPE
                        SYNTAX Integer32
                        MAX-ACCESS read-only
                        STATUS current
                        DESCRIPTION
                                "The max memory size to save output-file"
                        ::= { fkAutoCliBase 2 }

                
                -- 1.3.6.1.4.1.10428 9 1.101.1.11.1.1.3
                fkAutoCliMemoryUsedsize OBJECT-TYPE
                        SYNTAX Integer32
                        MAX-ACCESS read-only
                        STATUS current
                        DESCRIPTION
                                "The used memory size to save output-file"
                        ::= { fkAutoCliBase 3 }

                
                -- 1.3.6.1.4.1.10428 9 1.101.1.11.1.1.4
                fkAutoCliMemoryFreesize OBJECT-TYPE
                        SYNTAX Integer32
                        MAX-ACCESS read-only
                        STATUS current
                        DESCRIPTION
                                "The freed memory size to save output-file"
                        ::= { fkAutoCliBase 4 }

                
                -- 1.3.6.1.4.1.10428 9 1.101.1.11.1.1.5
                fkAutoCliTransferInterval OBJECT-TYPE
                        SYNTAX Integer32
                        UNITS "minute"
                        MAX-ACCESS read-only
                        STATUS current
                        DESCRIPTION
                                "The amount of time between the transference of outputfile"
                        ::= { fkAutoCliBase 5 }

                
                -- 1.3.6.1.4.1.10428 9 1.101.1.11.1.2
                fkAutoCliBaseControl OBJECT IDENTIFIER ::= { fkAutoCliInfo 2 }

                
                -- 1.3.6.1.4.1.10428 9 1.101.1.11.1.2.1
                fkAutoCliControlRequest OBJECT-TYPE
                        SYNTAX INTEGER
                                {
                                setAutoCliStatus(1),
                                setMemoryMaxsize(2),
                                setTransferInterval(3)
                                }
                        MAX-ACCESS read-write
                        STATUS current
                        DESCRIPTION
                                "Description."
                        ::= { fkAutoCliBaseControl 1 }

                
                -- 1.3.6.1.4.1.10428 9 1.101.1.11.1.2.2
                fkAutoCliControlStatus OBJECT-TYPE
                        SYNTAX FkControlStatusType
                        MAX-ACCESS read-only
                        STATUS current
                        DESCRIPTION
                                "Description."
                        ::= { fkAutoCliBaseControl 2 }

                
                -- 1.3.6.1.4.1.10428 9 1.101.1.11.1.2.3
                fkAutoCliControlTimer OBJECT-TYPE
                        SYNTAX Gauge32
                        MAX-ACCESS read-write
                        STATUS current
                        DESCRIPTION
                                "Description."
                        ::= { fkAutoCliBaseControl 3 }

                
                -- 1.3.6.1.4.1.10428 9 1.101.1.11.1.2.4
                fkAutoCliControlTimeStamp OBJECT-TYPE
                        SYNTAX TimeTicks
                        MAX-ACCESS read-only
                        STATUS current
                        DESCRIPTION
                                "Description."
                        ::= { fkAutoCliBaseControl 4 }

                
                -- 1.3.6.1.4.1.10428 9 1.101.1.11.1.2.5
                fkAutoCliControlReqResult OBJECT-TYPE
                        SYNTAX FkControlRequestResultType
                        MAX-ACCESS read-only
                        STATUS current
                        DESCRIPTION
                                "Description."
                        ::= { fkAutoCliBaseControl 5 }

                
                -- 1.3.6.1.4.1.10428 9 1.101.1.11.1.2.6
                fkAutoCliControlConfStatus OBJECT-TYPE
                        SYNTAX EnableFlag
                        MAX-ACCESS read-write
                        STATUS current
                        DESCRIPTION
                                "The IpAddress of FTP/TFTP server to save output-file"
                        ::= { fkAutoCliBaseControl 6 }

                
                -- 1.3.6.1.4.1.10428 9 1.101.1.11.1.2.7
                fkAutoCliControlMemoryMaxsize OBJECT-TYPE
                        SYNTAX Integer32
                        MAX-ACCESS read-write
                        STATUS current
                        DESCRIPTION
                                "The max memory size to save output-file"
                        ::= { fkAutoCliBaseControl 7 }

                
                -- 1.3.6.1.4.1.10428 9 1.101.1.11.1.2.8
                fkAutoCliControlTransferInterval OBJECT-TYPE
                        SYNTAX Integer32
                        UNITS "minute"
                        MAX-ACCESS read-write
                        STATUS current
                        DESCRIPTION
                                "The amount of time between the transference of outputfile"
                        ::= { fkAutoCliBaseControl 8 }

                
                -- 1.3.6.1.4.1.10428 9 1.101.1.11.1.3
                fkAutoCliBaseNotification OBJECT IDENTIFIER ::= { fkAutoCliInfo 3 }

                
                -- 1.3.6.1.4.1.10428 9 1.101.1.11.1.3.1
                fkAutoCliStatusChanged NOTIFICATION-TYPE
                        OBJECTS { fkAutoCliControlRequest, fkAutoCliControlTimeStamp, fkAutoCliControlReqResult, fkAutoCliConfStatus }
                        STATUS current
                        DESCRIPTION 
                                "Change auto cli administrative status."
                        ::= { fkAutoCliBaseNotification 1 }

                
                -- 1.3.6.1.4.1.10428 9 1.101.1.11.1.3.2
                fkAutoCliMemoryMaxsizeChanged NOTIFICATION-TYPE
                        OBJECTS { fkAutoCliControlRequest, fkAutoCliControlTimeStamp, fkAutoCliControlReqResult, fkAutoCliMemoryMaxSize }
                        STATUS current
                        DESCRIPTION 
                                "Description."
                        ::= { fkAutoCliBaseNotification 2 }

                
                -- 1.3.6.1.4.1.10428 9 1.101.1.11.1.3.3
                fkAutoCliTransferIntervalChanged NOTIFICATION-TYPE
                        OBJECTS { fkAutoCliControlRequest, fkAutoCliControlTimeStamp, fkAutoCliControlReqResult, fkAutoCliTransferInterval }
                        STATUS current
                        DESCRIPTION 
                                "Description."
                        ::= { fkAutoCliBaseNotification 3 }

                
                -- 1.3.6.1.4.1.10428 9 1.101.1.11.2
                fkAutoCliScriptFile OBJECT IDENTIFIER ::= { fkAutoCli 2 }

                
                -- 1.3.6.1.4.1.10428 9 1.101.1.11.2.1
                fkAutoCliScriptFileTable OBJECT-TYPE
                        SYNTAX SEQUENCE OF FkAutoCliScriptFileEntry
                        MAX-ACCESS not-accessible
                        STATUS current
                        DESCRIPTION
                                "Description."
                        ::= { fkAutoCliScriptFile 1 }

                
                -- 1.3.6.1.4.1.10428 9 1.101.1.11.2.1.1
                fkAutoCliScriptFileEntry OBJECT-TYPE
                        SYNTAX FkAutoCliScriptFileEntry
                        MAX-ACCESS not-accessible
                        STATUS current
                        DESCRIPTION
                                "Description."
                        INDEX { fkAutoCliScriptId }
                        ::= { fkAutoCliScriptFileTable 1 }

                
                FkAutoCliScriptFileEntry ::=
                        SEQUENCE { 
                                fkAutoCliScriptId
                                        INTEGER,
                                fkAutoCliScriptFileName
                                        OCTET STRING,
                                fkAutoCliScriptFileUser
                                        OCTET STRING,
                                fkAutoCliScriptFileSize
                                        Integer32,
                                fkAutoCliScriptFileUpdateTime
                                        OCTET STRING
                         }

                -- 1.3.6.1.4.1.10428 9 1.101.1.11.2.1.1.1
                fkAutoCliScriptId OBJECT-TYPE
                        SYNTAX INTEGER (1..2147483647)
                        MAX-ACCESS read-only
                        STATUS current
                        DESCRIPTION
                                "The id of script file"
                        ::= { fkAutoCliScriptFileEntry 1 }

                
                -- 1.3.6.1.4.1.10428 9 1.101.1.11.2.1.1.2
                fkAutoCliScriptFileName OBJECT-TYPE
                        SYNTAX OCTET STRING
                        MAX-ACCESS read-only
                        STATUS current
                        DESCRIPTION
                                "The name of script file"
                        ::= { fkAutoCliScriptFileEntry 2 }

                
                -- 1.3.6.1.4.1.10428 9 1.101.1.11.2.1.1.3
                fkAutoCliScriptFileUser OBJECT-TYPE
                        SYNTAX OCTET STRING
                        MAX-ACCESS read-only
                        STATUS current
                        DESCRIPTION
                                "The user of script file"
                        ::= { fkAutoCliScriptFileEntry 3 }

                
                -- 1.3.6.1.4.1.10428 9 1.101.1.11.2.1.1.4
                fkAutoCliScriptFileSize OBJECT-TYPE
                        SYNTAX Integer32
                        MAX-ACCESS read-only
                        STATUS current
                        DESCRIPTION
                                "The File size of script file"
                        ::= { fkAutoCliScriptFileEntry 4 }

                
                -- 1.3.6.1.4.1.10428 9 1.101.1.11.2.1.1.5
                fkAutoCliScriptFileUpdateTime OBJECT-TYPE
                        SYNTAX OCTET STRING
                        MAX-ACCESS read-only
                        STATUS current
                        DESCRIPTION
                                "The last updated time of script file"
                        ::= { fkAutoCliScriptFileEntry 5 }

                
                -- 1.3.6.1.4.1.10428 9 1.101.1.11.2.2
                fkAutoCliScriptFileControl OBJECT IDENTIFIER ::= { fkAutoCliScriptFile 2 }

                
                -- 1.3.6.1.4.1.10428 9 1.101.1.11.2.2.1
                fkAutoCliScriptFileControlRequest OBJECT-TYPE
                        SYNTAX INTEGER
                                {
                                ftpgetAutoCliScript(1),
                                tftpgetAutoCliScript(2),
                                destroyedAutoCliScript(3)
                                }
                        MAX-ACCESS read-write
                        STATUS current
                        DESCRIPTION
                                "Description."
                        ::= { fkAutoCliScriptFileControl 1 }

                
                -- 1.3.6.1.4.1.10428 9 1.101.1.11.2.2.2
                fkAutoCliScriptFileControlStatus OBJECT-TYPE
                        SYNTAX FkControlStatusType
                        MAX-ACCESS read-write
                        STATUS current
                        DESCRIPTION
                                "Description."
                        ::= { fkAutoCliScriptFileControl 2 }

                
                -- 1.3.6.1.4.1.10428 9 1.101.1.11.2.2.3
                fkAutoCliScriptFileControlTimer OBJECT-TYPE
                        SYNTAX Gauge32
                        MAX-ACCESS read-write
                        STATUS current
                        DESCRIPTION
                                "Description."
                        ::= { fkAutoCliScriptFileControl 3 }

                
                -- 1.3.6.1.4.1.10428 9 1.101.1.11.2.2.4
                fkAutoCliScriptFileControlTimeStamp OBJECT-TYPE
                        SYNTAX TimeTicks
                        MAX-ACCESS read-write
                        STATUS current
                        DESCRIPTION
                                "Description."
                        ::= { fkAutoCliScriptFileControl 4 }

                
                -- 1.3.6.1.4.1.10428 9 1.101.1.11.2.2.5
                fkAutoCliScriptFileControlReqResult OBJECT-TYPE
                        SYNTAX FkControlRequestResultType
                        MAX-ACCESS read-write
                        STATUS current
                        DESCRIPTION
                                "Description."
                        ::= { fkAutoCliScriptFileControl 5 }

                
                -- 1.3.6.1.4.1.10428 9 1.101.1.11.2.2.6
                fkAutoCliScriptFileControlIpAddress OBJECT-TYPE
                        SYNTAX IpAddress
                        MAX-ACCESS read-write
                        STATUS current
                        DESCRIPTION
                                "The ip address of FTP server to get a script file."
                        ::= { fkAutoCliScriptFileControl 6 }

                
                -- 1.3.6.1.4.1.10428 9 1.101.1.11.2.2.7
                fkAutoCliScriptFileControlUserName OBJECT-TYPE
                        SYNTAX OCTET STRING
                        MAX-ACCESS read-write
                        STATUS current
                        DESCRIPTION
                                "The user name of FTP server to get a script file"
                        ::= { fkAutoCliScriptFileControl 7 }

                
                -- 1.3.6.1.4.1.10428 9 1.101.1.11.2.2.8
                fkAutoCliScriptFileControlPassword OBJECT-TYPE
                        SYNTAX OCTET STRING
                        MAX-ACCESS read-write
                        STATUS current
                        DESCRIPTION
                                "The password of FTP server to get a script file"
                        ::= { fkAutoCliScriptFileControl 8 }

                
                -- 1.3.6.1.4.1.10428 9 1.101.1.11.2.2.9
                fkAutoCliScriptFileControlFilePath OBJECT-TYPE
                        SYNTAX OCTET STRING
                        MAX-ACCESS read-write
                        STATUS current
                        DESCRIPTION
                                "The file-path of FTP server to get a script file"
                        ::= { fkAutoCliScriptFileControl 9 }

                
                -- 1.3.6.1.4.1.10428 9 1.101.1.11.2.2.10
                fkAutoCliScriptFileControlScriptName OBJECT-TYPE
                        SYNTAX OCTET STRING
                        MAX-ACCESS read-write
                        STATUS current
                        DESCRIPTION
                                "The script file name"
                        ::= { fkAutoCliScriptFileControl 10 }

                
                -- 1.3.6.1.4.1.10428 9 1.101.1.11.2.3
                fkAutoCliScriptFileNotifications OBJECT IDENTIFIER ::= { fkAutoCliScriptFile 3 }

                
                -- 1.3.6.1.4.1.10428 9 1.101.1.11.2.3.1
                fkAutoCliScriptFileFtpCreated NOTIFICATION-TYPE
                        OBJECTS { fkAutoCliScriptFileControlRequest, fkAutoCliScriptFileControlTimeStamp, fkAutoCliScriptFileControlReqResult, fkAutoCliScriptFileName }
                        STATUS current
                        DESCRIPTION 
                                "ftpgetAutoCliScript"
                        ::= { fkAutoCliScriptFileNotifications 1 }

                
                -- 1.3.6.1.4.1.10428 9 1.101.1.11.2.3.2
                fkAutoCliScriptFileTftpCreated NOTIFICATION-TYPE
                        OBJECTS { fkAutoCliScriptFileControlRequest, fkAutoCliScriptFileControlTimeStamp, fkAutoCliScriptFileControlReqResult, fkAutoCliScriptFileName }
                        STATUS current
                        DESCRIPTION 
                                "tftpgetAutoCliScript"
                        ::= { fkAutoCliScriptFileNotifications 2 }

                
                -- 1.3.6.1.4.1.10428 9 1.101.1.11.2.3.3
                fkAutoCliScriptFileDestroyed NOTIFICATION-TYPE
                        OBJECTS { fkAutoCliScriptFileControlRequest, fkAutoCliScriptFileControlTimeStamp, fkAutoCliScriptFileControlReqResult, fkAutoCliScriptFileControlScriptName }
                        STATUS current
                        DESCRIPTION 
                                "destroyedAutoCliScript"
                        ::= { fkAutoCliScriptFileNotifications 3 }

                
                -- 1.3.6.1.4.1.10428 9 1.101.1.11.3
                fkAutoCliSchedule OBJECT IDENTIFIER ::= { fkAutoCli 3 }

                
                -- 1.3.6.1.4.1.10428 9 1.101.1.11.3.1
                fkAutoCliScheduleTable OBJECT-TYPE
                        SYNTAX SEQUENCE OF FkAutoCliScheduleEntry
                        MAX-ACCESS not-accessible
                        STATUS current
                        DESCRIPTION
                                "Description."
                        ::= { fkAutoCliSchedule 1 }

                
                -- 1.3.6.1.4.1.10428 9 1.101.1.11.3.1.1
                fkAutoCliScheduleEntry OBJECT-TYPE
                        SYNTAX FkAutoCliScheduleEntry
                        MAX-ACCESS not-accessible
                        STATUS current
                        DESCRIPTION
                                "Description."
                        INDEX { fkAutoCliScheduleName }
                        ::= { fkAutoCliScheduleTable 1 }

                
                FkAutoCliScheduleEntry ::=
                        SEQUENCE { 
                                fkAutoCliScheduleName
                                        OCTET STRING,
                                fkAutoCliScheduleType
                                        FkDefAutoCliScheduleType,
                                fkAutoCliScheduleInterval
                                        Integer32,
                                fkAutoCliScheduleYear
                                        Integer32,
                                fkAutoCliScheduleMonth
                                        Integer32,
                                fkAutoCliScheduleDay
                                        Integer32,
                                fkAutoCliScheduleHour
                                        Integer32,
                                fkAutoCliScheduleMinute
                                        Integer32,
                                fkAutoCliScheduleScriptName
                                        OCTET STRING,
                                fkAutoCliScheduleTransferType
                                        FkDefAutoCliScheduleTransferType,
                                fkAutoCliScheduleLastExecutedTime
                                        OCTET STRING,
                                fkAutoCliScheduleOutputRule
                                        OCTET STRING,
                                fkAutoCliScheduleLastResult
                                        FkDefAutoCliScheduleResult,
                                fkAutoCliScheduleProfileName
                                        OCTET STRING
                         }

                -- 1.3.6.1.4.1.10428 9 1.101.1.11.3.1.1.1
                fkAutoCliScheduleName OBJECT-TYPE
                        SYNTAX OCTET STRING
                        MAX-ACCESS read-only
                        STATUS current
                        DESCRIPTION
                                "The name of the schedule name "
                        ::= { fkAutoCliScheduleEntry 1 }

                
                -- 1.3.6.1.4.1.10428 9 1.101.1.11.3.1.1.2
                fkAutoCliScheduleType OBJECT-TYPE
                        SYNTAX FkDefAutoCliScheduleType
                        MAX-ACCESS read-only
                        STATUS current
                        DESCRIPTION
                                "The type of schedule.
                                Periodic(1) - scheduled with regular intervals.
                                At(2) - scheduled for exactly time.
                                Daily(3) - scheduled for every day.
                                Immediate(4) - scheduled immediately 
                                "
                        ::= { fkAutoCliScheduleEntry 2 }

                
                -- 1.3.6.1.4.1.10428 9 1.101.1.11.3.1.1.3
                fkAutoCliScheduleInterval OBJECT-TYPE
                        SYNTAX Integer32
                        MAX-ACCESS read-only
                        STATUS current
                        DESCRIPTION
                                "The period of execution time."
                        ::= { fkAutoCliScheduleEntry 3 }

                
                -- 1.3.6.1.4.1.10428 9 1.101.1.11.3.1.1.4
                fkAutoCliScheduleYear OBJECT-TYPE
                        SYNTAX Integer32
                        MAX-ACCESS read-only
                        STATUS current
                        DESCRIPTION
                                "The value of the year "
                        ::= { fkAutoCliScheduleEntry 4 }

                
                -- 1.3.6.1.4.1.10428 9 1.101.1.11.3.1.1.5
                fkAutoCliScheduleMonth OBJECT-TYPE
                        SYNTAX Integer32
                        MAX-ACCESS read-only
                        STATUS current
                        DESCRIPTION
                                "The value of the month"
                        ::= { fkAutoCliScheduleEntry 5 }

                
                -- 1.3.6.1.4.1.10428 9 1.101.1.11.3.1.1.6
                fkAutoCliScheduleDay OBJECT-TYPE
                        SYNTAX Integer32
                        MAX-ACCESS read-only
                        STATUS current
                        DESCRIPTION
                                "Description."
                        ::= { fkAutoCliScheduleEntry 6 }

                
                -- 1.3.6.1.4.1.10428 9 1.101.1.11.3.1.1.7
                fkAutoCliScheduleHour OBJECT-TYPE
                        SYNTAX Integer32
                        MAX-ACCESS read-only
                        STATUS current
                        DESCRIPTION
                                "The value of the hour"
                        ::= { fkAutoCliScheduleEntry 7 }

                
                -- 1.3.6.1.4.1.10428 9 1.101.1.11.3.1.1.8
                fkAutoCliScheduleMinute OBJECT-TYPE
                        SYNTAX Integer32
                        MAX-ACCESS read-only
                        STATUS current
                        DESCRIPTION
                                "The value of the minute"
                        ::= { fkAutoCliScheduleEntry 8 }

                
                -- 1.3.6.1.4.1.10428 9 1.101.1.11.3.1.1.9
                fkAutoCliScheduleScriptName OBJECT-TYPE
                        SYNTAX OCTET STRING
                        MAX-ACCESS read-only
                        STATUS current
                        DESCRIPTION
                                "The name of the script file"
                        ::= { fkAutoCliScheduleEntry 9 }

                
                -- 1.3.6.1.4.1.10428 9 1.101.1.11.3.1.1.10
                fkAutoCliScheduleTransferType OBJECT-TYPE
                        SYNTAX FkDefAutoCliScheduleTransferType
                        MAX-ACCESS read-only
                        STATUS current
                        DESCRIPTION
                                "The type of the transferation that indicate way to save output file"
                        ::= { fkAutoCliScheduleEntry 10 }

                
                -- 1.3.6.1.4.1.10428 9 1.101.1.11.3.1.1.11
                fkAutoCliScheduleLastExecutedTime OBJECT-TYPE
                        SYNTAX OCTET STRING
                        MAX-ACCESS read-only
                        STATUS current
                        DESCRIPTION
                                "The time of the last executed time"
                        ::= { fkAutoCliScheduleEntry 11 }

                
                -- 1.3.6.1.4.1.10428 9 1.101.1.11.3.1.1.12
                fkAutoCliScheduleOutputRule OBJECT-TYPE
                        SYNTAX OCTET STRING
                        MAX-ACCESS read-only
                        STATUS current
                        DESCRIPTION
                                "The Rule of the output file name"
                        ::= { fkAutoCliScheduleEntry 12 }

                
                -- 1.3.6.1.4.1.10428 9 1.101.1.11.3.1.1.13
                fkAutoCliScheduleLastResult OBJECT-TYPE
                        SYNTAX FkDefAutoCliScheduleResult
                        MAX-ACCESS read-only
                        STATUS current
                        DESCRIPTION
                                "The result of the last executed"
                        ::= { fkAutoCliScheduleEntry 13 }

                
                -- 1.3.6.1.4.1.10428 9 1.101.1.11.3.1.1.14
                fkAutoCliScheduleProfileName OBJECT-TYPE
                        SYNTAX OCTET STRING (SIZE (1..32))
                        MAX-ACCESS read-write
                        STATUS current
                        DESCRIPTION
                                "Description."
                        ::= { fkAutoCliScheduleEntry 14 }

                
                -- 1.3.6.1.4.1.10428 9 1.101.1.11.3.2
                fkAutoCliScheduleControl OBJECT IDENTIFIER ::= { fkAutoCliSchedule 2 }

                
                -- 1.3.6.1.4.1.10428 9 1.101.1.11.3.2.1
                fkAutoCliScheduleControlRequest OBJECT-TYPE
                        SYNTAX INTEGER
                                {
                                createAutoCliSchedule(1),
                                destroyAutoCliSchedule(2)
                                }
                        MAX-ACCESS read-write
                        STATUS current
                        DESCRIPTION
                                "Description."
                        ::= { fkAutoCliScheduleControl 1 }

                
                -- 1.3.6.1.4.1.10428 9 1.101.1.11.3.2.2
                fkAutoCliScheduleControlStatus OBJECT-TYPE
                        SYNTAX FkControlStatusType
                        MAX-ACCESS read-only
                        STATUS current
                        DESCRIPTION
                                "Description."
                        ::= { fkAutoCliScheduleControl 2 }

                
                -- 1.3.6.1.4.1.10428 9 1.101.1.11.3.2.3
                fkAutoCliScheduleControlTimer OBJECT-TYPE
                        SYNTAX Gauge32
                        MAX-ACCESS read-write
                        STATUS current
                        DESCRIPTION
                                "Description."
                        ::= { fkAutoCliScheduleControl 3 }

                
                -- 1.3.6.1.4.1.10428 9 1.101.1.11.3.2.4
                fkAutoCliScheduleControlTimeStamp OBJECT-TYPE
                        SYNTAX TimeTicks
                        MAX-ACCESS read-only
                        STATUS current
                        DESCRIPTION
                                "Description."
                        ::= { fkAutoCliScheduleControl 4 }

                
                -- 1.3.6.1.4.1.10428 9 1.101.1.11.3.2.5
                fkAutoCliScheduleControlReqResult OBJECT-TYPE
                        SYNTAX FkControlRequestResultType
                        MAX-ACCESS read-only
                        STATUS current
                        DESCRIPTION
                                "Description."
                        ::= { fkAutoCliScheduleControl 5 }

                
                -- 1.3.6.1.4.1.10428 9 1.101.1.11.3.2.6
                fkAutoCliScheduleControlName OBJECT-TYPE
                        SYNTAX OCTET STRING
                        MAX-ACCESS read-write
                        STATUS current
                        DESCRIPTION
                                "The name of the schedule name"
                        ::= { fkAutoCliScheduleControl 6 }

                
                -- 1.3.6.1.4.1.10428 9 1.101.1.11.3.2.7
                fkAutoCliScheduleControlType OBJECT-TYPE
                        SYNTAX FkDefAutoCliScheduleType
                        MAX-ACCESS read-write
                        STATUS current
                        DESCRIPTION
                                "The type of schedule.
                                Periodic(1) - scheduled with regular intervals.
                                At(2) - scheduled for exactly time.
                                Daily(3) - scheduled for every day.
                                Immediate(4) - scheduled immediately
                                "
                        ::= { fkAutoCliScheduleControl 7 }

                
                -- 1.3.6.1.4.1.10428 9 1.101.1.11.3.2.8
                fkAutoCliScheduleControlInterval OBJECT-TYPE
                        SYNTAX Integer32
                        MAX-ACCESS read-write
                        STATUS current
                        DESCRIPTION
                                "The period of execution time."
                        ::= { fkAutoCliScheduleControl 8 }

                
                -- 1.3.6.1.4.1.10428 9 1.101.1.11.3.2.9
                fkAutoCliScheduleControlYear OBJECT-TYPE
                        SYNTAX Integer32
                        MAX-ACCESS read-write
                        STATUS current
                        DESCRIPTION
                                "The value of the year "
                        ::= { fkAutoCliScheduleControl 9 }

                
                -- 1.3.6.1.4.1.10428 9 1.101.1.11.3.2.10
                fkAutoCliScheduleControlMonth OBJECT-TYPE
                        SYNTAX Integer32
                        MAX-ACCESS read-write
                        STATUS current
                        DESCRIPTION
                                "The value of the month"
                        ::= { fkAutoCliScheduleControl 10 }

                
                -- 1.3.6.1.4.1.10428 9 1.101.1.11.3.2.11
                fkAutoCliScheduleControlDay OBJECT-TYPE
                        SYNTAX Integer32
                        MAX-ACCESS read-write
                        STATUS current
                        DESCRIPTION
                                "Description."
                        ::= { fkAutoCliScheduleControl 11 }

                
                -- 1.3.6.1.4.1.10428 9 1.101.1.11.3.2.12
                fkAutoCliScheduleControlHour OBJECT-TYPE
                        SYNTAX Integer32
                        MAX-ACCESS read-write
                        STATUS current
                        DESCRIPTION
                                "The value of the hour"
                        ::= { fkAutoCliScheduleControl 12 }

                
                -- 1.3.6.1.4.1.10428 9 1.101.1.11.3.2.13
                fkAutoCliScheduleControlMinute OBJECT-TYPE
                        SYNTAX Integer32
                        MAX-ACCESS read-write
                        STATUS current
                        DESCRIPTION
                                "The value of the minute"
                        ::= { fkAutoCliScheduleControl 13 }

                
                -- 1.3.6.1.4.1.10428 9 1.101.1.11.3.2.14
                fkAutoCliScheduleControlScriptName OBJECT-TYPE
                        SYNTAX OCTET STRING
                        MAX-ACCESS read-write
                        STATUS current
                        DESCRIPTION
                                "The name of the script file"
                        ::= { fkAutoCliScheduleControl 14 }

                
                -- 1.3.6.1.4.1.10428 9 1.101.1.11.3.2.15
                fkAutoCliScheduleControlTransferType OBJECT-TYPE
                        SYNTAX FkDefAutoCliScheduleTransferType
                        MAX-ACCESS read-write
                        STATUS current
                        DESCRIPTION
                                "The type of the transferation that indicate way to save output file"
                        ::= { fkAutoCliScheduleControl 15 }

                
                -- 1.3.6.1.4.1.10428 9 1.101.1.11.3.2.16
                fkAutoCliScheduleControlOutputRule OBJECT-TYPE
                        SYNTAX OCTET STRING
                        MAX-ACCESS read-write
                        STATUS current
                        DESCRIPTION
                                "The Rule of the output file name"
                        ::= { fkAutoCliScheduleControl 16 }

                
                -- 1.3.6.1.4.1.10428 9 1.101.1.11.3.2.17
                fkAutoCliScheduleControlProfileName OBJECT-TYPE
                        SYNTAX OCTET STRING (SIZE (1..32))
                        MAX-ACCESS read-write
                        STATUS current
                        DESCRIPTION
                                "Description."
                        ::= { fkAutoCliScheduleControl 17 }

                
                -- 1.3.6.1.4.1.10428 9 1.101.1.11.3.3
                fkAutoCliScheduleNotifications OBJECT IDENTIFIER ::= { fkAutoCliSchedule 3 }

                
                -- 1.3.6.1.4.1.10428 9 1.101.1.11.3.3.1
                fkAutoCliScheduleCreated NOTIFICATION-TYPE
                        OBJECTS { fkAutoCliScheduleControlRequest, fkAutoCliScheduleControlTimeStamp, fkAutoCliScheduleControlReqResult, fkAutoCliScheduleType, fkAutoCliScheduleInterval, 
                                fkAutoCliScheduleYear, fkAutoCliScheduleMonth, fkAutoCliScheduleDay, fkAutoCliScheduleHour, fkAutoCliScheduleMinute, 
                                fkAutoCliScheduleScriptName, fkAutoCliScheduleTransferType, fkAutoCliScheduleOutputRule, fkAutoCliScheduleProfileName }
                        STATUS current
                        DESCRIPTION 
                                "Description."
                        ::= { fkAutoCliScheduleNotifications 1 }

                
                -- 1.3.6.1.4.1.10428 9 1.101.1.11.3.3.2
                fkAutoCliScheduleDestroyed NOTIFICATION-TYPE
                        OBJECTS { fkAutoCliScheduleControlRequest, fkAutoCliScheduleControlTimer, fkAutoCliScheduleControlReqResult, fkAutoCliScheduleControlName }
                        STATUS current
                        DESCRIPTION 
                                "Description."
                        ::= { fkAutoCliScheduleNotifications 2 }

                
                -- 1.3.6.1.4.1.10428 9 1.101.1.11.4
                fkAutoCliProfile OBJECT IDENTIFIER ::= { fkAutoCli 4 }

                
                -- 1.3.6.1.4.1.10428 9 1.101.1.11.4.1
                fkAutoCliProfileTable OBJECT-TYPE
                        SYNTAX SEQUENCE OF FkAutoCliProfileEntry
                        MAX-ACCESS not-accessible
                        STATUS current
                        DESCRIPTION
                                "Description."
                        ::= { fkAutoCliProfile 1 }

                
                -- 1.3.6.1.4.1.10428 9 1.101.1.11.4.1.1
                fkAutoCliProfileEntry OBJECT-TYPE
                        SYNTAX FkAutoCliProfileEntry
                        MAX-ACCESS not-accessible
                        STATUS current
                        DESCRIPTION
                                "Description."
                        INDEX { fkAutoCliProfileName }
                        ::= { fkAutoCliProfileTable 1 }

                
                FkAutoCliProfileEntry ::=
                        SEQUENCE { 
                                fkAutoCliProfileName
                                        OCTET STRING,
                                fkAutoCliProfileType
                                        INTEGER
                         }

                -- 1.3.6.1.4.1.10428 9 1.101.1.11.4.1.1.1
                fkAutoCliProfileName OBJECT-TYPE
                        SYNTAX OCTET STRING (SIZE (1..32))
                        MAX-ACCESS read-write
                        STATUS current
                        DESCRIPTION
                                "The name of the profile name."
                        ::= { fkAutoCliProfileEntry 1 }

                
                -- 1.3.6.1.4.1.10428 9 1.101.1.11.4.1.1.2
                fkAutoCliProfileType OBJECT-TYPE
                        SYNTAX INTEGER
                                {
                                tftp(1),
                                ftp(2)
                                }
                        MAX-ACCESS read-write
                        STATUS current
                        DESCRIPTION
                                "The name of the profile type."
                        ::= { fkAutoCliProfileEntry 2 }

                
                -- 1.3.6.1.4.1.10428 9 1.101.1.11.4.2
                fkAutoCliProfileControl OBJECT IDENTIFIER ::= { fkAutoCliProfile 2 }

                
                -- 1.3.6.1.4.1.10428 9 1.101.1.11.4.2.1
                fkAutoCliProfileControlRequest OBJECT-TYPE
                        SYNTAX INTEGER
                                {
                                createAutoCliProfile(1),
                                destroyAutoCliProfile(2)
                                }
                        MAX-ACCESS read-write
                        STATUS current
                        DESCRIPTION
                                "Description."
                        ::= { fkAutoCliProfileControl 1 }

                
                -- 1.3.6.1.4.1.10428 9 1.101.1.11.4.2.2
                fkAutoCliProfileControlStatus OBJECT-TYPE
                        SYNTAX FkControlStatusType
                        MAX-ACCESS read-only
                        STATUS current
                        DESCRIPTION
                                "Description."
                        ::= { fkAutoCliProfileControl 2 }

                
                -- 1.3.6.1.4.1.10428 9 1.101.1.11.4.2.3
                fkAutoCliProfileControlTimer OBJECT-TYPE
                        SYNTAX Gauge32
                        MAX-ACCESS read-write
                        STATUS current
                        DESCRIPTION
                                "Description."
                        ::= { fkAutoCliProfileControl 3 }

                
                -- 1.3.6.1.4.1.10428 9 1.101.1.11.4.2.4
                fkAutoCliProfileControlTimeStamp OBJECT-TYPE
                        SYNTAX TimeTicks
                        MAX-ACCESS read-only
                        STATUS current
                        DESCRIPTION
                                "Description."
                        ::= { fkAutoCliProfileControl 4 }

                
                -- 1.3.6.1.4.1.10428 9 1.101.1.11.4.2.5
                fkAutoCliProfileControlReqResult OBJECT-TYPE
                        SYNTAX FkControlRequestResultType
                        MAX-ACCESS read-only
                        STATUS current
                        DESCRIPTION
                                "Description."
                        ::= { fkAutoCliProfileControl 5 }

                
                -- 1.3.6.1.4.1.10428 9 1.101.1.11.4.2.6
                fkAutoCliProfileControlName OBJECT-TYPE
                        SYNTAX OCTET STRING (SIZE (1..32))
                        MAX-ACCESS read-write
                        STATUS current
                        DESCRIPTION
                                "The name of the profile name"
                        ::= { fkAutoCliProfileControl 6 }

                
                -- 1.3.6.1.4.1.10428 9 1.101.1.11.4.2.7
                fkAutoCliProfileControlType OBJECT-TYPE
                        SYNTAX INTEGER
                                {
                                tftp(1),
                                ftp(2)
                                }
                        MAX-ACCESS read-write
                        STATUS current
                        DESCRIPTION
                                "The name of the profile type"
                        ::= { fkAutoCliProfileControl 7 }

                
                -- 1.3.6.1.4.1.10428 9 1.101.1.11.4.3
                fkAutoCliProfileNotifications OBJECT IDENTIFIER ::= { fkAutoCliProfile 3 }

                
                -- 1.3.6.1.4.1.10428 9 1.101.1.11.4.3.1
                fkAutoCliProfileCreated NOTIFICATION-TYPE
                        OBJECTS { fkAutoCliProfileControlRequest, fkAutoCliProfileControlTimeStamp, fkAutoCliProfileControlReqResult, fkAutoCliProfileType }
                        STATUS current
                        DESCRIPTION 
                                "Description."
                        ::= { fkAutoCliProfileNotifications 1 }

                
                -- 1.3.6.1.4.1.10428 9 1.101.1.11.4.3.2
                fkAutoCliProfileDestroyed NOTIFICATION-TYPE
                        OBJECTS { fkAutoCliProfileControlRequest, fkAutoCliProfileControlTimeStamp, fkAutoCliProfileControlReqResult, fkAutoCliProfileControlName }
                        STATUS current
                        DESCRIPTION 
                                "Description."
                        ::= { fkAutoCliProfileNotifications 2 }

                
                -- 1.3.6.1.4.1.10428 9 1.101.1.11.5
                fkAutoCliProfileServer OBJECT IDENTIFIER ::= { fkAutoCli 5 }

                
                -- 1.3.6.1.4.1.10428 9 1.101.1.11.5.1
                fkAutoCliProfileServerTable OBJECT-TYPE
                        SYNTAX SEQUENCE OF FkAutoCliProfileServerEntry
                        MAX-ACCESS not-accessible
                        STATUS current
                        DESCRIPTION
                                "Description."
                        ::= { fkAutoCliProfileServer 1 }

                
                -- 1.3.6.1.4.1.10428 9 1.101.1.11.5.1.1
                fkAutoCliProfileServerEntry OBJECT-TYPE
                        SYNTAX FkAutoCliProfileServerEntry
                        MAX-ACCESS not-accessible
                        STATUS current
                        DESCRIPTION
                                "Description."
                        INDEX { fkAutoCliProfileName, fkAutoCliProfileServerIpAddress }
                        ::= { fkAutoCliProfileServerTable 1 }

                
                FkAutoCliProfileServerEntry ::=
                        SEQUENCE { 
                                fkAutoCliProfileServerType
                                        INTEGER,
                                fkAutoCliProfileServerIpAddress
                                        IpAddress,
                                fkAutoCliProfileServerUser
                                        OCTET STRING,
                                fkAutoCliProfileServerPassword
                                        OCTET STRING,
                                fkAutoCliProfileServerDir
                                        OCTET STRING
                         }

                -- 1.3.6.1.4.1.10428 9 1.101.1.11.5.1.1.1
                fkAutoCliProfileServerType OBJECT-TYPE
                        SYNTAX INTEGER
                                {
                                tftp(1),
                                ftp(2)
                                }
                        MAX-ACCESS read-write
                        STATUS current
                        DESCRIPTION
                                "The name of the profile's remote-server type."
                        ::= { fkAutoCliProfileServerEntry 1 }

                
                -- 1.3.6.1.4.1.10428 9 1.101.1.11.5.1.1.2
                fkAutoCliProfileServerIpAddress OBJECT-TYPE
                        SYNTAX IpAddress
                        MAX-ACCESS read-write
                        STATUS current
                        DESCRIPTION
                                "The name of the profile's remote-server ip."
                        ::= { fkAutoCliProfileServerEntry 2 }

                
                -- 1.3.6.1.4.1.10428 9 1.101.1.11.5.1.1.3
                fkAutoCliProfileServerUser OBJECT-TYPE
                        SYNTAX OCTET STRING (SIZE (0..32))
                        MAX-ACCESS read-write
                        STATUS current
                        DESCRIPTION
                                "The name of the profile's remote-server user."
                        ::= { fkAutoCliProfileServerEntry 3 }

                
                -- 1.3.6.1.4.1.10428 9 1.101.1.11.5.1.1.4
                fkAutoCliProfileServerPassword OBJECT-TYPE
                        SYNTAX OCTET STRING (SIZE (0..32))
                        MAX-ACCESS read-write
                        STATUS current
                        DESCRIPTION
                                "The name of the profile's remote-server password."
                        ::= { fkAutoCliProfileServerEntry 4 }

                
                -- 1.3.6.1.4.1.10428 9 1.101.1.11.5.1.1.5
                fkAutoCliProfileServerDir OBJECT-TYPE
                        SYNTAX OCTET STRING (SIZE (0..128))
                        MAX-ACCESS read-write
                        STATUS current
                        DESCRIPTION
                                "The name of the profile's remote-server directory."
                        ::= { fkAutoCliProfileServerEntry 5 }

                
                -- 1.3.6.1.4.1.10428 9 1.101.1.11.5.2
                fkAutoCliProfileServerControl OBJECT IDENTIFIER ::= { fkAutoCliProfileServer 2 }

                
                -- 1.3.6.1.4.1.10428 9 1.101.1.11.5.2.1
                fkAutoCliProfileServerControlRequest OBJECT-TYPE
                        SYNTAX INTEGER
                                {
                                createAutoCliProfileServer(1),
                                destroyAutoCliProfileServer(2),
                                destroyAutoCliProfileServerAll(3)
                                }
                        MAX-ACCESS read-write
                        STATUS current
                        DESCRIPTION
                                "Description."
                        ::= { fkAutoCliProfileServerControl 1 }

                
                -- 1.3.6.1.4.1.10428 9 1.101.1.11.5.2.2
                fkAutoCliProfileServerControlStatus OBJECT-TYPE
                        SYNTAX FkControlStatusType
                        MAX-ACCESS read-only
                        STATUS current
                        DESCRIPTION
                                "Description."
                        ::= { fkAutoCliProfileServerControl 2 }

                
                -- 1.3.6.1.4.1.10428 9 1.101.1.11.5.2.3
                fkAutoCliProfileServerControlTimer OBJECT-TYPE
                        SYNTAX Gauge32
                        MAX-ACCESS read-write
                        STATUS current
                        DESCRIPTION
                                "Description."
                        ::= { fkAutoCliProfileServerControl 3 }

                
                -- 1.3.6.1.4.1.10428 9 1.101.1.11.5.2.4
                fkAutoCliProfileServerControlTimeStamp OBJECT-TYPE
                        SYNTAX TimeTicks
                        MAX-ACCESS read-only
                        STATUS current
                        DESCRIPTION
                                "Description."
                        ::= { fkAutoCliProfileServerControl 4 }

                
                -- 1.3.6.1.4.1.10428 9 1.101.1.11.5.2.5
                fkAutoCliProfileServerControlReqResult OBJECT-TYPE
                        SYNTAX FkControlRequestResultType
                        MAX-ACCESS read-only
                        STATUS current
                        DESCRIPTION
                                "Description."
                        ::= { fkAutoCliProfileServerControl 5 }

                
                -- 1.3.6.1.4.1.10428 9 1.101.1.11.5.2.6
                fkAutoCliProfileServerControlProfName OBJECT-TYPE
                        SYNTAX OCTET STRING (SIZE (1..32))
                        MAX-ACCESS read-write
                        STATUS current
                        DESCRIPTION
                                "The name of the profile name"
                        ::= { fkAutoCliProfileServerControl 6 }

                
                -- 1.3.6.1.4.1.10428 9 1.101.1.11.5.2.7
                fkAutoCliProfileServerControlIpAddress OBJECT-TYPE
                        SYNTAX IpAddress
                        MAX-ACCESS read-write
                        STATUS current
                        DESCRIPTION
                                "Description."
                        ::= { fkAutoCliProfileServerControl 7 }

                
                -- 1.3.6.1.4.1.10428 9 1.101.1.11.5.2.8
                fkAutoCliProfileServerControlUser OBJECT-TYPE
                        SYNTAX OCTET STRING (SIZE (0..32))
                        MAX-ACCESS read-write
                        STATUS current
                        DESCRIPTION
                                "Description."
                        ::= { fkAutoCliProfileServerControl 8 }

                
                -- 1.3.6.1.4.1.10428 9 1.101.1.11.5.2.9
                fkAutoCliProfileServerControlPassword OBJECT-TYPE
                        SYNTAX OCTET STRING (SIZE (0..32))
                        MAX-ACCESS read-write
                        STATUS current
                        DESCRIPTION
                                "Description."
                        ::= { fkAutoCliProfileServerControl 9 }

                
                -- 1.3.6.1.4.1.10428 9 1.101.1.11.5.2.10
                fkAutoCliProfileServerControlDir OBJECT-TYPE
                        SYNTAX OCTET STRING (SIZE (0..128))
                        MAX-ACCESS read-write
                        STATUS current
                        DESCRIPTION
                                "Description."
                        ::= { fkAutoCliProfileServerControl 10 }

                
                -- 1.3.6.1.4.1.10428 9 1.101.1.11.5.3
                fkAutoCliProfileServerNotifications OBJECT IDENTIFIER ::= { fkAutoCliProfileServer 3 }

                
                -- 1.3.6.1.4.1.10428 9 1.101.1.11.5.3.1
                fkAutoCliProfileServerCreated NOTIFICATION-TYPE
                        OBJECTS { fkAutoCliProfileServerControlRequest, fkAutoCliProfileServerControlTimeStamp, fkAutoCliProfileServerControlReqResult, fkAutoCliProfileServerType, fkAutoCliProfileServerUser, 
                                fkAutoCliProfileServerPassword, fkAutoCliProfileServerDir }
                        STATUS current
                        DESCRIPTION 
                                "Description."
                        ::= { fkAutoCliProfileServerNotifications 1 }

                
                -- 1.3.6.1.4.1.10428 9 1.101.1.11.5.3.2
                fkAutoCliProfileServerDestroyed NOTIFICATION-TYPE
                        OBJECTS { fkAutoCliProfileServerControlRequest, fkAutoCliProfileServerControlTimeStamp, fkAutoCliProfileServerControlReqResult, fkAutoCliProfileServerControlProfName, fkAutoCliProfileServerControlIpAddress
                                 }
                        STATUS current
                        DESCRIPTION 
                                "Description."
                        ::= { fkAutoCliProfileServerNotifications 2 }

                
                -- 1.3.6.1.4.1.10428 9 1.101.1.11.5.3.3
                fkAutoCliProfileServerAllDestroyed NOTIFICATION-TYPE
                        OBJECTS { fkAutoCliProfileServerControlRequest, fkAutoCliProfileServerControlTimeStamp, fkAutoCliProfileServerControlReqResult, fkAutoCliProfileServerControlProfName }
                        STATUS current
                        DESCRIPTION 
                                "Description."
                        ::= { fkAutoCliProfileServerNotifications 3 }

                
                -- 1.3.6.1.4.1.10428 9 1.101.1.11.6
                fkAutoCliOutputMemory OBJECT IDENTIFIER ::= { fkAutoCli 6 }

                
                -- 1.3.6.1.4.1.10428 9 1.101.1.11.6.1
                fkAutoCliOutputMemoryFileTable OBJECT-TYPE
                        SYNTAX SEQUENCE OF FkAutoCliOutputMemoryFileEntry
                        MAX-ACCESS not-accessible
                        STATUS current
                        DESCRIPTION
                                "Description."
                        ::= { fkAutoCliOutputMemory 1 }

                
                -- 1.3.6.1.4.1.10428 9 1.101.1.11.6.1.1
                fkAutoCliOutputMemoryFileEntry OBJECT-TYPE
                        SYNTAX FkAutoCliOutputMemoryFileEntry
                        MAX-ACCESS not-accessible
                        STATUS current
                        DESCRIPTION
                                "Description."
                        INDEX { fkAutoCliOutputMemoryFileId }
                        ::= { fkAutoCliOutputMemoryFileTable 1 }

                
                FkAutoCliOutputMemoryFileEntry ::=
                        SEQUENCE { 
                                fkAutoCliOutputMemoryFileId
                                        INTEGER,
                                fkAutoCliOutputMemoryFileName
                                        OCTET STRING,
                                fkAutoCliOutputMemoryFileSize
                                        Integer32,
                                fkAutoCliOutputMemoryFileUpdatedTime
                                        OCTET STRING
                         }

                -- 1.3.6.1.4.1.10428 9 1.101.1.11.6.1.1.1
                fkAutoCliOutputMemoryFileId OBJECT-TYPE
                        SYNTAX INTEGER (1..2147483647)
                        MAX-ACCESS read-only
                        STATUS current
                        DESCRIPTION
                                "The id of the output file."
                        ::= { fkAutoCliOutputMemoryFileEntry 1 }

                
                -- 1.3.6.1.4.1.10428 9 1.101.1.11.6.1.1.2
                fkAutoCliOutputMemoryFileName OBJECT-TYPE
                        SYNTAX OCTET STRING
                        MAX-ACCESS read-only
                        STATUS current
                        DESCRIPTION
                                "The name of the output file."
                        ::= { fkAutoCliOutputMemoryFileEntry 2 }

                
                -- 1.3.6.1.4.1.10428 9 1.101.1.11.6.1.1.3
                fkAutoCliOutputMemoryFileSize OBJECT-TYPE
                        SYNTAX Integer32
                        MAX-ACCESS read-only
                        STATUS current
                        DESCRIPTION
                                "The file-size of the output file."
                        ::= { fkAutoCliOutputMemoryFileEntry 3 }

                
                -- 1.3.6.1.4.1.10428 9 1.101.1.11.6.1.1.4
                fkAutoCliOutputMemoryFileUpdatedTime OBJECT-TYPE
                        SYNTAX OCTET STRING
                        MAX-ACCESS read-only
                        STATUS current
                        DESCRIPTION
                                "The updated time of the output file"
                        ::= { fkAutoCliOutputMemoryFileEntry 4 }

                
                -- 1.3.6.1.4.1.10428 9 1.101.1.11.6.2
                fkAutoCliOutputMemoryFileControl OBJECT IDENTIFIER ::= { fkAutoCliOutputMemory 2 }

                
                -- 1.3.6.1.4.1.10428 9 1.101.1.11.6.2.1
                fkAutoCliOutputMemoryFileControlRequest OBJECT-TYPE
                        SYNTAX INTEGER
                                {
                                ftpputOutputFile(1),
                                tftpputOutputFile(2),
                                destroyOutputFile(3)
                                }
                        MAX-ACCESS read-write
                        STATUS current
                        DESCRIPTION
                                "Description."
                        ::= { fkAutoCliOutputMemoryFileControl 1 }

                
                -- 1.3.6.1.4.1.10428 9 1.101.1.11.6.2.2
                fkAutoCliOutputMemoryFileControlStatus OBJECT-TYPE
                        SYNTAX FkControlStatusType
                        MAX-ACCESS read-only
                        STATUS current
                        DESCRIPTION
                                "Description."
                        ::= { fkAutoCliOutputMemoryFileControl 2 }

                
                -- 1.3.6.1.4.1.10428 9 1.101.1.11.6.2.3
                fkAutoCliOutputMemoryFileControlTimer OBJECT-TYPE
                        SYNTAX Gauge32
                        MAX-ACCESS read-write
                        STATUS current
                        DESCRIPTION
                                "Description."
                        ::= { fkAutoCliOutputMemoryFileControl 3 }

                
                -- 1.3.6.1.4.1.10428 9 1.101.1.11.6.2.4
                fkAutoCliOutputMemoryFileControlTimeStamp OBJECT-TYPE
                        SYNTAX TimeTicks
                        MAX-ACCESS read-only
                        STATUS current
                        DESCRIPTION
                                "Description."
                        ::= { fkAutoCliOutputMemoryFileControl 4 }

                
                -- 1.3.6.1.4.1.10428 9 1.101.1.11.6.2.5
                fkAutoCliOutputMemoryFileControlReqResult OBJECT-TYPE
                        SYNTAX FkControlRequestResultType
                        MAX-ACCESS read-only
                        STATUS current
                        DESCRIPTION
                                "Description."
                        ::= { fkAutoCliOutputMemoryFileControl 5 }

                
                -- 1.3.6.1.4.1.10428 9 1.101.1.11.6.2.6
                fkAutoCliOutputMemoryFileControlServer OBJECT-TYPE
                        SYNTAX IpAddress
                        MAX-ACCESS read-write
                        STATUS current
                        DESCRIPTION
                                "The Ipaddress of the ftp server to put the output file."
                        ::= { fkAutoCliOutputMemoryFileControl 6 }

                
                -- 1.3.6.1.4.1.10428 9 1.101.1.11.6.2.7
                fkAutoCliOutputMemoryFileControlUserName OBJECT-TYPE
                        SYNTAX OCTET STRING
                        MAX-ACCESS read-write
                        STATUS current
                        DESCRIPTION
                                "The username of the ftp server to put the output file."
                        ::= { fkAutoCliOutputMemoryFileControl 7 }

                
                -- 1.3.6.1.4.1.10428 9 1.101.1.11.6.2.8
                fkAutoCliOutputMemoryFileControlPassword OBJECT-TYPE
                        SYNTAX OCTET STRING
                        MAX-ACCESS read-write
                        STATUS current
                        DESCRIPTION
                                "The password of the ftp server to put the output file."
                        ::= { fkAutoCliOutputMemoryFileControl 8 }

                
                -- 1.3.6.1.4.1.10428 9 1.101.1.11.6.2.9
                fkAutoCliOutputMemoryFileControlOutputFileName OBJECT-TYPE
                        SYNTAX OCTET STRING
                        MAX-ACCESS read-write
                        STATUS current
                        DESCRIPTION
                                "The output file name."
                        ::= { fkAutoCliOutputMemoryFileControl 9 }

                
                -- 1.3.6.1.4.1.10428 9 1.101.1.11.6.2.10
                fkAutoCliOutputMemoryFileControlRemotePath OBJECT-TYPE
                        SYNTAX OCTET STRING
                        MAX-ACCESS read-write
                        STATUS current
                        DESCRIPTION
                                "The remote path of the ftp server to put the output file"
                        ::= { fkAutoCliOutputMemoryFileControl 10 }

                
                -- 1.3.6.1.4.1.10428 9 1.101.1.11.6.3
                fkAutoCliOutputMemoryFileNotification OBJECT IDENTIFIER ::= { fkAutoCliOutputMemory 3 }

                
                -- 1.3.6.1.4.1.10428 9 1.101.1.11.6.3.1
                fkAutoCliOutputMemoryFileFtpCreated NOTIFICATION-TYPE
                        OBJECTS { fkAutoCliOutputMemoryFileControlRequest, fkAutoCliOutputMemoryFileControlTimeStamp, fkAutoCliOutputMemoryFileControlReqResult, fkAutoCliOutputMemoryFileName }
                        STATUS current
                        DESCRIPTION 
                                "Description."
                        ::= { fkAutoCliOutputMemoryFileNotification 1 }

                
                -- 1.3.6.1.4.1.10428 9 1.101.1.11.6.3.2
                fkAutoCliOutputMemoryFileTftpCreated NOTIFICATION-TYPE
                        OBJECTS { fkAutoCliOutputMemoryFileControlRequest, fkAutoCliOutputMemoryFileControlTimeStamp, fkAutoCliOutputMemoryFileControlReqResult, fkAutoCliOutputMemoryFileName }
                        STATUS current
                        DESCRIPTION 
                                "Description."
                        ::= { fkAutoCliOutputMemoryFileNotification 2 }

                
                -- 1.3.6.1.4.1.10428 9 1.101.1.11.6.3.3
                fkAutoCliOutputMemoryFileDestroyed NOTIFICATION-TYPE
                        OBJECTS { fkAutoCliOutputMemoryFileControlRequest, fkAutoCliOutputMemoryFileControlTimeStamp, fkAutoCliOutputMemoryFileControlOutputFileName, fkAutoCliOutputMemoryFileControlReqResult }
                        STATUS current
                        DESCRIPTION 
                                "Description."
                        ::= { fkAutoCliOutputMemoryFileNotification 3 }

                
                -- 1.3.6.1.4.1.10428 9 1.101.1.12
                fkAutoReset OBJECT IDENTIFIER ::= { fkSystemMaintenance 12 }

                
                -- 1.3.6.1.4.1.10428 9 1.101.1.12.1
                fkAutoResetPing OBJECT IDENTIFIER ::= { fkAutoReset 1 }

                
                -- 1.3.6.1.4.1.10428 9 1.101.1.12.1.1
                fkAutoResetPingInfo OBJECT IDENTIFIER ::= { fkAutoResetPing 1 }

                
                -- 1.3.6.1.4.1.10428 9 1.101.1.12.1.1.1
                fkAutoResetPingConfStatus OBJECT-TYPE
                        SYNTAX EnableFlag
                        MAX-ACCESS read-only
                        STATUS current
                        DESCRIPTION
                                "The administrative state of AutoResetPing "
                        ::= { fkAutoResetPingInfo 1 }

                
                -- 1.3.6.1.4.1.10428 9 1.101.1.12.1.1.2
                fkAutoResetPingIpAddress OBJECT-TYPE
                        SYNTAX IpAddress
                        MAX-ACCESS read-only
                        STATUS current
                        DESCRIPTION
                                "Gateway Ip address"
                        ::= { fkAutoResetPingInfo 2 }

                
                -- 1.3.6.1.4.1.10428 9 1.101.1.12.1.1.3
                fkAutoResetPingTransactionInterval OBJECT-TYPE
                        SYNTAX Integer32
                        MAX-ACCESS read-only
                        STATUS current
                        DESCRIPTION
                                "The interval between ping transaction (10 - 86400)"
                        ::= { fkAutoResetPingInfo 3 }

                
                -- 1.3.6.1.4.1.10428 9 1.101.1.12.1.1.4
                fkAutoResetPingNumberOfRequest OBJECT-TYPE
                        SYNTAX Integer32
                        MAX-ACCESS read-only
                        STATUS current
                        DESCRIPTION
                                "The number of ping request in 1 transaction (1-10)"
                        ::= { fkAutoResetPingInfo 4 }

                
                -- 1.3.6.1.4.1.10428 9 1.101.1.12.1.1.5
                fkAutoResetPingRequestInterval OBJECT-TYPE
                        SYNTAX Integer32
                        MAX-ACCESS read-only
                        STATUS current
                        DESCRIPTION
                                "The interval between ping request (1 - 100)"
                        ::= { fkAutoResetPingInfo 5 }

                
                -- 1.3.6.1.4.1.10428 9 1.101.1.12.1.1.6
                fkAutoResetPingTimeoutOfRequest OBJECT-TYPE
                        SYNTAX Integer32
                        MAX-ACCESS read-only
                        STATUS current
                        DESCRIPTION
                                "The timeout value for waiting reply message (1 - 10)"
                        ::= { fkAutoResetPingInfo 6 }

                
                -- 1.3.6.1.4.1.10428 9 1.101.1.12.1.1.7
                fkAutoResetPingLossThreshold OBJECT-TYPE
                        SYNTAX Integer32
                        MAX-ACCESS read-only
                        STATUS current
                        DESCRIPTION
                                "The threshold value of ping-transaction loss count for reset. (1 - 100)
                                 If ping-transaction loss count is reached at this value, The system will be reset
                                
                                "
                        ::= { fkAutoResetPingInfo 7 }

                
                -- 1.3.6.1.4.1.10428 9 1.101.1.12.1.1.8
                fkAutoResetPingEnableTime OBJECT-TYPE
                        SYNTAX OCTET STRING
                        MAX-ACCESS read-only
                        STATUS current
                        DESCRIPTION
                                "The time of the autoresetping status was enabled"
                        ::= { fkAutoResetPingInfo 8 }

                
                -- 1.3.6.1.4.1.10428 9 1.101.1.12.1.1.9
                fkAutoResetPingRequestCount OBJECT-TYPE
                        SYNTAX Integer32
                        MAX-ACCESS read-only
                        STATUS current
                        DESCRIPTION
                                "The count of request message in current transaction"
                        ::= { fkAutoResetPingInfo 9 }

                
                -- 1.3.6.1.4.1.10428 9 1.101.1.12.1.1.10
                fkAutoResetPingReplyCount OBJECT-TYPE
                        SYNTAX Integer32
                        MAX-ACCESS read-only
                        STATUS current
                        DESCRIPTION
                                "The count of reply message in current transaction"
                        ::= { fkAutoResetPingInfo 10 }

                
                -- 1.3.6.1.4.1.10428 9 1.101.1.12.1.1.11
                fkAutoResetPingLossCount OBJECT-TYPE
                        SYNTAX Integer32
                        MAX-ACCESS read-only
                        STATUS current
                        DESCRIPTION
                                "The count of loss message in current transaction"
                        ::= { fkAutoResetPingInfo 11 }

                
                -- 1.3.6.1.4.1.10428 9 1.101.1.12.1.1.12
                fkAutoResetPingTotalPingTransaction OBJECT-TYPE
                        SYNTAX Counter64
                        MAX-ACCESS read-only
                        STATUS current
                        DESCRIPTION
                                "The total count of ping transaction"
                        ::= { fkAutoResetPingInfo 12 }

                
                -- 1.3.6.1.4.1.10428 9 1.101.1.12.1.1.13
                fkAutoResetPingTotalLossTransaction OBJECT-TYPE
                        SYNTAX Counter64
                        MAX-ACCESS read-only
                        STATUS current
                        DESCRIPTION
                                "The total count of loss transaction"
                        ::= { fkAutoResetPingInfo 13 }

                
                -- 1.3.6.1.4.1.10428 9 1.101.1.12.1.1.14
                fkAutoResetPingRebootThreshold OBJECT-TYPE
                        SYNTAX INTEGER (1..100)
                        MAX-ACCESS read-only
                        STATUS current
                        DESCRIPTION
                                "The threshold of reboot-counter for autoReset. (1 - 100)
                                 If system is rebooted more than this value, system is not automatically reset anymore.
                                "
                        ::= { fkAutoResetPingInfo 14 }

                
                -- 1.3.6.1.4.1.10428 9 1.101.1.12.1.1.15
                fkAutoResetPingRebootCounter OBJECT-TYPE
                        SYNTAX Integer32
                        MAX-ACCESS read-only
                        STATUS current
                        DESCRIPTION
                                "The count of system-reboot"
                        ::= { fkAutoResetPingInfo 15 }

                
                -- 1.3.6.1.4.1.10428 9 1.101.1.12.1.1.16
                fkAutoResetPingRebootRecoveryTime OBJECT-TYPE
                        SYNTAX Integer32 (10..14400)
                        MAX-ACCESS read-only
                        STATUS current
                        DESCRIPTION
                                "The reboot recovery time 10-14400(minute)"
                        ::= { fkAutoResetPingInfo 16 }

                
                -- 1.3.6.1.4.1.10428 9 1.101.1.12.1.2
                fkAutoResetPingControl OBJECT IDENTIFIER ::= { fkAutoResetPing 2 }

                
                -- 1.3.6.1.4.1.10428 9 1.101.1.12.1.2.1
                fkAutoResetPingControlRequest OBJECT-TYPE
                        SYNTAX INTEGER
                                {
                                setAutoResetPingStatus(1),
                                modifyAutoResetPingInfo(2),
                                setAutoResetPingRebootCtrl(3),
                                clearAutoResetPingRebootCounter(4)
                                }
                        MAX-ACCESS read-write
                        STATUS current
                        DESCRIPTION
                                "Description."
                        ::= { fkAutoResetPingControl 1 }

                
                -- 1.3.6.1.4.1.10428 9 1.101.1.12.1.2.2
                fkAutoResetPingControlStatus OBJECT-TYPE
                        SYNTAX FkControlStatusType
                        MAX-ACCESS read-only
                        STATUS current
                        DESCRIPTION
                                "Description."
                        ::= { fkAutoResetPingControl 2 }

                
                -- 1.3.6.1.4.1.10428 9 1.101.1.12.1.2.3
                fkAutoResetPingControlTimer OBJECT-TYPE
                        SYNTAX Gauge32
                        MAX-ACCESS read-write
                        STATUS current
                        DESCRIPTION
                                "Description."
                        ::= { fkAutoResetPingControl 3 }

                
                -- 1.3.6.1.4.1.10428 9 1.101.1.12.1.2.4
                fkAutoResetPingControlTimeStamp OBJECT-TYPE
                        SYNTAX TimeTicks
                        MAX-ACCESS read-only
                        STATUS current
                        DESCRIPTION
                                "Description."
                        ::= { fkAutoResetPingControl 4 }

                
                -- 1.3.6.1.4.1.10428 9 1.101.1.12.1.2.5
                fkAutoResetPingControlReqResult OBJECT-TYPE
                        SYNTAX FkControlRequestResultType
                        MAX-ACCESS read-only
                        STATUS current
                        DESCRIPTION
                                "Description."
                        ::= { fkAutoResetPingControl 5 }

                
                -- 1.3.6.1.4.1.10428 9 1.101.1.12.1.2.6
                fkAutoResetPingControlConfStatus OBJECT-TYPE
                        SYNTAX EnableFlag
                        MAX-ACCESS read-write
                        STATUS current
                        DESCRIPTION
                                "The administrative state of AutoResetPing "
                        ::= { fkAutoResetPingControl 6 }

                
                -- 1.3.6.1.4.1.10428 9 1.101.1.12.1.2.7
                fkAutoResetPingControlIpAddress OBJECT-TYPE
                        SYNTAX IpAddress
                        MAX-ACCESS read-write
                        STATUS current
                        DESCRIPTION
                                "Gateway Ip address"
                        ::= { fkAutoResetPingControl 7 }

                
                -- 1.3.6.1.4.1.10428 9 1.101.1.12.1.2.8
                fkAutoResetPingControlTransactionInterval OBJECT-TYPE
                        SYNTAX Integer32
                        MAX-ACCESS read-write
                        STATUS current
                        DESCRIPTION
                                "The interval between ping transaction (10 - 86400)"
                        ::= { fkAutoResetPingControl 8 }

                
                -- 1.3.6.1.4.1.10428 9 1.101.1.12.1.2.9
                fkAutoResetPingControlNumberOfRequest OBJECT-TYPE
                        SYNTAX Integer32
                        MAX-ACCESS read-write
                        STATUS current
                        DESCRIPTION
                                "The number of ping request in 1 transaction (1-10)"
                        ::= { fkAutoResetPingControl 9 }

                
                -- 1.3.6.1.4.1.10428 9 1.101.1.12.1.2.10
                fkAutoResetPingControlRequestInterval OBJECT-TYPE
                        SYNTAX Integer32
                        MAX-ACCESS read-write
                        STATUS current
                        DESCRIPTION
                                "The interval between ping request (1 - 100)"
                        ::= { fkAutoResetPingControl 10 }

                
                -- 1.3.6.1.4.1.10428 9 1.101.1.12.1.2.11
                fkAutoResetPingControlTimeoutOfRequest OBJECT-TYPE
                        SYNTAX Integer32
                        MAX-ACCESS read-write
                        STATUS current
                        DESCRIPTION
                                "The timeout value for waiting reply message (1 - 10)"
                        ::= { fkAutoResetPingControl 11 }

                
                -- 1.3.6.1.4.1.10428 9 1.101.1.12.1.2.12
                fkAutoResetPingControlPingLossThreshold OBJECT-TYPE
                        SYNTAX Integer32
                        MAX-ACCESS read-write
                        STATUS current
                        DESCRIPTION
                                "The threshold value of ping-transaction loss count for reset. (1 - 100)
                                 If ping-transaction loss count is reached at this value, The system will be reset
                                "
                        ::= { fkAutoResetPingControl 12 }

                
                -- 1.3.6.1.4.1.10428 9 1.101.1.12.1.2.13
                fkAutoResetPingControlRebootThreshold OBJECT-TYPE
                        SYNTAX INTEGER (1..100)
                        MAX-ACCESS read-write
                        STATUS current
                        DESCRIPTION
                                "The threshold of reboot-counter for autoReset. (1 - 100)
                                 If system is rebooted more than this value, system is not automatically reset anymore."
                        ::= { fkAutoResetPingControl 13 }

                
                -- 1.3.6.1.4.1.10428 9 1.101.1.12.1.2.14
                fkAutoResetPingControlRebootRecoveryTime OBJECT-TYPE
                        SYNTAX Integer32 (10..14400)
                        MAX-ACCESS read-write
                        STATUS current
                        DESCRIPTION
                                "The reboot recovery time 10-14400(minute)"
                        ::= { fkAutoResetPingControl 14 }

                
                -- 1.3.6.1.4.1.10428 9 1.101.1.12.1.3
                fkAutoResetPingNotification OBJECT IDENTIFIER ::= { fkAutoResetPing 3 }

                
                -- 1.3.6.1.4.1.10428 9 1.101.1.12.1.3.1
                fkAutoResetPingStatusChanged NOTIFICATION-TYPE
                        OBJECTS { fkAutoResetPingControlRequest, fkAutoResetPingControlTimeStamp, fkAutoResetPingControlReqResult, fkAutoResetPingConfStatus }
                        STATUS current
                        DESCRIPTION 
                                "setAutoResetPingStatus"
                        ::= { fkAutoResetPingNotification 1 }

                
                -- 1.3.6.1.4.1.10428 9 1.101.1.12.1.3.2
                fkAutoResetPingInfoModified NOTIFICATION-TYPE
                        OBJECTS { fkAutoResetPingControlRequest, fkAutoResetPingControlTimeStamp, fkAutoResetPingControlReqResult, fkAutoResetPingIpAddress, fkAutoResetPingTransactionInterval, 
                                fkAutoResetPingNumberOfRequest, fkAutoResetPingRequestInterval, fkAutoResetPingTimeoutOfRequest, fkAutoResetPingLossThreshold }
                        STATUS current
                        DESCRIPTION 
                                "modifyAutoResetPingInfo"
                        ::= { fkAutoResetPingNotification 2 }

                
                -- 1.3.6.1.4.1.10428 9 1.101.1.12.1.3.3
                fkAutoResetPingRebootCtrlModified NOTIFICATION-TYPE
                        OBJECTS { fkAutoResetPingControlRequest, fkAutoResetPingControlTimeStamp, fkAutoResetPingControlReqResult, fkAutoResetPingRebootThreshold, fkAutoResetPingRebootRecoveryTime
                                 }
                        STATUS current
                        DESCRIPTION 
                                "setAutoResetPingRebootCtrl"
                        ::= { fkAutoResetPingNotification 3 }

                
                -- 1.3.6.1.4.1.10428 9 1.101.1.12.1.3.4
                fkAutoResetPingRebootCountClearSetted NOTIFICATION-TYPE
                        OBJECTS { fkAutoResetPingControlRequest, fkAutoResetPingControlTimeStamp, fkAutoResetPingControlReqResult }
                        STATUS current
                        DESCRIPTION 
                                "clearAutoResetPingRebootCounter"
                        ::= { fkAutoResetPingNotification 4 }

                
                -- 1.3.6.1.4.1.10428 9 1.101.1.12.2
                fkAutoResetMemoryleak OBJECT IDENTIFIER ::= { fkAutoReset 2 }

                
                -- 1.3.6.1.4.1.10428 9 1.101.1.12.2.1
                fkAutoResetMemoryleakInfo OBJECT IDENTIFIER ::= { fkAutoResetMemoryleak 1 }

                
                -- 1.3.6.1.4.1.10428 9 1.101.1.12.2.1.1
                fkAutoResetMemoryleakContStatus OBJECT-TYPE
                        SYNTAX EnableFlag
                        MAX-ACCESS read-only
                        STATUS current
                        DESCRIPTION
                                "The administrative state of AutoResetMemoryleak."
                        ::= { fkAutoResetMemoryleakInfo 1 }

                
                -- 1.3.6.1.4.1.10428 9 1.101.1.12.2.1.2
                fkAutoResetMemoryleakMemThreshold OBJECT-TYPE
                        SYNTAX Integer32
                        MAX-ACCESS read-only
                        STATUS current
                        DESCRIPTION
                                "The threshold for the free memory size.(1 - 524288)"
                        ::= { fkAutoResetMemoryleakInfo 2 }

                
                -- 1.3.6.1.4.1.10428 9 1.101.1.12.2.1.3
                fkAutoResetMemoryleakCheckInterval OBJECT-TYPE
                        SYNTAX Integer32
                        MAX-ACCESS read-only
                        STATUS current
                        DESCRIPTION
                                "The interval between check transaction. (10 - 86400)"
                        ::= { fkAutoResetMemoryleakInfo 3 }

                
                -- 1.3.6.1.4.1.10428 9 1.101.1.12.2.1.4
                fkAutoResetMemoryleakNumberOfVerification OBJECT-TYPE
                        SYNTAX Integer32
                        MAX-ACCESS read-only
                        STATUS current
                        DESCRIPTION
                                "The number of verification in 1 transaction. (1 - 10)"
                        ::= { fkAutoResetMemoryleakInfo 4 }

                
                -- 1.3.6.1.4.1.10428 9 1.101.1.12.2.1.5
                fkAutoResetMemoryleakVerificationInterval OBJECT-TYPE
                        SYNTAX Integer32
                        MAX-ACCESS read-only
                        STATUS current
                        DESCRIPTION
                                "The interval of verification. (1 - 10)"
                        ::= { fkAutoResetMemoryleakInfo 5 }

                
                -- 1.3.6.1.4.1.10428 9 1.101.1.12.2.1.6
                fkAutoResetMemoryleakCountThreshold OBJECT-TYPE
                        SYNTAX Integer32
                        MAX-ACCESS read-only
                        STATUS current
                        DESCRIPTION
                                "The threshold of memory-leak count for reboot-process (1 - 100)"
                        ::= { fkAutoResetMemoryleakInfo 6 }

                
                -- 1.3.6.1.4.1.10428 9 1.101.1.12.2.1.7
                fkAutoResetMemoryleakEnableTime OBJECT-TYPE
                        SYNTAX OCTET STRING
                        MAX-ACCESS read-only
                        STATUS current
                        DESCRIPTION
                                "The time of the autoresetmemoryleak status was enabled"
                        ::= { fkAutoResetMemoryleakInfo 7 }

                
                -- 1.3.6.1.4.1.10428 9 1.101.1.12.2.1.8
                fkAutoResetMemoryleakLastFreeMemory OBJECT-TYPE
                        SYNTAX Integer32
                        MAX-ACCESS read-only
                        STATUS current
                        DESCRIPTION
                                "The size of free memory at last verification."
                        ::= { fkAutoResetMemoryleakInfo 8 }

                
                -- 1.3.6.1.4.1.10428 9 1.101.1.12.2.1.9
                fkAutoResetMemoryleakVerificationCount OBJECT-TYPE
                        SYNTAX Integer32
                        MAX-ACCESS read-only
                        STATUS current
                        DESCRIPTION
                                "The count of verification in current transaction."
                        ::= { fkAutoResetMemoryleakInfo 9 }

                
                -- 1.3.6.1.4.1.10428 9 1.101.1.12.2.1.10
                fkAutoResetMemoryleakDetectionCount OBJECT-TYPE
                        SYNTAX Integer32
                        MAX-ACCESS read-only
                        STATUS current
                        DESCRIPTION
                                "The count of detection in current transaction."
                        ::= { fkAutoResetMemoryleakInfo 10 }

                
                -- 1.3.6.1.4.1.10428 9 1.101.1.12.2.1.11
                fkAutoResetMemoryleakTotalVerificationCount OBJECT-TYPE
                        SYNTAX Counter64
                        MAX-ACCESS read-only
                        STATUS current
                        DESCRIPTION
                                "The total verification count."
                        ::= { fkAutoResetMemoryleakInfo 11 }

                
                -- 1.3.6.1.4.1.10428 9 1.101.1.12.2.1.12
                fkAutoResetMemoryleakTotalDetectionCount OBJECT-TYPE
                        SYNTAX Counter64
                        MAX-ACCESS read-only
                        STATUS current
                        DESCRIPTION
                                "The total detection count."
                        ::= { fkAutoResetMemoryleakInfo 12 }

                
                -- 1.3.6.1.4.1.10428 9 1.101.1.12.2.1.13
                fkAutoResetMemoryleakReboottimeStartHour OBJECT-TYPE
                        SYNTAX Integer32 (-1..23)
                        MAX-ACCESS read-only
                        STATUS current
                        DESCRIPTION
                                "The start time (hour) to be able to reboot (0 - 23)
                                -1: no set"
                        ::= { fkAutoResetMemoryleakInfo 13 }

                
                -- 1.3.6.1.4.1.10428 9 1.101.1.12.2.1.14
                fkAutoResetMemoryleakReboottimeStartMin OBJECT-TYPE
                        SYNTAX Integer32 (-1..59)
                        MAX-ACCESS read-only
                        STATUS current
                        DESCRIPTION
                                "The start time (minute) to be able to reboot (0 - 59)
                                -1: no set"
                        ::= { fkAutoResetMemoryleakInfo 14 }

                
                -- 1.3.6.1.4.1.10428 9 1.101.1.12.2.1.15
                fkAutoResetMemoryleakReboottimeEndHour OBJECT-TYPE
                        SYNTAX Integer32 (-1..23)
                        MAX-ACCESS read-only
                        STATUS current
                        DESCRIPTION
                                "The end time (hour) to be able to reboot (0 - 23)
                                -1: no set"
                        ::= { fkAutoResetMemoryleakInfo 15 }

                
                -- 1.3.6.1.4.1.10428 9 1.101.1.12.2.1.16
                fkAutoResetMemoryleakReboottimeEndMin OBJECT-TYPE
                        SYNTAX Integer32 (-1..59)
                        MAX-ACCESS read-only
                        STATUS current
                        DESCRIPTION
                                "The end time (minute) to be able to reboot (0 - 59)
                                -1: no set"
                        ::= { fkAutoResetMemoryleakInfo 16 }

                
                -- 1.3.6.1.4.1.10428 9 1.101.1.12.2.1.17
                fkAutoResetMemoryleakRebootThreshold OBJECT-TYPE
                        SYNTAX INTEGER (1..100)
                        MAX-ACCESS read-only
                        STATUS current
                        DESCRIPTION
                                "The threshold of reboot-counter for autoReset. (1 - 100)
                                If system is rebooted more than this value, system is not automatically reset anymore.
                                "
                        ::= { fkAutoResetMemoryleakInfo 17 }

                
                -- 1.3.6.1.4.1.10428 9 1.101.1.12.2.1.18
                fkAutoResetMemoryleakRebootCount OBJECT-TYPE
                        SYNTAX Integer32
                        MAX-ACCESS read-only
                        STATUS current
                        DESCRIPTION
                                "The count of system-reboot"
                        ::= { fkAutoResetMemoryleakInfo 18 }

                
                -- 1.3.6.1.4.1.10428 9 1.101.1.12.2.2
                fkAutoResetMemoryleakControl OBJECT IDENTIFIER ::= { fkAutoResetMemoryleak 2 }

                
                -- 1.3.6.1.4.1.10428 9 1.101.1.12.2.2.1
                fkAutoResetMemoryleakControlRequest OBJECT-TYPE
                        SYNTAX INTEGER
                                {
                                setAutoResetMemoryleakStatus(1),
                                modifyAutoResetMemoryleakInfo(2),
                                modifyAutoResetMomoryleakReboottime(3),
                                setAutoResetMemoryRebootCtrl(4),
                                setAutoResetclearAutoResetRebootCounter(5)
                                }
                        MAX-ACCESS read-write
                        STATUS current
                        DESCRIPTION
                                "Description."
                        ::= { fkAutoResetMemoryleakControl 1 }

                
                -- 1.3.6.1.4.1.10428 9 1.101.1.12.2.2.2
                fkAutoResetMemoryleakControlStatus OBJECT-TYPE
                        SYNTAX FkControlStatusType
                        MAX-ACCESS read-only
                        STATUS current
                        DESCRIPTION
                                "Description."
                        ::= { fkAutoResetMemoryleakControl 2 }

                
                -- 1.3.6.1.4.1.10428 9 1.101.1.12.2.2.3
                fkAutoResetMemoryleakControlTimer OBJECT-TYPE
                        SYNTAX Gauge32
                        MAX-ACCESS read-write
                        STATUS current
                        DESCRIPTION
                                "Description."
                        ::= { fkAutoResetMemoryleakControl 3 }

                
                -- 1.3.6.1.4.1.10428 9 1.101.1.12.2.2.4
                fkAutoResetMemoryleakControlTimeStamp OBJECT-TYPE
                        SYNTAX TimeTicks
                        MAX-ACCESS read-only
                        STATUS current
                        DESCRIPTION
                                "Description."
                        ::= { fkAutoResetMemoryleakControl 4 }

                
                -- 1.3.6.1.4.1.10428 9 1.101.1.12.2.2.5
                fkAutoResetMemoryleakControlReqResult OBJECT-TYPE
                        SYNTAX FkControlRequestResultType
                        MAX-ACCESS read-only
                        STATUS current
                        DESCRIPTION
                                "Description."
                        ::= { fkAutoResetMemoryleakControl 5 }

                
                -- 1.3.6.1.4.1.10428 9 1.101.1.12.2.2.6
                fkAutoResetMemoryleakControlConfStatus OBJECT-TYPE
                        SYNTAX EnableFlag
                        MAX-ACCESS read-write
                        STATUS current
                        DESCRIPTION
                                "The administrative state of AutoResetMemoryleak."
                        ::= { fkAutoResetMemoryleakControl 6 }

                
                -- 1.3.6.1.4.1.10428 9 1.101.1.12.2.2.7
                fkAutoResetMemoryleakControlMemThreshold OBJECT-TYPE
                        SYNTAX Integer32
                        MAX-ACCESS read-write
                        STATUS current
                        DESCRIPTION
                                "The threshold for the free memory size.(1 - 524288)"
                        ::= { fkAutoResetMemoryleakControl 7 }

                
                -- 1.3.6.1.4.1.10428 9 1.101.1.12.2.2.8
                fkAutoResetMemoryleakControlCheckInterval OBJECT-TYPE
                        SYNTAX Integer32
                        MAX-ACCESS read-write
                        STATUS current
                        DESCRIPTION
                                "The interval between check transaction. (10 - 86400)"
                        ::= { fkAutoResetMemoryleakControl 8 }

                
                -- 1.3.6.1.4.1.10428 9 1.101.1.12.2.2.9
                fkAutoResetMemoryleakControlNumberOfVerification OBJECT-TYPE
                        SYNTAX Integer32
                        MAX-ACCESS read-write
                        STATUS current
                        DESCRIPTION
                                "The number of verification in 1 transaction. (1 - 10)"
                        ::= { fkAutoResetMemoryleakControl 9 }

                
                -- 1.3.6.1.4.1.10428 9 1.101.1.12.2.2.10
                fkAutoResetMemoryleakControlVerificationInterval OBJECT-TYPE
                        SYNTAX Integer32
                        MAX-ACCESS read-write
                        STATUS current
                        DESCRIPTION
                                "The interval of verification. (1 - 10)"
                        ::= { fkAutoResetMemoryleakControl 10 }

                
                -- 1.3.6.1.4.1.10428 9 1.101.1.12.2.2.11
                fkAutoResetMemoryleakControlCountThreshold OBJECT-TYPE
                        SYNTAX Integer32
                        MAX-ACCESS read-write
                        STATUS current
                        DESCRIPTION
                                "The threshold of memory-leak count for reboot-process (1 - 100)"
                        ::= { fkAutoResetMemoryleakControl 11 }

                
                -- 1.3.6.1.4.1.10428 9 1.101.1.12.2.2.12
                fkAutoResetMemoryleakControlReboottimeStartHour OBJECT-TYPE
                        SYNTAX Integer32 (-1..23)
                        MAX-ACCESS read-write
                        STATUS current
                        DESCRIPTION
                                "The start time (hour) to be able to reboot (0 - 23)
                                -1: clear."
                        ::= { fkAutoResetMemoryleakControl 12 }

                
                -- 1.3.6.1.4.1.10428 9 1.101.1.12.2.2.13
                fkAutoResetMemoryleakControlReboottimeStartMin OBJECT-TYPE
                        SYNTAX Integer32 (-1..59)
                        MAX-ACCESS read-write
                        STATUS current
                        DESCRIPTION
                                "The start time (minute) to be able to reboot (0 - 59)
                                -1: clear"
                        ::= { fkAutoResetMemoryleakControl 13 }

                
                -- 1.3.6.1.4.1.10428 9 1.101.1.12.2.2.14
                fkAutoResetMemoryleakControlReboottimeEndHour OBJECT-TYPE
                        SYNTAX Integer32 (-1..23)
                        MAX-ACCESS read-write
                        STATUS current
                        DESCRIPTION
                                "The end time (hour) to be able to reboot (0 - 23)
                                -1: clear"
                        ::= { fkAutoResetMemoryleakControl 14 }

                
                -- 1.3.6.1.4.1.10428 9 1.101.1.12.2.2.15
                fkAutoResetMemoryleakControlReboottimeEndMin OBJECT-TYPE
                        SYNTAX Integer32 (-1..59)
                        MAX-ACCESS read-write
                        STATUS current
                        DESCRIPTION
                                "The end time (minute) to be able to reboot (0 - 59)
                                -1: clear"
                        ::= { fkAutoResetMemoryleakControl 15 }

                
                -- 1.3.6.1.4.1.10428 9 1.101.1.12.2.2.16
                fkAutoResetMemoryleakControlRebootThreshold OBJECT-TYPE
                        SYNTAX INTEGER (1..100)
                        MAX-ACCESS read-write
                        STATUS current
                        DESCRIPTION
                                "The threshold of reboot-counter for autoReset.
                                If system is rebooted more than this value, system is not automatically reset anymore. (1 - 100)
                                "
                        ::= { fkAutoResetMemoryleakControl 16 }

                
                -- 1.3.6.1.4.1.10428 9 1.101.1.12.2.3
                fkAutoResetMemoryleakNotification OBJECT IDENTIFIER ::= { fkAutoResetMemoryleak 3 }

                
                -- 1.3.6.1.4.1.10428 9 1.101.1.12.2.3.1
                fkAutoResetMemoryleakStatusChanged NOTIFICATION-TYPE
                        OBJECTS { fkAutoResetMemoryleakControlRequest, fkAutoResetMemoryleakControlTimeStamp, fkAutoResetMemoryleakControlReqResult, fkAutoResetMemoryleakContStatus }
                        STATUS current
                        DESCRIPTION 
                                "setAutoResetMemoryleakStatus"
                        ::= { fkAutoResetMemoryleakNotification 1 }

                
                -- 1.3.6.1.4.1.10428 9 1.101.1.12.2.3.2
                fkAutoResetMemoryleakInfoModified NOTIFICATION-TYPE
                        OBJECTS { fkAutoResetMemoryleakControlRequest, fkAutoResetMemoryleakControlTimeStamp, fkAutoResetMemoryleakControlReqResult, fkAutoResetMemoryleakMemThreshold, fkAutoResetMemoryleakCheckInterval, 
                                fkAutoResetMemoryleakNumberOfVerification, fkAutoResetMemoryleakVerificationInterval, fkAutoResetMemoryleakCountThreshold }
                        STATUS current
                        DESCRIPTION 
                                "modifyAutoResetMemoryleakInfo"
                        ::= { fkAutoResetMemoryleakNotification 2 }

                
                -- 1.3.6.1.4.1.10428 9 1.101.1.12.2.3.3
                fkAutoResetMemoryleakReboottimeModified NOTIFICATION-TYPE
                        OBJECTS { fkAutoResetMemoryleakControlRequest, fkAutoResetMemoryleakControlTimeStamp, fkAutoResetMemoryleakControlReqResult, fkAutoResetMemoryleakReboottimeStartHour, fkAutoResetMemoryleakReboottimeStartMin, 
                                fkAutoResetMemoryleakReboottimeEndHour, fkAutoResetMemoryleakReboottimeEndMin }
                        STATUS current
                        DESCRIPTION 
                                "modifyAutoResetMomoryleakReboottime"
                        ::= { fkAutoResetMemoryleakNotification 3 }

                
                -- 1.3.6.1.4.1.10428 9 1.101.1.12.2.3.4
                fkAutoResetMemoryleakRebootCtrlModified NOTIFICATION-TYPE
                        OBJECTS { fkAutoResetMemoryleakControlRequest, fkAutoResetMemoryleakControlTimeStamp, fkAutoResetMemoryleakControlReqResult, fkAutoResetMemoryleakRebootThreshold }
                        STATUS current
                        DESCRIPTION 
                                "setAutoResetMemoryRebootCtrl"
                        ::= { fkAutoResetMemoryleakNotification 4 }

                
                -- 1.3.6.1.4.1.10428 9 1.101.1.12.2.3.5
                fkAutoResetMemoryleakRebootCountClearSetted NOTIFICATION-TYPE
                        OBJECTS { fkAutoResetMemoryleakControlRequest, fkAutoResetMemoryleakControlTimeStamp, fkAutoResetMemoryleakControlReqResult }
                        STATUS current
                        DESCRIPTION 
                                "setAutoResetclearAutoResetRebootCounter"
                        ::= { fkAutoResetMemoryleakNotification 5 }

                
                -- 1.3.6.1.4.1.10428 9 1.101.1.12.3
                fkAutoResetCpu OBJECT IDENTIFIER ::= { fkAutoReset 3 }

                
                -- 1.3.6.1.4.1.10428 9 1.101.1.12.3.1
                fkAutoResetCpuInfo OBJECT IDENTIFIER ::= { fkAutoResetCpu 1 }

                
                -- 1.3.6.1.4.1.10428 9 1.101.1.12.3.1.1
                fkAutoResetCpuStatus OBJECT-TYPE
                        SYNTAX INTEGER
                                {
                                off(0),
                                on(1)
                                }
                        MAX-ACCESS read-only
                        STATUS current
                        DESCRIPTION
                                "The auto-reset cpu status."
                        ::= { fkAutoResetCpuInfo 1 }

                
                -- 1.3.6.1.4.1.10428 9 1.101.1.12.3.1.2
                fkAutoResetCpuLoad OBJECT-TYPE
                        SYNTAX Integer32 (50..100)
                        MAX-ACCESS read-only
                        STATUS current
                        DESCRIPTION
                                "CPU load average per 1 min.(50 - 100)"
                        ::= { fkAutoResetCpuInfo 2 }

                
                -- 1.3.6.1.4.1.10428 9 1.101.1.12.3.1.3
                fkAutoResetCpuInterruptLoad OBJECT-TYPE
                        SYNTAX Integer32 (1..100)
                        MAX-ACCESS read-only
                        STATUS current
                        DESCRIPTION
                                "Interrupt load average per 1 min. (1 - 100)"
                        ::= { fkAutoResetCpuInfo 3 }

                
                -- 1.3.6.1.4.1.10428 9 1.101.1.12.3.1.4
                fkAutoResetCpuTime OBJECT-TYPE
                        SYNTAX Integer32
                        MAX-ACCESS read-only
                        STATUS current
                        DESCRIPTION
                                "The continuation time."
                        ::= { fkAutoResetCpuInfo 4 }

                
                -- 1.3.6.1.4.1.10428 9 1.101.1.12.3.2
                fkAutoResetCpuControl OBJECT IDENTIFIER ::= { fkAutoResetCpu 2 }

                
                -- 1.3.6.1.4.1.10428 9 1.101.1.12.3.2.1
                fkAutoResetCpuControlRequest OBJECT-TYPE
                        SYNTAX INTEGER
                                {
                                setAutoResetCpu(1),
                                delAutoResetCpu(2)
                                }
                        MAX-ACCESS read-write
                        STATUS current
                        DESCRIPTION
                                "The request of a user command"
                        ::= { fkAutoResetCpuControl 1 }

                
                -- 1.3.6.1.4.1.10428 9 1.101.1.12.3.2.2
                fkAutoResetCpuControlStatus OBJECT-TYPE
                        SYNTAX FkControlStatusType
                        MAX-ACCESS read-only
                        STATUS current
                        DESCRIPTION
                                "The status of user command"
                        ::= { fkAutoResetCpuControl 2 }

                
                -- 1.3.6.1.4.1.10428 9 1.101.1.12.3.2.3
                fkAutoResetCpuControlTimer OBJECT-TYPE
                        SYNTAX Gauge32
                        MAX-ACCESS read-write
                        STATUS current
                        DESCRIPTION
                                "The maximum time for the manager for a long running user command"
                        ::= { fkAutoResetCpuControl 3 }

                
                -- 1.3.6.1.4.1.10428 9 1.101.1.12.3.2.4
                fkAutoResetCpuControlTimeStamp OBJECT-TYPE
                        SYNTAX TimeTicks
                        MAX-ACCESS read-only
                        STATUS current
                        DESCRIPTION
                                "The time stamp of the last command(end of command)"
                        ::= { fkAutoResetCpuControl 4 }

                
                -- 1.3.6.1.4.1.10428 9 1.101.1.12.3.2.5
                fkAutoResetCpuControlReqResult OBJECT-TYPE
                        SYNTAX FkControlRequestResultType
                        MAX-ACCESS read-only
                        STATUS current
                        DESCRIPTION
                                "The result of the last user command"
                        ::= { fkAutoResetCpuControl 5 }

                
                -- 1.3.6.1.4.1.10428 9 1.101.1.12.3.2.6
                fkAutoResetCpuControlLoad OBJECT-TYPE
                        SYNTAX Integer32 (50..100)
                        MAX-ACCESS read-write
                        STATUS current
                        DESCRIPTION
                                "CPU load average per 1 min.(50 - 100)"
                        ::= { fkAutoResetCpuControl 6 }

                
                -- 1.3.6.1.4.1.10428 9 1.101.1.12.3.2.7
                fkAutoResetCpuControlInterruptLoad OBJECT-TYPE
                        SYNTAX Integer32 (1..100)
                        MAX-ACCESS read-write
                        STATUS current
                        DESCRIPTION
                                "Interrupt load average per 1 min. (1 - 100)"
                        ::= { fkAutoResetCpuControl 7 }

                
                -- 1.3.6.1.4.1.10428 9 1.101.1.12.3.2.8
                fkAutoResetCpuControlTime OBJECT-TYPE
                        SYNTAX Integer32
                        MAX-ACCESS read-write
                        STATUS current
                        DESCRIPTION
                                "The continuation time."
                        ::= { fkAutoResetCpuControl 8 }

                
                -- 1.3.6.1.4.1.10428 9 1.101.1.12.3.3
                fkAutoResetCpuNotification OBJECT IDENTIFIER ::= { fkAutoResetCpu 3 }

                
                -- 1.3.6.1.4.1.10428 9 1.101.1.12.3.3.1
                fkAutoResetCpuChanged NOTIFICATION-TYPE
                        OBJECTS { fkAutoResetCpuControlRequest, fkAutoResetCpuControlTimeStamp, fkAutoResetCpuControlReqResult, fkAutoResetCpuControlLoad, fkAutoResetCpuControlInterruptLoad, 
                                fkAutoResetCpuControlTime }
                        STATUS current
                        DESCRIPTION 
                                "setAutoResetCpu"
                        ::= { fkAutoResetCpuNotification 1 }

                
                -- 1.3.6.1.4.1.10428 9 1.101.1.12.3.3.2
                fkAutoResetCpuDeleted NOTIFICATION-TYPE
                        OBJECTS { fkAutoResetCpuControlRequest, fkAutoResetCpuControlTimeStamp, fkAutoResetCpuControlReqResult }
                        STATUS current
                        DESCRIPTION 
                                "delAutoResetCpu"
                        ::= { fkAutoResetCpuNotification 2 }

                
                -- 1.3.6.1.4.1.10428 9 1.101.1.12.4
                fkAutoResetInfo OBJECT IDENTIFIER ::= { fkAutoReset 4 }

                
                -- 1.3.6.1.4.1.10428 9 1.101.1.12.4.1
                fkAutoResetBootReason OBJECT-TYPE
                        SYNTAX OCTET STRING
                        MAX-ACCESS read-only
                        STATUS current
                        DESCRIPTION
                                "The Restart reason by auto-reset. (This is used only for trap string)"
                        ::= { fkAutoResetInfo 1 }

                
                -- 1.3.6.1.4.1.10428 9 1.101.1.13
                fkCoreDump OBJECT IDENTIFIER ::= { fkSystemMaintenance 13 }

                
                -- 1.3.6.1.4.1.10428 9 1.101.1.13.1
                fkCoreDumpInfoTable OBJECT-TYPE
                        SYNTAX SEQUENCE OF FkCoreDumpInfoEntry
                        MAX-ACCESS not-accessible
                        STATUS current
                        DESCRIPTION
                                "Description."
                        ::= { fkCoreDump 1 }

                
                -- 1.3.6.1.4.1.10428 9 1.101.1.15.1.1
                fkCoreDumpInfoEntry OBJECT-TYPE
                        SYNTAX FkCoreDumpInfoEntry
                        MAX-ACCESS not-accessible
                        STATUS current
                        DESCRIPTION
                                "Description."
                        INDEX { fkCoreDumpInfoPID }
                        ::= { fkCoreDumpInfoTable 1 }

                
                FkCoreDumpInfoEntry ::=
                        SEQUENCE { 
                                fkCoreDumpInfoPID
                                        INTEGER,
                                fkCoreDumpInfoStatus
                                        INTEGER,
                                fkCoreDumpFile
                                        OCTET STRING
                         }

                -- 1.3.6.1.4.1.10428 9 1.101.1.15.1.1.1
                fkCoreDumpInfoPID OBJECT-TYPE
                        SYNTAX INTEGER (1..2147483647)
                        MAX-ACCESS read-only
                        STATUS current
                        DESCRIPTION
                                "The process ID"
                        ::= { fkCoreDumpInfoEntry 1 }

                
                -- 1.3.6.1.4.1.10428 9 1.101.1.15.1.1.2
                fkCoreDumpInfoStatus OBJECT-TYPE
                        SYNTAX INTEGER
                                {
                                ok(1),
                                fail(2)
                                }
                        MAX-ACCESS read-only
                        STATUS current
                        DESCRIPTION
                                "The status of PID"
                        ::= { fkCoreDumpInfoEntry 2 }

                
                -- 1.3.6.1.4.1.10428 9 1.101.1.15.1.1.3
                fkCoreDumpFile OBJECT-TYPE
                        SYNTAX OCTET STRING
                        MAX-ACCESS read-only
                        STATUS current
                        DESCRIPTION
                                "Created coredump file name"
                        ::= { fkCoreDumpInfoEntry 3 }

                
                -- 1.3.6.1.4.1.10428 9 1.101.1.13.2
                fkCoreDumpControl OBJECT IDENTIFIER ::= { fkCoreDump 2 }

                
                -- 1.3.6.1.4.1.10428 9 1.101.1.13.2.1
                fkCoreDumpControlRequest OBJECT-TYPE
                        SYNTAX INTEGER
                                {
                                createCoredDumpEntry(1),
                                destroyCoredDumpEntry(2),
                                setCoredDumpEntryToRemote(3)
                                }
                        MAX-ACCESS read-write
                        STATUS current
                        DESCRIPTION
                                "Description."
                        ::= { fkCoreDumpControl 1 }

                
                -- 1.3.6.1.4.1.10428 9 1.101.1.13.2.2
                fkCoreDumpControlStatus OBJECT-TYPE
                        SYNTAX FkControlStatusType
                        MAX-ACCESS read-only
                        STATUS current
                        DESCRIPTION
                                "Description."
                        ::= { fkCoreDumpControl 2 }

                
                -- 1.3.6.1.4.1.10428 9 1.101.1.13.2.3
                fkCoreDumpControlTimer OBJECT-TYPE
                        SYNTAX Gauge32
                        MAX-ACCESS read-write
                        STATUS current
                        DESCRIPTION
                                "Description."
                        ::= { fkCoreDumpControl 3 }

                
                -- 1.3.6.1.4.1.10428 9 1.101.1.13.2.4
                fkCoreDumpControlTimeStamp OBJECT-TYPE
                        SYNTAX TimeTicks
                        MAX-ACCESS read-only
                        STATUS current
                        DESCRIPTION
                                "Description."
                        ::= { fkCoreDumpControl 4 }

                
                -- 1.3.6.1.4.1.10428 9 1.101.1.13.2.5
                fkCoreDumpControlReqResult OBJECT-TYPE
                        SYNTAX FkControlRequestResultType
                        MAX-ACCESS read-only
                        STATUS current
                        DESCRIPTION
                                "Description."
                        ::= { fkCoreDumpControl 5 }

                
                -- 1.3.6.1.4.1.10428 9 1.101.1.13.2.6
                fkCoreDumpControlPID OBJECT-TYPE
                        SYNTAX INTEGER (1..2147483647)
                        MAX-ACCESS read-write
                        STATUS current
                        DESCRIPTION
                                "Description."
                        ::= { fkCoreDumpControl 6 }

                
                -- 1.3.6.1.4.1.10428 9 1.101.1.13.2.7
                fkCoreDumpControlServerIP OBJECT-TYPE
                        SYNTAX IpAddress
                        MAX-ACCESS read-write
                        STATUS current
                        DESCRIPTION
                                "Description."
                        ::= { fkCoreDumpControl 7 }

                
                -- 1.3.6.1.4.1.10428 9 1.101.1.13.2.8
                fkCoreDumpControlUserID OBJECT-TYPE
                        SYNTAX OCTET STRING
                        MAX-ACCESS read-write
                        STATUS current
                        DESCRIPTION
                                "Description."
                        ::= { fkCoreDumpControl 8 }

                
                -- 1.3.6.1.4.1.10428 9 1.101.1.13.2.9
                fkCoreDumpControlPassword OBJECT-TYPE
                        SYNTAX OCTET STRING
                        MAX-ACCESS read-write
                        STATUS current
                        DESCRIPTION
                                "Description."
                        ::= { fkCoreDumpControl 9 }

                
                -- 1.3.6.1.4.1.10428 9 1.101.1.13.2.10
                fkCoreDumpControlCoredumpFile OBJECT-TYPE
                        SYNTAX OCTET STRING
                        MAX-ACCESS read-write
                        STATUS current
                        DESCRIPTION
                                "Description."
                        ::= { fkCoreDumpControl 10 }

                
                -- 1.3.6.1.4.1.10428 9 1.101.1.13.3
                fkCoreDumpNotification OBJECT IDENTIFIER ::= { fkCoreDump 3 }

                
                -- 1.3.6.1.4.1.10428 9 1.101.1.13.3.1
                fkCoreDumpEntryCreated NOTIFICATION-TYPE
                        OBJECTS { fkCoreDumpControlRequest, fkCoreDumpControlTimeStamp, fkCoreDumpControlReqResult, fkCoreDumpInfoPID, fkCoreDumpInfoStatus
                                 }
                        STATUS current
                        DESCRIPTION 
                                "Description."
                        ::= { fkCoreDumpNotification 1 }

                
                -- 1.3.6.1.4.1.10428 9 1.101.1.13.3.2
                fkCoreDumpEntryDestroyed NOTIFICATION-TYPE
                        OBJECTS { fkCoreDumpControlRequest, fkCoreDumpControlTimeStamp, fkCoreDumpControlReqResult, fkCoreDumpInfoPID }
                        STATUS current
                        DESCRIPTION 
                                "Description."
                        ::= { fkCoreDumpNotification 2 }

                
                -- 1.3.6.1.4.1.10428 9 1.101.1.13.3.3
                fkCoreDumpEntryChanged NOTIFICATION-TYPE
                        OBJECTS { fkCoreDumpControlRequest, fkCoreDumpControlTimeStamp, fkCoreDumpControlReqResult, fkCoreDumpFile }
                        STATUS current
                        DESCRIPTION 
                                "Description."
                        ::= { fkCoreDumpNotification 3 }

                
                -- 1.3.6.1.4.1.10428 9 1.101.1.14
                fkService OBJECT IDENTIFIER ::= { fkSystemMaintenance 14 }

                
                -- 1.3.6.1.4.1.10428 9 1.101.1.14.1
                fkServiceTable OBJECT-TYPE
                        SYNTAX SEQUENCE OF FkServiceEntry
                        MAX-ACCESS not-accessible
                        STATUS current
                        DESCRIPTION
                                "Description."
                        ::= { fkService 1 }

                
                -- 1.3.6.1.4.1.10428 9 1.101.1.16.1.1
                fkServiceEntry OBJECT-TYPE
                        SYNTAX FkServiceEntry
                        MAX-ACCESS not-accessible
                        STATUS current
                        DESCRIPTION
                                "Description."
                        INDEX { fkServiceIndex, fkServiceProtocol }
                        ::= { fkServiceTable 1 }

                
                FkServiceEntry ::=
                        SEQUENCE { 
                                fkServiceIndex
                                        INTEGER,
                                fkServiceProtocol
                                        INTEGER,
                                fkServiceName
                                        OCTET STRING,
                                fkServicePort
                                        INTEGER,
                                fkServiceAdminStatus
                                        INTEGER
                         }

                -- 1.3.6.1.4.1.10428 9 1.101.1.16.1.1.1
                fkServiceIndex OBJECT-TYPE
                        SYNTAX INTEGER
                                {
                                ftpdata(20),
                                ftp(21),
                                ssh(22),
                                telnet(23),
                                tftp(69),
                                snmp(161)
                                }
                        MAX-ACCESS read-only
                        STATUS current
                        DESCRIPTION
                                "Service Index"
                        ::= { fkServiceEntry 1 }

                
                -- 1.3.6.1.4.1.10428 9 1.101.1.16.1.1.2
                fkServiceProtocol OBJECT-TYPE
                        SYNTAX INTEGER
                                {
                                tcp(1),
                                udp(2)
                                }
                        MAX-ACCESS read-only
                        STATUS current
                        DESCRIPTION
                                "Service Protocol"
                        ::= { fkServiceEntry 2 }

                
                -- 1.3.6.1.4.1.10428 9 1.101.1.16.1.1.3
                fkServiceName OBJECT-TYPE
                        SYNTAX OCTET STRING
                        MAX-ACCESS read-only
                        STATUS current
                        DESCRIPTION
                                "Service name"
                        ::= { fkServiceEntry 3 }

                
                -- 1.3.6.1.4.1.10428 9 1.101.1.16.1.1.4
                fkServicePort OBJECT-TYPE
                        SYNTAX INTEGER (1..65535)
                        MAX-ACCESS read-only
                        STATUS current
                        DESCRIPTION
                                "Service Port"
                        ::= { fkServiceEntry 4 }

                
                -- 1.3.6.1.4.1.10428 9 1.101.1.16.1.1.5
                fkServiceAdminStatus OBJECT-TYPE
                        SYNTAX INTEGER
                                {
                                enable(1),
                                disable(2)
                                }
                        MAX-ACCESS read-only
                        STATUS current
                        DESCRIPTION
                                "The current status of service.
                                "
                        ::= { fkServiceEntry 5 }

                
                -- 1.3.6.1.4.1.10428 9 1.101.1.14.2
                fkServiceControl OBJECT IDENTIFIER ::= { fkService 2 }

                
                -- 1.3.6.1.4.1.10428 9 1.101.1.14.2.1
                fkServiceControlRequest OBJECT-TYPE
                        SYNTAX INTEGER
                                {
                                setServicePort(1),
                                setServiceStatus(2)
                                }
                        MAX-ACCESS read-write
                        STATUS current
                        DESCRIPTION
                                "Description."
                        ::= { fkServiceControl 1 }

                
                -- 1.3.6.1.4.1.10428 9 1.101.1.14.2.2
                fkServiceControlStatus OBJECT-TYPE
                        SYNTAX FkControlStatusType
                        MAX-ACCESS read-only
                        STATUS current
                        DESCRIPTION
                                "Description."
                        ::= { fkServiceControl 2 }

                
                -- 1.3.6.1.4.1.10428 9 1.101.1.14.2.3
                fkServiceControlTimer OBJECT-TYPE
                        SYNTAX Gauge32
                        MAX-ACCESS read-write
                        STATUS current
                        DESCRIPTION
                                "Description."
                        ::= { fkServiceControl 3 }

                
                -- 1.3.6.1.4.1.10428 9 1.101.1.14.2.4
                fkServiceControlTimeStamp OBJECT-TYPE
                        SYNTAX TimeTicks
                        MAX-ACCESS read-only
                        STATUS current
                        DESCRIPTION
                                "Description."
                        ::= { fkServiceControl 4 }

                
                -- 1.3.6.1.4.1.10428 9 1.101.1.14.2.5
                fkServiceControlReqResult OBJECT-TYPE
                        SYNTAX FkControlRequestResultType
                        MAX-ACCESS read-only
                        STATUS current
                        DESCRIPTION
                                "Result of the last command."
                        ::= { fkServiceControl 5 }

                
                -- 1.3.6.1.4.1.10428 9 1.101.1.14.2.6
                fkServiceControlIndex OBJECT-TYPE
                        SYNTAX INTEGER
                                {
                                ftpdata(20),
                                ftp(21),
                                ssh(22),
                                telnet(23),
                                tftp(69),
                                snmp(161)
                                }
                        MAX-ACCESS read-write
                        STATUS current
                        DESCRIPTION
                                "Service Index"
                        ::= { fkServiceControl 6 }

                
                -- 1.3.6.1.4.1.10428 9 1.101.1.14.2.7
                fkServiceControlProtocol OBJECT-TYPE
                        SYNTAX INTEGER
                                {
                                tcp(1),
                                udp(2)
                                }
                        MAX-ACCESS read-write
                        STATUS current
                        DESCRIPTION
                                "Service Protocol"
                        ::= { fkServiceControl 7 }

                
                -- 1.3.6.1.4.1.10428 9 1.101.1.14.2.8
                fkServiceControlPort OBJECT-TYPE
                        SYNTAX INTEGER (1..65535)
                        MAX-ACCESS read-write
                        STATUS current
                        DESCRIPTION
                                "Service Port"
                        ::= { fkServiceControl 8 }

                
                -- 1.3.6.1.4.1.10428 9 1.101.1.14.2.9
                fkServiceControlAdminStatus OBJECT-TYPE
                        SYNTAX INTEGER
                                {
                                enable(1),
                                disable(2)
                                }
                        MAX-ACCESS read-write
                        STATUS current
                        DESCRIPTION
                                "The current status of service.
                                "
                        ::= { fkServiceControl 9 }

                
                -- 1.3.6.1.4.1.10428 9 1.101.1.14.3
                fkServiceNotification OBJECT IDENTIFIER ::= { fkService 3 }

                
                -- 1.3.6.1.4.1.10428 9 1.101.1.14.3.1
                fkServicePortChanged NOTIFICATION-TYPE
                        OBJECTS { fkServiceControlRequest, fkServiceControlTimeStamp, fkServiceControlReqResult, fkServicePort }
                        STATUS current
                        DESCRIPTION 
                                "setServicePort"
                        ::= { fkServiceNotification 1 }

                
                -- 1.3.6.1.4.1.10428 9 1.101.1.14.3.2
                fkServiceAdminStatusChanged NOTIFICATION-TYPE
                        OBJECTS { fkServiceControlRequest, fkServiceControlTimeStamp, fkServiceControlReqResult, fkServiceControlIndex, fkServiceControlAdminStatus
                                 }
                        STATUS current
                        DESCRIPTION 
                                "Description."
                        ::= { fkServiceNotification 2 }

                
                -- 1.3.6.1.4.1.10428 9 1.101.1.15
                fkSystemUser OBJECT IDENTIFIER ::= { fkSystemMaintenance 15 }

                
                -- 1.3.6.1.4.1.10428 9 1.101.1.15.1
                fkSystemUserTable OBJECT-TYPE
                        SYNTAX SEQUENCE OF FkSystemUserEntry
                        MAX-ACCESS not-accessible
                        STATUS current
                        DESCRIPTION
                                "Description."
                        ::= { fkSystemUser 1 }

                
                -- 1.3.6.1.4.1.10428 9 1.101.1.17.1.1
                fkSystemUserEntry OBJECT-TYPE
                        SYNTAX FkSystemUserEntry
                        MAX-ACCESS not-accessible
                        STATUS current
                        DESCRIPTION
                                "Description."
                        INDEX { fkSystemUserName }
                        ::= { fkSystemUserTable 1 }

                
                FkSystemUserEntry ::=
                        SEQUENCE { 
                                fkSystemUserName
                                        OCTET STRING,
                                fkSystemUserLevel
                                        INTEGER,
                                fkSystemUserPassword
                                        OCTET STRING,
                                fkSystemUserDesc
                                        OCTET STRING
                         }

                -- 1.3.6.1.4.1.10428 9 1.101.1.17.1.1.1
                fkSystemUserName OBJECT-TYPE
                        SYNTAX OCTET STRING (SIZE (1..255))
                        MAX-ACCESS read-only
                        STATUS current
                        DESCRIPTION
                                "User Name. where 'admin' is reserved name."
                        ::= { fkSystemUserEntry 1 }

                
                -- 1.3.6.1.4.1.10428 9 1.101.1.17.1.1.2
                fkSystemUserLevel OBJECT-TYPE
                        SYNTAX INTEGER (0..15)
                        MAX-ACCESS read-only
                        STATUS current
                        DESCRIPTION
                                "User's level"
                        ::= { fkSystemUserEntry 2 }

                
                -- 1.3.6.1.4.1.10428 9 1.101.1.17.1.1.3
                fkSystemUserPassword OBJECT-TYPE
                        SYNTAX OCTET STRING (SIZE (0..255))
                        MAX-ACCESS read-only
                        STATUS current
                        DESCRIPTION
                                "User's password (always encrypted)"
                        ::= { fkSystemUserEntry 3 }

                
                -- 1.3.6.1.4.1.10428 9 1.101.1.17.1.1.4
                fkSystemUserDesc OBJECT-TYPE
                        SYNTAX OCTET STRING (SIZE (0..255))
                        MAX-ACCESS read-only
                        STATUS current
                        DESCRIPTION
                                "User Description"
                        ::= { fkSystemUserEntry 4 }

                
                -- 1.3.6.1.4.1.10428 9 1.101.1.15.2
                fkSystemUserControl OBJECT IDENTIFIER ::= { fkSystemUser 2 }

                
                -- 1.3.6.1.4.1.10428 9 1.101.1.15.2.1
                fkSystemUserControlRequest OBJECT-TYPE
                        SYNTAX INTEGER
                                {
                                addUser(1),
                                renameUser(2),
                                setPassword(3),
                                deleteUser(4),
                                setLevel(5)
                                }
                        MAX-ACCESS read-write
                        STATUS current
                        DESCRIPTION
                                "Description."
                        ::= { fkSystemUserControl 1 }

                
                -- 1.3.6.1.4.1.10428 9 1.101.1.15.2.2
                fkSystemUserControlStatus OBJECT-TYPE
                        SYNTAX FkControlStatusType
                        MAX-ACCESS read-only
                        STATUS current
                        DESCRIPTION
                                "Description."
                        ::= { fkSystemUserControl 2 }

                
                -- 1.3.6.1.4.1.10428 9 1.101.1.15.2.3
                fkSystemUserControlTimer OBJECT-TYPE
                        SYNTAX Gauge32
                        MAX-ACCESS read-write
                        STATUS current
                        DESCRIPTION
                                "Description."
                        ::= { fkSystemUserControl 3 }

                
                -- 1.3.6.1.4.1.10428 9 1.101.1.15.2.4
                fkSystemUserControlTimeStamp OBJECT-TYPE
                        SYNTAX TimeTicks
                        MAX-ACCESS read-only
                        STATUS current
                        DESCRIPTION
                                "Description."
                        ::= { fkSystemUserControl 4 }

                
                -- 1.3.6.1.4.1.10428 9 1.101.1.15.2.5
                fkSystemUserControlReqResult OBJECT-TYPE
                        SYNTAX FkControlRequestResultType
                        MAX-ACCESS read-only
                        STATUS current
                        DESCRIPTION
                                "Result of the last command."
                        ::= { fkSystemUserControl 5 }

                
                -- 1.3.6.1.4.1.10428 9 1.101.1.15.2.6
                fkSystemUserControlName OBJECT-TYPE
                        SYNTAX OCTET STRING (SIZE (1..255))
                        MAX-ACCESS read-write
                        STATUS current
                        DESCRIPTION
                                "User Name. where 'admin' is reserved name."
                        ::= { fkSystemUserControl 6 }

                
                -- 1.3.6.1.4.1.10428 9 1.101.1.15.2.7
                fkSystemUserControlRename OBJECT-TYPE
                        SYNTAX OCTET STRING (SIZE (1..255))
                        MAX-ACCESS read-write
                        STATUS current
                        DESCRIPTION
                                "New User Name. where 'admin' is reserved name. (when rename user.)"
                        ::= { fkSystemUserControl 7 }

                
                -- 1.3.6.1.4.1.10428 9 1.101.1.15.2.8
                fkSystemUserControlLevel OBJECT-TYPE
                        SYNTAX INTEGER (0..15)
                        MAX-ACCESS read-write
                        STATUS current
                        DESCRIPTION
                                "User's level"
                        ::= { fkSystemUserControl 8 }

                
                -- 1.3.6.1.4.1.10428 9 1.101.1.15.2.9
                fkSystemUserControlPwType OBJECT-TYPE
                        SYNTAX INTEGER
                                {
                                plain(1),
                                encrypt(2)
                                }
                        MAX-ACCESS read-write
                        STATUS current
                        DESCRIPTION
                                "Description."
                        ::= { fkSystemUserControl 9 }

                
                -- 1.3.6.1.4.1.10428 9 1.101.1.15.2.10
                fkSystemUserControlPassword OBJECT-TYPE
                        SYNTAX OCTET STRING (SIZE (0..255))
                        MAX-ACCESS read-write
                        STATUS current
                        DESCRIPTION
                                "User's password"
                        ::= { fkSystemUserControl 10 }

                
                -- 1.3.6.1.4.1.10428 9 1.101.1.15.2.11
                fkSystemUserControlDesc OBJECT-TYPE
                        SYNTAX OCTET STRING (SIZE (0..255))
                        MAX-ACCESS read-write
                        STATUS current
                        DESCRIPTION
                                "User Description"
                        ::= { fkSystemUserControl 11 }

                
                -- 1.3.6.1.4.1.10428 9 1.101.1.15.3
                fkSystemUserNotification OBJECT IDENTIFIER ::= { fkSystemUser 3 }

                
                -- 1.3.6.1.4.1.10428 9 1.101.1.15.3.1
                fkSystemUserCreated NOTIFICATION-TYPE
                        OBJECTS { fkSystemUserControlRequest, fkSystemUserControlTimeStamp, fkSystemUserControlReqResult, fkSystemUserLevel, fkSystemUserPassword, 
                                fkSystemUserDesc }
                        STATUS current
                        DESCRIPTION 
                                "addUser"
                        ::= { fkSystemUserNotification 1 }

                
                -- 1.3.6.1.4.1.10428 9 1.101.1.15.3.2
                fkSystemUserNameChanged NOTIFICATION-TYPE
                        OBJECTS { fkSystemUserControlRequest, fkSystemUserControlTimeStamp, fkSystemUserControlReqResult, fkSystemUserControlName, fkSystemUserControlRename
                                 }
                        STATUS current
                        DESCRIPTION 
                                "renameUser"
                        ::= { fkSystemUserNotification 2 }

                
                -- 1.3.6.1.4.1.10428 9 1.101.1.15.3.3
                fkSystemUserPasswordChanged NOTIFICATION-TYPE
                        OBJECTS { fkSystemUserControlRequest, fkSystemUserControlTimeStamp, fkSystemUserControlReqResult, fkSystemUserPassword }
                        STATUS current
                        DESCRIPTION 
                                "setPassword"
                        ::= { fkSystemUserNotification 3 }

                
                -- 1.3.6.1.4.1.10428 9 1.101.1.15.3.4
                fkSystemUserDestroyed NOTIFICATION-TYPE
                        OBJECTS { fkSystemUserControlRequest, fkSystemUserControlTimeStamp, fkSystemUserControlReqResult, fkSystemUserControlName }
                        STATUS current
                        DESCRIPTION 
                                "deleteUser"
                        ::= { fkSystemUserNotification 4 }

                
                -- 1.3.6.1.4.1.10428 9 1.101.1.15.3.5
                fkSystemUserLevelChanged NOTIFICATION-TYPE
                        OBJECTS { fkSystemUserControlTimeStamp, fkSystemUserControlReqResult, fkSystemUserControlRequest }
                        STATUS current
                        DESCRIPTION 
                                "Description."
                        ::= { fkSystemUserNotification 5 }

                
                -- 1.3.6.1.4.1.10428 9 1.101.1.16
                fkParameter OBJECT IDENTIFIER ::= { fkSystemMaintenance 16 }

                
                -- 1.3.6.1.4.1.10428 9 1.101.1.16.1
                fkParameterTable OBJECT-TYPE
                        SYNTAX SEQUENCE OF FkParameterEntry
                        MAX-ACCESS not-accessible
                        STATUS current
                        DESCRIPTION
                                "Description."
                        ::= { fkParameter 1 }

                
                -- 1.3.6.1.4.1.10428 9 1.101.1.16.1.1
                fkParameterEntry OBJECT-TYPE
                        SYNTAX FkParameterEntry
                        MAX-ACCESS not-accessible
                        STATUS current
                        DESCRIPTION
                                "Description."
                        INDEX { fkParameterName }
                        ::= { fkParameterTable 1 }

                
                FkParameterEntry ::=
                        SEQUENCE { 
                                fkParameterName
                                        OCTET STRING,
                                fkParameterValue
                                        OCTET STRING,
                                fkParameterMode
                                        INTEGER
                         }

                -- 1.3.6.1.4.1.10428 9 1.101.1.16.1.1.1
                fkParameterName OBJECT-TYPE
                        SYNTAX OCTET STRING (SIZE (1..32))
                        MAX-ACCESS read-only
                        STATUS current
                        DESCRIPTION
                                "Description."
                        ::= { fkParameterEntry 1 }

                
                -- 1.3.6.1.4.1.10428 9 1.101.1.16.1.1.2
                fkParameterValue OBJECT-TYPE
                        SYNTAX OCTET STRING (SIZE (1..64))
                        MAX-ACCESS read-only
                        STATUS current
                        DESCRIPTION
                                "Description."
                        ::= { fkParameterEntry 2 }

                
                -- 1.3.6.1.4.1.10428 9 1.101.1.16.1.1.3
                fkParameterMode OBJECT-TYPE
                        SYNTAX INTEGER
                                {
                                dynamic(1),
                                static(2)
                                }
                        MAX-ACCESS read-only
                        STATUS current
                        DESCRIPTION
                                "Description."
                        ::= { fkParameterEntry 3 }

                
                -- 1.3.6.1.4.1.10428 9 1.101.1.16.2
                fkParameterControl OBJECT IDENTIFIER ::= { fkParameter 2 }

                
                -- 1.3.6.1.4.1.10428 9 1.101.1.16.2.1
                fkParameterControlRequest OBJECT-TYPE
                        SYNTAX INTEGER
                                {
                                createParameter(1),
                                destroyParameter(2),
                                modifyParameterMode(3),
                                modifyParameterValue(4)
                                }
                        MAX-ACCESS read-write
                        STATUS current
                        DESCRIPTION
                                "Description."
                        ::= { fkParameterControl 1 }

                
                -- 1.3.6.1.4.1.10428 9 1.101.1.16.2.2
                fkParameterControlStatus OBJECT-TYPE
                        SYNTAX FkControlStatusType
                        MAX-ACCESS read-only
                        STATUS current
                        DESCRIPTION
                                "Description."
                        ::= { fkParameterControl 2 }

                
                -- 1.3.6.1.4.1.10428 9 1.101.1.16.2.3
                fkParameterControlTimer OBJECT-TYPE
                        SYNTAX Gauge32
                        MAX-ACCESS read-write
                        STATUS current
                        DESCRIPTION
                                "Description."
                        ::= { fkParameterControl 3 }

                
                -- 1.3.6.1.4.1.10428 9 1.101.1.16.2.4
                fkParameterControlTimeStamp OBJECT-TYPE
                        SYNTAX TimeTicks
                        MAX-ACCESS read-only
                        STATUS current
                        DESCRIPTION
                                "Description."
                        ::= { fkParameterControl 4 }

                
                -- 1.3.6.1.4.1.10428 9 1.101.1.16.2.5
                fkParameterControlReqResult OBJECT-TYPE
                        SYNTAX FkControlRequestResultType
                        MAX-ACCESS read-only
                        STATUS current
                        DESCRIPTION
                                "Description."
                        ::= { fkParameterControl 5 }

                
                -- 1.3.6.1.4.1.10428 9 1.101.1.16.2.6
                fkParameterControlName OBJECT-TYPE
                        SYNTAX OCTET STRING (SIZE (1..32))
                        MAX-ACCESS read-write
                        STATUS current
                        DESCRIPTION
                                "Description."
                        ::= { fkParameterControl 6 }

                
                -- 1.3.6.1.4.1.10428 9 1.101.1.16.2.7
                fkParameterControlValue OBJECT-TYPE
                        SYNTAX OCTET STRING (SIZE (1..64))
                        MAX-ACCESS read-write
                        STATUS current
                        DESCRIPTION
                                "Description."
                        ::= { fkParameterControl 7 }

                
                -- 1.3.6.1.4.1.10428 9 1.101.1.16.2.8
                fkParameterControlMode OBJECT-TYPE
                        SYNTAX INTEGER
                                {
                                dynamic(1),
                                static(2)
                                }
                        MAX-ACCESS read-write
                        STATUS current
                        DESCRIPTION
                                "Description."
                        ::= { fkParameterControl 8 }

                
                -- 1.3.6.1.4.1.10428 9 1.101.1.16.3
                fkParameterNotification OBJECT IDENTIFIER ::= { fkParameter 3 }

                
                -- 1.3.6.1.4.1.10428 9 1.101.1.16.3.1
                fkParameterCreated NOTIFICATION-TYPE
                        OBJECTS { fkParameterControlRequest, fkParameterControlTimeStamp, fkParameterControlReqResult, fkParameterValue, fkParameterMode
                                 }
                        STATUS current
                        DESCRIPTION 
                                "Description."
                        ::= { fkParameterNotification 1 }

                
                -- 1.3.6.1.4.1.10428 9 1.101.1.16.3.2
                fkParameterDestroyed NOTIFICATION-TYPE
                        OBJECTS { fkParameterControlRequest, fkParameterControlTimeStamp, fkParameterControlReqResult, fkParameterControlName }
                        STATUS current
                        DESCRIPTION 
                                "Description."
                        ::= { fkParameterNotification 2 }

                
                -- 1.3.6.1.4.1.10428 9 1.101.1.16.3.3
                fkParameterModeChanged NOTIFICATION-TYPE
                        OBJECTS { fkParameterControlRequest, fkParameterControlTimeStamp, fkParameterControlReqResult, fkParameterMode }
                        STATUS current
                        DESCRIPTION 
                                "Description."
                        ::= { fkParameterNotification 3 }

                
                -- 1.3.6.1.4.1.10428 9 1.101.1.16.3.4
                fkParameterValueChanged NOTIFICATION-TYPE
                        OBJECTS { fkParameterControlRequest, fkParameterControlTimeStamp, fkParameterControlReqResult, fkParameterValue }
                        STATUS current
                        DESCRIPTION 
                                "Description."
                        ::= { fkParameterNotification 4 }

                
                -- 1.3.6.1.4.1.10428 9 1.101.1.17
                fkSwWatchdogBase OBJECT IDENTIFIER ::= { fkSystemMaintenance 17 }

                
                -- 1.3.6.1.4.1.10428 9 1.101.1.17.1
                fkSwWatchdogTable OBJECT-TYPE
                        SYNTAX SEQUENCE OF FkSwWatchdogEntry
                        MAX-ACCESS not-accessible
                        STATUS current
                        DESCRIPTION
                                "Description."
                        ::= { fkSwWatchdogBase 1 }

                
                -- 1.3.6.1.4.1.10428 9 1.101.1.17.1.1
                fkSwWatchdogEntry OBJECT-TYPE
                        SYNTAX FkSwWatchdogEntry
                        MAX-ACCESS not-accessible
                        STATUS current
                        DESCRIPTION
                                "Description."
                        INDEX { fkSwWatchdogType }
                        ::= { fkSwWatchdogTable 1 }

                
                FkSwWatchdogEntry ::=
                        SEQUENCE { 
                                fkSwWatchdogType
                                        INTEGER,
                                fkSwWatchdogInterval
                                        INTEGER,
                                fkSwWatchdogThreshold
                                        INTEGER,
                                fkSwWatchdogAction
                                        INTEGER,
                                fkSwWatchdogErrcnt
                                        Integer32
                         }

                -- 1.3.6.1.4.1.10428 9 1.101.1.17.1.1.1
                fkSwWatchdogType OBJECT-TYPE
                        SYNTAX INTEGER
                                {
                                daemonMonitoring(1),
                                inetMonitoring(2),
                                ponMonitoring(3)
                                }
                        MAX-ACCESS read-only
                        STATUS current
                        DESCRIPTION
                                "Description."
                        ::= { fkSwWatchdogEntry 1 }

                
                -- 1.3.6.1.4.1.10428 9 1.101.1.17.1.1.2
                fkSwWatchdogInterval OBJECT-TYPE
                        SYNTAX INTEGER (10..86400)
                        UNITS "sec"
                        MAX-ACCESS read-only
                        STATUS current
                        DESCRIPTION
                                "Description."
                        ::= { fkSwWatchdogEntry 2 }

                
                -- 1.3.6.1.4.1.10428 9 1.101.1.17.1.1.3
                fkSwWatchdogThreshold OBJECT-TYPE
                        SYNTAX INTEGER (1..10)
                        MAX-ACCESS read-only
                        STATUS current
                        DESCRIPTION
                                "Description."
                        ::= { fkSwWatchdogEntry 3 }

                
                -- 1.3.6.1.4.1.10428 9 1.101.1.17.1.1.4
                fkSwWatchdogAction OBJECT-TYPE
                        SYNTAX INTEGER
                                {
                                none(1),
                                daemonRestart(2),
                                systemReset(3),
                                systemResetWithSaveCfg(4),
                                onuPortReset(5)
                                }
                        MAX-ACCESS read-only
                        STATUS current
                        DESCRIPTION
                                "Description."
                        ::= { fkSwWatchdogEntry 4 }

                
                -- 1.3.6.1.4.1.10428 9 1.101.1.17.1.1.5
                fkSwWatchdogErrcnt OBJECT-TYPE
                        SYNTAX Integer32
                        MAX-ACCESS read-only
                        STATUS current
                        DESCRIPTION
                                "Description."
                        ::= { fkSwWatchdogEntry 5 }

                
                -- 1.3.6.1.4.1.10428 9 1.101.1.17.2
                fkSwWatchdogControl OBJECT IDENTIFIER ::= { fkSwWatchdogBase 2 }

                
                -- 1.3.6.1.4.1.10428 9 1.101.1.17.2.1
                fkSwWatchdogControlRequest OBJECT-TYPE
                        SYNTAX INTEGER
                                {
                                createSwwatchdog(1),
                                deleteSwwatchdog(2)
                                }
                        MAX-ACCESS read-write
                        STATUS current
                        DESCRIPTION
                                "Description."
                        ::= { fkSwWatchdogControl 1 }

                
                -- 1.3.6.1.4.1.10428 9 1.101.1.17.2.2
                fkSwWatchdogControlStatus OBJECT-TYPE
                        SYNTAX FkControlStatusType
                        MAX-ACCESS read-only
                        STATUS current
                        DESCRIPTION
                                "Description."
                        ::= { fkSwWatchdogControl 2 }

                
                -- 1.3.6.1.4.1.10428 9 1.101.1.17.2.3
                fkSwWatchdogControlTimer OBJECT-TYPE
                        SYNTAX Gauge32
                        MAX-ACCESS read-write
                        STATUS current
                        DESCRIPTION
                                "Description."
                        ::= { fkSwWatchdogControl 3 }

                
                -- 1.3.6.1.4.1.10428 9 1.101.1.17.2.4
                fkSwWatchdogControlTimeStamp OBJECT-TYPE
                        SYNTAX TimeTicks
                        MAX-ACCESS read-only
                        STATUS current
                        DESCRIPTION
                                "Description."
                        ::= { fkSwWatchdogControl 4 }

                
                -- 1.3.6.1.4.1.10428 9 1.101.1.17.2.5
                fkSwWatchdogControlReqResult OBJECT-TYPE
                        SYNTAX FkControlRequestResultType
                        MAX-ACCESS read-only
                        STATUS current
                        DESCRIPTION
                                "Description."
                        ::= { fkSwWatchdogControl 5 }

                
                -- 1.3.6.1.4.1.10428 9 1.101.1.17.2.6
                fkSwWatchdogControlType OBJECT-TYPE
                        SYNTAX INTEGER
                                {
                                daemonMonitoring(1),
                                inetMonitoring(2),
                                ponMonitoring(3)
                                }
                        MAX-ACCESS read-write
                        STATUS current
                        DESCRIPTION
                                "Description."
                        ::= { fkSwWatchdogControl 6 }

                
                -- 1.3.6.1.4.1.10428 9 1.101.1.17.2.7
                fkSwWatchdogControlInterval OBJECT-TYPE
                        SYNTAX INTEGER (10..86400)
                        MAX-ACCESS read-write
                        STATUS current
                        DESCRIPTION
                                "Description."
                        ::= { fkSwWatchdogControl 7 }

                
                -- 1.3.6.1.4.1.10428 9 1.101.1.17.2.8
                fkSwWatchdogControlThreshold OBJECT-TYPE
                        SYNTAX INTEGER (1..10)
                        MAX-ACCESS read-write
                        STATUS current
                        DESCRIPTION
                                "Description."
                        ::= { fkSwWatchdogControl 8 }

                
                -- 1.3.6.1.4.1.10428 9 1.101.1.17.2.9
                fkSwWatchdogControlAction OBJECT-TYPE
                        SYNTAX INTEGER
                                {
                                none(1),
                                daemonRestart(2),
                                systemReset(3),
                                systemResetWithSaveCfg(4),
                                onuPortReset(5)
                                }
                        MAX-ACCESS read-write
                        STATUS current
                        DESCRIPTION
                                "Description."
                        ::= { fkSwWatchdogControl 9 }

                
                -- 1.3.6.1.4.1.10428 9 1.101.1.17.3
                fkSwWatchdogNotification OBJECT IDENTIFIER ::= { fkSwWatchdogBase 3 }

                
                -- 1.3.6.1.4.1.10428 9 1.101.1.17.3.1
                fkSwWatchdogCreated NOTIFICATION-TYPE
                        OBJECTS { fkSwWatchdogInterval, fkSwWatchdogThreshold, fkSwWatchdogAction }
                        STATUS current
                        DESCRIPTION 
                                "Description."
                        ::= { fkSwWatchdogNotification 1 }

                
                -- 1.3.6.1.4.1.10428 9 1.101.1.17.3.2
                fkSwWatchdogDeleted NOTIFICATION-TYPE
                        OBJECTS { fkSwWatchdogControlType }
                        STATUS current
                        DESCRIPTION 
                                "Description."
                        ::= { fkSwWatchdogNotification 2 }

                
                -- 1.3.6.1.4.1.10428 9 1.101.1.18
                fkAutoUpgrade OBJECT IDENTIFIER ::= { fkSystemMaintenance 18 }

                
                -- 1.3.6.1.4.1.10428 9 1.101.1.18.1
                fkAutoUpgradeProfile OBJECT IDENTIFIER ::= { fkAutoUpgrade 1 }

                
                -- 1.3.6.1.4.1.10428 9 1.101.1.18.1.1
                fkAutoUpgradeProfileTable OBJECT-TYPE
                        SYNTAX SEQUENCE OF FkAutoUpgradeProfileEntry
                        MAX-ACCESS not-accessible
                        STATUS current
                        DESCRIPTION
                                "Description."
                        ::= { fkAutoUpgradeProfile 1 }

                
                -- 1.3.6.1.4.1.10428 9 1.101.1.18.1.1.1
                fkAutoUpgradeProfileEntry OBJECT-TYPE
                        SYNTAX FkAutoUpgradeProfileEntry
                        MAX-ACCESS not-accessible
                        STATUS current
                        DESCRIPTION
                                "Description."
                        INDEX { fkAutoUpgradeProfileName }
                        ::= { fkAutoUpgradeProfileTable 1 }

                
                FkAutoUpgradeProfileEntry ::=
                        SEQUENCE { 
                                fkAutoUpgradeProfileName
                                        OCTET STRING,
                                fkAutoUpgradeProfileOldVer
                                        OCTET STRING,
                                fkAutoUpgradeProfileNewVer
                                        OCTET STRING,
                                fkAutoUpgradeProfileSize
                                        Integer32,
                                fkAutoUpgradeProfileDate
                                        OCTET STRING,
                                fkAutoUpgradeProfilePeriodType
                                        INTEGER,
                                fkAutoUpgradeProfilePeriodDate
                                        OCTET STRING,
                                fkAutoUpgradeProfileTimeout
                                        Integer32,
                                fkAutoUpgradeProfileRetry
                                        Integer32,
                                fkAutoUpgradeProfileRegSec
                                        Integer32,
                                fkAutoUpgradeProfileReloadTime
                                        Integer32
                         }

                -- 1.3.6.1.4.1.10428 9 1.101.1.18.1.1.1.1
                fkAutoUpgradeProfileName OBJECT-TYPE
                        SYNTAX OCTET STRING
                        MAX-ACCESS read-only
                        STATUS current
                        DESCRIPTION
                                "Description."
                        ::= { fkAutoUpgradeProfileEntry 1 }

                
                -- 1.3.6.1.4.1.10428 9 1.101.1.18.1.1.1.2
                fkAutoUpgradeProfileOldVer OBJECT-TYPE
                        SYNTAX OCTET STRING
                        MAX-ACCESS read-only
                        STATUS current
                        DESCRIPTION
                                "Description."
                        ::= { fkAutoUpgradeProfileEntry 2 }

                
                -- 1.3.6.1.4.1.10428 9 1.101.1.18.1.1.1.3
                fkAutoUpgradeProfileNewVer OBJECT-TYPE
                        SYNTAX OCTET STRING
                        MAX-ACCESS read-only
                        STATUS current
                        DESCRIPTION
                                "Description."
                        ::= { fkAutoUpgradeProfileEntry 3 }

                
                -- 1.3.6.1.4.1.10428 9 1.101.1.18.1.1.1.4
                fkAutoUpgradeProfileSize OBJECT-TYPE
                        SYNTAX Integer32
                        MAX-ACCESS read-only
                        STATUS current
                        DESCRIPTION
                                "Description."
                        ::= { fkAutoUpgradeProfileEntry 4 }

                
                -- 1.3.6.1.4.1.10428 9 1.101.1.18.1.1.1.5
                fkAutoUpgradeProfileDate OBJECT-TYPE
                        SYNTAX OCTET STRING
                        MAX-ACCESS read-only
                        STATUS current
                        DESCRIPTION
                                "Description."
                        ::= { fkAutoUpgradeProfileEntry 5 }

                
                -- 1.3.6.1.4.1.10428 9 1.101.1.18.1.1.1.6
                fkAutoUpgradeProfilePeriodType OBJECT-TYPE
                        SYNTAX INTEGER
                                {
                                daily(1),
                                weekly(2),
                                monthly(3),
                                interval(4)
                                }
                        MAX-ACCESS read-only
                        STATUS current
                        DESCRIPTION
                                "Description."
                        ::= { fkAutoUpgradeProfileEntry 6 }

                
                -- 1.3.6.1.4.1.10428 9 1.101.1.18.1.1.1.7
                fkAutoUpgradeProfilePeriodDate OBJECT-TYPE
                        SYNTAX OCTET STRING
                        MAX-ACCESS read-only
                        STATUS current
                        DESCRIPTION
                                "Description."
                        ::= { fkAutoUpgradeProfileEntry 7 }

                
                -- 1.3.6.1.4.1.10428 9 1.101.1.18.1.1.1.8
                fkAutoUpgradeProfileTimeout OBJECT-TYPE
                        SYNTAX Integer32
                        MAX-ACCESS read-only
                        STATUS current
                        DESCRIPTION
                                "Description."
                        ::= { fkAutoUpgradeProfileEntry 8 }

                
                -- 1.3.6.1.4.1.10428 9 1.101.1.18.1.1.1.9
                fkAutoUpgradeProfileRetry OBJECT-TYPE
                        SYNTAX Integer32
                        MAX-ACCESS read-only
                        STATUS current
                        DESCRIPTION
                                "Description."
                        ::= { fkAutoUpgradeProfileEntry 9 }

                
                -- 1.3.6.1.4.1.10428 9 1.101.1.18.1.1.1.10
                fkAutoUpgradeProfileRegSec OBJECT-TYPE
                        SYNTAX Integer32
                        MAX-ACCESS read-only
                        STATUS current
                        DESCRIPTION
                                "Description."
                        ::= { fkAutoUpgradeProfileEntry 10 }

                
                -- 1.3.6.1.4.1.10428 9 1.101.1.18.1.1.1.11
                fkAutoUpgradeProfileReloadTime OBJECT-TYPE
                        SYNTAX Integer32
                        MAX-ACCESS read-only
                        STATUS current
                        DESCRIPTION
                                "Description."
                        ::= { fkAutoUpgradeProfileEntry 11 }

                
                -- 1.3.6.1.4.1.10428 9 1.101.1.18.1.2
                fkAutoUpgradeProfileControl OBJECT IDENTIFIER ::= { fkAutoUpgradeProfile 2 }

                
                -- 1.3.6.1.4.1.10428 9 1.101.1.18.1.2.1
                fkAutoUpgradeProfileControlRequest OBJECT-TYPE
                        SYNTAX INTEGER
                                {
                                createAutoUpgrdProfile(1),
                                destroyAutoUpgrdProfile(2),
                                modifyAutoUpgrdProfile(3)
                                }
                        MAX-ACCESS read-write
                        STATUS current
                        DESCRIPTION
                                "Description."
                        ::= { fkAutoUpgradeProfileControl 1 }

                
                -- 1.3.6.1.4.1.10428 9 1.101.1.18.1.2.2
                fkAutoUpgradeProfileControlStatus OBJECT-TYPE
                        SYNTAX FkControlStatusType
                        MAX-ACCESS read-only
                        STATUS current
                        DESCRIPTION
                                "Description."
                        ::= { fkAutoUpgradeProfileControl 2 }

                
                -- 1.3.6.1.4.1.10428 9 1.101.1.18.1.2.3
                fkAutoUpgradeProfileControlTimer OBJECT-TYPE
                        SYNTAX Gauge32
                        MAX-ACCESS read-write
                        STATUS current
                        DESCRIPTION
                                "Description."
                        ::= { fkAutoUpgradeProfileControl 3 }

                
                -- 1.3.6.1.4.1.10428 9 1.101.1.18.1.2.4
                fkAutoUpgradeProfileControlTimeStamp OBJECT-TYPE
                        SYNTAX TimeTicks
                        MAX-ACCESS read-only
                        STATUS current
                        DESCRIPTION
                                "Description."
                        ::= { fkAutoUpgradeProfileControl 4 }

                
                -- 1.3.6.1.4.1.10428 9 1.101.1.18.1.2.5
                fkAutoUpgradeProfileControlReqResult OBJECT-TYPE
                        SYNTAX FkControlRequestResultType
                        MAX-ACCESS read-only
                        STATUS current
                        DESCRIPTION
                                "Description."
                        ::= { fkAutoUpgradeProfileControl 5 }

                
                -- 1.3.6.1.4.1.10428 9 1.101.1.18.1.2.6
                fkAutoUpgradeProfileControlName OBJECT-TYPE
                        SYNTAX OCTET STRING
                        MAX-ACCESS read-write
                        STATUS current
                        DESCRIPTION
                                "Description."
                        ::= { fkAutoUpgradeProfileControl 6 }

                
                -- 1.3.6.1.4.1.10428 9 1.101.1.18.1.2.7
                fkAutoUpgradeProfileControlOldVer OBJECT-TYPE
                        SYNTAX OCTET STRING
                        MAX-ACCESS read-write
                        STATUS current
                        DESCRIPTION
                                "Description."
                        ::= { fkAutoUpgradeProfileControl 7 }

                
                -- 1.3.6.1.4.1.10428 9 1.101.1.18.1.2.8
                fkAutoUpgradeProfileControlNewVer OBJECT-TYPE
                        SYNTAX OCTET STRING
                        MAX-ACCESS read-write
                        STATUS current
                        DESCRIPTION
                                "Description."
                        ::= { fkAutoUpgradeProfileControl 8 }

                
                -- 1.3.6.1.4.1.10428 9 1.101.1.18.1.2.9
                fkAutoUpgradeProfileControlSize OBJECT-TYPE
                        SYNTAX Integer32
                        MAX-ACCESS read-write
                        STATUS current
                        DESCRIPTION
                                "Description."
                        ::= { fkAutoUpgradeProfileControl 9 }

                
                -- 1.3.6.1.4.1.10428 9 1.101.1.18.1.2.10
                fkAutoUpgradeProfileControlDate OBJECT-TYPE
                        SYNTAX OCTET STRING
                        MAX-ACCESS read-write
                        STATUS current
                        DESCRIPTION
                                "Description."
                        ::= { fkAutoUpgradeProfileControl 10 }

                
                -- 1.3.6.1.4.1.10428 9 1.101.1.18.1.2.11
                fkAutoUpgradeProfileControlPeriodType OBJECT-TYPE
                        SYNTAX INTEGER
                                {
                                daily(1),
                                weekly(2),
                                monthly(3),
                                interval(4)
                                }
                        MAX-ACCESS read-write
                        STATUS current
                        DESCRIPTION
                                "Description."
                        ::= { fkAutoUpgradeProfileControl 11 }

                
                -- 1.3.6.1.4.1.10428 9 1.101.1.18.1.2.12
                fkAutoUpgradeProfileControlPeriodDate OBJECT-TYPE
                        SYNTAX OCTET STRING
                        MAX-ACCESS read-write
                        STATUS current
                        DESCRIPTION
                                "Description."
                        ::= { fkAutoUpgradeProfileControl 12 }

                
                -- 1.3.6.1.4.1.10428 9 1.101.1.18.1.2.13
                fkAutoUpgradeProfileControlTimeout OBJECT-TYPE
                        SYNTAX Integer32
                        MAX-ACCESS read-write
                        STATUS current
                        DESCRIPTION
                                "Description."
                        ::= { fkAutoUpgradeProfileControl 13 }

                
                -- 1.3.6.1.4.1.10428 9 1.101.1.18.1.2.14
                fkAutoUpgradeProfileControlRetry OBJECT-TYPE
                        SYNTAX Integer32
                        MAX-ACCESS read-write
                        STATUS current
                        DESCRIPTION
                                "Description."
                        ::= { fkAutoUpgradeProfileControl 14 }

                
                -- 1.3.6.1.4.1.10428 9 1.101.1.18.1.2.15
                fkAutoUpgradeProfileControlRegSec OBJECT-TYPE
                        SYNTAX Integer32
                        MAX-ACCESS read-write
                        STATUS current
                        DESCRIPTION
                                "Description."
                        ::= { fkAutoUpgradeProfileControl 15 }

                
                -- 1.3.6.1.4.1.10428 9 1.101.1.18.1.2.16
                fkAutoUpgradeProfileControlReloadTime OBJECT-TYPE
                        SYNTAX Integer32
                        MAX-ACCESS read-write
                        STATUS current
                        DESCRIPTION
                                "Description."
                        ::= { fkAutoUpgradeProfileControl 16 }

                
                -- 1.3.6.1.4.1.10428 9 1.101.1.18.1.3
                fkAutoUpgradeProfileNotification OBJECT IDENTIFIER ::= { fkAutoUpgradeProfile 3 }

                
                -- 1.3.6.1.4.1.10428 9 1.101.1.18.1.3.1
                fkAutoUpgradeProfileCreated NOTIFICATION-TYPE
                        OBJECTS { fkAutoUpgradeProfileControlRequest, fkAutoUpgradeProfileControlTimeStamp, fkAutoUpgradeProfileControlReqResult, fkAutoUpgradeProfileControlName, fkAutoUpgradeProfileControlOldVer, 
                                fkAutoUpgradeProfileControlNewVer, fkAutoUpgradeProfileControlSize, fkAutoUpgradeProfileControlDate, fkAutoUpgradeProfileControlPeriodType, fkAutoUpgradeProfileControlPeriodDate, 
                                fkAutoUpgradeProfileControlTimeout, fkAutoUpgradeProfileControlRetry, fkAutoUpgradeProfileControlRegSec, fkAutoUpgradeProfileControlReloadTime }
                        STATUS current
                        DESCRIPTION 
                                "Description."
                        ::= { fkAutoUpgradeProfileNotification 1 }

                
                -- 1.3.6.1.4.1.10428 9 1.101.1.18.1.3.2
                fkAutoUpgradeProfileDeleted NOTIFICATION-TYPE
                        OBJECTS { fkAutoUpgradeProfileControlRequest, fkAutoUpgradeProfileControlTimeStamp, fkAutoUpgradeProfileControlReqResult, fkAutoUpgradeProfileControlName }
                        STATUS current
                        DESCRIPTION 
                                "Description."
                        ::= { fkAutoUpgradeProfileNotification 2 }

                
                -- 1.3.6.1.4.1.10428 9 1.101.1.18.1.3.3
                fkAutoUpgradeProfileChanged NOTIFICATION-TYPE
                        OBJECTS { fkAutoUpgradeProfileControlRequest, fkAutoUpgradeProfileControlTimeStamp, fkAutoUpgradeProfileControlReqResult, fkAutoUpgradeProfileControlName, fkAutoUpgradeProfileControlOldVer, 
                                fkAutoUpgradeProfileControlNewVer, fkAutoUpgradeProfileControlSize, fkAutoUpgradeProfileControlDate, fkAutoUpgradeProfileControlPeriodType, fkAutoUpgradeProfileControlPeriodDate, 
                                fkAutoUpgradeProfileControlTimeout, fkAutoUpgradeProfileControlRetry, fkAutoUpgradeProfileControlRegSec, fkAutoUpgradeProfileControlReloadTime }
                        STATUS current
                        DESCRIPTION 
                                "Description."
                        ::= { fkAutoUpgradeProfileNotification 3 }

                
                -- 1.3.6.1.4.1.10428 9 1.101.1.18.2
                fkAutoUpgradeMgmt OBJECT IDENTIFIER ::= { fkAutoUpgrade 2 }

                
                -- 1.3.6.1.4.1.10428 9 1.101.1.18.2.1
                fkAutoUpgradeOltTable OBJECT-TYPE
                        SYNTAX SEQUENCE OF FkAutoUpgradeOltEntry
                        MAX-ACCESS not-accessible
                        STATUS current
                        DESCRIPTION
                                "Description."
                        ::= { fkAutoUpgradeMgmt 1 }

                
                -- 1.3.6.1.4.1.10428 9 1.101.1.18.2.1.1
                fkAutoUpgradeOltEntry OBJECT-TYPE
                        SYNTAX FkAutoUpgradeOltEntry
                        MAX-ACCESS not-accessible
                        STATUS current
                        DESCRIPTION
                                "Description."
                        INDEX { fkAutoUpgradeOltSlotIndex, fkAutoUpgradeOltFwType, fkAutoUpgradeOltProfileName, fkAutoUpgradeOltSlotType }
                        ::= { fkAutoUpgradeOltTable 1 }

                
                FkAutoUpgradeOltEntry ::=
                        SEQUENCE { 
                                fkAutoUpgradeOltSlotIndex
                                        INTEGER,
                                fkAutoUpgradeOltFwType
                                        INTEGER,
                                fkAutoUpgradeOltProfileName
                                        OCTET STRING,
                                fkAutoUpgradeOltSlotType
                                        INTEGER
                         }

                -- 1.3.6.1.4.1.10428 9 1.101.1.18.2.1.1.1
                fkAutoUpgradeOltSlotIndex OBJECT-TYPE
                        SYNTAX INTEGER (0..64)
                        MAX-ACCESS read-only
                        STATUS current
                        DESCRIPTION
                                "Description."
                        ::= { fkAutoUpgradeOltEntry 1 }

                
                -- 1.3.6.1.4.1.10428 9 1.101.1.18.2.1.1.2
                fkAutoUpgradeOltFwType OBJECT-TYPE
                        SYNTAX INTEGER
                                {
                                os(1),
                                bootloader(2)
                                }
                        MAX-ACCESS read-only
                        STATUS current
                        DESCRIPTION
                                "Description."
                        ::= { fkAutoUpgradeOltEntry 2 }

                
                -- 1.3.6.1.4.1.10428 9 1.101.1.18.2.1.1.3
                fkAutoUpgradeOltProfileName OBJECT-TYPE
                        SYNTAX OCTET STRING
                        MAX-ACCESS read-only
                        STATUS current
                        DESCRIPTION
                                "Description."
                        ::= { fkAutoUpgradeOltEntry 3 }

                
                -- 1.3.6.1.4.1.10428 9 1.101.1.18.2.1.1.4
                fkAutoUpgradeOltSlotType OBJECT-TYPE
                        SYNTAX INTEGER
                                {
                                sfu(1),
                                siuge12(2),
                                siuepon12(3),
                                siugpon4(4),
                                niuge12(5)
                                }
                        MAX-ACCESS read-only
                        STATUS current
                        DESCRIPTION
                                "Description."
                        ::= { fkAutoUpgradeOltEntry 4 }

                
                -- 1.3.6.1.4.1.10428 9 1.101.1.18.2.2
                fkAutoUpgradeOntTable OBJECT-TYPE
                        SYNTAX SEQUENCE OF FkAutoUpgradeOntEntry
                        MAX-ACCESS not-accessible
                        STATUS current
                        DESCRIPTION
                                "Description."
                        ::= { fkAutoUpgradeMgmt 2 }

                
                -- 1.3.6.1.4.1.10428 9 1.101.1.18.2.2.1
                fkAutoUpgradeOntEntry OBJECT-TYPE
                        SYNTAX FkAutoUpgradeOntEntry
                        MAX-ACCESS not-accessible
                        STATUS current
                        DESCRIPTION
                                "Description."
                        INDEX { fkAutoUpgradeOntOltIndex, fkAutoUpgradeOntIndex, fkAutoUpgradeOntFwType, fkAutoUpgradeOntProfileName }
                        ::= { fkAutoUpgradeOntTable 1 }

                
                FkAutoUpgradeOntEntry ::=
                        SEQUENCE { 
                                fkAutoUpgradeOntOltIndex
                                        INTEGER,
                                fkAutoUpgradeOntIndex
                                        INTEGER,
                                fkAutoUpgradeOntFwType
                                        INTEGER,
                                fkAutoUpgradeOntProfileName
                                        OCTET STRING
                         }

                -- 1.3.6.1.4.1.10428 9 1.101.1.18.2.2.1.1
                fkAutoUpgradeOntOltIndex OBJECT-TYPE
                        SYNTAX INTEGER (0..64)
                        MAX-ACCESS read-only
                        STATUS current
                        DESCRIPTION
                                "Description."
                        ::= { fkAutoUpgradeOntEntry 1 }

                
                -- 1.3.6.1.4.1.10428 9 1.101.1.18.2.2.1.2
                fkAutoUpgradeOntIndex OBJECT-TYPE
                        SYNTAX INTEGER (0..64)
                        MAX-ACCESS read-only
                        STATUS current
                        DESCRIPTION
                                "Description."
                        ::= { fkAutoUpgradeOntEntry 2 }

                
                -- 1.3.6.1.4.1.10428 9 1.101.1.18.2.2.1.3
                fkAutoUpgradeOntFwType OBJECT-TYPE
                        SYNTAX INTEGER
                                {
                                os(1),
                                bootloader(2)
                                }
                        MAX-ACCESS read-only
                        STATUS current
                        DESCRIPTION
                                "Description."
                        ::= { fkAutoUpgradeOntEntry 3 }

                
                -- 1.3.6.1.4.1.10428 9 1.101.1.18.2.2.1.4
                fkAutoUpgradeOntProfileName OBJECT-TYPE
                        SYNTAX OCTET STRING
                        MAX-ACCESS read-only
                        STATUS current
                        DESCRIPTION
                                "Description."
                        ::= { fkAutoUpgradeOntEntry 4 }

                
                -- 1.3.6.1.4.1.10428 9 1.101.1.18.2.3
                fkAutoUpgradeMgmtControl OBJECT IDENTIFIER ::= { fkAutoUpgradeMgmt 3 }

                
                -- 1.3.6.1.4.1.10428 9 1.101.1.18.2.3.1
                fkAutoUpgradeMgmtControlRequest OBJECT-TYPE
                        SYNTAX INTEGER
                                {
                                setAutoUpgrdOltProfile(1),
                                unsetAutoUpgrdOltProfile(2),
                                setAutoUpgrdOntProfile(3),
                                unsetAutoUpgrdOntProfile(4)
                                }
                        MAX-ACCESS read-write
                        STATUS current
                        DESCRIPTION
                                "Description."
                        ::= { fkAutoUpgradeMgmtControl 1 }

                
                -- 1.3.6.1.4.1.10428 9 1.101.1.18.2.3.2
                fkAutoUpgradeMgmtControlStatus OBJECT-TYPE
                        SYNTAX FkControlStatusType
                        MAX-ACCESS read-only
                        STATUS current
                        DESCRIPTION
                                "Description."
                        ::= { fkAutoUpgradeMgmtControl 2 }

                
                -- 1.3.6.1.4.1.10428 9 1.101.1.18.2.3.3
                fkAutoUpgradeMgmtControlTimer OBJECT-TYPE
                        SYNTAX Gauge32
                        MAX-ACCESS read-write
                        STATUS current
                        DESCRIPTION
                                "Description."
                        ::= { fkAutoUpgradeMgmtControl 3 }

                
                -- 1.3.6.1.4.1.10428 9 1.101.1.18.2.3.4
                fkAutoUpgradeMgmtControlTimeStamp OBJECT-TYPE
                        SYNTAX TimeTicks
                        MAX-ACCESS read-only
                        STATUS current
                        DESCRIPTION
                                "Description."
                        ::= { fkAutoUpgradeMgmtControl 4 }

                
                -- 1.3.6.1.4.1.10428 9 1.101.1.18.2.3.5
                fkAutoUpgradeMgmtControlReqResult OBJECT-TYPE
                        SYNTAX FkControlRequestResultType
                        MAX-ACCESS read-only
                        STATUS current
                        DESCRIPTION
                                "Description."
                        ::= { fkAutoUpgradeMgmtControl 5 }

                
                -- 1.3.6.1.4.1.10428 9 1.101.1.18.2.3.6
                fkAutoUpgradeMgmtControlOltIndex OBJECT-TYPE
                        SYNTAX OCTET STRING
                        MAX-ACCESS read-write
                        STATUS current
                        DESCRIPTION
                                "Description."
                        ::= { fkAutoUpgradeMgmtControl 6 }

                
                -- 1.3.6.1.4.1.10428 9 1.101.1.18.2.3.7
                fkAutoUpgradeMgmtControlOntIndex OBJECT-TYPE
                        SYNTAX OCTET STRING
                        MAX-ACCESS read-write
                        STATUS current
                        DESCRIPTION
                                "Description."
                        ::= { fkAutoUpgradeMgmtControl 7 }

                
                -- 1.3.6.1.4.1.10428 9 1.101.1.18.2.3.8
                fkAutoUpgradeMgmtControlFwType OBJECT-TYPE
                        SYNTAX INTEGER
                                {
                                os(1),
                                bootloader(2)
                                }
                        MAX-ACCESS read-write
                        STATUS current
                        DESCRIPTION
                                "Description."
                        ::= { fkAutoUpgradeMgmtControl 8 }

                
                -- 1.3.6.1.4.1.10428 9 1.101.1.18.2.3.9
                fkAutoUpgradeMgmtControlProfileName OBJECT-TYPE
                        SYNTAX OCTET STRING
                        MAX-ACCESS read-write
                        STATUS current
                        DESCRIPTION
                                "Description."
                        ::= { fkAutoUpgradeMgmtControl 9 }

                
                -- 1.3.6.1.4.1.10428 9 1.101.1.18.2.3.10
                fkAutoUpgradeMgmtControlSlotType OBJECT-TYPE
                        SYNTAX INTEGER
                                {
                                sfu(1),
                                siuge12(2),
                                siuepon12(3),
                                siugpon4(4),
                                niuge12(5)
                                }
                        MAX-ACCESS read-write
                        STATUS current
                        DESCRIPTION
                                "Description."
                        ::= { fkAutoUpgradeMgmtControl 10 }

                
                -- 1.3.6.1.4.1.10428 9 1.101.1.18.2.4
                fkAutoUpgradeMgmtNotification OBJECT IDENTIFIER ::= { fkAutoUpgradeMgmt 4 }

                
                -- 1.3.6.1.4.1.10428 9 1.101.1.18.2.4.1
                fkAutoUpgradeSetOltProfile NOTIFICATION-TYPE
                        OBJECTS { fkAutoUpgradeMgmtControlRequest, fkAutoUpgradeMgmtControlTimeStamp, fkAutoUpgradeMgmtControlReqResult, fkAutoUpgradeMgmtControlOltIndex, fkAutoUpgradeMgmtControlFwType, 
                                fkAutoUpgradeMgmtControlProfileName, fkAutoUpgradeMgmtControlSlotType }
                        STATUS current
                        DESCRIPTION 
                                "Description."
                        ::= { fkAutoUpgradeMgmtNotification 1 }

                
                -- 1.3.6.1.4.1.10428 9 1.101.1.18.2.4.2
                fkAutoUpgradeUnSetOltProfile NOTIFICATION-TYPE
                        OBJECTS { fkAutoUpgradeMgmtControlRequest, fkAutoUpgradeMgmtControlTimeStamp, fkAutoUpgradeMgmtControlReqResult, fkAutoUpgradeMgmtControlOltIndex, fkAutoUpgradeMgmtControlFwType, 
                                fkAutoUpgradeMgmtControlProfileName, fkAutoUpgradeMgmtControlSlotType }
                        STATUS current
                        DESCRIPTION 
                                "Description."
                        ::= { fkAutoUpgradeMgmtNotification 2 }

                
                -- 1.3.6.1.4.1.10428 9 1.101.1.18.2.4.3
                fkAutoUpgradeSetOntProfile NOTIFICATION-TYPE
                        OBJECTS { fkAutoUpgradeMgmtControlRequest, fkAutoUpgradeMgmtControlTimeStamp, fkAutoUpgradeMgmtControlReqResult, fkAutoUpgradeMgmtControlOntIndex, fkAutoUpgradeMgmtControlFwType, 
                                fkAutoUpgradeMgmtControlProfileName }
                        STATUS current
                        DESCRIPTION 
                                "Description."
                        ::= { fkAutoUpgradeMgmtNotification 3 }

                
                -- 1.3.6.1.4.1.10428 9 1.101.1.18.2.4.4
                fkAutoUpgradeUnSetOntProfile NOTIFICATION-TYPE
                        OBJECTS { fkAutoUpgradeMgmtControlRequest, fkAutoUpgradeMgmtControlTimeStamp, fkAutoUpgradeMgmtControlReqResult, fkAutoUpgradeMgmtControlOntIndex, fkAutoUpgradeMgmtControlFwType, 
                                fkAutoUpgradeMgmtControlProfileName }
                        STATUS current
                        DESCRIPTION 
                                "Description."
                        ::= { fkAutoUpgradeMgmtNotification 4 }

                
                -- 1.3.6.1.4.1.10428 9 1.101.1.18.3
                fkAutoUpgradeLog OBJECT IDENTIFIER ::= { fkAutoUpgrade 3 }

                
                -- 1.3.6.1.4.1.10428 9 1.101.1.18.3.1
                fkAutoUpgradeLogInfo OBJECT IDENTIFIER ::= { fkAutoUpgradeLog 1 }

                
                -- 1.3.6.1.4.1.10428 9 1.101.1.18.3.2
                fkAutoUpgradeLogControl OBJECT IDENTIFIER ::= { fkAutoUpgradeLog 2 }

                
                -- 1.3.6.1.4.1.10428 9 1.101.1.18.3.2.1
                fkAutoUpgradeLogControlRequest OBJECT-TYPE
                        SYNTAX INTEGER
                                {
                                delAutoUpgradeOltLog(1),
                                delAutoUpgradeOltLogAll(2),
                                delAutoUpgradeOntLog(3),
                                delAutoUpgradeOntLogAll(4),
                                exportAutoUpgradeOltLog(5),
                                exportAutoUpgradeOntLog(6)
                                }
                        MAX-ACCESS read-write
                        STATUS current
                        DESCRIPTION
                                "Description."
                        ::= { fkAutoUpgradeLogControl 1 }

                
                -- 1.3.6.1.4.1.10428 9 1.101.1.18.3.2.2
                fkAutoUpgradeLogControlStatus OBJECT-TYPE
                        SYNTAX FkControlStatusType
                        MAX-ACCESS read-only
                        STATUS current
                        DESCRIPTION
                                "Description."
                        ::= { fkAutoUpgradeLogControl 2 }

                
                -- 1.3.6.1.4.1.10428 9 1.101.1.18.3.2.3
                fkAutoUpgradeLogControlTimer OBJECT-TYPE
                        SYNTAX Gauge32
                        MAX-ACCESS read-write
                        STATUS current
                        DESCRIPTION
                                "Description."
                        ::= { fkAutoUpgradeLogControl 3 }

                
                -- 1.3.6.1.4.1.10428 9 1.101.1.18.3.2.4
                fkAutoUpgradeLogControlTimeStamp OBJECT-TYPE
                        SYNTAX TimeTicks
                        MAX-ACCESS read-only
                        STATUS current
                        DESCRIPTION
                                "Description."
                        ::= { fkAutoUpgradeLogControl 4 }

                
                -- 1.3.6.1.4.1.10428 9 1.101.1.18.3.2.5
                fkAutoUpgradeLogControlReqResult OBJECT-TYPE
                        SYNTAX FkControlRequestResultType
                        MAX-ACCESS read-only
                        STATUS current
                        DESCRIPTION
                                "Description."
                        ::= { fkAutoUpgradeLogControl 5 }

                
                -- 1.3.6.1.4.1.10428 9 1.101.1.18.3.2.6
                fkAutoUpgradeLogControlSlotIndex OBJECT-TYPE
                        SYNTAX OCTET STRING
                        MAX-ACCESS read-write
                        STATUS current
                        DESCRIPTION
                                "Description."
                        ::= { fkAutoUpgradeLogControl 6 }

                
                -- 1.3.6.1.4.1.10428 9 1.101.1.18.3.2.7
                fkAutoUpgradeLogControlOntIndex OBJECT-TYPE
                        SYNTAX OCTET STRING
                        MAX-ACCESS read-write
                        STATUS current
                        DESCRIPTION
                                "Description."
                        ::= { fkAutoUpgradeLogControl 7 }

                
                -- 1.3.6.1.4.1.10428 9 1.101.1.18.3.2.8
                fkAutoUpgradeLogControlExportMethod OBJECT-TYPE
                        SYNTAX INTEGER
                                {
                                ftp(1),
                                tftp(2)
                                }
                        MAX-ACCESS read-write
                        STATUS current
                        DESCRIPTION
                                "Description."
                        ::= { fkAutoUpgradeLogControl 8 }

                
                -- 1.3.6.1.4.1.10428 9 1.101.1.18.3.2.9
                fkAutoUpgradeLogControlServer OBJECT-TYPE
                        SYNTAX IpAddress
                        MAX-ACCESS read-write
                        STATUS current
                        DESCRIPTION
                                "Description."
                        ::= { fkAutoUpgradeLogControl 9 }

                
                -- 1.3.6.1.4.1.10428 9 1.101.1.18.3.2.10
                fkAutoUpgradeLogControlUser OBJECT-TYPE
                        SYNTAX OCTET STRING
                        MAX-ACCESS read-write
                        STATUS current
                        DESCRIPTION
                                "Description."
                        ::= { fkAutoUpgradeLogControl 10 }

                
                -- 1.3.6.1.4.1.10428 9 1.101.1.18.3.2.11
                fkAutoUpgradeLogControlPasswd OBJECT-TYPE
                        SYNTAX OCTET STRING
                        MAX-ACCESS read-write
                        STATUS current
                        DESCRIPTION
                                "Description."
                        ::= { fkAutoUpgradeLogControl 11 }

                
                -- 1.3.6.1.4.1.10428 9 1.101.1.18.3.3
                fkAutoUpgradeLogNotification OBJECT IDENTIFIER ::= { fkAutoUpgradeLog 3 }

                
                -- 1.3.6.1.4.1.10428 9 1.101.1.18.3.3.1
                fkAutoUpgradeDeleteOltLog NOTIFICATION-TYPE
                        OBJECTS { fkAutoUpgradeLogControlRequest, fkAutoUpgradeLogControlTimeStamp, fkAutoUpgradeLogControlReqResult, fkAutoUpgradeLogControlSlotIndex }
                        STATUS current
                        DESCRIPTION 
                                "Description."
                        ::= { fkAutoUpgradeLogNotification 1 }

                
                -- 1.3.6.1.4.1.10428 9 1.101.1.18.3.3.2
                fkAutoUpgradeDeleteAllOltLog NOTIFICATION-TYPE
                        OBJECTS { fkAutoUpgradeLogControlRequest, fkAutoUpgradeLogControlTimeStamp, fkAutoUpgradeLogControlReqResult }
                        STATUS current
                        DESCRIPTION 
                                "Description."
                        ::= { fkAutoUpgradeLogNotification 2 }

                
                -- 1.3.6.1.4.1.10428 9 1.101.1.18.3.3.3
                fkAutoUpgradeDeleteOntLog NOTIFICATION-TYPE
                        OBJECTS { fkAutoUpgradeLogControlRequest, fkAutoUpgradeLogControlTimeStamp, fkAutoUpgradeLogControlReqResult, fkAutoUpgradeLogControlOntIndex }
                        STATUS current
                        DESCRIPTION 
                                "Description."
                        ::= { fkAutoUpgradeLogNotification 3 }

                
                -- 1.3.6.1.4.1.10428 9 1.101.1.18.3.3.4
                fkAutoUpgradeDeleteAllOntLog NOTIFICATION-TYPE
                        OBJECTS { fkAutoUpgradeLogControlRequest, fkAutoUpgradeLogControlTimeStamp, fkAutoUpgradeLogControlReqResult }
                        STATUS current
                        DESCRIPTION 
                                "Description."
                        ::= { fkAutoUpgradeLogNotification 4 }

                
                -- 1.3.6.1.4.1.10428 9 1.101.1.18.3.3.5
                fkAutoUpgradeExportOltLog NOTIFICATION-TYPE
                        OBJECTS { fkAutoUpgradeLogControlRequest, fkAutoUpgradeLogControlTimeStamp, fkAutoUpgradeLogControlReqResult, fkAutoUpgradeLogControlSlotIndex, fkAutoUpgradeLogControlExportMethod, 
                                fkAutoUpgradeLogControlServer, fkAutoUpgradeLogControlUser }
                        STATUS current
                        DESCRIPTION 
                                "Description."
                        ::= { fkAutoUpgradeLogNotification 5 }

                
                -- 1.3.6.1.4.1.10428 9 1.101.1.18.3.3.6
                fkAutoUpgradeExportOntLog NOTIFICATION-TYPE
                        OBJECTS { fkAutoUpgradeLogControlRequest, fkAutoUpgradeLogControlTimeStamp, fkAutoUpgradeLogControlReqResult, fkAutoUpgradeLogControlOntIndex, fkAutoUpgradeLogControlExportMethod, 
                                fkAutoUpgradeLogControlServer, fkAutoUpgradeLogControlUser }
                        STATUS current
                        DESCRIPTION 
                                "Description."
                        ::= { fkAutoUpgradeLogNotification 6 }

                
                -- 1.3.6.1.4.1.10428 9 1.101.1.100
                fkFtpclient OBJECT IDENTIFIER ::= { fkSystemMaintenance 100 }

                
                -- 1.3.6.1.4.1.10428 9 1.101.1.100.1
                fkFtpclientTable OBJECT-TYPE
                        SYNTAX SEQUENCE OF FkFtpclientEntry
                        MAX-ACCESS not-accessible
                        STATUS current
                        DESCRIPTION
                                "Description."
                        ::= { fkFtpclient 1 }

                
                -- 1.3.6.1.4.1.10428 9 1.101.1.100.1.1
                fkFtpclientEntry OBJECT-TYPE
                        SYNTAX FkFtpclientEntry
                        MAX-ACCESS not-accessible
                        STATUS current
                        DESCRIPTION
                                "Description."
                        INDEX { fkFtpclientIndex }
                        ::= { fkFtpclientTable 1 }

                
                FkFtpclientEntry ::=
                        SEQUENCE { 
                                fkFtpclientIndex
                                        Integer32,
                                fkFtpclientFileName
                                        OCTET STRING,
                                fkFtpclientFileSize
                                        Integer32
                         }

                -- 1.3.6.1.4.1.10428 9 1.101.1.100.1.1.1
                fkFtpclientIndex OBJECT-TYPE
                        SYNTAX Integer32 (1..65535)
                        MAX-ACCESS read-only
                        STATUS current
                        DESCRIPTION
                                "index."
                        ::= { fkFtpclientEntry 1 }

                
                -- 1.3.6.1.4.1.10428 9 1.101.1.100.1.1.2
                fkFtpclientFileName OBJECT-TYPE
                        SYNTAX OCTET STRING
                        MAX-ACCESS read-only
                        STATUS current
                        DESCRIPTION
                                "The File name."
                        ::= { fkFtpclientEntry 2 }

                
                -- 1.3.6.1.4.1.10428 9 1.101.1.100.1.1.3
                fkFtpclientFileSize OBJECT-TYPE
                        SYNTAX Integer32
                        MAX-ACCESS read-only
                        STATUS current
                        DESCRIPTION
                                "The File size."
                        ::= { fkFtpclientEntry 3 }

                
                -- 1.3.6.1.4.1.10428 9 1.101.1.100.2
                fkFtpclientControl OBJECT IDENTIFIER ::= { fkFtpclient 2 }

                
                -- 1.3.6.1.4.1.10428 9 1.101.1.100.2.1
                fkFtpclientControlRequest OBJECT-TYPE
                        SYNTAX INTEGER { updateDirectoryInfo(1) }
                        MAX-ACCESS read-write
                        STATUS current
                        DESCRIPTION
                                "Description."
                        ::= { fkFtpclientControl 1 }

                
                -- 1.3.6.1.4.1.10428 9 1.101.1.100.2.2
                fkFtpclientControlStatus OBJECT-TYPE
                        SYNTAX FkControlStatusType
                        MAX-ACCESS read-only
                        STATUS current
                        DESCRIPTION
                                "Description."
                        ::= { fkFtpclientControl 2 }

                
                -- 1.3.6.1.4.1.10428 9 1.101.1.100.2.3
                fkFtpclientControlTimer OBJECT-TYPE
                        SYNTAX Gauge32
                        MAX-ACCESS read-write
                        STATUS current
                        DESCRIPTION
                                "Description."
                        ::= { fkFtpclientControl 3 }

                
                -- 1.3.6.1.4.1.10428 9 1.101.1.100.2.4
                fkFtpclientControlTimeStamp OBJECT-TYPE
                        SYNTAX TimeTicks
                        MAX-ACCESS read-only
                        STATUS current
                        DESCRIPTION
                                "Description."
                        ::= { fkFtpclientControl 4 }

                
                -- 1.3.6.1.4.1.10428 9 1.101.1.100.2.5
                fkFtpclientControlReqResult OBJECT-TYPE
                        SYNTAX FkControlRequestResultType
                        MAX-ACCESS read-only
                        STATUS current
                        DESCRIPTION
                                "Description."
                        ::= { fkFtpclientControl 5 }

                
                -- 1.3.6.1.4.1.10428 9 1.101.1.100.2.6
                fkFtpclientControlServerIp OBJECT-TYPE
                        SYNTAX IpAddress
                        MAX-ACCESS read-write
                        STATUS current
                        DESCRIPTION
                                "The server IP address."
                        ::= { fkFtpclientControl 6 }

                
                -- 1.3.6.1.4.1.10428 9 1.101.1.100.2.7
                fkFtpclientControlUserId OBJECT-TYPE
                        SYNTAX OCTET STRING
                        MAX-ACCESS read-write
                        STATUS current
                        DESCRIPTION
                                "The user ID."
                        ::= { fkFtpclientControl 7 }

                
                -- 1.3.6.1.4.1.10428 9 1.101.1.100.2.8
                fkFtpclientControlPassword OBJECT-TYPE
                        SYNTAX OCTET STRING
                        MAX-ACCESS read-write
                        STATUS current
                        DESCRIPTION
                                "The password"
                        ::= { fkFtpclientControl 8 }

                
                -- 1.3.6.1.4.1.10428 9 1.101.1.100.2.9
                fkFtpclientControlDirectoryPath OBJECT-TYPE
                        SYNTAX OCTET STRING
                        MAX-ACCESS read-write
                        STATUS current
                        DESCRIPTION
                                "The directory path."
                        ::= { fkFtpclientControl 9 }

                
                -- 1.3.6.1.4.1.10428 9 1.101.1.100.3
                fkFtpclientNotification OBJECT IDENTIFIER ::= { fkFtpclient 3 }

                
                -- 1.3.6.1.4.1.10428 9 1.101.1.100.3.1
                fkFtpclientDirectoryInfoUpdated NOTIFICATION-TYPE
                        OBJECTS { fkFtpclientControlRequest, fkFtpclientControlTimeStamp, fkFtpclientControlReqResult, fkFtpclientControlServerIp, fkFtpclientControlUserId, 
                                fkFtpclientControlPassword, fkFtpclientControlDirectoryPath }
                        STATUS current
                        DESCRIPTION 
                                "UpdateDirectoryInfo"
                        ::= { fkFtpclientNotification 1 }

                
                -- 1.3.6.1.4.1.10428 9 1.101.1.101
                fkSystemMaintenanceGroup OBJECT-GROUP
                        OBJECTS { fkSystemModelName, fkSystemSerialNumber, fkSystemHWVersion, fkSystemBLVersion, fkSystemSWCompatibility, 
                                fkSystemOSVersion, fkSystemMacAddress, fkSystemHostName, fkSystemCPULoadAll, fkSystemCPULoadInterrupt, 
                                fkSystemCPUThreshold, fkSystemCPUInterval, fkSystemMemoryTotal, fkSystemMemoryFree, fkSystemMemoryShared, 
                                fkSystemMemoryBuffers, fkSystemMemoryCached, fkSystemMemorySwapTotal, fkSystemMemorySwapFree, fkSystemDefaultOS, 
                                fkSystemOS1Version, fkSystemOS1Size, fkSystemOS1BuildNumber, fkSystemOS2Version, fkSystemOS2Size, 
                                fkSystemOS2BuildNumber, fkSystemFlashTotalSize, fkSystemFlashOSSize, fkSystemFlashConfigSize, fkSystemFlashOSUsedSize, 
                                fkSystemFlashConfigUsedSize, fkSystemClock, fkSystemTimezone, fkSystemDNSDomainName, fkSystemInitBanner, 
                                fkSystemSuccessBanner, fkSystemFailBanner, fkSystemSyslogState, fkSystemSyslogVolatileNumber, fkSystemSyslogNonVolatileNumber, 
                                fkSystemSyslogBindAddress, fkSystemSyslogLocalCode, fkSystemSSHState, fkSystemNTPState, fkSystemBackupInterval, 
                                fkSystemDhcpActivity, fkSystemDefaultTTL, fkSystemSyslogVolatileSize, fkSystemSyslogBindInterfaceName, fkSystemSessionTime, 
                                fkSystemExecTimeout, fkSystemWatchdogStatus, fkLoginIndex, fkLoginUser, fkLoginTTY, 
                                fkLoginRemote, fkLoginTime, fkBackupConfigFile, fkProcessID, fkProcessUser, 
                                fkProcessCPU, fkProcessMemory, fkProcessVSZ, fkProcessRSS, fkProcessTerminal, 
                                fkProcessStatus, fkProcessStartTime, fkProcessUsedTime, fkProcessCommand, fkNTPServerName, 
                                fkSyslogConfIndex, fkSyslogConfMode, fkSyslogConfFacility, fkSyslogConfSeverity, fkSyslogConfTarget, 
                                fkSyslogConfStorage, fkSyslogConfTargetAddress, fkSyslogHistVolIndex, fkSyslogHistVolMsgText, fkSyslogHistVolTime, 
                                fkSyslogHistNVolIndex, fkSyslogHistNVolMsgText, fkSyslogHistNVolTime, fkSSHRemoteIndex, fkSSHRemoteUser, 
                                fkSSHRemoteHost, fkSSHRemoteTime, fkAutoCliConfStatus, fkAutoCliMemoryMaxSize, fkAutoCliMemoryUsedsize, 
                                fkAutoCliMemoryFreesize, fkAutoCliTransferInterval, fkAutoCliScriptId, fkAutoCliScriptFileName, fkAutoCliScriptFileUser, 
                                fkAutoCliScriptFileSize, fkAutoCliScriptFileUpdateTime, fkAutoCliScheduleName, fkAutoCliScheduleType, fkAutoCliScheduleInterval, 
                                fkAutoCliScheduleYear, fkAutoCliScheduleMonth, fkAutoCliScheduleDay, fkAutoCliScheduleHour, fkAutoCliScheduleMinute, 
                                fkAutoCliScheduleScriptName, fkAutoCliScheduleTransferType, fkAutoCliScheduleLastExecutedTime, fkAutoCliScheduleOutputRule, fkAutoCliScheduleLastResult, 
                                fkAutoCliOutputMemoryFileId, fkAutoCliOutputMemoryFileName, fkAutoCliOutputMemoryFileSize, fkAutoCliOutputMemoryFileUpdatedTime, fkAutoResetPingConfStatus, 
                                fkAutoResetPingIpAddress, fkAutoResetPingTransactionInterval, fkAutoResetPingNumberOfRequest, fkAutoResetPingRequestInterval, fkAutoResetPingTimeoutOfRequest, 
                                fkAutoResetPingEnableTime, fkAutoResetPingRequestCount, fkAutoResetPingReplyCount, fkAutoResetPingLossCount, fkAutoResetPingTotalPingTransaction, 
                                fkAutoResetPingTotalLossTransaction, fkAutoResetMemoryleakContStatus, fkAutoResetMemoryleakMemThreshold, fkAutoResetMemoryleakCheckInterval, fkAutoResetMemoryleakNumberOfVerification, 
                                fkAutoResetMemoryleakVerificationInterval, fkAutoResetMemoryleakRebootCount, fkAutoResetMemoryleakEnableTime, fkAutoResetMemoryleakLastFreeMemory, fkAutoResetMemoryleakVerificationCount, 
                                fkAutoResetMemoryleakDetectionCount, fkAutoResetMemoryleakTotalVerificationCount, fkAutoResetMemoryleakTotalDetectionCount, fkAutoResetMemoryleakReboottimeStartHour, fkAutoResetMemoryleakReboottimeStartMin, 
                                fkAutoResetMemoryleakReboottimeEndHour, fkAutoResetMemoryleakReboottimeEndMin, fkCoreDumpInfoPID, fkCoreDumpInfoStatus, fkCoreDumpFile, 
                                fkServiceIndex, fkServiceProtocol, fkServiceName, fkServicePort, fkSystemNtpBindInterface, 
                                fkSystemFtpBindInterface, fkSystemRedundancyPort, fkDNSServerIndex, fkDNSServerName, fkAutoResetMemoryleakRebootThreshold, 
                                fkAutoResetMemoryleakCountThreshold, fkAutoResetPingRebootCounter, fkSystemSyslogVolatileMaxLine, fkParameterMode, fkParameterValue, 
                                fkParameterName, fkAutoResetPingRebootThreshold, fkAutoResetPingLossThreshold, fkSystemUserName, fkSystemUserLevel, 
                                fkSystemUserPassword, fkAutoCliScheduleProfileName, fkAutoCliProfileServerType, fkAutoCliProfileServerIpAddress, fkAutoCliProfileServerUser, 
                                fkAutoCliProfileServerPassword, fkAutoCliProfileServerDir, fkSwWatchdogType, fkSwWatchdogInterval, fkSwWatchdogThreshold, 
                                fkSwWatchdogAction, fkSwWatchdogErrcnt, fkSystemBootInfo, fkSystemTempHighThreshold, fkSystemTempLowThreshold, 
                                fkSystemMemThreshold, fkSystemLowCPUThreshold, fkSystemLowCPUInterval, fkSystemControlRequest, fkSystemControlStatus, 
                                fkSystemControlTimer, fkSystemControlTimeStamp, fkSystemControlReqResult, fkSystemControlHostName, fkSystemControlCPUThreshold, 
                                fkSystemControlCPUInterval, fkSystemControlDefaultOS, fkSystemControlClock, fkSystemControlTimezone, fkSystemControlDNSDomainName, 
                                fkSystemControlInitBanner, fkSystemControlSuccessBanner, fkSystemControlFailBanner, fkSystemControlSyslogState, fkSystemControlSyslogVolatileNumber, 
                                fkSystemControlSyslogNonVolatileNumber, fkSystemControlSyslogBindAddress, fkSystemControlSyslogLocalCode, fkSystemControlSSHState, fkSystemControlNTPState, 
                                fkSystemControlOSUpgradeNumber, fkSystemControlServerAddress, fkSystemControlUpDownFlag, fkSystemControlUserID, fkSystemControlPassword, 
                                fkSystemControlFileName, fkSystemControlBackupFlag, fkSystemControlReloadOS, fkSystemControlBackupInterval, fkSystemControlDhcpActivity, 
                                fkSystemControlDefaultTTL, fkSystemControlSyslogVolatileSize, fkSystemControlSyslogBindInterfaceName, fkSystemControlSrcPort, fkSystemControlDstPort, 
                                fkSystemControlSessionTime, fkSystemControlExecTimeout, fkSystemControlWatchdogStatus, fkSystemControlClearOs, fkSystemControlNtpBindInterface, 
                                fkSystemControlFtpBindInterface, fkSystemControlSyslogVolMaxLine, fkSystemControlTempHighThreshold, fkSystemControlTempLowThreshold, fkSystemControlMemThreshold, 
                                fkSystemControlLowCPUThreshold, fkSystemControlLowCPUInterval, fkDNSServerControlRequest, fkDNSServerControlStatus, fkDNSServerControlTimer, 
                                fkDNSServerControlTImeStamp, fkDNSServerControlReqResult, fkDNSServerControlIndex, fkDNSServerControlName, fkBackupControlRequest, 
                                fkBackupControlStatus, fkBackupControlTimer, fkBackupControlTimeStamp, fkBackupControlReqResult, fkBackupControlCreateMode, 
                                fkBackupControlServerIP, fkBackupControlUserID, fkBackupControlPassword, fkBackupControlSrcConfigFile, fkBackupControlDstConfigFile, 
                                fkNTPServerControlRequest, fkNTPServerControlStatus, fkNTPServerControlTimer, fkNTPServerControlTImeStamp, fkNTPServerControlReqResult, 
                                fkNTPServerControlName, fkSyslogConfControlRequest, fkSyslogConfControlStatus, fkSyslogConfControlTimer, fkSyslogConfControlTimeStamp, 
                                fkSyslogConfControlReqResult, fkSyslogConfControlIndex, fkSyslogConfControlMode, fkSyslogConfControlSeverity, fkSyslogConfControlFacility, 
                                fkSyslogConfControlTarget, fkSyslogConfControlStorage, fkSyslogConfControlTargetAddress, fkSSHRemoteControlRequest, fkSSHRemoteControlStatus, 
                                fkSSHRemoteControlTimer, fkSSHRemoteControlTImeStamp, fkSSHRemoteControlReqResult, fkSSHRemoteControlIndex, fkAutoCliControlRequest, 
                                fkAutoCliControlStatus, fkAutoCliControlTimer, fkAutoCliControlTimeStamp, fkAutoCliControlReqResult, fkAutoCliControlConfStatus, 
                                fkAutoCliControlMemoryMaxsize, fkAutoCliControlTransferInterval, fkAutoCliScriptFileControlRequest, fkAutoCliScriptFileControlStatus, fkAutoCliScriptFileControlTimer, 
                                fkAutoCliScriptFileControlTimeStamp, fkAutoCliScriptFileControlReqResult, fkAutoCliScriptFileControlIpAddress, fkAutoCliScriptFileControlUserName, fkAutoCliScriptFileControlPassword, 
                                fkAutoCliScriptFileControlFilePath, fkAutoCliScriptFileControlScriptName, fkAutoCliScheduleControlRequest, fkAutoCliScheduleControlStatus, fkAutoCliScheduleControlTimer, 
                                fkAutoCliScheduleControlTimeStamp, fkAutoCliScheduleControlReqResult, fkAutoCliScheduleControlName, fkAutoCliScheduleControlType, fkAutoCliScheduleControlInterval, 
                                fkAutoCliScheduleControlYear, fkAutoCliScheduleControlMonth, fkAutoCliScheduleControlDay, fkAutoCliScheduleControlHour, fkAutoCliScheduleControlMinute, 
                                fkAutoCliScheduleControlScriptName, fkAutoCliScheduleControlTransferType, fkAutoCliScheduleControlOutputRule, fkAutoCliScheduleControlProfileName, fkAutoCliProfileControlRequest, 
                                fkAutoCliProfileControlStatus, fkAutoCliProfileControlTimer, fkAutoCliProfileControlTimeStamp, fkAutoCliProfileControlReqResult, fkAutoCliProfileControlName, 
                                fkAutoCliProfileControlType, fkAutoCliProfileServerControlRequest, fkAutoCliProfileServerControlStatus, fkAutoCliProfileServerControlTimer, fkAutoCliProfileServerControlTimeStamp, 
                                fkAutoCliProfileServerControlReqResult, fkAutoCliProfileServerControlProfName, fkAutoCliProfileServerControlIpAddress, fkAutoCliProfileServerControlUser, fkAutoCliProfileServerControlPassword, 
                                fkAutoCliProfileServerControlDir, fkAutoCliOutputMemoryFileControlRequest, fkAutoCliOutputMemoryFileControlStatus, fkAutoCliOutputMemoryFileControlTimer, fkAutoCliOutputMemoryFileControlTimeStamp, 
                                fkAutoCliOutputMemoryFileControlReqResult, fkAutoCliOutputMemoryFileControlServer, fkAutoCliOutputMemoryFileControlUserName, fkAutoCliOutputMemoryFileControlPassword, fkAutoCliOutputMemoryFileControlOutputFileName, 
                                fkAutoCliOutputMemoryFileControlRemotePath, fkAutoResetPingControlRequest, fkAutoResetPingControlStatus, fkAutoResetPingControlTimer, fkAutoResetPingControlTimeStamp, 
                                fkAutoResetPingControlReqResult, fkAutoResetPingControlConfStatus, fkAutoResetPingControlIpAddress, fkAutoResetPingControlTransactionInterval, fkAutoResetPingControlNumberOfRequest, 
                                fkAutoResetPingControlRequestInterval, fkAutoResetPingControlTimeoutOfRequest, fkAutoResetPingControlPingLossThreshold, fkAutoResetPingControlRebootThreshold, fkAutoResetMemoryleakControlRequest, 
                                fkAutoResetMemoryleakControlStatus, fkAutoResetMemoryleakControlTimer, fkAutoResetMemoryleakControlTimeStamp, fkAutoResetMemoryleakControlReqResult, fkAutoResetMemoryleakControlConfStatus, 
                                fkAutoResetMemoryleakControlMemThreshold, fkAutoResetMemoryleakControlCheckInterval, fkAutoResetMemoryleakControlNumberOfVerification, fkAutoResetMemoryleakControlVerificationInterval, fkAutoResetMemoryleakControlCountThreshold, 
                                fkAutoResetMemoryleakControlReboottimeStartHour, fkAutoResetMemoryleakControlReboottimeStartMin, fkAutoResetMemoryleakControlReboottimeEndHour, fkAutoResetMemoryleakControlReboottimeEndMin, fkAutoResetMemoryleakControlRebootThreshold, 
                                fkCoreDumpControlRequest, fkCoreDumpControlStatus, fkCoreDumpControlTimer, fkCoreDumpControlTimeStamp, fkCoreDumpControlReqResult, 
                                fkCoreDumpControlPID, fkCoreDumpControlServerIP, fkCoreDumpControlUserID, fkCoreDumpControlPassword, fkCoreDumpControlCoredumpFile, 
                                fkServiceControlRequest, fkServiceControlStatus, fkServiceControlTimer, fkServiceControlTimeStamp, fkServiceControlReqResult, 
                                fkServiceControlIndex, fkServiceControlProtocol, fkServiceControlPort, fkSystemUserControlRequest, fkSystemUserControlStatus, 
                                fkSystemUserControlTimer, fkSystemUserControlTimeStamp, fkSystemUserControlReqResult, fkSystemUserControlName, fkSystemUserControlRename, 
                                fkSystemUserControlLevel, fkSystemUserControlPwType, fkSystemUserControlPassword, fkSystemUserControlDesc, fkParameterControlRequest, 
                                fkParameterControlStatus, fkParameterControlTimer, fkParameterControlTimeStamp, fkParameterControlReqResult, fkParameterControlName, 
                                fkParameterControlValue, fkParameterControlMode, fkSwWatchdogControlRequest, fkSwWatchdogControlStatus, fkSwWatchdogControlTimer, 
                                fkSwWatchdogControlTimeStamp, fkSwWatchdogControlReqResult, fkSwWatchdogControlType, fkSwWatchdogControlInterval, fkSwWatchdogControlThreshold, 
                                fkSwWatchdogControlAction, fkSystemRunningOS, fkSystemSlotIndex, fkSystemSlotUptime, fkSystemSlotModelName, 
                                fkSystemSlotSerialNumber, fkSystemSlotHWVersion, fkSystemSlotBLVersion, fkSystemSlotSWCompatibility, fkSystemSlotOSVersion, 
                                fkSystemSlotMacAddress, fkSystemSlotCPULoadAll, fkSystemSlotCPULoadInterrupt, fkSystemSlotMemoryTotal, fkSystemSlotMemoryFree, 
                                fkSystemSlotMemoryShared, fkSystemSlotMemoryBuffers, fkSystemSlotMemoryCached, fkSystemSlotMemorySwapTotal, fkSystemSlotMemorySwapFree, 
                                fkSystemSlotBootReason, fkSystemSlotBootTime, fkSystemSlotVoltage, fkAutoUpgradeProfileName, fkAutoUpgradeProfileOldVer, 
                                fkAutoUpgradeProfileNewVer, fkAutoUpgradeProfileSize, fkAutoUpgradeProfileDate, fkAutoUpgradeProfilePeriodType, fkAutoUpgradeProfilePeriodDate, 
                                fkAutoUpgradeProfileTimeout, fkAutoUpgradeProfileRetry, fkAutoUpgradeProfileRegSec, fkAutoUpgradeProfileReloadTime, fkAutoUpgradeProfileControlRequest, 
                                fkAutoUpgradeProfileControlStatus, fkAutoUpgradeProfileControlTimer, fkAutoUpgradeProfileControlTimeStamp, fkAutoUpgradeProfileControlReqResult, fkAutoUpgradeProfileControlName, 
                                fkAutoUpgradeProfileControlOldVer, fkAutoUpgradeProfileControlNewVer, fkAutoUpgradeProfileControlSize, fkAutoUpgradeProfileControlDate, fkAutoUpgradeProfileControlPeriodType, 
                                fkAutoUpgradeProfileControlPeriodDate, fkAutoUpgradeProfileControlTimeout, fkAutoUpgradeProfileControlRetry, fkAutoUpgradeProfileControlRegSec, fkAutoUpgradeProfileControlReloadTime, 
                                fkAutoUpgradeOltSlotIndex, fkAutoUpgradeOltFwType, fkAutoUpgradeOltSlotType, fkAutoUpgradeOntOltIndex, fkAutoUpgradeOntIndex, 
                                fkAutoUpgradeOntFwType, fkAutoUpgradeMgmtControlRequest, fkAutoUpgradeMgmtControlStatus, fkAutoUpgradeMgmtControlTimer, fkAutoUpgradeMgmtControlTimeStamp, 
                                fkAutoUpgradeMgmtControlReqResult, fkAutoUpgradeMgmtControlOltIndex, fkAutoUpgradeMgmtControlOntIndex, fkAutoUpgradeMgmtControlFwType, fkAutoUpgradeLogControlRequest, 
                                fkAutoUpgradeLogControlStatus, fkAutoUpgradeLogControlTimer, fkAutoUpgradeLogControlTimeStamp, fkAutoUpgradeLogControlReqResult, fkAutoUpgradeLogControlSlotIndex, 
                                fkAutoUpgradeLogControlOntIndex, fkAutoUpgradeLogControlExportMethod, fkAutoUpgradeLogControlServer, fkAutoUpgradeLogControlUser, fkAutoUpgradeLogControlPasswd, 
                                fkAutoUpgradeMgmtControlSlotType, fkSystemNtpBindAddress, fkSystemEnablePasswdType, fkSystemEnablePasswd, fkSystemServicePasswdEncryption, 
                                fkSystemControlNtpBindAddress, fkSystemControlEnablePasswdType, fkSystemControlEnablePasswd, fkSystemControlServicePasswdEncryption, fkServiceAdminStatus, 
                                fkServiceControlAdminStatus, fkSystemUptime64, fkSystemNtpPollnterval, fkSystemControlNtpPollInterval, fkSystemCPUDuration, 
                                fkSystemLowCPUDuration, fkSystemControlCPUDuration, fkSystemControlLowCPUDuration, fkAutoResetCpuStatus, fkAutoResetCpuLoad, 
                                fkAutoResetCpuInterruptLoad, fkAutoResetCpuTime, fkAutoResetCpuControlLoad, fkAutoResetCpuControlInterruptLoad, fkAutoResetCpuControlTime, 
                                fkSystemUserDesc, fkAutoCliProfileName, fkAutoCliProfileType, fkAutoUpgradeOltProfileName, fkAutoUpgradeOntProfileName, 
                                fkSystemBarcode, fkAutoResetBootReason, fkAutoResetPingRebootRecoveryTime, fkAutoResetPingControlRebootRecoveryTime, fkSystemEnhancedFeature, 
                                fkSystemGetBranchModel, fkFtpclientIndex, fkFtpclientFileName, fkFtpclientFileSize, fkFtpclientControlRequest, 
                                fkFtpclientControlStatus, fkFtpclientControlTimer, fkFtpclientControlTimeStamp, fkFtpclientControlReqResult, fkFtpclientControlServerIp, 
                                fkFtpclientControlUserId, fkFtpclientControlPassword, fkFtpclientControlDirectoryPath, fkSystemTargetId, fkSystemNodeName, 
                                fkSystemNetworkName, fkSystemShelfId, fkSystemSlotId, fkAutoUpgradeMgmtControlProfileName, fkAutoResetCpuControlRequest, 
                                fkAutoResetCpuControlStatus, fkAutoResetCpuControlTimer, fkAutoResetCpuControlTimeStamp, fkAutoResetCpuControlReqResult }
                        STATUS current
                        DESCRIPTION 
                                "Description."
                        ::= { fkSystemMaintenance 101 }

                
                -- 1.3.6.1.4.1.10428 9 1.101.1.102
                fkSystemMaintenanceNotificationGroup NOTIFICATION-GROUP
                        NOTIFICATIONS { fkSystemSystemInfoProfileChanged, fkSystemCPUThresholdProfileChanged, fkSystemDefaultOSChanged, fkSystemRTCProfileChanged, fkSystemDNSDomainNameChanged, 
                                fkSystemBannerProfileChanged, fkSystemSyslogProfileChanged, fkSystemSSHStateChanged, fkSystemNTPStateChanged, fkSystemOSProfileChanged, 
                                fkSystemBackupChanged, fkSystemBackupIntervalChanged, fkSystemDhcpActivityChanged, fkSystemDefaultTTLChanged, fkSystemSyslogBindInterfaceNameChanged, 
                                fkSystemSyslogBindInterfaceNameCleared, fkSystemConfigPortMoved, fkSystemConfigPortCopied, fkSystemConfigPortCleared, fkSystemSessionTimeChanged, 
                                fkSystemExecTimeoutChanged, fkSystemWatchdogStatusChanged, fkSystemNosDestroyed, fkDNSServerCreated, fkDNSServerDestroyed, 
                                fkBackupCreated, fkBackupDestroyed, fkBackupChanged, fkNTPServerCreated, fkNTPServerDestroyed, 
                                fkSyslogConfCreated, fkSyslogConfDestroyed, fkSSHRemoteConnectiondestoryed, fkAutoCliStatusChanged, fkAutoCliMemoryMaxsizeChanged, 
                                fkAutoCliTransferIntervalChanged, fkAutoCliScriptFileFtpCreated, fkAutoCliScriptFileDestroyed, fkAutoCliScheduleCreated, fkAutoCliScheduleDestroyed, 
                                fkAutoCliOutputMemoryFileFtpCreated, fkAutoCliOutputMemoryFileDestroyed, fkAutoResetPingStatusChanged, fkAutoResetPingInfoModified, fkAutoResetMemoryleakStatusChanged, 
                                fkAutoResetMemoryleakInfoModified, fkAutoResetMemoryleakReboottimeModified, fkCoreDumpEntryCreated, fkCoreDumpEntryDestroyed, fkCoreDumpEntryChanged, 
                                fkServicePortChanged, fkAutoResetMemoryleakRebootCountClearSetted, fkAutoResetMemoryleakRebootCtrlModified, fkAutoResetPingRebootCountClearSetted, fkParameterValueChanged, 
                                fkParameterModeChanged, fkParameterDestroyed, fkParameterCreated, fkAutoResetPingRebootCtrlModified, fkSystemNtpBindInterfaceChanged, 
                                fkSystemFtpBindInterfaceChanged, fkSystemRedundancyPortChanged, fkRedundancyPortCleared, fkBackupConfigBySftpChanged, fkBackupConfigByScpChanged, 
                                fkBackupKeyBySftpChanged, fkBackupKeyByScpChanged, fkSystemUserCreated, fkSystemUserNameChanged, fkSystemUserPasswordChanged, 
                                fkAutoCliScriptFileTftpCreated, fkAutoCliProfileCreated, fkAutoCliProfileServerCreated, fkAutoCliProfileServerDestroyed, fkAutoCliProfileServerAllDestroyed, 
                                fkAutoCliOutputMemoryFileTftpCreated, fkSwWatchdogCreated, fkSwWatchdogDeleted, fkSystemTempThresholdChanged, fkSystemMemThresholdChanged, 
                                fkAutoUpgradeProfileCreated, fkAutoUpgradeProfileDeleted, fkAutoUpgradeProfileChanged, fkAutoUpgradeSetOltProfile, fkAutoUpgradeUnSetOltProfile, 
                                fkAutoUpgradeSetOntProfile, fkAutoUpgradeUnSetOntProfile, fkAutoUpgradeDeleteOltLog, fkAutoUpgradeDeleteAllOltLog, fkAutoUpgradeDeleteOntLog, 
                                fkAutoUpgradeDeleteAllOntLog, fkAutoUpgradeExportOltLog, fkAutoUpgradeExportOntLog, fkSystemBootloaderProfileChanged, fkSystemNtpBindAddressChanged, 
                                fkSystemEnablePasswdChanged, fkSystemEnableServicePasswdEncryptionChanged, fkServiceAdminStatusChanged, fkSystemUserLevelChanged, fkSystemPasswdRestored, 
                                fkSystemNtpPollIntervalChanged, fkAutoResetCpuChanged, fkAutoResetCpuDeleted, fkSystemUserDestroyed, fkFtpclientDirectoryInfoUpdated, 
                                fkAutoCliProfileDestroyed, fkSystemRestoreFactoryChanged }
                        STATUS current
                        DESCRIPTION 
                                "Description."
                        ::= { fkSystemMaintenance 102 }

                
        
        END

--
-- fk-systemmaintenance-mib.mib
--
