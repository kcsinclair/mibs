--
-- fk-Dhcp-snooping-mib.my
-- MIB generated by MG-SOFT Visual MIB Builder Version 3.0 Build 285
-- Monday, August 29, 2005 at 13:16:22
--

	FK-DHCP-SNOOPING-MIB DEFINITIONS ::= BEGIN
 
		IMPORTS
			fkMgmt			
				FROM FKOLTG1040-SMI			
			InterfaceIndex			
				FROM IF-MIB			
			FkControlStatusType, FkControlRequestResultType			
				FROM FK-TC-MIB			
			TimeTicks, IpAddress, Integer32, Gauge32, OBJECT-TYPE, 
			MODULE-IDENTITY, NOTIFICATION-TYPE			
				FROM SNMPv2-SMI			
			MacAddress			
				FROM SNMPv2-TC;
	
	
		-- 1.3.6.1.4.1.10428 9 1.101.12
		fkDhcpSnooping MODULE-IDENTITY 
			LAST-UPDATED "200507291407Z"		-- July 29, 2005 at 14:07 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 12 }

		
	
	
	
--
-- Node definitions
--
	
		-- 1.3.6.1.4.1.10428 9 1.101.12.1
		fkGlobal OBJECT IDENTIFIER::= { fkDhcpSnooping 1 }

		
		-- 1.3.6.1.4.1.10428 9 1.101.12.1.1
		fkGlobalInfo OBJECT IDENTIFIER::= { fkGlobal 1 }

		
		-- 1.3.6.1.4.1.10428 9 1.101.12.1.1.1
		fkFeatureEnable OBJECT-TYPE
			SYNTAX INTEGER
				{
				inactive(0),
				active(1)
				}
			MAX-ACCESS read-only
			STATUS current
			DESCRIPTION
				"This object indicates whether the DHCP Snooping feature is
				 enabled at the device level."
			::= { fkGlobalInfo 1 }

		
		-- 1.3.6.1.4.1.10428 9 1.101.12.1.2
		fkGlobalControl OBJECT IDENTIFIER::= { fkGlobal 2 }

		
		-- 1.3.6.1.4.1.10428 9 1.101.12.1.2.1
		fkGlobalControlRequest OBJECT-TYPE
			SYNTAX INTEGER { setSnoopingEnable(1) }
			MAX-ACCESS read-write
			STATUS current
			DESCRIPTION
				"The request of a user command."
			::= { fkGlobalControl 1 }

		
		-- 1.3.6.1.4.1.10428 9 1.101.12.1.2.2
		fkGlobalControlStatus OBJECT-TYPE
			SYNTAX FkControlStatusType
			MAX-ACCESS read-only
			STATUS current
			DESCRIPTION
				"The status of a user command."
			::= { fkGlobalControl 2 }

		
		-- 1.3.6.1.4.1.10428 9 1.101.12.1.2.3
		fkGlobalControlTimer OBJECT-TYPE
			SYNTAX Gauge32
			MAX-ACCESS read-write
			STATUS current
			DESCRIPTION
				"The maximum wait time for the manager for a long running user command."
			::= { fkGlobalControl 3 }

		
		-- 1.3.6.1.4.1.10428 9 1.101.12.1.2.4
		fkGlobalControlTimeStamp OBJECT-TYPE
			SYNTAX TimeTicks
			MAX-ACCESS read-only
			STATUS current
			DESCRIPTION
				"The time stamp of the last command (end of command)."
			::= { fkGlobalControl 4 }

		
		-- 1.3.6.1.4.1.10428 9 1.101.12.1.2.5
		fkGlobalControlReqResult OBJECT-TYPE
			SYNTAX FkControlRequestResultType
			MAX-ACCESS read-only
			STATUS current
			DESCRIPTION
				"The result of the last user command."
			::= { fkGlobalControl 5 }

		
		-- 1.3.6.1.4.1.10428 9 1.101.12.1.2.6
		fkGlobalControlFeatureEnable OBJECT-TYPE
			SYNTAX INTEGER
				{
				inactive(0),
				active(1)
				}
			MAX-ACCESS read-write
			STATUS current
			DESCRIPTION
				"Description."
			::= { fkGlobalControl 6 }

		
		-- 1.3.6.1.4.1.10428 9 1.101.12.1.3
		fkGlobalNotification OBJECT IDENTIFIER::= { fkGlobal 3 }

		
		-- 1.3.6.1.4.1.10428 9 1.101.12.1.3.1
		fkGlobalFeatureEnableChanged NOTIFICATION-TYPE
			OBJECTS { fkGlobalControlRequest, fkGlobalControlTimeStamp, fkGlobalControlReqResult, fkFeatureEnable }
			STATUS current
			DESCRIPTION 
				"Description."
			::= { fkGlobalNotification 1 }

		
		-- 1.3.6.1.4.1.10428 9 1.101.12.2
		fkPortSrcGuard OBJECT IDENTIFIER::= { fkDhcpSnooping 2 }

		
		-- 1.3.6.1.4.1.10428 9 1.101.12.2.1
		fkPortSrcGuardConfig OBJECT IDENTIFIER::= { fkPortSrcGuard 1 }

		
		-- 1.3.6.1.4.1.10428 9 1.101.12.2.1.1
		fkPortSrcGuardConfigTable OBJECT-TYPE
			SYNTAX SEQUENCE OF FkPortSrcGuardConfigEntry
			MAX-ACCESS not-accessible
			STATUS current
			DESCRIPTION
				"A table provides the mechanism to enable or disable  
				 IP Source Guard at each physical port capable of
				 this feature. 
				
				 When DHCP Snooping is enabled at an interface, a list of
				 IP addresses is obtained through DHCP Snooping for this
				 particular port. If IP Source Guard is enabled, only
				 traffic from these IP addresses is allowed to pass through
				 the port."
			::= { fkPortSrcGuardConfig 1 }

		
		-- 1.3.6.1.4.1.10428 9 1.101.12.2.1.1.1
		fkPortSrcGuardConfigEntry OBJECT-TYPE
			SYNTAX FkPortSrcGuardConfigEntry
			MAX-ACCESS not-accessible
			STATUS current
			DESCRIPTION
				"A row instance contains the configuration to enable
				 or disable IP Source Guard at each physical port
				 capable of this feature."
			INDEX { fkPortSrcGuardIndex }
			::= { fkPortSrcGuardConfigTable 1 }

		
		FkPortSrcGuardConfigEntry ::=
			SEQUENCE { 
				fkPortSrcGuardIndex
					INTEGER,
				fkPortSrcGuardEnable
					INTEGER
			 }

		-- 1.3.6.1.4.1.10428 9 1.101.12.2.1.1.1.1
		fkPortSrcGuardIndex OBJECT-TYPE
			SYNTAX INTEGER
			MAX-ACCESS read-only
			STATUS current
			DESCRIPTION
				"Same as fkBridgePortIndex."
			::= { fkPortSrcGuardConfigEntry 1 }

		
		-- 1.3.6.1.4.1.10428 9 1.101.12.2.1.1.1.2
		fkPortSrcGuardEnable OBJECT-TYPE
			SYNTAX INTEGER
				{
				disable(0),
				enable(1)
				}
			MAX-ACCESS read-only
			STATUS current
			DESCRIPTION
				"This object indicates whether IP Source Guard is enabled
				 at this port. 
				
				 If this object is set to 'true', IP Source Guard is
				 enabled. Traffic coming to this interface will be forwarded
				 if it is from the list of IP addresses obtained through
				 DHCP Snooping. Otherwise, it is denied.
				
				 If this object is set to 'false', IP Source Guard is
				 disabled."
			::= { fkPortSrcGuardConfigEntry 2 }

		
		-- 1.3.6.1.4.1.10428 9 1.101.12.2.1.2
		fkPortSrcGuardConfigControl OBJECT IDENTIFIER::= { fkPortSrcGuardConfig 2 }

		
		-- 1.3.6.1.4.1.10428 9 1.101.12.2.1.2.1
		fkPortSrcGuardConfigControlRequest OBJECT-TYPE
			SYNTAX INTEGER { setPortSrcGuardConfig(1) }
			MAX-ACCESS read-write
			STATUS current
			DESCRIPTION
				"The request of a user command."
			::= { fkPortSrcGuardConfigControl 1 }

		
		-- 1.3.6.1.4.1.10428 9 1.101.12.2.1.2.2
		fkPortSrcGuardConfigControlStatus OBJECT-TYPE
			SYNTAX FkControlStatusType
			MAX-ACCESS read-only
			STATUS current
			DESCRIPTION
				"The status of a user command."
			::= { fkPortSrcGuardConfigControl 2 }

		
		-- 1.3.6.1.4.1.10428 9 1.101.12.2.1.2.3
		fkPortSrcGuardConfigControlTimer OBJECT-TYPE
			SYNTAX Gauge32
			MAX-ACCESS read-write
			STATUS current
			DESCRIPTION
				"The maximum wait time for the manager for a long running user command."
			::= { fkPortSrcGuardConfigControl 3 }

		
		-- 1.3.6.1.4.1.10428 9 1.101.12.2.1.2.4
		fkPortSrcGuardConfigControlTimeStamp OBJECT-TYPE
			SYNTAX TimeTicks
			MAX-ACCESS read-only
			STATUS current
			DESCRIPTION
				"The time stamp of the last command (end of command)."
			::= { fkPortSrcGuardConfigControl 4 }

		
		-- 1.3.6.1.4.1.10428 9 1.101.12.2.1.2.5
		fkPortSrcGuardConfigControlReqResult OBJECT-TYPE
			SYNTAX FkControlRequestResultType
			MAX-ACCESS read-only
			STATUS current
			DESCRIPTION
				"The result of the last user command."
			::= { fkPortSrcGuardConfigControl 5 }

		
		-- 1.3.6.1.4.1.10428 9 1.101.12.2.1.2.6
		fkPortSrcGuardConfigControlIndex OBJECT-TYPE
			SYNTAX INTEGER
			MAX-ACCESS read-write
			STATUS current
			DESCRIPTION
				"The port number that IP Source Guard is enabled at."
			::= { fkPortSrcGuardConfigControl 6 }

		
		-- 1.3.6.1.4.1.10428 9 1.101.12.2.1.2.7
		fkPortSrcGuardConfigControlEnable OBJECT-TYPE
			SYNTAX INTEGER
				{
				disable(0),
				enable(1)
				}
			MAX-ACCESS read-write
			STATUS current
			DESCRIPTION
				"The flag to specify whether IP Source Guard is enabled or not."
			::= { fkPortSrcGuardConfigControl 7 }

		
		-- 1.3.6.1.4.1.10428 9 1.101.12.2.1.3
		fkPortSrcGuardConfigNotification OBJECT IDENTIFIER::= { fkPortSrcGuardConfig 3 }

		
		-- 1.3.6.1.4.1.10428 9 1.101.12.2.1.3.1
		fkPortSrcGuardConfigEnableChanged NOTIFICATION-TYPE
			OBJECTS { fkPortSrcGuardConfigControlRequest, fkPortSrcGuardConfigControlTImeStamp, fkPortSrcGuardConfigControlReqResult, fkPortSrcGuardEnable }
			STATUS current
			DESCRIPTION 
				"Description."
			::= { fkPortSrcGuardConfigNotification 1 }

		
		-- 1.3.6.1.4.1.10428 9 1.101.12.2.2
		fkPortSrcGuardAddress OBJECT IDENTIFIER::= { fkPortSrcGuard 2 }

		
		-- 1.3.6.1.4.1.10428 9 1.101.12.2.2.1
		fkPortSrcGuardAddressTable OBJECT-TYPE
			SYNTAX SEQUENCE OF FkPortSrcGuardAddressEntry
			MAX-ACCESS not-accessible
			STATUS current
			DESCRIPTION
				"A table provides the information on IP addresses used
				 for IP Source Guard purpose at each physical port
				 capable of this feature."
			::= { fkPortSrcGuardAddress 1 }

		
		-- 1.3.6.1.4.1.10428 9 1.101.12.2.2.1.1
		fkPortSrcGuardAddressEntry OBJECT-TYPE
			SYNTAX FkPortSrcGuardAddressEntry
			MAX-ACCESS not-accessible
			STATUS current
			DESCRIPTION
				"A row instance contains the IP address type and IP
				 address used for IP Source Guard purpose at each
				 physical port capable of this feature."
			INDEX { fkPortSrcGuardIndex, fkPortSrcGuardAddressIp }
			::= { fkPortSrcGuardAddressTable 1 }

		
		FkPortSrcGuardAddressEntry ::=
			SEQUENCE { 
				fkPortSrcGuardAddressIp
					IpAddress,
				fkPortSrcGuardAddressMask
					IpAddress,
				fkPortSrcGuardAddressMac
					MacAddress,
				fkPortSrcGuardAddressLease
					Integer32
			 }

		-- 1.3.6.1.4.1.10428 9 1.101.12.2.2.1.1.1
		fkPortSrcGuardAddressIp OBJECT-TYPE
			SYNTAX IpAddress
			MAX-ACCESS read-only
			STATUS current
			DESCRIPTION
				"This object indicates the IP address obtained at
				 this port through DHCP Snooping."
			::= { fkPortSrcGuardAddressEntry 1 }

		
		-- 1.3.6.1.4.1.10428 9 1.101.12.2.2.1.1.2
		fkPortSrcGuardAddressMask OBJECT-TYPE
			SYNTAX IpAddress
			MAX-ACCESS read-only
			STATUS current
			DESCRIPTION
				"This object indicates the subnet mask of IP address 
				 obtained at this port through DHCP Snooping."
			::= { fkPortSrcGuardAddressEntry 2 }

		
		-- 1.3.6.1.4.1.10428 9 1.101.12.2.2.1.1.3
		fkPortSrcGuardAddressMac OBJECT-TYPE
			SYNTAX MacAddress
			MAX-ACCESS read-only
			STATUS current
			DESCRIPTION
				"This object indicates the MAC responding to IP address 
				 obtained at this port through DHCP Snooping."
			::= { fkPortSrcGuardAddressEntry 3 }

		
		-- 1.3.6.1.4.1.10428 9 1.101.12.2.2.1.1.4
		fkPortSrcGuardAddressLease OBJECT-TYPE
			SYNTAX Integer32
			MAX-ACCESS read-only
			STATUS current
			DESCRIPTION
				"This object indicates the lease time of IP address 
				 obtained at this port through DHCP Snooping."
			::= { fkPortSrcGuardAddressEntry 4 }

		
		-- 1.3.6.1.4.1.10428 9 1.101.12.2.2.2
		fkPortSrcGuardAddressControl OBJECT IDENTIFIER::= { fkPortSrcGuardAddress 2 }

		
		-- 1.3.6.1.4.1.10428 9 1.101.12.2.2.2.1
		fkPortSrcGuardAddressControlRequest OBJECT-TYPE
			SYNTAX INTEGER
				{
				createPortSrcGuardAddress(1),
				destroyPortSrcGuardAddress(2)
				}
			MAX-ACCESS read-write
			STATUS current
			DESCRIPTION
				"The request of a user command."
			::= { fkPortSrcGuardAddressControl 1 }

		
		-- 1.3.6.1.4.1.10428 9 1.101.12.2.2.2.2
		fkPortSrcGuardAddressControlStatus OBJECT-TYPE
			SYNTAX FkControlStatusType
			MAX-ACCESS read-only
			STATUS current
			DESCRIPTION
				"The status of a user command."
			::= { fkPortSrcGuardAddressControl 2 }

		
		-- 1.3.6.1.4.1.10428 9 1.101.12.2.2.2.3
		fkPortSrcGuardAddressControlTimer OBJECT-TYPE
			SYNTAX Gauge32
			MAX-ACCESS read-write
			STATUS current
			DESCRIPTION
				"The maximum wait time for the manager for a long running user command."
			::= { fkPortSrcGuardAddressControl 3 }

		
		-- 1.3.6.1.4.1.10428 9 1.101.12.2.2.2.4
		fkPortSrcGuardAddressControlTimeStamp OBJECT-TYPE
			SYNTAX TimeTicks
			MAX-ACCESS read-only
			STATUS current
			DESCRIPTION
				"The time stamp of the last command (end of command)."
			::= { fkPortSrcGuardAddressControl 4 }

		
		-- 1.3.6.1.4.1.10428 9 1.101.12.2.2.2.5
		fkPortSrcGuardAddressControlReqResult OBJECT-TYPE
			SYNTAX FkControlRequestResultType
			MAX-ACCESS read-only
			STATUS current
			DESCRIPTION
				"The result of the last user command."
			::= { fkPortSrcGuardAddressControl 5 }

		
		-- 1.3.6.1.4.1.10428 9 1.101.12.2.2.2.6
		fkPortSrcGuardAddressControlIndex OBJECT-TYPE
			SYNTAX InterfaceIndex
			MAX-ACCESS read-write
			STATUS current
			DESCRIPTION
				"Description."
			::= { fkPortSrcGuardAddressControl 6 }

		
		-- 1.3.6.1.4.1.10428 9 1.101.12.2.2.2.7
		fkPortSrcGuardAddressControlIp OBJECT-TYPE
			SYNTAX IpAddress
			MAX-ACCESS read-write
			STATUS current
			DESCRIPTION
				"Description."
			::= { fkPortSrcGuardAddressControl 7 }

		
		-- 1.3.6.1.4.1.10428 9 1.101.12.2.2.2.8
		fkPortSrcGuardAddressControlMask OBJECT-TYPE
			SYNTAX IpAddress
			MAX-ACCESS read-write
			STATUS current
			DESCRIPTION
				"Description."
			::= { fkPortSrcGuardAddressControl 8 }

		
		-- 1.3.6.1.4.1.10428 9 1.101.12.2.2.3
		fkPortSrcGuardAddressNotification OBJECT IDENTIFIER::= { fkPortSrcGuardAddress 3 }

		
		-- 1.3.6.1.4.1.10428 9 1.101.12.2.2.3.1
		fkPortSrcGuardAddressCreated NOTIFICATION-TYPE
			OBJECTS { fkPortSrcGuardAddressControlRequest, fkPortSrcGuardAddressControlTImeStamp, fkPortSrcGuardAddressControlReqResult, fkPortSrcGuardAddressIp, fkPortSrcGuardAddressMask
				 }
			STATUS current
			DESCRIPTION 
				"Description."
			::= { fkPortSrcGuardAddressNotification 1 }

		
		-- 1.3.6.1.4.1.10428 9 1.101.12.2.2.3.2
		fkPortSrcGuardAddressDestroyed NOTIFICATION-TYPE
			OBJECTS { fkPortSrcGuardAddressControlRequest, fkPortSrcGuardAddressControlTImeStamp, fkPortSrcGuardAddressControlReqResult, fkPortSrcGuardAddressIp, fkPortSrcGuardAddressMask
				 }
			STATUS current
			DESCRIPTION 
				"Description."
			::= { fkPortSrcGuardAddressNotification 2 }

		
	
	END

--
-- fk-Dhcp-snooping-mib.my
--
