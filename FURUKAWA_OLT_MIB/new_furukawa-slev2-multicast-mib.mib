--
-- fkv2-multicast-mib.mib
-- MIB generated by MG-SOFT Visual MIB Builder Version 6.0  Build 88
-- Friday, April 05, 2013 at 15:33:56
--

--  FKV2-MULTICAST-MIB.my
-- MIB generated by MG-SOFT Visual MIB Builder Version 6.0  Build 88
-- Friday, October 05, 2007 at 10:51:05
-- 

	FKV2-MULTICAST-MIB DEFINITIONS ::= BEGIN
 
		IMPORTS
			fkV2Mgmt			
				FROM FKOLTG1040-SMI			
			IANAipMRouteProtocol, IANAipRouteProtocol			
				FROM IANA-RTPROTO-MIB			
			FkControlStatusType, FkControlRequestResultType			
				FROM FK-TC-MIB			
			OBJECT-GROUP, NOTIFICATION-GROUP			
				FROM SNMPv2-CONF			
			TimeTicks, IpAddress, Integer32, Unsigned32, Gauge32, 
			Counter32, Counter64, BITS, OBJECT-TYPE, MODULE-IDENTITY, 
			NOTIFICATION-TYPE			
				FROM SNMPv2-SMI			
			TimeStamp			
				FROM SNMPv2-TC;
	
	
--  1.3.6.1.4.1.10428 9 1.102.12
-- November 09, 2005 at 09:03 GMT
		-- 1.3.6.1.4.1.10428 9 1.102.12
		fkV2Multicast MODULE-IDENTITY 
			LAST-UPDATED "200511090903Z"		-- November 09, 2005 at 09:03 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkV2Mgmt 12 }

		
	
--
-- Type definitions
--
	
--  Type definitions
-- 
-- 1.3.6.1.4.1.10428 9 1.102.12
-- December 08, 2004 at 09:03 GMT
-- 
-- Type definitions
-- 
		Boolean ::= INTEGER
			{
			disable(0),
			enable(1)
			}

	
	
--
-- Node definitions
--
	
--  Node definitions
-- 
-- Multicast Common Configuration
-- 1.3.6.1.4.1.10428 9 1.102.12.1
		-- 1.3.6.1.4.1.10428 9 1.102.12.1
		fkV2McastBase OBJECT IDENTIFIER ::= { fkV2Multicast 1 }

		
--  Multicast for IPv4
-- 1.3.6.1.4.1.10428 9 1.102.12.2
		-- 1.3.6.1.4.1.10428 9 1.102.12.2
		fkV2Multicast4 OBJECT IDENTIFIER ::= { fkV2Multicast 2 }

		
--  Multicast Routing
-- 1.3.6.1.4.1.10428 9 1.102.12.2.1
		-- 1.3.6.1.4.1.10428 9 1.102.12.2.1
		fkV2Mrib4 OBJECT IDENTIFIER ::= { fkV2Multicast4 1 }

		
--  Multicast Routing Configuration
-- 1.3.6.1.4.1.10428 9 1.102.12.2.1.1
		-- 1.3.6.1.4.1.10428 9 1.102.12.2.1.1
		fkV2M4RouteBase OBJECT IDENTIFIER ::= { fkV2Mrib4 1 }

		
--  Multicast Routing Configuration Group
-- 1.3.6.1.4.1.10428 9 1.102.12.2.1.1.1
		-- 1.3.6.1.4.1.10428 9 1.102.12.2.1.1.1
		fkV2M4RouteInfo OBJECT IDENTIFIER ::= { fkV2M4RouteBase 1 }

		
--  1.3.6.1.4.1.10428 9 1.102.12.2.1.1.1.1
		-- 1.3.6.1.4.1.10428 9 1.102.12.2.1.1.1.1
		fkV2M4RouteInfoActivity OBJECT-TYPE
			SYNTAX Boolean
			MAX-ACCESS read-only
			STATUS current
			DESCRIPTION
				"Enable/disable status of multicast routing on this router."
			::= { fkV2M4RouteInfo 1 }

		
--  1.3.6.1.4.1.10428 9 1.102.12.2.1.1.1.2
		-- 1.3.6.1.4.1.10428 9 1.102.12.2.1.1.1.2
		fkV2M4RouteInfoLimit OBJECT-TYPE
			SYNTAX INTEGER (1..2147483647)
			MAX-ACCESS read-only
			STATUS current
			DESCRIPTION
				"Limiting number of multicast routes that can be added to 
				a multicast routing table."
			::= { fkV2M4RouteInfo 2 }

		
--  1.3.6.1.4.1.10428 9 1.102.12.2.1.1.1.3
		-- 1.3.6.1.4.1.10428 9 1.102.12.2.1.1.1.3
		fkV2M4RouteInfoThreshold OBJECT-TYPE
			SYNTAX INTEGER (1..2147483647)
			MAX-ACCESS read-only
			STATUS current
			DESCRIPTION
				"Threshold number at which to generate a warning message."
			::= { fkV2M4RouteInfo 3 }

		
--  1.3.6.1.4.1.10428 9 1.102.12.2.1.1.1.4
		-- 1.3.6.1.4.1.10428 9 1.102.12.2.1.1.1.4
		fkV2M4RouteInfoUnknownFlood OBJECT-TYPE
			SYNTAX Boolean
			MAX-ACCESS read-only
			STATUS current
			DESCRIPTION
				"Flooding status of unknown multicast packets on this router."
			::= { fkV2M4RouteInfo 4 }

		
--  1.3.6.1.4.1.10428 9 1.102.12.2.1.1.1.5
		-- 1.3.6.1.4.1.10428 9 1.102.12.2.1.1.1.5
		fkV2M4RouteInfoEntryCount OBJECT-TYPE
			SYNTAX Gauge32
			MAX-ACCESS read-only
			STATUS current
			DESCRIPTION
				"The number of rows in the fkV2MRoute4Table. 
				This can be used to monitor the multicast routing table size"
			::= { fkV2M4RouteInfo 5 }

		
--  1.3.6.1.4.1.10428 9 1.102.12.2.1.1.1.6
		-- 1.3.6.1.4.1.10428 9 1.102.12.2.1.1.1.6
		fkV2M4RouteInfoNocacheRecvMsg OBJECT-TYPE
			SYNTAX Counter64
			MAX-ACCESS read-only
			STATUS current
			DESCRIPTION
				"The number of all NOCACHE event messages which this MRIB has received 
				from the Multicast Forwarder for all entries.
				The Multicast Forwarder generates the NOCACHE event when it receives 
				a data packet destined to (S,G), and does not have an (S,G) MRT entry."
			::= { fkV2M4RouteInfo 6 }

		
--  1.3.6.1.4.1.10428 9 1.102.12.2.1.1.1.7
		-- 1.3.6.1.4.1.10428 9 1.102.12.2.1.1.1.7
		fkV2M4RouteInfoWholepktRecvMsg OBJECT-TYPE
			SYNTAX Counter64
			MAX-ACCESS read-only
			STATUS current
			DESCRIPTION
				"The number of all WHOLEPKT event messages which this MRIB has received 
				from the Multicast Forwarder for all entries.
				The Multicast Forwarder generates the WHOLEPKT event whenever 
				the special REGISTER VIF appears in the out interface list of an (S,G) MRT 
				in the multicast forwarder."
			::= { fkV2M4RouteInfo 7 }

		
--  1.3.6.1.4.1.10428 9 1.102.12.2.1.1.1.8
		-- 1.3.6.1.4.1.10428 9 1.102.12.2.1.1.1.8
		fkV2M4RouteInfoWrongvifRecvMsg OBJECT-TYPE
			SYNTAX Counter64
			MAX-ACCESS read-only
			STATUS current
			DESCRIPTION
				"The number of all WRONGVIF event messages which this MRIB has received 
				from the Multicast Forwarder for all entries.
				The Multicast Forwarder generates a WRONGVIF event when it 
				receives a packet destined to (S,G) on an interface that 
				does not match the IIF of the (S,G) MRT in the Multicast Forwarder."
			::= { fkV2M4RouteInfo 8 }

		
--  1.3.6.1.4.1.10428 9 1.102.12.2.1.1.1.9
		-- 1.3.6.1.4.1.10428 9 1.102.12.2.1.1.1.9
		fkV2M4RouteInfoNocacheSentMsg OBJECT-TYPE
			SYNTAX Counter64
			MAX-ACCESS read-only
			STATUS current
			DESCRIPTION
				"The number of all NSM_MSG_IPV4_MRT_NOCACHE(NSM_MSG_IPV6_MRT_NOCACHE) 
				messages which MRIB sent to multicast protocol for all entries.
				When the MRIB receives NOCACHE event message from Multicast Forwarder, 
				it relays it to all multicast protocols, ensuring that the correct 
				multicast protocol adds an (S,G) MRT to the MRIB."
			::= { fkV2M4RouteInfo 9 }

		
--  1.3.6.1.4.1.10428 9 1.102.12.2.1.1.1.10
		-- 1.3.6.1.4.1.10428 9 1.102.12.2.1.1.1.10
		fkV2M4RouteInfoWholepktSentMsg OBJECT-TYPE
			SYNTAX Counter64
			MAX-ACCESS read-only
			STATUS current
			DESCRIPTION
				"The number of all NSM_MSG_IPV4_MRT_WHOLEPKT_REQUEST(NSM_MSG_IPV6_MRT_WHOLEPKT_REQUEST) 
				messages which MRIB sent to multicast protocol for all entries.
				When the MRIB receives WHOLEPKT event message from Multicast Forwarder, 
				it sends an message to the multicast protocol.
				
				It is inefficient and expensive to relay this whole message to the multicast 
				protocol, because IP packet can be as large as 64 KB.
				To avoid sending the WHOLEPKT message to the multicast protocol, 
				NSM_MSG_IPV4_MRT_WHOLEPKT_REQUEST message contains the (S,G) key, 
				the REGISTER VIF index, and a unique identifier for the instance of 
				the WHOLEPKT message from the Multicast Forwarder, whitout the all packet data."
			::= { fkV2M4RouteInfo 10 }

		
--  1.3.6.1.4.1.10428 9 1.102.12.2.1.1.1.11
		-- 1.3.6.1.4.1.10428 9 1.102.12.2.1.1.1.11
		fkV2M4RouteInfoWrongvifSentMsg OBJECT-TYPE
			SYNTAX Counter64
			MAX-ACCESS read-only
			STATUS current
			DESCRIPTION
				"The number of all NSM_MSG_IPV4_MRT_WRONGVIF(NSM_MSG_IPV6_MRT_WRONGVIF) messages 
				which MRIB sent to multicast protocol for all entries.
				When the MRIB receives WRONGVIF event message from Multicast Forwarder, 
				it relays it to all multicast protocols that have requested PIM service."
			::= { fkV2M4RouteInfo 11 }

		
		-- 1.3.6.1.4.1.10428 9 1.102.12.2.1.1.1.12
		fkV2M4RoutInfoIpMrouteJoinedCount OBJECT-TYPE
			SYNTAX Counter32
			MAX-ACCESS read-only
			STATUS current
			DESCRIPTION
				"The count of Mroute Joined channel"
			::= { fkV2M4RouteInfo 12 }

		
--  Multicast Routing Configuration Control
-- 1.3.6.1.4.1.10428 9 1.102.12.2.1.1.2
		-- 1.3.6.1.4.1.10428 9 1.102.12.2.1.1.2
		fkV2M4RouteInfoControl OBJECT IDENTIFIER ::= { fkV2M4RouteBase 2 }

		
--  1.3.6.1.4.1.10428 9 1.102.12.2.1.1.2.1
		-- 1.3.6.1.4.1.10428 9 1.102.12.2.1.1.2.1
		fkV2M4RouteInfoControlRequest OBJECT-TYPE
			SYNTAX INTEGER
				{
				setMRouteInfoActivity(1),
				setMRouteInfoLimitProfile(2),
				setMRouteInfoUnknownFlood(3)
				}
			MAX-ACCESS read-write
			STATUS current
			DESCRIPTION
				" The request of a user command"
			::= { fkV2M4RouteInfoControl 1 }

		
--  1.3.6.1.4.1.10428 9 1.102.12.2.1.1.2.2
		-- 1.3.6.1.4.1.10428 9 1.102.12.2.1.1.2.2
		fkV2M4RouteInfoControlStatus OBJECT-TYPE
			SYNTAX FkControlStatusType
			MAX-ACCESS read-only
			STATUS current
			DESCRIPTION
				"The status of user command"
			::= { fkV2M4RouteInfoControl 2 }

		
--  1.3.6.1.4.1.10428 9 1.102.12.2.1.1.2.3
		-- 1.3.6.1.4.1.10428 9 1.102.12.2.1.1.2.3
		fkV2M4RouteInfoControlTimer OBJECT-TYPE
			SYNTAX Gauge32
			MAX-ACCESS read-write
			STATUS current
			DESCRIPTION
				" The maximum time for the manager for a long running user command"
			::= { fkV2M4RouteInfoControl 3 }

		
--  1.3.6.1.4.1.10428 9 1.102.12.2.1.1.2.4
		-- 1.3.6.1.4.1.10428 9 1.102.12.2.1.1.2.4
		fkV2M4RouteInfoControlTimeStamp OBJECT-TYPE
			SYNTAX TimeStamp
			MAX-ACCESS read-only
			STATUS current
			DESCRIPTION
				" The time stamp of the last command(end of command)"
			::= { fkV2M4RouteInfoControl 4 }

		
--  1.3.6.1.4.1.10428 9 1.102.12.2.1.1.2.5
		-- 1.3.6.1.4.1.10428 9 1.102.12.2.1.1.2.5
		fkV2M4RouteInfoControlReqResult OBJECT-TYPE
			SYNTAX FkControlRequestResultType
			MAX-ACCESS read-only
			STATUS current
			DESCRIPTION
				" The result of the last user command"
			::= { fkV2M4RouteInfoControl 5 }

		
--  1.3.6.1.4.1.10428 9 1.102.12.2.1.1.2.6
		-- 1.3.6.1.4.1.10428 9 1.102.12.2.1.1.2.6
		fkV2M4RouteInfoControlActivity OBJECT-TYPE
			SYNTAX Boolean
			MAX-ACCESS read-write
			STATUS current
			DESCRIPTION
				"CLI:(no) ip multicast-routing"
			::= { fkV2M4RouteInfoControl 6 }

		
--  1.3.6.1.4.1.10428 9 1.102.12.2.1.1.2.7
		-- 1.3.6.1.4.1.10428 9 1.102.12.2.1.1.2.7
		fkV2M4RouteInfoControlLimit OBJECT-TYPE
			SYNTAX INTEGER (-1 | 1..2147483647)
			MAX-ACCESS read-write
			STATUS current
			DESCRIPTION
				"CLI:(no) ip multicast route-limit LIMIT (THRESHOLD)
				value(-1) : (no)"
			::= { fkV2M4RouteInfoControl 7 }

		
--  1.3.6.1.4.1.10428 9 1.102.12.2.1.1.2.8
		-- 1.3.6.1.4.1.10428 9 1.102.12.2.1.1.2.8
		fkV2M4RouteInfoControlThreshold OBJECT-TYPE
			SYNTAX INTEGER (-1 | 1..2147483647)
			MAX-ACCESS read-write
			STATUS current
			DESCRIPTION
				"CLI:(no) ip multicast route-limit LIMIT (THRESHOLD)
				value(-1) : (no)"
			::= { fkV2M4RouteInfoControl 8 }

		
--  1.3.6.1.4.1.10428 9 1.102.12.2.1.1.2.9
		-- 1.3.6.1.4.1.10428 9 1.102.12.2.1.1.2.9
		fkV2M4RouteInfoControlUnknownFlood OBJECT-TYPE
			SYNTAX Boolean
			MAX-ACCESS read-write
			STATUS current
			DESCRIPTION
				"CLI: (no) ip multicast unknown-flood"
			::= { fkV2M4RouteInfoControl 9 }

		
--  Multicast Routing Configuration Notification
-- 1.3.6.1.4.1.10428 9 1.102.12.2.1.1.3
		-- 1.3.6.1.4.1.10428 9 1.102.12.2.1.1.3
		fkV2M4RouteInfoNotification OBJECT IDENTIFIER ::= { fkV2M4RouteBase 3 }

		
--  1.3.6.1.4.1.10428 9 1.102.12.2.1.1.3.1
		-- 1.3.6.1.4.1.10428 9 1.102.12.2.1.1.3.1
		fkV2M4RouteInfoActivityChanged NOTIFICATION-TYPE
			OBJECTS { fkV2M4RouteInfoControlRequest, fkV2M4RouteInfoControlReqResult, fkV2M4RouteInfoControlTimeStamp, fkV2M4RouteInfoActivity }
			STATUS current
			DESCRIPTION 
				" "
			::= { fkV2M4RouteInfoNotification 1 }

		
--  1.3.6.1.4.1.10428 9 1.102.12.2.1.1.3.2
		-- 1.3.6.1.4.1.10428 9 1.102.12.2.1.1.3.2
		fkV2M4RouteInfoLimitChanged NOTIFICATION-TYPE
			OBJECTS { fkV2M4RouteInfoControlRequest, fkV2M4RouteInfoControlReqResult, fkV2M4RouteInfoControlTimeStamp, fkV2M4RouteInfoLimit, fkV2M4RouteInfoThreshold
				 }
			STATUS current
			DESCRIPTION 
				"Description."
			::= { fkV2M4RouteInfoNotification 2 }

		
--  1.3.6.1.4.1.10428 9 1.102.12.2.1.1.3.3
		-- 1.3.6.1.4.1.10428 9 1.102.12.2.1.1.3.3
		fkV2M4RouteInfoUnkwonFloodChanged NOTIFICATION-TYPE
			OBJECTS { fkV2M4RouteInfoControlRequest, fkV2M4RouteInfoControlReqResult, fkV2M4RouteInfoControlTimeStamp, fkV2M4RouteInfoUnknownFlood }
			STATUS current
			DESCRIPTION 
				"Description."
			::= { fkV2M4RouteInfoNotification 3 }

		
--  Multicast Routing Information Base
-- 1.3.6.1.4.1.10428 9 1.102.12.2.1.2
		-- 1.3.6.1.4.1.10428 9 1.102.12.2.1.2
		fkV2M4Route OBJECT IDENTIFIER ::= { fkV2Mrib4 2 }

		
--  Multicast Routing Information Base Table
-- 1.3.6.1.4.1.10428 9 1.102.12.2.1.2.1
		-- 1.3.6.1.4.1.10428 9 1.102.12.2.1.2.1
		fkV2M4RouteTable OBJECT-TYPE
			SYNTAX SEQUENCE OF FkV2M4RouteEntry
			MAX-ACCESS not-accessible
			STATUS current
			DESCRIPTION
				"The (conceptual) table containing multicast routing
				information for IP datagrams sent by particular sources to
				the IP multicast groups known to this router.
				"
			::= { fkV2M4Route 1 }

		
--  Multicast Routing Information Base Entry
-- 1.3.6.1.4.1.10428 9 1.102.12.2.2.2.1.1
		-- 1.3.6.1.4.1.10428 9 1.102.12.2.1.2.1.1
		fkV2M4RouteEntry OBJECT-TYPE
			SYNTAX FkV2M4RouteEntry
			MAX-ACCESS not-accessible
			STATUS current
			DESCRIPTION
				"An entry (conceptual row) containing the multicast routing
				information for IP datagrams from a particular source and
				addressed to a particular IP multicast group address.
				Discontinuities in counters in this entry can be detected by
				observing the value of fkV2M4RouteUpTime.
				key: fkV2M4RouteGroup, fkV2M4RouteSource, fkV2M4RouteSrcMask"
			INDEX { fkV2M4RouteGroup, fkV2M4RouteSource, fkV2M4RouteSrcMask }
			::= { fkV2M4RouteTable 1 }

		
		FkV2M4RouteEntry ::=
			SEQUENCE { 
				fkV2M4RouteGroup
					IpAddress,
				fkV2M4RouteSource
					IpAddress,
				fkV2M4RouteSrcMask
					IpAddress,
				fkV2M4RouteInInterface
					Integer32,
				fkV2M4RouteUpstreamNeighbor
					IpAddress,
				fkV2M4RouteUpTime
					TimeTicks,
				fkV2MRouteExpiryTime
					TimeTicks,
				fkV2M4RouteMcProtocol
					IANAipMRouteProtocol,
				fkV2M4RouteRtProtocol
					IANAipRouteProtocol,
				fkV2M4RouteRtAddress
					IpAddress,
				fkV2M4RouteRtMask
					INTEGER,
				fkV2M4RouteRtType
					INTEGER,
				fkV2M4RouteOutIfCount
					Integer32,
				fkV2M4RouteOutInterface
					OCTET STRING,
				fkV2M4RouteFlags
					BITS,
				fkV2M4RouteStsFwdPkts
					Counter64,
				fkV2M4RouteStsFwdBytes
					Counter64,
				fkV2M4RouteStsWrongIfPkts
					Counter64,
				fkV2M4RouteStsWholepktRecvMsg
					Counter64,
				fkV2M4RouteStsWrongvifRecvMsg
					Counter64,
				fkV2M4RouteStsWholepktSentMsg
					Counter64,
				fkV2M4RouteStsWrongvifSentMsg
					Counter64,
				fkV2M4RouteStsTimedSentMsg
					Counter64,
				fkV2M4RouteStsImmediateSentMsg
					Counter64,
				fkV2M4RouteStsRegAckRecvMsg
					Counter64,
				fkV2M4RouteStsRegNackRecvMsg
					Counter64,
				fkV2M4RouteStsRegSentPkts
					Counter64
			 }

--  1.3.6.1.4.1.10428 9 1.102.12.2.2.2.1.1.1
		-- 1.3.6.1.4.1.10428 9 1.102.12.2.1.2.1.1.1
		fkV2M4RouteGroup OBJECT-TYPE
			SYNTAX IpAddress
			MAX-ACCESS read-only
			STATUS current
			DESCRIPTION
				"The IP multicast group address for which this entry 
				contains multicast routing information."
			::= { fkV2M4RouteEntry 1 }

		
--  1.3.6.1.4.1.10428 9 1.102.12.2.2.2.1.1.2
		-- 1.3.6.1.4.1.10428 9 1.102.12.2.1.2.1.1.2
		fkV2M4RouteSource OBJECT-TYPE
			SYNTAX IpAddress
			MAX-ACCESS read-only
			STATUS current
			DESCRIPTION
				"The network address which when combined with the 
				corresponding value of ipMRouteSourceMask identifies the 
				sources for which this entry contains multicast routing 
				information. For (*,G) entry, value 0.0.0.0"
			::= { fkV2M4RouteEntry 2 }

		
--  1.3.6.1.4.1.10428 9 1.102.12.2.2.2.1.1.3
		-- 1.3.6.1.4.1.10428 9 1.102.12.2.1.2.1.1.3
		fkV2M4RouteSrcMask OBJECT-TYPE
			SYNTAX IpAddress
			MAX-ACCESS read-only
			STATUS current
			DESCRIPTION
				"The network mask which when combined with the corresponding 
				value of  fkV2M4RouteSource identifies the sources for which 
				this entry contains multicast routing information.
				For (*,G) entry, value 0.0.0.0"
			::= { fkV2M4RouteEntry 3 }

		
--  1.3.6.1.4.1.10428 9 1.102.12.2.2.2.1.1.4
		-- 1.3.6.1.4.1.10428 9 1.102.12.2.1.2.1.1.4
		fkV2M4RouteInInterface OBJECT-TYPE
			SYNTAX Integer32
			MAX-ACCESS read-only
			STATUS current
			DESCRIPTION
				"The value of ifIndex for the interface on which IP
				datagrams sent by these sources to this multicast address
				are received.  A value of 0 indicates that datagrams are not
				subject to an incoming interface check, but may be accepted
				on multiple interfaces (e.g., in CBT)."
			::= { fkV2M4RouteEntry 4 }

		
--  1.3.6.1.4.1.10428 9 1.102.12.2.2.2.1.1.5
		-- 1.3.6.1.4.1.10428 9 1.102.12.2.1.2.1.1.5
		fkV2M4RouteUpstreamNeighbor OBJECT-TYPE
			SYNTAX IpAddress
			MAX-ACCESS read-only
			STATUS current
			DESCRIPTION
				"The address of the upstream neighbor (e.g., RPF neighbor) 
				from which IP datagrams from these sources to this multicast 
				address are received, or 0.0.0.0 if the upstream neighbor is 
				unknown (e.g., in CBT)."
			::= { fkV2M4RouteEntry 5 }

		
--  1.3.6.1.4.1.10428 9 1.102.12.2.2.2.1.1.6
		-- 1.3.6.1.4.1.10428 9 1.102.12.2.1.2.1.1.6
		fkV2M4RouteUpTime OBJECT-TYPE
			SYNTAX TimeTicks
			MAX-ACCESS read-only
			STATUS current
			DESCRIPTION
				"The time since the multicast routing information 
				represented by this entry was learned by the router."
			::= { fkV2M4RouteEntry 6 }

		
--  1.3.6.1.4.1.10428 9 1.102.12.2.2.2.1.1.7
		-- 1.3.6.1.4.1.10428 9 1.102.12.2.1.2.1.1.7
		fkV2MRouteExpiryTime OBJECT-TYPE
			SYNTAX TimeTicks
			MAX-ACCESS read-only
			STATUS current
			DESCRIPTION
				"The minimum amount of time remaining before this entry will
				be aged out.  The value 0 indicates that the entry is not
				subject to aging."
			::= { fkV2M4RouteEntry 7 }

		
--  1.3.6.1.4.1.10428 9 1.102.12.2.2.2.1.1.8
		-- 1.3.6.1.4.1.10428 9 1.102.12.2.1.2.1.1.8
		fkV2M4RouteMcProtocol OBJECT-TYPE
			SYNTAX IANAipMRouteProtocol
			MAX-ACCESS read-only
			STATUS current
			DESCRIPTION
				"The multicast routing protocol via which this multicast
				forwarding entry was learned."
			::= { fkV2M4RouteEntry 8 }

		
--  1.3.6.1.4.1.10428 9 1.102.12.2.2.2.1.1.9
		-- 1.3.6.1.4.1.10428 9 1.102.12.2.1.2.1.1.9
		fkV2M4RouteRtProtocol OBJECT-TYPE
			SYNTAX IANAipRouteProtocol
			MAX-ACCESS read-only
			STATUS current
			DESCRIPTION
				"The routing mechanism via which the route used to find the
				upstream or parent interface for this multicast forwarding
				entry was learned.  Inclusion of values for routing
				protocols is not intended to imply that those protocols need
				be supported."
			::= { fkV2M4RouteEntry 9 }

		
--  1.3.6.1.4.1.10428 9 1.102.12.2.2.2.1.1.10
		-- 1.3.6.1.4.1.10428 9 1.102.12.2.1.2.1.1.10
		fkV2M4RouteRtAddress OBJECT-TYPE
			SYNTAX IpAddress
			MAX-ACCESS read-only
			STATUS current
			DESCRIPTION
				"The address portion of the route used to find the upstream
				or parent interface for this multicast forwarding entry."
			::= { fkV2M4RouteEntry 10 }

		
--  1.3.6.1.4.1.10428 9 1.102.12.2.2.2.1.1.11
		-- 1.3.6.1.4.1.10428 9 1.102.12.2.1.2.1.1.11
		fkV2M4RouteRtMask OBJECT-TYPE
			SYNTAX INTEGER (1..32)
			MAX-ACCESS read-write
			STATUS current
			DESCRIPTION
				"The mask associated with the route used to find the upstream
				or parent interface for this multicast forwarding entry."
			::= { fkV2M4RouteEntry 11 }

		
--  1.3.6.1.4.1.10428 9 1.102.12.2.2.2.1.1.12
		-- 1.3.6.1.4.1.10428 9 1.102.12.2.1.2.1.1.12
		fkV2M4RouteRtType OBJECT-TYPE
			SYNTAX INTEGER
				{
				unicast(1),
				multicast(2)
				}
			MAX-ACCESS read-only
			STATUS current
			DESCRIPTION
				"The reason the given route was placed in the (logical)
				multicast Routing Information Base (RIB).  A value of
				unicast means that the route would normally be placed only
				in the unicast RIB, but was placed in the multicast RIB
				(instead or in addition) due to local configuration, such as
				when running PIM over RIP.  A value of multicast means that
				the route was explicitly added to the multicast RIB by the
				routing protocol, such as DVMRP or Multiprotocol BGP."
			::= { fkV2M4RouteEntry 12 }

		
--  1.3.6.1.4.1.10428 9 1.102.12.2.2.2.1.1.13
		-- 1.3.6.1.4.1.10428 9 1.102.12.2.1.2.1.1.13
		fkV2M4RouteOutIfCount OBJECT-TYPE
			SYNTAX Integer32
			MAX-ACCESS read-only
			STATUS current
			DESCRIPTION
				"The number of entry's outgoing interfaces."
			::= { fkV2M4RouteEntry 13 }

		
--  1.3.6.1.4.1.10428 9 1.102.12.2.2.2.1.1.14
		-- 1.3.6.1.4.1.10428 9 1.102.12.2.1.2.1.1.14
		fkV2M4RouteOutInterface OBJECT-TYPE
			SYNTAX OCTET STRING (SIZE (1..512))
			MAX-ACCESS read-only
			STATUS current
			DESCRIPTION
				"The bitmap of entry's outgoing interfaces."
			::= { fkV2M4RouteEntry 14 }

		
--  1.3.6.1.4.1.10428 9 1.102.12.2.2.2.1.1.15
		-- 1.3.6.1.4.1.10428 9 1.102.12.2.1.2.1.1.15
		fkV2M4RouteFlags OBJECT-TYPE
			SYNTAX BITS
				{
				immediateState(0),
				timedState(1),
				forworderInstalled(2)
				}
			MAX-ACCESS read-only
			STATUS current
			DESCRIPTION
				"MRIB entry's flags."
			::= { fkV2M4RouteEntry 15 }

		
--  1.3.6.1.4.1.10428 9 1.102.12.2.2.2.1.1.16
		-- 1.3.6.1.4.1.10428 9 1.102.12.2.1.2.1.1.16
		fkV2M4RouteStsFwdPkts OBJECT-TYPE
			SYNTAX Counter64
			MAX-ACCESS read-only
			STATUS current
			DESCRIPTION
				"The number of packets which this router has received from
				these sources and addressed to this multicast group
				address, and which were forwarded by this router."
			::= { fkV2M4RouteEntry 16 }

		
--  1.3.6.1.4.1.10428 9 1.102.12.2.2.2.1.1.17
		-- 1.3.6.1.4.1.10428 9 1.102.12.2.1.2.1.1.17
		fkV2M4RouteStsFwdBytes OBJECT-TYPE
			SYNTAX Counter64
			MAX-ACCESS read-only
			STATUS current
			DESCRIPTION
				"The number of octets contained in IP datagrams which were
				received from these sources and addressed to this multicast
				group address, and which were forwarded by this router."
			::= { fkV2M4RouteEntry 17 }

		
--  1.3.6.1.4.1.10428 9 1.102.12.2.2.2.1.1.18
		-- 1.3.6.1.4.1.10428 9 1.102.12.2.1.2.1.1.18
		fkV2M4RouteStsWrongIfPkts OBJECT-TYPE
			SYNTAX Counter64
			MAX-ACCESS read-only
			STATUS current
			DESCRIPTION
				"The number of packets which this router has received from
				these sources and addressed to this multicast group address,
				which were dropped because they were not received on the
				interface indicated by fkV2M4RouteInInterface.  Packets which are
				not subject to an incoming interface check (e.g., using CBT)
				are not counted."
			::= { fkV2M4RouteEntry 18 }

		
--  1.3.6.1.4.1.10428 9 1.102.12.2.2.2.1.1.19
		-- 1.3.6.1.4.1.10428 9 1.102.12.2.1.2.1.1.19
		fkV2M4RouteStsWholepktRecvMsg OBJECT-TYPE
			SYNTAX Counter64
			MAX-ACCESS read-only
			STATUS current
			DESCRIPTION
				"The number of WHOLEPKT event messages which this MRIB has received 
				from the Multicast Forwarder for this entry.
				The Multicast Forwarder generates the WHOLEPKT event whenever 
				the special REGISTER VIF appears in the out interface list of an (S,G) MRT 
				in the multicast forwarder."
			::= { fkV2M4RouteEntry 19 }

		
--  1.3.6.1.4.1.10428 9 1.102.12.2.2.2.1.1.20
		-- 1.3.6.1.4.1.10428 9 1.102.12.2.1.2.1.1.20
		fkV2M4RouteStsWrongvifRecvMsg OBJECT-TYPE
			SYNTAX Counter64
			MAX-ACCESS read-only
			STATUS current
			DESCRIPTION
				"The number of WRONGVIF event messages which this MRIB has received 
				from the Multicast Forwarder for this entry.
				The Multicast Forwarder generates a WRONGVIF event when it 
				receives a packet destined to (S,G) on an interface that 
				does not match the IIF of the (S,G) MRT in the Multicast Forwarder."
			::= { fkV2M4RouteEntry 20 }

		
--  1.3.6.1.4.1.10428 9 1.102.12.2.2.2.1.1.21
		-- 1.3.6.1.4.1.10428 9 1.102.12.2.1.2.1.1.21
		fkV2M4RouteStsWholepktSentMsg OBJECT-TYPE
			SYNTAX Counter64
			MAX-ACCESS read-only
			STATUS current
			DESCRIPTION
				"The number of NSM_MSG_IPV4_MRT_WHOLEPKT_REQUEST(NSM_MSG_IPV6_MRT_WHOLEPKT_REQUEST) 
				messages which MRIB sent to multicast protocol for this entry.
				When the MRIB receives WHOLEPKT event message from Multicast Forwarder, 
				it sends an message to the multicast protocol.
				
				It is inefficient and expensive to relay this whole message to the multicast 
				protocol, because IP packet can be as large as 64 KB.
				To avoid sending the WHOLEPKT message to the multicast protocol, 
				NSM_MSG_IPV4_MRT_WHOLEPKT_REQUEST message contains the (S,G) key, 
				the REGISTER VIF index, and a unique identifier for the instance of 
				the WHOLEPKT message from the Multicast Forwarder, whitout the all packet data."
			::= { fkV2M4RouteEntry 21 }

		
--  1.3.6.1.4.1.10428 9 1.102.12.2.2.2.1.1.22
		-- 1.3.6.1.4.1.10428 9 1.102.12.2.1.2.1.1.22
		fkV2M4RouteStsWrongvifSentMsg OBJECT-TYPE
			SYNTAX Counter64
			MAX-ACCESS read-only
			STATUS current
			DESCRIPTION
				"The number of NSM_MSG_IPV4_MRT_WRONGVIF(NSM_MSG_IPV6_MRT_WRONGVIF) messages 
				which MRIB sent to multicast protocol for this entry.
				When the MRIB receives WRONGVIF event message from Multicast Forwarder, 
				it relays it to all multicast protocols that have requested PIM service."
			::= { fkV2M4RouteEntry 22 }

		
--  1.3.6.1.4.1.10428 9 1.102.12.2.2.2.1.1.23
		-- 1.3.6.1.4.1.10428 9 1.102.12.2.1.2.1.1.23
		fkV2M4RouteStsTimedSentMsg OBJECT-TYPE
			SYNTAX Counter64
			MAX-ACCESS read-only
			STATUS current
			DESCRIPTION
				"The number of notification messages occured by timed event 
				of MRIB by which multicast protocols update own statistics 
				information."
			::= { fkV2M4RouteEntry 23 }

		
--  1.3.6.1.4.1.10428 9 1.102.12.2.2.2.1.1.24
		-- 1.3.6.1.4.1.10428 9 1.102.12.2.1.2.1.1.24
		fkV2M4RouteStsImmediateSentMsg OBJECT-TYPE
			SYNTAX Counter64
			MAX-ACCESS read-only
			STATUS current
			DESCRIPTION
				"The number of notification messages occured by immediate event 
				of MRIB by which multicast protocols update own statistics 
				information."
			::= { fkV2M4RouteEntry 24 }

		
--  1.3.6.1.4.1.10428 9 1.102.12.2.2.2.1.1.25
		-- 1.3.6.1.4.1.10428 9 1.102.12.2.1.2.1.1.25
		fkV2M4RouteStsRegAckRecvMsg OBJECT-TYPE
			SYNTAX Counter64
			MAX-ACCESS read-only
			STATUS current
			DESCRIPTION
				"The number of ACK messages which the MRIB has received from 
				multicast protocol for this MRIB entry, and by which MRIB 
				originates a Register packet to the destination RP provided 
				in this ACK reply."
			::= { fkV2M4RouteEntry 25 }

		
--  1.3.6.1.4.1.10428 9 1.102.12.2.2.2.1.1.26
		-- 1.3.6.1.4.1.10428 9 1.102.12.2.1.2.1.1.26
		fkV2M4RouteStsRegNackRecvMsg OBJECT-TYPE
			SYNTAX Counter64
			MAX-ACCESS read-only
			STATUS current
			DESCRIPTION
				"The number of NACK messages which the MRIB has received from 
				multicast protocol for this MRIB entry, and by which MRIB don't 
				originates a Register packet to the destination RP provided 
				in this ACK reply."
			::= { fkV2M4RouteEntry 26 }

		
--  1.3.6.1.4.1.10428 9 1.102.12.2.2.2.1.1.27
		-- 1.3.6.1.4.1.10428 9 1.102.12.2.1.2.1.1.27
		fkV2M4RouteStsRegSentPkts OBJECT-TYPE
			SYNTAX Counter64
			MAX-ACCESS read-only
			STATUS current
			DESCRIPTION
				"The number of Register packets which the MRIB sent to 
				the destination RP for this entry."
			::= { fkV2M4RouteEntry 27 }

		
--  Multicast Routing Information Base Control
-- 1.3.6.1.4.1.10428 9 1.102.12.2.1.2.2
		-- 1.3.6.1.4.1.10428 9 1.102.12.2.1.2.2
		fkV2M4RouteControl OBJECT IDENTIFIER ::= { fkV2M4Route 2 }

		
--  1.3.6.1.4.1.10428 9 1.102.12.2.1.2.2.1
		-- 1.3.6.1.4.1.10428 9 1.102.12.2.1.2.2.1
		fkV2M4RouteControlRequest OBJECT-TYPE
			SYNTAX INTEGER
				{
				destroyMRouteEntry(1),
				clearMRouteAllEntries(2),
				clearMRouteStatistics(3),
				clearMRouteAllStatistics(4)
				}
			MAX-ACCESS read-write
			STATUS current
			DESCRIPTION
				"The request of a user command"
			::= { fkV2M4RouteControl 1 }

		
--  1.3.6.1.4.1.10428 9 1.102.12.2.1.2.2.2
		-- 1.3.6.1.4.1.10428 9 1.102.12.2.1.2.2.2
		fkV2M4RouteControlStatus OBJECT-TYPE
			SYNTAX FkControlStatusType
			MAX-ACCESS read-only
			STATUS current
			DESCRIPTION
				"The status of user command"
			::= { fkV2M4RouteControl 2 }

		
--  1.3.6.1.4.1.10428 9 1.102.12.2.1.2.2.3
		-- 1.3.6.1.4.1.10428 9 1.102.12.2.1.2.2.3
		fkV2M4RouteControlTimer OBJECT-TYPE
			SYNTAX Gauge32
			MAX-ACCESS read-write
			STATUS current
			DESCRIPTION
				"The maximum time for the manager for a long running user command"
			::= { fkV2M4RouteControl 3 }

		
--  1.3.6.1.4.1.10428 9 1.102.12.2.1.2.2.4
		-- 1.3.6.1.4.1.10428 9 1.102.12.2.1.2.2.4
		fkV2M4RouteControlTimeStamp OBJECT-TYPE
			SYNTAX TimeTicks
			MAX-ACCESS read-only
			STATUS current
			DESCRIPTION
				"The time stamp of the last command(end of command)"
			::= { fkV2M4RouteControl 4 }

		
--  1.3.6.1.4.1.10428 9 1.102.12.2.1.2.2.5
		-- 1.3.6.1.4.1.10428 9 1.102.12.2.1.2.2.5
		fkV2M4RouteControlReqResult OBJECT-TYPE
			SYNTAX FkControlRequestResultType
			MAX-ACCESS read-only
			STATUS current
			DESCRIPTION
				"The result of the last user command"
			::= { fkV2M4RouteControl 5 }

		
--  1.3.6.1.4.1.10428 9 1.102.12.2.1.2.2.6
		-- 1.3.6.1.4.1.10428 9 1.102.12.2.1.2.2.6
		fkV2M4RouteControlGroup OBJECT-TYPE
			SYNTAX IpAddress
			MAX-ACCESS read-write
			STATUS current
			DESCRIPTION
				"The IP multicast group address for which this entry 
				contains multicast routing information."
			::= { fkV2M4RouteControl 6 }

		
--  1.3.6.1.4.1.10428 9 1.102.12.2.1.2.2.7
		-- 1.3.6.1.4.1.10428 9 1.102.12.2.1.2.2.7
		fkV2M4RouteControlSource OBJECT-TYPE
			SYNTAX IpAddress
			MAX-ACCESS read-write
			STATUS current
			DESCRIPTION
				"The network address which when combined with the 
				corresponding value of ipMRouteSourceMask identifies the 
				sources for which this entry contains multicast routing 
				information. For (*,G) entry, value 0.0.0.0"
			::= { fkV2M4RouteControl 7 }

		
--  1.3.6.1.4.1.10428 9 1.102.12.2.1.2.2.8
		-- 1.3.6.1.4.1.10428 9 1.102.12.2.1.2.2.8
		fkV2M4RouteControlSrcMask OBJECT-TYPE
			SYNTAX IpAddress
			MAX-ACCESS read-write
			STATUS current
			DESCRIPTION
				"The network mask which when combined with the corresponding 
				value of  fkV2M4RouteSource identifies the sources for which 
				this entry contains multicast routing information.
				For (*,G) entry, value 0.0.0.0"
			::= { fkV2M4RouteControl 8 }

		
--  1.3.6.1.4.1.10428 9 1.102.12.2.1.2.2.9
		-- 1.3.6.1.4.1.10428 9 1.102.12.2.1.2.2.9
		fkV2M4RouteControlMcastProtocol OBJECT-TYPE
			SYNTAX INTEGER
				{
				anyMRouteProtocol(0),
				pimSparseMode(8)
				}
			MAX-ACCESS read-write
			STATUS current
			DESCRIPTION
				"The multicast routing protocol via which this multicast
				forwarding entry was learned."
			::= { fkV2M4RouteControl 9 }

		
--  Multicast Routing Information Base Notification
-- 1.3.6.1.4.1.10428 9 1.102.12.2.1.2.3
		-- 1.3.6.1.4.1.10428 9 1.102.12.2.1.2.3
		fkV2M4RouteNotification OBJECT IDENTIFIER ::= { fkV2M4Route 3 }

		
--  1.3.6.1.4.1.10428 9 1.102.12.2.1.2.3.1
		-- 1.3.6.1.4.1.10428 9 1.102.12.2.1.2.3.1
		fkV2M4RouteEntryDestroyed NOTIFICATION-TYPE
			OBJECTS { fkV2M4RouteControlRequest, fkV2M4RouteControlReqResult, fkV2M4RouteControlTimeStamp, fkV2M4RouteControlGroup, fkV2M4RouteControlSource, 
				fkV2M4RouteControlSrcMask, fkV2M4RouteControlMcastProtocol }
			STATUS current
			DESCRIPTION 
				"Description."
			::= { fkV2M4RouteNotification 1 }

		
--  1.3.6.1.4.1.10428 9 1.102.12.2.1.2.3.2
		-- 1.3.6.1.4.1.10428 9 1.102.12.2.1.2.3.2
		fkV2M4RoutAllEntriesCleared NOTIFICATION-TYPE
			OBJECTS { fkV2M4RouteControlRequest, fkV2M4RouteControlReqResult, fkV2M4RouteControlTimeStamp }
			STATUS current
			DESCRIPTION 
				"Description."
			::= { fkV2M4RouteNotification 2 }

		
--  1.3.6.1.4.1.10428 9 1.102.12.2.1.2.3.3
		-- 1.3.6.1.4.1.10428 9 1.102.12.2.1.2.3.3
		fkV2M4RoutStatisticsCleared NOTIFICATION-TYPE
			OBJECTS { fkV2M4RouteControlRequest, fkV2M4RouteControlReqResult, fkV2M4RouteControlTimeStamp, fkV2M4RouteControlGroup, fkV2M4RouteControlSource, 
				fkV2M4RouteControlSrcMask }
			STATUS current
			DESCRIPTION 
				"Description."
			::= { fkV2M4RouteNotification 3 }

		
--  1.3.6.1.4.1.10428 9 1.102.12.2.1.2.3.4
		-- 1.3.6.1.4.1.10428 9 1.102.12.2.1.2.3.4
		fkV2M4RoutAllStatisticsCleared NOTIFICATION-TYPE
			OBJECTS { fkV2M4RouteControlRequest, fkV2M4RouteControlReqResult, fkV2M4RouteControlTimeStamp }
			STATUS current
			DESCRIPTION 
				"Description."
			::= { fkV2M4RouteNotification 4 }

		
--  Multicast Routing Information Base Next-Hop
-- 1.3.6.1.4.1.10428 9 1.102.12.2.1.3
		-- 1.3.6.1.4.1.10428 9 1.102.12.2.1.3
		fkV2M4RouteNextHop OBJECT IDENTIFIER ::= { fkV2Mrib4 3 }

		
--  Multicast Routing Information Base Next-Hop Table
-- 1.3.6.1.4.1.10428 9 1.102.12.2.1.3.1
		-- 1.3.6.1.4.1.10428 9 1.102.12.2.1.3.1
		fkV2M4RouteNextHopTable OBJECT-TYPE
			SYNTAX SEQUENCE OF FkV2M4RouteNextHopEntry
			MAX-ACCESS not-accessible
			STATUS current
			DESCRIPTION
				"The (conceptual) table containing information on the 
				next-hops on outgoing interfaces for routing IP multicast
				datagrams.  Each entry is one of a list of next-hops on
				outgoing interfaces for particular sources sending to a
				particular multicast group address."
			::= { fkV2M4RouteNextHop 1 }

		
--  Multicast Routing Information Base Next-Hop Entry
-- 1.3.6.1.4.1.10428 9 1.102.12.2.2.3.1.1
		-- 1.3.6.1.4.1.10428 9 1.102.12.2.1.3.1.1
		fkV2M4RouteNextHopEntry OBJECT-TYPE
			SYNTAX FkV2M4RouteNextHopEntry
			MAX-ACCESS not-accessible
			STATUS current
			DESCRIPTION
				"An entry (conceptual row) in the list of next-hops on
				outgoing interfaces to which IP multicast datagrams from
				particular sources to a IP multicast group address are
				routed.  Discontinuities in counters in this entry can be
				detected by observing the value of fkV2M4RouteUpTime.
				key: fkV2M4RouteGroup, fkV2M4RouteSource, fkV2M4RouteSrcMask, fkV2M4RouteNextHopIfIndex, fkV2M4RouteNextHopAddress"
			INDEX { fkV2M4RouteGroup, fkV2M4RouteSource, fkV2M4RouteSrcMask, fkV2M4RouteNextHopIfIndex, fkV2M4RouteNextHopAddress
				 }
			::= { fkV2M4RouteNextHopTable 1 }

		
		FkV2M4RouteNextHopEntry ::=
			SEQUENCE { 
				fkV2M4RouteNextHopIfIndex
					INTEGER,
				fkV2M4RouteNextHopAddress
					IpAddress,
				fkV2M4RouteNextHopState
					INTEGER,
				fkV2M4RouteNextHopUpTime
					TimeTicks,
				fkV2M4RouteNextHopExpiryTime
					TimeTicks,
				fkV2M4RouteNextHopProtocol
					IANAipMRouteProtocol,
				fkV2M4RouteNextHopClosestMemberHops
					Integer32,
				fkV2M4RouteNextHopPkts
					Counter64
			 }

--  1.3.6.1.4.1.10428 9 1.102.12.2.2.3.1.1.1
		-- 1.3.6.1.4.1.10428 9 1.102.12.2.1.3.1.1.1
		fkV2M4RouteNextHopIfIndex OBJECT-TYPE
			SYNTAX INTEGER (1..4094)
			MAX-ACCESS read-only
			STATUS current
			DESCRIPTION
				"The ifIndex value of the interface for the outgoing 
				interface for this next-hop."
			::= { fkV2M4RouteNextHopEntry 1 }

		
--  1.3.6.1.4.1.10428 9 1.102.12.2.2.3.1.1.2
		-- 1.3.6.1.4.1.10428 9 1.102.12.2.1.3.1.1.2
		fkV2M4RouteNextHopAddress OBJECT-TYPE
			SYNTAX IpAddress
			MAX-ACCESS read-only
			STATUS current
			DESCRIPTION
				"The address of the next-hop specific to this entry. For 
				most interfaces, this is identical to  fkV2M4RouteGroup. 
				NBMA interfaces, however, may have multiple next-hop 
				addresses out a single outgoing interface."
			::= { fkV2M4RouteNextHopEntry 2 }

		
--  1.3.6.1.4.1.10428 9 1.102.12.2.2.3.1.1.3
		-- 1.3.6.1.4.1.10428 9 1.102.12.2.1.3.1.1.3
		fkV2M4RouteNextHopState OBJECT-TYPE
			SYNTAX INTEGER
				{
				pruned(1),
				forwarding(2)
				}
			MAX-ACCESS read-only
			STATUS current
			DESCRIPTION
				"An indication of whether the outgoing interface and next-
				hop represented by this entry is currently being used to
				forward IP datagrams.  The value 'forwarding' indicates it
				is currently being used; the value 'pruned' indicates it is
				not."
			::= { fkV2M4RouteNextHopEntry 3 }

		
--  1.3.6.1.4.1.10428 9 1.102.12.2.2.3.1.1.4
		-- 1.3.6.1.4.1.10428 9 1.102.12.2.1.3.1.1.4
		fkV2M4RouteNextHopUpTime OBJECT-TYPE
			SYNTAX TimeTicks
			MAX-ACCESS read-only
			STATUS current
			DESCRIPTION
				"The time since the multicast routing information
				represented by this entry was learned by the router."
			::= { fkV2M4RouteNextHopEntry 4 }

		
--  1.3.6.1.4.1.10428 9 1.102.12.2.2.3.1.1.5
		-- 1.3.6.1.4.1.10428 9 1.102.12.2.1.3.1.1.5
		fkV2M4RouteNextHopExpiryTime OBJECT-TYPE
			SYNTAX TimeTicks
			MAX-ACCESS read-only
			STATUS current
			DESCRIPTION
				"The minimum amount of time remaining before this entry will
				be aged out.  If ipMRouteNextHopState is pruned(1), the
				remaining time until the prune expires and the state reverts
				to forwarding(2).  Otherwise, the remaining time until this
				entry is removed from the table.  The time remaining may be
				copied from fkV2MRouteExpiryTime if the protocol in use for
				this entry does not specify next-hop timers.  The value 0
				indicates that the entry is not subject to aging."
			::= { fkV2M4RouteNextHopEntry 5 }

		
--  1.3.6.1.4.1.10428 9 1.102.12.2.2.3.1.1.6
		-- 1.3.6.1.4.1.10428 9 1.102.12.2.1.3.1.1.6
		fkV2M4RouteNextHopProtocol OBJECT-TYPE
			SYNTAX IANAipMRouteProtocol
			MAX-ACCESS read-only
			STATUS current
			DESCRIPTION
				"The routing mechanism via which this next-hop was learned."
			::= { fkV2M4RouteNextHopEntry 6 }

		
--  1.3.6.1.4.1.10428 9 1.102.12.2.2.3.1.1.7
		-- 1.3.6.1.4.1.10428 9 1.102.12.2.1.3.1.1.7
		fkV2M4RouteNextHopClosestMemberHops OBJECT-TYPE
			SYNTAX Integer32
			MAX-ACCESS read-only
			STATUS current
			DESCRIPTION
				"The minimum number of hops between this router and any
				member of this IP multicast group reached via this next-hop
				on this outgoing interface.  Any IP multicast datagrams for
				the group which have a TTL less than this number of hops
				will not be forwarded to this next-hop."
			::= { fkV2M4RouteNextHopEntry 7 }

		
--  1.3.6.1.4.1.10428 9 1.102.12.2.2.3.1.1.8
		-- 1.3.6.1.4.1.10428 9 1.102.12.2.1.3.1.1.8
		fkV2M4RouteNextHopPkts OBJECT-TYPE
			SYNTAX Counter64
			MAX-ACCESS read-only
			STATUS current
			DESCRIPTION
				"The number of packets which have been forwarded using this
				route."
			::= { fkV2M4RouteNextHopEntry 8 }

		
--  Multicast Routing Information Base Interface
-- 1.3.6.1.4.1.10428 9 1.102.12.2.1.4
		-- 1.3.6.1.4.1.10428 9 1.102.12.2.1.4
		fkV2M4RouteInterface OBJECT IDENTIFIER ::= { fkV2Mrib4 4 }

		
--  Multicast Routing Information Base Interface Table
-- 1.3.6.1.4.1.10428 9 1.102.12.2.1.4.1
		-- 1.3.6.1.4.1.10428 9 1.102.12.2.1.4.1
		fkV2M4RouteIfTable OBJECT-TYPE
			SYNTAX SEQUENCE OF FkV2M4RouteIfEntry
			MAX-ACCESS not-accessible
			STATUS current
			DESCRIPTION
				"The (conceptual) table containing multicast routing
				information specific to interfaces."
			::= { fkV2M4RouteInterface 1 }

		
--  Multicast Routing Information Base Interface Entry
-- 1.3.6.1.4.1.10428 9 1.102.12.2.2.4.1.1
		-- 1.3.6.1.4.1.10428 9 1.102.12.2.1.4.1.1
		fkV2M4RouteIfEntry OBJECT-TYPE
			SYNTAX FkV2M4RouteIfEntry
			MAX-ACCESS not-accessible
			STATUS current
			DESCRIPTION
				"An entry (conceptual row) containing the multicast routing
				information for a particular interface.
				key: fkV2M4RouteIfIndex"
			INDEX { fkV2M4RouteIfIndex }
			::= { fkV2M4RouteIfTable 1 }

		
		FkV2M4RouteIfEntry ::=
			SEQUENCE { 
				fkV2M4RouteIfIndex
					Integer32,
				fkV2M4RouteIfName
					OCTET STRING,
				fkV2M4RouteIfTtl
					Integer32,
				fkV2M4RouteIfRateLimit
					Integer32,
				fkV2M4RouteIfProtocol
					IANAipMRouteProtocol,
				fkV2M4RouteIfInMcastOctets
					Counter64,
				fkV2M4RouteIfOutMcastOctets
					Counter64
			 }

--  1.3.6.1.4.1.10428 9 1.102.12.2.2.4.1.1.1
		-- 1.3.6.1.4.1.10428 9 1.102.12.2.1.4.1.1.1
		fkV2M4RouteIfIndex OBJECT-TYPE
			SYNTAX Integer32 (1..4094)
			MAX-ACCESS read-only
			STATUS current
			DESCRIPTION
				"The ifIndex value of the interface for which this entry
				contains information."
			::= { fkV2M4RouteIfEntry 1 }

		
--  1.3.6.1.4.1.10428 9 1.102.12.2.2.4.1.1.2
		-- 1.3.6.1.4.1.10428 9 1.102.12.2.1.4.1.1.2
		fkV2M4RouteIfName OBJECT-TYPE
			SYNTAX OCTET STRING (SIZE (0..8))
			MAX-ACCESS read-only
			STATUS current
			DESCRIPTION
				"The ifName of the interface for which this entry
				contains information."
			::= { fkV2M4RouteIfEntry 2 }

		
--  1.3.6.1.4.1.10428 9 1.102.12.2.2.4.1.1.3
		-- 1.3.6.1.4.1.10428 9 1.102.12.2.1.4.1.1.3
		fkV2M4RouteIfTtl OBJECT-TYPE
			SYNTAX Integer32 (0..255)
			MAX-ACCESS read-only
			STATUS current
			DESCRIPTION
				"The datagram TTL threshold for the interface. Any IP
				multicast datagrams with a TTL less than this threshold will
				not be forwarded out the interface. The default value of 0
				means all multicast packets are forwarded out the
				interface."
			::= { fkV2M4RouteIfEntry 3 }

		
--  1.3.6.1.4.1.10428 9 1.102.12.2.2.4.1.1.4
		-- 1.3.6.1.4.1.10428 9 1.102.12.2.1.4.1.1.4
		fkV2M4RouteIfRateLimit OBJECT-TYPE
			SYNTAX Integer32
			MAX-ACCESS read-only
			STATUS current
			DESCRIPTION
				"The rate-limit, in kilobits per second, of forwarded
				multicast traffic on the interface.  A rate-limit of 0
				indicates that no rate limiting is done."
			DEFVAL { 0 }
			::= { fkV2M4RouteIfEntry 4 }

		
--  1.3.6.1.4.1.10428 9 1.102.12.2.2.4.1.1.5
		-- 1.3.6.1.4.1.10428 9 1.102.12.2.1.4.1.1.5
		fkV2M4RouteIfProtocol OBJECT-TYPE
			SYNTAX IANAipMRouteProtocol
			MAX-ACCESS read-only
			STATUS current
			DESCRIPTION
				"The routing protocol running on this interface."
			::= { fkV2M4RouteIfEntry 5 }

		
--  1.3.6.1.4.1.10428 9 1.102.12.2.2.4.1.1.6
		-- 1.3.6.1.4.1.10428 9 1.102.12.2.1.4.1.1.6
		fkV2M4RouteIfInMcastOctets OBJECT-TYPE
			SYNTAX Counter64
			MAX-ACCESS read-only
			STATUS current
			DESCRIPTION
				"The number of octets of multicast packets that have arrived
				on the interface, including framing characters.  This object
				is similar to ifInOctets in the Interfaces MIB, except that
				only multicast packets are counted."
			::= { fkV2M4RouteIfEntry 6 }

		
--  1.3.6.1.4.1.10428 9 1.102.12.2.2.4.1.1.7
		-- 1.3.6.1.4.1.10428 9 1.102.12.2.1.4.1.1.7
		fkV2M4RouteIfOutMcastOctets OBJECT-TYPE
			SYNTAX Counter64
			MAX-ACCESS read-only
			STATUS current
			DESCRIPTION
				"The number of octets of multicast packets that have been
				sent on the interface."
			::= { fkV2M4RouteIfEntry 7 }

		
--  Multicast Routing Information Base Interface Control
-- 1.3.6.1.4.1.10428 9 1.102.12.2.1.4.2
		-- 1.3.6.1.4.1.10428 9 1.102.12.2.1.4.2
		fkV2M4RouteIfControl OBJECT IDENTIFIER ::= { fkV2M4RouteInterface 2 }

		
--  1.3.6.1.4.1.10428 9 1.102.12.2.1.4.2.1
		-- 1.3.6.1.4.1.10428 9 1.102.12.2.1.4.2.1
		fkV2M4RouteIfControlRequest OBJECT-TYPE
			SYNTAX INTEGER { setMRouteInterfaceProfile(1) }
			MAX-ACCESS read-write
			STATUS current
			DESCRIPTION
				"The request of a user command"
			::= { fkV2M4RouteIfControl 1 }

		
--  1.3.6.1.4.1.10428 9 1.102.12.2.1.4.2.2
		-- 1.3.6.1.4.1.10428 9 1.102.12.2.1.4.2.2
		fkV2M4RouteIfControlStatus OBJECT-TYPE
			SYNTAX FkControlStatusType
			MAX-ACCESS read-only
			STATUS current
			DESCRIPTION
				"The status of user command"
			::= { fkV2M4RouteIfControl 2 }

		
--  1.3.6.1.4.1.10428 9 1.102.12.2.1.4.2.3
		-- 1.3.6.1.4.1.10428 9 1.102.12.2.1.4.2.3
		fkV2M4RouteIfControlTimer OBJECT-TYPE
			SYNTAX Gauge32
			MAX-ACCESS read-write
			STATUS current
			DESCRIPTION
				"The maximum time for the manager for a long running user command"
			::= { fkV2M4RouteIfControl 3 }

		
--  1.3.6.1.4.1.10428 9 1.102.12.2.1.4.2.4
		-- 1.3.6.1.4.1.10428 9 1.102.12.2.1.4.2.4
		fkV2M4RouteIfControlTimeStamp OBJECT-TYPE
			SYNTAX TimeTicks
			MAX-ACCESS read-only
			STATUS current
			DESCRIPTION
				"The time stamp of the last command(end of command)"
			::= { fkV2M4RouteIfControl 4 }

		
--  1.3.6.1.4.1.10428 9 1.102.12.2.1.4.2.5
		-- 1.3.6.1.4.1.10428 9 1.102.12.2.1.4.2.5
		fkV2M4RouteIfControlReqResult OBJECT-TYPE
			SYNTAX FkControlRequestResultType
			MAX-ACCESS read-only
			STATUS current
			DESCRIPTION
				"The result of the last user command"
			::= { fkV2M4RouteIfControl 5 }

		
--  1.3.6.1.4.1.10428 9 1.102.12.2.1.4.2.6
		-- 1.3.6.1.4.1.10428 9 1.102.12.2.1.4.2.6
		fkV2M4RouteIfControlIndex OBJECT-TYPE
			SYNTAX INTEGER (1..4094)
			MAX-ACCESS read-write
			STATUS current
			DESCRIPTION
				"The ifIndex value of the interface for which this control changes
				multicast configuration."
			::= { fkV2M4RouteIfControl 6 }

		
--  1.3.6.1.4.1.10428 9 1.102.12.2.1.4.2.7
		-- 1.3.6.1.4.1.10428 9 1.102.12.2.1.4.2.7
		fkV2M4RouteIfControlTtl OBJECT-TYPE
			SYNTAX Integer32 (0..255)
			MAX-ACCESS read-write
			STATUS current
			DESCRIPTION
				"The datagram TTL threshold for the interface. Any IP
				multicast datagrams with a TTL less than this threshold will
				not be forwarded out the interface. The default value of 0
				means all multicast packets are forwarded out the
				interface."
			::= { fkV2M4RouteIfControl 7 }

		
--  1.3.6.1.4.1.10428 9 1.102.12.2.1.4.2.8
		-- 1.3.6.1.4.1.10428 9 1.102.12.2.1.4.2.8
		fkV2M4RouteIfControlRateLimit OBJECT-TYPE
			SYNTAX Integer32
			MAX-ACCESS read-write
			STATUS current
			DESCRIPTION
				"The rate-limit, in kilobits per second, of forwarded
				multicast traffic on the interface.  A rate-limit of 0
				indicates that no rate limiting is done."
			::= { fkV2M4RouteIfControl 8 }

		
--  Multicast Routing Information Base Interface Notification
-- 1.3.6.1.4.1.10428 9 1.102.12.2.1.4.3
		-- 1.3.6.1.4.1.10428 9 1.102.12.2.1.4.3
		fkV2M4RouteIfNotification OBJECT IDENTIFIER ::= { fkV2M4RouteInterface 3 }

		
--  1.3.6.1.4.1.10428 9 1.102.12.2.1.4.3.1
		-- 1.3.6.1.4.1.10428 9 1.102.12.2.1.4.3.1
		fkV2M4RouteInterfaceProfileChanged NOTIFICATION-TYPE
			OBJECTS { fkV2M4RouteIfControlRequest, fkV2M4RouteIfControlReqResult, fkV2M4RouteIfControlTimeStamp, fkV2M4RouteIfTtl, fkV2M4RouteIfRateLimit
				 }
			STATUS current
			DESCRIPTION 
				"Description."
			::= { fkV2M4RouteIfNotification 1 }

		
--  Internet Group Management Protocol
-- 1.3.6.1.4.1.10428 9 1.102.12.2.2
		-- 1.3.6.1.4.1.10428 9 1.102.12.2.2
		fkV2Igmp OBJECT IDENTIFIER ::= { fkV2Multicast4 2 }

		
--  IGMP Configuration
-- 1.3.6.1.4.1.10428 9 1.102.12.2.2.1
		-- 1.3.6.1.4.1.10428 9 1.102.12.2.2.1
		fkV2IgmpBase OBJECT IDENTIFIER ::= { fkV2Igmp 1 }

		
--  IGMP Configuration Group
-- 1.3.6.1.4.1.10428 9 1.102.12.2.2.1.1
		-- 1.3.6.1.4.1.10428 9 1.102.12.2.2.1.1
		fkV2IgmpInfo OBJECT IDENTIFIER ::= { fkV2IgmpBase 1 }

		
--  1.3.6.1.4.1.10428 9 1.102.12.2.2.1.1.1
		-- 1.3.6.1.4.1.10428 9 1.102.12.2.2.1.1.1
		fkV2IgmpInfoSnoopActivity OBJECT-TYPE
			SYNTAX Boolean
			MAX-ACCESS read-only
			STATUS current
			DESCRIPTION
				"This object indicates whether IGMP Snooping has been enabled for the system."
			::= { fkV2IgmpInfo 1 }

		
--  1.3.6.1.4.1.10428 9 1.102.12.2.2.1.1.2
		-- 1.3.6.1.4.1.10428 9 1.102.12.2.2.1.1.2
		fkV2IgmpInfoSnoopVersion OBJECT-TYPE
			SYNTAX INTEGER
				{
				igmpV1(1),
				igmpV2(2),
				igmpV3(3)
				}
			MAX-ACCESS read-only
			STATUS current
			DESCRIPTION
				"The maximum version of IGMP supported."
			::= { fkV2IgmpInfo 2 }

		
--  1.3.6.1.4.1.10428 9 1.102.12.2.2.1.1.3
		-- 1.3.6.1.4.1.10428 9 1.102.12.2.2.1.1.3
		fkV2IgmpInfoSnoopVersionMode OBJECT-TYPE
			SYNTAX INTEGER
				{
				static(0),
				dynamic(1)
				}
			MAX-ACCESS read-only
			STATUS current
			DESCRIPTION
				"Global IGMP Snooping Version Mode"
			::= { fkV2IgmpInfo 3 }

		
--  1.3.6.1.4.1.10428 9 1.102.12.2.2.1.1.4
		-- 1.3.6.1.4.1.10428 9 1.102.12.2.2.1.1.4
		fkV2IgmpInfoSnoopFastLeave OBJECT-TYPE
			SYNTAX Boolean
			MAX-ACCESS read-only
			STATUS current
			DESCRIPTION
				"This object indicates whether Fast-Leave mechanism has been configured to be enabled in the system. If Fast-Leave is enabled in the switch, IGMP Snooping will prune the port on which an IGMP leave message has been received without waiting for the Group Specific Query to timeout to determine whether there are any more hosts on that port for that group. If the value of fkV2IgmpInfoSnoopVersion is not 3, this object will not have any effect."
			::= { fkV2IgmpInfo 4 }

		
--  1.3.6.1.4.1.10428 9 1.102.12.2.2.1.1.5
		-- 1.3.6.1.4.1.10428 9 1.102.12.2.2.1.1.5
		fkV2IgmpInfoSnoopFastBlock OBJECT-TYPE
			SYNTAX Boolean
			MAX-ACCESS read-only
			STATUS current
			DESCRIPTION
				"The object indicates whether Fast-Block mechanism has been enabled for the system. This object only has effect if the value of fkV2IgmpInfoSnoopVersion is 3."
			::= { fkV2IgmpInfo 5 }

		
--  1.3.6.1.4.1.10428 9 1.102.12.2.2.1.1.6
		-- 1.3.6.1.4.1.10428 9 1.102.12.2.2.1.1.6
		fkV2IgmpInfoSnoopReportSuppression OBJECT-TYPE
			SYNTAX Boolean
			MAX-ACCESS read-only
			STATUS current
			DESCRIPTION
				"When this object is set to 'true', IGMP Snooping will suppress duplicate IGMP Reports.  When this object is set to 'false', all IGMP Reports are forwarded to all multicast routers. Alias is IGMP Snooping Proxy."
			::= { fkV2IgmpInfo 6 }

		
--  1.3.6.1.4.1.10428 9 1.102.12.2.2.1.1.7
		-- 1.3.6.1.4.1.10428 9 1.102.12.2.2.1.1.7
		fkV2IgmpInfoSnoopQuerierActivity OBJECT-TYPE
			SYNTAX Boolean
			MAX-ACCESS read-only
			STATUS current
			DESCRIPTION
				"The object indicates whether the device will participate in the IGMP Querier election. If the object is set to 'true', the device will participate to an election process to be a Querier."
			::= { fkV2IgmpInfo 7 }

		
--  1.3.6.1.4.1.10428 9 1.102.12.2.2.1.1.8
		-- 1.3.6.1.4.1.10428 9 1.102.12.2.2.1.1.8
		fkV2IgmpInfoSnoopQueryInterval OBJECT-TYPE
			SYNTAX Unsigned32 (0..31744)
			MAX-ACCESS read-only
			STATUS current
			DESCRIPTION
				"The frequency at which IGMP packets are transmitted on this interface."
			::= { fkV2IgmpInfo 8 }

		
--  1.3.6.1.4.1.10428 9 1.102.12.2.2.1.1.9
		-- 1.3.6.1.4.1.10428 9 1.102.12.2.2.1.1.9
		fkV2IgmpInfoSnoopMaxResponseTime OBJECT-TYPE
			SYNTAX Integer32 (0..31744)
			MAX-ACCESS read-only
			STATUS current
			DESCRIPTION
				"The maximum query response time advertised in queries on this interface."
			::= { fkV2IgmpInfo 9 }

		
--  1.3.6.1.4.1.10428 9 1.102.12.2.2.1.1.10
		-- 1.3.6.1.4.1.10428 9 1.102.12.2.2.1.1.10
		fkV2IgmpInfoSnoopLastMembQueryIntvl OBJECT-TYPE
			SYNTAX Unsigned32 (0..31744)
			MAX-ACCESS read-only
			STATUS current
			DESCRIPTION
				"The Last Member Qury Interval is the Max Response Time inserted into Group-Specific Queries sent in response to Leave Group messages, and is also the amount of time Between Group-Specific Query messages. This value may be tuned to modify the leave latency of the network. A reduced value results in reduced time to detect the loss of the last member of a group. The value of this object is irrelevant if mgmdRouterInterfaceVersion is 1"
			::= { fkV2IgmpInfo 10 }

		
--  1.3.6.1.4.1.10428 9 1.102.12.2.2.1.1.11
		-- 1.3.6.1.4.1.10428 9 1.102.12.2.2.1.1.11
		fkV2IgmpInfoTcnFloodActivity OBJECT-TYPE
			SYNTAX Boolean
			MAX-ACCESS read-only
			STATUS current
			DESCRIPTION
				"TRUE is multicast traffic will be flooded on all ports of the VLAN for TcnFloodQueryCount of IGMP General Queries upon receiving a Topology Change Notification (TCN) for the VLAN. FALSE is not flooding."
			::= { fkV2IgmpInfo 11 }

		
--  1.3.6.1.4.1.10428 9 1.102.12.2.2.1.1.12
		-- 1.3.6.1.4.1.10428 9 1.102.12.2.2.1.1.12
		fkV2IgmpInfoTcnQuerySolicitActivity OBJECT-TYPE
			SYNTAX Boolean
			MAX-ACCESS read-only
			STATUS current
			DESCRIPTION
				"This object specifies whether the device running IGMP Snooping will solicit IGMP General Queries from the Querier upon receiving a Topology Change Notification (TCN). The root device will always solicit IGMP General Queries on TCN irrespective of the value of this."
			::= { fkV2IgmpInfo 12 }

		
--  1.3.6.1.4.1.10428 9 1.102.12.2.2.1.1.13
		-- 1.3.6.1.4.1.10428 9 1.102.12.2.2.1.1.13
		fkV2IgmpInfoTcnFloodQueryCount OBJECT-TYPE
			SYNTAX INTEGER (1..10)
			MAX-ACCESS read-only
			STATUS current
			DESCRIPTION
				"This object specifies the flooding period for multicast traffic upon receiving Topology Change Notifications (TCN). IGMP Snooping will flood multicast traffic until this count number of IGMP General Queries are received by IGMP Snooping."
			::= { fkV2IgmpInfo 13 }

		
--  1.3.6.1.4.1.10428 9 1.102.12.2.2.1.1.14
		-- 1.3.6.1.4.1.10428 9 1.102.12.2.2.1.1.14
		fkV2IgmpInfoExplicitTracking OBJECT-TYPE
			SYNTAX Boolean
			MAX-ACCESS read-only
			STATUS current
			DESCRIPTION
				"In IGMPv3, it decide the device tracks reporters or not."
			::= { fkV2IgmpInfo 14 }

		
--  1.3.6.1.4.1.10428 9 1.102.12.2.2.1.1.15
		-- 1.3.6.1.4.1.10428 9 1.102.12.2.2.1.1.15
		fkV2IgmpInfoMvrActivity OBJECT-TYPE
			SYNTAX Boolean
			MAX-ACCESS read-only
			STATUS current
			DESCRIPTION
				"The active state of MVR."
			::= { fkV2IgmpInfo 15 }

		
--  1.3.6.1.4.1.10428 9 1.102.12.2.2.1.1.16
		-- 1.3.6.1.4.1.10428 9 1.102.12.2.2.1.1.16
		fkV2IgmpInfoTcnQueryInterval OBJECT-TYPE
			SYNTAX INTEGER (0 | 1..1800)
			MAX-ACCESS read-only
			STATUS current
			DESCRIPTION
				"TCN query interval"
			::= { fkV2IgmpInfo 16 }

		
--  1.3.6.1.4.1.10428 9 1.102.12.2.2.1.1.17
		-- 1.3.6.1.4.1.10428 9 1.102.12.2.2.1.1.17
		fkV2IgmpInfoTcnQuerySolicitAddress OBJECT-TYPE
			SYNTAX IpAddress
			MAX-ACCESS read-only
			STATUS current
			DESCRIPTION
				"The source adddress of TCN solicit"
			::= { fkV2IgmpInfo 17 }

		
--  1.3.6.1.4.1.10428 9 1.102.12.2.2.1.1.18
		-- 1.3.6.1.4.1.10428 9 1.102.12.2.2.1.1.18
		fkV2IgmpInfoVerifyTTL OBJECT-TYPE
			SYNTAX Boolean
			MAX-ACCESS read-only
			STATUS current
			DESCRIPTION
				"The activie state of Verify-TTL"
			::= { fkV2IgmpInfo 18 }

		
		-- 1.3.6.1.4.1.10428 9 1.102.12.2.2.1.1.19
		fkV2IgmpInfoSnoopExplicitTrackingMacBased OBJECT-TYPE
			SYNTAX Boolean
			MAX-ACCESS read-only
			STATUS current
			DESCRIPTION
				"In IGMPv3, it decide the mac-based device tracks reporters or not."
			::= { fkV2IgmpInfo 19 }

		
		-- 1.3.6.1.4.1.10428 9 1.102.12.2.2.1.1.20
		fkV2IgmpInfoSnoopTcnQueryGeneralStatus OBJECT-TYPE
			SYNTAX INTEGER
				{
				disable(0),
				enable(1)
				}
			MAX-ACCESS read-only
			STATUS current
			DESCRIPTION
				"The status is indicated Generating  an IGMPv2 gereral query. "
			::= { fkV2IgmpInfo 20 }

		
		-- 1.3.6.1.4.1.10428 9 1.102.12.2.2.1.1.21
		fkV2IgmpInfoSnoopTcnQueryGeneralMaxResponseTime OBJECT-TYPE
			SYNTAX Integer32 (0..25)
			MAX-ACCESS read-only
			STATUS current
			DESCRIPTION
				"IGMP Snooping general query maximum response time (1-25sec, Default:1sec).
				when the TCN query general status is disable, max reponse time is 0."
			::= { fkV2IgmpInfo 21 }

		
--  1.3.6.1.4.1.10428 9 1.102.12.2.2.1.1.1
		-- 1.3.6.1.4.1.10428 9 1.102.12.2.2.1.1.22
		fkV2IgmpinfoSnoopMrouterCpu OBJECT-TYPE
			SYNTAX INTEGER
				{
				disable(0),
				enable(1)
				}
			MAX-ACCESS read-only
			STATUS current
			DESCRIPTION
				"fkV2IgmpinfoSnoopMrouterCpu"
			::= { fkV2IgmpInfo 22 }

		
		-- 1.3.6.1.4.1.10428 9 1.102.12.2.2.1.1.23
		fkV2IgmpInfoMaxGroupSystemCnt OBJECT-TYPE
			SYNTAX Unsigned32 (1..2147483647)
			MAX-ACCESS read-only
			STATUS current
			DESCRIPTION
				"The max group system count."
			::= { fkV2IgmpInfo 23 }

		
		-- 1.3.6.1.4.1.10428 9 1.102.12.2.2.1.1.24
		fkV2IgmpInfoSnoopMRtLearningMode OBJECT-TYPE
			SYNTAX INTEGER
				{
				none(0),
				pim(1)
				}
			MAX-ACCESS read-only
			STATUS current
			DESCRIPTION
				"This object specifies the multicast router port learning method for IGMP Snooping
				
				    none(0): don't learning, Only use static router ports.
				
				    pim(1) : Protocol Independent Multicast.
				"
			::= { fkV2IgmpInfo 24 }

		
		-- 1.3.6.1.4.1.10428 9 1.102.12.2.2.1.1.25
		fkV2IgmpInfoSnoopQuerierAddress OBJECT-TYPE
			SYNTAX IpAddress
			MAX-ACCESS read-only
			STATUS current
			DESCRIPTION
				"Description."
			::= { fkV2IgmpInfo 25 }

		
--  IGMP Configuration Control
-- 1.3.6.1.4.1.10428 9 1.102.12.2.2.1.2
		-- 1.3.6.1.4.1.10428 9 1.102.12.2.2.1.2
		fkV2IgmpInfoControl OBJECT IDENTIFIER ::= { fkV2IgmpBase 2 }

		
--  1.3.6.1.4.1.10428 9 1.102.12.2.2.1.2.1
		-- 1.3.6.1.4.1.10428 9 1.102.12.2.2.1.2.1
		fkV2IgmpInfoControlRequest OBJECT-TYPE
			SYNTAX INTEGER
				{
				setIgmpInfoSnoopActivity(1),
				setIgmpInfoQuerierProfile(2),
				setIgmpInfoTcnProfile(3),
				setIgmpInfoMvrActivity(4),
				setIgmpInfoTcnProfileQueryInterval(5),
				setIgmpInfoTcnProfileSolicitAddr(6),
				setIgmpInfoVerifyTTL(7),
				setIgmpInfoSnoopExplicitTrackingMacBased(8),
				setIgmpInfoSnoopTcnGeneral(9),
				setIgmpInfoSnoopMrouterCpu(10),
				setIgmpInfoMaxGroupSystemCnt(11),
				delIgmpInfoMaxGroupSystemCnt(12),
				setIgmpInfoSnoopMrouterProfile(13)
				}
			MAX-ACCESS read-write
			STATUS current
			DESCRIPTION
				" The request of a user command"
			::= { fkV2IgmpInfoControl 1 }

		
--  1.3.6.1.4.1.10428 9 1.102.12.2.2.1.2.2
		-- 1.3.6.1.4.1.10428 9 1.102.12.2.2.1.2.2
		fkV2IgmpInfoControlStatus OBJECT-TYPE
			SYNTAX FkControlStatusType
			MAX-ACCESS read-only
			STATUS current
			DESCRIPTION
				" The status of user command"
			::= { fkV2IgmpInfoControl 2 }

		
--  1.3.6.1.4.1.10428 9 1.102.12.2.2.1.2.3
		-- 1.3.6.1.4.1.10428 9 1.102.12.2.2.1.2.3
		fkV2IgmpInfoControlTimer OBJECT-TYPE
			SYNTAX Gauge32
			MAX-ACCESS read-write
			STATUS current
			DESCRIPTION
				" The maximum time for the manager for a long running user command"
			::= { fkV2IgmpInfoControl 3 }

		
--  1.3.6.1.4.1.10428 9 1.102.12.2.2.1.2.4
		-- 1.3.6.1.4.1.10428 9 1.102.12.2.2.1.2.4
		fkV2IgmpInfoControlTimeStamp OBJECT-TYPE
			SYNTAX TimeStamp
			MAX-ACCESS read-only
			STATUS current
			DESCRIPTION
				" The time stamp of the last command(end of command)"
			::= { fkV2IgmpInfoControl 4 }

		
--  1.3.6.1.4.1.10428 9 1.102.12.2.2.1.2.5
		-- 1.3.6.1.4.1.10428 9 1.102.12.2.2.1.2.5
		fkV2IgmpInfoControlReqResult OBJECT-TYPE
			SYNTAX FkControlRequestResultType
			MAX-ACCESS read-only
			STATUS current
			DESCRIPTION
				" The result of the last user command
				"
			::= { fkV2IgmpInfoControl 5 }

		
--  1.3.6.1.4.1.10428 9 1.102.12.2.2.1.2.6
		-- 1.3.6.1.4.1.10428 9 1.102.12.2.2.1.2.6
		fkV2IgmpInfoControlSnoopActivity OBJECT-TYPE
			SYNTAX Boolean
			MAX-ACCESS read-write
			STATUS current
			DESCRIPTION
				"This object indicates whether IGMP Snooping has been enabled for the system."
			::= { fkV2IgmpInfoControl 6 }

		
--  1.3.6.1.4.1.10428 9 1.102.12.2.2.1.2.7
		-- 1.3.6.1.4.1.10428 9 1.102.12.2.2.1.2.7
		fkV2IgmpInfoControlSnoopVersion OBJECT-TYPE
			SYNTAX INTEGER
				{
				dynamic(0),
				igmpV1(1),
				igmpV2(2),
				igmpV3(3)
				}
			MAX-ACCESS read-write
			STATUS current
			DESCRIPTION
				"The maximum version of IGMP supported."
			::= { fkV2IgmpInfoControl 7 }

		
--  1.3.6.1.4.1.10428 9 1.102.12.2.2.1.2.8
		-- 1.3.6.1.4.1.10428 9 1.102.12.2.2.1.2.8
		fkV2IgmpInfoControlSnoopFastLeave OBJECT-TYPE
			SYNTAX Boolean
			MAX-ACCESS read-write
			STATUS current
			DESCRIPTION
				"This object indicates whether Fast-Leave mechanism has been configured to be enabled in the system. If Fast-Leave is enabled in the switch, IGMP Snooping will prune the port on which an IGMP leave message has been received without waiting for the Group Specific Query to timeout to determine whether there are any more hosts on that port for that group. If the value of fkV2IgmpInfoSnoopVersion is not 3, this object will not have any effect."
			::= { fkV2IgmpInfoControl 8 }

		
--  1.3.6.1.4.1.10428 9 1.102.12.2.2.1.2.9
		-- 1.3.6.1.4.1.10428 9 1.102.12.2.2.1.2.9
		fkV2IgmpInfoControlSnoopFastBlock OBJECT-TYPE
			SYNTAX Boolean
			MAX-ACCESS read-write
			STATUS current
			DESCRIPTION
				"The object indicates whether Fast-Block mechanism has been enabled for the system. This object only has effect if the value of fkV2IgmpInfoSnoopVersion is 3."
			::= { fkV2IgmpInfoControl 9 }

		
--  1.3.6.1.4.1.10428 9 1.102.12.2.2.1.2.10
		-- 1.3.6.1.4.1.10428 9 1.102.12.2.2.1.2.10
		fkV2IgmpInfoControlSnoopReportSuppression OBJECT-TYPE
			SYNTAX Boolean
			MAX-ACCESS read-write
			STATUS current
			DESCRIPTION
				"When this object is set to 'true', IGMP Snooping will suppress duplicate IGMP Reports.  When this object is set to 'false', all IGMP Reports are forwarded to all multicast routers. Alias is IGMP Snooping Proxy."
			::= { fkV2IgmpInfoControl 10 }

		
--  1.3.6.1.4.1.10428 9 1.102.12.2.2.1.2.11
		-- 1.3.6.1.4.1.10428 9 1.102.12.2.2.1.2.11
		fkV2IgmpInfoControlSnoopQuerierActivity OBJECT-TYPE
			SYNTAX Boolean
			MAX-ACCESS read-write
			STATUS current
			DESCRIPTION
				"The object indicates whether the device will participate in the IGMP Querier election. If the object is set to 'true', the device will participate to an election process to be a Querier."
			::= { fkV2IgmpInfoControl 11 }

		
--  1.3.6.1.4.1.10428 9 1.102.12.2.2.1.2.12
		-- 1.3.6.1.4.1.10428 9 1.102.12.2.2.1.2.12
		fkV2IgmpInfoControlSnoopQueryInterval OBJECT-TYPE
			SYNTAX Unsigned32 (1..1800)
			MAX-ACCESS read-write
			STATUS current
			DESCRIPTION
				"The frequency at which IGMP packets are transmitted on this interface."
			::= { fkV2IgmpInfoControl 12 }

		
--  1.3.6.1.4.1.10428 9 1.102.12.2.2.1.2.13
		-- 1.3.6.1.4.1.10428 9 1.102.12.2.2.1.2.13
		fkV2IgmpInfoControlSnoopMaxResponseTime OBJECT-TYPE
			SYNTAX Unsigned32 (1..25)
			MAX-ACCESS read-write
			STATUS current
			DESCRIPTION
				"The maximum query response time advertised in queries on this interface."
			::= { fkV2IgmpInfoControl 13 }

		
--  1.3.6.1.4.1.10428 9 1.102.12.2.2.1.2.14
		-- 1.3.6.1.4.1.10428 9 1.102.12.2.2.1.2.14
		fkV2IgmpInfoControlSnoopLastMembQueryIntvl OBJECT-TYPE
			SYNTAX Unsigned32 (100..10000)
			MAX-ACCESS read-write
			STATUS current
			DESCRIPTION
				"The Last Member Qury Interval is the Max Response Time inserted into Group-Specific Queries sent in response to Leave Group messages, and is also the amount of time Between Group-Specific Query messages. This value may be tuned to modify the leave latency of the network. A reduced value results in reduced time to detect the loss of the last member of a group. The value of this object is irrelevant if mgmdRouterInterfaceVersion is 1"
			::= { fkV2IgmpInfoControl 14 }

		
--  1.3.6.1.4.1.10428 9 1.102.12.2.2.1.2.15
		-- 1.3.6.1.4.1.10428 9 1.102.12.2.2.1.2.15
		fkV2IgmpInfoControlTcnFloodActivity OBJECT-TYPE
			SYNTAX Boolean
			MAX-ACCESS read-write
			STATUS current
			DESCRIPTION
				"TRUE is multicast traffic will be flooded on all ports of the VLAN for TcnFloodQueryCount of IGMP General Queries upon receiving a Topology Change Notification (TCN) for the VLAN. FALSE is not flooding."
			::= { fkV2IgmpInfoControl 15 }

		
--  1.3.6.1.4.1.10428 9 1.102.12.2.2.1.2.16
		-- 1.3.6.1.4.1.10428 9 1.102.12.2.2.1.2.16
		fkV2IgmpInfoControlTcnQuerySolicitActivity OBJECT-TYPE
			SYNTAX Boolean
			MAX-ACCESS read-write
			STATUS current
			DESCRIPTION
				"This object specifies whether the device running IGMP Snooping will solicit IGMP General Queries from the Querier upon receiving a Topology Change Notification (TCN). The root device will always solicit IGMP General Queries on TCN irrespective of the value of this."
			::= { fkV2IgmpInfoControl 16 }

		
--  1.3.6.1.4.1.10428 9 1.102.12.2.2.1.2.17
		-- 1.3.6.1.4.1.10428 9 1.102.12.2.2.1.2.17
		fkV2IgmpInfoControlTcnFloodQueryCount OBJECT-TYPE
			SYNTAX Integer32 (1..10)
			MAX-ACCESS read-write
			STATUS current
			DESCRIPTION
				"This object specifies the flooding period for multicast traffic upon receiving Topology Change Notifications (TCN). IGMP Snooping will flood multicast traffic until this count number of IGMP General Queries are received by IGMP Snooping."
			DEFVAL { 2 }
			::= { fkV2IgmpInfoControl 17 }

		
--  1.3.6.1.4.1.10428 9 1.102.12.2.2.1.2.18
		-- 1.3.6.1.4.1.10428 9 1.102.12.2.2.1.2.18
		fkV2IgmpInfoControlExplicitTracking OBJECT-TYPE
			SYNTAX Boolean
			MAX-ACCESS read-write
			STATUS current
			DESCRIPTION
				"In IGMPv3, it decide the device tracks reporters or not."
			::= { fkV2IgmpInfoControl 18 }

		
--  1.3.6.1.4.1.10428 9 1.102.12.2.2.1.2.19
		-- 1.3.6.1.4.1.10428 9 1.102.12.2.2.1.2.19
		fkV2IgmpInfoControlMvrActivity OBJECT-TYPE
			SYNTAX Boolean
			MAX-ACCESS read-write
			STATUS current
			DESCRIPTION
				"The active state of MVR."
			::= { fkV2IgmpInfoControl 19 }

		
--  1.3.6.1.4.1.10428 9 1.102.12.2.2.1.2.20
		-- 1.3.6.1.4.1.10428 9 1.102.12.2.2.1.2.20
		fkV2IgmpInfoControlTcnQueryInterval OBJECT-TYPE
			SYNTAX INTEGER (0 | 1..1800)
			MAX-ACCESS read-write
			STATUS current
			DESCRIPTION
				"TCN query interval"
			::= { fkV2IgmpInfoControl 20 }

		
--  1.3.6.1.4.1.10428 9 1.102.12.2.2.1.2.21
		-- 1.3.6.1.4.1.10428 9 1.102.12.2.2.1.2.21
		fkV2IgmpInfoControlTcnQuerySolicitAddress OBJECT-TYPE
			SYNTAX IpAddress
			MAX-ACCESS read-write
			STATUS current
			DESCRIPTION
				"The source adddress of TCN solicit"
			::= { fkV2IgmpInfoControl 21 }

		
--  1.3.6.1.4.1.10428 9 1.102.12.2.2.1.2.22
		-- 1.3.6.1.4.1.10428 9 1.102.12.2.2.1.2.22
		fkV2IgmpInfoControlVerifyTTL OBJECT-TYPE
			SYNTAX Boolean
			MAX-ACCESS read-write
			STATUS current
			DESCRIPTION
				"The activie state of Verify-TTL"
			::= { fkV2IgmpInfoControl 22 }

		
		-- 1.3.6.1.4.1.10428 9 1.102.12.2.2.1.2.23
		fkV2IgmpInfoControlSnoopExplicitTrackingMacBased OBJECT-TYPE
			SYNTAX Boolean
			MAX-ACCESS read-write
			STATUS current
			DESCRIPTION
				"In IGMPv3, it decide the mac-based device tracks reporters or not."
			::= { fkV2IgmpInfoControl 23 }

		
		-- 1.3.6.1.4.1.10428 9 1.102.12.2.2.1.2.24
		fkV2IgmpInfoControlSnoopTcnQueryGeneralStatus OBJECT-TYPE
			SYNTAX INTEGER
				{
				disable(0),
				enable(1)
				}
			MAX-ACCESS read-write
			STATUS current
			DESCRIPTION
				"The status is indicated Generating  an IGMPv2 gereral query. "
			::= { fkV2IgmpInfoControl 24 }

		
		-- 1.3.6.1.4.1.10428 9 1.102.12.2.2.1.2.25
		fkV2IgmpInfoControlSnoopTcnQueryGeneralMaxResponseTime OBJECT-TYPE
			SYNTAX Integer32 (1..25)
			MAX-ACCESS read-write
			STATUS current
			DESCRIPTION
				"IGMP Snooping general query maximum response time (1-25sec, Default:1sec)."
			::= { fkV2IgmpInfoControl 25 }

		
--  1.3.6.1.4.1.10428 9 1.102.12.2.2.1.1.1
		-- 1.3.6.1.4.1.10428 9 1.102.12.2.2.1.2.26
		fkV2IgmpinfoControlSnoopMrouterCpu OBJECT-TYPE
			SYNTAX INTEGER
				{
				disable(0),
				enable(1)
				}
			MAX-ACCESS read-write
			STATUS current
			DESCRIPTION
				"fkV2IgmpinfoSnoopMrouterCpu"
			::= { fkV2IgmpInfoControl 26 }

		
		-- 1.3.6.1.4.1.10428 9 1.102.12.2.2.1.2.27
		fkV2IgmpInfoControlMaxGroupSystemCnt OBJECT-TYPE
			SYNTAX Unsigned32 (1..2147483647)
			MAX-ACCESS read-write
			STATUS current
			DESCRIPTION
				"The max group system count."
			::= { fkV2IgmpInfoControl 27 }

		
		-- 1.3.6.1.4.1.10428 9 1.102.12.2.2.1.2.28
		fkV2IgmpInfoControlSnoopMRtLearningMode OBJECT-TYPE
			SYNTAX INTEGER
				{
				none(0),
				pim(1)
				}
			MAX-ACCESS read-only
			STATUS current
			DESCRIPTION
				"This object specifies the multicast router port learning method for IGMP Snooping
				
				    none(0): don't learning, Only use static router ports.
				
				    pim(1) : Protocol Independent Multicast.
				"
			::= { fkV2IgmpInfoControl 28 }

		
		-- 1.3.6.1.4.1.10428 9 1.102.12.2.2.1.2.29
		fkV2IgmpInfoControlSnoopQuerierAddress OBJECT-TYPE
			SYNTAX IpAddress
			MAX-ACCESS read-write
			STATUS current
			DESCRIPTION
				"Description."
			::= { fkV2IgmpInfoControl 29 }

		
--  IGMP Configuration Notification
-- 1.3.6.1.4.1.10428 9 1.102.12.2.2.1.3
		-- 1.3.6.1.4.1.10428 9 1.102.12.2.2.1.3
		fkV2IgmpInfoNotification OBJECT IDENTIFIER ::= { fkV2IgmpBase 3 }

		
--  1.3.6.1.4.1.10428 9 1.102.12.2.2.1.3.1
		-- 1.3.6.1.4.1.10428 9 1.102.12.2.2.1.3.1
		fkV2IgmpInfoSnoopActivityChanged NOTIFICATION-TYPE
			OBJECTS { fkV2IgmpInfoControlRequest, fkV2IgmpInfoControlReqResult, fkV2IgmpInfoControlTimeStamp, fkV2IgmpInfoSnoopActivity, fkV2IgmpInfoSnoopVersion, 
				fkV2IgmpInfoSnoopVersionMode, fkV2IgmpInfoSnoopFastLeave, fkV2IgmpInfoSnoopFastBlock, fkV2IgmpInfoSnoopReportSuppression, fkV2IgmpInfoExplicitTracking
				 }
			STATUS current
			DESCRIPTION 
				"setMcastInfoMvrActivity"
			::= { fkV2IgmpInfoNotification 1 }

		
--  1.3.6.1.4.1.10428 9 1.102.12.2.2.1.3.2
		-- 1.3.6.1.4.1.10428 9 1.102.12.2.2.1.3.2
		fkV2IgmpInfoQuerierProfileChanged NOTIFICATION-TYPE
			OBJECTS { fkV2IgmpInfoControlRequest, fkV2IgmpInfoControlTimeStamp, fkV2IgmpInfoControlReqResult, fkV2IgmpInfoSnoopQuerierActivity, fkV2IgmpInfoSnoopQueryInterval, 
				fkV2IgmpInfoSnoopMaxResponseTime, fkV2IgmpInfoSnoopLastMembQueryIntvl, fkV2IgmpInfoControlSnoopQuerierAddress }
			STATUS current
			DESCRIPTION 
				"Description."
			::= { fkV2IgmpInfoNotification 2 }

		
--  1.3.6.1.4.1.10428 9 1.102.12.2.2.1.3.3
		-- 1.3.6.1.4.1.10428 9 1.102.12.2.2.1.3.3
		fkV2IgmpInfoTcnProfileChanged NOTIFICATION-TYPE
			OBJECTS { fkV2IgmpInfoControlRequest, fkV2IgmpInfoControlReqResult, fkV2IgmpInfoControlTimeStamp, fkV2IgmpInfoTcnFloodActivity, fkV2IgmpInfoTcnQuerySolicitActivity, 
				fkV2IgmpInfoTcnFloodQueryCount }
			STATUS current
			DESCRIPTION 
				"Description."
			::= { fkV2IgmpInfoNotification 3 }

		
--  1.3.6.1.4.1.10428 9 1.102.12.2.2.1.3.4
		-- 1.3.6.1.4.1.10428 9 1.102.12.2.2.1.3.4
		fkV2IgmpInfoMvrActivityChanged NOTIFICATION-TYPE
			OBJECTS { fkV2IgmpInfoControlRequest, fkV2IgmpInfoControlReqResult, fkV2IgmpInfoControlTimeStamp, fkV2IgmpInfoMvrActivity }
			STATUS current
			DESCRIPTION 
				"setMcastInfoMvrActivity"
			::= { fkV2IgmpInfoNotification 4 }

		
--  1.3.6.1.4.1.10428 9 1.102.12.2.2.1.3.5
		-- 1.3.6.1.4.1.10428 9 1.102.12.2.2.1.3.5
		fkV2IgmpInfoTcnProfileQueryIntervalChanged NOTIFICATION-TYPE
			OBJECTS { fkV2IgmpInfoControlRequest, fkV2IgmpInfoControlTimeStamp, fkV2IgmpInfoControlReqResult, fkV2IgmpInfoTcnQueryInterval }
			STATUS current
			DESCRIPTION 
				"Description."
			::= { fkV2IgmpInfoNotification 5 }

		
--  1.3.6.1.4.1.10428 9 1.102.12.2.2.1.3.6
		-- 1.3.6.1.4.1.10428 9 1.102.12.2.2.1.3.6
		fkV2IgmpInfoTcnProfileSolicitAddressChanged NOTIFICATION-TYPE
			OBJECTS { fkV2IgmpInfoControlRequest, fkV2IgmpInfoControlTimeStamp, fkV2IgmpInfoControlReqResult, fkV2IgmpInfoTcnQuerySolicitAddress }
			STATUS current
			DESCRIPTION 
				"Description."
			::= { fkV2IgmpInfoNotification 6 }

		
--  1.3.6.1.4.1.10428 9 1.102.12.2.2.1.3.7
		-- 1.3.6.1.4.1.10428 9 1.102.12.2.2.1.3.7
		fkV2IgmpInfoVerifyTTLChanged NOTIFICATION-TYPE
			OBJECTS { fkV2IgmpInfoControlRequest, fkV2IgmpInfoControlTimeStamp, fkV2IgmpInfoControlReqResult, fkV2IgmpInfoVerifyTTL }
			STATUS current
			DESCRIPTION 
				"Description."
			::= { fkV2IgmpInfoNotification 7 }

		
		-- 1.3.6.1.4.1.10428 9 1.102.12.2.2.1.3.8
		fkV2IgmpInfoSnoopExplicitTrackingMacBasedChanged NOTIFICATION-TYPE
			OBJECTS { fkV2IgmpInfoControlRequest, fkV2IgmpInfoControlTimeStamp, fkV2IgmpInfoControlReqResult, fkV2IgmpInfoControlSnoopExplicitTrackingMacBased }
			STATUS current
			DESCRIPTION 
				"Description."
			::= { fkV2IgmpInfoNotification 8 }

		
		-- 1.3.6.1.4.1.10428 9 1.102.12.2.2.1.3.9
		fkV2IgmpInfoSnoopTcnQueryGeneralChanged NOTIFICATION-TYPE
			OBJECTS { fkV2IgmpInfoControlRequest, fkV2IgmpInfoControlTimeStamp, fkV2IgmpInfoControlReqResult, fkV2IgmpInfoSnoopTcnQueryGeneralStatus, fkV2IgmpInfoSnoopTcnQueryGeneralMaxResponseTime
				 }
			STATUS current
			DESCRIPTION 
				"setIgmpInfoSnoopTcnGeneral"
			::= { fkV2IgmpInfoNotification 9 }

		
		-- 1.3.6.1.4.1.10428 9 1.102.12.2.2.1.3.10
		fkV2IgmpinfoSnoopMrouterCpuChanged NOTIFICATION-TYPE
			OBJECTS { fkV2IgmpInfoControlRequest, fkV2IgmpInfoControlTimeStamp, fkV2IgmpInfoControlReqResult, fkV2IgmpinfoControlSnoopMrouterCpu }
			STATUS current
			DESCRIPTION 
				"setIgmpInfoSnoopMrouterCpu"
			::= { fkV2IgmpInfoNotification 10 }

		
		-- 1.3.6.1.4.1.10428 9 1.102.12.2.2.1.3.11
		fkV2IgmpInfoMaxGroupSystemCntChanged NOTIFICATION-TYPE
			OBJECTS { fkV2IgmpInfoControlRequest, fkV2IgmpInfoControlTimeStamp, fkV2IgmpInfoControlReqResult, fkV2IgmpInfoControlMaxGroupSystemCnt }
			STATUS current
			DESCRIPTION 
				"setIgmpInfoMaxGroupSystemCnt"
			::= { fkV2IgmpInfoNotification 11 }

		
		-- 1.3.6.1.4.1.10428 9 1.102.12.2.2.1.3.12
		fkV2IgmpInfoMaxGroupSystemCntDeleted NOTIFICATION-TYPE
			OBJECTS { fkV2IgmpInfoControlRequest, fkV2IgmpInfoControlTimeStamp, fkV2IgmpInfoControlReqResult }
			STATUS current
			DESCRIPTION 
				"delIgmpInfoMaxGroupSystemCnt"
			::= { fkV2IgmpInfoNotification 12 }

		
		-- 1.3.6.1.4.1.10428 9 1.102.12.2.2.1.3.13
		fkV2IgmpInfoSnoopMRouteProfileChanged NOTIFICATION-TYPE
			OBJECTS { fkV2IgmpInfoControlRequest, fkV2IgmpInfoControlTimeStamp, fkV2IgmpInfoControlReqResult, fkV2IgmpInfoControlSnoopMRtLearningMode }
			STATUS current
			DESCRIPTION 
				"setIgmpInfoSnoopMrouterProfile"
			::= { fkV2IgmpInfoNotification 13 }

		
--  IGMP Helper
-- 1.3.6.1.4.1.10428 9 1.102.12.2.2.2
		-- 1.3.6.1.4.1.10428 9 1.102.12.2.2.2
		fkV2IgmpHelper OBJECT IDENTIFIER ::= { fkV2Igmp 2 }

		
--  IGMP Helper VLAN
-- 1.3.6.1.4.1.10428 9 1.102.12.2.2.2.1
		-- 1.3.6.1.4.1.10428 9 1.102.12.2.2.2.1
		fkV2IghVlan OBJECT IDENTIFIER ::= { fkV2IgmpHelper 1 }

		
--  IGMP Helper VLAN Table
-- 1.3.6.1.4.1.10428 9 1.102.12.2.2.2.1.1
		-- 1.3.6.1.4.1.10428 9 1.102.12.2.2.2.1.1
		fkV2IghVlanTable OBJECT-TYPE
			SYNTAX SEQUENCE OF FkV2IghVlanEntry
			MAX-ACCESS not-accessible
			STATUS current
			DESCRIPTION
				"IGH vlan table."
			::= { fkV2IghVlan 1 }

		
--  IGMP Helper VLAN Entry
-- 1.3.6.1.4.1.10428 9 1.102.12.2.2.2.1.1.1
		-- 1.3.6.1.4.1.10428 9 1.102.12.2.2.2.1.1.1
		fkV2IghVlanEntry OBJECT-TYPE
			SYNTAX FkV2IghVlanEntry
			MAX-ACCESS not-accessible
			STATUS current
			DESCRIPTION
				"key: fkV2IghVlanIndex"
			INDEX { fkV2IghVlanIndex }
			::= { fkV2IghVlanTable 1 }

		
		FkV2IghVlanEntry ::=
			SEQUENCE { 
				fkV2IghVlanIndex
					INTEGER,
				fkV2IghVlanHelperAddress
					IpAddress,
				fkV2IghVlanOperAddress
					IpAddress
			 }

--  1.3.6.1.4.1.10428 9 1.102.12.2.2.2.1.1.1.1
		-- 1.3.6.1.4.1.10428 9 1.102.12.2.2.2.1.1.1.1
		fkV2IghVlanIndex OBJECT-TYPE
			SYNTAX INTEGER (1..4094)
			MAX-ACCESS read-only
			STATUS current
			DESCRIPTION
				"This object indicates the number of VLAN which is used in IGMP features.
				"
			::= { fkV2IghVlanEntry 1 }

		
--  1.3.6.1.4.1.10428 9 1.102.12.2.2.2.1.1.1.2
		-- 1.3.6.1.4.1.10428 9 1.102.12.2.2.2.1.1.1.2
		fkV2IghVlanHelperAddress OBJECT-TYPE
			SYNTAX IpAddress
			MAX-ACCESS read-only
			STATUS current
			DESCRIPTION
				"This object indicates the helper address of the VLAN is used in IGMP snooping TCN, MVR, Static Host (fkV2IghGroup), etc."
			::= { fkV2IghVlanEntry 2 }

		
--  1.3.6.1.4.1.10428 9 1.102.12.2.2.2.1.1.1.3
		-- 1.3.6.1.4.1.10428 9 1.102.12.2.2.2.1.1.1.3
		fkV2IghVlanOperAddress OBJECT-TYPE
			SYNTAX IpAddress
			MAX-ACCESS read-only
			STATUS current
			DESCRIPTION
				"Real source address used in IGMP report/leave message. It decided by fkV2IghVlanHelperAddress or interface address."
			::= { fkV2IghVlanEntry 3 }

		
--  IGMP Helper VLAN Control
-- 1.3.6.1.4.1.10428 9 1.102.12.2.2.2.1.2
		-- 1.3.6.1.4.1.10428 9 1.102.12.2.2.2.1.2
		fkV2IghVlanControl OBJECT IDENTIFIER ::= { fkV2IghVlan 2 }

		
--  1.3.6.1.4.1.10428 9 1.102.12.2.2.2.1.2.1
		-- 1.3.6.1.4.1.10428 9 1.102.12.2.2.2.1.2.1
		fkV2IghVlanControlRequest OBJECT-TYPE
			SYNTAX INTEGER { setIgmpHelperVlanProfile(1) }
			MAX-ACCESS read-write
			STATUS current
			DESCRIPTION
				"createMvrVlan(1), destroyMvrVlan(2) not supported because MVR VLANs is automatically added or/and deleted by adding or/and deleting MVR GROUPs."
			::= { fkV2IghVlanControl 1 }

		
--  1.3.6.1.4.1.10428 9 1.102.12.2.2.2.1.2.2
		-- 1.3.6.1.4.1.10428 9 1.102.12.2.2.2.1.2.2
		fkV2IghVlanControlStatus OBJECT-TYPE
			SYNTAX FkControlStatusType
			MAX-ACCESS read-only
			STATUS current
			DESCRIPTION
				"The status of a user command. "
			::= { fkV2IghVlanControl 2 }

		
--  1.3.6.1.4.1.10428 9 1.102.12.2.2.2.1.2.3
		-- 1.3.6.1.4.1.10428 9 1.102.12.2.2.2.1.2.3
		fkV2IghVlanControlTimer OBJECT-TYPE
			SYNTAX Gauge32
			MAX-ACCESS read-write
			STATUS current
			DESCRIPTION
				"The maximum wait time for the manager for a long running user command."
			::= { fkV2IghVlanControl 3 }

		
--  1.3.6.1.4.1.10428 9 1.102.12.2.2.2.1.2.4
		-- 1.3.6.1.4.1.10428 9 1.102.12.2.2.2.1.2.4
		fkV2IghVlanControlTimeStamp OBJECT-TYPE
			SYNTAX TimeStamp
			MAX-ACCESS read-only
			STATUS current
			DESCRIPTION
				"The time stamp of the last command (end of command)."
			::= { fkV2IghVlanControl 4 }

		
--  1.3.6.1.4.1.10428 9 1.102.12.2.2.2.1.2.5
		-- 1.3.6.1.4.1.10428 9 1.102.12.2.2.2.1.2.5
		fkV2IghVlanControlReqResult OBJECT-TYPE
			SYNTAX FkControlRequestResultType
			MAX-ACCESS read-only
			STATUS current
			DESCRIPTION
				"The result of the last user command."
			::= { fkV2IghVlanControl 5 }

		
--  1.3.6.1.4.1.10428 9 1.102.12.2.2.2.1.2.6
		-- 1.3.6.1.4.1.10428 9 1.102.12.2.2.2.1.2.6
		fkV2IghVlanControlIndex OBJECT-TYPE
			SYNTAX INTEGER (1..4094)
			MAX-ACCESS read-write
			STATUS current
			DESCRIPTION
				"This object indicates the VLAN number on which MVR feature is configured."
			::= { fkV2IghVlanControl 6 }

		
--  1.3.6.1.4.1.10428 9 1.102.12.2.2.2.1.2.7
		-- 1.3.6.1.4.1.10428 9 1.102.12.2.2.2.1.2.7
		fkV2IghVlanControlHelperAddress OBJECT-TYPE
			SYNTAX IpAddress
			MAX-ACCESS read-write
			STATUS current
			DESCRIPTION
				"This object indicates the helper address of VLAN number on which MVR feature is configured."
			::= { fkV2IghVlanControl 7 }

		
--  IGMP Helper VLAN Notification
-- 1.3.6.1.4.1.10428 9 1.102.12.2.2.2.1.3
		-- 1.3.6.1.4.1.10428 9 1.102.12.2.2.2.1.3
		fkV2IghVlanNotification OBJECT IDENTIFIER ::= { fkV2IghVlan 3 }

		
--  1.3.6.1.4.1.10428 9 1.102.12.2.2.2.1.3.1
		-- 1.3.6.1.4.1.10428 9 1.102.12.2.2.2.1.3.1
		fkV2IghVlanProfileChanged NOTIFICATION-TYPE
			OBJECTS { fkV2IghVlanControlRequest, fkV2IghVlanControlReqResult, fkV2IghVlanControlTimeStamp, fkV2IghVlanHelperAddress }
			STATUS current
			DESCRIPTION 
				"setMvr4VlanHelperAddress"
			::= { fkV2IghVlanNotification 1 }

		
--  IGMP Helper Group
-- 1.3.6.1.4.1.10428 9 1.102.12.2.2.2.2
		-- 1.3.6.1.4.1.10428 9 1.102.12.2.2.2.2
		fkV2IghJoin OBJECT IDENTIFIER ::= { fkV2IgmpHelper 2 }

		
--  IGMP Helper Group Table
-- 1.3.6.1.4.1.10428 9 1.102.12.2.2.2.2.1
		-- 1.3.6.1.4.1.10428 9 1.102.12.2.2.2.2.1
		fkV2IghJoinTable OBJECT-TYPE
			SYNTAX SEQUENCE OF FkV2IghJoinEntry
			MAX-ACCESS not-accessible
			STATUS current
			DESCRIPTION
				"IGH join table."
			::= { fkV2IghJoin 1 }

		
--  IGMP Helper Group Entry
-- 1.3.6.1.4.1.10428 9 1.102.12.2.2.2.2.1.1
		-- 1.3.6.1.4.1.10428 9 1.102.12.2.2.2.2.1.1
		fkV2IghJoinEntry OBJECT-TYPE
			SYNTAX FkV2IghJoinEntry
			MAX-ACCESS not-accessible
			STATUS current
			DESCRIPTION
				"key: fkV2IghVlanIndex, fkV2IghJoinAddress, fkV2IghJoinSource, fkV2IghJoinReporter, fkV2IghJoinPortIndex"
			INDEX { fkV2IghVlanIndex, fkV2IghJoinAddress, fkV2IghJoinSource, fkV2IghJoinReporter, fkV2IghJoinPortIndex
				 }
			::= { fkV2IghJoinTable 1 }

		
		FkV2IghJoinEntry ::=
			SEQUENCE { 
				fkV2IghJoinAddress
					IpAddress,
				fkV2IghJoinSource
					IpAddress,
				fkV2IghJoinPortIndex
					INTEGER,
				fkV2IghJoinReporter
					IpAddress
			 }

--  1.3.6.1.4.1.10428 9 1.102.12.2.2.2.2.1.1.1
		-- 1.3.6.1.4.1.10428 9 1.102.12.2.2.2.2.1.1.1
		fkV2IghJoinAddress OBJECT-TYPE
			SYNTAX IpAddress
			MAX-ACCESS read-only
			STATUS current
			DESCRIPTION
				"IP multicast address of multicast service (S,G) required by virtual (static or built-in) host to emulate."
			::= { fkV2IghJoinEntry 1 }

		
--  1.3.6.1.4.1.10428 9 1.102.12.2.2.2.2.1.1.2
		-- 1.3.6.1.4.1.10428 9 1.102.12.2.2.2.2.1.1.2
		fkV2IghJoinSource OBJECT-TYPE
			SYNTAX IpAddress
			MAX-ACCESS read-only
			STATUS current
			DESCRIPTION
				"Source address of multicast service (S,G) required by virtual host to emulate. For (*,G) entry, value is 0.0.0.0"
			::= { fkV2IghJoinEntry 2 }

		
--  1.3.6.1.4.1.10428 9 1.102.12.2.2.2.2.1.1.3
		-- 1.3.6.1.4.1.10428 9 1.102.12.2.2.2.2.1.1.3
		fkV2IghJoinPortIndex OBJECT-TYPE
			SYNTAX INTEGER (1..255)
			MAX-ACCESS read-only
			STATUS current
			DESCRIPTION
				"Index of port to what virtual host to emulate is connected."
			::= { fkV2IghJoinEntry 3 }

		
--  1.3.6.1.4.1.10428 9 1.102.12.2.2.2.2.1.1.4
		-- 1.3.6.1.4.1.10428 9 1.102.12.2.2.2.2.1.1.4
		fkV2IghJoinReporter OBJECT-TYPE
			SYNTAX IpAddress
			MAX-ACCESS read-only
			STATUS current
			DESCRIPTION
				"IP address of virtual host to emulate. If value is 0.0.0.0, fkV2IghVlanOperAddress is used as source address of IGMP control message"
			::= { fkV2IghJoinEntry 4 }

		
		-- 1.3.6.1.4.1.10428 9 1.102.12.2.2.2.2.2
		fkV2IghJoinControl OBJECT IDENTIFIER ::= { fkV2IghJoin 2 }

		
		-- 1.3.6.1.4.1.10428 9 1.102.12.2.2.2.2.2.1
		fkV2IghJoinControlRequest OBJECT-TYPE
			SYNTAX INTEGER
				{
				createIgmpHelperJoin(1),
				destroyIgmpHelperJoin(2),
				clearIgmpHelperJoin(3)
				}
			MAX-ACCESS read-write
			STATUS current
			DESCRIPTION
				"The request of a user command"
			::= { fkV2IghJoinControl 1 }

		
		-- 1.3.6.1.4.1.10428 9 1.102.12.2.2.2.2.2.2
		fkV2IghJoinControlStatus OBJECT-TYPE
			SYNTAX FkControlStatusType
			MAX-ACCESS read-only
			STATUS current
			DESCRIPTION
				"The status of a user command. "
			::= { fkV2IghJoinControl 2 }

		
		-- 1.3.6.1.4.1.10428 9 1.102.12.2.2.2.2.2.3
		fkV2IghJoinControlTimer OBJECT-TYPE
			SYNTAX Gauge32
			MAX-ACCESS read-write
			STATUS current
			DESCRIPTION
				"The maximum wait time for the manager for a long running user command."
			::= { fkV2IghJoinControl 3 }

		
		-- 1.3.6.1.4.1.10428 9 1.102.12.2.2.2.2.2.4
		fkV2IghJoinControlTimeStamp OBJECT-TYPE
			SYNTAX TimeStamp
			MAX-ACCESS read-only
			STATUS current
			DESCRIPTION
				"The time stamp of the last command (end of command)."
			::= { fkV2IghJoinControl 4 }

		
		-- 1.3.6.1.4.1.10428 9 1.102.12.2.2.2.2.2.5
		fkV2IghJoinControlReqResult OBJECT-TYPE
			SYNTAX FkControlRequestResultType
			MAX-ACCESS read-only
			STATUS current
			DESCRIPTION
				"The result of the last user command."
			::= { fkV2IghJoinControl 5 }

		
		-- 1.3.6.1.4.1.10428 9 1.102.12.2.2.2.2.2.6
		fkV2IghJoinControlVlanIndex OBJECT-TYPE
			SYNTAX INTEGER (0 | 1..4094)
			MAX-ACCESS read-write
			STATUS current
			DESCRIPTION
				"This object indicates the VLAN number on which MVR feature is configured.
				For all VLANs, the value is 0 (zero)"
			::= { fkV2IghJoinControl 6 }

		
		-- 1.3.6.1.4.1.10428 9 1.102.12.2.2.2.2.2.7
		fkV2IghJoinControlAddress OBJECT-TYPE
			SYNTAX IpAddress
			MAX-ACCESS read-write
			STATUS current
			DESCRIPTION
				"This object indicates the helper address of VLAN number on which MVR feature is configured.
				For all GROUPs, the value is 0.0.0.0"
			::= { fkV2IghJoinControl 7 }

		
		-- 1.3.6.1.4.1.10428 9 1.102.12.2.2.2.2.2.8
		fkV2IghJoinControlSource OBJECT-TYPE
			SYNTAX IpAddress
			MAX-ACCESS read-write
			STATUS current
			DESCRIPTION
				"Source address of multicast service (S,G) required by virtual host to emulate. For (*,G) entry, value is 0.0.0.0
				(not supported)"
			::= { fkV2IghJoinControl 8 }

		
		-- 1.3.6.1.4.1.10428 9 1.102.12.2.2.2.2.2.9
		fkV2IghJoinControlPortIndex OBJECT-TYPE
			SYNTAX INTEGER (1..255)
			MAX-ACCESS read-write
			STATUS current
			DESCRIPTION
				"Index of port to what virtual host to emulate is connected."
			::= { fkV2IghJoinControl 9 }

		
		-- 1.3.6.1.4.1.10428 9 1.102.12.2.2.2.2.2.10
		fkV2IghJoinControlReporter OBJECT-TYPE
			SYNTAX IpAddress
			MAX-ACCESS read-write
			STATUS current
			DESCRIPTION
				"IP address of virtual host to emulate. If value is 0.0.0.0, fkV2IghVlanOperAddress is used as source address of IGMP control message"
			::= { fkV2IghJoinControl 10 }

		
		-- 1.3.6.1.4.1.10428 9 1.102.12.2.2.2.2.3
		fkV2IghJoinNotification OBJECT IDENTIFIER ::= { fkV2IghJoin 3 }

		
		-- 1.3.6.1.4.1.10428 9 1.102.12.2.2.2.2.3.1
		fkV2IghJoinCreated NOTIFICATION-TYPE
			OBJECTS { fkV2IghJoinControlRequest, fkV2IghJoinControlTimeStamp, fkV2IghJoinControlReqResult, fkV2IghJoinControlVlanIndex, fkV2IghJoinControlAddress, 
				fkV2IghJoinControlSource, fkV2IghJoinControlReporter, fkV2IghJoinControlPortIndex }
			STATUS current
			DESCRIPTION 
				"Description."
			::= { fkV2IghJoinNotification 1 }

		
		-- 1.3.6.1.4.1.10428 9 1.102.12.2.2.2.2.3.2
		fkV2IghJoinDestroyed NOTIFICATION-TYPE
			OBJECTS { fkV2IghJoinControlRequest, fkV2IghJoinControlTimeStamp, fkV2IghJoinControlReqResult, fkV2IghJoinControlVlanIndex, fkV2IghJoinControlAddress, 
				fkV2IghJoinControlSource, fkV2IghJoinControlReporter, fkV2IghJoinControlPortIndex }
			STATUS current
			DESCRIPTION 
				"Description."
			::= { fkV2IghJoinNotification 2 }

		
		-- 1.3.6.1.4.1.10428 9 1.102.12.2.2.2.2.3.3
		fkV2IghJoinCleared NOTIFICATION-TYPE
			OBJECTS { fkV2IghJoinControlRequest, fkV2IghJoinControlTimeStamp, fkV2IghJoinControlReqResult, fkV2IghJoinControlVlanIndex, fkV2IghJoinControlAddress, 
				fkV2IghJoinControlSource }
			STATUS current
			DESCRIPTION 
				"Description."
			::= { fkV2IghJoinNotification 3 }

		
		-- 1.3.6.1.4.1.10428 9 1.102.12.2.2.2.3
		fkV2IghGroup OBJECT IDENTIFIER ::= { fkV2IgmpHelper 3 }

		
		-- 1.3.6.1.4.1.10428 9 1.102.12.2.2.2.3.1
		fkV2IghGroupTable OBJECT-TYPE
			SYNTAX SEQUENCE OF FkV2IghGroupEntry
			MAX-ACCESS not-accessible
			STATUS current
			DESCRIPTION
				"IGH group table."
			::= { fkV2IghGroup 1 }

		
		-- 1.3.6.1.4.1.10428 9 1.102.12.2.2.2.3.1.1
		fkV2IghGroupEntry OBJECT-TYPE
			SYNTAX FkV2IghGroupEntry
			MAX-ACCESS not-accessible
			STATUS current
			DESCRIPTION
				"key: fkV2IghVlanIndex, fkV2IghGroupAddress, fkV2IghGroupSource, fkV2IghGroupPortIndex"
			INDEX { fkV2IghVlanIndex, fkV2IghGroupAddress, fkV2IghGroupSource, fkV2IghGroupPortIndex }
			::= { fkV2IghGroupTable 1 }

		
		FkV2IghGroupEntry ::=
			SEQUENCE { 
				fkV2IghGroupAddress
					IpAddress,
				fkV2IghGroupSource
					IpAddress,
				fkV2IghGroupPortIndex
					INTEGER
			 }

		-- 1.3.6.1.4.1.10428 9 1.102.12.2.2.2.3.1.1.1
		fkV2IghGroupAddress OBJECT-TYPE
			SYNTAX IpAddress
			MAX-ACCESS read-only
			STATUS current
			DESCRIPTION
				"IP multicast address of multicast service (S,G) required by virtual 
				(static or built-in) host to emulate."
			::= { fkV2IghGroupEntry 1 }

		
		-- 1.3.6.1.4.1.10428 9 1.102.12.2.2.2.3.1.1.2
		fkV2IghGroupSource OBJECT-TYPE
			SYNTAX IpAddress
			MAX-ACCESS read-only
			STATUS current
			DESCRIPTION
				"Source address of multicast service (S,G) required by virtual host to emulate. For (*,G) entry, value is 0.0.0.0"
			::= { fkV2IghGroupEntry 2 }

		
		-- 1.3.6.1.4.1.10428 9 1.102.12.2.2.2.3.1.1.3
		fkV2IghGroupPortIndex OBJECT-TYPE
			SYNTAX INTEGER (1..255)
			MAX-ACCESS read-only
			STATUS current
			DESCRIPTION
				"Index of port to what virtual host to emulate is connected."
			::= { fkV2IghGroupEntry 3 }

		
		-- 1.3.6.1.4.1.10428 9 1.102.12.2.2.2.3.2
		fkV2IghGroupControl OBJECT IDENTIFIER ::= { fkV2IghGroup 2 }

		
		-- 1.3.6.1.4.1.10428 9 1.102.12.2.2.2.3.2.1
		fkV2IghGroupControlRequest OBJECT-TYPE
			SYNTAX INTEGER
				{
				createIgmpHelperGroup(1),
				destroyIgmpHelperGroup(2),
				clearIgmpHelperGroup(3)
				}
			MAX-ACCESS read-write
			STATUS current
			DESCRIPTION
				"createMvrVlan(1), destroyMvrVlan(2) not supported because MVR VLANs is automatically added or/and deleted by adding or/and deleting MVR GROUPs."
			::= { fkV2IghGroupControl 1 }

		
		-- 1.3.6.1.4.1.10428 9 1.102.12.2.2.2.3.2.2
		fkV2IghGroupControlStatus OBJECT-TYPE
			SYNTAX FkControlStatusType
			MAX-ACCESS read-only
			STATUS current
			DESCRIPTION
				"The status of a user command. "
			::= { fkV2IghGroupControl 2 }

		
		-- 1.3.6.1.4.1.10428 9 1.102.12.2.2.2.3.2.3
		fkV2IghGroupControlTimer OBJECT-TYPE
			SYNTAX Gauge32
			MAX-ACCESS read-write
			STATUS current
			DESCRIPTION
				"The maximum wait time for the manager for a long running user command."
			::= { fkV2IghGroupControl 3 }

		
		-- 1.3.6.1.4.1.10428 9 1.102.12.2.2.2.3.2.4
		fkV2IghGroupControlTimeStamp OBJECT-TYPE
			SYNTAX TimeStamp
			MAX-ACCESS read-only
			STATUS current
			DESCRIPTION
				"The time stamp of the last command (end of command)."
			::= { fkV2IghGroupControl 4 }

		
		-- 1.3.6.1.4.1.10428 9 1.102.12.2.2.2.3.2.5
		fkV2IghGroupControlReqResult OBJECT-TYPE
			SYNTAX FkControlRequestResultType
			MAX-ACCESS read-only
			STATUS current
			DESCRIPTION
				"The result of the last user command."
			::= { fkV2IghGroupControl 5 }

		
		-- 1.3.6.1.4.1.10428 9 1.102.12.2.2.2.3.2.6
		fkV2IghGroupControlVlanIndex OBJECT-TYPE
			SYNTAX INTEGER (0 | 1..4094)
			MAX-ACCESS read-write
			STATUS current
			DESCRIPTION
				"This object indicates the VLAN number on which MVR feature is configured.
				For all VLANs, the value is 0 (zero)"
			::= { fkV2IghGroupControl 6 }

		
		-- 1.3.6.1.4.1.10428 9 1.102.12.2.2.2.3.2.7
		fkV2IghGroupControlAddress OBJECT-TYPE
			SYNTAX IpAddress
			MAX-ACCESS read-write
			STATUS current
			DESCRIPTION
				"This object indicates the helper address of VLAN number on which MVR feature is configured.
				For all GROUPs, the value is 0.0.0.0"
			::= { fkV2IghGroupControl 7 }

		
		-- 1.3.6.1.4.1.10428 9 1.102.12.2.2.2.3.2.8
		fkV2IghGroupControlSource OBJECT-TYPE
			SYNTAX IpAddress
			MAX-ACCESS read-write
			STATUS current
			DESCRIPTION
				"Source address of multicast service (S,G) required by virtual host to emulate. For (*,G) entry, value is 0.0.0.0
				(not supported)"
			::= { fkV2IghGroupControl 8 }

		
		-- 1.3.6.1.4.1.10428 9 1.102.12.2.2.2.3.2.9
		fkV2IghGroupControlPortIndex OBJECT-TYPE
			SYNTAX INTEGER (1..255)
			MAX-ACCESS read-write
			STATUS current
			DESCRIPTION
				"Index of port to what virtual host to emulate is connected."
			::= { fkV2IghGroupControl 9 }

		
		-- 1.3.6.1.4.1.10428 9 1.102.12.2.2.2.3.3
		fkV2IghGroupNotification OBJECT IDENTIFIER ::= { fkV2IghGroup 3 }

		
		-- 1.3.6.1.4.1.10428 9 1.102.12.2.2.2.3.3.1
		fkV2IghGroupCreated NOTIFICATION-TYPE
			OBJECTS { fkV2IghGroupControlRequest, fkV2IghGroupControlTimeStamp, fkV2IghGroupControlReqResult, fkV2IghGroupControlVlanIndex, fkV2IghGroupControlAddress, 
				fkV2IghGroupControlSource, fkV2IghGroupControlPortIndex }
			STATUS current
			DESCRIPTION 
				"Description."
			::= { fkV2IghGroupNotification 1 }

		
		-- 1.3.6.1.4.1.10428 9 1.102.12.2.2.2.3.3.2
		fkV2IghGroupDestroyed NOTIFICATION-TYPE
			OBJECTS { fkV2IghGroupControlRequest, fkV2IghGroupControlTimeStamp, fkV2IghGroupControlReqResult, fkV2IghGroupControlVlanIndex, fkV2IghGroupControlAddress, 
				fkV2IghGroupControlSource, fkV2IghGroupControlPortIndex }
			STATUS current
			DESCRIPTION 
				"Description."
			::= { fkV2IghGroupNotification 2 }

		
		-- 1.3.6.1.4.1.10428 9 1.102.12.2.2.2.3.3.3
		fkV2IghGroupCleared NOTIFICATION-TYPE
			OBJECTS { fkV2IghGroupControlRequest, fkV2IghGroupControlTimeStamp, fkV2IghGroupControlReqResult, fkV2IghGroupControlVlanIndex, fkV2IghGroupControlAddress
				 }
			STATUS current
			DESCRIPTION 
				"Description."
			::= { fkV2IghGroupNotification 3 }

		
		-- 1.3.6.1.4.1.10428 9 1.102.12.2.2.2.4
		fkV2IghJoinProfile OBJECT IDENTIFIER ::= { fkV2IgmpHelper 4 }

		
		-- 1.3.6.1.4.1.10428 9 1.102.12.2.2.2.4.1
		fkV2IghJoinProfileTable OBJECT-TYPE
			SYNTAX SEQUENCE OF FkV2IghJoinProfileEntry
			MAX-ACCESS not-accessible
			STATUS current
			DESCRIPTION
				"IGH join profile table."
			::= { fkV2IghJoinProfile 1 }

		
		-- 1.3.6.1.4.1.10428 9 1.102.12.2.2.2.4.1.1
		fkV2IghJoinProfileEntry OBJECT-TYPE
			SYNTAX FkV2IghJoinProfileEntry
			MAX-ACCESS not-accessible
			STATUS current
			DESCRIPTION
				"key: fkV2IghVlanIndex, fkV2IghJoinProfilePortIndex, fkV2IghJoinProfileId, fkV2IghJoinProfileReporter"
			INDEX { fkV2IghVlanIndex, fkV2IghJoinProfilePortIndex, fkV2IghJoinProfileId, fkV2IghJoinProfileReporter }
			::= { fkV2IghJoinProfileTable 1 }

		
		FkV2IghJoinProfileEntry ::=
			SEQUENCE { 
				fkV2IghJoinProfilePortIndex
					INTEGER,
				fkV2IghJoinProfileId
					Integer32,
				fkV2IghJoinProfileReporter
					IpAddress
			 }

		-- 1.3.6.1.4.1.10428 9 1.102.12.2.2.2.4.1.1.1
		fkV2IghJoinProfilePortIndex OBJECT-TYPE
			SYNTAX INTEGER (1..255)
			MAX-ACCESS read-only
			STATUS current
			DESCRIPTION
				"Index of port to what virtual host to emulate is connected."
			::= { fkV2IghJoinProfileEntry 1 }

		
		-- 1.3.6.1.4.1.10428 9 1.102.12.2.2.2.4.1.1.2
		fkV2IghJoinProfileId OBJECT-TYPE
			SYNTAX Integer32 (1..65535)
			MAX-ACCESS read-only
			STATUS current
			DESCRIPTION
				"IGMP profile ID. Same as fkV2IgfProfileIndex"
			::= { fkV2IghJoinProfileEntry 2 }

		
		-- 1.3.6.1.4.1.10428 9 1.102.12.2.2.2.4.1.1.3
		fkV2IghJoinProfileReporter OBJECT-TYPE
			SYNTAX IpAddress
			MAX-ACCESS read-only
			STATUS current
			DESCRIPTION
				"IP address of virtual host to emulate. If value is 0.0.0.0, fkV2IghVlanOperAddress is used as source address of IGMP control message"
			::= { fkV2IghJoinProfileEntry 3 }

		
		-- 1.3.6.1.4.1.10428 9 1.102.12.2.2.2.4.2
		fkV2IghJoinProfileControl OBJECT IDENTIFIER ::= { fkV2IghJoinProfile 2 }

		
		-- 1.3.6.1.4.1.10428 9 1.102.12.2.2.2.4.2.1
		fkV2IghJoinProfileControlRequest OBJECT-TYPE
			SYNTAX INTEGER
				{
				createIgmpHelperJoinProfile(1),
				destroyIgmpHelperJoinProfile(2)
				}
			MAX-ACCESS read-write
			STATUS current
			DESCRIPTION
				"The request of a user command"
			::= { fkV2IghJoinProfileControl 1 }

		
		-- 1.3.6.1.4.1.10428 9 1.102.12.2.2.2.4.2.2
		fkV2IghJoinProfileControlStatus OBJECT-TYPE
			SYNTAX FkControlStatusType
			MAX-ACCESS read-only
			STATUS current
			DESCRIPTION
				"The status of a user command. "
			::= { fkV2IghJoinProfileControl 2 }

		
		-- 1.3.6.1.4.1.10428 9 1.102.12.2.2.2.4.2.3
		fkV2IghJoinProfileControlTimer OBJECT-TYPE
			SYNTAX Gauge32
			MAX-ACCESS read-write
			STATUS current
			DESCRIPTION
				"The maximum wait time for the manager for a long running user command."
			::= { fkV2IghJoinProfileControl 3 }

		
		-- 1.3.6.1.4.1.10428 9 1.102.12.2.2.2.4.2.4
		fkV2IghJoinProfileControlTimeStamp OBJECT-TYPE
			SYNTAX TimeStamp
			MAX-ACCESS read-only
			STATUS current
			DESCRIPTION
				"The time stamp of the last command (end of command)."
			::= { fkV2IghJoinProfileControl 4 }

		
		-- 1.3.6.1.4.1.10428 9 1.102.12.2.2.2.4.2.5
		fkV2IghJoinProfileControlReqResult OBJECT-TYPE
			SYNTAX FkControlRequestResultType
			MAX-ACCESS read-only
			STATUS current
			DESCRIPTION
				"The result of the last user command."
			::= { fkV2IghJoinProfileControl 5 }

		
		-- 1.3.6.1.4.1.10428 9 1.102.12.2.2.2.4.2.6
		fkV2IghJoinProfileControlVlanIndex OBJECT-TYPE
			SYNTAX INTEGER (0 | 1..4094)
			MAX-ACCESS read-write
			STATUS current
			DESCRIPTION
				"This object indicates the VLAN number on which MVR feature is configured.
				For all VLANs, the value is 0 (zero)"
			::= { fkV2IghJoinProfileControl 6 }

		
		-- 1.3.6.1.4.1.10428 9 1.102.12.2.2.2.4.2.7
		fkV2IghJoinProfileControlPortIndex OBJECT-TYPE
			SYNTAX INTEGER (1..255)
			MAX-ACCESS read-write
			STATUS current
			DESCRIPTION
				"port index"
			::= { fkV2IghJoinProfileControl 7 }

		
		-- 1.3.6.1.4.1.10428 9 1.102.12.2.2.2.4.2.8
		fkV2IghJoinProfileControlId OBJECT-TYPE
			SYNTAX INTEGER (0..65535)
			MAX-ACCESS read-write
			STATUS current
			DESCRIPTION
				"IGMP profile ID. Same as fkV2IgfProfileIndex"
			::= { fkV2IghJoinProfileControl 8 }

		
		-- 1.3.6.1.4.1.10428 9 1.102.12.2.2.2.4.2.9
		fkV2IghJoinProfileControlReporter OBJECT-TYPE
			SYNTAX IpAddress
			MAX-ACCESS read-write
			STATUS current
			DESCRIPTION
				"Join profile reporter"
			::= { fkV2IghJoinProfileControl 9 }

		
		-- 1.3.6.1.4.1.10428 9 1.102.12.2.2.2.4.3
		fkV2IghJoinProfileNotification OBJECT IDENTIFIER ::= { fkV2IghJoinProfile 3 }

		
		-- 1.3.6.1.4.1.10428 9 1.102.12.2.2.2.4.3.1
		fkV2IghJoinProfileCreated NOTIFICATION-TYPE
			OBJECTS { fkV2IghJoinProfileControlRequest, fkV2IghJoinProfileControlTimeStamp, fkV2IghJoinProfileControlReqResult, fkV2IghJoinProfileControlVlanIndex, fkV2IghJoinProfileControlPortIndex, 
				fkV2IghJoinProfileControlId, fkV2IghJoinProfileControlReporter }
			STATUS current
			DESCRIPTION 
				"Description."
			::= { fkV2IghJoinProfileNotification 1 }

		
		-- 1.3.6.1.4.1.10428 9 1.102.12.2.2.2.4.3.2
		fkV2IghJoinProfileDestroyed NOTIFICATION-TYPE
			OBJECTS { fkV2IghJoinProfileControlRequest, fkV2IghJoinProfileControlTimeStamp, fkV2IghJoinProfileControlReqResult, fkV2IghJoinProfileControlVlanIndex, fkV2IghJoinProfileControlPortIndex, 
				fkV2IghJoinProfileControlId, fkV2IghJoinProfileControlReporter }
			STATUS current
			DESCRIPTION 
				"Description."
			::= { fkV2IghJoinProfileNotification 2 }

		
		-- 1.3.6.1.4.1.10428 9 1.102.12.2.2.2.5
		fkV2IghGroupProfile OBJECT IDENTIFIER ::= { fkV2IgmpHelper 5 }

		
		-- 1.3.6.1.4.1.10428 9 1.102.12.2.2.2.5.1
		fkV2IghGroupProfileTable OBJECT-TYPE
			SYNTAX SEQUENCE OF FkV2IghGroupProfileEntry
			MAX-ACCESS not-accessible
			STATUS current
			DESCRIPTION
				"IGH group profile table."
			::= { fkV2IghGroupProfile 1 }

		
		-- 1.3.6.1.4.1.10428 9 1.102.12.2.2.2.5.1.1
		fkV2IghGroupProfileEntry OBJECT-TYPE
			SYNTAX FkV2IghGroupProfileEntry
			MAX-ACCESS not-accessible
			STATUS current
			DESCRIPTION
				"key: fkV2IghVlanIndex, fkV2IghGroupProfilePortIndex, fkV2IghGroupProfileId"
			INDEX { fkV2IghVlanIndex, fkV2IghGroupProfilePortIndex, fkV2IghGroupProfileId }
			::= { fkV2IghGroupProfileTable 1 }

		
		FkV2IghGroupProfileEntry ::=
			SEQUENCE { 
				fkV2IghGroupProfilePortIndex
					INTEGER,
				fkV2IghGroupProfileId
					Integer32
			 }

		-- 1.3.6.1.4.1.10428 9 1.102.12.2.2.2.5.1.1.1
		fkV2IghGroupProfilePortIndex OBJECT-TYPE
			SYNTAX INTEGER (1..255)
			MAX-ACCESS read-only
			STATUS current
			DESCRIPTION
				"Index of port to what virtual host to emulate is connected."
			::= { fkV2IghGroupProfileEntry 1 }

		
		-- 1.3.6.1.4.1.10428 9 1.102.12.2.2.2.5.1.1.2
		fkV2IghGroupProfileId OBJECT-TYPE
			SYNTAX Integer32 (1..65535)
			MAX-ACCESS read-only
			STATUS current
			DESCRIPTION
				"IGMP profile Id. Same as fkV2IgfProfileIndex"
			::= { fkV2IghGroupProfileEntry 2 }

		
		-- 1.3.6.1.4.1.10428 9 1.102.12.2.2.2.5.2
		fkV2IghGroupProfileControl OBJECT IDENTIFIER ::= { fkV2IghGroupProfile 2 }

		
		-- 1.3.6.1.4.1.10428 9 1.102.12.2.2.2.5.2.1
		fkV2IghGroupProfileControlRequest OBJECT-TYPE
			SYNTAX INTEGER
				{
				createIgmpHelperGroupProfile(1),
				destroyIgmpHelperGroupProfile(2)
				}
			MAX-ACCESS read-write
			STATUS current
			DESCRIPTION
				"The request of a user command"
			::= { fkV2IghGroupProfileControl 1 }

		
		-- 1.3.6.1.4.1.10428 9 1.102.12.2.2.2.5.2.2
		fkV2IghGroupProfileControlStatus OBJECT-TYPE
			SYNTAX FkControlStatusType
			MAX-ACCESS read-only
			STATUS current
			DESCRIPTION
				"The status of a user command. "
			::= { fkV2IghGroupProfileControl 2 }

		
		-- 1.3.6.1.4.1.10428 9 1.102.12.2.2.2.5.2.3
		fkV2IghGroupProfileControlTimer OBJECT-TYPE
			SYNTAX Gauge32
			MAX-ACCESS read-write
			STATUS current
			DESCRIPTION
				"The maximum wait time for the manager for a long running user command."
			::= { fkV2IghGroupProfileControl 3 }

		
		-- 1.3.6.1.4.1.10428 9 1.102.12.2.2.2.5.2.4
		fkV2IghGroupProfileControlTimeStamp OBJECT-TYPE
			SYNTAX TimeStamp
			MAX-ACCESS read-only
			STATUS current
			DESCRIPTION
				"The time stamp of the last command (end of command)."
			::= { fkV2IghGroupProfileControl 4 }

		
		-- 1.3.6.1.4.1.10428 9 1.102.12.2.2.2.5.2.5
		fkV2IghGroupProfileControlReqResult OBJECT-TYPE
			SYNTAX FkControlRequestResultType
			MAX-ACCESS read-only
			STATUS current
			DESCRIPTION
				"The result of the last user command."
			::= { fkV2IghGroupProfileControl 5 }

		
		-- 1.3.6.1.4.1.10428 9 1.102.12.2.2.2.5.2.6
		fkV2IghGroupProfileControlVlanIndex OBJECT-TYPE
			SYNTAX INTEGER (0 | 1..4094)
			MAX-ACCESS read-write
			STATUS current
			DESCRIPTION
				"This object indicates the VLAN number on which MVR feature is configured.
				For all VLANs, the value is 0 (zero)"
			::= { fkV2IghGroupProfileControl 6 }

		
		-- 1.3.6.1.4.1.10428 9 1.102.12.2.2.2.5.2.7
		fkV2IghGroupProfileControlPortIndex OBJECT-TYPE
			SYNTAX INTEGER (1..255)
			MAX-ACCESS read-write
			STATUS current
			DESCRIPTION
				"Port index"
			::= { fkV2IghGroupProfileControl 7 }

		
		-- 1.3.6.1.4.1.10428 9 1.102.12.2.2.2.5.2.8
		fkV2IghGroupProfileControlId OBJECT-TYPE
			SYNTAX INTEGER (0..65535)
			MAX-ACCESS read-write
			STATUS current
			DESCRIPTION
				"IGMP profile Id. Same as fkV2IgfProfileIndex"
			::= { fkV2IghGroupProfileControl 8 }

		
		-- 1.3.6.1.4.1.10428 9 1.102.12.2.2.2.5.3
		fkV2IghGroupProfileNotification OBJECT IDENTIFIER ::= { fkV2IghGroupProfile 3 }

		
		-- 1.3.6.1.4.1.10428 9 1.102.12.2.2.2.5.3.1
		fkV2IghGroupProfileCreated NOTIFICATION-TYPE
			OBJECTS { fkV2IghGroupProfileControlRequest, fkV2IghGroupProfileControlTimeStamp, fkV2IghGroupProfileControlReqResult, fkV2IghGroupProfileControlVlanIndex, fkV2IghGroupProfileControlPortIndex, 
				fkV2IghGroupProfileControlId }
			STATUS current
			DESCRIPTION 
				"Description."
			::= { fkV2IghGroupProfileNotification 1 }

		
		-- 1.3.6.1.4.1.10428 9 1.102.12.2.2.2.5.3.2
		fkV2IghGroupProfileDestroyed NOTIFICATION-TYPE
			OBJECTS { fkV2IghGroupProfileControlRequest, fkV2IghGroupProfileControlTimeStamp, fkV2IghGroupProfileControlReqResult, fkV2IghGroupProfileControlVlanIndex, fkV2IghGroupProfileControlPortIndex, 
				fkV2IghGroupProfileControlId }
			STATUS current
			DESCRIPTION 
				"Description."
			::= { fkV2IghGroupProfileNotification 2 }

		
--  IGMP Source-Specific Multicast(SSM) Mapping
-- 1.3.6.1.4.1.10428 9 1.102.12.2.2.3
		-- 1.3.6.1.4.1.10428 9 1.102.12.2.2.3
		fkV2IgmpSsmMapping OBJECT IDENTIFIER ::= { fkV2Igmp 3 }

		
--  IGMP SSM Mapping Table
-- 1.3.6.1.4.1.10428 9 1.102.12.2.2.3.1
		-- 1.3.6.1.4.1.10428 9 1.102.12.2.2.3.1
		fkV2IgmpSsmMapTable OBJECT-TYPE
			SYNTAX SEQUENCE OF FkV2IgmpSsmMapEntry
			MAX-ACCESS not-accessible
			STATUS current
			DESCRIPTION
				"IGMP SSM map tabel."
			::= { fkV2IgmpSsmMapping 1 }

		
--  IGMP SSM Mapping Entry
-- 1.3.6.1.4.1.10428 9 1.102.12.2.2.3.1.1
		-- 1.3.6.1.4.1.10428 9 1.102.12.2.2.3.1.1
		fkV2IgmpSsmMapEntry OBJECT-TYPE
			SYNTAX FkV2IgmpSsmMapEntry
			MAX-ACCESS not-accessible
			STATUS current
			DESCRIPTION
				"key: fkV2IgmpSsmMapGroup, fkV2IgmpSsmMapSource"
			INDEX { fkV2IgmpSsmMapGroup, fkV2IgmpSsmMapSource }
			::= { fkV2IgmpSsmMapTable 1 }

		
		FkV2IgmpSsmMapEntry ::=
			SEQUENCE { 
				fkV2IgmpSsmMapGroup
					IpAddress,
				fkV2IgmpSsmMapSource
					IpAddress,
				fkV2IgmpSsmMapType
					INTEGER,
				fkV2IgmpSsmMapExpire
					TimeTicks
			 }

--  1.3.6.1.4.1.10428 9 1.102.12.2.2.3.1.1.1
		-- 1.3.6.1.4.1.10428 9 1.102.12.2.2.3.1.1.1
		fkV2IgmpSsmMapGroup OBJECT-TYPE
			SYNTAX IpAddress
			MAX-ACCESS read-only
			STATUS current
			DESCRIPTION
				"The group address of (*,G) entry in Source-Specific Multicast (SSM)."
			::= { fkV2IgmpSsmMapEntry 1 }

		
--  1.3.6.1.4.1.10428 9 1.102.12.2.2.3.1.1.2
		-- 1.3.6.1.4.1.10428 9 1.102.12.2.2.3.1.1.2
		fkV2IgmpSsmMapSource OBJECT-TYPE
			SYNTAX IpAddress
			MAX-ACCESS read-only
			STATUS current
			DESCRIPTION
				"The source address for group entry (*,G)."
			::= { fkV2IgmpSsmMapEntry 2 }

		
--  1.3.6.1.4.1.10428 9 1.102.12.2.2.3.1.1.3
		-- 1.3.6.1.4.1.10428 9 1.102.12.2.2.3.1.1.3
		fkV2IgmpSsmMapType OBJECT-TYPE
			SYNTAX INTEGER
				{
				dynamic(1),
				static(2)
				}
			MAX-ACCESS read-only
			STATUS current
			DESCRIPTION
				"The type of this entry. Static(2) indicate that this 
				entry is setted by administative manner. Dynamic(1), 
				entry generated by remote SSM Mapping server (ex: DNS)."
			::= { fkV2IgmpSsmMapEntry 3 }

		
--  1.3.6.1.4.1.10428 9 1.102.12.2.2.3.1.1.4
		-- 1.3.6.1.4.1.10428 9 1.102.12.2.2.3.1.1.4
		fkV2IgmpSsmMapExpire OBJECT-TYPE
			SYNTAX TimeTicks
			MAX-ACCESS read-only
			STATUS current
			DESCRIPTION
				"In static, this value is zero, otherwise time remaining 
				before ageing."
			::= { fkV2IgmpSsmMapEntry 4 }

		
--  IGMP SSM Mapping Control
-- 1.3.6.1.4.1.10428 9 1.102.12.2.2.3.2
		-- 1.3.6.1.4.1.10428 9 1.102.12.2.2.3.2
		fkV2IgmpSsmMapControl OBJECT IDENTIFIER ::= { fkV2IgmpSsmMapping 2 }

		
--  1.3.6.1.4.1.10428 9 1.102.12.2.2.3.2.1
		-- 1.3.6.1.4.1.10428 9 1.102.12.2.2.3.2.1
		fkV2IgmpSsmMapControlRequest OBJECT-TYPE
			SYNTAX INTEGER
				{
				createIgmpStaticSsmMapping(1),
				destroyIgmpStaticSsmMapping(2)
				}
			MAX-ACCESS read-write
			STATUS current
			DESCRIPTION
				" The request of a user command"
			::= { fkV2IgmpSsmMapControl 1 }

		
--  1.3.6.1.4.1.10428 9 1.102.12.2.2.3.2.2
		-- 1.3.6.1.4.1.10428 9 1.102.12.2.2.3.2.2
		fkV2IgmpSsmMapControlStatus OBJECT-TYPE
			SYNTAX FkControlStatusType
			MAX-ACCESS read-only
			STATUS current
			DESCRIPTION
				" The status of user command"
			::= { fkV2IgmpSsmMapControl 2 }

		
--  1.3.6.1.4.1.10428 9 1.102.12.2.2.3.2.3
		-- 1.3.6.1.4.1.10428 9 1.102.12.2.2.3.2.3
		fkV2IgmpSsmMapControlTimer OBJECT-TYPE
			SYNTAX TimeTicks
			MAX-ACCESS read-write
			STATUS current
			DESCRIPTION
				" The maximum time for the manager for a long running user command"
			::= { fkV2IgmpSsmMapControl 3 }

		
--  1.3.6.1.4.1.10428 9 1.102.12.2.2.3.2.4
		-- 1.3.6.1.4.1.10428 9 1.102.12.2.2.3.2.4
		fkV2IgmpSsmMapControlTimeStamp OBJECT-TYPE
			SYNTAX TimeTicks
			MAX-ACCESS read-only
			STATUS current
			DESCRIPTION
				" The time stamp of the last command(end of command)"
			::= { fkV2IgmpSsmMapControl 4 }

		
--  1.3.6.1.4.1.10428 9 1.102.12.2.2.3.2.5
		-- 1.3.6.1.4.1.10428 9 1.102.12.2.2.3.2.5
		fkV2IgmpSsmMapControlReqResult OBJECT-TYPE
			SYNTAX Integer32
			MAX-ACCESS read-only
			STATUS current
			DESCRIPTION
				" The result of the last user command"
			::= { fkV2IgmpSsmMapControl 5 }

		
--  1.3.6.1.4.1.10428 9 1.102.12.2.2.3.2.6
		-- 1.3.6.1.4.1.10428 9 1.102.12.2.2.3.2.6
		fkV2IgmpSsmMapControlGroup OBJECT-TYPE
			SYNTAX IpAddress
			MAX-ACCESS read-write
			STATUS current
			DESCRIPTION
				" The group address of (*,G) entry in Source-Specific Multicast (SSM)."
			::= { fkV2IgmpSsmMapControl 6 }

		
--  1.3.6.1.4.1.10428 9 1.102.12.2.2.3.2.7
		-- 1.3.6.1.4.1.10428 9 1.102.12.2.2.3.2.7
		fkV2IgmpSsmMapControlSource OBJECT-TYPE
			SYNTAX IpAddress
			MAX-ACCESS read-write
			STATUS current
			DESCRIPTION
				" The source address for group entry (*,G)."
			::= { fkV2IgmpSsmMapControl 7 }

		
--  IGMP SSM Mapping Notification
-- 1.3.6.1.4.1.10428 9 1.102.12.2.2.3.3
		-- 1.3.6.1.4.1.10428 9 1.102.12.2.2.3.3
		fkV2IgmpSsmMapNotification OBJECT IDENTIFIER ::= { fkV2IgmpSsmMapping 3 }

		
--  1.3.6.1.4.1.10428 9 1.102.12.2.2.3.3.1
		-- 1.3.6.1.4.1.10428 9 1.102.12.2.2.3.3.1
		fkV2IgmpSsmMapCreated NOTIFICATION-TYPE
			OBJECTS { fkV2IgmpSsmMapControlRequest, fkV2IgmpSsmMapControlReqResult, fkV2IgmpSsmMapControlTimeStamp, fkV2IgmpSsmMapType, fkV2IgmpSsmMapExpire
				 }
			STATUS current
			DESCRIPTION 
				" "
			::= { fkV2IgmpSsmMapNotification 1 }

		
--  1.3.6.1.4.1.10428 9 1.102.12.2.2.3.3.2
		-- 1.3.6.1.4.1.10428 9 1.102.12.2.2.3.3.2
		fkV2IgmpSsmMapDestroyed NOTIFICATION-TYPE
			OBJECTS { fkV2IgmpSsmMapControlRequest, fkV2IgmpSsmMapControlReqResult, fkV2IgmpSsmMapControlTimeStamp, fkV2IgmpSsmMapControlGroup, fkV2IgmpSsmMapControlSource
				 }
			STATUS current
			DESCRIPTION 
				" "
			::= { fkV2IgmpSsmMapNotification 2 }

		
--  IGMP Agent (Layer 3)
-- 1.3.6.1.4.1.10428 9 1.102.12.2.2.4
		-- 1.3.6.1.4.1.10428 9 1.102.12.2.2.4
		fkV2IgmpAgent OBJECT IDENTIFIER ::= { fkV2Igmp 4 }

		
--  IGMP Interface
-- 1.3.6.1.4.1.10428 9 1.102.12.2.2.4.1
		-- 1.3.6.1.4.1.10428 9 1.102.12.2.2.4.1
		fkV2IgmpInterface OBJECT IDENTIFIER ::= { fkV2IgmpAgent 1 }

		
--  IGMP Interface Table
-- 1.3.6.1.4.1.10428 9 1.102.12.2.2.4.1.1
		-- 1.3.6.1.4.1.10428 9 1.102.12.2.2.4.1.1
		fkV2IgmpIfTable OBJECT-TYPE
			SYNTAX SEQUENCE OF FkV2IgmpIfEntry
			MAX-ACCESS not-accessible
			STATUS current
			DESCRIPTION
				" IGMP interface table."
			::= { fkV2IgmpInterface 1 }

		
--  IGMP Interface Entry
-- 1.3.6.1.4.1.10428 9 1.102.12.2.2.4.1.1.1
		-- 1.3.6.1.4.1.10428 9 1.102.12.2.2.4.1.1.1
		fkV2IgmpIfEntry OBJECT-TYPE
			SYNTAX FkV2IgmpIfEntry
			MAX-ACCESS not-accessible
			STATUS current
			DESCRIPTION
				"IGMP Interface Table Entries
				key: fkV2IgmpIfIndex"
			INDEX { fkV2IgmpIfIndex }
			::= { fkV2IgmpIfTable 1 }

		
		FkV2IgmpIfEntry ::=
			SEQUENCE { 
				fkV2IgmpIfIndex
					INTEGER,
				fkV2IgmpIfActivity
					Boolean,
				fkV2IgmpIfVersion
					INTEGER,
				fkV2IgmpIfQueryInterval
					Integer32,
				fkV2IgmpIfQuerierTimeOut
					Integer32,
				fkV2IgmpIfMaxResponseTime
					Integer32,
				fkV2IgmpIfLastMembQueryCount
					Integer32,
				fkV2IgmpIfLastMembQueryIntvl
					Integer32,
				fkV2IgmpIfFastLeaveGroupList
					OCTET STRING,
				fkV2IgmpIfQuerierState
					INTEGER,
				fkV2IgmpIfQuerierAddress
					IpAddress,
				fkV2IgmpIfQuerierUptime
					TimeTicks,
				fkV2IgmpIfQuerierExpireTime
					TimeTicks,
				fkV2IgmpIfWrongVersionQueriers
					Counter32,
				fkV2IgmpIfGroupMembIntvl
					Unsigned32,
				fkV2IgmpIfAccessGroup
					OCTET STRING,
				fkV2IgmpIfRobustness
					Integer32,
				fkV2IgmpIfJoins
					Counter32,
				fkV2IgmpIfGroups
					Gauge32,
				fkV2IgmpIfMRouteProxyIfIndex
					Integer32,
				fkV2IgmpIfMRouteProxyStatus
					Boolean,
				fkV2IgmpIfStartupQueryInterval
					Integer32,
				fkV2IgmpIfUnsolictedReportInterval
					Integer32,
				fkV2IgmpIfLeaves
					Counter32,
				fkV2IgmpIfLimit
					Integer32,
				fkV2IgmpIfExceptGroup
					OCTET STRING,
				fkV2IgmpIfVerifySrcIp
					Boolean
			 }

--  1.3.6.1.4.1.10428 9 1.102.12.2.2.4.1.1.1.1
		-- 1.3.6.1.4.1.10428 9 1.102.12.2.2.4.1.1.1.1
		fkV2IgmpIfIndex OBJECT-TYPE
			SYNTAX INTEGER (1..4094)
			MAX-ACCESS read-only
			STATUS current
			DESCRIPTION
				" Network interface index.
				(= fkNetIfIndex)
				"
			::= { fkV2IgmpIfEntry 1 }

		
--  1.3.6.1.4.1.10428 9 1.102.12.2.2.4.1.1.1.2
		-- 1.3.6.1.4.1.10428 9 1.102.12.2.2.4.1.1.1.2
		fkV2IgmpIfActivity OBJECT-TYPE
			SYNTAX Boolean
			MAX-ACCESS read-only
			STATUS current
			DESCRIPTION
				"TRUE is IGMP enabled on this interface, FALSE is not."
			::= { fkV2IgmpIfEntry 2 }

		
--  1.3.6.1.4.1.10428 9 1.102.12.2.2.4.1.1.1.3
		-- 1.3.6.1.4.1.10428 9 1.102.12.2.2.4.1.1.1.3
		fkV2IgmpIfVersion OBJECT-TYPE
			SYNTAX INTEGER
				{
				one(1),
				two(2),
				three(3)
				}
			MAX-ACCESS read-only
			STATUS current
			DESCRIPTION
				"The maximum version of IGMP which the host
				can run on this interface."
			DEFVAL { 3 }
			::= { fkV2IgmpIfEntry 3 }

		
--  1.3.6.1.4.1.10428 9 1.102.12.2.2.4.1.1.1.4
		-- 1.3.6.1.4.1.10428 9 1.102.12.2.2.4.1.1.1.4
		fkV2IgmpIfQueryInterval OBJECT-TYPE
			SYNTAX Integer32 (0..31744)
			UNITS "seconds"
			MAX-ACCESS read-only
			STATUS current
			DESCRIPTION
				"The frequency at which IGMP packets are 
				transmitted on this interface."
			DEFVAL { 125 }
			::= { fkV2IgmpIfEntry 4 }

		
--  1.3.6.1.4.1.10428 9 1.102.12.2.2.4.1.1.1.5
		-- 1.3.6.1.4.1.10428 9 1.102.12.2.2.4.1.1.1.5
		fkV2IgmpIfQuerierTimeOut OBJECT-TYPE
			SYNTAX Integer32 (60..300)
			UNITS "seconds"
			MAX-ACCESS read-only
			STATUS current
			DESCRIPTION
				" Other Querier Present Interval. Default value is (QueryInterval * Robustness) + (MaxResponseTime / 2)"
			DEFVAL { 255 }
			::= { fkV2IgmpIfEntry 5 }

		
--  1.3.6.1.4.1.10428 9 1.102.12.2.2.4.1.1.1.6
		-- 1.3.6.1.4.1.10428 9 1.102.12.2.2.4.1.1.1.6
		fkV2IgmpIfMaxResponseTime OBJECT-TYPE
			SYNTAX Integer32 (0..31744)
			UNITS "seconds"
			MAX-ACCESS read-only
			STATUS current
			DESCRIPTION
				"The maximum query response time advertised
				in queries on this interface."
			DEFVAL { 10 }
			::= { fkV2IgmpIfEntry 6 }

		
--  1.3.6.1.4.1.10428 9 1.102.12.2.2.4.1.1.1.7
		-- 1.3.6.1.4.1.10428 9 1.102.12.2.2.4.1.1.1.7
		fkV2IgmpIfLastMembQueryCount OBJECT-TYPE
			SYNTAX Integer32 (1..255)
			MAX-ACCESS read-only
			STATUS current
			DESCRIPTION
				"Represents the number of Group-specific and 
				Group-and-Source-specific queries sent by the 
				router before it assumes there are no local members."
			::= { fkV2IgmpIfEntry 7 }

		
--  1.3.6.1.4.1.10428 9 1.102.12.2.2.4.1.1.1.8
		-- 1.3.6.1.4.1.10428 9 1.102.12.2.2.4.1.1.1.8
		fkV2IgmpIfLastMembQueryIntvl OBJECT-TYPE
			SYNTAX Integer32 (0..31744)
			MAX-ACCESS read-only
			STATUS current
			DESCRIPTION
				"The Last Member Query Interval is the Max Response 
				Time inserted into Group-Specific Queries sent in 
				response to Leave Group messages, and is also the 
				amount of time Between Group-Specific Query messages.
				
				This value may be tuned to modify the leave latency 
				of the network. 
				
				A reduced value results in reduced time to detect 
				the loss of the last member of a group. 
				
				The value of this object is irrelevant if 
				mgmdRouterInterfaceVersion is 1."
			::= { fkV2IgmpIfEntry 8 }

		
--  1.3.6.1.4.1.10428 9 1.102.12.2.2.4.1.1.1.9
		-- 1.3.6.1.4.1.10428 9 1.102.12.2.2.4.1.1.1.9
		fkV2IgmpIfFastLeaveGroupList OBJECT-TYPE
			SYNTAX OCTET STRING
			MAX-ACCESS read-only
			STATUS current
			DESCRIPTION
				" Other Querier Present Interval. Default value is (QueryInterval * Robustness) + (MaxResponseTime / 2)"
			::= { fkV2IgmpIfEntry 9 }

		
--  1.3.6.1.4.1.10428 9 1.102.12.2.2.4.1.1.1.10
		-- 1.3.6.1.4.1.10428 9 1.102.12.2.2.4.1.1.1.10
		fkV2IgmpIfQuerierState OBJECT-TYPE
			SYNTAX INTEGER
				{
				querier(1),
				nonQuerier(2)
				}
			MAX-ACCESS read-only
			STATUS current
			DESCRIPTION
				"It indicates currnet status on IGMP querier in the interface.
				
				querier(1) is currently querier, nonQuerier(2) interface 
				is inactive or not querier now."
			::= { fkV2IgmpIfEntry 10 }

		
--  1.3.6.1.4.1.10428 9 1.102.12.2.2.4.1.1.1.11
		-- 1.3.6.1.4.1.10428 9 1.102.12.2.2.4.1.1.1.11
		fkV2IgmpIfQuerierAddress OBJECT-TYPE
			SYNTAX IpAddress
			MAX-ACCESS read-only
			STATUS current
			DESCRIPTION
				"The address of IGMP Querier on the IP subnet to
				which this interface is attached."
			::= { fkV2IgmpIfEntry 11 }

		
--  1.3.6.1.4.1.10428 9 1.102.12.2.2.4.1.1.1.12
		-- 1.3.6.1.4.1.10428 9 1.102.12.2.2.4.1.1.1.12
		fkV2IgmpIfQuerierUptime OBJECT-TYPE
			SYNTAX TimeTicks
			MAX-ACCESS read-only
			STATUS current
			DESCRIPTION
				"The time since fkV2IgmpIfQuerier was last changed."
			::= { fkV2IgmpIfEntry 12 }

		
--  1.3.6.1.4.1.10428 9 1.102.12.2.2.4.1.1.1.13
		-- 1.3.6.1.4.1.10428 9 1.102.12.2.2.4.1.1.1.13
		fkV2IgmpIfQuerierExpireTime OBJECT-TYPE
			SYNTAX TimeTicks
			MAX-ACCESS read-only
			STATUS current
			DESCRIPTION
				"The amount of time remaining before the other querier
				present timer expires. If the local system is the 
				querier, the value of this object is zero."
			::= { fkV2IgmpIfEntry 13 }

		
--  1.3.6.1.4.1.10428 9 1.102.12.2.2.4.1.1.1.14
		-- 1.3.6.1.4.1.10428 9 1.102.12.2.2.4.1.1.1.14
		fkV2IgmpIfWrongVersionQueriers OBJECT-TYPE
			SYNTAX Counter32
			MAX-ACCESS read-only
			STATUS current
			DESCRIPTION
				"The of general queries received whose IGMP version
				does not match the equivalent FkV2IgmpIfVersion,
				over the lifetime of the row entry.
				
				IGMP require that all routers on a LAN be configured 
				to run the same version.
				
				Thus, if any general queries are received with the 
				wrong version, this indicates a configuration error."
			::= { fkV2IgmpIfEntry 14 }

		
--  1.3.6.1.4.1.10428 9 1.102.12.2.2.4.1.1.1.15
		-- 1.3.6.1.4.1.10428 9 1.102.12.2.2.4.1.1.1.15
		fkV2IgmpIfGroupMembIntvl OBJECT-TYPE
			SYNTAX Unsigned32
			MAX-ACCESS read-only
			STATUS current
			DESCRIPTION
				"Group Membership Interval. This value must be (fkV2IgmpIfQueryInterval * fkV2IgmpIfRobustness) + fkV2IgmpIfMaxResponseTime."
			::= { fkV2IgmpIfEntry 15 }

		
--  1.3.6.1.4.1.10428 9 1.102.12.2.2.4.1.1.1.16
		-- 1.3.6.1.4.1.10428 9 1.102.12.2.2.4.1.1.1.16
		fkV2IgmpIfAccessGroup OBJECT-TYPE
			SYNTAX OCTET STRING
			MAX-ACCESS read-only
			STATUS current
			DESCRIPTION
				"List of IGMP Groups allowed to access."
			::= { fkV2IgmpIfEntry 16 }

		
--  1.3.6.1.4.1.10428 9 1.102.12.2.2.4.1.1.1.17
		-- 1.3.6.1.4.1.10428 9 1.102.12.2.2.4.1.1.1.17
		fkV2IgmpIfRobustness OBJECT-TYPE
			SYNTAX Integer32 (1..255)
			MAX-ACCESS read-only
			STATUS current
			DESCRIPTION
				"The Robustness Variable allows tuning for the expected
				packet loss on a subnet.
				
				If a subnet is expected to be lossy, the Robustness 
				Variable may be increased.  
				
				IGMP is robust to (Robustness Variable-1) packet losses."
			DEFVAL { 2 }
			::= { fkV2IgmpIfEntry 17 }

		
--  1.3.6.1.4.1.10428 9 1.102.12.2.2.4.1.1.1.18
		-- 1.3.6.1.4.1.10428 9 1.102.12.2.2.4.1.1.1.18
		fkV2IgmpIfJoins OBJECT-TYPE
			SYNTAX Counter32
			MAX-ACCESS read-only
			STATUS current
			DESCRIPTION
				"The number of times a group membership has been added
				on this interface; that is, the number of times an 
				entry for this interface has been added to the Cache Table.
				
				This object gives an indication of the amount of IGMP 
				activity over the lifetime of the row entry."
			::= { fkV2IgmpIfEntry 18 }

		
--  1.3.6.1.4.1.10428 9 1.102.12.2.2.4.1.1.1.19
		-- 1.3.6.1.4.1.10428 9 1.102.12.2.2.4.1.1.1.19
		fkV2IgmpIfGroups OBJECT-TYPE
			SYNTAX Gauge32
			MAX-ACCESS read-only
			STATUS current
			DESCRIPTION
				"The current number of entries for this interface in the 
				RouterCache Table."
			::= { fkV2IgmpIfEntry 19 }

		
--  1.3.6.1.4.1.10428 9 1.102.12.2.2.4.1.1.1.20
		-- 1.3.6.1.4.1.10428 9 1.102.12.2.2.4.1.1.1.20
		fkV2IgmpIfMRouteProxyIfIndex OBJECT-TYPE
			SYNTAX Integer32
			MAX-ACCESS read-only
			STATUS current
			DESCRIPTION
				"This value is the igmp-proxy hostside ifindex to multicast routing."
			::= { fkV2IgmpIfEntry 20 }

		
--  1.3.6.1.4.1.10428 9 1.102.12.2.2.4.1.1.1.21
		-- 1.3.6.1.4.1.10428 9 1.102.12.2.2.4.1.1.1.21
		fkV2IgmpIfMRouteProxyStatus OBJECT-TYPE
			SYNTAX Boolean
			MAX-ACCESS read-only
			STATUS current
			DESCRIPTION
				"The true is Igmp Proxy service Enabled on this interface, the false is not."
			::= { fkV2IgmpIfEntry 21 }

		
--  1.3.6.1.4.1.10428 9 1.102.12.2.2.4.1.1.1.22
		-- 1.3.6.1.4.1.10428 9 1.102.12.2.2.4.1.1.1.22
		fkV2IgmpIfStartupQueryInterval OBJECT-TYPE
			SYNTAX Integer32
			MAX-ACCESS read-only
			STATUS current
			DESCRIPTION
				"Startup Query Interval.
				This value is the interval between General Queries send by a Querier on startup.
				"
			::= { fkV2IgmpIfEntry 22 }

		
--  1.3.6.1.4.1.10428 9 1.102.12.2.2.4.1.1.1.23
		-- 1.3.6.1.4.1.10428 9 1.102.12.2.2.4.1.1.1.23
		fkV2IgmpIfUnsolictedReportInterval OBJECT-TYPE
			SYNTAX Integer32
			MAX-ACCESS read-only
			STATUS current
			DESCRIPTION
				"Unsolicted Report Interval.
				This value is the time between repetitions of a host's initial report of membership in a group."
			::= { fkV2IgmpIfEntry 23 }

		
--  1.3.6.1.4.1.10428 9 1.102.12.2.2.4.1.1.1.24
		-- 1.3.6.1.4.1.10428 9 1.102.12.2.2.4.1.1.1.24
		fkV2IgmpIfLeaves OBJECT-TYPE
			SYNTAX Counter32
			MAX-ACCESS read-only
			STATUS current
			DESCRIPTION
				"The number of times a group membership has been removed on this interface; that is, the number of times an entry for this interface has been removed to the Cache Table "
			::= { fkV2IgmpIfEntry 24 }

		
--  1.3.6.1.4.1.10428 9 1.102.12.2.2.4.1.1.1.25
		-- 1.3.6.1.4.1.10428 9 1.102.12.2.2.4.1.1.1.25
		fkV2IgmpIfLimit OBJECT-TYPE
			SYNTAX Integer32
			MAX-ACCESS read-only
			STATUS current
			DESCRIPTION
				"This value is the tolerance limit of igmp groups in this interface"
			::= { fkV2IgmpIfEntry 25 }

		
--  1.3.6.1.4.1.10428 9 1.102.12.2.2.4.1.1.1.26
		-- 1.3.6.1.4.1.10428 9 1.102.12.2.2.4.1.1.1.26
		fkV2IgmpIfExceptGroup OBJECT-TYPE
			SYNTAX OCTET STRING
			MAX-ACCESS read-only
			STATUS current
			DESCRIPTION
				"The permmited group list over the tolerance limit of igmp groups in this interface "
			::= { fkV2IgmpIfEntry 26 }

		
--  1.3.6.1.4.1.10428 9 1.102.12.2.2.4.1.1.1.27
		-- 1.3.6.1.4.1.10428 9 1.102.12.2.2.4.1.1.1.27
		fkV2IgmpIfVerifySrcIp OBJECT-TYPE
			SYNTAX Boolean
			MAX-ACCESS read-only
			STATUS current
			DESCRIPTION
				"The activie state of Verify-SrcIp"
			::= { fkV2IgmpIfEntry 27 }

		
--  IGMP Interface Control
-- 1.3.6.1.4.1.10428 9 1.102.12.2.2.4.1.2
		-- 1.3.6.1.4.1.10428 9 1.102.12.2.2.4.1.2
		fkV2IgmpIfControl OBJECT IDENTIFIER ::= { fkV2IgmpInterface 2 }

		
--  1.3.6.1.4.1.10428 9 1.102.12.2.2.4.1.2.1
		-- 1.3.6.1.4.1.10428 9 1.102.12.2.2.4.1.2.1
		fkV2IgmpIfControlRequest OBJECT-TYPE
			SYNTAX INTEGER
				{
				setIgmpInterfaceActivity(1),
				setIgmpInterfaceProfile(2),
				setIgmpMrouteProxy(3),
				setIgmpProxyService(4),
				clearIgmpStatistics(5),
				setIgmpVerifySrcIp(6)
				}
			MAX-ACCESS read-write
			STATUS current
			DESCRIPTION
				" The request of a user command"
			::= { fkV2IgmpIfControl 1 }

		
--  1.3.6.1.4.1.10428 9 1.102.12.2.2.4.1.2.2
		-- 1.3.6.1.4.1.10428 9 1.102.12.2.2.4.1.2.2
		fkV2IgmpIfControlStatus OBJECT-TYPE
			SYNTAX FkControlStatusType
			MAX-ACCESS read-only
			STATUS current
			DESCRIPTION
				" The status of user command"
			::= { fkV2IgmpIfControl 2 }

		
--  1.3.6.1.4.1.10428 9 1.102.12.2.2.4.1.2.3
		-- 1.3.6.1.4.1.10428 9 1.102.12.2.2.4.1.2.3
		fkV2IgmpIfControlTimer OBJECT-TYPE
			SYNTAX Gauge32
			MAX-ACCESS read-write
			STATUS current
			DESCRIPTION
				" The maximum time for the manager for a long running user command"
			::= { fkV2IgmpIfControl 3 }

		
--  1.3.6.1.4.1.10428 9 1.102.12.2.2.4.1.2.4
		-- 1.3.6.1.4.1.10428 9 1.102.12.2.2.4.1.2.4
		fkV2IgmpIfControlTimeStamp OBJECT-TYPE
			SYNTAX TimeStamp
			MAX-ACCESS read-only
			STATUS current
			DESCRIPTION
				" The time stamp of the last command(end of command)"
			::= { fkV2IgmpIfControl 4 }

		
--  1.3.6.1.4.1.10428 9 1.102.12.2.2.4.1.2.5
		-- 1.3.6.1.4.1.10428 9 1.102.12.2.2.4.1.2.5
		fkV2IgmpIfControlReqResult OBJECT-TYPE
			SYNTAX FkControlRequestResultType
			MAX-ACCESS read-only
			STATUS current
			DESCRIPTION
				" The result of the last user command"
			::= { fkV2IgmpIfControl 5 }

		
--  1.3.6.1.4.1.10428 9 1.102.12.2.2.4.1.2.6
		-- 1.3.6.1.4.1.10428 9 1.102.12.2.2.4.1.2.6
		fkV2IgmpIfControlIndex OBJECT-TYPE
			SYNTAX INTEGER (1..4094)
			MAX-ACCESS read-write
			STATUS current
			DESCRIPTION
				" Network interface index.
				(= fkNetIfIndex)
				"
			::= { fkV2IgmpIfControl 6 }

		
--  1.3.6.1.4.1.10428 9 1.102.12.2.2.4.1.2.7
		-- 1.3.6.1.4.1.10428 9 1.102.12.2.2.4.1.2.7
		fkV2IgmpIfControlActivity OBJECT-TYPE
			SYNTAX Boolean
			MAX-ACCESS read-write
			STATUS current
			DESCRIPTION
				"Network interface index.
				(= fkNetIfIndex)
				"
			::= { fkV2IgmpIfControl 7 }

		
--  1.3.6.1.4.1.10428 9 1.102.12.2.2.4.1.2.8
		-- 1.3.6.1.4.1.10428 9 1.102.12.2.2.4.1.2.8
		fkV2IgmpIfControlVersion OBJECT-TYPE
			SYNTAX INTEGER (-1 | 1..3)
			MAX-ACCESS read-write
			STATUS current
			DESCRIPTION
				"CLI : (no) ip igmp version <1-3>
				value(-1) : default"
			::= { fkV2IgmpIfControl 8 }

		
--  1.3.6.1.4.1.10428 9 1.102.12.2.2.4.1.2.9
		-- 1.3.6.1.4.1.10428 9 1.102.12.2.2.4.1.2.9
		fkV2IgmpIfControlQueryInterval OBJECT-TYPE
			SYNTAX Integer32 (-1 | 1..18000)
			UNITS "seconds"
			MAX-ACCESS read-write
			STATUS current
			DESCRIPTION
				"CLI : (no) ip igmp query-interval <1-1800>
				value(-1) : (no)"
			::= { fkV2IgmpIfControl 9 }

		
--  1.3.6.1.4.1.10428 9 1.102.12.2.2.4.1.2.10
		-- 1.3.6.1.4.1.10428 9 1.102.12.2.2.4.1.2.10
		fkV2IgmpIfControlQuerierTimeOut OBJECT-TYPE
			SYNTAX Integer32 (-1 | 60..300)
			UNITS "seconds"
			MAX-ACCESS read-write
			STATUS current
			DESCRIPTION
				"CLI : (no) ip igmp querier-timeout <60-300>
				value(-1) : (no)"
			DEFVAL { 255 }
			::= { fkV2IgmpIfControl 10 }

		
--  1.3.6.1.4.1.10428 9 1.102.12.2.2.4.1.2.11
		-- 1.3.6.1.4.1.10428 9 1.102.12.2.2.4.1.2.11
		fkV2IgmpIfControlMaxResponseTime OBJECT-TYPE
			SYNTAX Integer32 (-1 | 1..240)
			UNITS "seconds"
			MAX-ACCESS read-write
			STATUS current
			DESCRIPTION
				"CLI: (no) ip igmp query-max-response-time <1-240>
				value(-1) : (no)"
			DEFVAL { 10 }
			::= { fkV2IgmpIfControl 11 }

		
--  1.3.6.1.4.1.10428 9 1.102.12.2.2.4.1.2.12
		-- 1.3.6.1.4.1.10428 9 1.102.12.2.2.4.1.2.12
		fkV2IgmpIfControlLastMembQueryCount OBJECT-TYPE
			SYNTAX Integer32 (-1 | 2..7)
			MAX-ACCESS read-write
			STATUS current
			DESCRIPTION
				"CLI : (no) ip igmp last-member-query-count <2-7>
				value(-1) : (no)"
			DEFVAL { 2 }
			::= { fkV2IgmpIfControl 12 }

		
--  1.3.6.1.4.1.10428 9 1.102.12.2.2.4.1.2.13
		-- 1.3.6.1.4.1.10428 9 1.102.12.2.2.4.1.2.13
		fkV2IgmpIfControlLastMembQueryIntvl OBJECT-TYPE
			SYNTAX Integer32 (-1 | 1000..25500)
			UNITS "milliseconds"
			MAX-ACCESS read-write
			STATUS current
			DESCRIPTION
				"CLI : (no) ip igmp last-member-query-interval <1000-25500>
				value(-1) : (no)"
			DEFVAL { 1000 }
			::= { fkV2IgmpIfControl 13 }

		
--  1.3.6.1.4.1.10428 9 1.102.12.2.2.4.1.2.14
		-- 1.3.6.1.4.1.10428 9 1.102.12.2.2.4.1.2.14
		fkV2IgmpIfControlFastLeaveGroupList OBJECT-TYPE
			SYNTAX OCTET STRING
			MAX-ACCESS read-write
			STATUS current
			DESCRIPTION
				"CLI : (no) ip igmp immediate-leave group-list ACCESS-LIST
				value(0) : (no)"
			::= { fkV2IgmpIfControl 14 }

		
--  1.3.6.1.4.1.10428 9 1.102.12.2.2.4.1.2.15
		-- 1.3.6.1.4.1.10428 9 1.102.12.2.2.4.1.2.15
		fkV2IgmpIfControlAccessGroup OBJECT-TYPE
			SYNTAX OCTET STRING
			MAX-ACCESS read-write
			STATUS current
			DESCRIPTION
				"CLI : (no) ip igm access-group ACCESS-LIST
				value(0) : (no)"
			::= { fkV2IgmpIfControl 15 }

		
--  1.3.6.1.4.1.10428 9 1.102.12.2.2.4.1.2.16
		-- 1.3.6.1.4.1.10428 9 1.102.12.2.2.4.1.2.16
		fkV2IgmpIfControlRobustness OBJECT-TYPE
			SYNTAX Integer32 (-1 | 2..7)
			MAX-ACCESS read-write
			STATUS current
			DESCRIPTION
				"CLI : (no) ip igmp robustiness-variable <2-7>
				value(-1) : (no)"
			DEFVAL { 2 }
			::= { fkV2IgmpIfControl 16 }

		
--  1.3.6.1.4.1.10428 9 1.102.12.2.2.4.1.2.17
		-- 1.3.6.1.4.1.10428 9 1.102.12.2.2.4.1.2.17
		fkV2IgmpIfControlMRouteProxyIfIndex OBJECT-TYPE
			SYNTAX INTEGER (-1 | 1..4094)
			MAX-ACCESS read-write
			STATUS current
			DESCRIPTION
				"CLI : (no) ip igmp mroute-proxy IFNAME 
				The value of -1 is (no)"
			::= { fkV2IgmpIfControl 17 }

		
--  1.3.6.1.4.1.10428 9 1.102.12.2.2.4.1.2.18
		-- 1.3.6.1.4.1.10428 9 1.102.12.2.2.4.1.2.18
		fkV2IgmpIfControlProxyStatus OBJECT-TYPE
			SYNTAX Boolean
			MAX-ACCESS read-write
			STATUS current
			DESCRIPTION
				"CLI : (no) ip igmp proxy-service"
			::= { fkV2IgmpIfControl 18 }

		
--  1.3.6.1.4.1.10428 9 1.102.12.2.2.4.1.2.19
		-- 1.3.6.1.4.1.10428 9 1.102.12.2.2.4.1.2.19
		fkV2IgmpIfControlStartupQueryInterval OBJECT-TYPE
			SYNTAX INTEGER (-1 | 1..18000)
			MAX-ACCESS read-write
			STATUS current
			DESCRIPTION
				"CLI : (no) ip igmp startup-query-interval <1-18000>
				The value of -1 is (no)"
			DEFVAL { 32 }
			::= { fkV2IgmpIfControl 19 }

		
--  1.3.6.1.4.1.10428 9 1.102.12.2.2.4.1.2.20
		-- 1.3.6.1.4.1.10428 9 1.102.12.2.2.4.1.2.20
		fkV2IgmpIfControlUnsolictedReportInterval OBJECT-TYPE
			SYNTAX INTEGER (-1 | 1..18000)
			MAX-ACCESS read-write
			STATUS current
			DESCRIPTION
				"CLI : (no) ip igmp unsolicted-report-interval <1-18000>
				The value of -1 is (no)"
			DEFVAL { 10 }
			::= { fkV2IgmpIfControl 20 }

		
--  1.3.6.1.4.1.10428 9 1.102.12.2.2.4.1.2.21
		-- 1.3.6.1.4.1.10428 9 1.102.12.2.2.4.1.2.21
		fkV2IgmpIfControlLimit OBJECT-TYPE
			SYNTAX Integer32
			MAX-ACCESS read-write
			STATUS current
			DESCRIPTION
				"This value is the tolerance limit of igmp groups in this interface
				(supported only model 5924N)
				"
			::= { fkV2IgmpIfControl 21 }

		
--  1.3.6.1.4.1.10428 9 1.102.12.2.2.4.1.2.22
		-- 1.3.6.1.4.1.10428 9 1.102.12.2.2.4.1.2.22
		fkV2IgmpIfControlExceptGroup OBJECT-TYPE
			SYNTAX OCTET STRING
			MAX-ACCESS read-write
			STATUS current
			DESCRIPTION
				"The permmited group list over the tolerance limit of igmp groups in this interface
				(supported only model 5924N)
				"
			::= { fkV2IgmpIfControl 22 }

		
--  1.3.6.1.4.1.10428 9 1.102.12.2.2.4.1.2.23
		-- 1.3.6.1.4.1.10428 9 1.102.12.2.2.4.1.2.23
		fkV2IgmpIfControlVerifySrcIp OBJECT-TYPE
			SYNTAX Boolean
			MAX-ACCESS read-write
			STATUS current
			DESCRIPTION
				"The activie state of Verify-SrcIp"
			::= { fkV2IgmpIfControl 23 }

		
--  IGMP Interface Notification
-- 1.3.6.1.4.1.10428 9 1.102.12.2.2.4.1.3
		-- 1.3.6.1.4.1.10428 9 1.102.12.2.2.4.1.3
		fkV2IgmpIfNotification OBJECT IDENTIFIER ::= { fkV2IgmpInterface 3 }

		
--  1.3.6.1.4.1.10428 9 1.102.12.2.2.4.1.3.1
		-- 1.3.6.1.4.1.10428 9 1.102.12.2.2.4.1.3.1
		fkV2IgmpInterfaceActivityChanged NOTIFICATION-TYPE
			OBJECTS { fkV2IgmpIfControlRequest, fkV2IgmpIfControlTimeStamp, fkV2IgmpIfControlReqResult, fkV2IgmpIfActivity }
			STATUS current
			DESCRIPTION 
				" "
			::= { fkV2IgmpIfNotification 1 }

		
--  1.3.6.1.4.1.10428 9 1.102.12.2.2.4.1.3.2
		-- 1.3.6.1.4.1.10428 9 1.102.12.2.2.4.1.3.2
		fkV2IgmpInterfaceProfileChanged NOTIFICATION-TYPE
			OBJECTS { fkV2IgmpIfControlTimeStamp, fkV2IgmpIfControlRequest, fkV2IgmpIfExceptGroup, fkV2IgmpIfLimit, fkV2IgmpIfControlReqResult, 
				fkV2IgmpIfVersion, fkV2IgmpIfQueryInterval, fkV2IgmpIfQuerierTimeOut, fkV2IgmpIfMaxResponseTime, fkV2IgmpIfLastMembQueryCount, 
				fkV2IgmpIfLastMembQueryIntvl, fkV2IgmpIfFastLeaveGroupList, fkV2IgmpIfAccessGroup, fkV2IgmpIfRobustness, fkV2IgmpIfStartupQueryInterval, 
				fkV2IgmpIfUnsolictedReportInterval }
			STATUS current
			DESCRIPTION 
				"Description."
			::= { fkV2IgmpIfNotification 2 }

		
--  1.3.6.1.4.1.10428 9 1.102.12.2.2.4.1.3.3
		-- 1.3.6.1.4.1.10428 9 1.102.12.2.2.4.1.3.3
		fkV2IgmpInterfaceMrouteChanged NOTIFICATION-TYPE
			OBJECTS { fkV2IgmpIfControlRequest, fkV2IgmpIfControlTimeStamp, fkV2IgmpIfControlReqResult, fkV2IgmpIfMRouteProxyIfIndex }
			STATUS current
			DESCRIPTION 
				"Description."
			::= { fkV2IgmpIfNotification 3 }

		
--  1.3.6.1.4.1.10428 9 1.102.12.2.2.4.1.3.4
		-- 1.3.6.1.4.1.10428 9 1.102.12.2.2.4.1.3.4
		fkV2IgmpInterfaceProxyServiceChanged NOTIFICATION-TYPE
			OBJECTS { fkV2IgmpIfControlRequest, fkV2IgmpIfControlTimeStamp, fkV2IgmpIfControlReqResult, fkV2IgmpIfMRouteProxyStatus }
			STATUS current
			DESCRIPTION 
				"Description."
			::= { fkV2IgmpIfNotification 4 }

		
--  1.3.6.1.4.1.10428 9 1.102.12.2.2.4.1.3.5
		-- 1.3.6.1.4.1.10428 9 1.102.12.2.2.4.1.3.5
		fkV2IgmpInterfaceStatsCleared NOTIFICATION-TYPE
			OBJECTS { fkV2IgmpIfControlRequest, fkV2IgmpIfControlTimeStamp, fkV2IgmpIfControlReqResult, fkV2IgmpIfJoins, fkV2IgmpIfLeaves
				 }
			STATUS current
			DESCRIPTION 
				"Description."
			::= { fkV2IgmpIfNotification 5 }

		
--  1.3.6.1.4.1.10428 9 1.102.12.2.2.4.1.3.6
		-- 1.3.6.1.4.1.10428 9 1.102.12.2.2.4.1.3.6
		fkV2IgmpInterfaceVerifySrcIpChanged NOTIFICATION-TYPE
			OBJECTS { fkV2IgmpIfControlRequest, fkV2IgmpIfControlTimeStamp, fkV2IgmpIfControlReqResult, fkV2IgmpIfControlVerifySrcIp }
			STATUS current
			DESCRIPTION 
				"Description."
			::= { fkV2IgmpIfNotification 6 }

		
--  IGMP Cache (Group)
-- 1.3.6.1.4.1.10428 9 1.102.12.2.2.4.2
		-- 1.3.6.1.4.1.10428 9 1.102.12.2.2.4.2
		fkV2IgmpCache OBJECT IDENTIFIER ::= { fkV2IgmpAgent 2 }

		
--  IGMP Cache Table
-- 1.3.6.1.4.1.10428 9 1.102.12.2.2.4.2.1
		-- 1.3.6.1.4.1.10428 9 1.102.12.2.2.4.2.1
		fkV2IgmpCacheTable OBJECT-TYPE
			SYNTAX SEQUENCE OF FkV2IgmpCacheEntry
			MAX-ACCESS not-accessible
			STATUS current
			DESCRIPTION
				" IGMP cache table."
			::= { fkV2IgmpCache 1 }

		
--  IGMP Cache Entry
-- 1.3.6.1.4.1.10428 9 1.102.12.2.2.4.2.1.1
		-- 1.3.6.1.4.1.10428 9 1.102.12.2.2.4.2.1.1
		fkV2IgmpCacheEntry OBJECT-TYPE
			SYNTAX FkV2IgmpCacheEntry
			MAX-ACCESS not-accessible
			STATUS current
			DESCRIPTION
				"key: fkV2IgmpIfIndex, fkV2IgmpCacheGroup"
			INDEX { fkV2IgmpIfIndex, fkV2IgmpCacheGroup }
			::= { fkV2IgmpCacheTable 1 }

		
		FkV2IgmpCacheEntry ::=
			SEQUENCE { 
				fkV2IgmpCacheGroup
					IpAddress,
				fkV2IgmpCacheLastReporter
					IpAddress,
				fkV2IgmpCacheVersion
					BITS,
				fkV2IgmpCacheSourceFilterMode
					INTEGER,
				fkV2IgmpCacheExcludeModeExpiryTimer
					TimeTicks,
				fkV2IgmpCacheUpTime
					TimeTicks,
				fkV2IgmpCacheExpiryTime
					TimeTicks,
				fkV2IgmpCacheVersion2HostTimer
					TimeTicks,
				fkV2IgmpCacheVersion1HostTimer
					TimeTicks
			 }

--  1.3.6.1.4.1.10428 9 1.102.12.2.2.4.2.1.1.1
		-- 1.3.6.1.4.1.10428 9 1.102.12.2.2.4.2.1.1.1
		fkV2IgmpCacheGroup OBJECT-TYPE
			SYNTAX IpAddress
			MAX-ACCESS read-only
			STATUS current
			DESCRIPTION
				" It is a IP multicast address learned by IGMP."
			::= { fkV2IgmpCacheEntry 1 }

		
--  1.3.6.1.4.1.10428 9 1.102.12.2.2.4.2.1.1.2
		-- 1.3.6.1.4.1.10428 9 1.102.12.2.2.4.2.1.1.2
		fkV2IgmpCacheLastReporter OBJECT-TYPE
			SYNTAX IpAddress
			MAX-ACCESS read-only
			STATUS current
			DESCRIPTION
				"The IP address of the source of the membership report received for this IP Multicast group address on this interface. If no membership report has been received, this object has the value 0.0.0.0."
			::= { fkV2IgmpCacheEntry 2 }

		
--  1.3.6.1.4.1.10428 9 1.102.12.2.2.4.2.1.1.3
		-- 1.3.6.1.4.1.10428 9 1.102.12.2.2.4.2.1.1.3
		fkV2IgmpCacheVersion OBJECT-TYPE
			SYNTAX BITS
				{
				unused(0),
				igmpV1(1),
				igmpV2(2),
				igmpV3(3)
				}
			MAX-ACCESS read-only
			STATUS current
			DESCRIPTION
				"This object indicates the IGMP versions for the group. This is determined by the type of IGMP Membership Reports received by the device."
			::= { fkV2IgmpCacheEntry 3 }

		
--  1.3.6.1.4.1.10428 9 1.102.12.2.2.4.2.1.1.4
		-- 1.3.6.1.4.1.10428 9 1.102.12.2.2.4.2.1.1.4
		fkV2IgmpCacheSourceFilterMode OBJECT-TYPE
			SYNTAX INTEGER
				{
				unknown(0),
				include(1),
				exclude(2)
				}
			MAX-ACCESS read-only
			STATUS current
			DESCRIPTION
				"The current cache state, applicable to IGMPv3 compatible nodes. The value indicates whether the state is INCLUDE or EXCLUDE."
			::= { fkV2IgmpCacheEntry 4 }

		
--  1.3.6.1.4.1.10428 9 1.102.12.2.2.4.2.1.1.5
		-- 1.3.6.1.4.1.10428 9 1.102.12.2.2.4.2.1.1.5
		fkV2IgmpCacheExcludeModeExpiryTimer OBJECT-TYPE
			SYNTAX TimeTicks
			MAX-ACCESS read-only
			STATUS current
			DESCRIPTION
				"This value is applicable only to IGMPv3 compatible routers, and represents the time remaining before the interface EXCLUDE state expires and the interface state transitions to INCLUDE mode. This value can never be greater than fkV2IgmpCacheExpiryTime."
			::= { fkV2IgmpCacheEntry 5 }

		
--  1.3.6.1.4.1.10428 9 1.102.12.2.2.4.2.1.1.6
		-- 1.3.6.1.4.1.10428 9 1.102.12.2.2.4.2.1.1.6
		fkV2IgmpCacheUpTime OBJECT-TYPE
			SYNTAX TimeTicks
			MAX-ACCESS read-only
			STATUS current
			DESCRIPTION
				"The time elapsed since this entry was created."
			::= { fkV2IgmpCacheEntry 6 }

		
--  1.3.6.1.4.1.10428 9 1.102.12.2.2.4.2.1.1.7
		-- 1.3.6.1.4.1.10428 9 1.102.12.2.2.4.2.1.1.7
		fkV2IgmpCacheExpiryTime OBJECT-TYPE
			SYNTAX TimeTicks
			MAX-ACCESS read-only
			STATUS current
			DESCRIPTION
				"This value represents the time remaining before the Group Membership Interval state expires. The value must always be greater than 0."
			::= { fkV2IgmpCacheEntry 7 }

		
--  1.3.6.1.4.1.10428 9 1.102.12.2.2.4.2.1.1.8
		-- 1.3.6.1.4.1.10428 9 1.102.12.2.2.4.2.1.1.8
		fkV2IgmpCacheVersion2HostTimer OBJECT-TYPE
			SYNTAX TimeTicks
			MAX-ACCESS read-only
			STATUS current
			DESCRIPTION
				"The time remaining until the local router will assume that there are no longer any IGMPv2 members on the IP subnet attached to this interface. This entry applies to IGMP hosts. Upon hearing any IGMPv2 Membership Report, this value is reset to the group membership timer. Assuming no IGMPv1 hosts have been detected, the local router does not ignore any IGMPv2 Leave messages for this group that it receives on this interface."
			::= { fkV2IgmpCacheEntry 8 }

		
--  1.3.6.1.4.1.10428 9 1.102.12.2.2.4.2.1.1.9
		-- 1.3.6.1.4.1.10428 9 1.102.12.2.2.4.2.1.1.9
		fkV2IgmpCacheVersion1HostTimer OBJECT-TYPE
			SYNTAX TimeTicks
			MAX-ACCESS read-only
			STATUS current
			DESCRIPTION
				"The time remaining until the local router will assume that there are no longer any IGMP version 1 members on the IP subnet attached to this interface. This entry only applies to IGMPv1 hosts. Upon hearing any IGMPv1 Membership Report, this value is reset to the group membership timer. While this time remaining is non-zero, the local router ignores any IGMPv2 Leave messages (IGMPv2 only) for this group that it receives on this interface."
			::= { fkV2IgmpCacheEntry 9 }

		
--  IGMP Cache (Group)
-- 1.3.6.1.4.1.10428 9 1.102.12.2.2.4.3
		-- 1.3.6.1.4.1.10428 9 1.102.12.2.2.4.3
		fkV2IgmpSource OBJECT IDENTIFIER ::= { fkV2IgmpAgent 3 }

		
--  IGMP Cache Table
-- 1.3.6.1.4.1.10428 9 1.102.12.2.2.4.3.1
		-- 1.3.6.1.4.1.10428 9 1.102.12.2.2.4.3.1
		fkV2IgmpSourceTable OBJECT-TYPE
			SYNTAX SEQUENCE OF FkV2IgmpSourceEntry
			MAX-ACCESS not-accessible
			STATUS current
			DESCRIPTION
				"IGMP source table."
			::= { fkV2IgmpSource 1 }

		
--  IGMP Cache Entry
-- 1.3.6.1.4.1.10428 9 1.102.12.2.2.4.3.1.1
		-- 1.3.6.1.4.1.10428 9 1.102.12.2.2.4.3.1.1
		fkV2IgmpSourceEntry OBJECT-TYPE
			SYNTAX FkV2IgmpSourceEntry
			MAX-ACCESS not-accessible
			STATUS current
			DESCRIPTION
				"key: fkV2IgmpIfIndex, fkV2IgmpCacheGroup, fkV2IgmpSourceAddress"
			INDEX { fkV2IgmpIfIndex, fkV2IgmpCacheGroup, fkV2IgmpSourceAddress }
			::= { fkV2IgmpSourceTable 1 }

		
		FkV2IgmpSourceEntry ::=
			SEQUENCE { 
				fkV2IgmpSourceAddress
					IpAddress,
				fkV2IgmpSourceType
					INTEGER,
				fkV2IgmpSourceUpTime
					TimeTicks,
				fkV2IgmpSourceExpiryTime
					TimeTicks,
				fkV2IgmpSourceSsmMapped
					Boolean
			 }

--  1.3.6.1.4.1.10428 9 1.102.12.2.2.4.3.1.1.1
		-- 1.3.6.1.4.1.10428 9 1.102.12.2.2.4.3.1.1.1
		fkV2IgmpSourceAddress OBJECT-TYPE
			SYNTAX IpAddress
			MAX-ACCESS read-only
			STATUS current
			DESCRIPTION
				"Source of IP multicast group, fkV2IgmpCacheGroup.For (*,G) entry, value is 0.0.0.0"
			::= { fkV2IgmpSourceEntry 1 }

		
--  1.3.6.1.4.1.10428 9 1.102.12.2.2.4.3.1.1.2
		-- 1.3.6.1.4.1.10428 9 1.102.12.2.2.4.3.1.1.2
		fkV2IgmpSourceType OBJECT-TYPE
			SYNTAX INTEGER
				{
				dynamic(1),
				static(2)
				}
			MAX-ACCESS read-only
			STATUS current
			DESCRIPTION
				"It indicates whether the multicast group (S/*,G) is learned by IGMP report messages or administrative maner."
			::= { fkV2IgmpSourceEntry 2 }

		
--  1.3.6.1.4.1.10428 9 1.102.12.2.2.4.3.1.1.3
		-- 1.3.6.1.4.1.10428 9 1.102.12.2.2.4.3.1.1.3
		fkV2IgmpSourceUpTime OBJECT-TYPE
			SYNTAX TimeTicks
			MAX-ACCESS read-only
			STATUS current
			DESCRIPTION
				"The time elapsed since this entry was created. For (*,G) entry, it is equal to fkV2IgmpCacheUpTime"
			::= { fkV2IgmpSourceEntry 3 }

		
--  1.3.6.1.4.1.10428 9 1.102.12.2.2.4.3.1.1.4
		-- 1.3.6.1.4.1.10428 9 1.102.12.2.2.4.3.1.1.4
		fkV2IgmpSourceExpiryTime OBJECT-TYPE
			SYNTAX TimeTicks
			MAX-ACCESS read-only
			STATUS current
			DESCRIPTION
				"This value represents the time remaining before the Group Membership Interval state expires. The value must always be greater than 0. For (*,G) entry, it is equal to fkV2IgmpCacheExpiryTime"
			::= { fkV2IgmpSourceEntry 4 }

		
--  1.3.6.1.4.1.10428 9 1.102.12.2.2.4.3.1.1.5
		-- 1.3.6.1.4.1.10428 9 1.102.12.2.2.4.3.1.1.5
		fkV2IgmpSourceSsmMapped OBJECT-TYPE
			SYNTAX Boolean
			MAX-ACCESS read-only
			STATUS current
			DESCRIPTION
				"The value TRUE indicate that source of multicast group is decided by SSM Mapping Table, and FALSE is not."
			::= { fkV2IgmpSourceEntry 5 }

		
--  IGMP Cache Control
-- 1.3.6.1.4.1.10428 9 1.102.12.2.2.4.3.2
		-- 1.3.6.1.4.1.10428 9 1.102.12.2.2.4.3.2
		fkV2IgmpSourceControl OBJECT IDENTIFIER ::= { fkV2IgmpSource 2 }

		
--   Not supported.
-- 
-- 1.3.6.1.4.1.10428 9 1.102.12.2.2.4.3.2.1
		-- 1.3.6.1.4.1.10428 9 1.102.12.2.2.4.3.2.1
		fkV2IgmpSourceControlRequest OBJECT-TYPE
			SYNTAX INTEGER
				{
				createIgmpSourceStaticEntry(1),
				destroyIgmpSourceStaticEntry(2)
				}
			MAX-ACCESS read-write
			STATUS current
			DESCRIPTION
				" The request of a user command"
			::= { fkV2IgmpSourceControl 1 }

		
--  1.3.6.1.4.1.10428 9 1.102.12.2.2.4.3.2.2
		-- 1.3.6.1.4.1.10428 9 1.102.12.2.2.4.3.2.2
		fkV2IgmpSourceControlStatus OBJECT-TYPE
			SYNTAX FkControlStatusType
			MAX-ACCESS read-only
			STATUS current
			DESCRIPTION
				"The status of user command"
			::= { fkV2IgmpSourceControl 2 }

		
--  1.3.6.1.4.1.10428 9 1.102.12.2.2.4.3.2.3
		-- 1.3.6.1.4.1.10428 9 1.102.12.2.2.4.3.2.3
		fkV2IgmpSourceControlTimer OBJECT-TYPE
			SYNTAX Gauge32
			MAX-ACCESS read-write
			STATUS current
			DESCRIPTION
				"The maximum time for the manager for a long running user comman"
			::= { fkV2IgmpSourceControl 3 }

		
--  1.3.6.1.4.1.10428 9 1.102.12.2.2.4.3.2.4
		-- 1.3.6.1.4.1.10428 9 1.102.12.2.2.4.3.2.4
		fkV2IgmpSourceControlTimeStamp OBJECT-TYPE
			SYNTAX TimeStamp
			MAX-ACCESS read-only
			STATUS current
			DESCRIPTION
				" The time stamp of the last command(end of command)"
			::= { fkV2IgmpSourceControl 4 }

		
--  1.3.6.1.4.1.10428 9 1.102.12.2.2.4.3.2.5
		-- 1.3.6.1.4.1.10428 9 1.102.12.2.2.4.3.2.5
		fkV2IgmpSourceControlReqResult OBJECT-TYPE
			SYNTAX FkControlRequestResultType
			MAX-ACCESS read-only
			STATUS current
			DESCRIPTION
				" The result of the last user command"
			::= { fkV2IgmpSourceControl 5 }

		
--  1.3.6.1.4.1.10428 9 1.102.12.2.2.4.3.2.6
		-- 1.3.6.1.4.1.10428 9 1.102.12.2.2.4.3.2.6
		fkV2IgmpSourceControlIfIndex OBJECT-TYPE
			SYNTAX Integer32
			MAX-ACCESS read-write
			STATUS current
			DESCRIPTION
				"interface index."
			::= { fkV2IgmpSourceControl 6 }

		
--  1.3.6.1.4.1.10428 9 1.102.12.2.2.4.3.2.7
		-- 1.3.6.1.4.1.10428 9 1.102.12.2.2.4.3.2.7
		fkV2IgmpSourceControlGroup OBJECT-TYPE
			SYNTAX IpAddress
			MAX-ACCESS read-write
			STATUS current
			DESCRIPTION
				" The group IP address"
			::= { fkV2IgmpSourceControl 7 }

		
--  1.3.6.1.4.1.10428 9 1.102.12.2.2.4.3.2.8
		-- 1.3.6.1.4.1.10428 9 1.102.12.2.2.4.3.2.8
		fkV2IgmpSourceControlAddress OBJECT-TYPE
			SYNTAX IpAddress
			MAX-ACCESS read-write
			STATUS current
			DESCRIPTION
				" The source IP address"
			::= { fkV2IgmpSourceControl 8 }

		
--  IGMP Cache Notification
-- 1.3.6.1.4.1.10428 9 1.102.12.2.2.4.3.3
		-- 1.3.6.1.4.1.10428 9 1.102.12.2.2.4.3.3
		fkV2IgmpSourceNotification OBJECT IDENTIFIER ::= { fkV2IgmpSource 3 }

		
--  1.3.6.1.4.1.10428 9 1.102.12.2.2.4.3.3.1
		-- 1.3.6.1.4.1.10428 9 1.102.12.2.2.4.3.3.1
		fkV2IgmpSourceCreated NOTIFICATION-TYPE
			OBJECTS { fkV2IgmpSourceControlRequest, fkV2IgmpSourceControlReqResult, fkV2IgmpSourceControlTimeStamp, fkV2IgmpSourceType }
			STATUS current
			DESCRIPTION 
				"In IGMPv3, Adding static (S,G) entry is imply that SourceFilterMode is 'allow'."
			::= { fkV2IgmpSourceNotification 1 }

		
--  1.3.6.1.4.1.10428 9 1.102.12.2.2.4.3.3.2
		-- 1.3.6.1.4.1.10428 9 1.102.12.2.2.4.3.3.2
		fkV2IgmpSourceDestroyed NOTIFICATION-TYPE
			OBJECTS { fkV2IgmpSourceControlRequest, fkV2IgmpSourceControlReqResult, fkV2IgmpSourceControlTimeStamp, fkV2IgmpSourceType }
			STATUS current
			DESCRIPTION 
				"In IGMPv3, Removing static (S,G) entry is imply that SourceFilterMode is 'block'."
			::= { fkV2IgmpSourceNotification 2 }

		
--  1.3.6.1.4.1.10428 9 1.102.12.2.2.4.4
		-- 1.3.6.1.4.1.10428 9 1.102.12.2.2.4.4
		fkV2IgmpGroupState OBJECT IDENTIFIER ::= { fkV2IgmpAgent 4 }

		
--  1.3.6.1.4.1.10428 9 1.102.12.2.2.4.4.1
		-- 1.3.6.1.4.1.10428 9 1.102.12.2.2.4.4.1
		fkV2IgmpGRunningTable OBJECT-TYPE
			SYNTAX SEQUENCE OF FkV2IgmpGRunningEntry
			MAX-ACCESS not-accessible
			STATUS current
			DESCRIPTION
				"IGMP group running table."
			::= { fkV2IgmpGroupState 1 }

		
--  1.3.6.1.4.1.10428 9 1.102.12.2.2.4.4.1.1
		-- 1.3.6.1.4.1.10428 9 1.102.12.2.2.4.4.1.1
		fkV2IgmpGRunningEntry OBJECT-TYPE
			SYNTAX FkV2IgmpGRunningEntry
			MAX-ACCESS not-accessible
			STATUS current
			DESCRIPTION
				"key: fkV2IgmpGRunningGroupAddr"
			INDEX { fkV2IgmpGRunningGroupAddr }
			::= { fkV2IgmpGRunningTable 1 }

		
		FkV2IgmpGRunningEntry ::=
			SEQUENCE { 
				fkV2IgmpGRunningGroupAddr
					IpAddress,
				fkV2IgmpGRunningTotalUptime
					OCTET STRING,
				fkV2IgmpGRunningLastJoined
					OCTET STRING,
				fkV2IgmpGRunningLastLeaved
					OCTET STRING,
				fkV2IgmpGRunningState
					INTEGER
			 }

--  1.3.6.1.4.1.10428 9 1.102.12.2.2.4.4.1.1.1
		-- 1.3.6.1.4.1.10428 9 1.102.12.2.2.4.4.1.1.1
		fkV2IgmpGRunningGroupAddr OBJECT-TYPE
			SYNTAX IpAddress
			MAX-ACCESS read-only
			STATUS current
			DESCRIPTION
				"IP multicast address learned by IGMP"
			::= { fkV2IgmpGRunningEntry 1 }

		
--  1.3.6.1.4.1.10428 9 1.102.12.2.2.4.4.1.1.2
		-- 1.3.6.1.4.1.10428 9 1.102.12.2.2.4.4.1.1.2
		fkV2IgmpGRunningTotalUptime OBJECT-TYPE
			SYNTAX OCTET STRING
			MAX-ACCESS read-only
			STATUS current
			DESCRIPTION
				"The total time of multicast service."
			::= { fkV2IgmpGRunningEntry 2 }

		
--  1.3.6.1.4.1.10428 9 1.102.12.2.2.4.4.1.1.3
		-- 1.3.6.1.4.1.10428 9 1.102.12.2.2.4.4.1.1.3
		fkV2IgmpGRunningLastJoined OBJECT-TYPE
			SYNTAX OCTET STRING
			MAX-ACCESS read-only
			STATUS current
			DESCRIPTION
				"The time have elapsed since the receiving last join message "
			::= { fkV2IgmpGRunningEntry 3 }

		
--  1.3.6.1.4.1.10428 9 1.102.12.2.2.4.4.1.1.4
		-- 1.3.6.1.4.1.10428 9 1.102.12.2.2.4.4.1.1.4
		fkV2IgmpGRunningLastLeaved OBJECT-TYPE
			SYNTAX OCTET STRING
			MAX-ACCESS read-only
			STATUS current
			DESCRIPTION
				"The time have elapsed since the receiving last leave message."
			::= { fkV2IgmpGRunningEntry 4 }

		
--  1.3.6.1.4.1.10428 9 1.102.12.2.2.4.4.1.1.5
		-- 1.3.6.1.4.1.10428 9 1.102.12.2.2.4.4.1.1.5
		fkV2IgmpGRunningState OBJECT-TYPE
			SYNTAX INTEGER
				{
				joined(1),
				leaved(2)
				}
			MAX-ACCESS read-only
			STATUS current
			DESCRIPTION
				"The state of multicast group."
			::= { fkV2IgmpGRunningEntry 5 }

		
--  1.3.6.1.4.1.10428 9 1.102.12.2.2.4.4.2
		-- 1.3.6.1.4.1.10428 9 1.102.12.2.2.4.4.2
		fkV2IgmpSRunningTable OBJECT-TYPE
			SYNTAX SEQUENCE OF FkV2IgmpSRunningEntry
			MAX-ACCESS not-accessible
			STATUS current
			DESCRIPTION
				"IGMP source running table."
			::= { fkV2IgmpGroupState 2 }

		
--  1.3.6.1.4.1.10428 9 1.102.12.2.2.4.4.2.1
		-- 1.3.6.1.4.1.10428 9 1.102.12.2.2.4.4.2.1
		fkV2IgmpSRunningEntry OBJECT-TYPE
			SYNTAX FkV2IgmpSRunningEntry
			MAX-ACCESS not-accessible
			STATUS current
			DESCRIPTION
				"key: fkV2IgmpSRunningGroupAddr, fkV2IgmpSRunningSourceAddr"
			INDEX { fkV2IgmpSRunningGroupAddr, fkV2IgmpSRunningSourceAddr }
			::= { fkV2IgmpSRunningTable 1 }

		
		FkV2IgmpSRunningEntry ::=
			SEQUENCE { 
				fkV2IgmpSRunningGroupAddr
					IpAddress,
				fkV2IgmpSRunningSourceAddr
					IpAddress,
				fkV2IgmpSRunningTotalUptime
					OCTET STRING,
				fkV2IgmpSRunningLastJoined
					OCTET STRING,
				fkV2IgmpSRunningLastLeaved
					OCTET STRING,
				fkV2IgmpSRunningState
					INTEGER
			 }

--  1.3.6.1.4.1.10428 9 1.102.12.2.2.4.4.2.1.1
		-- 1.3.6.1.4.1.10428 9 1.102.12.2.2.4.4.2.1.1
		fkV2IgmpSRunningGroupAddr OBJECT-TYPE
			SYNTAX IpAddress
			MAX-ACCESS read-only
			STATUS current
			DESCRIPTION
				"IP multicast address learned by IGMP."
			::= { fkV2IgmpSRunningEntry 1 }

		
--  1.3.6.1.4.1.10428 9 1.102.12.2.2.4.4.2.1.2
		-- 1.3.6.1.4.1.10428 9 1.102.12.2.2.4.4.2.1.2
		fkV2IgmpSRunningSourceAddr OBJECT-TYPE
			SYNTAX IpAddress
			MAX-ACCESS read-only
			STATUS current
			DESCRIPTION
				"The source ip adderess of multicast server."
			::= { fkV2IgmpSRunningEntry 2 }

		
--  1.3.6.1.4.1.10428 9 1.102.12.2.2.4.4.2.1.3
		-- 1.3.6.1.4.1.10428 9 1.102.12.2.2.4.4.2.1.3
		fkV2IgmpSRunningTotalUptime OBJECT-TYPE
			SYNTAX OCTET STRING
			MAX-ACCESS read-only
			STATUS current
			DESCRIPTION
				"The total time of multicast service."
			::= { fkV2IgmpSRunningEntry 3 }

		
--  1.3.6.1.4.1.10428 9 1.102.12.2.2.4.4.2.1.4
		-- 1.3.6.1.4.1.10428 9 1.102.12.2.2.4.4.2.1.4
		fkV2IgmpSRunningLastJoined OBJECT-TYPE
			SYNTAX OCTET STRING
			MAX-ACCESS read-only
			STATUS current
			DESCRIPTION
				"The time have elapsed since the receiving last join message "
			::= { fkV2IgmpSRunningEntry 4 }

		
--  1.3.6.1.4.1.10428 9 1.102.12.2.2.4.4.2.1.5
		-- 1.3.6.1.4.1.10428 9 1.102.12.2.2.4.4.2.1.5
		fkV2IgmpSRunningLastLeaved OBJECT-TYPE
			SYNTAX OCTET STRING
			MAX-ACCESS read-only
			STATUS current
			DESCRIPTION
				"The time have elapsed since the receiving last leave message."
			::= { fkV2IgmpSRunningEntry 5 }

		
--  1.3.6.1.4.1.10428 9 1.102.12.2.2.4.4.2.1.6
		-- 1.3.6.1.4.1.10428 9 1.102.12.2.2.4.4.2.1.6
		fkV2IgmpSRunningState OBJECT-TYPE
			SYNTAX INTEGER
				{
				joined(1),
				leaved(2)
				}
			MAX-ACCESS read-only
			STATUS current
			DESCRIPTION
				"The state of multicast group."
			::= { fkV2IgmpSRunningEntry 6 }

		
--  1.3.6.1.4.1.10428 9 1.102.12.2.2.4.4.3
		-- 1.3.6.1.4.1.10428 9 1.102.12.2.2.4.4.3
		fkV2IgmpGStateControl OBJECT IDENTIFIER ::= { fkV2IgmpGroupState 3 }

		
--  1.3.6.1.4.1.10428 9 1.102.12.2.2.4.4.3.1
		-- 1.3.6.1.4.1.10428 9 1.102.12.2.2.4.4.3.1
		fkV2IgmpGStateControlRequest OBJECT-TYPE
			SYNTAX INTEGER
				{
				clearGroupEntry(1),
				clearSessionEntry(2),
				clearAllEntry(3)
				}
			MAX-ACCESS read-write
			STATUS current
			DESCRIPTION
				"The request of a user command"
			::= { fkV2IgmpGStateControl 1 }

		
--  1.3.6.1.4.1.10428 9 1.102.12.2.2.4.4.3.2
		-- 1.3.6.1.4.1.10428 9 1.102.12.2.2.4.4.3.2
		fkV2IgmpGStateControlStatus OBJECT-TYPE
			SYNTAX FkControlStatusType
			MAX-ACCESS read-only
			STATUS current
			DESCRIPTION
				"The status of user command"
			::= { fkV2IgmpGStateControl 2 }

		
--  1.3.6.1.4.1.10428 9 1.102.12.2.2.4.4.3.3
		-- 1.3.6.1.4.1.10428 9 1.102.12.2.2.4.4.3.3
		fkV2IgmpGStateControlTimer OBJECT-TYPE
			SYNTAX Gauge32
			MAX-ACCESS read-write
			STATUS current
			DESCRIPTION
				"The maximum time for the manager for a long running user command"
			::= { fkV2IgmpGStateControl 3 }

		
--  1.3.6.1.4.1.10428 9 1.102.12.2.2.4.4.3.4
		-- 1.3.6.1.4.1.10428 9 1.102.12.2.2.4.4.3.4
		fkV2IgmpGStateControlTimeStamp OBJECT-TYPE
			SYNTAX TimeStamp
			MAX-ACCESS read-only
			STATUS current
			DESCRIPTION
				"The time stamp of the last command(end of command)"
			::= { fkV2IgmpGStateControl 4 }

		
--  1.3.6.1.4.1.10428 9 1.102.12.2.2.4.4.3.5
		-- 1.3.6.1.4.1.10428 9 1.102.12.2.2.4.4.3.5
		fkV2IgmpGStateControlRequestResult OBJECT-TYPE
			SYNTAX FkControlRequestResultType
			MAX-ACCESS read-only
			STATUS current
			DESCRIPTION
				"The result of the last user command"
			::= { fkV2IgmpGStateControl 5 }

		
--  1.3.6.1.4.1.10428 9 1.102.12.2.2.4.4.3.6
		-- 1.3.6.1.4.1.10428 9 1.102.12.2.2.4.4.3.6
		fkV2IgmpGStateControlGroupAddr OBJECT-TYPE
			SYNTAX IpAddress
			MAX-ACCESS read-write
			STATUS current
			DESCRIPTION
				"IP multicast address learned by IGMP."
			::= { fkV2IgmpGStateControl 6 }

		
--  1.3.6.1.4.1.10428 9 1.102.12.2.2.4.4.3.7
		-- 1.3.6.1.4.1.10428 9 1.102.12.2.2.4.4.3.7
		fkV2IgmpGStateControlSourceAddr OBJECT-TYPE
			SYNTAX IpAddress
			MAX-ACCESS read-write
			STATUS current
			DESCRIPTION
				"IP multicast address learned by IGMP."
			::= { fkV2IgmpGStateControl 7 }

		
--  1.3.6.1.4.1.10428 9 1.102.12.2.2.4.4.4
		-- 1.3.6.1.4.1.10428 9 1.102.12.2.2.4.4.4
		fkV2IgmpGStateNotification OBJECT IDENTIFIER ::= { fkV2IgmpGroupState 4 }

		
--  1.3.6.1.4.1.10428 9 1.102.12.2.2.4.4.4.1
		-- 1.3.6.1.4.1.10428 9 1.102.12.2.2.4.4.4.1
		fkV2IgmpGStateGroupCleared NOTIFICATION-TYPE
			OBJECTS { fkV2IgmpGStateControlRequest, fkV2IgmpGStateControlTimeStamp, fkV2IgmpGStateControlRequestResult, fkV2IgmpGStateControlGroupAddr }
			STATUS current
			DESCRIPTION 
				"Description."
			::= { fkV2IgmpGStateNotification 1 }

		
--  1.3.6.1.4.1.10428 9 1.102.12.2.2.4.4.4.2
		-- 1.3.6.1.4.1.10428 9 1.102.12.2.2.4.4.4.2
		fkV2IgmpGStateSessionCleared NOTIFICATION-TYPE
			OBJECTS { fkV2IgmpGStateControlRequest, fkV2IgmpGStateControlTimeStamp, fkV2IgmpGStateControlRequestResult, fkV2IgmpGStateControlGroupAddr, fkV2IgmpGStateControlSourceAddr
				 }
			STATUS current
			DESCRIPTION 
				"Description."
			::= { fkV2IgmpGStateNotification 2 }

		
--  1.3.6.1.4.1.10428 9 1.102.12.2.2.4.4.4.3
		-- 1.3.6.1.4.1.10428 9 1.102.12.2.2.4.4.4.3
		fkV2IgmpGStateAllCleared NOTIFICATION-TYPE
			OBJECTS { fkV2IgmpGStateControlRequest, fkV2IgmpGStateControlTimeStamp, fkV2IgmpGStateControlRequestResult }
			STATUS current
			DESCRIPTION 
				"Description."
			::= { fkV2IgmpGStateNotification 3 }

		
--  IGMP Snooping
-- 1.3.6.1.4.1.10428 9 1.102.12.2.2.5
		-- 1.3.6.1.4.1.10428 9 1.102.12.2.2.5
		fkV2IgmpSnooping OBJECT IDENTIFIER ::= { fkV2Igmp 5 }

		
--  IGMP Snooping VLAN
-- 1.3.6.1.4.1.10428 9 1.102.12.2.2.5.1
		-- 1.3.6.1.4.1.10428 9 1.102.12.2.2.5.1
		fkV2IgsVlan OBJECT IDENTIFIER ::= { fkV2IgmpSnooping 1 }

		
--  IGMP Snooping VLAN Table
-- 1.3.6.1.4.1.10428 9 1.102.12.2.2.5.1.1
		-- 1.3.6.1.4.1.10428 9 1.102.12.2.2.5.1.1
		fkV2IgsVlanTable OBJECT-TYPE
			SYNTAX SEQUENCE OF FkV2IgsVlanEntry
			MAX-ACCESS not-accessible
			STATUS current
			DESCRIPTION
				" IGS vlan table."
			::= { fkV2IgsVlan 1 }

		
--  IGMP Snooping VLAN Entry
-- 1.3.6.1.4.1.10428 9 1.102.12.2.2.5.1.1.1
		-- 1.3.6.1.4.1.10428 9 1.102.12.2.2.5.1.1.1
		fkV2IgsVlanEntry OBJECT-TYPE
			SYNTAX FkV2IgsVlanEntry
			MAX-ACCESS not-accessible
			STATUS current
			DESCRIPTION
				"Index field will be added by Na, Hojin
				key: fkV2IgsVlanIndex"
			INDEX { fkV2IgsVlanIndex }
			::= { fkV2IgsVlanTable 1 }

		
		FkV2IgsVlanEntry ::=
			SEQUENCE { 
				fkV2IgsVlanIndex
					INTEGER,
				fkV2IgsVlanActivity
					Boolean,
				fkV2IgsVlanVersion
					INTEGER,
				fkV2IgsVlanVersionMode
					INTEGER,
				fkV2IgsVlanFastLeave
					Boolean,
				fkV2IgsVlanFastBlock
					Boolean,
				fkV2IgsVlanMRtLearningMode
					INTEGER,
				fkV2IgsVlanMRtDynamicPortMap
					OCTET STRING,
				fkV2IgsVlanMRtStaticPortMap
					OCTET STRING,
				fkV2IgsVlanReportSuppression
					Boolean,
				fkV2IgsVlanQuerierActivity
					Boolean,
				fkV2IgsVlanQueryInterval
					Unsigned32,
				fkV2IgsVlanRobustness
					Unsigned32,
				fkV2IgsVlanMaxResponseTime
					Unsigned32,
				fkV2IgsVlanQuerierTimeOut
					Unsigned32,
				fkV2IgsVlanLastMembQueryIntvl
					Unsigned32,
				fkV2IgsVlanLastMembQueryCount
					Unsigned32,
				fkV2IgsVlanQuerierState
					INTEGER,
				fkV2IgsVlanQuerierVersion
					INTEGER,
				fkV2IgsVlanQuerierAddress
					IpAddress,
				fkV2IgsVlanQuerierPortIndex
					INTEGER,
				fkV2IgsVlanQuerierUptime
					TimeTicks,
				fkV2IgsVlanQuerierExpireTime
					TimeTicks,
				fkV2IgsVlanTcnFloodActivity
					Boolean,
				fkV2IgsVlanExplicitTracking
					Boolean,
				fkV2IgsVlanTxGeneralQueries
					Counter32,
				fkV2IgsVlanTxSpecialQueries
					Counter32,
				fkV2IgsVlanTxReportMessages
					Counter32,
				fkV2IgsVlanTxLeaveMessages
					Counter32,
				fkV2IgsVlanRxGeneralQueries
					Counter32,
				fkV2IgsVlanRxSpecialQueries
					Counter32,
				fkV2IgsVlanRxReportMessages
					Counter32,
				fkV2IgsVlanRxLeaveMessages
					Counter32,
				fkV2IgsVlanRxValidMessages
					Counter32,
				fkV2IgsVlanRxWrongMessages
					Counter32
			 }

--  1.3.6.1.4.1.10428 9 1.102.12.2.2.5.1.1.1.1
		-- 1.3.6.1.4.1.10428 9 1.102.12.2.2.5.1.1.1.1
		fkV2IgsVlanIndex OBJECT-TYPE
			SYNTAX INTEGER (1..4094)
			MAX-ACCESS read-only
			STATUS current
			DESCRIPTION
				"This object indicates the VLAN in which IGMP Snooping is configured. (= fkNetIfIndex)"
			::= { fkV2IgsVlanEntry 1 }

		
--  1.3.6.1.4.1.10428 9 1.102.12.2.2.5.1.1.1.2
		-- 1.3.6.1.4.1.10428 9 1.102.12.2.2.5.1.1.1.2
		fkV2IgsVlanActivity OBJECT-TYPE
			SYNTAX Boolean
			MAX-ACCESS read-only
			STATUS current
			DESCRIPTION
				"When this object is set to 'true' IGMP Snooping is enabled on this VLAN else disabled."
			::= { fkV2IgsVlanEntry 2 }

		
--  1.3.6.1.4.1.10428 9 1.102.12.2.2.5.1.1.1.3
		-- 1.3.6.1.4.1.10428 9 1.102.12.2.2.5.1.1.1.3
		fkV2IgsVlanVersion OBJECT-TYPE
			SYNTAX INTEGER
				{
				igmpV1(1),
				igmpV2(2),
				igmpV3(3)
				}
			MAX-ACCESS read-only
			STATUS current
			DESCRIPTION
				"This object indicate IGMP version on the VLAN that IGMP Snooping is enabled."
			::= { fkV2IgsVlanEntry 3 }

		
--  1.3.6.1.4.1.10428 9 1.102.12.2.2.5.1.1.1.4
		-- 1.3.6.1.4.1.10428 9 1.102.12.2.2.5.1.1.1.4
		fkV2IgsVlanVersionMode OBJECT-TYPE
			SYNTAX INTEGER
				{
				static(0),
				dynamic(1)
				}
			MAX-ACCESS read-write
			STATUS current
			DESCRIPTION
				"IGMP Snooping Version Mode on the VLAN."
			::= { fkV2IgsVlanEntry 4 }

		
--  1.3.6.1.4.1.10428 9 1.102.12.2.2.5.1.1.1.5
		-- 1.3.6.1.4.1.10428 9 1.102.12.2.2.5.1.1.1.5
		fkV2IgsVlanFastLeave OBJECT-TYPE
			SYNTAX Boolean
			MAX-ACCESS read-only
			STATUS current
			DESCRIPTION
				"This object specifies whether Fast-Leave mechanism (also known as Immediate-Leave) is to be performed by IGMP Snooping or not. When enabled, IGMP Snooping will remove the interface from the group mentioned in the IGMP Leave message received on that interface without waiting for the IGMP Group-Specific Query to timeout to determine whether there are any more hosts on that interface for that group."
			::= { fkV2IgsVlanEntry 5 }

		
--  1.3.6.1.4.1.10428 9 1.102.12.2.2.5.1.1.1.6
		-- 1.3.6.1.4.1.10428 9 1.102.12.2.2.5.1.1.1.6
		fkV2IgsVlanFastBlock OBJECT-TYPE
			SYNTAX Boolean
			MAX-ACCESS read-only
			STATUS current
			DESCRIPTION
				"The object indicates whether Fast-Block mechanism has been enabled for the VLAN. This object only has effect if the value of fkV2IgsVlanVersion is 3."
			::= { fkV2IgsVlanEntry 6 }

		
--  1.3.6.1.4.1.10428 9 1.102.12.2.2.5.1.1.1.7
		-- 1.3.6.1.4.1.10428 9 1.102.12.2.2.5.1.1.1.7
		fkV2IgsVlanMRtLearningMode OBJECT-TYPE
			SYNTAX INTEGER
				{
				none(0),
				pim(1)
				}
			MAX-ACCESS read-only
			STATUS current
			DESCRIPTION
				"This object specifies the multicast router port learning method for IGMP Snooping as described below:none(0) : don't learning, Only use static router ports.pim(1) : Protocol Independent Multicast."
			::= { fkV2IgsVlanEntry 7 }

		
--  1.3.6.1.4.1.10428 9 1.102.12.2.2.5.1.1.1.8
		-- 1.3.6.1.4.1.10428 9 1.102.12.2.2.5.1.1.1.8
		fkV2IgsVlanMRtDynamicPortMap OBJECT-TYPE
			SYNTAX OCTET STRING (SIZE (0..64))
			MAX-ACCESS read-only
			STATUS current
			DESCRIPTION
				"Multicast router ports learned by dynamic method (ex: PIM when MRouterLearningMode is 'pim'"
			::= { fkV2IgsVlanEntry 8 }

		
--  1.3.6.1.4.1.10428 9 1.102.12.2.2.5.1.1.1.9
		-- 1.3.6.1.4.1.10428 9 1.102.12.2.2.5.1.1.1.9
		fkV2IgsVlanMRtStaticPortMap OBJECT-TYPE
			SYNTAX OCTET STRING (SIZE (0..64))
			MAX-ACCESS read-only
			STATUS current
			DESCRIPTION
				"Multicast router ports setted by administrative maner. Bit 0 is CPU port."
			::= { fkV2IgsVlanEntry 9 }

		
--  1.3.6.1.4.1.10428 9 1.102.12.2.2.5.1.1.1.10
		-- 1.3.6.1.4.1.10428 9 1.102.12.2.2.5.1.1.1.10
		fkV2IgsVlanReportSuppression OBJECT-TYPE
			SYNTAX Boolean
			MAX-ACCESS read-only
			STATUS current
			DESCRIPTION
				"It's TRUE, IGMP Snooping will suppress duplicate IGMP Reports on the VLAN. FALSE, all IGMP Reports are forwarded to multicast routers on the VLAN. Alias of this is IGMP Snooping Proxy."
			::= { fkV2IgsVlanEntry 10 }

		
--  1.3.6.1.4.1.10428 9 1.102.12.2.2.5.1.1.1.11
		-- 1.3.6.1.4.1.10428 9 1.102.12.2.2.5.1.1.1.11
		fkV2IgsVlanQuerierActivity OBJECT-TYPE
			SYNTAX Boolean
			MAX-ACCESS read-only
			STATUS current
			DESCRIPTION
				"The object indicates whether the device will participate in the IGMP Querier election in a VLAN. If the object is set to 'true', the device will participate to an election process to be a Querier. If this is set to 'false' while the device is acting as the Querier in a VLAN, a new election will be activated to choose a different Querier."
			::= { fkV2IgsVlanEntry 11 }

		
--  1.3.6.1.4.1.10428 9 1.102.12.2.2.5.1.1.1.12
		-- 1.3.6.1.4.1.10428 9 1.102.12.2.2.5.1.1.1.12
		fkV2IgsVlanQueryInterval OBJECT-TYPE
			SYNTAX Unsigned32 (0..31744)
			MAX-ACCESS read-only
			STATUS current
			DESCRIPTION
				"The frequency at which IGMP packets are transmitted on this interface."
			::= { fkV2IgsVlanEntry 12 }

		
--  1.3.6.1.4.1.10428 9 1.102.12.2.2.5.1.1.1.13
		-- 1.3.6.1.4.1.10428 9 1.102.12.2.2.5.1.1.1.13
		fkV2IgsVlanRobustness OBJECT-TYPE
			SYNTAX Unsigned32 (1..255)
			MAX-ACCESS read-only
			STATUS current
			DESCRIPTION
				"The Robustness Variable allows tuning for the expected packet loss on a subnet. If a subnet is expected to be lossy, the Robustness Variable may be increased. IGMP is robust to (Robustness Variable-1) packet losses."
			::= { fkV2IgsVlanEntry 13 }

		
--  1.3.6.1.4.1.10428 9 1.102.12.2.2.5.1.1.1.14
		-- 1.3.6.1.4.1.10428 9 1.102.12.2.2.5.1.1.1.14
		fkV2IgsVlanMaxResponseTime OBJECT-TYPE
			SYNTAX Unsigned32 (0..31744)
			MAX-ACCESS read-only
			STATUS current
			DESCRIPTION
				"The maximum query response time advertised in queries on this interface."
			::= { fkV2IgsVlanEntry 14 }

		
--  1.3.6.1.4.1.10428 9 1.102.12.2.2.5.1.1.1.15
		-- 1.3.6.1.4.1.10428 9 1.102.12.2.2.5.1.1.1.15
		fkV2IgsVlanQuerierTimeOut OBJECT-TYPE
			SYNTAX Unsigned32 (0..31744)
			MAX-ACCESS read-only
			STATUS current
			DESCRIPTION
				"Other Querier Present Interval. Default value is (QueryInterval * Robustness) + (MaxResponseTime / 2)"
			::= { fkV2IgsVlanEntry 15 }

		
--  1.3.6.1.4.1.10428 9 1.102.12.2.2.5.1.1.1.16
		-- 1.3.6.1.4.1.10428 9 1.102.12.2.2.5.1.1.1.16
		fkV2IgsVlanLastMembQueryIntvl OBJECT-TYPE
			SYNTAX Unsigned32 (0..31744)
			MAX-ACCESS read-only
			STATUS current
			DESCRIPTION
				"The Last Member Query Interval is the Max Response Time inserted into Group-Specific Queries sent in response to Leave Group messages, and is also the amount of time Between Group-Specific Query messages. This value may be tuned to modify the leave latency of the network. A reduced value results in reduced time to detect the loss of the last member of a group. The value of this object is irrelevant if mgmdRouterInterfaceVersion is 1"
			::= { fkV2IgsVlanEntry 16 }

		
--  1.3.6.1.4.1.10428 9 1.102.12.2.2.5.1.1.1.17
		-- 1.3.6.1.4.1.10428 9 1.102.12.2.2.5.1.1.1.17
		fkV2IgsVlanLastMembQueryCount OBJECT-TYPE
			SYNTAX Unsigned32 (1..255)
			MAX-ACCESS read-only
			STATUS current
			DESCRIPTION
				"Represents the number of Group-specific and Group-and-Source-specific queries sent by the router before it assumes there are no local members."
			::= { fkV2IgsVlanEntry 17 }

		
--  1.3.6.1.4.1.10428 9 1.102.12.2.2.5.1.1.1.18
		-- 1.3.6.1.4.1.10428 9 1.102.12.2.2.5.1.1.1.18
		fkV2IgsVlanQuerierState OBJECT-TYPE
			SYNTAX INTEGER
				{
				disabled(1),
				electing(2),
				querier(3),
				candidate(4),
				inactive(5)
				}
			MAX-ACCESS read-only
			STATUS current
			DESCRIPTION
				"The object indicates the current state of the device as an IGMP Querier in a VLAN.disabled(1) : Querier function is disabled for this device in this VLAN.electing(2) : It is in the election process of the Querier.querier(3) : It is the current Querier in this VLAN.candidate (4): It is a alternative Querier in this VLAN.inactive(5) : VLAN is inactive or not an Ethernet"
			::= { fkV2IgsVlanEntry 18 }

		
--  1.3.6.1.4.1.10428 9 1.102.12.2.2.5.1.1.1.19
		-- 1.3.6.1.4.1.10428 9 1.102.12.2.2.5.1.1.1.19
		fkV2IgsVlanQuerierVersion OBJECT-TYPE
			SYNTAX INTEGER
				{
				one(1),
				two(2),
				three(3)
				}
			MAX-ACCESS read-only
			STATUS current
			DESCRIPTION
				"The object indicates IGMP version of the Querier for the VLAN. IGMP version of the Querier is determined by the type of IGMP General Query received by the device."
			::= { fkV2IgsVlanEntry 19 }

		
--  1.3.6.1.4.1.10428 9 1.102.12.2.2.5.1.1.1.20
		-- 1.3.6.1.4.1.10428 9 1.102.12.2.2.5.1.1.1.20
		fkV2IgsVlanQuerierAddress OBJECT-TYPE
			SYNTAX IpAddress
			MAX-ACCESS read-only
			STATUS current
			DESCRIPTION
				"It is IP address of the IGMP Querier for the VLAN."
			::= { fkV2IgsVlanEntry 20 }

		
--  1.3.6.1.4.1.10428 9 1.102.12.2.2.5.1.1.1.21
		-- 1.3.6.1.4.1.10428 9 1.102.12.2.2.5.1.1.1.21
		fkV2IgsVlanQuerierPortIndex OBJECT-TYPE
			SYNTAX INTEGER (0..255)
			MAX-ACCESS read-only
			STATUS current
			DESCRIPTION
				"It is the port on which IGMP Querier is detected for the VLAN. It is zero if the device itself is acting as IGMP Querier for the VLAN."
			::= { fkV2IgsVlanEntry 21 }

		
--  1.3.6.1.4.1.10428 9 1.102.12.2.2.5.1.1.1.22
		-- 1.3.6.1.4.1.10428 9 1.102.12.2.2.5.1.1.1.22
		fkV2IgsVlanQuerierUptime OBJECT-TYPE
			SYNTAX TimeTicks
			MAX-ACCESS read-only
			STATUS current
			DESCRIPTION
				"The time since Querier on the VLAN was last changed."
			::= { fkV2IgsVlanEntry 22 }

		
--  1.3.6.1.4.1.10428 9 1.102.12.2.2.5.1.1.1.23
		-- 1.3.6.1.4.1.10428 9 1.102.12.2.2.5.1.1.1.23
		fkV2IgsVlanQuerierExpireTime OBJECT-TYPE
			SYNTAX TimeTicks
			MAX-ACCESS read-only
			STATUS current
			DESCRIPTION
				"The amount of time remaining before the Other Querier Present Timer expires. If the local system is the querier, the value of this object is zero."
			::= { fkV2IgsVlanEntry 23 }

		
--  1.3.6.1.4.1.10428 9 1.102.12.2.2.5.1.1.1.24
		-- 1.3.6.1.4.1.10428 9 1.102.12.2.2.5.1.1.1.24
		fkV2IgsVlanTcnFloodActivity OBJECT-TYPE
			SYNTAX Boolean
			MAX-ACCESS read-only
			STATUS current
			DESCRIPTION
				"TRUE is multicast traffic will be flooded on all ports of the VLAN for TcnFloodQueryCount of IGMP General Queries upon receiving a Topology Change Notification (TCN) for the VLAN. FALSE is not flooding."
			::= { fkV2IgsVlanEntry 24 }

		
--  1.3.6.1.4.1.10428 9 1.102.12.2.2.5.1.1.1.25
		-- 1.3.6.1.4.1.10428 9 1.102.12.2.2.5.1.1.1.25
		fkV2IgsVlanExplicitTracking OBJECT-TYPE
			SYNTAX Boolean
			MAX-ACCESS read-only
			STATUS current
			DESCRIPTION
				"In IGMPv3, it decide the device tracks reporters or not."
			::= { fkV2IgsVlanEntry 25 }

		
--  1.3.6.1.4.1.10428 9 1.102.12.2.2.5.1.1.1.26
		-- 1.3.6.1.4.1.10428 9 1.102.12.2.2.5.1.1.1.26
		fkV2IgsVlanTxGeneralQueries OBJECT-TYPE
			SYNTAX Counter32
			MAX-ACCESS read-only
			STATUS current
			DESCRIPTION
				"Total IGMP General Queries that have been transmitted through an interface."
			::= { fkV2IgsVlanEntry 26 }

		
--  1.3.6.1.4.1.10428 9 1.102.12.2.2.5.1.1.1.27
		-- 1.3.6.1.4.1.10428 9 1.102.12.2.2.5.1.1.1.27
		fkV2IgsVlanTxSpecialQueries OBJECT-TYPE
			SYNTAX Counter32
			MAX-ACCESS read-only
			STATUS current
			DESCRIPTION
				"Total IGMP Group-Specific Queries that have been transmitted through an interface."
			::= { fkV2IgsVlanEntry 27 }

		
--  1.3.6.1.4.1.10428 9 1.102.12.2.2.5.1.1.1.28
		-- 1.3.6.1.4.1.10428 9 1.102.12.2.2.5.1.1.1.28
		fkV2IgsVlanTxReportMessages OBJECT-TYPE
			SYNTAX Counter32
			MAX-ACCESS read-only
			STATUS current
			DESCRIPTION
				"Total IGMP Membership Reports that have been transmitted through an interface."
			::= { fkV2IgsVlanEntry 28 }

		
--  1.3.6.1.4.1.10428 9 1.102.12.2.2.5.1.1.1.29
		-- 1.3.6.1.4.1.10428 9 1.102.12.2.2.5.1.1.1.29
		fkV2IgsVlanTxLeaveMessages OBJECT-TYPE
			SYNTAX Counter32
			MAX-ACCESS read-only
			STATUS current
			DESCRIPTION
				"Total IGMP Leave messages that have been transmitted through an interface."
			::= { fkV2IgsVlanEntry 29 }

		
--  1.3.6.1.4.1.10428 9 1.102.12.2.2.5.1.1.1.30
		-- 1.3.6.1.4.1.10428 9 1.102.12.2.2.5.1.1.1.30
		fkV2IgsVlanRxGeneralQueries OBJECT-TYPE
			SYNTAX Counter32
			MAX-ACCESS read-only
			STATUS current
			DESCRIPTION
				"Total IGMP General Queries that have been received at an interface."
			::= { fkV2IgsVlanEntry 30 }

		
--  1.3.6.1.4.1.10428 9 1.102.12.2.2.5.1.1.1.31
		-- 1.3.6.1.4.1.10428 9 1.102.12.2.2.5.1.1.1.31
		fkV2IgsVlanRxSpecialQueries OBJECT-TYPE
			SYNTAX Counter32
			MAX-ACCESS read-only
			STATUS current
			DESCRIPTION
				"Total IGMP Group-Specific Queries that have been received at an interface."
			::= { fkV2IgsVlanEntry 31 }

		
--  1.3.6.1.4.1.10428 9 1.102.12.2.2.5.1.1.1.32
		-- 1.3.6.1.4.1.10428 9 1.102.12.2.2.5.1.1.1.32
		fkV2IgsVlanRxReportMessages OBJECT-TYPE
			SYNTAX Counter32
			MAX-ACCESS read-only
			STATUS current
			DESCRIPTION
				"Total IGMP Membership Reports that have been received at an interface."
			::= { fkV2IgsVlanEntry 32 }

		
--  1.3.6.1.4.1.10428 9 1.102.12.2.2.5.1.1.1.33
		-- 1.3.6.1.4.1.10428 9 1.102.12.2.2.5.1.1.1.33
		fkV2IgsVlanRxLeaveMessages OBJECT-TYPE
			SYNTAX Counter32
			MAX-ACCESS read-only
			STATUS current
			DESCRIPTION
				"Total IGMP Leave messages that have been received at an interface."
			::= { fkV2IgsVlanEntry 33 }

		
--  1.3.6.1.4.1.10428 9 1.102.12.2.2.5.1.1.1.34
		-- 1.3.6.1.4.1.10428 9 1.102.12.2.2.5.1.1.1.34
		fkV2IgsVlanRxValidMessages OBJECT-TYPE
			SYNTAX Counter32
			MAX-ACCESS read-only
			STATUS current
			DESCRIPTION
				"Total valid IGMP packets have been received at an interface."
			::= { fkV2IgsVlanEntry 34 }

		
--  1.3.6.1.4.1.10428 9 1.102.12.2.2.5.1.1.1.35
		-- 1.3.6.1.4.1.10428 9 1.102.12.2.2.5.1.1.1.35
		fkV2IgsVlanRxWrongMessages OBJECT-TYPE
			SYNTAX Counter32
			MAX-ACCESS read-only
			STATUS current
			DESCRIPTION
				"Total packets those are not valid IGMP messages received at an interface."
			::= { fkV2IgsVlanEntry 35 }

		
--  IGMP Snooping VLAN Control
-- 1.3.6.1.4.1.10428 9 1.102.12.2.2.5.1.2
		-- 1.3.6.1.4.1.10428 9 1.102.12.2.2.5.1.2
		fkV2IgsVlanControl OBJECT IDENTIFIER ::= { fkV2IgsVlan 2 }

		
--  1.3.6.1.4.1.10428 9 1.102.12.2.2.5.1.2.1
		-- 1.3.6.1.4.1.10428 9 1.102.12.2.2.5.1.2.1
		fkV2IgsVlanControlRequest OBJECT-TYPE
			SYNTAX INTEGER
				{
				createIgmpSnoopVlan(1),
				destroyIgmpSnoopVlan(2),
				setIgmpSnoopVlanProfile(3),
				setIgmpSnoopMRouteProfile(4),
				setIgmpSnoopQuerierProfile(5),
				setIgmpSnoopTcnProfile(6),
				clearIgmpSnoopStatistics(7)
				}
			MAX-ACCESS read-write
			STATUS current
			DESCRIPTION
				" The request of a user command"
			::= { fkV2IgsVlanControl 1 }

		
--  1.3.6.1.4.1.10428 9 1.102.12.2.2.5.1.2.2
		-- 1.3.6.1.4.1.10428 9 1.102.12.2.2.5.1.2.2
		fkV2IgsVlanControlStatus OBJECT-TYPE
			SYNTAX FkControlStatusType
			MAX-ACCESS read-only
			STATUS current
			DESCRIPTION
				" The status of user command"
			::= { fkV2IgsVlanControl 2 }

		
--  1.3.6.1.4.1.10428 9 1.102.12.2.2.5.1.2.3
		-- 1.3.6.1.4.1.10428 9 1.102.12.2.2.5.1.2.3
		fkV2IgsVlanControlTimer OBJECT-TYPE
			SYNTAX Gauge32
			MAX-ACCESS read-write
			STATUS current
			DESCRIPTION
				" The maximum time for the manager for a long running user command"
			::= { fkV2IgsVlanControl 3 }

		
--  1.3.6.1.4.1.10428 9 1.102.12.2.2.5.1.2.4
		-- 1.3.6.1.4.1.10428 9 1.102.12.2.2.5.1.2.4
		fkV2IgsVlanControlTimeStamp OBJECT-TYPE
			SYNTAX TimeStamp
			MAX-ACCESS read-only
			STATUS current
			DESCRIPTION
				" The time stamp of the last command(end of command)"
			::= { fkV2IgsVlanControl 4 }

		
--  1.3.6.1.4.1.10428 9 1.102.12.2.2.5.1.2.5
		-- 1.3.6.1.4.1.10428 9 1.102.12.2.2.5.1.2.5
		fkV2IgsVlanControlReqResult OBJECT-TYPE
			SYNTAX FkControlRequestResultType
			MAX-ACCESS read-only
			STATUS current
			DESCRIPTION
				" The result of the last user command"
			::= { fkV2IgsVlanControl 5 }

		
--  1.3.6.1.4.1.10428 9 1.102.12.2.2.5.1.2.6
		-- 1.3.6.1.4.1.10428 9 1.102.12.2.2.5.1.2.6
		fkV2IgsVlanControlIndex OBJECT-TYPE
			SYNTAX INTEGER (1..4094)
			MAX-ACCESS read-write
			STATUS current
			DESCRIPTION
				"value(0) : all vlan"
			::= { fkV2IgsVlanControl 6 }

		
--  1.3.6.1.4.1.10428 9 1.102.12.2.2.5.1.2.7
		-- 1.3.6.1.4.1.10428 9 1.102.12.2.2.5.1.2.7
		fkV2IgsVlanControlActivity OBJECT-TYPE
			SYNTAX Boolean
			MAX-ACCESS read-write
			STATUS current
			DESCRIPTION
				"When this object is set to 'true' IGMP Snooping is enabled on this VLAN else disabled."
			::= { fkV2IgsVlanControl 7 }

		
--  1.3.6.1.4.1.10428 9 1.102.12.2.2.5.1.2.8
		-- 1.3.6.1.4.1.10428 9 1.102.12.2.2.5.1.2.8
		fkV2IgsVlanControlVersion OBJECT-TYPE
			SYNTAX INTEGER
				{
				dynamic(0),
				igmpV1(1),
				igmpV2(2),
				igmpV3(3)
				}
			MAX-ACCESS read-write
			STATUS current
			DESCRIPTION
				"default = igmpV3"
			::= { fkV2IgsVlanControl 8 }

		
--  1.3.6.1.4.1.10428 9 1.102.12.2.2.5.1.2.9
		-- 1.3.6.1.4.1.10428 9 1.102.12.2.2.5.1.2.9
		fkV2IgsVlanControlFastLeave OBJECT-TYPE
			SYNTAX Boolean
			MAX-ACCESS read-write
			STATUS current
			DESCRIPTION
				"This object specifies whether Fast-Leave mechanism (also known as Immediate-Leave) is to be performed by IGMP Snooping or not. When enabled, IGMP Snooping will remove the interface from the group mentioned in the IGMP Leave message received on that interface without waiting for the IGMP Group-Specific Query to timeout to determine whether there are any more hosts on that interface for that group."
			::= { fkV2IgsVlanControl 9 }

		
--  1.3.6.1.4.1.10428 9 1.102.12.2.2.5.1.2.10
		-- 1.3.6.1.4.1.10428 9 1.102.12.2.2.5.1.2.10
		fkV2IgsVlanControlFastBlock OBJECT-TYPE
			SYNTAX Boolean
			MAX-ACCESS read-write
			STATUS current
			DESCRIPTION
				"The object indicates whether Fast-Block mechanism has been enabled for the VLAN. This object only has effect if the value of fkV2IgsVlanVersion is 3."
			::= { fkV2IgsVlanControl 10 }

		
--  1.3.6.1.4.1.10428 9 1.102.12.2.2.5.1.2.11
		-- 1.3.6.1.4.1.10428 9 1.102.12.2.2.5.1.2.11
		fkV2IgsVlanControlMRtLearningMode OBJECT-TYPE
			SYNTAX INTEGER
				{
				none(0),
				pim(1)
				}
			MAX-ACCESS read-write
			STATUS current
			DESCRIPTION
				"This object specifies the multicast router port learning method for IGMP Snooping as described below:
				none(0) : don’t learning, Only use static router ports.
				pim(1) : Protocol Independent Multicast.
				"
			::= { fkV2IgsVlanControl 11 }

		
--  1.3.6.1.4.1.10428 9 1.102.12.2.2.5.1.2.12
		-- 1.3.6.1.4.1.10428 9 1.102.12.2.2.5.1.2.12
		fkV2IgsVlanControlMRtStaticPortMap OBJECT-TYPE
			SYNTAX OCTET STRING (SIZE (0..64))
			MAX-ACCESS read-write
			STATUS current
			DESCRIPTION
				"Multicast router ports learned by dynamic method (ex: PIM when MRouterLearningMode is ‘pim’"
			::= { fkV2IgsVlanControl 12 }

		
--  1.3.6.1.4.1.10428 9 1.102.12.2.2.5.1.2.13
		-- 1.3.6.1.4.1.10428 9 1.102.12.2.2.5.1.2.13
		fkV2IgsVlanControlReportSuppression OBJECT-TYPE
			SYNTAX Boolean
			MAX-ACCESS read-write
			STATUS current
			DESCRIPTION
				"It’s TRUE, IGMP Snooping will suppress duplicate IGMP Reports on the VLAN. FALSE, all IGMP Reports are forwarded to multicast routers on the VLAN. Alias of this is IGMP Snooping Proxy."
			::= { fkV2IgsVlanControl 13 }

		
--  1.3.6.1.4.1.10428 9 1.102.12.2.2.5.1.2.14
		-- 1.3.6.1.4.1.10428 9 1.102.12.2.2.5.1.2.14
		fkV2IgsVlanControlQuerierActivity OBJECT-TYPE
			SYNTAX Boolean
			MAX-ACCESS read-write
			STATUS current
			DESCRIPTION
				"The object indicates whether the device will participate in the IGMP Querier election in a VLAN. If the object is set to 'true', the device will participate to an election process to be a Querier. If this is set to 'false' while the device is acting as the Querier in a VLAN, a new election will be activated to choose a different Querier."
			::= { fkV2IgsVlanControl 14 }

		
--  1.3.6.1.4.1.10428 9 1.102.12.2.2.5.1.2.15
		-- 1.3.6.1.4.1.10428 9 1.102.12.2.2.5.1.2.15
		fkV2IgsVlanControlQueryInterval OBJECT-TYPE
			SYNTAX Unsigned32 (0..31744)
			MAX-ACCESS read-write
			STATUS current
			DESCRIPTION
				"The frequency at which IGMP packets are transmitted on this interface."
			::= { fkV2IgsVlanControl 15 }

		
--  1.3.6.1.4.1.10428 9 1.102.12.2.2.5.1.2.16
		-- 1.3.6.1.4.1.10428 9 1.102.12.2.2.5.1.2.16
		fkV2IgsVlanControlRobustness OBJECT-TYPE
			SYNTAX Unsigned32 (1..7)
			MAX-ACCESS read-write
			STATUS current
			DESCRIPTION
				"The Robustness Variable allows tuning for the expected packet loss on a subnet. If a subnet is expected to be lossy, the Robustness Variable may be increased. IGMP is robust to (Robustness Variable-1) packet losses."
			::= { fkV2IgsVlanControl 16 }

		
--  1.3.6.1.4.1.10428 9 1.102.12.2.2.5.1.2.17
		-- 1.3.6.1.4.1.10428 9 1.102.12.2.2.5.1.2.17
		fkV2IgsVlanControlMaxResponseTime OBJECT-TYPE
			SYNTAX Unsigned32 (0..31744)
			MAX-ACCESS read-write
			STATUS current
			DESCRIPTION
				"The maximum query response time advertised in queries on this interface."
			::= { fkV2IgsVlanControl 17 }

		
--  1.3.6.1.4.1.10428 9 1.102.12.2.2.5.1.2.18
		-- 1.3.6.1.4.1.10428 9 1.102.12.2.2.5.1.2.18
		fkV2IgsVlanControlQuerierTimeOut OBJECT-TYPE
			SYNTAX Unsigned32 (60..300)
			MAX-ACCESS read-write
			STATUS current
			DESCRIPTION
				"Other Querier Present Interval. Default value is (QueryInterval * Robustness) + (MaxResponseTime / 2)"
			::= { fkV2IgsVlanControl 18 }

		
--  1.3.6.1.4.1.10428 9 1.102.12.2.2.5.1.2.19
		-- 1.3.6.1.4.1.10428 9 1.102.12.2.2.5.1.2.19
		fkV2IgsVlanControlLastMembQueryIntvl OBJECT-TYPE
			SYNTAX Unsigned32 (0..31744)
			MAX-ACCESS read-write
			STATUS current
			DESCRIPTION
				"The Last Member Query Interval is the Max Response Time inserted into Group-Specific Queries sent in response to Leave Group messages, and is also the amount of time Between Group-Specific Query messages. This value may be tuned to modify the leave latency of the network. A reduced value results in reduced time to detect the loss of the last member of a group. The value of this object is irrelevant if mgmdRouterInterfaceVersion is 1"
			::= { fkV2IgsVlanControl 19 }

		
--  1.3.6.1.4.1.10428 9 1.102.12.2.2.5.1.2.20
		-- 1.3.6.1.4.1.10428 9 1.102.12.2.2.5.1.2.20
		fkV2IgsVlanControlTcnFloodActivity OBJECT-TYPE
			SYNTAX Boolean
			MAX-ACCESS read-write
			STATUS current
			DESCRIPTION
				"TRUE is multicast traffic will be flooded on all ports of the VLAN for TcnFloodQueryCount of IGMP General Queries upon receiving a Topology Change Notification (TCN) for the VLAN. FALSE is not flooding."
			::= { fkV2IgsVlanControl 20 }

		
--  1.3.6.1.4.1.10428 9 1.102.12.2.2.5.1.2.21
		-- 1.3.6.1.4.1.10428 9 1.102.12.2.2.5.1.2.21
		fkV2IgsVlanControlExplicitTracking OBJECT-TYPE
			SYNTAX Boolean
			MAX-ACCESS read-write
			STATUS current
			DESCRIPTION
				"In IGMPv3, it decide the device tracks reporters or not."
			::= { fkV2IgsVlanControl 21 }

		
		-- 1.3.6.1.4.1.10428 9 1.102.12.2.2.5.1.2.22
		fkV2IgsVlanControlQuerierAddress OBJECT-TYPE
			SYNTAX IpAddress
			MAX-ACCESS read-write
			STATUS current
			DESCRIPTION
				"Description."
			::= { fkV2IgsVlanControl 22 }

		
--  IGMP Snooping VLAN Notification
-- 1.3.6.1.4.1.10428 9 1.102.12.2.2.5.1.3
		-- 1.3.6.1.4.1.10428 9 1.102.12.2.2.5.1.3
		fkV2IgsVlanNotification OBJECT IDENTIFIER ::= { fkV2IgsVlan 3 }

		
--  1.3.6.1.4.1.10428 9 1.102.12.2.2.5.1.3.1
		-- 1.3.6.1.4.1.10428 9 1.102.12.2.2.5.1.3.1
		fkV2IgsVlanCreated NOTIFICATION-TYPE
			OBJECTS { fkV2IgsVlanControlRequest, fkV2IgsVlanControlTimeStamp, fkV2IgsVlanControlReqResult, fkV2IgsVlanActivity }
			STATUS current
			DESCRIPTION 
				"createIgmpSnoopVlan"
			::= { fkV2IgsVlanNotification 1 }

		
--  1.3.6.1.4.1.10428 9 1.102.12.2.2.5.1.3.2
		-- 1.3.6.1.4.1.10428 9 1.102.12.2.2.5.1.3.2
		fkV2IgsVlanDestroyed NOTIFICATION-TYPE
			OBJECTS { fkV2IgsVlanControlRequest, fkV2IgsVlanControlTimeStamp, fkV2IgsVlanControlReqResult, fkV2IgsVlanControlIndex }
			STATUS current
			DESCRIPTION 
				"destroyIgmpSnoopVlan"
			::= { fkV2IgsVlanNotification 2 }

		
--  1.3.6.1.4.1.10428 9 1.102.12.2.2.5.1.3.3
		-- 1.3.6.1.4.1.10428 9 1.102.12.2.2.5.1.3.3
		fkV2IgsVlanProfileChanged NOTIFICATION-TYPE
			OBJECTS { fkV2IgsVlanControlRequest, fkV2IgsVlanControlTimeStamp, fkV2IgsVlanControlReqResult, fkV2IgsVlanVersion, fkV2IgsVlanVersionMode, 
				fkV2IgsVlanFastLeave, fkV2IgsVlanFastBlock, fkV2IgsVlanReportSuppression, fkV2IgsVlanExplicitTracking }
			STATUS current
			DESCRIPTION 
				"setIgmpSnoopVlanProfile"
			::= { fkV2IgsVlanNotification 3 }

		
--  1.3.6.1.4.1.10428 9 1.102.12.2.2.5.1.3.4
		-- 1.3.6.1.4.1.10428 9 1.102.12.2.2.5.1.3.4
		fkV2IgsVlanMRouteProfileChanged NOTIFICATION-TYPE
			OBJECTS { fkV2IgsVlanControlRequest, fkV2IgsVlanControlTimeStamp, fkV2IgsVlanControlReqResult, fkV2IgsVlanMRtLearningMode, fkV2IgsVlanMRtStaticPortMap
				 }
			STATUS current
			DESCRIPTION 
				"setIgmpSnoopMRouteProfile"
			::= { fkV2IgsVlanNotification 4 }

		
--  1.3.6.1.4.1.10428 9 1.102.12.2.2.5.1.3.5
		-- 1.3.6.1.4.1.10428 9 1.102.12.2.2.5.1.3.5
		fkV2IgsVlanQuerierProfileChanced NOTIFICATION-TYPE
			OBJECTS { fkV2IgsVlanControlRequest, fkV2IgsVlanControlTimeStamp, fkV2IgsVlanControlReqResult, fkV2IgsVlanQuerierActivity, fkV2IgsVlanQueryInterval, 
				fkV2IgsVlanRobustness, fkV2IgsVlanMaxResponseTime, fkV2IgsVlanQuerierTimeOut, fkV2IgsVlanLastMembQueryIntvl, fkV2IgsVlanQuerierAddress
				 }
			STATUS current
			DESCRIPTION 
				"setIgmpSnoopQuerierProfile"
			::= { fkV2IgsVlanNotification 5 }

		
--  1.3.6.1.4.1.10428 9 1.102.12.2.2.5.1.3.6
		-- 1.3.6.1.4.1.10428 9 1.102.12.2.2.5.1.3.6
		fkV2IgsVlanTcnProfileChanced NOTIFICATION-TYPE
			OBJECTS { fkV2IgsVlanControlRequest, fkV2IgsVlanControlTimeStamp, fkV2IgsVlanControlReqResult, fkV2IgsVlanTcnFloodActivity }
			STATUS current
			DESCRIPTION 
				"setIgmpSnoopTcnProfile"
			::= { fkV2IgsVlanNotification 6 }

		
--  1.3.6.1.4.1.10428 9 1.102.12.2.2.5.1.3.7
		-- 1.3.6.1.4.1.10428 9 1.102.12.2.2.5.1.3.7
		fkV2IgsVlanStatisticsCleared NOTIFICATION-TYPE
			OBJECTS { fkV2IgsVlanControlRequest, fkV2IgsVlanControlTimeStamp, fkV2IgsVlanControlReqResult, fkV2IgsVlanControlIndex }
			STATUS current
			DESCRIPTION 
				"clearIgmpSnoopStatistics"
			::= { fkV2IgsVlanNotification 7 }

		
--  IGMP Snooping Group
-- 1.3.6.1.4.1.10428 9 1.102.12.2.2.5.2
		-- 1.3.6.1.4.1.10428 9 1.102.12.2.2.5.2
		fkV2IgsGroup OBJECT IDENTIFIER ::= { fkV2IgmpSnooping 2 }

		
--  IGMP Snooping Group Table
-- 1.3.6.1.4.1.10428 9 1.102.12.2.2.5.2.1
		-- 1.3.6.1.4.1.10428 9 1.102.12.2.2.5.2.1
		fkV2IgsGroupTable OBJECT-TYPE
			SYNTAX SEQUENCE OF FkV2IgsGroupEntry
			MAX-ACCESS not-accessible
			STATUS current
			DESCRIPTION
				"IGS group table."
			::= { fkV2IgsGroup 1 }

		
--  IGMP Snooping Group Entry
-- 1.3.6.1.4.1.10428 9 1.102.12.2.2.5.2.2.1
		-- 1.3.6.1.4.1.10428 9 1.102.12.2.2.5.2.1.1
		fkV2IgsGroupEntry OBJECT-TYPE
			SYNTAX FkV2IgsGroupEntry
			MAX-ACCESS not-accessible
			STATUS current
			DESCRIPTION
				"key: fkV2IgsVlanIndex, fkV2IgsGroupAddress, fkV2IgsGroupPortIndex"
			INDEX { fkV2IgsVlanIndex, fkV2IgsGroupAddress, fkV2IgsGroupPortIndex }
			::= { fkV2IgsGroupTable 1 }

		
		FkV2IgsGroupEntry ::=
			SEQUENCE { 
				fkV2IgsGroupAddress
					IpAddress,
				fkV2IgsGroupPortIndex
					INTEGER,
				fkV2IgsGroupSourceFilterMode
					INTEGER,
				fkV2IgsGroupExcludeModeExpiryTimer
					TimeTicks,
				fkV2IgsGroupUpTime
					TimeTicks,
				fkV2IgsGroupExpiryTime
					TimeTicks,
				fkV2IgsGroupPortInfo
					Integer32
			 }

--  1.3.6.1.4.1.10428 9 1.102.12.2.2.5.2.2.1.1
		-- 1.3.6.1.4.1.10428 9 1.102.12.2.2.5.2.1.1.1
		fkV2IgsGroupAddress OBJECT-TYPE
			SYNTAX IpAddress
			MAX-ACCESS read-only
			STATUS current
			DESCRIPTION
				"It is a IP multicast address learned by IGMP Snooping."
			::= { fkV2IgsGroupEntry 1 }

		
--  1.3.6.1.4.1.10428 9 1.102.12.2.2.5.2.2.1.2
		-- 1.3.6.1.4.1.10428 9 1.102.12.2.2.5.2.1.1.2
		fkV2IgsGroupPortIndex OBJECT-TYPE
			SYNTAX INTEGER (1..512)
			MAX-ACCESS read-only
			STATUS current
			DESCRIPTION
				"This object indicates the port on VLAN in which the group is learned."
			::= { fkV2IgsGroupEntry 2 }

		
--  1.3.6.1.4.1.10428 9 1.102.12.2.2.5.2.2.1.3
		-- 1.3.6.1.4.1.10428 9 1.102.12.2.2.5.2.1.1.3
		fkV2IgsGroupSourceFilterMode OBJECT-TYPE
			SYNTAX INTEGER
				{
				unknown(0),
				include(1),
				exclude(2)
				}
			MAX-ACCESS read-only
			STATUS current
			DESCRIPTION
				"The current group state, applicable to IGMPv3 compatible nodes. The value indicates whether the state is INCLUDE or EXCLUDE."
			::= { fkV2IgsGroupEntry 3 }

		
--  1.3.6.1.4.1.10428 9 1.102.12.2.2.5.2.2.1.4
		-- 1.3.6.1.4.1.10428 9 1.102.12.2.2.5.2.1.1.4
		fkV2IgsGroupExcludeModeExpiryTimer OBJECT-TYPE
			SYNTAX TimeTicks
			MAX-ACCESS read-only
			STATUS current
			DESCRIPTION
				"This value is applicable only to IGMPv3 compatible routers, and represents the time remaining before the interface EXCLUDE state expires and the interface state transitions to INCLUDE mode. This value can never be greater than fkV2IgmpCacheExpiryTime."
			::= { fkV2IgsGroupEntry 4 }

		
--  1.3.6.1.4.1.10428 9 1.102.12.2.2.5.2.2.1.5
		-- 1.3.6.1.4.1.10428 9 1.102.12.2.2.5.2.1.1.5
		fkV2IgsGroupUpTime OBJECT-TYPE
			SYNTAX TimeTicks
			MAX-ACCESS read-only
			STATUS current
			DESCRIPTION
				"The time elapsed since this entry was created."
			::= { fkV2IgsGroupEntry 5 }

		
--  1.3.6.1.4.1.10428 9 1.102.12.2.2.5.2.2.1.6
		-- 1.3.6.1.4.1.10428 9 1.102.12.2.2.5.2.1.1.6
		fkV2IgsGroupExpiryTime OBJECT-TYPE
			SYNTAX TimeTicks
			MAX-ACCESS read-only
			STATUS current
			DESCRIPTION
				"This value represents the time remaining before the Group Membership Interval state expires. The value must always be greater than 0."
			::= { fkV2IgsGroupEntry 6 }

		
		-- 1.3.6.1.4.1.10428 9 1.102.12.2.2.5.2.1.1.7
		fkV2IgsGroupPortInfo OBJECT-TYPE
			SYNTAX Integer32
			MAX-ACCESS read-only
			STATUS current
			DESCRIPTION
				"Port information."
			::= { fkV2IgsGroupEntry 7 }

		
--  IGMP Snooping Group
-- 1.3.6.1.4.1.10428 9 1.102.12.2.2.5.3
		-- 1.3.6.1.4.1.10428 9 1.102.12.2.2.5.3
		fkV2IgsSource OBJECT IDENTIFIER ::= { fkV2IgmpSnooping 3 }

		
--  IGMP Snooping Group Table
-- 1.3.6.1.4.1.10428 9 1.102.12.2.2.5.3.1
		-- 1.3.6.1.4.1.10428 9 1.102.12.2.2.5.3.1
		fkV2IgsSourceTable OBJECT-TYPE
			SYNTAX SEQUENCE OF FkV2IgsSourceEntry
			MAX-ACCESS not-accessible
			STATUS current
			DESCRIPTION
				"IGS source table."
			::= { fkV2IgsSource 1 }

		
--  IGMP Snooping Group Entry
-- 1.3.6.1.4.1.10428 9 1.102.12.2.2.5.3.1.1
		-- 1.3.6.1.4.1.10428 9 1.102.12.2.2.5.3.1.1
		fkV2IgsSourceEntry OBJECT-TYPE
			SYNTAX FkV2IgsSourceEntry
			MAX-ACCESS not-accessible
			STATUS current
			DESCRIPTION
				"key: fkV2IgsVlanIndex, fkV2IgsGroupAddress, fkV2IgsGroupPortIndex, fkV2IgsSourceAddress"
			INDEX { fkV2IgsVlanIndex, fkV2IgsGroupAddress, fkV2IgsGroupPortIndex, fkV2IgsSourceAddress }
			::= { fkV2IgsSourceTable 1 }

		
		FkV2IgsSourceEntry ::=
			SEQUENCE { 
				fkV2IgsSourceAddress
					IpAddress,
				fkV2IgsSourceType
					INTEGER,
				fkV2IgsSourceUpTime
					TimeTicks,
				fkV2IgsSourceExpiryTime
					TimeTicks,
				fkV2IgsSourceSsmMapped
					Boolean,
				fkV2IgsSourceVId
					Integer32,
				fkV2IgsSourcenGrpAddr
					IpAddress,
				fkV2IgsSourcePort
					Integer32,
				fkV2IgsSourcePortInfo
					Integer32
			 }

--  1.3.6.1.4.1.10428 9 1.102.12.2.2.5.3.1.1.1
		-- 1.3.6.1.4.1.10428 9 1.102.12.2.2.5.3.1.1.1
		fkV2IgsSourceAddress OBJECT-TYPE
			SYNTAX IpAddress
			MAX-ACCESS read-only
			STATUS current
			DESCRIPTION
				"Source of IP multicast group, fkV2IgsGroupAddress.For (*,G) entry, value is 0.0.0.0"
			::= { fkV2IgsSourceEntry 1 }

		
--  1.3.6.1.4.1.10428 9 1.102.12.2.2.5.3.1.1.2
		-- 1.3.6.1.4.1.10428 9 1.102.12.2.2.5.3.1.1.2
		fkV2IgsSourceType OBJECT-TYPE
			SYNTAX INTEGER
				{
				dynamic(1),
				static(2)
				}
			MAX-ACCESS read-only
			STATUS current
			DESCRIPTION
				"It indicates whether the multicast group (S/*,G) is learned by snooping of IGMP report messages or administrative maner."
			::= { fkV2IgsSourceEntry 2 }

		
--  1.3.6.1.4.1.10428 9 1.102.12.2.2.5.3.1.1.3
		-- 1.3.6.1.4.1.10428 9 1.102.12.2.2.5.3.1.1.3
		fkV2IgsSourceUpTime OBJECT-TYPE
			SYNTAX TimeTicks
			MAX-ACCESS read-only
			STATUS current
			DESCRIPTION
				"The time elapsed since this entry was created."
			::= { fkV2IgsSourceEntry 3 }

		
--  1.3.6.1.4.1.10428 9 1.102.12.2.2.5.3.1.1.4
		-- 1.3.6.1.4.1.10428 9 1.102.12.2.2.5.3.1.1.4
		fkV2IgsSourceExpiryTime OBJECT-TYPE
			SYNTAX TimeTicks
			MAX-ACCESS read-only
			STATUS current
			DESCRIPTION
				"This value represents the time remaining before the Group Membership Interval state expires. The value must always be greater than 0."
			::= { fkV2IgsSourceEntry 4 }

		
--  1.3.6.1.4.1.10428 9 1.102.12.2.2.5.3.1.1.5
		-- 1.3.6.1.4.1.10428 9 1.102.12.2.2.5.3.1.1.5
		fkV2IgsSourceSsmMapped OBJECT-TYPE
			SYNTAX Boolean
			MAX-ACCESS read-only
			STATUS current
			DESCRIPTION
				"The value TRUE indicate that source of multicast group is decided by SSM Mapping Table, and FALSE is not."
			::= { fkV2IgsSourceEntry 5 }

		
		-- 1.3.6.1.4.1.10428 9 1.102.12.2.2.5.3.1.1.6
		fkV2IgsSourceVId OBJECT-TYPE
			SYNTAX Integer32 (1..4094)
			MAX-ACCESS read-only
			STATUS current
			DESCRIPTION
				"This object indicates the VLAN in which IGMP Snooping is configured. (= fkNetIfIndex)"
			::= { fkV2IgsSourceEntry 6 }

		
		-- 1.3.6.1.4.1.10428 9 1.102.12.2.2.5.3.1.1.7
		fkV2IgsSourcenGrpAddr OBJECT-TYPE
			SYNTAX IpAddress
			MAX-ACCESS read-only
			STATUS current
			DESCRIPTION
				"It is a IP multicast address learned by IGMP Snooping."
			::= { fkV2IgsSourceEntry 7 }

		
		-- 1.3.6.1.4.1.10428 9 1.102.12.2.2.5.3.1.1.8
		fkV2IgsSourcePort OBJECT-TYPE
			SYNTAX Integer32
			MAX-ACCESS read-only
			STATUS current
			DESCRIPTION
				"This object indicates the port on VLAN in which the group is learned."
			::= { fkV2IgsSourceEntry 8 }

		
		-- 1.3.6.1.4.1.10428 9 1.102.12.2.2.5.3.1.1.9
		fkV2IgsSourcePortInfo OBJECT-TYPE
			SYNTAX Integer32
			MAX-ACCESS read-only
			STATUS current
			DESCRIPTION
				"Port information."
			::= { fkV2IgsSourceEntry 9 }

		
--  IGMP Snooping Group Control
-- 1.3.6.1.4.1.10428 9 1.102.12.2.2.5.3.2
		-- 1.3.6.1.4.1.10428 9 1.102.12.2.2.5.3.2
		fkV2IgsSourceControl OBJECT IDENTIFIER ::= { fkV2IgsSource 2 }

		
--  1.3.6.1.4.1.10428 9 1.102.12.2.2.5.3.2.1
		-- 1.3.6.1.4.1.10428 9 1.102.12.2.2.5.3.2.1
		fkV2IgsSourceControlRequest OBJECT-TYPE
			SYNTAX INTEGER
				{
				createIgmpSnoopSourceStatic(1),
				destroyIgmpSnoopSourceStatic(2)
				}
			MAX-ACCESS read-write
			STATUS current
			DESCRIPTION
				" The request of a user command"
			::= { fkV2IgsSourceControl 1 }

		
--  1.3.6.1.4.1.10428 9 1.102.12.2.2.5.3.2.2
		-- 1.3.6.1.4.1.10428 9 1.102.12.2.2.5.3.2.2
		fkV2IgsSourceControlStatus OBJECT-TYPE
			SYNTAX FkControlStatusType
			MAX-ACCESS read-only
			STATUS current
			DESCRIPTION
				"The status of user command"
			::= { fkV2IgsSourceControl 2 }

		
--  1.3.6.1.4.1.10428 9 1.102.12.2.2.5.3.2.3
		-- 1.3.6.1.4.1.10428 9 1.102.12.2.2.5.3.2.3
		fkV2IgsSourceControlTimer OBJECT-TYPE
			SYNTAX Gauge32
			MAX-ACCESS read-write
			STATUS current
			DESCRIPTION
				" The maximum time for the manager for a long running user command"
			::= { fkV2IgsSourceControl 3 }

		
--  1.3.6.1.4.1.10428 9 1.102.12.2.2.5.3.2.4
		-- 1.3.6.1.4.1.10428 9 1.102.12.2.2.5.3.2.4
		fkV2IgsSourceControlTimeStamp OBJECT-TYPE
			SYNTAX TimeStamp
			MAX-ACCESS read-only
			STATUS current
			DESCRIPTION
				" The time stamp of the last command(end of command)"
			::= { fkV2IgsSourceControl 4 }

		
--  1.3.6.1.4.1.10428 9 1.102.12.2.2.5.3.2.5
		-- 1.3.6.1.4.1.10428 9 1.102.12.2.2.5.3.2.5
		fkV2IgsSourceControlReqResult OBJECT-TYPE
			SYNTAX FkControlRequestResultType
			MAX-ACCESS read-only
			STATUS current
			DESCRIPTION
				" The result of the last user command"
			::= { fkV2IgsSourceControl 5 }

		
--  1.3.6.1.4.1.10428 9 1.102.12.2.2.5.3.2.6
		-- 1.3.6.1.4.1.10428 9 1.102.12.2.2.5.3.2.6
		fkV2IgsSourceControlVlanIndex OBJECT-TYPE
			SYNTAX INTEGER (1..4094)
			MAX-ACCESS read-write
			STATUS current
			DESCRIPTION
				"value(0) : all vlan"
			::= { fkV2IgsSourceControl 6 }

		
--  1.3.6.1.4.1.10428 9 1.102.12.2.2.5.3.2.7
		-- 1.3.6.1.4.1.10428 9 1.102.12.2.2.5.3.2.7
		fkV2IgsSourceControlGroup OBJECT-TYPE
			SYNTAX IpAddress
			MAX-ACCESS read-write
			STATUS current
			DESCRIPTION
				"Group IP address"
			::= { fkV2IgsSourceControl 7 }

		
--  1.3.6.1.4.1.10428 9 1.102.12.2.2.5.3.2.8
		-- 1.3.6.1.4.1.10428 9 1.102.12.2.2.5.3.2.8
		fkV2IgsSourceControlPortIndex OBJECT-TYPE
			SYNTAX INTEGER (1..512)
			MAX-ACCESS read-write
			STATUS current
			DESCRIPTION
				"Port index"
			::= { fkV2IgsSourceControl 8 }

		
--  1.3.6.1.4.1.10428 9 1.102.12.2.2.5.3.2.9
		-- 1.3.6.1.4.1.10428 9 1.102.12.2.2.5.3.2.9
		fkV2IgsSourceControlAddress OBJECT-TYPE
			SYNTAX IpAddress
			MAX-ACCESS read-write
			STATUS current
			DESCRIPTION
				"Source IP address"
			::= { fkV2IgsSourceControl 9 }

		
--  IGMP Snooping Group Notification
-- 1.3.6.1.4.1.10428 9 1.102.12.2.2.5.3.3
		-- 1.3.6.1.4.1.10428 9 1.102.12.2.2.5.3.3
		fkV2IgsSourceNotification OBJECT IDENTIFIER ::= { fkV2IgsSource 3 }

		
--  1.3.6.1.4.1.10428 9 1.102.12.2.2.5.3.3.1
		-- 1.3.6.1.4.1.10428 9 1.102.12.2.2.5.3.3.1
		fkV2IgsSourceCreated NOTIFICATION-TYPE
			OBJECTS { fkV2IgsSourceControlRequest, fkV2IgsSourceControlReqResult, fkV2IgsSourceControlTimeStamp, fkV2IgsSourceType }
			STATUS current
			DESCRIPTION 
				"In IGMPv3, Adding (S,G) entry is imply that SourceFilterMode is 'allow'."
			::= { fkV2IgsSourceNotification 1 }

		
--  1.3.6.1.4.1.10428 9 1.102.12.2.2.5.3.3.2
		-- 1.3.6.1.4.1.10428 9 1.102.12.2.2.5.3.3.2
		fkV2IgsSourceDestroyed NOTIFICATION-TYPE
			OBJECTS { fkV2IgsSourceControlRequest, fkV2IgsSourceControlReqResult, fkV2IgsSourceControlTimeStamp, fkV2IgsSourceType }
			STATUS current
			DESCRIPTION 
				"In IGMPv3, Removing static (S,G) entry is imply that SourceFilterMode is 'block'."
			::= { fkV2IgsSourceNotification 2 }

		
--  IGMP Snooping Reporter
-- 1.3.6.1.4.1.10428 9 1.102.12.2.2.5.4
		-- 1.3.6.1.4.1.10428 9 1.102.12.2.2.5.4
		fkV2IgsReporter OBJECT IDENTIFIER ::= { fkV2IgmpSnooping 4 }

		
--  IGMP Snooping Reporter Table
-- 1.3.6.1.4.1.10428 9 1.102.12.2.2.5.4.1
		-- 1.3.6.1.4.1.10428 9 1.102.12.2.2.5.4.1
		fkV2IgsReporterTable OBJECT-TYPE
			SYNTAX SEQUENCE OF FkV2IgsReporterEntry
			MAX-ACCESS not-accessible
			STATUS current
			DESCRIPTION
				"IGS reporter table."
			::= { fkV2IgsReporter 1 }

		
--  IGMP Snooping Reporter Entry
-- 1.3.6.1.4.1.10428 9 1.102.12.2.2.5.4.1.1
		-- 1.3.6.1.4.1.10428 9 1.102.12.2.2.5.4.1.1
		fkV2IgsReporterEntry OBJECT-TYPE
			SYNTAX FkV2IgsReporterEntry
			MAX-ACCESS not-accessible
			STATUS current
			DESCRIPTION
				"key: fkV2IgsVlanIndex, fkV2IgsGroupAddress, fkV2IgsGroupPortIndex, fkV2IgsSourceAddress, fkV2IgsReporterAddress"
			INDEX { fkV2IgsVlanIndex, fkV2IgsGroupAddress, fkV2IgsGroupPortIndex, fkV2IgsSourceAddress, fkV2IgsReporterAddress
				 }
			::= { fkV2IgsReporterTable 1 }

		
		FkV2IgsReporterEntry ::=
			SEQUENCE { 
				fkV2IgsReporterAddress
					IpAddress,
				fkV2IgsReporterExpiryTime
					TimeTicks,
				fkV2IgsReporterMac
					OCTET STRING,
				fkV2IgsReporterVersion
					INTEGER,
				fkV2IgsReporterMode
					INTEGER,
				fkV2IgsReporterPortInfo
					Integer32
			 }

--  1.3.6.1.4.1.10428 9 1.102.12.2.2.5.4.1.1.1
		-- 1.3.6.1.4.1.10428 9 1.102.12.2.2.5.4.1.1.1
		fkV2IgsReporterAddress OBJECT-TYPE
			SYNTAX IpAddress
			MAX-ACCESS read-only
			STATUS current
			DESCRIPTION
				"IP address of reporter."
			::= { fkV2IgsReporterEntry 1 }

		
--  1.3.6.1.4.1.10428 9 1.102.12.2.2.5.4.1.1.2
		-- 1.3.6.1.4.1.10428 9 1.102.12.2.2.5.4.1.1.2
		fkV2IgsReporterExpiryTime OBJECT-TYPE
			SYNTAX TimeTicks
			MAX-ACCESS read-only
			STATUS current
			DESCRIPTION
				"This value represents the time remaining before the reporter has expire."
			::= { fkV2IgsReporterEntry 2 }

		
--  1.3.6.1.4.1.10428 9 1.102.12.2.2.5.4.1.1.3
		-- 1.3.6.1.4.1.10428 9 1.102.12.2.2.5.4.1.1.3
		fkV2IgsReporterMac OBJECT-TYPE
			SYNTAX OCTET STRING (SIZE (6))
			MAX-ACCESS read-only
			STATUS current
			DESCRIPTION
				"Hardware address of reporter."
			::= { fkV2IgsReporterEntry 3 }

		
--  1.3.6.1.4.1.10428 9 1.102.12.2.2.5.4.1.1.4
		-- 1.3.6.1.4.1.10428 9 1.102.12.2.2.5.4.1.1.4
		fkV2IgsReporterVersion OBJECT-TYPE
			SYNTAX INTEGER
				{
				igmpV1(1),
				igmpV2(2),
				igmpV3(3)
				}
			MAX-ACCESS read-only
			STATUS current
			DESCRIPTION
				"IGMP version"
			::= { fkV2IgsReporterEntry 4 }

		
--  1.3.6.1.4.1.10428 9 1.102.12.2.2.5.4.1.1.5
		-- 1.3.6.1.4.1.10428 9 1.102.12.2.2.5.4.1.1.5
		fkV2IgsReporterMode OBJECT-TYPE
			SYNTAX INTEGER
				{
				unknown(0),
				includeAllow(1),
				includeBlock(2),
				excludeAllow(3),
				excludeBlock(4)
				}
			MAX-ACCESS read-only
			STATUS current
			DESCRIPTION
				"Filter mode"
			::= { fkV2IgsReporterEntry 5 }

		
		-- 1.3.6.1.4.1.10428 9 1.102.12.2.2.5.4.1.1.6
		fkV2IgsReporterPortInfo OBJECT-TYPE
			SYNTAX Integer32
			MAX-ACCESS read-only
			STATUS current
			DESCRIPTION
				"Port information."
			::= { fkV2IgsReporterEntry 6 }

		
--  1.3.6.1.4.1.10428 9 1.102.12.2.2.5.5
		-- 1.3.6.1.4.1.10428 9 1.102.12.2.2.5.5
		fkV2IgsPort OBJECT IDENTIFIER ::= { fkV2IgmpSnooping 5 }

		
--  1.3.6.1.4.1.10428 9 1.102.12.2.2.5.5.1
		-- 1.3.6.1.4.1.10428 9 1.102.12.2.2.5.5.1
		fkV2IgsPortTable OBJECT-TYPE
			SYNTAX SEQUENCE OF FkV2IgsPortEntry
			MAX-ACCESS not-accessible
			STATUS current
			DESCRIPTION
				"IGS port table."
			::= { fkV2IgsPort 1 }

		
--  1.3.6.1.4.1.10428 9 1.102.12.2.2.5.5.1.1
		-- 1.3.6.1.4.1.10428 9 1.102.12.2.2.5.5.1.1
		fkV2IgsPortEntry OBJECT-TYPE
			SYNTAX FkV2IgsPortEntry
			MAX-ACCESS not-accessible
			STATUS current
			DESCRIPTION
				"key: fkV2IgsPortIndex"
			INDEX { fkV2IgsPortIndex }
			::= { fkV2IgsPortTable 1 }

		
		FkV2IgsPortEntry ::=
			SEQUENCE { 
				fkV2IgsPortIndex
					INTEGER,
				fkV2IgsPortFastLeave
					Boolean,
				fkV2IgsPortExplicitTrackingMaxHosts
					INTEGER,
				fkV2IgsPortExplicitTrackingMacBased
					Boolean,
				fkV2IgsPortDot1qSelection
					INTEGER,
				fkV2IgsPortMrouter
					INTEGER
			 }

--  1.3.6.1.4.1.10428 9 1.102.12.2.2.5.5.1.1.1
		-- 1.3.6.1.4.1.10428 9 1.102.12.2.2.5.5.1.1.1
		fkV2IgsPortIndex OBJECT-TYPE
			SYNTAX INTEGER (1..512)
			MAX-ACCESS read-only
			STATUS current
			DESCRIPTION
				"This object indicates the port index
				"
			::= { fkV2IgsPortEntry 1 }

		
--  1.3.6.1.4.1.10428 9 1.102.12.2.2.5.5.1.1.2
		-- 1.3.6.1.4.1.10428 9 1.102.12.2.2.5.5.1.1.2
		fkV2IgsPortFastLeave OBJECT-TYPE
			SYNTAX Boolean
			MAX-ACCESS read-only
			STATUS current
			DESCRIPTION
				"This object specifies whether Fast-Leave mechanism (also known as Immediate-Leave) is to be performed by IGMP Snooping or not. When enabled, IGMP Snooping will remove the interface from the group mentioned in the IGMP Leave message received on that interface without waiting for the IGMP Group-Specific Query to timeout to determine whether there are any more hosts on that interface for that port
				"
			::= { fkV2IgsPortEntry 2 }

		
--  1.3.6.1.4.1.10428 9 1.102.12.2.2.5.5.1.1.3
		-- 1.3.6.1.4.1.10428 9 1.102.12.2.2.5.5.1.1.3
		fkV2IgsPortExplicitTrackingMaxHosts OBJECT-TYPE
			SYNTAX INTEGER (1..65535)
			MAX-ACCESS read-only
			STATUS current
			DESCRIPTION
				"This object indicates the maximum number of hosts in the specified port"
			::= { fkV2IgsPortEntry 3 }

		
		-- 1.3.6.1.4.1.10428 9 1.102.12.2.2.5.5.1.1.4
		fkV2IgsPortExplicitTrackingMacBased OBJECT-TYPE
			SYNTAX Boolean
			MAX-ACCESS read-only
			STATUS current
			DESCRIPTION
				"Tracking mac based"
			::= { fkV2IgsPortEntry 4 }

		
		-- 1.3.6.1.4.1.10428 9 1.102.12.2.2.5.5.1.1.5
		fkV2IgsPortDot1qSelection OBJECT-TYPE
			SYNTAX INTEGER
				{
				inner(1),
				outer(2)
				}
			MAX-ACCESS read-only
			STATUS current
			DESCRIPTION
				"Dot1q selection
				1: inner
				2: outer
				"
			::= { fkV2IgsPortEntry 5 }

		
		-- 1.3.6.1.4.1.10428 9 1.102.12.2.2.5.5.1.1.6
		fkV2IgsPortMrouter OBJECT-TYPE
			SYNTAX INTEGER
				{
				disable(0),
				enable(1)
				}
			MAX-ACCESS read-only
			STATUS current
			DESCRIPTION
				"Mrouter Interface. "
			::= { fkV2IgsPortEntry 6 }

		
--  1.3.6.1.4.1.10428 9 1.102.12.2.2.5.5.2
		-- 1.3.6.1.4.1.10428 9 1.102.12.2.2.5.5.2
		fkV2IgsPortControl OBJECT IDENTIFIER ::= { fkV2IgsPort 2 }

		
--  1.3.6.1.4.1.10428 9 1.102.12.2.2.5.5.2.1
		-- 1.3.6.1.4.1.10428 9 1.102.12.2.2.5.5.2.1
		fkV2IgsPortControlRequest OBJECT-TYPE
			SYNTAX INTEGER
				{
				setIgmpSnoopPortProfile(1),
				setIgsExplicitTrackingMaxHosts(2),
				setIgsExplicitTrackingMacBased(3),
				setIgsPortDot1q(4),
				setIgsPortMrouter(5)
				}
			MAX-ACCESS read-write
			STATUS current
			DESCRIPTION
				"The request of a user command"
			::= { fkV2IgsPortControl 1 }

		
--  1.3.6.1.4.1.10428 9 1.102.12.2.2.5.5.2.2
		-- 1.3.6.1.4.1.10428 9 1.102.12.2.2.5.5.2.2
		fkV2IgsPortControlStatus OBJECT-TYPE
			SYNTAX FkControlStatusType
			MAX-ACCESS read-only
			STATUS current
			DESCRIPTION
				"The status of user command"
			::= { fkV2IgsPortControl 2 }

		
--  1.3.6.1.4.1.10428 9 1.102.12.2.2.5.5.2.3
		-- 1.3.6.1.4.1.10428 9 1.102.12.2.2.5.5.2.3
		fkV2IgsPortControlTimer OBJECT-TYPE
			SYNTAX Gauge32
			MAX-ACCESS read-write
			STATUS current
			DESCRIPTION
				"The maximum time for the manager for a long running user command"
			::= { fkV2IgsPortControl 3 }

		
--  1.3.6.1.4.1.10428 9 1.102.12.2.2.5.5.2.4
		-- 1.3.6.1.4.1.10428 9 1.102.12.2.2.5.5.2.4
		fkV2IgsPortControlTimeStamp OBJECT-TYPE
			SYNTAX TimeTicks
			MAX-ACCESS read-only
			STATUS current
			DESCRIPTION
				"The time stamp of the last command(end of command)"
			::= { fkV2IgsPortControl 4 }

		
--  1.3.6.1.4.1.10428 9 1.102.12.2.2.5.5.2.5
		-- 1.3.6.1.4.1.10428 9 1.102.12.2.2.5.5.2.5
		fkV2IgsPortControlReqResult OBJECT-TYPE
			SYNTAX FkControlRequestResultType
			MAX-ACCESS read-only
			STATUS current
			DESCRIPTION
				"The result of the last user command"
			::= { fkV2IgsPortControl 5 }

		
--  1.3.6.1.4.1.10428 9 1.102.12.2.2.5.5.2.6
		-- 1.3.6.1.4.1.10428 9 1.102.12.2.2.5.5.2.6
		fkV2IgsPortControlIndex OBJECT-TYPE
			SYNTAX INTEGER (1..512)
			MAX-ACCESS read-write
			STATUS current
			DESCRIPTION
				"This object indicates the port index
				"
			::= { fkV2IgsPortControl 6 }

		
--  1.3.6.1.4.1.10428 9 1.102.12.2.2.5.5.2.7
		-- 1.3.6.1.4.1.10428 9 1.102.12.2.2.5.5.2.7
		fkV2IgsPortControlFastLeave OBJECT-TYPE
			SYNTAX Boolean
			MAX-ACCESS read-write
			STATUS current
			DESCRIPTION
				"This object specifies whether Fast-Leave mechanism
				"
			::= { fkV2IgsPortControl 7 }

		
--  1.3.6.1.4.1.10428 9 1.102.12.2.2.5.5.2.8
		-- 1.3.6.1.4.1.10428 9 1.102.12.2.2.5.5.2.8
		fkV2IgsPortControlExplicitTrackingMaxHosts OBJECT-TYPE
			SYNTAX INTEGER (1..65535)
			MAX-ACCESS read-write
			STATUS current
			DESCRIPTION
				"This object indicates the maximum number of hosts in the specified port"
			::= { fkV2IgsPortControl 8 }

		
		-- 1.3.6.1.4.1.10428 9 1.102.12.2.2.5.5.2.9
		fkV2IgsPortControlExplicitTrackingMacBased OBJECT-TYPE
			SYNTAX Boolean
			MAX-ACCESS read-write
			STATUS current
			DESCRIPTION
				"Tracking mac based"
			::= { fkV2IgsPortControl 9 }

		
		-- 1.3.6.1.4.1.10428 9 1.102.12.2.2.5.5.2.10
		fkV2IgsPortControlDot1qSelection OBJECT-TYPE
			SYNTAX INTEGER
				{
				inner(1),
				outer(2)
				}
			MAX-ACCESS read-write
			STATUS current
			DESCRIPTION
				"Dot1q selection
				1: inner
				2: outer
				"
			::= { fkV2IgsPortControl 10 }

		
		-- 1.3.6.1.4.1.10428 9 1.102.12.2.2.5.5.2.11
		fkV2IgsPortControlMrouter OBJECT-TYPE
			SYNTAX INTEGER
				{
				disable(0),
				enable(1)
				}
			MAX-ACCESS read-write
			STATUS current
			DESCRIPTION
				"Mrouter Interface. "
			::= { fkV2IgsPortControl 11 }

		
--  1.3.6.1.4.1.10428 9 1.102.12.2.2.5.5.3
		-- 1.3.6.1.4.1.10428 9 1.102.12.2.2.5.5.3
		fkV2IgsPortNotifications OBJECT IDENTIFIER ::= { fkV2IgsPort 3 }

		
--  1.3.6.1.4.1.10428 9 1.102.12.2.2.5.5.3.1
		-- 1.3.6.1.4.1.10428 9 1.102.12.2.2.5.5.3.1
		fkV2IgsPortrofileChanged NOTIFICATION-TYPE
			OBJECTS { fkV2IgsPortControlRequest, fkV2IgsPortControlTimeStamp, fkV2IgsPortControlReqResult, fkV2IgsPortFastLeave }
			STATUS current
			DESCRIPTION 
				"Description."
			::= { fkV2IgsPortNotifications 1 }

		
--  1.3.6.1.4.1.10428 9 1.102.12.2.2.5.5.3.2
		-- 1.3.6.1.4.1.10428 9 1.102.12.2.2.5.5.3.2
		fkV2IgsPortExplicitTrackingMaxHostsChanged NOTIFICATION-TYPE
			OBJECTS { fkV2IgsPortControlRequest, fkV2IgsPortControlTimeStamp, fkV2IgsPortControlReqResult, fkV2IgsPortControlIndex, fkV2IgsPortControlExplicitTrackingMaxHosts
				 }
			STATUS current
			DESCRIPTION 
				"Description."
			::= { fkV2IgsPortNotifications 2 }

		
		-- 1.3.6.1.4.1.10428 9 1.102.12.2.2.5.5.3.3
		fkV2IgsPortExplicitTrackingMacBasedChanged NOTIFICATION-TYPE
			OBJECTS { fkV2IgsPortControlRequest, fkV2IgsPortControlTimeStamp, fkV2IgsPortControlReqResult, fkV2IgsPortControlIndex, fkV2IgsPortControlExplicitTrackingMacBased
				 }
			STATUS current
			DESCRIPTION 
				"Description."
			::= { fkV2IgsPortNotifications 3 }

		
		-- 1.3.6.1.4.1.10428 9 1.102.12.2.2.5.5.3.4
		fkV2IgsPortDot1qChanged NOTIFICATION-TYPE
			OBJECTS { fkV2IgsPortControlRequest, fkV2IgsPortControlTimeStamp, fkV2IgsPortControlReqResult, fkV2IgsPortControlIndex, fkV2IgsPortControlDot1qSelection
				 }
			STATUS current
			DESCRIPTION 
				"Description."
			::= { fkV2IgsPortNotifications 4 }

		
--  1.3.6.1.4.1.10428 9 1.102.12.2.2.5.5.3.1
		-- 1.3.6.1.4.1.10428 9 1.102.12.2.2.5.5.3.5
		fkV2IgsPortMrouterchanged NOTIFICATION-TYPE
			OBJECTS { fkV2IgsPortControlRequest, fkV2IgsPortControlTimeStamp, fkV2IgsPortControlReqResult, fkV2IgsPortControlIndex, fkV2IgsPortControlMrouter
				 }
			STATUS current
			DESCRIPTION 
				"setIgsMrouter"
			::= { fkV2IgsPortNotifications 5 }

		
--  1.3.6.1.4.1.10428 9 1.102.12.2.2.5.6
		-- 1.3.6.1.4.1.10428 9 1.102.12.2.2.5.6
		fkV2IgsPortStats OBJECT IDENTIFIER ::= { fkV2IgmpSnooping 6 }

		
--  1.3.6.1.4.1.10428 9 1.102.12.2.2.5.6.1
		-- 1.3.6.1.4.1.10428 9 1.102.12.2.2.5.6.1
		fkV2IgsStatsTable OBJECT-TYPE
			SYNTAX SEQUENCE OF FkV2IgsStatsEntry
			MAX-ACCESS not-accessible
			STATUS current
			DESCRIPTION
				"IGS stats table."
			::= { fkV2IgsPortStats 1 }

		
--  1.3.6.1.4.1.10428 9 1.102.12.2.2.5.6.1.1
		-- 1.3.6.1.4.1.10428 9 1.102.12.2.2.5.6.1.1
		fkV2IgsStatsEntry OBJECT-TYPE
			SYNTAX FkV2IgsStatsEntry
			MAX-ACCESS not-accessible
			STATUS current
			DESCRIPTION
				"key: fkV2IgsPortIndex"
			INDEX { fkV2IgsPortIndex }
			::= { fkV2IgsStatsTable 1 }

		
		FkV2IgsStatsEntry ::=
			SEQUENCE { 
				fkV2IgsStatsPortIndex
					INTEGER,
				fkV2IgsStatsTxGeneralQueries
					Unsigned32,
				fkV2IgsStatsTxGroupSpecificQueies
					Unsigned32,
				fkV2IgsStatsTxReports
					Unsigned32,
				fkV2IgsStatsTxLeaves
					Unsigned32,
				fkV2IgsStatsRxGeneralQueries
					Unsigned32,
				fkV2IgsStatsRxGroupSpecificQueies
					Unsigned32,
				fkV2IgsStatsRxReports
					Unsigned32,
				fkV2IgsStatsRxLeaves
					Unsigned32,
				fkV2IgsStatsRxValidPackets
					Unsigned32,
				fkV2IgsStatsRxInvalidPackets
					Unsigned32,
				fkV2IgsStatsRxOtherPackets
					Unsigned32,
				fkV2IgsStatsRxMacGeneralQueries
					Unsigned32,
				fkV2IgsStatsRxTopoNotifications
					Unsigned32,
				fkV2IgsStatsv3Allows
					Unsigned32,
				fkV2IgsStatsv3Blocks
					Unsigned32,
				fkV2IgsStatsv3IsIncluded
					Unsigned32,
				fkV2IgsStatsv3IsExcluded
					Unsigned32,
				fkV2IgsStatsv3ToIncluded
					Unsigned32,
				fkV2IgsStatsv3ToExcluded
					Unsigned32,
				fkV2IgsStatsRxFilteredPackets
					Unsigned32
			 }

--  1.3.6.1.4.1.10428 9 1.102.12.2.2.5.6.1.1.1
		-- 1.3.6.1.4.1.10428 9 1.102.12.2.2.5.6.1.1.1
		fkV2IgsStatsPortIndex OBJECT-TYPE
			SYNTAX INTEGER (1..512)
			MAX-ACCESS read-only
			STATUS current
			DESCRIPTION
				"The Port index to access IGS IGMP Snooping Statistics Information"
			::= { fkV2IgsStatsEntry 1 }

		
--  1.3.6.1.4.1.10428 9 1.102.12.2.2.5.6.1.1.2
		-- 1.3.6.1.4.1.10428 9 1.102.12.2.2.5.6.1.1.2
		fkV2IgsStatsTxGeneralQueries OBJECT-TYPE
			SYNTAX Unsigned32
			MAX-ACCESS read-only
			STATUS current
			DESCRIPTION
				"The count of sending the General Query Messages to the specific port"
			::= { fkV2IgsStatsEntry 2 }

		
--  1.3.6.1.4.1.10428 9 1.102.12.2.2.5.6.1.1.3
		-- 1.3.6.1.4.1.10428 9 1.102.12.2.2.5.6.1.1.3
		fkV2IgsStatsTxGroupSpecificQueies OBJECT-TYPE
			SYNTAX Unsigned32
			MAX-ACCESS read-only
			STATUS current
			DESCRIPTION
				"The count of sending the Group Specific Query Messages to the specific port"
			::= { fkV2IgsStatsEntry 3 }

		
--  1.3.6.1.4.1.10428 9 1.102.12.2.2.5.6.1.1.4
		-- 1.3.6.1.4.1.10428 9 1.102.12.2.2.5.6.1.1.4
		fkV2IgsStatsTxReports OBJECT-TYPE
			SYNTAX Unsigned32
			MAX-ACCESS read-only
			STATUS current
			DESCRIPTION
				"The count of sending the Membership Report Messages to the secific port"
			::= { fkV2IgsStatsEntry 4 }

		
--  1.3.6.1.4.1.10428 9 1.102.12.2.2.5.6.1.1.5
		-- 1.3.6.1.4.1.10428 9 1.102.12.2.2.5.6.1.1.5
		fkV2IgsStatsTxLeaves OBJECT-TYPE
			SYNTAX Unsigned32
			MAX-ACCESS read-only
			STATUS current
			DESCRIPTION
				"The count of sending the Leave Membership Messages to the specific port"
			::= { fkV2IgsStatsEntry 5 }

		
--  1.3.6.1.4.1.10428 9 1.102.12.2.2.5.6.1.1.6
		-- 1.3.6.1.4.1.10428 9 1.102.12.2.2.5.6.1.1.6
		fkV2IgsStatsRxGeneralQueries OBJECT-TYPE
			SYNTAX Unsigned32
			MAX-ACCESS read-only
			STATUS current
			DESCRIPTION
				"The count of receiving the General Query Messages from the specific port"
			::= { fkV2IgsStatsEntry 6 }

		
--  1.3.6.1.4.1.10428 9 1.102.12.2.2.5.6.1.1.7
		-- 1.3.6.1.4.1.10428 9 1.102.12.2.2.5.6.1.1.7
		fkV2IgsStatsRxGroupSpecificQueies OBJECT-TYPE
			SYNTAX Unsigned32
			MAX-ACCESS read-only
			STATUS current
			DESCRIPTION
				"The count of receiving the Group Specific Query Messages from the specific port"
			::= { fkV2IgsStatsEntry 7 }

		
--  1.3.6.1.4.1.10428 9 1.102.12.2.2.5.6.1.1.8
		-- 1.3.6.1.4.1.10428 9 1.102.12.2.2.5.6.1.1.8
		fkV2IgsStatsRxReports OBJECT-TYPE
			SYNTAX Unsigned32
			MAX-ACCESS read-only
			STATUS current
			DESCRIPTION
				"The count of recieving the Membership Report Messages from the specific ports"
			::= { fkV2IgsStatsEntry 8 }

		
--  1.3.6.1.4.1.10428 9 1.102.12.2.2.5.6.1.1.9
		-- 1.3.6.1.4.1.10428 9 1.102.12.2.2.5.6.1.1.9
		fkV2IgsStatsRxLeaves OBJECT-TYPE
			SYNTAX Unsigned32
			MAX-ACCESS read-only
			STATUS current
			DESCRIPTION
				"The count of receiving the Leave Membership Messages from the specific port"
			::= { fkV2IgsStatsEntry 9 }

		
--  1.3.6.1.4.1.10428 9 1.102.12.2.2.5.6.1.1.10
		-- 1.3.6.1.4.1.10428 9 1.102.12.2.2.5.6.1.1.10
		fkV2IgsStatsRxValidPackets OBJECT-TYPE
			SYNTAX Unsigned32
			MAX-ACCESS read-only
			STATUS current
			DESCRIPTION
				"The count of receiving the valid IGMP Packets from the specific port"
			::= { fkV2IgsStatsEntry 10 }

		
--  1.3.6.1.4.1.10428 9 1.102.12.2.2.5.6.1.1.11
		-- 1.3.6.1.4.1.10428 9 1.102.12.2.2.5.6.1.1.11
		fkV2IgsStatsRxInvalidPackets OBJECT-TYPE
			SYNTAX Unsigned32
			MAX-ACCESS read-only
			STATUS current
			DESCRIPTION
				"The count of receiving the Invalid Packets from the specific port"
			::= { fkV2IgsStatsEntry 11 }

		
--  1.3.6.1.4.1.10428 9 1.102.12.2.2.5.6.1.1.12
		-- 1.3.6.1.4.1.10428 9 1.102.12.2.2.5.6.1.1.12
		fkV2IgsStatsRxOtherPackets OBJECT-TYPE
			SYNTAX Unsigned32
			MAX-ACCESS read-only
			STATUS current
			DESCRIPTION
				"The count of receiving the valid IGMP Packets but not defined from the specific port"
			::= { fkV2IgsStatsEntry 12 }

		
--  1.3.6.1.4.1.10428 9 1.102.12.2.2.5.6.1.1.13
		-- 1.3.6.1.4.1.10428 9 1.102.12.2.2.5.6.1.1.13
		fkV2IgsStatsRxMacGeneralQueries OBJECT-TYPE
			SYNTAX Unsigned32
			MAX-ACCESS read-only
			STATUS current
			DESCRIPTION
				"The count of receiving the MAC General Query Messages from the specific port"
			::= { fkV2IgsStatsEntry 13 }

		
--  1.3.6.1.4.1.10428 9 1.102.12.2.2.5.6.1.1.14
		-- 1.3.6.1.4.1.10428 9 1.102.12.2.2.5.6.1.1.14
		fkV2IgsStatsRxTopoNotifications OBJECT-TYPE
			SYNTAX Unsigned32
			MAX-ACCESS read-only
			STATUS current
			DESCRIPTION
				"The count of receiving the Topology Change Notification Messages from the specific port"
			::= { fkV2IgsStatsEntry 14 }

		
--  1.3.6.1.4.1.10428 9 1.102.12.2.2.5.6.1.1.15
		-- 1.3.6.1.4.1.10428 9 1.102.12.2.2.5.6.1.1.15
		fkV2IgsStatsv3Allows OBJECT-TYPE
			SYNTAX Unsigned32
			MAX-ACCESS read-only
			STATUS current
			DESCRIPTION
				"The count of receiving the IGMP Version-3 Allow Messages from the specific port"
			::= { fkV2IgsStatsEntry 15 }

		
--  1.3.6.1.4.1.10428 9 1.102.12.2.2.5.6.1.1.16
		-- 1.3.6.1.4.1.10428 9 1.102.12.2.2.5.6.1.1.16
		fkV2IgsStatsv3Blocks OBJECT-TYPE
			SYNTAX Unsigned32
			MAX-ACCESS read-only
			STATUS current
			DESCRIPTION
				"The count of receiving the IGMP Version-3 Block Messages from the specific port"
			::= { fkV2IgsStatsEntry 16 }

		
--  1.3.6.1.4.1.10428 9 1.102.12.2.2.5.6.1.1.17
		-- 1.3.6.1.4.1.10428 9 1.102.12.2.2.5.6.1.1.17
		fkV2IgsStatsv3IsIncluded OBJECT-TYPE
			SYNTAX Unsigned32
			MAX-ACCESS read-only
			STATUS current
			DESCRIPTION
				"The count of recieving the IGMP version-3 Membership Report Messages Whose Type is ISINCLUDE from the specific port"
			::= { fkV2IgsStatsEntry 17 }

		
--  1.3.6.1.4.1.10428 9 1.102.12.2.2.5.6.1.1.18
		-- 1.3.6.1.4.1.10428 9 1.102.12.2.2.5.6.1.1.18
		fkV2IgsStatsv3IsExcluded OBJECT-TYPE
			SYNTAX Unsigned32
			MAX-ACCESS read-only
			STATUS current
			DESCRIPTION
				"The count of receiving the IGMP version-3 Membership Report Messages Whose type is ISEXCLUDE from the specific port"
			::= { fkV2IgsStatsEntry 18 }

		
--  1.3.6.1.4.1.10428 9 1.102.12.2.2.5.6.1.1.19
		-- 1.3.6.1.4.1.10428 9 1.102.12.2.2.5.6.1.1.19
		fkV2IgsStatsv3ToIncluded OBJECT-TYPE
			SYNTAX Unsigned32
			MAX-ACCESS read-only
			STATUS current
			DESCRIPTION
				"The count of receiving the IGMP version-3 Membership Report Messages Whose type is TOINCLUDE from the specific port"
			::= { fkV2IgsStatsEntry 19 }

		
--  1.3.6.1.4.1.10428 9 1.102.12.2.2.5.6.1.1.20
		-- 1.3.6.1.4.1.10428 9 1.102.12.2.2.5.6.1.1.20
		fkV2IgsStatsv3ToExcluded OBJECT-TYPE
			SYNTAX Unsigned32
			MAX-ACCESS read-only
			STATUS current
			DESCRIPTION
				"The count of receiving the IGMP version-3 Membership Report Messages Whose type is TOEXCLUDE from the specific port"
			::= { fkV2IgsStatsEntry 20 }

		
--  1.3.6.1.4.1.10428 9 1.102.12.2.2.5.6.1.1.21
		-- 1.3.6.1.4.1.10428 9 1.102.12.2.2.5.6.1.1.21
		fkV2IgsStatsRxFilteredPackets OBJECT-TYPE
			SYNTAX Unsigned32
			MAX-ACCESS read-only
			STATUS current
			DESCRIPTION
				"The count of receiving the valid IGMP Packet that is blocked  by IGMP Filter from the specific port"
			::= { fkV2IgsStatsEntry 21 }

		
--  1.3.6.1.4.1.10428 9 1.102.12.2.2.5.6.2
		-- 1.3.6.1.4.1.10428 9 1.102.12.2.2.5.6.2
		fkV2IgsStatsControl OBJECT IDENTIFIER ::= { fkV2IgsPortStats 2 }

		
--  1.3.6.1.4.1.10428 9 1.102.12.2.2.5.6.2.1
		-- 1.3.6.1.4.1.10428 9 1.102.12.2.2.5.6.2.1
		fkV2IgsStatsControlRequest OBJECT-TYPE
			SYNTAX INTEGER { clearIgsStats(1) }
			MAX-ACCESS read-write
			STATUS current
			DESCRIPTION
				"The request of a user command"
			::= { fkV2IgsStatsControl 1 }

		
--  1.3.6.1.4.1.10428 9 1.102.12.2.2.5.6.2.2
		-- 1.3.6.1.4.1.10428 9 1.102.12.2.2.5.6.2.2
		fkV2IgsStatsControlStatus OBJECT-TYPE
			SYNTAX FkControlStatusType
			MAX-ACCESS read-write
			STATUS current
			DESCRIPTION
				"The status of user command"
			::= { fkV2IgsStatsControl 2 }

		
--  1.3.6.1.4.1.10428 9 1.102.12.2.2.5.6.2.3
		-- 1.3.6.1.4.1.10428 9 1.102.12.2.2.5.6.2.3
		fkV2IgsStatsControlControlTimer OBJECT-TYPE
			SYNTAX Gauge32
			MAX-ACCESS read-write
			STATUS current
			DESCRIPTION
				"The maximum time for the manager for a long running user command"
			::= { fkV2IgsStatsControl 3 }

		
--  1.3.6.1.4.1.10428 9 1.102.12.2.2.5.6.2.4
		-- 1.3.6.1.4.1.10428 9 1.102.12.2.2.5.6.2.4
		fkV2IgsStatsControlTimeStamp OBJECT-TYPE
			SYNTAX TimeTicks
			MAX-ACCESS read-write
			STATUS current
			DESCRIPTION
				"The time stamp of the last command(end of command)"
			::= { fkV2IgsStatsControl 4 }

		
--  1.3.6.1.4.1.10428 9 1.102.12.2.2.5.6.2.5
		-- 1.3.6.1.4.1.10428 9 1.102.12.2.2.5.6.2.5
		fkV2IgsStatsControlReqResult OBJECT-TYPE
			SYNTAX FkControlRequestResultType
			MAX-ACCESS read-write
			STATUS current
			DESCRIPTION
				"The result of the last user command
				"
			::= { fkV2IgsStatsControl 5 }

		
--  1.3.6.1.4.1.10428 9 1.102.12.2.2.5.6.2.6
		-- 1.3.6.1.4.1.10428 9 1.102.12.2.2.5.6.2.6
		fkV2IgsStatsControlIndex OBJECT-TYPE
			SYNTAX Integer32
			MAX-ACCESS read-write
			STATUS current
			DESCRIPTION
				"IGS stats index."
			::= { fkV2IgsStatsControl 6 }

		
--  1.3.6.1.4.1.10428 9 1.102.12.2.2.5.6.3
		-- 1.3.6.1.4.1.10428 9 1.102.12.2.2.5.6.3
		fkV2IgsStatsNotification OBJECT IDENTIFIER ::= { fkV2IgsPortStats 3 }

		
--  1.3.6.1.4.1.10428 9 1.102.12.2.2.5.6.3.1
		-- 1.3.6.1.4.1.10428 9 1.102.12.2.2.5.6.3.1
		fkV2IgsStatsCleared NOTIFICATION-TYPE
			OBJECTS { fkV2IgsStatsControlRequest, fkV2IgsStatsControlTimeStamp, fkV2IgsStatsControlReqResult, fkV2IgsStatsPortIndex }
			STATUS current
			DESCRIPTION 
				"Description."
			::= { fkV2IgsStatsNotification 1 }

		
--  1.3.6.1.4.1.10428 9 1.102.12.2.2.5.6
		-- 1.3.6.1.4.1.10428 9 1.102.12.2.2.5.7
		fkV2IgsVlanStats OBJECT IDENTIFIER ::= { fkV2IgmpSnooping 7 }

		
--  1.3.6.1.4.1.10428 9 1.102.12.2.2.5.6.1
		-- 1.3.6.1.4.1.10428 9 1.102.12.2.2.5.7.1
		fkV2IgsVlanStatsTable OBJECT-TYPE
			SYNTAX SEQUENCE OF FkV2IgsVlanStatsEntry
			MAX-ACCESS not-accessible
			STATUS current
			DESCRIPTION
				"IGS stats table."
			::= { fkV2IgsVlanStats 1 }

		
--  1.3.6.1.4.1.10428 9 1.102.12.2.2.5.6.1.1
		-- 1.3.6.1.4.1.10428 9 1.102.12.2.2.5.7.1.1
		fkV2IgsVlanStatsEntry OBJECT-TYPE
			SYNTAX FkV2IgsVlanStatsEntry
			MAX-ACCESS not-accessible
			STATUS current
			DESCRIPTION
				"key: fkV2IgsPortIndex"
			INDEX { fkV2IgsVlanStatsVlanIndex }
			::= { fkV2IgsVlanStatsTable 1 }

		
		FkV2IgsVlanStatsEntry ::=
			SEQUENCE { 
				fkV2IgsVlanStatsVlanIndex
					INTEGER,
				fkV2IgsVlanStatsTxGeneralQueries
					Unsigned32,
				fkV2IgsVlanStatsTxGroupSpecificQueies
					Unsigned32,
				fkV2IgsVlanStatsTxReports
					Unsigned32,
				fkV2IgsVlanStatsTxLeaves
					Unsigned32,
				fkV2IgsVlanStatsRxGeneralQueries
					Unsigned32,
				fkV2IgsVlanStatsRxGroupSpecificQueies
					Unsigned32,
				fkV2IgsVlanStatsRxReports
					Unsigned32,
				fkV2IgsVlanStatsRxLeaves
					Unsigned32,
				fkV2IgsVlanStatsRxValidPackets
					Unsigned32,
				fkV2IgsVlanStatsRxInvalidPackets
					Unsigned32,
				fkV2IgsVlanStatsRxOtherPackets
					Unsigned32,
				fkV2IgsVlanStatsRxMacGeneralQueries
					Unsigned32,
				fkV2IgsVlanStatsRxTopoNotifications
					Unsigned32,
				fkV2IgsVlanStatsv3Allows
					Unsigned32,
				fkV2IgsVlanStatsv3Blocks
					Unsigned32,
				fkV2IgsVlanStatsv3IsIncluded
					Unsigned32,
				fkV2IgsVlanStatsv3IsExcluded
					Unsigned32,
				fkV2IgsVlanStatsv3ToIncluded
					Unsigned32,
				fkV2IgsVlanStatsv3ToExcluded
					Unsigned32,
				fkV2IgsVlanStatsRxFilteredPackets
					Unsigned32,
				fkV2IgsVlanStatsTotalRxReports
					Unsigned32,
				fkV2IgsVlanStatsUnsuccessRxReports
					Unsigned32
			 }

--  1.3.6.1.4.1.10428 9 1.102.12.2.2.5.6.1.1.1
		-- 1.3.6.1.4.1.10428 9 1.102.12.2.2.5.7.1.1.1
		fkV2IgsVlanStatsVlanIndex OBJECT-TYPE
			SYNTAX INTEGER (1..512)
			MAX-ACCESS read-only
			STATUS current
			DESCRIPTION
				"The Port index to access IGS IGMP Snooping Statistics Information"
			::= { fkV2IgsVlanStatsEntry 1 }

		
--  1.3.6.1.4.1.10428 9 1.102.12.2.2.5.6.1.1.2
		-- 1.3.6.1.4.1.10428 9 1.102.12.2.2.5.7.1.1.2
		fkV2IgsVlanStatsTxGeneralQueries OBJECT-TYPE
			SYNTAX Unsigned32
			MAX-ACCESS read-only
			STATUS current
			DESCRIPTION
				"The count of sending the General Query Messages to the specific port"
			::= { fkV2IgsVlanStatsEntry 2 }

		
--  1.3.6.1.4.1.10428 9 1.102.12.2.2.5.6.1.1.3
		-- 1.3.6.1.4.1.10428 9 1.102.12.2.2.5.7.1.1.3
		fkV2IgsVlanStatsTxGroupSpecificQueies OBJECT-TYPE
			SYNTAX Unsigned32
			MAX-ACCESS read-only
			STATUS current
			DESCRIPTION
				"The count of sending the Group Specific Query Messages to the specific port"
			::= { fkV2IgsVlanStatsEntry 3 }

		
--  1.3.6.1.4.1.10428 9 1.102.12.2.2.5.6.1.1.4
		-- 1.3.6.1.4.1.10428 9 1.102.12.2.2.5.7.1.1.4
		fkV2IgsVlanStatsTxReports OBJECT-TYPE
			SYNTAX Unsigned32
			MAX-ACCESS read-only
			STATUS current
			DESCRIPTION
				"The count of sending the Membership Report Messages to the secific port"
			::= { fkV2IgsVlanStatsEntry 4 }

		
--  1.3.6.1.4.1.10428 9 1.102.12.2.2.5.6.1.1.5
		-- 1.3.6.1.4.1.10428 9 1.102.12.2.2.5.7.1.1.5
		fkV2IgsVlanStatsTxLeaves OBJECT-TYPE
			SYNTAX Unsigned32
			MAX-ACCESS read-only
			STATUS current
			DESCRIPTION
				"The count of sending the Leave Membership Messages to the specific port"
			::= { fkV2IgsVlanStatsEntry 5 }

		
--  1.3.6.1.4.1.10428 9 1.102.12.2.2.5.6.1.1.6
		-- 1.3.6.1.4.1.10428 9 1.102.12.2.2.5.7.1.1.6
		fkV2IgsVlanStatsRxGeneralQueries OBJECT-TYPE
			SYNTAX Unsigned32
			MAX-ACCESS read-only
			STATUS current
			DESCRIPTION
				"The count of receiving the General Query Messages from the specific port"
			::= { fkV2IgsVlanStatsEntry 6 }

		
--  1.3.6.1.4.1.10428 9 1.102.12.2.2.5.6.1.1.7
		-- 1.3.6.1.4.1.10428 9 1.102.12.2.2.5.7.1.1.7
		fkV2IgsVlanStatsRxGroupSpecificQueies OBJECT-TYPE
			SYNTAX Unsigned32
			MAX-ACCESS read-only
			STATUS current
			DESCRIPTION
				"The count of receiving the Group Specific Query Messages from the specific port"
			::= { fkV2IgsVlanStatsEntry 7 }

		
--  1.3.6.1.4.1.10428 9 1.102.12.2.2.5.6.1.1.8
		-- 1.3.6.1.4.1.10428 9 1.102.12.2.2.5.7.1.1.8
		fkV2IgsVlanStatsRxReports OBJECT-TYPE
			SYNTAX Unsigned32
			MAX-ACCESS read-only
			STATUS current
			DESCRIPTION
				"The count of recieving the Membership Report Messages from the specific ports. (SuccessRxReports)"
			::= { fkV2IgsVlanStatsEntry 8 }

		
--  1.3.6.1.4.1.10428 9 1.102.12.2.2.5.6.1.1.9
		-- 1.3.6.1.4.1.10428 9 1.102.12.2.2.5.7.1.1.9
		fkV2IgsVlanStatsRxLeaves OBJECT-TYPE
			SYNTAX Unsigned32
			MAX-ACCESS read-only
			STATUS current
			DESCRIPTION
				"The count of receiving the Leave Membership Messages from the specific port"
			::= { fkV2IgsVlanStatsEntry 9 }

		
--  1.3.6.1.4.1.10428 9 1.102.12.2.2.5.6.1.1.10
		-- 1.3.6.1.4.1.10428 9 1.102.12.2.2.5.7.1.1.10
		fkV2IgsVlanStatsRxValidPackets OBJECT-TYPE
			SYNTAX Unsigned32
			MAX-ACCESS read-only
			STATUS current
			DESCRIPTION
				"The count of receiving the valid IGMP Packets from the specific port"
			::= { fkV2IgsVlanStatsEntry 10 }

		
--  1.3.6.1.4.1.10428 9 1.102.12.2.2.5.6.1.1.11
		-- 1.3.6.1.4.1.10428 9 1.102.12.2.2.5.7.1.1.11
		fkV2IgsVlanStatsRxInvalidPackets OBJECT-TYPE
			SYNTAX Unsigned32
			MAX-ACCESS read-only
			STATUS current
			DESCRIPTION
				"The count of receiving the Invalid Packets from the specific port"
			::= { fkV2IgsVlanStatsEntry 11 }

		
--  1.3.6.1.4.1.10428 9 1.102.12.2.2.5.6.1.1.12
		-- 1.3.6.1.4.1.10428 9 1.102.12.2.2.5.7.1.1.12
		fkV2IgsVlanStatsRxOtherPackets OBJECT-TYPE
			SYNTAX Unsigned32
			MAX-ACCESS read-only
			STATUS current
			DESCRIPTION
				"The count of receiving the valid IGMP Packets but not defined from the specific port"
			::= { fkV2IgsVlanStatsEntry 12 }

		
--  1.3.6.1.4.1.10428 9 1.102.12.2.2.5.6.1.1.13
		-- 1.3.6.1.4.1.10428 9 1.102.12.2.2.5.7.1.1.13
		fkV2IgsVlanStatsRxMacGeneralQueries OBJECT-TYPE
			SYNTAX Unsigned32
			MAX-ACCESS read-only
			STATUS current
			DESCRIPTION
				"The count of receiving the MAC General Query Messages from the specific port"
			::= { fkV2IgsVlanStatsEntry 13 }

		
--  1.3.6.1.4.1.10428 9 1.102.12.2.2.5.6.1.1.14
		-- 1.3.6.1.4.1.10428 9 1.102.12.2.2.5.7.1.1.14
		fkV2IgsVlanStatsRxTopoNotifications OBJECT-TYPE
			SYNTAX Unsigned32
			MAX-ACCESS read-only
			STATUS current
			DESCRIPTION
				"The count of receiving the Topology Change Notification Messages from the specific port"
			::= { fkV2IgsVlanStatsEntry 14 }

		
--  1.3.6.1.4.1.10428 9 1.102.12.2.2.5.6.1.1.15
		-- 1.3.6.1.4.1.10428 9 1.102.12.2.2.5.7.1.1.15
		fkV2IgsVlanStatsv3Allows OBJECT-TYPE
			SYNTAX Unsigned32
			MAX-ACCESS read-only
			STATUS current
			DESCRIPTION
				"The count of receiving the IGMP Version-3 Allow Messages from the specific port"
			::= { fkV2IgsVlanStatsEntry 15 }

		
--  1.3.6.1.4.1.10428 9 1.102.12.2.2.5.6.1.1.16
		-- 1.3.6.1.4.1.10428 9 1.102.12.2.2.5.7.1.1.16
		fkV2IgsVlanStatsv3Blocks OBJECT-TYPE
			SYNTAX Unsigned32
			MAX-ACCESS read-only
			STATUS current
			DESCRIPTION
				"The count of receiving the IGMP Version-3 Block Messages from the specific port"
			::= { fkV2IgsVlanStatsEntry 16 }

		
--  1.3.6.1.4.1.10428 9 1.102.12.2.2.5.6.1.1.17
		-- 1.3.6.1.4.1.10428 9 1.102.12.2.2.5.7.1.1.17
		fkV2IgsVlanStatsv3IsIncluded OBJECT-TYPE
			SYNTAX Unsigned32
			MAX-ACCESS read-only
			STATUS current
			DESCRIPTION
				"The count of recieving the IGMP version-3 Membership Report Messages Whose Type is ISINCLUDE from the specific port"
			::= { fkV2IgsVlanStatsEntry 17 }

		
--  1.3.6.1.4.1.10428 9 1.102.12.2.2.5.6.1.1.18
		-- 1.3.6.1.4.1.10428 9 1.102.12.2.2.5.7.1.1.18
		fkV2IgsVlanStatsv3IsExcluded OBJECT-TYPE
			SYNTAX Unsigned32
			MAX-ACCESS read-only
			STATUS current
			DESCRIPTION
				"The count of receiving the IGMP version-3 Membership Report Messages Whose type is ISEXCLUDE from the specific port"
			::= { fkV2IgsVlanStatsEntry 18 }

		
--  1.3.6.1.4.1.10428 9 1.102.12.2.2.5.6.1.1.19
		-- 1.3.6.1.4.1.10428 9 1.102.12.2.2.5.7.1.1.19
		fkV2IgsVlanStatsv3ToIncluded OBJECT-TYPE
			SYNTAX Unsigned32
			MAX-ACCESS read-only
			STATUS current
			DESCRIPTION
				"The count of receiving the IGMP version-3 Membership Report Messages Whose type is TOINCLUDE from the specific port"
			::= { fkV2IgsVlanStatsEntry 19 }

		
--  1.3.6.1.4.1.10428 9 1.102.12.2.2.5.6.1.1.20
		-- 1.3.6.1.4.1.10428 9 1.102.12.2.2.5.7.1.1.20
		fkV2IgsVlanStatsv3ToExcluded OBJECT-TYPE
			SYNTAX Unsigned32
			MAX-ACCESS read-only
			STATUS current
			DESCRIPTION
				"The count of receiving the IGMP version-3 Membership Report Messages Whose type is TOEXCLUDE from the specific port"
			::= { fkV2IgsVlanStatsEntry 20 }

		
--  1.3.6.1.4.1.10428 9 1.102.12.2.2.5.6.1.1.21
		-- 1.3.6.1.4.1.10428 9 1.102.12.2.2.5.7.1.1.21
		fkV2IgsVlanStatsRxFilteredPackets OBJECT-TYPE
			SYNTAX Unsigned32
			MAX-ACCESS read-only
			STATUS current
			DESCRIPTION
				"The count of receiving the valid IGMP Packet that is blocked  by IGMP Filter from the specific port"
			::= { fkV2IgsVlanStatsEntry 21 }

		
		-- 1.3.6.1.4.1.10428 9 1.102.12.2.2.5.7.1.1.22
		fkV2IgsVlanStatsTotalRxReports OBJECT-TYPE
			SYNTAX Unsigned32
			MAX-ACCESS read-only
			STATUS current
			DESCRIPTION
				"Total RX reports."
			::= { fkV2IgsVlanStatsEntry 22 }

		
		-- 1.3.6.1.4.1.10428 9 1.102.12.2.2.5.7.1.1.23
		fkV2IgsVlanStatsUnsuccessRxReports OBJECT-TYPE
			SYNTAX Unsigned32
			MAX-ACCESS read-only
			STATUS current
			DESCRIPTION
				"Total RX reports."
			::= { fkV2IgsVlanStatsEntry 23 }

		
--  1.3.6.1.4.1.10428 9 1.102.12.2.2.5.6.2
		-- 1.3.6.1.4.1.10428 9 1.102.12.2.2.5.7.2
		fkV2IgsVlanStatsControl OBJECT IDENTIFIER ::= { fkV2IgsVlanStats 2 }

		
--  1.3.6.1.4.1.10428 9 1.102.12.2.2.5.6.2.1
		-- 1.3.6.1.4.1.10428 9 1.102.12.2.2.5.7.2.1
		fkV2IgsVlanStatsControlRequest OBJECT-TYPE
			SYNTAX INTEGER { clearIgsVlanStats(1) }
			MAX-ACCESS read-write
			STATUS current
			DESCRIPTION
				"The request of a user command"
			::= { fkV2IgsVlanStatsControl 1 }

		
--  1.3.6.1.4.1.10428 9 1.102.12.2.2.5.6.2.2
		-- 1.3.6.1.4.1.10428 9 1.102.12.2.2.5.7.2.2
		fkV2IgsVlanStatsControlStatus OBJECT-TYPE
			SYNTAX FkControlStatusType
			MAX-ACCESS read-write
			STATUS current
			DESCRIPTION
				"The status of user command"
			::= { fkV2IgsVlanStatsControl 2 }

		
--  1.3.6.1.4.1.10428 9 1.102.12.2.2.5.6.2.3
		-- 1.3.6.1.4.1.10428 9 1.102.12.2.2.5.7.2.3
		fkV2IgsVlanStatsControlControlTimer OBJECT-TYPE
			SYNTAX Gauge32
			MAX-ACCESS read-write
			STATUS current
			DESCRIPTION
				"The maximum time for the manager for a long running user command"
			::= { fkV2IgsVlanStatsControl 3 }

		
--  1.3.6.1.4.1.10428 9 1.102.12.2.2.5.6.2.4
		-- 1.3.6.1.4.1.10428 9 1.102.12.2.2.5.7.2.4
		fkV2IgsVlanStatsControlTimeStamp OBJECT-TYPE
			SYNTAX TimeTicks
			MAX-ACCESS read-write
			STATUS current
			DESCRIPTION
				"The time stamp of the last command(end of command)"
			::= { fkV2IgsVlanStatsControl 4 }

		
--  1.3.6.1.4.1.10428 9 1.102.12.2.2.5.6.2.5
		-- 1.3.6.1.4.1.10428 9 1.102.12.2.2.5.7.2.5
		fkV2IgsVlanStatsControlReqResult OBJECT-TYPE
			SYNTAX FkControlRequestResultType
			MAX-ACCESS read-write
			STATUS current
			DESCRIPTION
				"The result of the last user command
				"
			::= { fkV2IgsVlanStatsControl 5 }

		
--  1.3.6.1.4.1.10428 9 1.102.12.2.2.5.6.2.6
		-- 1.3.6.1.4.1.10428 9 1.102.12.2.2.5.7.2.6
		fkV2IgsVlanStatsControlIndex OBJECT-TYPE
			SYNTAX Integer32
			MAX-ACCESS read-write
			STATUS current
			DESCRIPTION
				"IGS stats index."
			::= { fkV2IgsVlanStatsControl 6 }

		
--  1.3.6.1.4.1.10428 9 1.102.12.2.2.5.6.3
		-- 1.3.6.1.4.1.10428 9 1.102.12.2.2.5.7.3
		fkV2IgsVlanStatsNotification OBJECT IDENTIFIER ::= { fkV2IgsVlanStats 3 }

		
--  1.3.6.1.4.1.10428 9 1.102.12.2.2.5.6.3.1
		-- 1.3.6.1.4.1.10428 9 1.102.12.2.2.5.7.3.1
		fkV2IgsVlanStatsCleared NOTIFICATION-TYPE
			OBJECTS { fkV2IgsVlanStatsControlRequest, fkV2IgsVlanStatsControlTimeStamp, fkV2IgsVlanStatsControlReqResult, fkV2IgsVlanStatsControlIndex }
			STATUS current
			DESCRIPTION 
				"Description."
			::= { fkV2IgsVlanStatsNotification 1 }

		
--  IGMP Filter
-- 1.3.6.1.4.1.10428 9 1.102.12.2.2.6
		-- 1.3.6.1.4.1.10428 9 1.102.12.2.2.6
		fkV2IgmpFilter OBJECT IDENTIFIER ::= { fkV2Igmp 6 }

		
--  IGMP Profile
-- 1.3.6.1.4.1.10428 9 1.102.12.2.2.6.1
		-- 1.3.6.1.4.1.10428 9 1.102.12.2.2.6.1
		fkV2IgfProfile OBJECT IDENTIFIER ::= { fkV2IgmpFilter 1 }

		
--  IGMP Profile Table
-- 1.3.6.1.4.1.10428 9 1.102.12.2.2.6.1.1
		-- 1.3.6.1.4.1.10428 9 1.102.12.2.2.6.1.1
		fkV2IgfProfileTable OBJECT-TYPE
			SYNTAX SEQUENCE OF FkV2IgfProfileEntry
			MAX-ACCESS not-accessible
			STATUS current
			DESCRIPTION
				" IGF profile table."
			::= { fkV2IgfProfile 1 }

		
--  IGMP Profile Entry
-- 1.3.6.1.4.1.10428 9 1.102.12.2.2.6.1.1.1
		-- 1.3.6.1.4.1.10428 9 1.102.12.2.2.6.1.1.1
		fkV2IgfProfileEntry OBJECT-TYPE
			SYNTAX FkV2IgfProfileEntry
			MAX-ACCESS not-accessible
			STATUS current
			DESCRIPTION
				"key: fkV2IgfProfileIndex"
			INDEX { fkV2IgfProfileIndex }
			::= { fkV2IgfProfileTable 1 }

		
		FkV2IgfProfileEntry ::=
			SEQUENCE { 
				fkV2IgfProfileIndex
					INTEGER,
				fkV2IgfProfilePermission
					INTEGER,
				fkV2IgfProfileName
					OCTET STRING
			 }

--  1.3.6.1.4.1.10428 9 1.102.12.2.2.6.1.1.1.1
		-- 1.3.6.1.4.1.10428 9 1.102.12.2.2.6.1.1.1.1
		fkV2IgfProfileIndex OBJECT-TYPE
			SYNTAX INTEGER (1..2147483647)
			MAX-ACCESS read-only
			STATUS current
			DESCRIPTION
				" Unique index of IGMP profile"
			::= { fkV2IgfProfileEntry 1 }

		
--  1.3.6.1.4.1.10428 9 1.102.12.2.2.6.1.1.1.2
		-- 1.3.6.1.4.1.10428 9 1.102.12.2.2.6.1.1.1.2
		fkV2IgfProfilePermission OBJECT-TYPE
			SYNTAX INTEGER
				{
				permit(1),
				deny(2)
				}
			MAX-ACCESS read-only
			STATUS current
			DESCRIPTION
				" It is a policy (permission) of the IGMP profile."
			::= { fkV2IgfProfileEntry 2 }

		
--  1.3.6.1.4.1.10428 9 1.102.12.2.2.6.1.1.1.3
		-- 1.3.6.1.4.1.10428 9 1.102.12.2.2.6.1.1.1.3
		fkV2IgfProfileName OBJECT-TYPE
			SYNTAX OCTET STRING
			MAX-ACCESS read-only
			STATUS current
			DESCRIPTION
				"Name of IGMP profile"
			::= { fkV2IgfProfileEntry 3 }

		
--  IGMP Profile Control
-- 1.3.6.1.4.1.10428 9 1.102.12.2.2.6.1.2
		-- 1.3.6.1.4.1.10428 9 1.102.12.2.2.6.1.2
		fkV2IgfProfileControl OBJECT IDENTIFIER ::= { fkV2IgfProfile 2 }

		
--  1.3.6.1.4.1.10428 9 1.102.12.2.2.6.1.2.1
		-- 1.3.6.1.4.1.10428 9 1.102.12.2.2.6.1.2.1
		fkV2IgfProfileControlRequest OBJECT-TYPE
			SYNTAX INTEGER
				{
				createIgmpProfile(1),
				destroyIgmpProfile(2),
				setIgmpProfile(3),
				createIgmpProfileByName(4)
				}
			MAX-ACCESS read-write
			STATUS current
			DESCRIPTION
				" The request of a user command"
			::= { fkV2IgfProfileControl 1 }

		
--  1.3.6.1.4.1.10428 9 1.102.12.2.2.6.1.2.2
		-- 1.3.6.1.4.1.10428 9 1.102.12.2.2.6.1.2.2
		fkV2IgfProfileControlStatus OBJECT-TYPE
			SYNTAX FkControlStatusType
			MAX-ACCESS read-only
			STATUS current
			DESCRIPTION
				" The status of user command"
			::= { fkV2IgfProfileControl 2 }

		
--  1.3.6.1.4.1.10428 9 1.102.12.2.2.6.1.2.3
		-- 1.3.6.1.4.1.10428 9 1.102.12.2.2.6.1.2.3
		fkV2IgfProfileControlTimer OBJECT-TYPE
			SYNTAX Gauge32
			MAX-ACCESS read-write
			STATUS current
			DESCRIPTION
				" The maximum time for the manager for a long running user command"
			::= { fkV2IgfProfileControl 3 }

		
--  1.3.6.1.4.1.10428 9 1.102.12.2.2.6.1.2.4
		-- 1.3.6.1.4.1.10428 9 1.102.12.2.2.6.1.2.4
		fkV2IgfProfileControlTimeStamp OBJECT-TYPE
			SYNTAX TimeStamp
			MAX-ACCESS read-only
			STATUS current
			DESCRIPTION
				" The time stamp of the last command(end of command)"
			::= { fkV2IgfProfileControl 4 }

		
--  1.3.6.1.4.1.10428 9 1.102.12.2.2.6.1.2.5
		-- 1.3.6.1.4.1.10428 9 1.102.12.2.2.6.1.2.5
		fkV2IgfProfileControlReqResult OBJECT-TYPE
			SYNTAX FkControlRequestResultType
			MAX-ACCESS read-only
			STATUS current
			DESCRIPTION
				" The result of the last user command
				"
			::= { fkV2IgfProfileControl 5 }

		
--  1.3.6.1.4.1.10428 9 1.102.12.2.2.6.1.2.6
		-- 1.3.6.1.4.1.10428 9 1.102.12.2.2.6.1.2.6
		fkV2IgfProfileControlIndex OBJECT-TYPE
			SYNTAX Unsigned32
			MAX-ACCESS read-write
			STATUS current
			DESCRIPTION
				"CLI : (no) ip igmp profile <1-4294967295>
				value(0) : (no)"
			::= { fkV2IgfProfileControl 6 }

		
--  1.3.6.1.4.1.10428 9 1.102.12.2.2.6.1.2.7
		-- 1.3.6.1.4.1.10428 9 1.102.12.2.2.6.1.2.7
		fkV2IgfProfileControlPermission OBJECT-TYPE
			SYNTAX INTEGER
				{
				permit(1),
				deny(2)
				}
			MAX-ACCESS read-write
			STATUS current
			DESCRIPTION
				"CLI : permit
				deny"
			DEFVAL { 1 }
			::= { fkV2IgfProfileControl 7 }

		
--  1.3.6.1.4.1.10428 9 1.102.12.2.2.6.1.2.8
		-- 1.3.6.1.4.1.10428 9 1.102.12.2.2.6.1.2.8
		fkV2IgfProfileControlName OBJECT-TYPE
			SYNTAX OCTET STRING
			MAX-ACCESS read-write
			STATUS current
			DESCRIPTION
				"Name of IGMP profile
				(Supported only model 5924N)
				"
			::= { fkV2IgfProfileControl 8 }

		
--  IGMP Profile Notification
-- 1.3.6.1.4.1.10428 9 1.102.12.2.2.6.1.3
		-- 1.3.6.1.4.1.10428 9 1.102.12.2.2.6.1.3
		fkV2IgfProfileNotification OBJECT IDENTIFIER ::= { fkV2IgfProfile 3 }

		
--  1.3.6.1.4.1.10428 9 1.102.12.2.2.6.1.3.1
		-- 1.3.6.1.4.1.10428 9 1.102.12.2.2.6.1.3.1
		fkV2IgfProfileCreated NOTIFICATION-TYPE
			OBJECTS { fkV2IgfProfileControlRequest, fkV2IgfProfileControlReqResult, fkV2IgfProfileControlTimeStamp, fkV2IgfProfilePermission }
			STATUS current
			DESCRIPTION 
				" "
			::= { fkV2IgfProfileNotification 1 }

		
--  1.3.6.1.4.1.10428 9 1.102.12.2.2.6.1.3.2
		-- 1.3.6.1.4.1.10428 9 1.102.12.2.2.6.1.3.2
		fkV2IgfProfileDestroyed NOTIFICATION-TYPE
			OBJECTS { fkV2IgfProfileControlRequest, fkV2IgfProfileControlReqResult, fkV2IgfProfileControlTimeStamp, fkV2IgfProfilePermission }
			STATUS current
			DESCRIPTION 
				"Description."
			::= { fkV2IgfProfileNotification 2 }

		
--  1.3.6.1.4.1.10428 9 1.102.12.2.2.6.1.3.3
		-- 1.3.6.1.4.1.10428 9 1.102.12.2.2.6.1.3.3
		fkV2IgfProfileChanged NOTIFICATION-TYPE
			OBJECTS { fkV2IgfProfileControlRequest, fkV2IgfProfileControlReqResult, fkV2IgfProfileControlTimeStamp, fkV2IgfProfilePermission }
			STATUS current
			DESCRIPTION 
				"Description."
			::= { fkV2IgfProfileNotification 3 }

		
--  1.3.6.1.4.1.10428 9 1.102.12.2.2.6.1.3.4
		-- 1.3.6.1.4.1.10428 9 1.102.12.2.2.6.1.3.4
		fkV2IgfProfileByNameCreated NOTIFICATION-TYPE
			OBJECTS { fkV2IgfProfileControlRequest, fkV2IgfProfileControlTimeStamp, fkV2IgfProfileControlReqResult, fkV2IgfProfilePermission, fkV2IgfProfileName
				 }
			STATUS current
			DESCRIPTION 
				"Description."
			::= { fkV2IgfProfileNotification 4 }

		
--  IGMP Profile Range
-- 1.3.6.1.4.1.10428 9 1.102.12.2.2.6.2
		-- 1.3.6.1.4.1.10428 9 1.102.12.2.2.6.2
		fkV2IgfpRange OBJECT IDENTIFIER ::= { fkV2IgmpFilter 2 }

		
--  IGMP Profile Range Table
-- 1.3.6.1.4.1.10428 9 1.102.12.2.2.6.2.1
		-- 1.3.6.1.4.1.10428 9 1.102.12.2.2.6.2.1
		fkV2IgfpRangeTable OBJECT-TYPE
			SYNTAX SEQUENCE OF FkV2IgfpRangeEntry
			MAX-ACCESS not-accessible
			STATUS current
			DESCRIPTION
				"IGFP ranger talbe."
			::= { fkV2IgfpRange 1 }

		
--  IGMP Profile Range Entry
-- 1.3.6.1.4.1.10428 9 1.102.12.2.2.6.2.1.1
		-- 1.3.6.1.4.1.10428 9 1.102.12.2.2.6.2.1.1
		fkV2IgfpRangeEntry OBJECT-TYPE
			SYNTAX FkV2IgfpRangeEntry
			MAX-ACCESS not-accessible
			STATUS current
			DESCRIPTION
				"key: fkV2IgfProfileIndex, fkV2IgfpRangeStartAddress, fkV2IgfpRangeEndAddress"
			INDEX { fkV2IgfProfileIndex, fkV2IgfpRangeStartAddress, fkV2IgfpRangeEndAddress }
			::= { fkV2IgfpRangeTable 1 }

		
		FkV2IgfpRangeEntry ::=
			SEQUENCE { 
				fkV2IgfpRangeStartAddress
					IpAddress,
				fkV2IgfpRangeEndAddress
					IpAddress
			 }

--  1.3.6.1.4.1.10428 9 1.102.12.2.2.6.2.1.1.1
		-- 1.3.6.1.4.1.10428 9 1.102.12.2.2.6.2.1.1.1
		fkV2IgfpRangeStartAddress OBJECT-TYPE
			SYNTAX IpAddress
			MAX-ACCESS read-only
			STATUS current
			DESCRIPTION
				" Start IP multicast address in a range of IGMP profile."
			::= { fkV2IgfpRangeEntry 1 }

		
--  1.3.6.1.4.1.10428 9 1.102.12.2.2.6.2.1.1.2
		-- 1.3.6.1.4.1.10428 9 1.102.12.2.2.6.2.1.1.2
		fkV2IgfpRangeEndAddress OBJECT-TYPE
			SYNTAX IpAddress
			MAX-ACCESS read-only
			STATUS current
			DESCRIPTION
				"End IP multicast address in a range of IGMP profile."
			::= { fkV2IgfpRangeEntry 2 }

		
--  IGMP Profile Range Control
-- 1.3.6.1.4.1.10428 9 1.102.12.2.2.6.2.2
		-- 1.3.6.1.4.1.10428 9 1.102.12.2.2.6.2.2
		fkV2IgfpRangeControl OBJECT IDENTIFIER ::= { fkV2IgfpRange 2 }

		
--  1.3.6.1.4.1.10428 9 1.102.12.2.2.6.2.2.1
		-- 1.3.6.1.4.1.10428 9 1.102.12.2.2.6.2.2.1
		fkV2IgfpRangeControlRequest OBJECT-TYPE
			SYNTAX INTEGER
				{
				addIgmpProfileRange(1),
				delIgmpProfileRange(2)
				}
			MAX-ACCESS read-write
			STATUS current
			DESCRIPTION
				" The request of a user command"
			::= { fkV2IgfpRangeControl 1 }

		
--  1.3.6.1.4.1.10428 9 1.102.12.2.2.6.2.2.2
		-- 1.3.6.1.4.1.10428 9 1.102.12.2.2.6.2.2.2
		fkV2IgfpRangeControlStatus OBJECT-TYPE
			SYNTAX FkControlStatusType
			MAX-ACCESS read-only
			STATUS current
			DESCRIPTION
				" The status of user command"
			::= { fkV2IgfpRangeControl 2 }

		
--  1.3.6.1.4.1.10428 9 1.102.12.2.2.6.2.2.3
		-- 1.3.6.1.4.1.10428 9 1.102.12.2.2.6.2.2.3
		fkV2IgfpRangeControlTimer OBJECT-TYPE
			SYNTAX Gauge32
			MAX-ACCESS read-write
			STATUS current
			DESCRIPTION
				" The maximum time for the manager for a long running user command"
			::= { fkV2IgfpRangeControl 3 }

		
--  1.3.6.1.4.1.10428 9 1.102.12.2.2.6.2.2.4
		-- 1.3.6.1.4.1.10428 9 1.102.12.2.2.6.2.2.4
		fkV2IgfpRangeControlTimeStamp OBJECT-TYPE
			SYNTAX TimeStamp
			MAX-ACCESS read-only
			STATUS current
			DESCRIPTION
				" The time stamp of the last command(end of command)"
			::= { fkV2IgfpRangeControl 4 }

		
--  1.3.6.1.4.1.10428 9 1.102.12.2.2.6.2.2.5
		-- 1.3.6.1.4.1.10428 9 1.102.12.2.2.6.2.2.5
		fkV2IgfpRangeControlReqResult OBJECT-TYPE
			SYNTAX FkControlRequestResultType
			MAX-ACCESS read-only
			STATUS current
			DESCRIPTION
				" The result of the last user command"
			::= { fkV2IgfpRangeControl 5 }

		
--  1.3.6.1.4.1.10428 9 1.102.12.2.2.6.2.2.6
		-- 1.3.6.1.4.1.10428 9 1.102.12.2.2.6.2.2.6
		fkV2IgfpRangeControlProfileIndex OBJECT-TYPE
			SYNTAX Unsigned32
			MAX-ACCESS read-write
			STATUS current
			DESCRIPTION
				"CLI : (no) ip igmp profile <1-4294967295>
				value(0) : (no)"
			::= { fkV2IgfpRangeControl 6 }

		
--  1.3.6.1.4.1.10428 9 1.102.12.2.2.6.2.2.7
		-- 1.3.6.1.4.1.10428 9 1.102.12.2.2.6.2.2.7
		fkV2IgfpRangeControlStartAddress OBJECT-TYPE
			SYNTAX IpAddress
			MAX-ACCESS read-write
			STATUS current
			DESCRIPTION
				"CLI : range A.B.C.D A.B.C.D"
			::= { fkV2IgfpRangeControl 7 }

		
--  1.3.6.1.4.1.10428 9 1.102.12.2.2.6.2.2.8
		-- 1.3.6.1.4.1.10428 9 1.102.12.2.2.6.2.2.8
		fkV2IgfpRangeControlEndAddress OBJECT-TYPE
			SYNTAX IpAddress
			MAX-ACCESS read-write
			STATUS current
			DESCRIPTION
				"CLI : range A.B.C.D A.B.C.D"
			::= { fkV2IgfpRangeControl 8 }

		
--  IGMP Profile Range Notification
-- 1.3.6.1.4.1.10428 9 1.102.12.2.2.6.2.3
		-- 1.3.6.1.4.1.10428 9 1.102.12.2.2.6.2.3
		fkV2IgfpRangeNotification OBJECT IDENTIFIER ::= { fkV2IgfpRange 3 }

		
--  1.3.6.1.4.1.10428 9 1.102.12.2.2.6.2.3.1
		-- 1.3.6.1.4.1.10428 9 1.102.12.2.2.6.2.3.1
		fkV2IgfpRangeAdded NOTIFICATION-TYPE
			OBJECTS { fkV2IgfpRangeControlRequest, fkV2IgfpRangeControlReqResult, fkV2IgfpRangeControlTimeStamp, fkV2IgfpRangeControlProfileIndex, fkV2IgfpRangeControlStartAddress, 
				fkV2IgfpRangeControlEndAddress }
			STATUS current
			DESCRIPTION 
				"Description."
			::= { fkV2IgfpRangeNotification 1 }

		
--  1.3.6.1.4.1.10428 9 1.102.12.2.2.6.2.3.2
		-- 1.3.6.1.4.1.10428 9 1.102.12.2.2.6.2.3.2
		fkV2IgfpRangeDeleted NOTIFICATION-TYPE
			OBJECTS { fkV2IgfpRangeControlRequest, fkV2IgfpRangeControlReqResult, fkV2IgfpRangeControlTimeStamp, fkV2IgfpRangeControlProfileIndex, fkV2IgfpRangeControlStartAddress, 
				fkV2IgfpRangeControlEndAddress }
			STATUS current
			DESCRIPTION 
				"Description."
			::= { fkV2IgfpRangeNotification 2 }

		
--  IGMP Filter Port
-- 1.3.6.1.4.1.10428 9 1.102.12.2.2.6.3
		-- 1.3.6.1.4.1.10428 9 1.102.12.2.2.6.3
		fkV2IgfPort OBJECT IDENTIFIER ::= { fkV2IgmpFilter 3 }

		
--  IGMP Filter Port Table
-- 1.3.6.1.4.1.10428 9 1.102.12.2.2.6.3.1
		-- 1.3.6.1.4.1.10428 9 1.102.12.2.2.6.3.1
		fkV2IgfPortTable OBJECT-TYPE
			SYNTAX SEQUENCE OF FkV2IgfPortEntry
			MAX-ACCESS not-accessible
			STATUS current
			DESCRIPTION
				" IGF port table."
			::= { fkV2IgfPort 1 }

		
--  IGMP Filter Port Entry
-- 1.3.6.1.4.1.10428 9 1.102.12.2.2.6.3.1.1
		-- 1.3.6.1.4.1.10428 9 1.102.12.2.2.6.3.1.1
		fkV2IgfPortEntry OBJECT-TYPE
			SYNTAX FkV2IgfPortEntry
			MAX-ACCESS not-accessible
			STATUS current
			DESCRIPTION
				"key: fkV2IgfPortIndex"
			INDEX { fkV2IgfPortIndex }
			::= { fkV2IgfPortTable 1 }

		
		FkV2IgfPortEntry ::=
			SEQUENCE { 
				fkV2IgfPortIndex
					Integer32,
				fkV2IgfPortProfileIndex
					Unsigned32,
				fkV2IgfPortMaxGroupCount
					Unsigned32,
				fkV2IgfPortMaxGroupAction
					INTEGER,
				fkV2IgfPortDhcpSnoopBindingPermission
					INTEGER,
				fkV2IgfPortPacketType
					BITS
			 }

--  1.3.6.1.4.1.10428 9 1.102.12.2.2.6.3.1.1.1
		-- 1.3.6.1.4.1.10428 9 1.102.12.2.2.6.3.1.1.1
		fkV2IgfPortIndex OBJECT-TYPE
			SYNTAX Integer32 (1..255)
			MAX-ACCESS read-only
			STATUS current
			DESCRIPTION
				" A port index to apply IGMP profile"
			::= { fkV2IgfPortEntry 1 }

		
--  1.3.6.1.4.1.10428 9 1.102.12.2.2.6.3.1.1.2
		-- 1.3.6.1.4.1.10428 9 1.102.12.2.2.6.3.1.1.2
		fkV2IgfPortProfileIndex OBJECT-TYPE
			SYNTAX Unsigned32 (0..2147483647)
			MAX-ACCESS read-only
			STATUS current
			DESCRIPTION
				" A port index to apply IGMP profile"
			::= { fkV2IgfPortEntry 2 }

		
--  1.3.6.1.4.1.10428 9 1.102.12.2.2.6.3.1.1.3
		-- 1.3.6.1.4.1.10428 9 1.102.12.2.2.6.3.1.1.3
		fkV2IgfPortMaxGroupCount OBJECT-TYPE
			SYNTAX Unsigned32 (0..2147483647)
			MAX-ACCESS read-only
			STATUS current
			DESCRIPTION
				" Maximum group count on the port."
			::= { fkV2IgfPortEntry 3 }

		
--  1.3.6.1.4.1.10428 9 1.102.12.2.2.6.3.1.1.4
		-- 1.3.6.1.4.1.10428 9 1.102.12.2.2.6.3.1.1.4
		fkV2IgfPortMaxGroupAction OBJECT-TYPE
			SYNTAX INTEGER
				{
				unknown(0),
				deny(1),
				replace(2)
				}
			MAX-ACCESS read-only
			STATUS current
			DESCRIPTION
				" Policy applied when exceeds the maximum group count. default value ‘deny(1)’."
			::= { fkV2IgfPortEntry 4 }

		
--  1.3.6.1.4.1.10428 9 1.102.12.2.2.6.3.1.1.5
		-- 1.3.6.1.4.1.10428 9 1.102.12.2.2.6.3.1.1.5
		fkV2IgfPortDhcpSnoopBindingPermission OBJECT-TYPE
			SYNTAX INTEGER
				{
				unused(0),
				permit(1),
				deny(2)
				}
			MAX-ACCESS read-only
			STATUS current
			DESCRIPTION
				"DHCP snoop binding permission
				0 : unused
				1 : permit
				2 : deny
				"
			::= { fkV2IgfPortEntry 5 }

		
		-- 1.3.6.1.4.1.10428 9 1.102.12.2.2.6.3.1.1.6
		fkV2IgfPortPacketType OBJECT-TYPE
			SYNTAX BITS
				{
				all(0),
				v1report(1),
				v2report(2),
				v3report(3),
				query(4),
				leave(5)
				}
			MAX-ACCESS read-only
			STATUS current
			DESCRIPTION
				"The packet-filter type."
			::= { fkV2IgfPortEntry 6 }

		
--  IGMP Filter Port Control
-- 1.3.6.1.4.1.10428 9 1.102.12.2.2.6.3.2
		-- 1.3.6.1.4.1.10428 9 1.102.12.2.2.6.3.2
		fkV2IgfPortControl OBJECT IDENTIFIER ::= { fkV2IgfPort 2 }

		
--  1.3.6.1.4.1.10428 9 1.102.12.2.2.6.3.2.1
		-- 1.3.6.1.4.1.10428 9 1.102.12.2.2.6.3.2.1
		fkV2IgfPortControlRequest OBJECT-TYPE
			SYNTAX INTEGER
				{
				setIgmpFilterPortProfileIndex(1),
				setIgmpFilterPortMaxGroupProfile(2),
				setIgmpFilterPortDhcpSnoopBindingPermission(3),
				setIgmpFilterPortPacketType(4)
				}
			MAX-ACCESS read-write
			STATUS current
			DESCRIPTION
				" The request of a user command"
			::= { fkV2IgfPortControl 1 }

		
--  1.3.6.1.4.1.10428 9 1.102.12.2.2.6.3.2.2
		-- 1.3.6.1.4.1.10428 9 1.102.12.2.2.6.3.2.2
		fkV2IgfPortControlStatus OBJECT-TYPE
			SYNTAX FkControlStatusType
			MAX-ACCESS read-only
			STATUS current
			DESCRIPTION
				" The status of user command"
			::= { fkV2IgfPortControl 2 }

		
--  1.3.6.1.4.1.10428 9 1.102.12.2.2.6.3.2.3
		-- 1.3.6.1.4.1.10428 9 1.102.12.2.2.6.3.2.3
		fkV2IgfPortControlTimer OBJECT-TYPE
			SYNTAX Gauge32
			MAX-ACCESS read-write
			STATUS current
			DESCRIPTION
				"The maximum time for the manager for a long running user command"
			::= { fkV2IgfPortControl 3 }

		
--  1.3.6.1.4.1.10428 9 1.102.12.2.2.6.3.2.4
		-- 1.3.6.1.4.1.10428 9 1.102.12.2.2.6.3.2.4
		fkV2IgfPortControlTimeStamp OBJECT-TYPE
			SYNTAX TimeStamp
			MAX-ACCESS read-only
			STATUS current
			DESCRIPTION
				" The time stamp of the last command(end of command)"
			::= { fkV2IgfPortControl 4 }

		
--  1.3.6.1.4.1.10428 9 1.102.12.2.2.6.3.2.5
		-- 1.3.6.1.4.1.10428 9 1.102.12.2.2.6.3.2.5
		fkV2IgfPortControlReqResult OBJECT-TYPE
			SYNTAX FkControlRequestResultType
			MAX-ACCESS read-only
			STATUS current
			DESCRIPTION
				" The time stamp of the last command(end of command)
				The result of the last user command"
			::= { fkV2IgfPortControl 5 }

		
--  1.3.6.1.4.1.10428 9 1.102.12.2.2.6.3.2.6
		-- 1.3.6.1.4.1.10428 9 1.102.12.2.2.6.3.2.6
		fkV2IgfPortControlIndex OBJECT-TYPE
			SYNTAX INTEGER (1..512)
			MAX-ACCESS read-write
			STATUS current
			DESCRIPTION
				" A port index to apply IGMP profile"
			::= { fkV2IgfPortControl 6 }

		
--  1.3.6.1.4.1.10428 9 1.102.12.2.2.6.3.2.7
		-- 1.3.6.1.4.1.10428 9 1.102.12.2.2.6.3.2.7
		fkV2IgfPortControlProfileIndex OBJECT-TYPE
			SYNTAX Unsigned32 (0..2147483647)
			MAX-ACCESS read-write
			STATUS current
			DESCRIPTION
				"CLI : (no) ip igmp filter port PORT profile <1-4294967295>
				value(0) : (no)"
			::= { fkV2IgfPortControl 7 }

		
--  1.3.6.1.4.1.10428 9 1.102.12.2.2.6.3.2.8
		-- 1.3.6.1.4.1.10428 9 1.102.12.2.2.6.3.2.8
		fkV2IgfPortControlMaxGroupCount OBJECT-TYPE
			SYNTAX Unsigned32 (0..2147483647)
			MAX-ACCESS read-write
			STATUS current
			DESCRIPTION
				"CLI : (no) ip igmp max-groups port PORT count <1-4294967295> action (deny|replace)"
			::= { fkV2IgfPortControl 8 }

		
--  1.3.6.1.4.1.10428 9 1.102.12.2.2.6.3.2.9
		-- 1.3.6.1.4.1.10428 9 1.102.12.2.2.6.3.2.9
		fkV2IgfPortControlMaxGroupAction OBJECT-TYPE
			SYNTAX INTEGER
				{
				deny(1),
				replace(2)
				}
			MAX-ACCESS read-write
			STATUS current
			DESCRIPTION
				"CLI : (no) ip igmp max-groups port PORT count <1-4294967295> action (deny|replace)"
			::= { fkV2IgfPortControl 9 }

		
--  1.3.6.1.4.1.10428 9 1.102.12.2.2.6.3.2.10
		-- 1.3.6.1.4.1.10428 9 1.102.12.2.2.6.3.2.10
		fkV2IgfPortControlDhcpSnoopBindingPermission OBJECT-TYPE
			SYNTAX INTEGER
				{
				unused(0),
				permit(1),
				deny(2)
				}
			MAX-ACCESS read-write
			STATUS current
			DESCRIPTION
				"DHCP snoop binding permission
				0 : unused
				1 : permit
				2 : deny
				"
			::= { fkV2IgfPortControl 10 }

		
		-- 1.3.6.1.4.1.10428 9 1.102.12.2.2.6.3.2.11
		fkV2IgfPortControlPacketType OBJECT-TYPE
			SYNTAX BITS
				{
				all(0),
				v1report(1),
				v2report(2),
				v3report(3),
				query(4),
				leave(5)
				}
			MAX-ACCESS read-write
			STATUS current
			DESCRIPTION
				"The packet-filter type."
			::= { fkV2IgfPortControl 11 }

		
--  IGMP Filter Port Notification
-- 1.3.6.1.4.1.10428 9 1.102.12.2.2.6.3.3
		-- 1.3.6.1.4.1.10428 9 1.102.12.2.2.6.3.3
		fkV2IgfPortNotification OBJECT IDENTIFIER ::= { fkV2IgfPort 3 }

		
--  1.3.6.1.4.1.10428 9 1.102.12.2.2.6.3.3.1
		-- 1.3.6.1.4.1.10428 9 1.102.12.2.2.6.3.3.1
		fkV2IgfPortProfileChanged NOTIFICATION-TYPE
			OBJECTS { fkV2IgfPortControlRequest, fkV2IgfPortControlReqResult, fkV2IgfPortControlTimeStamp, fkV2IgfPortProfileIndex }
			STATUS current
			DESCRIPTION 
				" "
			::= { fkV2IgfPortNotification 1 }

		
--  1.3.6.1.4.1.10428 9 1.102.12.2.2.6.3.3.2
		-- 1.3.6.1.4.1.10428 9 1.102.12.2.2.6.3.3.2
		fkV2IgfPortMaxGroupChanged NOTIFICATION-TYPE
			OBJECTS { fkV2IgfPortControlRequest, fkV2IgfPortControlReqResult, fkV2IgfPortControlTimeStamp, fkV2IgfPortMaxGroupCount, fkV2IgfPortMaxGroupAction
				 }
			STATUS current
			DESCRIPTION 
				" "
			::= { fkV2IgfPortNotification 2 }

		
--  1.3.6.1.4.1.10428 9 1.102.12.2.2.6.3.3.3
		-- 1.3.6.1.4.1.10428 9 1.102.12.2.2.6.3.3.3
		fkV2IgfPortDhcpSnoopBindingPermissionChanged NOTIFICATION-TYPE
			OBJECTS { fkV2IgfPortControlRequest, fkV2IgfPortControlTimeStamp, fkV2IgfPortControlReqResult, fkV2IgfPortDhcpSnoopBindingPermission }
			STATUS current
			DESCRIPTION 
				"Description."
			::= { fkV2IgfPortNotification 3 }

		
		-- 1.3.6.1.4.1.10428 9 1.102.12.2.2.6.3.3.4
		fkV2IgfPortPacketTypeChanged NOTIFICATION-TYPE
			OBJECTS { fkV2IgfPortControlRequest, fkV2IgfPortControlTimeStamp, fkV2IgfPortControlReqResult, fkV2IgfPortControlPacketType }
			STATUS current
			DESCRIPTION 
				"Description."
			::= { fkV2IgfPortNotification 4 }

		
--  Multicast VLAN Registration
-- 1.3.6.1.4.1.10428 9 1.102.12.2.2.7
		-- 1.3.6.1.4.1.10428 9 1.102.12.2.2.7
		fkV2Mvr4 OBJECT IDENTIFIER ::= { fkV2Igmp 7 }

		
--  MVR Port
-- 1.3.6.1.4.1.10428 9 1.102.12.2.2.7.1
		-- 1.3.6.1.4.1.10428 9 1.102.12.2.2.7.1
		fkV2Mvr4Port OBJECT IDENTIFIER ::= { fkV2Mvr4 1 }

		
--  MVR Port Table
-- 1.3.6.1.4.1.10428 9 1.102.12.2.2.7.1.1
		-- 1.3.6.1.4.1.10428 9 1.102.12.2.2.7.1.1
		fkV2Mvr4PortTable OBJECT-TYPE
			SYNTAX SEQUENCE OF FkV2Mvr4PortEntry
			MAX-ACCESS not-accessible
			STATUS current
			DESCRIPTION
				"port table."
			::= { fkV2Mvr4Port 1 }

		
--  MVR Port Entry
-- 1.3.6.1.4.1.10428 9 1.102.12.2.2.7.1.1.1
		-- 1.3.6.1.4.1.10428 9 1.102.12.2.2.7.1.1.1
		fkV2Mvr4PortEntry OBJECT-TYPE
			SYNTAX FkV2Mvr4PortEntry
			MAX-ACCESS not-accessible
			STATUS current
			DESCRIPTION
				"key: fkV2Mvr4PortIndex"
			INDEX { fkV2Mvr4PortIndex }
			::= { fkV2Mvr4PortTable 1 }

		
		FkV2Mvr4PortEntry ::=
			SEQUENCE { 
				fkV2Mvr4PortIndex
					INTEGER,
				fkV2Mvr4PortType
					INTEGER
			 }

--  1.3.6.1.4.1.10428 9 1.102.12.2.2.7.1.1.1.1
		-- 1.3.6.1.4.1.10428 9 1.102.12.2.2.7.1.1.1.1
		fkV2Mvr4PortIndex OBJECT-TYPE
			SYNTAX INTEGER (1..512)
			MAX-ACCESS read-only
			STATUS current
			DESCRIPTION
				"Same as ifIndex (for all ifTable entries)."
			::= { fkV2Mvr4PortEntry 1 }

		
--  1.3.6.1.4.1.10428 9 1.102.12.2.2.7.1.1.1.2
		-- 1.3.6.1.4.1.10428 9 1.102.12.2.2.7.1.1.1.2
		fkV2Mvr4PortType OBJECT-TYPE
			SYNTAX INTEGER
				{
				none(0),
				source(1),
				receiver(2)
				}
			MAX-ACCESS read-only
			STATUS current
			DESCRIPTION
				"It indicates the port's MVR operation type."
			DEFVAL { none }
			::= { fkV2Mvr4PortEntry 2 }

		
--  MVR Port Control
-- 1.3.6.1.4.1.10428 9 1.102.12.2.2.7.1.2
		-- 1.3.6.1.4.1.10428 9 1.102.12.2.2.7.1.2
		fkV2Mvr4PortControl OBJECT IDENTIFIER ::= { fkV2Mvr4Port 2 }

		
--  1.3.6.1.4.1.10428 9 1.102.12.2.2.7.1.2.1
		-- 1.3.6.1.4.1.10428 9 1.102.12.2.2.7.1.2.1
		fkV2Mvr4PortControlRequest OBJECT-TYPE
			SYNTAX INTEGER { setMvrPortProfile(1) }
			MAX-ACCESS read-write
			STATUS current
			DESCRIPTION
				" The request of a user command"
			::= { fkV2Mvr4PortControl 1 }

		
--  1.3.6.1.4.1.10428 9 1.102.12.2.2.7.1.2.2
		-- 1.3.6.1.4.1.10428 9 1.102.12.2.2.7.1.2.2
		fkV2Mvr4PortControlStatus OBJECT-TYPE
			SYNTAX FkControlStatusType
			MAX-ACCESS read-only
			STATUS current
			DESCRIPTION
				" The status of user command"
			::= { fkV2Mvr4PortControl 2 }

		
--  1.3.6.1.4.1.10428 9 1.102.12.2.2.7.1.2.3
		-- 1.3.6.1.4.1.10428 9 1.102.12.2.2.7.1.2.3
		fkV2Mvr4PortControlTimer OBJECT-TYPE
			SYNTAX Gauge32
			MAX-ACCESS read-write
			STATUS current
			DESCRIPTION
				" The maximum time for the manager for a long running user command"
			::= { fkV2Mvr4PortControl 3 }

		
--  1.3.6.1.4.1.10428 9 1.102.12.2.2.7.1.2.4
		-- 1.3.6.1.4.1.10428 9 1.102.12.2.2.7.1.2.4
		fkV2Mvr4PortControlTimeStamp OBJECT-TYPE
			SYNTAX TimeStamp
			MAX-ACCESS read-only
			STATUS current
			DESCRIPTION
				" The time stamp of the last command(end of command)"
			::= { fkV2Mvr4PortControl 4 }

		
--  1.3.6.1.4.1.10428 9 1.102.12.2.2.7.1.2.5
		-- 1.3.6.1.4.1.10428 9 1.102.12.2.2.7.1.2.5
		fkV2Mvr4PortControlReqResult OBJECT-TYPE
			SYNTAX FkControlRequestResultType
			MAX-ACCESS read-only
			STATUS current
			DESCRIPTION
				" The result of the last user command"
			::= { fkV2Mvr4PortControl 5 }

		
--  1.3.6.1.4.1.10428 9 1.102.12.2.2.7.1.2.6
		-- 1.3.6.1.4.1.10428 9 1.102.12.2.2.7.1.2.6
		fkV2Mvr4PortControlIndex OBJECT-TYPE
			SYNTAX INTEGER (1..512)
			MAX-ACCESS read-write
			STATUS current
			DESCRIPTION
				"Same as ifIndex (for all ifTable entries)."
			::= { fkV2Mvr4PortControl 6 }

		
--  1.3.6.1.4.1.10428 9 1.102.12.2.2.7.1.2.7
		-- 1.3.6.1.4.1.10428 9 1.102.12.2.2.7.1.2.7
		fkV2Mvr4PortControlType OBJECT-TYPE
			SYNTAX INTEGER
				{
				none(0),
				source(1),
				receiver(2)
				}
			MAX-ACCESS read-write
			STATUS current
			DESCRIPTION
				"It indicates the port's MVR operation type."
			::= { fkV2Mvr4PortControl 7 }

		
--  MVR Port Notification
-- 1.3.6.1.4.1.10428 9 1.102.12.2.2.7.1.3
		-- 1.3.6.1.4.1.10428 9 1.102.12.2.2.7.1.3
		fkV2Mvr4PortNotification OBJECT IDENTIFIER ::= { fkV2Mvr4Port 3 }

		
--  1.3.6.1.4.1.10428 9 1.102.12.2.2.7.1.3.1
		-- 1.3.6.1.4.1.10428 9 1.102.12.2.2.7.1.3.1
		fkV2Mvr4PortProfileChanged NOTIFICATION-TYPE
			OBJECTS { fkV2Mvr4PortControlRequest, fkV2Mvr4PortControlReqResult, fkV2Mvr4PortControlTimeStamp, fkV2Mvr4PortType }
			STATUS current
			DESCRIPTION 
				"setMvrPort"
			::= { fkV2Mvr4PortNotification 1 }

		
--  MVR Group
-- 1.3.6.1.4.1.10428 9 1.102.12.2.2.7.2
		-- 1.3.6.1.4.1.10428 9 1.102.12.2.2.7.2
		fkV2Mvr4Group OBJECT IDENTIFIER ::= { fkV2Mvr4 2 }

		
--  MVR Group Table
-- 1.3.6.1.4.1.10428 9 1.102.12.2.2.7.2.1
		-- 1.3.6.1.4.1.10428 9 1.102.12.2.2.7.2.1
		fkV2Mvr4GroupTable OBJECT-TYPE
			SYNTAX SEQUENCE OF FkV2Mvr4GroupEntry
			MAX-ACCESS not-accessible
			STATUS current
			DESCRIPTION
				"MVR group table."
			::= { fkV2Mvr4Group 1 }
-- group table.
		
--  MVR Group Entry
-- 1.3.6.1.4.1.10428 9 1.102.12.2.2.7.2.1.1
		-- 1.3.6.1.4.1.10428 9 1.102.12.2.2.7.2.1.1
		fkV2Mvr4GroupEntry OBJECT-TYPE
			SYNTAX FkV2Mvr4GroupEntry
			MAX-ACCESS not-accessible
			STATUS current
			DESCRIPTION
				"key: fkV2Mvr4GroupAddress"
			INDEX { fkV2Mvr4GroupAddress }
			::= { fkV2Mvr4GroupTable 1 }
-- key: fkV2Mvr4GroupAddress
		
		FkV2Mvr4GroupEntry ::=
			SEQUENCE { 
				fkV2Mvr4GroupAddress
					IpAddress,
				fkV2Mvr4GroupVlanIndex
					INTEGER
			 }

--  1.3.6.1.4.1.10428 9 1.102.12.2.2.7.2.1.1.1
		-- 1.3.6.1.4.1.10428 9 1.102.12.2.2.7.2.1.1.1
		fkV2Mvr4GroupAddress OBJECT-TYPE
			SYNTAX IpAddress
			MAX-ACCESS read-only
			STATUS current
			DESCRIPTION
				"This object indicates group address for MVR."
			::= { fkV2Mvr4GroupEntry 1 }

		
--  1.3.6.1.4.1.10428 9 1.102.12.2.2.7.2.1.1.2
		-- 1.3.6.1.4.1.10428 9 1.102.12.2.2.7.2.1.1.2
		fkV2Mvr4GroupVlanIndex OBJECT-TYPE
			SYNTAX INTEGER (1..4094)
			MAX-ACCESS read-only
			STATUS current
			DESCRIPTION
				"This object indicates the VLAN for MVR."
			::= { fkV2Mvr4GroupEntry 2 }

		
--  MVR Group Control
-- 1.3.6.1.4.1.10428 9 1.102.12.2.2.7.2.2
		-- 1.3.6.1.4.1.10428 9 1.102.12.2.2.7.2.2
		fkV2Mvr4GroupControl OBJECT IDENTIFIER ::= { fkV2Mvr4Group 2 }

		
--  1.3.6.1.4.1.10428 9 1.102.12.2.2.7.2.2.1
		-- 1.3.6.1.4.1.10428 9 1.102.12.2.2.7.2.2.1
		fkV2Mvr4GroupControlRequest OBJECT-TYPE
			SYNTAX INTEGER
				{
				createMvrGroup(1),
				destroyMvrGroup(2)
				}
			MAX-ACCESS read-write
			STATUS current
			DESCRIPTION
				" The request of a user command"
			::= { fkV2Mvr4GroupControl 1 }

		
--  1.3.6.1.4.1.10428 9 1.102.12.2.2.7.2.2.2
		-- 1.3.6.1.4.1.10428 9 1.102.12.2.2.7.2.2.2
		fkV2Mvr4GroupControlStatus OBJECT-TYPE
			SYNTAX FkControlStatusType
			MAX-ACCESS read-only
			STATUS current
			DESCRIPTION
				" The status of user command"
			::= { fkV2Mvr4GroupControl 2 }

		
--  1.3.6.1.4.1.10428 9 1.102.12.2.2.7.2.2.3
		-- 1.3.6.1.4.1.10428 9 1.102.12.2.2.7.2.2.3
		fkV2Mvr4GroupControlTimer OBJECT-TYPE
			SYNTAX Gauge32
			MAX-ACCESS read-write
			STATUS current
			DESCRIPTION
				" The maximum time for the manager for a long running user command"
			::= { fkV2Mvr4GroupControl 3 }

		
--  1.3.6.1.4.1.10428 9 1.102.12.2.2.7.2.2.4
		-- 1.3.6.1.4.1.10428 9 1.102.12.2.2.7.2.2.4
		fkV2Mvr4GroupControlTimeStamp OBJECT-TYPE
			SYNTAX TimeStamp
			MAX-ACCESS read-only
			STATUS current
			DESCRIPTION
				" The time stamp of the last command(end of command)"
			::= { fkV2Mvr4GroupControl 4 }

		
--  1.3.6.1.4.1.10428 9 1.102.12.2.2.7.2.2.5
		-- 1.3.6.1.4.1.10428 9 1.102.12.2.2.7.2.2.5
		fkV2Mvr4GroupControlReqResult OBJECT-TYPE
			SYNTAX FkControlRequestResultType
			MAX-ACCESS read-only
			STATUS current
			DESCRIPTION
				" The result of the last user command"
			::= { fkV2Mvr4GroupControl 5 }

		
--  1.3.6.1.4.1.10428 9 1.102.12.2.2.7.2.2.6
		-- 1.3.6.1.4.1.10428 9 1.102.12.2.2.7.2.2.6
		fkV2Mvr4GroupControlAddress OBJECT-TYPE
			SYNTAX IpAddress
			MAX-ACCESS read-write
			STATUS current
			DESCRIPTION
				"This object indicates group address for MVR."
			::= { fkV2Mvr4GroupControl 6 }

		
--  1.3.6.1.4.1.10428 9 1.102.12.2.2.7.2.2.7
		-- 1.3.6.1.4.1.10428 9 1.102.12.2.2.7.2.2.7
		fkV2Mvr4GroupControlVlanIndex OBJECT-TYPE
			SYNTAX INTEGER (1..4094)
			MAX-ACCESS read-write
			STATUS current
			DESCRIPTION
				"This object indicates the VLAN for MVR."
			::= { fkV2Mvr4GroupControl 7 }

		
--  MVR Group Notification
-- 1.3.6.1.4.1.10428 9 1.102.12.2.2.7.2.3
		-- 1.3.6.1.4.1.10428 9 1.102.12.2.2.7.2.3
		fkV2Mvr4GroupNotification OBJECT IDENTIFIER ::= { fkV2Mvr4Group 3 }

		
--  1.3.6.1.4.1.10428 9 1.102.12.2.2.7.2.3.1
		-- 1.3.6.1.4.1.10428 9 1.102.12.2.2.7.2.3.1
		fkV2Mvr4GroupCreated NOTIFICATION-TYPE
			OBJECTS { fkV2Mvr4GroupControlRequest, fkV2Mvr4GroupControlReqResult, fkV2Mvr4GroupControlTimeStamp, fkV2Mvr4GroupVlanIndex }
			STATUS current
			DESCRIPTION 
				"It indicates that the group has been created on the VLAN."
			::= { fkV2Mvr4GroupNotification 1 }

		
--  1.3.6.1.4.1.10428 9 1.102.12.2.2.7.2.3.2
		-- 1.3.6.1.4.1.10428 9 1.102.12.2.2.7.2.3.2
		fkV2Mvr4GroupDestroyed NOTIFICATION-TYPE
			OBJECTS { fkV2Mvr4GroupControlRequest, fkV2Mvr4GroupControlReqResult, fkV2Mvr4GroupControlTimeStamp, fkV2Mvr4GroupVlanIndex }
			STATUS current
			DESCRIPTION 
				"It indicates that the group has been destroyed from the VLAN."
			::= { fkV2Mvr4GroupNotification 2 }

		
--  IGMP Counter
-- 1.3.6.1.4.1.10428 9 1.102.12.2.2.8
		-- 1.3.6.1.4.1.10428 9 1.102.12.2.2.8
		fkV2IgmpCounterInfo OBJECT IDENTIFIER ::= { fkV2Igmp 8 }

		
		-- 1.3.6.1.4.1.10428 9 1.102.12.2.2.8.1
		fkV2IgmpCounterInfoGroupCount OBJECT-TYPE
			SYNTAX Counter32
			MAX-ACCESS read-only
			STATUS current
			DESCRIPTION
				"Count of IGMP Group entry."
			::= { fkV2IgmpCounterInfo 1 }

		
		-- 1.3.6.1.4.1.10428 9 1.102.12.2.2.8.2
		fkV2IgmpCounterInfoSnoopingCount OBJECT-TYPE
			SYNTAX Counter32
			MAX-ACCESS read-only
			STATUS current
			DESCRIPTION
				"Count of IGMP Snooping Group entry."
			::= { fkV2IgmpCounterInfo 2 }

		
--  Protocol Independent Multicast
-- 1.3.6.1.4.1.10428 9 1.102.12.2.3
		-- 1.3.6.1.4.1.10428 9 1.102.12.2.3
		fkV2Pim4 OBJECT IDENTIFIER ::= { fkV2Multicast4 3 }

		
--  PIM Configuration
-- 1.3.6.1.4.1.10428 9 1.102.12.2.3.1
		-- 1.3.6.1.4.1.10428 9 1.102.12.2.3.1
		fkV2Pim4Base OBJECT IDENTIFIER ::= { fkV2Pim4 1 }

		
--  PIM Configuration Group
-- 1.3.6.1.4.1.10428 9 1.102.12.2.3.1.1
		-- 1.3.6.1.4.1.10428 9 1.102.12.2.3.1.1
		fkV2Pim4Info OBJECT IDENTIFIER ::= { fkV2Pim4Base 1 }

		
--  1.3.6.1.4.1.10428 9 1.102.12.2.3.1.1.1
		-- 1.3.6.1.4.1.10428 9 1.102.12.2.3.1.1.1
		fkV2Pim4InfoSnoopActivity OBJECT-TYPE
			SYNTAX Boolean
			MAX-ACCESS read-only
			STATUS current
			DESCRIPTION
				"The active state of PIM snooping."
			::= { fkV2Pim4Info 1 }

		
--  PIM Configuration Control
-- 1.3.6.1.4.1.10428 9 1.102.12.2.3.1.2
		-- 1.3.6.1.4.1.10428 9 1.102.12.2.3.1.2
		fkV2Pim4InfoControl OBJECT IDENTIFIER ::= { fkV2Pim4Base 2 }

		
--  1.3.6.1.4.1.10428 9 1.102.12.2.3.1.2.1
		-- 1.3.6.1.4.1.10428 9 1.102.12.2.3.1.2.1
		fkV2Pim4InfoControlRequest OBJECT-TYPE
			SYNTAX INTEGER { setPimSnoopingActivity(1) }
			MAX-ACCESS read-write
			STATUS current
			DESCRIPTION
				" The request of a user command"
			::= { fkV2Pim4InfoControl 1 }

		
--  1.3.6.1.4.1.10428 9 1.102.12.2.3.1.2.2
		-- 1.3.6.1.4.1.10428 9 1.102.12.2.3.1.2.2
		fkV2Pim4InfoControlStatus OBJECT-TYPE
			SYNTAX FkControlStatusType
			MAX-ACCESS read-only
			STATUS current
			DESCRIPTION
				"The status of user command"
			::= { fkV2Pim4InfoControl 2 }

		
--  1.3.6.1.4.1.10428 9 1.102.12.2.3.1.2.3
		-- 1.3.6.1.4.1.10428 9 1.102.12.2.3.1.2.3
		fkV2Pim4InfoControlTimer OBJECT-TYPE
			SYNTAX Gauge32
			MAX-ACCESS read-write
			STATUS current
			DESCRIPTION
				" The maximum time for the manager for a long running user command"
			::= { fkV2Pim4InfoControl 3 }

		
--  1.3.6.1.4.1.10428 9 1.102.12.2.3.1.2.4
		-- 1.3.6.1.4.1.10428 9 1.102.12.2.3.1.2.4
		fkV2Pim4InfoControlTimeStamp OBJECT-TYPE
			SYNTAX TimeStamp
			MAX-ACCESS read-only
			STATUS current
			DESCRIPTION
				"The time stamp of the last command(end of command)"
			::= { fkV2Pim4InfoControl 4 }

		
--  1.3.6.1.4.1.10428 9 1.102.12.2.3.1.2.5
		-- 1.3.6.1.4.1.10428 9 1.102.12.2.3.1.2.5
		fkV2Pim4InfoControlReqResult OBJECT-TYPE
			SYNTAX FkControlRequestResultType
			MAX-ACCESS read-only
			STATUS current
			DESCRIPTION
				" The result of the last user command"
			::= { fkV2Pim4InfoControl 5 }

		
--  1.3.6.1.4.1.10428 9 1.102.12.2.3.1.2.6
		-- 1.3.6.1.4.1.10428 9 1.102.12.2.3.1.2.6
		fkV2Pim4InfoControlSnoopActivity OBJECT-TYPE
			SYNTAX Boolean
			MAX-ACCESS read-write
			STATUS current
			DESCRIPTION
				"The active state of PIM snooping."
			::= { fkV2Pim4InfoControl 6 }

		
--  PIM Configuration Notification
-- 1.3.6.1.4.1.10428 9 1.102.12.2.3.1.3
		-- 1.3.6.1.4.1.10428 9 1.102.12.2.3.1.3
		fkV2Pim4InfoNotification OBJECT IDENTIFIER ::= { fkV2Pim4Base 3 }

		
--  1.3.6.1.4.1.10428 9 1.102.12.2.3.1.3.1
		-- 1.3.6.1.4.1.10428 9 1.102.12.2.3.1.3.1
		fkV2Pim4InfoSnoopingActivityChanged NOTIFICATION-TYPE
			OBJECTS { fkV2Pim4InfoControlRequest, fkV2Pim4InfoControlReqResult, fkV2Pim4InfoControlTimeStamp, fkV2Pim4InfoSnoopActivity }
			STATUS current
			DESCRIPTION 
				"fkV2Pim4InfoSnoopingActivityChanged"
			::= { fkV2Pim4InfoNotification 1 }

		
--  PIM Agent (Daemon)
-- 1.3.6.1.4.1.10428 9 1.102.12.2.3.2
		-- 1.3.6.1.4.1.10428 9 1.102.12.2.3.2
		fkV2Pim4Agent OBJECT IDENTIFIER ::= { fkV2Pim4 2 }

		
--  PIM Snooping
-- 1.3.6.1.4.1.10428 9 1.102.12.2.3.3
		-- 1.3.6.1.4.1.10428 9 1.102.12.2.3.3
		fkV2Pim4Snooping OBJECT IDENTIFIER ::= { fkV2Pim4 3 }

		
--  PIM Snooping VLAN
-- 1.3.6.1.4.1.10428 9 1.102.12.2.3.3.1
		-- 1.3.6.1.4.1.10428 9 1.102.12.2.3.3.1
		fkV2Pim4Vlan OBJECT IDENTIFIER ::= { fkV2Pim4Snooping 1 }

		
--  PIM Snooping VLAN Table
-- 1.3.6.1.4.1.10428 9 1.102.12.2.3.3.1.1
		-- 1.3.6.1.4.1.10428 9 1.102.12.2.3.3.1.1
		fkV2Pim4VlanTable OBJECT-TYPE
			SYNTAX SEQUENCE OF FkV2Pim4VlanEntry
			MAX-ACCESS not-accessible
			STATUS current
			DESCRIPTION
				"PIM vlan table."
			::= { fkV2Pim4Vlan 1 }

		
--  PIM Snooping VLAN Entry
-- 1.3.6.1.4.1.10428 9 1.102.12.2.4.3.1.1.1
		-- 1.3.6.1.4.1.10428 9 1.102.12.2.3.3.1.1.1
		fkV2Pim4VlanEntry OBJECT-TYPE
			SYNTAX FkV2Pim4VlanEntry
			MAX-ACCESS not-accessible
			STATUS current
			DESCRIPTION
				"key: fkV2Pim4VlanIndex"
			INDEX { fkV2Pim4VlanIndex }
			::= { fkV2Pim4VlanTable 1 }

		
		FkV2Pim4VlanEntry ::=
			SEQUENCE { 
				fkV2Pim4VlanIndex
					INTEGER,
				fkV2Pim4VlanAdminActivity
					Boolean,
				fkV2Pim4VlanOperActivity
					Boolean
			 }

--  1.3.6.1.4.1.10428 9 1.102.12.2.4.3.1.1.1.1
		-- 1.3.6.1.4.1.10428 9 1.102.12.2.3.3.1.1.1.1
		fkV2Pim4VlanIndex OBJECT-TYPE
			SYNTAX INTEGER (1..4094)
			MAX-ACCESS read-only
			STATUS current
			DESCRIPTION
				"This object indicates the VLAN for PIM snooping."
			::= { fkV2Pim4VlanEntry 1 }

		
--  1.3.6.1.4.1.10428 9 1.102.12.2.4.3.1.1.1.2
		-- 1.3.6.1.4.1.10428 9 1.102.12.2.3.3.1.1.1.2
		fkV2Pim4VlanAdminActivity OBJECT-TYPE
			SYNTAX Boolean
			MAX-ACCESS read-only
			STATUS current
			DESCRIPTION
				"It indicates the activity status of  the corresponding VLAN's PIM snooping, this is set by administrator."
			::= { fkV2Pim4VlanEntry 2 }

		
--  1.3.6.1.4.1.10428 9 1.102.12.2.4.3.1.1.1.3
		-- 1.3.6.1.4.1.10428 9 1.102.12.2.3.3.1.1.1.3
		fkV2Pim4VlanOperActivity OBJECT-TYPE
			SYNTAX Boolean
			MAX-ACCESS read-only
			STATUS current
			DESCRIPTION
				"It indicates the operating status of  the corresponding VLAN's PIM snooping."
			::= { fkV2Pim4VlanEntry 3 }

		
--  PIM Snooping VLAN Control
-- 1.3.6.1.4.1.10428 9 1.102.12.2.3.3.1.2
		-- 1.3.6.1.4.1.10428 9 1.102.12.2.3.3.1.2
		fkV2Pim4VlanControl OBJECT IDENTIFIER ::= { fkV2Pim4Vlan 2 }

		
--  1.3.6.1.4.1.10428 9 1.102.12.2.3.3.1.2.1
		-- 1.3.6.1.4.1.10428 9 1.102.12.2.3.3.1.2.1
		fkV2Pim4VlanControlRequest OBJECT-TYPE
			SYNTAX INTEGER { setPimSnoopVlanActivity(1) }
			MAX-ACCESS read-write
			STATUS current
			DESCRIPTION
				" The request of a user command"
			::= { fkV2Pim4VlanControl 1 }

		
--  1.3.6.1.4.1.10428 9 1.102.12.2.3.3.1.2.2
		-- 1.3.6.1.4.1.10428 9 1.102.12.2.3.3.1.2.2
		fkV2Pim4VlanControlStatus OBJECT-TYPE
			SYNTAX FkControlStatusType
			MAX-ACCESS read-only
			STATUS current
			DESCRIPTION
				" The status of user command"
			::= { fkV2Pim4VlanControl 2 }

		
--  1.3.6.1.4.1.10428 9 1.102.12.2.3.3.1.2.3
		-- 1.3.6.1.4.1.10428 9 1.102.12.2.3.3.1.2.3
		fkV2Pim4VlanControlTimer OBJECT-TYPE
			SYNTAX Gauge32
			MAX-ACCESS read-write
			STATUS current
			DESCRIPTION
				" The maximum time for the manager for a long running user command"
			::= { fkV2Pim4VlanControl 3 }

		
--    
-- 1.3.6.1.4.1.10428 9 1.102.12.2.3.3.1.2.4
		-- 1.3.6.1.4.1.10428 9 1.102.12.2.3.3.1.2.4
		fkV2Pim4VlanControlTimeStamp OBJECT-TYPE
			SYNTAX TimeStamp
			MAX-ACCESS read-only
			STATUS current
			DESCRIPTION
				" The time stamp of the last command(end of command)"
			::= { fkV2Pim4VlanControl 4 }

		
--  1.3.6.1.4.1.10428 9 1.102.12.2.3.3.1.2.5
		-- 1.3.6.1.4.1.10428 9 1.102.12.2.3.3.1.2.5
		fkV2Pim4VlanControlReqResult OBJECT-TYPE
			SYNTAX FkControlRequestResultType
			MAX-ACCESS read-only
			STATUS current
			DESCRIPTION
				" The result of the last user command
				"
			::= { fkV2Pim4VlanControl 5 }

		
--  1.3.6.1.4.1.10428 9 1.102.12.2.3.3.1.2.6
		-- 1.3.6.1.4.1.10428 9 1.102.12.2.3.3.1.2.6
		fkV2Pim4VlanControlIndex OBJECT-TYPE
			SYNTAX INTEGER (-1 | 1..4094)
			MAX-ACCESS read-write
			STATUS current
			DESCRIPTION
				"This object indicates the VLAN for PIM snooping."
			::= { fkV2Pim4VlanControl 6 }

		
--  1.3.6.1.4.1.10428 9 1.102.12.2.3.3.1.2.7
		-- 1.3.6.1.4.1.10428 9 1.102.12.2.3.3.1.2.7
		fkV2Pim4VlanControlAdminActivity OBJECT-TYPE
			SYNTAX Boolean
			MAX-ACCESS read-write
			STATUS current
			DESCRIPTION
				"It indicates the activity status of  the corresponding VLAN's PIM snooping, this is set by administrator."
			::= { fkV2Pim4VlanControl 7 }

		
--  PIM Snooping VLAN Notification
-- 1.3.6.1.4.1.10428 9 1.102.12.2.3.3.1.3
		-- 1.3.6.1.4.1.10428 9 1.102.12.2.3.3.1.3
		fkV2Pim4VlanNotification OBJECT IDENTIFIER ::= { fkV2Pim4Vlan 3 }

		
--  1.3.6.1.4.1.10428 9 1.102.12.2.3.3.1.3.1
		-- 1.3.6.1.4.1.10428 9 1.102.12.2.3.3.1.3.1
		fkV2Pim4VlanActivityChanged NOTIFICATION-TYPE
			OBJECTS { fkV2Pim4VlanControlRequest, fkV2Pim4VlanControlReqResult, fkV2Pim4VlanControlTimeStamp, fkV2Pim4VlanAdminActivity }
			STATUS current
			DESCRIPTION 
				"setPIM4SnoopActivity"
			::= { fkV2Pim4VlanNotification 1 }

		
--  1.3.6.1.4.1.10428 9 1.102.12.2.4
		-- 1.3.6.1.4.1.10428 9 1.102.12.2.4
		fkV2IgmpProxy OBJECT IDENTIFIER ::= { fkV2Multicast4 4 }

		
--  1.3.6.1.4.1.10428 9 1.102.12.2.4.1
		-- 1.3.6.1.4.1.10428 9 1.102.12.2.4.1
		fkV2IgmpProxyBase OBJECT IDENTIFIER ::= { fkV2IgmpProxy 1 }

		
		-- 1.3.6.1.4.1.10428 9 1.102.12.2.4.1.1
		fkV2IgmpProxyInfo OBJECT IDENTIFIER ::= { fkV2IgmpProxyBase 1 }

		
		-- 1.3.6.1.4.1.10428 9 1.102.12.2.4.1.1.1
		fkV2IgmpProxyMultipath OBJECT-TYPE
			SYNTAX Boolean
			MAX-ACCESS read-only
			STATUS current
			DESCRIPTION
				"This is igmp proxy multipath activity."
			::= { fkV2IgmpProxyInfo 1 }

		
		-- 1.3.6.1.4.1.10428 9 1.102.12.2.4.1.2
		fkV2IgmpProxyInfoControl OBJECT IDENTIFIER ::= { fkV2IgmpProxyBase 2 }

		
		-- 1.3.6.1.4.1.10428 9 1.102.12.2.4.1.2.1
		fkV2IgmpProxyInfoControlRequest OBJECT-TYPE
			SYNTAX INTEGER { setIgmpProxyMultipath(1) }
			MAX-ACCESS read-write
			STATUS current
			DESCRIPTION
				"The request of a user command"
			::= { fkV2IgmpProxyInfoControl 1 }

		
		-- 1.3.6.1.4.1.10428 9 1.102.12.2.4.1.2.2
		fkV2IgmpProxyInfoControlStatus OBJECT-TYPE
			SYNTAX FkControlStatusType
			MAX-ACCESS read-write
			STATUS current
			DESCRIPTION
				"The status of user command"
			::= { fkV2IgmpProxyInfoControl 2 }

		
		-- 1.3.6.1.4.1.10428 9 1.102.12.2.4.1.2.3
		fkV2IgmpProxyInfoControlTimer OBJECT-TYPE
			SYNTAX Gauge32
			MAX-ACCESS read-write
			STATUS current
			DESCRIPTION
				"The maximum time for the manager for a long running user command"
			::= { fkV2IgmpProxyInfoControl 3 }

		
		-- 1.3.6.1.4.1.10428 9 1.102.12.2.4.1.2.4
		fkV2IgmpProxyInfoControlTimeStamp OBJECT-TYPE
			SYNTAX TimeTicks
			MAX-ACCESS read-write
			STATUS current
			DESCRIPTION
				"The time stamp of the last command(end of command)"
			::= { fkV2IgmpProxyInfoControl 4 }

		
		-- 1.3.6.1.4.1.10428 9 1.102.12.2.4.1.2.5
		fkV2IgmpProxyInfoControlReqResult OBJECT-TYPE
			SYNTAX FkControlRequestResultType
			MAX-ACCESS read-write
			STATUS current
			DESCRIPTION
				"The result of the last user command"
			::= { fkV2IgmpProxyInfoControl 5 }

		
		-- 1.3.6.1.4.1.10428 9 1.102.12.2.4.1.2.6
		fkV2IgmpProxyInfoControlMultipath OBJECT-TYPE
			SYNTAX Boolean
			MAX-ACCESS read-write
			STATUS current
			DESCRIPTION
				"This is igmp proxy multipath activity."
			::= { fkV2IgmpProxyInfoControl 6 }

		
		-- 1.3.6.1.4.1.10428 9 1.102.12.2.4.1.3
		fkV2IgmpProxyInfoNotification OBJECT IDENTIFIER ::= { fkV2IgmpProxyBase 3 }

		
		-- 1.3.6.1.4.1.10428 9 1.102.12.2.4.1.3.1
		fkV2IgmpProxyMultipathChanged NOTIFICATION-TYPE
			OBJECTS { fkV2IgmpProxyInfoControlRequest, fkV2IgmpProxyInfoControlTimeStamp, fkV2IgmpProxyInfoControlReqResult, fkV2IgmpProxyInfoControlMultipath }
			STATUS current
			DESCRIPTION 
				"Description."
			::= { fkV2IgmpProxyInfoNotification 1 }

		
--  1.3.6.1.4.1.10428 9 1.102.12.2.4.2
		-- 1.3.6.1.4.1.10428 9 1.102.12.2.4.2
		fkV2IgmpProxyAgent OBJECT IDENTIFIER ::= { fkV2IgmpProxy 2 }

		
--  1.3.6.1.4.1.10428 9 1.102.12.2.4.2.1
		-- 1.3.6.1.4.1.10428 9 1.102.12.2.4.2.1
		fkV2IgmpProxyInterface OBJECT IDENTIFIER ::= { fkV2IgmpProxyAgent 1 }

		
--  1.3.6.1.4.1.10428 9 1.102.12.2.4.2.1.1
		-- 1.3.6.1.4.1.10428 9 1.102.12.2.4.2.1.1
		fkV2IgmpProxyIfTable OBJECT-TYPE
			SYNTAX SEQUENCE OF FkV2IgmpProxyIfEntry
			MAX-ACCESS not-accessible
			STATUS current
			DESCRIPTION
				"IGMP proxy interface table."
			::= { fkV2IgmpProxyInterface 1 }

		
--  1.3.6.1.4.1.10428 9 1.102.12.2.4.2.1.1.1
		-- 1.3.6.1.4.1.10428 9 1.102.12.2.4.2.1.1.1
		fkV2IgmpProxyIfEntry OBJECT-TYPE
			SYNTAX FkV2IgmpProxyIfEntry
			MAX-ACCESS not-accessible
			STATUS current
			DESCRIPTION
				"key: fkV2IgmpProxyIfIndex, fkV2IgmpProxyIfMRouteIfIndex"
			INDEX { fkV2IgmpProxyIfIndex, fkV2IgmpProxyIfMRouteIfIndex }
			::= { fkV2IgmpProxyIfTable 1 }

		
		FkV2IgmpProxyIfEntry ::=
			SEQUENCE { 
				fkV2IgmpProxyIfIndex
					INTEGER,
				fkV2IgmpProxyIfMRouteIfIndex
					INTEGER,
				fkV2IgmpProxyIfMRouteQuerySIpMode
					INTEGER,
				fkV2IgmpProxyIfMRouteQuerySIpAddr
					IpAddress,
				fkV2IgmpProxyIfService
					Boolean,
				fkV2IgmpProxyIfServiceSIpMode
					INTEGER,
				fkV2IgmpProxyIfServiceSIpAddr
					IpAddress,
				fkV2IgmpProxyIfServicePriority
					Integer32
			 }

--  1.3.6.1.4.1.10428 9 1.102.12.2.4.2.1.1.1.1
		-- 1.3.6.1.4.1.10428 9 1.102.12.2.4.2.1.1.1.1
		fkV2IgmpProxyIfIndex OBJECT-TYPE
			SYNTAX INTEGER (1..4096)
			MAX-ACCESS read-only
			STATUS current
			DESCRIPTION
				"Network interface index."
			::= { fkV2IgmpProxyIfEntry 1 }

		
--  1.3.6.1.4.1.10428 9 1.102.12.2.4.2.1.1.1.2
		-- 1.3.6.1.4.1.10428 9 1.102.12.2.4.2.1.1.1.2
		fkV2IgmpProxyIfMRouteIfIndex OBJECT-TYPE
			SYNTAX INTEGER (0 | 1..4096)
			MAX-ACCESS read-only
			STATUS current
			DESCRIPTION
				"This value is the igmp-proxy hostside ifindex to multicast routing"
			::= { fkV2IgmpProxyIfEntry 2 }

		
--  1.3.6.1.4.1.10428 9 1.102.12.2.4.2.1.1.1.3
		-- 1.3.6.1.4.1.10428 9 1.102.12.2.4.2.1.1.1.3
		fkV2IgmpProxyIfMRouteQuerySIpMode OBJECT-TYPE
			SYNTAX INTEGER
				{
				unUsed(0),
				interfaceIpAddress(1),
				proxyService(2)
				}
			MAX-ACCESS read-only
			STATUS current
			DESCRIPTION
				"This value is the querier source IP address Mode"
			::= { fkV2IgmpProxyIfEntry 3 }

		
--  1.3.6.1.4.1.10428 9 1.102.12.2.4.2.1.1.1.4
		-- 1.3.6.1.4.1.10428 9 1.102.12.2.4.2.1.1.1.4
		fkV2IgmpProxyIfMRouteQuerySIpAddr OBJECT-TYPE
			SYNTAX IpAddress
			MAX-ACCESS read-only
			STATUS current
			DESCRIPTION
				"This value is the igmp-proxy querier source IP address"
			::= { fkV2IgmpProxyIfEntry 4 }

		
--  1.3.6.1.4.1.10428 9 1.102.12.2.4.2.1.1.1.5
		-- 1.3.6.1.4.1.10428 9 1.102.12.2.4.2.1.1.1.5
		fkV2IgmpProxyIfService OBJECT-TYPE
			SYNTAX Boolean
			MAX-ACCESS read-only
			STATUS current
			DESCRIPTION
				"he true is Igmp Proxy service Enabled on this interface, the false is not."
			::= { fkV2IgmpProxyIfEntry 5 }

		
--  1.3.6.1.4.1.10428 9 1.102.12.2.4.2.1.1.1.6
		-- 1.3.6.1.4.1.10428 9 1.102.12.2.4.2.1.1.1.6
		fkV2IgmpProxyIfServiceSIpMode OBJECT-TYPE
			SYNTAX INTEGER
				{
				unUsed(0),
				interfaceIpAddress(1),
				manual(2),
				firstReporter(3),
				lastReporter(4)
				}
			MAX-ACCESS read-only
			STATUS current
			DESCRIPTION
				"This value is the source Ip address Mode of mroute proxy service"
			::= { fkV2IgmpProxyIfEntry 6 }

		
--  1.3.6.1.4.1.10428 9 1.102.12.2.4.2.1.1.1.7
		-- 1.3.6.1.4.1.10428 9 1.102.12.2.4.2.1.1.1.7
		fkV2IgmpProxyIfServiceSIpAddr OBJECT-TYPE
			SYNTAX IpAddress
			MAX-ACCESS read-only
			STATUS current
			DESCRIPTION
				"This value is the source Ip address by user manually"
			::= { fkV2IgmpProxyIfEntry 7 }

		
		-- 1.3.6.1.4.1.10428 9 1.102.12.2.4.2.1.1.1.8
		fkV2IgmpProxyIfServicePriority OBJECT-TYPE
			SYNTAX Integer32 (0..255)
			MAX-ACCESS read-only
			STATUS current
			DESCRIPTION
				"The IGMP proxy service priority"
			::= { fkV2IgmpProxyIfEntry 8 }

		
--  1.3.6.1.4.1.10428 9 1.102.12.2.4.2.1.2
		-- 1.3.6.1.4.1.10428 9 1.102.12.2.4.2.1.2
		fkV2IgmpProxyIfControl OBJECT IDENTIFIER ::= { fkV2IgmpProxyInterface 2 }

		
--  1.3.6.1.4.1.10428 9 1.102.12.2.4.2.1.2.1
		-- 1.3.6.1.4.1.10428 9 1.102.12.2.4.2.1.2.1
		fkV2IgmpProxyIfControlRequest OBJECT-TYPE
			SYNTAX INTEGER
				{
				setIgmpProxyIfMroute(1),
				setIgmpProxyIfMrouteSrcIp(2),
				setIgmpProxyIfService(3),
				setIgmpProxyIfServiceSrcIp(4),
				destroyIgmpProxyIfMroute(5)
				}
			MAX-ACCESS read-write
			STATUS current
			DESCRIPTION
				"The request of a user command"
			::= { fkV2IgmpProxyIfControl 1 }

		
--  1.3.6.1.4.1.10428 9 1.102.12.2.4.2.1.2.2
		-- 1.3.6.1.4.1.10428 9 1.102.12.2.4.2.1.2.2
		fkV2IgmpProxyIfControlStatus OBJECT-TYPE
			SYNTAX FkControlStatusType
			MAX-ACCESS read-only
			STATUS current
			DESCRIPTION
				"The status of user command"
			::= { fkV2IgmpProxyIfControl 2 }

		
--  1.3.6.1.4.1.10428 9 1.102.12.2.4.2.1.2.3
		-- 1.3.6.1.4.1.10428 9 1.102.12.2.4.2.1.2.3
		fkV2IgmpProxyIfControlTimer OBJECT-TYPE
			SYNTAX Gauge32
			MAX-ACCESS read-write
			STATUS current
			DESCRIPTION
				"The maximum time for the manager for a long running user command"
			::= { fkV2IgmpProxyIfControl 3 }

		
--  1.3.6.1.4.1.10428 9 1.102.12.2.4.2.1.2.4
		-- 1.3.6.1.4.1.10428 9 1.102.12.2.4.2.1.2.4
		fkV2IgmpProxyIfControlTimeStamp OBJECT-TYPE
			SYNTAX TimeStamp
			MAX-ACCESS read-only
			STATUS current
			DESCRIPTION
				"The time stamp of the last command(end of command)"
			::= { fkV2IgmpProxyIfControl 4 }

		
--  1.3.6.1.4.1.10428 9 1.102.12.2.4.2.1.2.5
		-- 1.3.6.1.4.1.10428 9 1.102.12.2.4.2.1.2.5
		fkV2IgmpProxyIfControlReqResult OBJECT-TYPE
			SYNTAX FkControlRequestResultType
			MAX-ACCESS read-only
			STATUS current
			DESCRIPTION
				"The result of the last user command"
			::= { fkV2IgmpProxyIfControl 5 }

		
--  1.3.6.1.4.1.10428 9 1.102.12.2.4.2.1.2.6
		-- 1.3.6.1.4.1.10428 9 1.102.12.2.4.2.1.2.6
		fkV2IgmpProxyIfControlIndex OBJECT-TYPE
			SYNTAX INTEGER (1..4096)
			MAX-ACCESS read-write
			STATUS current
			DESCRIPTION
				"Network interface index."
			::= { fkV2IgmpProxyIfControl 6 }

		
--  1.3.6.1.4.1.10428 9 1.102.12.2.4.2.1.2.7
		-- 1.3.6.1.4.1.10428 9 1.102.12.2.4.2.1.2.7
		fkV2IgmpProxyIfControlMrouteIfIndex OBJECT-TYPE
			SYNTAX INTEGER (-1 | 1..4096)
			MAX-ACCESS read-write
			STATUS current
			DESCRIPTION
				"This value is the igmp-proxy hostside ifindex to multicast routing"
			::= { fkV2IgmpProxyIfControl 7 }

		
--  1.3.6.1.4.1.10428 9 1.102.12.2.4.2.1.2.8
		-- 1.3.6.1.4.1.10428 9 1.102.12.2.4.2.1.2.8
		fkV2IgmpProxyIfControlMrouteQuerySIpMode OBJECT-TYPE
			SYNTAX INTEGER
				{
				interfaceIpAddress(1),
				proxyService(2)
				}
			MAX-ACCESS read-write
			STATUS current
			DESCRIPTION
				"This value is the querier source IP address Mode"
			::= { fkV2IgmpProxyIfControl 8 }

		
--  1.3.6.1.4.1.10428 9 1.102.12.2.4.2.1.2.9
		-- 1.3.6.1.4.1.10428 9 1.102.12.2.4.2.1.2.9
		fkV2IgmpProxyIfControlService OBJECT-TYPE
			SYNTAX Boolean
			MAX-ACCESS read-write
			STATUS current
			DESCRIPTION
				"The true is Igmp Proxy service Enabled on this interface, the false is not."
			::= { fkV2IgmpProxyIfControl 9 }

		
--  1.3.6.1.4.1.10428 9 1.102.12.2.4.2.1.2.10
		-- 1.3.6.1.4.1.10428 9 1.102.12.2.4.2.1.2.10
		fkV2IgmpProxyIfControlServiceSIpMode OBJECT-TYPE
			SYNTAX INTEGER
				{
				interfaceIpAddress(1),
				manual(2),
				firstReporter(3),
				lastReporter(4)
				}
			MAX-ACCESS read-write
			STATUS current
			DESCRIPTION
				"This value is the source Ip address Mode of mroute proxy service"
			::= { fkV2IgmpProxyIfControl 10 }

		
--  1.3.6.1.4.1.10428 9 1.102.12.2.4.2.1.2.11
		-- 1.3.6.1.4.1.10428 9 1.102.12.2.4.2.1.2.11
		fkV2IgmpProxyIfControlServiceSIpAddr OBJECT-TYPE
			SYNTAX IpAddress
			MAX-ACCESS read-write
			STATUS current
			DESCRIPTION
				"This value is the source Ip address by user manually"
			::= { fkV2IgmpProxyIfControl 11 }

		
--  1.3.6.1.4.1.10428 9 1.102.12.2.4.2.1.3
		-- 1.3.6.1.4.1.10428 9 1.102.12.2.4.2.1.3
		fkV2IgmpProxyIfNotification OBJECT IDENTIFIER ::= { fkV2IgmpProxyInterface 3 }

		
--  1.3.6.1.4.1.10428 9 1.102.12.2.4.2.1.3.1
		-- 1.3.6.1.4.1.10428 9 1.102.12.2.4.2.1.3.1
		fkV2IgmpProxyInterfaceMrouteChanged NOTIFICATION-TYPE
			OBJECTS { fkV2IgmpProxyIfControlRequest, fkV2IgmpProxyIfControlTimeStamp, fkV2IgmpProxyIfControlReqResult, fkV2IgmpProxyIfControlIndex, fkV2IgmpProxyIfControlMrouteIfIndex
				 }
			STATUS current
			DESCRIPTION 
				"Description."
			::= { fkV2IgmpProxyIfNotification 1 }

		
--  1.3.6.1.4.1.10428 9 1.102.12.2.4.2.1.3.2
		-- 1.3.6.1.4.1.10428 9 1.102.12.2.4.2.1.3.2
		fkV2IgmpProxyInterfaceMrouteSourceIpChanged NOTIFICATION-TYPE
			OBJECTS { fkV2IgmpProxyIfControlRequest, fkV2IgmpProxyIfControlTimeStamp, fkV2IgmpProxyIfControlReqResult, fkV2IgmpProxyIfControlIndex, fkV2IgmpProxyIfControlMrouteQuerySIpMode
				 }
			STATUS current
			DESCRIPTION 
				"Description."
			::= { fkV2IgmpProxyIfNotification 2 }

		
--  1.3.6.1.4.1.10428 9 1.102.12.2.4.2.1.3.3
		-- 1.3.6.1.4.1.10428 9 1.102.12.2.4.2.1.3.3
		fkV2IgmpProxyInterfaceServiceChanged NOTIFICATION-TYPE
			OBJECTS { fkV2IgmpProxyIfControlRequest, fkV2IgmpProxyIfControlTimeStamp, fkV2IgmpProxyIfControlReqResult, fkV2IgmpProxyIfControlIndex, fkV2IgmpProxyIfControlService
				 }
			STATUS current
			DESCRIPTION 
				"Description."
			::= { fkV2IgmpProxyIfNotification 3 }

		
--  1.3.6.1.4.1.10428 9 1.102.12.2.4.2.1.3.4
		-- 1.3.6.1.4.1.10428 9 1.102.12.2.4.2.1.3.4
		fkV2IgmpProxyInterfaceServiceSourceIpChanged NOTIFICATION-TYPE
			OBJECTS { fkV2IgmpProxyIfControlRequest, fkV2IgmpProxyIfControlTimeStamp, fkV2IgmpProxyIfControlReqResult, fkV2IgmpProxyIfControlIndex, fkV2IgmpProxyIfControlServiceSIpMode, 
				fkV2IgmpProxyIfControlServiceSIpAddr }
			STATUS current
			DESCRIPTION 
				"Description."
			::= { fkV2IgmpProxyIfNotification 4 }

		
--  1.3.6.1.4.1.10428 9 1.102.12.2.4.2.1.3.1
		-- 1.3.6.1.4.1.10428 9 1.102.12.2.4.2.1.3.5
		fkV2IgmpProxyInterfaceMrouteDeleted NOTIFICATION-TYPE
			OBJECTS { fkV2IgmpProxyIfControlRequest, fkV2IgmpProxyIfControlTimeStamp, fkV2IgmpProxyIfControlReqResult, fkV2IgmpProxyIfControlIndex, fkV2IgmpProxyIfControlMrouteIfIndex
				 }
			STATUS current
			DESCRIPTION 
				"Description."
			::= { fkV2IgmpProxyIfNotification 5 }

		
--  1.3.6.1.4.1.10428 9 1.102.12.3
		-- 1.3.6.1.4.1.10428 9 1.102.12.3
		fkV2Multicast6 OBJECT IDENTIFIER ::= { fkV2Multicast 3 }

		
		-- 1.3.6.1.4.1.10428 9 1.102.12.4
		fkV2McastIPTvMgmt OBJECT IDENTIFIER ::= { fkV2Multicast 4 }

		
		-- 1.3.6.1.4.1.10428 9 1.102.12.4.1
		fkV2McastIPTvBase OBJECT IDENTIFIER ::= { fkV2McastIPTvMgmt 1 }

		
		-- 1.3.6.1.4.1.10428 9 1.102.12.4.1.1
		fkV2McastIPTvInfo OBJECT IDENTIFIER ::= { fkV2McastIPTvBase 1 }

		
		-- 1.3.6.1.4.1.10428 9 1.102.12.4.1.1.1
		fkV2McastIPTvInfoCacState OBJECT-TYPE
			SYNTAX INTEGER
				{
				enable(1),
				disable(2)
				}
			MAX-ACCESS read-only
			STATUS current
			DESCRIPTION
				"The system-wide cac state. default: disable(2)"
			DEFVAL { 2 }
			::= { fkV2McastIPTvInfo 1 }

		
		-- 1.3.6.1.4.1.10428 9 1.102.12.4.1.1.2
		fkV2McastIPTvInfoPackageLimit OBJECT-TYPE
			SYNTAX INTEGER (0..65535)
			MAX-ACCESS read-only
			STATUS current
			DESCRIPTION
				"The system-wide package limitation"
			::= { fkV2McastIPTvInfo 2 }

		
		-- 1.3.6.1.4.1.10428 9 1.102.12.4.1.1.3
		fkV2McastIPTvInfoPreviewProfileLimit OBJECT-TYPE
			SYNTAX INTEGER (0..65535)
			MAX-ACCESS read-only
			STATUS current
			DESCRIPTION
				"The system-wide preview-profile limitation"
			::= { fkV2McastIPTvInfo 3 }

		
		-- 1.3.6.1.4.1.10428 9 1.102.12.4.1.1.4
		fkV2McastIPTvInfoChannelLimit OBJECT-TYPE
			SYNTAX INTEGER (0..65535)
			MAX-ACCESS read-only
			STATUS current
			DESCRIPTION
				"The system-wide channel limitation"
			::= { fkV2McastIPTvInfo 4 }

		
		-- 1.3.6.1.4.1.10428 9 1.102.12.4.1.1.5
		fkV2McastIPTvInfoCacProfileLimit OBJECT-TYPE
			SYNTAX INTEGER (0..65535)
			MAX-ACCESS read-only
			STATUS current
			DESCRIPTION
				"The system-wide cac-profile limitation"
			::= { fkV2McastIPTvInfo 5 }

		
		-- 1.3.6.1.4.1.10428 9 1.102.12.4.1.1.6
		fkV2McastIPTvInfoSubscriberLimit OBJECT-TYPE
			SYNTAX INTEGER (0..65535)
			MAX-ACCESS read-only
			STATUS current
			DESCRIPTION
				"The system-wide subscribers limitation"
			::= { fkV2McastIPTvInfo 6 }

		
		-- 1.3.6.1.4.1.10428 9 1.102.12.4.1.1.7
		fkV2McastIPTvInfoSubscriberHistoryLimit OBJECT-TYPE
			SYNTAX INTEGER (0..65535)
			MAX-ACCESS read-only
			STATUS current
			DESCRIPTION
				"The system-wide subscriber's history limitation"
			::= { fkV2McastIPTvInfo 7 }

		
		-- 1.3.6.1.4.1.10428 9 1.102.12.4.1.1.8
		fkV2McastIPTvInfoFullviewRecogTime OBJECT-TYPE
			SYNTAX INTEGER (0..65535)
			MAX-ACCESS read-only
			STATUS current
			DESCRIPTION
				"The system-wide full-view recognition time"
			::= { fkV2McastIPTvInfo 8 }

		
		-- 1.3.6.1.4.1.10428 9 1.102.12.4.1.2
		fkV2McastIPTvControlInfo OBJECT IDENTIFIER ::= { fkV2McastIPTvBase 2 }

		
		-- 1.3.6.1.4.1.10428 9 1.102.12.4.1.2.1
		fkV2McastIPTvInfoControlRequest OBJECT-TYPE
			SYNTAX INTEGER
				{
				setIPTvCACState(1),
				setIPTvGlobalLimit(2),
				setIPTvFullviewRecognitionTime(3)
				}
			MAX-ACCESS read-write
			STATUS current
			DESCRIPTION
				"The request of a user command"
			::= { fkV2McastIPTvControlInfo 1 }

		
		-- 1.3.6.1.4.1.10428 9 1.102.12.4.1.2.2
		fkV2McastIPTvInfoControlStatus OBJECT-TYPE
			SYNTAX FkControlStatusType
			MAX-ACCESS read-only
			STATUS current
			DESCRIPTION
				"The status of user command"
			::= { fkV2McastIPTvControlInfo 2 }

		
		-- 1.3.6.1.4.1.10428 9 1.102.12.4.1.2.3
		fkV2McastIPTvInfoControlTimer OBJECT-TYPE
			SYNTAX Gauge32
			MAX-ACCESS read-write
			STATUS current
			DESCRIPTION
				"The maximum time for the manager for a long running user command"
			::= { fkV2McastIPTvControlInfo 3 }

		
		-- 1.3.6.1.4.1.10428 9 1.102.12.4.1.2.4
		fkV2McastIPTvInfoControlTimeStamp OBJECT-TYPE
			SYNTAX TimeStamp
			MAX-ACCESS read-only
			STATUS current
			DESCRIPTION
				"The time stamp of the last command(end of command)"
			::= { fkV2McastIPTvControlInfo 4 }

		
		-- 1.3.6.1.4.1.10428 9 1.102.12.4.1.2.5
		fkV2McastIPTvInfoControlReqResult OBJECT-TYPE
			SYNTAX FkControlRequestResultType
			MAX-ACCESS read-only
			STATUS current
			DESCRIPTION
				"The result of the last user command"
			::= { fkV2McastIPTvControlInfo 5 }

		
		-- 1.3.6.1.4.1.10428 9 1.102.12.4.1.2.6
		fkV2McastIPTvInfoControlCacState OBJECT-TYPE
			SYNTAX INTEGER
				{
				enable(1),
				disable(2)
				}
			MAX-ACCESS read-write
			STATUS current
			DESCRIPTION
				"The system-wide cac state"
			::= { fkV2McastIPTvControlInfo 6 }

		
		-- 1.3.6.1.4.1.10428 9 1.102.12.4.1.2.7
		fkV2McastIPTvInfoControlPackageLimit OBJECT-TYPE
			SYNTAX INTEGER (0..65535)
			MAX-ACCESS read-write
			STATUS current
			DESCRIPTION
				"The system-wide package limitation"
			::= { fkV2McastIPTvControlInfo 7 }

		
		-- 1.3.6.1.4.1.10428 9 1.102.12.4.1.2.8
		fkV2McastIPTvInfoControlPreviewProfileLimit OBJECT-TYPE
			SYNTAX INTEGER (0..65535)
			MAX-ACCESS read-write
			STATUS current
			DESCRIPTION
				"The system-wide preview-profile limitation"
			::= { fkV2McastIPTvControlInfo 8 }

		
		-- 1.3.6.1.4.1.10428 9 1.102.12.4.1.2.9
		fkV2McastIPTvInfoControlChannelLimit OBJECT-TYPE
			SYNTAX INTEGER (0..65535)
			MAX-ACCESS read-write
			STATUS current
			DESCRIPTION
				"The system-wide channel limitation"
			::= { fkV2McastIPTvControlInfo 9 }

		
		-- 1.3.6.1.4.1.10428 9 1.102.12.4.1.2.10
		fkV2McastIPTvInfoControlCacProfileLimit OBJECT-TYPE
			SYNTAX INTEGER (0..65535)
			MAX-ACCESS read-write
			STATUS current
			DESCRIPTION
				"The system-wide cac-profile limitation"
			::= { fkV2McastIPTvControlInfo 10 }

		
		-- 1.3.6.1.4.1.10428 9 1.102.12.4.1.2.11
		fkV2McastIPTvInfoControlSubscriberLimit OBJECT-TYPE
			SYNTAX INTEGER (0..65535)
			MAX-ACCESS read-write
			STATUS current
			DESCRIPTION
				"The system-wide subscribers limitation"
			::= { fkV2McastIPTvControlInfo 11 }

		
		-- 1.3.6.1.4.1.10428 9 1.102.12.4.1.2.12
		fkV2McastIPTvInfoContorlSubscriberHistoryLimit OBJECT-TYPE
			SYNTAX INTEGER (0..65535)
			MAX-ACCESS read-write
			STATUS current
			DESCRIPTION
				"The system-wide subscriber's history limitation"
			::= { fkV2McastIPTvControlInfo 12 }

		
		-- 1.3.6.1.4.1.10428 9 1.102.12.4.1.2.13
		fkV2McastIPTvInfoControlFullviewRecogTime OBJECT-TYPE
			SYNTAX INTEGER (0..65535)
			MAX-ACCESS read-write
			STATUS current
			DESCRIPTION
				"The system-wide full-view recognition time"
			::= { fkV2McastIPTvControlInfo 13 }

		
		-- 1.3.6.1.4.1.10428 9 1.102.12.4.1.3
		fkV2McastIPTvInfoNotification OBJECT IDENTIFIER ::= { fkV2McastIPTvBase 3 }

		
		-- 1.3.6.1.4.1.10428 9 1.102.12.4.1.3.1
		fkV2McastIPTvInfoCacStateChanged NOTIFICATION-TYPE
			OBJECTS { fkV2McastIPTvInfoControlRequest, fkV2McastIPTvInfoControlTimeStamp, fkV2McastIPTvInfoControlReqResult, fkV2McastIPTvInfoControlCacState }
			STATUS current
			DESCRIPTION 
				"Description."
			::= { fkV2McastIPTvInfoNotification 1 }

		
		-- 1.3.6.1.4.1.10428 9 1.102.12.4.1.3.2
		fkV2McastIPTvInfoLimitChanged NOTIFICATION-TYPE
			OBJECTS { fkV2McastIPTvInfoControlRequest, fkV2McastIPTvInfoControlTimeStamp, fkV2McastIPTvInfoControlReqResult, fkV2McastIPTvInfoControlPackageLimit, fkV2McastIPTvInfoControlPreviewProfileLimit, 
				fkV2McastIPTvInfoControlChannelLimit, fkV2McastIPTvInfoControlCacProfileLimit, fkV2McastIPTvInfoControlSubscriberLimit, fkV2McastIPTvInfoContorlSubscriberHistoryLimit }
			STATUS current
			DESCRIPTION 
				"Description."
			::= { fkV2McastIPTvInfoNotification 2 }

		
		-- 1.3.6.1.4.1.10428 9 1.102.12.4.1.3.3
		fkV2McastIPTvInfoFullviewRecogTimeChanged NOTIFICATION-TYPE
			OBJECTS { fkV2McastIPTvInfoControlRequest, fkV2McastIPTvInfoControlTimeStamp, fkV2McastIPTvInfoControlReqResult, fkV2McastIPTvInfoControlFullviewRecogTime }
			STATUS current
			DESCRIPTION 
				"Description."
			::= { fkV2McastIPTvInfoNotification 3 }

		
		-- 1.3.6.1.4.1.10428 9 1.102.12.4.2
		fkV2McastIPTvPackage OBJECT IDENTIFIER ::= { fkV2McastIPTvMgmt 2 }

		
		-- 1.3.6.1.4.1.10428 9 1.102.12.4.2.1
		fkV2McastPackageTable OBJECT-TYPE
			SYNTAX SEQUENCE OF FkV2McastPackageEntry
			MAX-ACCESS not-accessible
			STATUS current
			DESCRIPTION
				"multicast package table."
			::= { fkV2McastIPTvPackage 1 }

		
		-- 1.3.6.1.4.1.10428 9 1.102.12.4.2.1.1
		fkV2McastPackageEntry OBJECT-TYPE
			SYNTAX FkV2McastPackageEntry
			MAX-ACCESS not-accessible
			STATUS current
			DESCRIPTION
				"key: fkV2McastIPTvPackageId"
			INDEX { fkV2McastIPTvPackageId }
			::= { fkV2McastPackageTable 1 }

		
		FkV2McastPackageEntry ::=
			SEQUENCE { 
				fkV2McastIPTvPackageId
					Integer32,
				fkV2McastIPTvPackageDescription
					OCTET STRING,
				fkV2McastIPTvPackagePreviewChannelCnt
					INTEGER,
				fkV2McastIPTvPackageFullviewChannelCnt
					INTEGER
			 }

		-- 1.3.6.1.4.1.10428 9 1.102.12.4.2.1.1.1
		fkV2McastIPTvPackageId OBJECT-TYPE
			SYNTAX Integer32 (1..65535)
			MAX-ACCESS read-only
			STATUS current
			DESCRIPTION
				"Package id"
			::= { fkV2McastPackageEntry 1 }

		
		-- 1.3.6.1.4.1.10428 9 1.102.12.4.2.1.1.2
		fkV2McastIPTvPackageDescription OBJECT-TYPE
			SYNTAX OCTET STRING
			MAX-ACCESS read-only
			STATUS current
			DESCRIPTION
				"Package description"
			::= { fkV2McastPackageEntry 2 }

		
		-- 1.3.6.1.4.1.10428 9 1.102.12.4.2.1.1.3
		fkV2McastIPTvPackagePreviewChannelCnt OBJECT-TYPE
			SYNTAX INTEGER (0..65535)
			MAX-ACCESS read-only
			STATUS current
			DESCRIPTION
				"The number of preview channel list"
			::= { fkV2McastPackageEntry 3 }

		
		-- 1.3.6.1.4.1.10428 9 1.102.12.4.2.1.1.4
		fkV2McastIPTvPackageFullviewChannelCnt OBJECT-TYPE
			SYNTAX INTEGER (0..65535)
			MAX-ACCESS read-only
			STATUS current
			DESCRIPTION
				"The number of fullview channel list"
			::= { fkV2McastPackageEntry 4 }

		
		-- 1.3.6.1.4.1.10428 9 1.102.12.4.2.2
		fkV2McastIPTvPackageChannelTable OBJECT-TYPE
			SYNTAX SEQUENCE OF FkV2McastIPTvPackageChannelEntry
			MAX-ACCESS not-accessible
			STATUS current
			DESCRIPTION
				"multicast IPTV package channel table."
			::= { fkV2McastIPTvPackage 2 }

		
		-- 1.3.6.1.4.1.10428 9 1.102.12.4.2.2.1
		fkV2McastIPTvPackageChannelEntry OBJECT-TYPE
			SYNTAX FkV2McastIPTvPackageChannelEntry
			MAX-ACCESS not-accessible
			STATUS current
			DESCRIPTION
				"key: fkV2McastIPTvPackageId, fkV2McastIPTvPackageChannelId"
			INDEX { fkV2McastIPTvPackageId, fkV2McastIPTvPackageChannelId }
			::= { fkV2McastIPTvPackageChannelTable 1 }

		
		FkV2McastIPTvPackageChannelEntry ::=
			SEQUENCE { 
				fkV2McastIPTvPackageChannelId
					Integer32,
				fkV2McastIPTvPackageChannelEntitlement
					INTEGER
			 }

		-- 1.3.6.1.4.1.10428 9 1.102.12.4.2.2.1.1
		fkV2McastIPTvPackageChannelId OBJECT-TYPE
			SYNTAX Integer32 (1..65535)
			MAX-ACCESS read-only
			STATUS current
			DESCRIPTION
				"Channel id"
			::= { fkV2McastIPTvPackageChannelEntry 1 }

		
		-- 1.3.6.1.4.1.10428 9 1.102.12.4.2.2.1.2
		fkV2McastIPTvPackageChannelEntitlement OBJECT-TYPE
			SYNTAX INTEGER
				{
				preview(1),
				fullview(2)
				}
			MAX-ACCESS read-only
			STATUS current
			DESCRIPTION
				"The Entitlement of channel view"
			::= { fkV2McastIPTvPackageChannelEntry 2 }

		
		-- 1.3.6.1.4.1.10428 9 1.102.12.4.2.3
		fkV2McastIPTvPackageControl OBJECT IDENTIFIER ::= { fkV2McastIPTvPackage 3 }

		
		-- 1.3.6.1.4.1.10428 9 1.102.12.4.2.3.1
		fkV2McastIPTvPackageControlRequest OBJECT-TYPE
			SYNTAX INTEGER
				{
				createPackage(1),
				updatePackage(2),
				deletePackage(3),
				addPackageChannel(4),
				removePackageChannel(5)
				}
			MAX-ACCESS read-write
			STATUS current
			DESCRIPTION
				"The request of a user command"
			::= { fkV2McastIPTvPackageControl 1 }

		
		-- 1.3.6.1.4.1.10428 9 1.102.12.4.2.3.2
		fkV2McastIPTvPackageControlStatus OBJECT-TYPE
			SYNTAX FkControlStatusType
			MAX-ACCESS read-only
			STATUS current
			DESCRIPTION
				"The status of user command"
			::= { fkV2McastIPTvPackageControl 2 }

		
		-- 1.3.6.1.4.1.10428 9 1.102.12.4.2.3.3
		fkV2McastIPTvPackageControlTimer OBJECT-TYPE
			SYNTAX Gauge32
			MAX-ACCESS read-write
			STATUS current
			DESCRIPTION
				"The maximum time for the manager for a long running user command"
			::= { fkV2McastIPTvPackageControl 3 }

		
		-- 1.3.6.1.4.1.10428 9 1.102.12.4.2.3.4
		fkV2McastIPTvPackageControlTimeStamp OBJECT-TYPE
			SYNTAX TimeStamp
			MAX-ACCESS read-only
			STATUS current
			DESCRIPTION
				"The time stamp of the last command(end of command)"
			::= { fkV2McastIPTvPackageControl 4 }

		
		-- 1.3.6.1.4.1.10428 9 1.102.12.4.2.3.5
		fkV2McastIPTvPackageControlReqResult OBJECT-TYPE
			SYNTAX FkControlRequestResultType
			MAX-ACCESS read-only
			STATUS current
			DESCRIPTION
				"The result of the last user command"
			::= { fkV2McastIPTvPackageControl 5 }

		
		-- 1.3.6.1.4.1.10428 9 1.102.12.4.2.3.6
		fkV2McastIPTvPackageControlId OBJECT-TYPE
			SYNTAX INTEGER (0..65535)
			MAX-ACCESS read-write
			STATUS current
			DESCRIPTION
				"Package id"
			::= { fkV2McastIPTvPackageControl 6 }

		
		-- 1.3.6.1.4.1.10428 9 1.102.12.4.2.3.7
		fkV2McastIPTvPackageControlDescription OBJECT-TYPE
			SYNTAX OCTET STRING
			MAX-ACCESS read-write
			STATUS current
			DESCRIPTION
				"Package description"
			::= { fkV2McastIPTvPackageControl 7 }

		
		-- 1.3.6.1.4.1.10428 9 1.102.12.4.2.3.8
		fkV2McastIPTvPackageControlPreviewChannelCnt OBJECT-TYPE
			SYNTAX INTEGER (0..65535)
			MAX-ACCESS read-write
			STATUS current
			DESCRIPTION
				"The number of preview channel"
			::= { fkV2McastIPTvPackageControl 8 }

		
		-- 1.3.6.1.4.1.10428 9 1.102.12.4.2.3.9
		fkV2McastIPTvPackageControlPreviewChannelList OBJECT-TYPE
			SYNTAX OCTET STRING
			MAX-ACCESS read-write
			STATUS current
			DESCRIPTION
				"Preview channel list (each value length 4byte)"
			::= { fkV2McastIPTvPackageControl 9 }

		
		-- 1.3.6.1.4.1.10428 9 1.102.12.4.2.3.10
		fkV2McastIPTvPackageControlFullviewChannelCnt OBJECT-TYPE
			SYNTAX INTEGER (0..65535)
			MAX-ACCESS read-write
			STATUS current
			DESCRIPTION
				"The number of fullview channel"
			::= { fkV2McastIPTvPackageControl 10 }

		
		-- 1.3.6.1.4.1.10428 9 1.102.12.4.2.3.11
		fkV2McastIPTvPackageControlFullviewChannelList OBJECT-TYPE
			SYNTAX OCTET STRING
			MAX-ACCESS read-write
			STATUS current
			DESCRIPTION
				"Fullview channel list (each value length 4byte)"
			::= { fkV2McastIPTvPackageControl 11 }

		
		-- 1.3.6.1.4.1.10428 9 1.102.12.4.2.4
		fkV2McastIPTvPackageNotification OBJECT IDENTIFIER ::= { fkV2McastIPTvPackage 4 }

		
		-- 1.3.6.1.4.1.10428 9 1.102.12.4.2.4.1
		fkV2McastIPTvPackageCreated NOTIFICATION-TYPE
			OBJECTS { fkV2McastIPTvPackageControlRequest, fkV2McastIPTvPackageControlTimeStamp, fkV2McastIPTvPackageControlReqResult, fkV2McastIPTvPackageControlId, fkV2McastIPTvPackageControlDescription
				 }
			STATUS current
			DESCRIPTION 
				"Description."
			::= { fkV2McastIPTvPackageNotification 1 }

		
		-- 1.3.6.1.4.1.10428 9 1.102.12.4.2.4.2
		fkV2McastIPTvPackageChanged NOTIFICATION-TYPE
			OBJECTS { fkV2McastIPTvPackageControlRequest, fkV2McastIPTvPackageControlTimeStamp, fkV2McastIPTvPackageControlReqResult, fkV2McastIPTvPackageControlId, fkV2McastIPTvPackageControlDescription
				 }
			STATUS current
			DESCRIPTION 
				"Description."
			::= { fkV2McastIPTvPackageNotification 2 }

		
		-- 1.3.6.1.4.1.10428 9 1.102.12.4.2.4.3
		fkV2McastIPTvPackageDeleted NOTIFICATION-TYPE
			OBJECTS { fkV2McastIPTvPackageControlRequest, fkV2McastIPTvPackageControlTimeStamp, fkV2McastIPTvPackageControlReqResult, fkV2McastIPTvPackageControlId }
			STATUS current
			DESCRIPTION 
				"Description."
			::= { fkV2McastIPTvPackageNotification 3 }

		
		-- 1.3.6.1.4.1.10428 9 1.102.12.4.2.4.4
		fkV2McastIPTvPackageAddChannel NOTIFICATION-TYPE
			OBJECTS { fkV2McastIPTvPackageControlRequest, fkV2McastIPTvPackageControlTimeStamp, fkV2McastIPTvPackageControlReqResult, fkV2McastIPTvPackageControlId, fkV2McastIPTvPackageControlPreviewChannelCnt, 
				fkV2McastIPTvPackageControlFullviewChannelCnt }
			STATUS current
			DESCRIPTION 
				"Description."
			::= { fkV2McastIPTvPackageNotification 4 }

		
		-- 1.3.6.1.4.1.10428 9 1.102.12.4.2.4.5
		fkV2McastIPTvPackageRemoveChannel NOTIFICATION-TYPE
			OBJECTS { fkV2McastIPTvPackageControlRequest, fkV2McastIPTvPackageControlTimeStamp, fkV2McastIPTvPackageControlReqResult, fkV2McastIPTvPackageControlPreviewChannelCnt, fkV2McastIPTvPackageControlFullviewChannelCnt
				 }
			STATUS current
			DESCRIPTION 
				"Description."
			::= { fkV2McastIPTvPackageNotification 5 }

		
		-- 1.3.6.1.4.1.10428 9 1.102.12.4.3
		fkV2McastIPTvPreviewProfile OBJECT IDENTIFIER ::= { fkV2McastIPTvMgmt 3 }

		
		-- 1.3.6.1.4.1.10428 9 1.102.12.4.3.1
		fkV2McastIPTvPreviewProfileTable OBJECT-TYPE
			SYNTAX SEQUENCE OF FkV2McastIPTvPreviewProfileEntry
			MAX-ACCESS not-accessible
			STATUS current
			DESCRIPTION
				"multicast IPTV preview profile table."
			::= { fkV2McastIPTvPreviewProfile 1 }

		
		-- 1.3.6.1.4.1.10428 9 1.102.12.4.3.1.1
		fkV2McastIPTvPreviewProfileEntry OBJECT-TYPE
			SYNTAX FkV2McastIPTvPreviewProfileEntry
			MAX-ACCESS not-accessible
			STATUS current
			DESCRIPTION
				"Description."
			INDEX { fkV2McastIPTvPreviewProfileId }
			::= { fkV2McastIPTvPreviewProfileTable 1 }
-- key: fkV2McastIPTvPreviewProfileId
		
		FkV2McastIPTvPreviewProfileEntry ::=
			SEQUENCE { 
				fkV2McastIPTvPreviewProfileId
					Integer32,
				fkV2McastIPTvPreviewProfileMaxDuration
					INTEGER,
				fkV2McastIPTvPreviewProfileMaxPreviews
					INTEGER,
				fkV2McastIPTvPreviewProfileBlackoutDuration
					INTEGER,
				fkV2McastIPTvPreviewProfileRecognitionTime
					INTEGER
			 }

		-- 1.3.6.1.4.1.10428 9 1.102.12.4.3.1.1.1
		fkV2McastIPTvPreviewProfileId OBJECT-TYPE
			SYNTAX Integer32 (1..65535)
			MAX-ACCESS read-only
			STATUS current
			DESCRIPTION
				"Preview profile id"
			::= { fkV2McastIPTvPreviewProfileEntry 1 }

		
		-- 1.3.6.1.4.1.10428 9 1.102.12.4.3.1.1.2
		fkV2McastIPTvPreviewProfileMaxDuration OBJECT-TYPE
			SYNTAX INTEGER (0..65535)
			MAX-ACCESS read-only
			STATUS current
			DESCRIPTION
				"Restricted time duration for Preview Channel (sec)"
			::= { fkV2McastIPTvPreviewProfileEntry 2 }

		
		-- 1.3.6.1.4.1.10428 9 1.102.12.4.3.1.1.3
		fkV2McastIPTvPreviewProfileMaxPreviews OBJECT-TYPE
			SYNTAX INTEGER (0..65535)
			MAX-ACCESS read-only
			STATUS current
			DESCRIPTION
				"Restricted number of times for Preview Channel"
			::= { fkV2McastIPTvPreviewProfileEntry 3 }

		
		-- 1.3.6.1.4.1.10428 9 1.102.12.4.3.1.1.4
		fkV2McastIPTvPreviewProfileBlackoutDuration OBJECT-TYPE
			SYNTAX INTEGER (0..65535)
			MAX-ACCESS read-only
			STATUS current
			DESCRIPTION
				"Time duration for blackout after seeing Preview Channel (sec)"
			::= { fkV2McastIPTvPreviewProfileEntry 4 }

		
		-- 1.3.6.1.4.1.10428 9 1.102.12.4.3.1.1.5
		fkV2McastIPTvPreviewProfileRecognitionTime OBJECT-TYPE
			SYNTAX INTEGER (0..65535)
			MAX-ACCESS read-only
			STATUS current
			DESCRIPTION
				"Time duration for Recognition (sec)"
			::= { fkV2McastIPTvPreviewProfileEntry 5 }

		
		-- 1.3.6.1.4.1.10428 9 1.102.12.4.3.2
		fkV2McastIPTvPreviewProfileReset OBJECT IDENTIFIER ::= { fkV2McastIPTvPreviewProfile 2 }

		
		-- 1.3.6.1.4.1.10428 9 1.102.12.4.3.2.1
		fkV2McastIPTvPreviewProfileResetTimePeriod OBJECT-TYPE
			SYNTAX INTEGER
				{
				everyday(0),
				date1(1),
				date2(2),
				date3(3),
				date4(4),
				date5(5),
				date6(6),
				date7(7),
				date8(8),
				date9(9),
				date10(10),
				date11(11),
				date12(12),
				date13(13),
				date14(14),
				date15(15),
				date16(16),
				date17(17),
				date18(18),
				date19(19),
				date20(20),
				date21(21),
				date22(22),
				date23(23),
				date24(24),
				date25(25),
				date26(26),
				date27(27),
				date28(28),
				date29(29),
				date30(30),
				date31(31),
				sunday(32),
				monday(33),
				tuesday(34),
				wednesday(35),
				thursday(36),
				friday(37),
				saturday(38),
				none(39)
				}
			MAX-ACCESS read-only
			STATUS current
			DESCRIPTION
				"The period when Preview counters are initialized for Subscriber."
			::= { fkV2McastIPTvPreviewProfileReset 1 }

		
		-- 1.3.6.1.4.1.10428 9 1.102.12.4.3.2.2
		fkV2McastIPTvPreviewProfileResetTime OBJECT-TYPE
			SYNTAX OCTET STRING
			MAX-ACCESS read-only
			STATUS current
			DESCRIPTION
				"The time when Preview counters are initialized for Subscriber. 
				Reset time Format : hh:mm"
			::= { fkV2McastIPTvPreviewProfileReset 2 }

		
		-- 1.3.6.1.4.1.10428 9 1.102.12.4.3.3
		fkV2McastIPTvPreviewProfileControl OBJECT IDENTIFIER ::= { fkV2McastIPTvPreviewProfile 3 }

		
		-- 1.3.6.1.4.1.10428 9 1.102.12.4.3.3.1
		fkV2McastIPTvPreviewProfileControlRequest OBJECT-TYPE
			SYNTAX INTEGER
				{
				createPreviewProfile(1),
				updatePreviewProfile(2),
				deletePreviewProfile(3),
				setPreviewReset(4),
				setPreviewInstantReset(5)
				}
			MAX-ACCESS read-write
			STATUS current
			DESCRIPTION
				"The request of a user command"
			::= { fkV2McastIPTvPreviewProfileControl 1 }

		
		-- 1.3.6.1.4.1.10428 9 1.102.12.4.3.3.2
		fkV2McastIPTvPreviewProfileControlStatus OBJECT-TYPE
			SYNTAX FkControlStatusType
			MAX-ACCESS read-only
			STATUS current
			DESCRIPTION
				"The status of user command"
			::= { fkV2McastIPTvPreviewProfileControl 2 }

		
		-- 1.3.6.1.4.1.10428 9 1.102.12.4.3.3.3
		fkV2McastIPTvPreviewProfileControlTimer OBJECT-TYPE
			SYNTAX Gauge32
			MAX-ACCESS read-write
			STATUS current
			DESCRIPTION
				"The maximum time for the manager for a long running user command"
			::= { fkV2McastIPTvPreviewProfileControl 3 }

		
		-- 1.3.6.1.4.1.10428 9 1.102.12.4.3.3.4
		fkV2McastIPTvPreviewProfileControlTimeStamp OBJECT-TYPE
			SYNTAX TimeStamp
			MAX-ACCESS read-only
			STATUS current
			DESCRIPTION
				"The time stamp of the last command(end of command)"
			::= { fkV2McastIPTvPreviewProfileControl 4 }

		
		-- 1.3.6.1.4.1.10428 9 1.102.12.4.3.3.5
		fkV2McastIPTvPreviewProfileControlReqResult OBJECT-TYPE
			SYNTAX FkControlRequestResultType
			MAX-ACCESS read-only
			STATUS current
			DESCRIPTION
				"The result of the last user command"
			::= { fkV2McastIPTvPreviewProfileControl 5 }

		
		-- 1.3.6.1.4.1.10428 9 1.102.12.4.3.3.6
		fkV2McastIPTvPreviewProfileControlId OBJECT-TYPE
			SYNTAX INTEGER (0..65535)
			MAX-ACCESS read-write
			STATUS current
			DESCRIPTION
				"Preview profile id"
			::= { fkV2McastIPTvPreviewProfileControl 6 }

		
		-- 1.3.6.1.4.1.10428 9 1.102.12.4.3.3.7
		fkV2McastIPTvPreviewProfileControlMaxDuration OBJECT-TYPE
			SYNTAX INTEGER (0..65535)
			MAX-ACCESS read-write
			STATUS current
			DESCRIPTION
				"Restricted time duration for Preview Channel (sec)"
			::= { fkV2McastIPTvPreviewProfileControl 7 }

		
		-- 1.3.6.1.4.1.10428 9 1.102.12.4.3.3.8
		fkV2McastIPTvPreviewProfileControlMaxPreviews OBJECT-TYPE
			SYNTAX INTEGER (0..65535)
			MAX-ACCESS read-write
			STATUS current
			DESCRIPTION
				"Restricted number of times for Preview Channel"
			::= { fkV2McastIPTvPreviewProfileControl 8 }

		
		-- 1.3.6.1.4.1.10428 9 1.102.12.4.3.3.9
		fkV2McastIPTvPreviewProfileControlBlackoutDuration OBJECT-TYPE
			SYNTAX INTEGER (0..65535)
			MAX-ACCESS read-write
			STATUS current
			DESCRIPTION
				"Time duration for blackout after seeing Preview Channel(sec)"
			::= { fkV2McastIPTvPreviewProfileControl 9 }

		
		-- 1.3.6.1.4.1.10428 9 1.102.12.4.3.3.10
		fkV2McastIPTvPreviewProfileControlRecognitionTime OBJECT-TYPE
			SYNTAX INTEGER (0..65535)
			MAX-ACCESS read-write
			STATUS current
			DESCRIPTION
				"Time duration for Recognition (sec)"
			::= { fkV2McastIPTvPreviewProfileControl 10 }

		
		-- 1.3.6.1.4.1.10428 9 1.102.12.4.3.3.11
		fkV2McastIPTvPreviewProfileControlResetTimePeriod OBJECT-TYPE
			SYNTAX INTEGER
				{
				everyday(0),
				date1(1),
				date2(2),
				date3(3),
				date4(4),
				date5(5),
				date6(6),
				date7(7),
				date8(8),
				date9(9),
				date10(10),
				date11(11),
				date12(12),
				date13(13),
				date14(14),
				date15(15),
				date16(16),
				date17(17),
				date18(18),
				date19(19),
				date20(20),
				date21(21),
				date22(22),
				date23(23),
				date24(24),
				date25(25),
				date26(26),
				date27(27),
				date28(28),
				date29(29),
				date30(30),
				date31(31),
				sunday(32),
				monday(33),
				tuesday(34),
				wednesday(35),
				thursday(36),
				friday(37),
				saturday(38),
				none(39)
				}
			MAX-ACCESS read-write
			STATUS current
			DESCRIPTION
				"The period when Preview counters are initialized for Subscriber."
			::= { fkV2McastIPTvPreviewProfileControl 11 }

		
		-- 1.3.6.1.4.1.10428 9 1.102.12.4.3.3.12
		fkV2McastIPTvPreviewProfileControlResetTime OBJECT-TYPE
			SYNTAX OCTET STRING
			MAX-ACCESS read-write
			STATUS current
			DESCRIPTION
				"The time when Preview counters are initialized for Subscriber. 
				Reset time Format : hh:mm"
			::= { fkV2McastIPTvPreviewProfileControl 12 }

		
		-- 1.3.6.1.4.1.10428 9 1.102.12.4.3.4
		fkV2McastIPTvPreviewProfileNotification OBJECT IDENTIFIER ::= { fkV2McastIPTvPreviewProfile 4 }

		
		-- 1.3.6.1.4.1.10428 9 1.102.12.4.3.4.1
		fkV2McastIPTvPreviewProfileCreated NOTIFICATION-TYPE
			OBJECTS { fkV2McastIPTvPreviewProfileControlRequest, fkV2McastIPTvPreviewProfileControlTimeStamp, fkV2McastIPTvPreviewProfileControlReqResult, fkV2McastIPTvPreviewProfileControlId, fkV2McastIPTvPreviewProfileControlMaxDuration, 
				fkV2McastIPTvPreviewProfileControlMaxPreviews, fkV2McastIPTvPreviewProfileControlBlackoutDuration, fkV2McastIPTvPreviewProfileControlRecognitionTime }
			STATUS current
			DESCRIPTION 
				"Description."
			::= { fkV2McastIPTvPreviewProfileNotification 1 }

		
		-- 1.3.6.1.4.1.10428 9 1.102.12.4.3.4.2
		fkV2McastIPTvPreviewProfileChanged NOTIFICATION-TYPE
			OBJECTS { fkV2McastIPTvPreviewProfileControlRequest, fkV2McastIPTvPreviewProfileControlTimeStamp, fkV2McastIPTvPreviewProfileControlReqResult, fkV2McastIPTvPreviewProfileControlId, fkV2McastIPTvPreviewProfileControlMaxDuration, 
				fkV2McastIPTvPreviewProfileControlMaxPreviews, fkV2McastIPTvPreviewProfileControlBlackoutDuration, fkV2McastIPTvPreviewProfileControlRecognitionTime }
			STATUS current
			DESCRIPTION 
				"Description."
			::= { fkV2McastIPTvPreviewProfileNotification 2 }

		
		-- 1.3.6.1.4.1.10428 9 1.102.12.4.3.4.3
		fkV2McastIPTvPreviewProfileDeleted NOTIFICATION-TYPE
			OBJECTS { fkV2McastIPTvPreviewProfileControlRequest, fkV2McastIPTvPreviewProfileControlTimeStamp, fkV2McastIPTvPreviewProfileControlReqResult, fkV2McastIPTvPreviewProfileControlId }
			STATUS current
			DESCRIPTION 
				"Description."
			::= { fkV2McastIPTvPreviewProfileNotification 3 }

		
		-- 1.3.6.1.4.1.10428 9 1.102.12.4.3.4.4
		fkV2McastIPTvPreviewProfileResetChanged NOTIFICATION-TYPE
			OBJECTS { fkV2McastIPTvPreviewProfileControlRequest, fkV2McastIPTvPreviewProfileControlTimeStamp, fkV2McastIPTvPreviewProfileControlReqResult, fkV2McastIPTvPreviewProfileControlResetTimePeriod, fkV2McastIPTvPreviewProfileControlResetTime
				 }
			STATUS current
			DESCRIPTION 
				"Description."
			::= { fkV2McastIPTvPreviewProfileNotification 4 }

		
		-- 1.3.6.1.4.1.10428 9 1.102.12.4.3.4.5
		fkV2McastIPTvPreviewInstantReset NOTIFICATION-TYPE
			OBJECTS { fkV2McastIPTvPreviewProfileControlRequest, fkV2McastIPTvPreviewProfileControlTimeStamp, fkV2McastIPTvPreviewProfileControlReqResult }
			STATUS current
			DESCRIPTION 
				"Description."
			::= { fkV2McastIPTvPreviewProfileNotification 5 }

		
		-- 1.3.6.1.4.1.10428 9 1.102.12.4.4
		fkV2McastIPTvChannel OBJECT IDENTIFIER ::= { fkV2McastIPTvMgmt 4 }

		
		-- 1.3.6.1.4.1.10428 9 1.102.12.4.4.1
		fkV2McastIPTvChannelTable OBJECT-TYPE
			SYNTAX SEQUENCE OF FkV2McastIPTvChannelEntry
			MAX-ACCESS not-accessible
			STATUS current
			DESCRIPTION
				"multicast IPTV channel table."
			::= { fkV2McastIPTvChannel 1 }

		
		-- 1.3.6.1.4.1.10428 9 1.102.12.4.4.1.1
		fkV2McastIPTvChannelEntry OBJECT-TYPE
			SYNTAX FkV2McastIPTvChannelEntry
			MAX-ACCESS not-accessible
			STATUS current
			DESCRIPTION
				"key: fkV2McastIPTvChannelId"
			INDEX { fkV2McastIPTvChannelId }
			::= { fkV2McastIPTvChannelTable 1 }

		
		FkV2McastIPTvChannelEntry ::=
			SEQUENCE { 
				fkV2McastIPTvChannelId
					Integer32,
				fkV2McastIPTvChannelSourceAddress
					IpAddress,
				fkV2McastIPTvChannelGroupAddress
					IpAddress,
				fkV2McastIPTvChannelBandwidth
					INTEGER,
				fkV2McastIPTvChannelPreviewProfileId
					INTEGER,
				fkV2McastIPTvChannelCacGroupId
					INTEGER,
				fkV2McastIPTvChannelDescription
					OCTET STRING
			 }

		-- 1.3.6.1.4.1.10428 9 1.102.12.4.4.1.1.1
		fkV2McastIPTvChannelId OBJECT-TYPE
			SYNTAX Integer32 (1..65535)
			MAX-ACCESS read-only
			STATUS current
			DESCRIPTION
				"Channel id"
			::= { fkV2McastIPTvChannelEntry 1 }

		
		-- 1.3.6.1.4.1.10428 9 1.102.12.4.4.1.1.2
		fkV2McastIPTvChannelSourceAddress OBJECT-TYPE
			SYNTAX IpAddress
			MAX-ACCESS read-only
			STATUS current
			DESCRIPTION
				"Multicast server address"
			::= { fkV2McastIPTvChannelEntry 2 }

		
		-- 1.3.6.1.4.1.10428 9 1.102.12.4.4.1.1.3
		fkV2McastIPTvChannelGroupAddress OBJECT-TYPE
			SYNTAX IpAddress
			MAX-ACCESS read-only
			STATUS current
			DESCRIPTION
				"Multicast address (IP address of IGMP group)"
			::= { fkV2McastIPTvChannelEntry 3 }

		
		-- 1.3.6.1.4.1.10428 9 1.102.12.4.4.1.1.4
		fkV2McastIPTvChannelBandwidth OBJECT-TYPE
			SYNTAX INTEGER (0..65535)
			MAX-ACCESS read-only
			STATUS current
			DESCRIPTION
				"Bandwidth of Channel (KB)"
			::= { fkV2McastIPTvChannelEntry 4 }

		
		-- 1.3.6.1.4.1.10428 9 1.102.12.4.4.1.1.5
		fkV2McastIPTvChannelPreviewProfileId OBJECT-TYPE
			SYNTAX INTEGER (0..65535)
			MAX-ACCESS read-only
			STATUS current
			DESCRIPTION
				"Preview profile id"
			::= { fkV2McastIPTvChannelEntry 5 }

		
		-- 1.3.6.1.4.1.10428 9 1.102.12.4.4.1.1.6
		fkV2McastIPTvChannelCacGroupId OBJECT-TYPE
			SYNTAX INTEGER (0..65535)
			MAX-ACCESS read-only
			STATUS current
			DESCRIPTION
				"The ID of CAC group"
			::= { fkV2McastIPTvChannelEntry 6 }

		
		-- 1.3.6.1.4.1.10428 9 1.102.12.4.4.1.1.7
		fkV2McastIPTvChannelDescription OBJECT-TYPE
			SYNTAX OCTET STRING
			MAX-ACCESS read-only
			STATUS current
			DESCRIPTION
				"The description of Channel"
			::= { fkV2McastIPTvChannelEntry 7 }

		
		-- 1.3.6.1.4.1.10428 9 1.102.12.4.4.2
		fkV2McastIPTvChannelPackageTable OBJECT-TYPE
			SYNTAX SEQUENCE OF FkV2McastIPTvChannelPackageEntry
			MAX-ACCESS not-accessible
			STATUS current
			DESCRIPTION
				"multicast IPTV channel package table."
			::= { fkV2McastIPTvChannel 2 }

		
		-- 1.3.6.1.4.1.10428 9 1.102.12.4.4.2.1
		fkV2McastIPTvChannelPackageEntry OBJECT-TYPE
			SYNTAX FkV2McastIPTvChannelPackageEntry
			MAX-ACCESS not-accessible
			STATUS current
			DESCRIPTION
				"key: fkV2McastIPTvChannelId, fkV2McastIPTvPackageId"
			INDEX { fkV2McastIPTvChannelId, fkV2McastIPTvPackageId }
			::= { fkV2McastIPTvChannelPackageTable 1 }

		
		FkV2McastIPTvChannelPackageEntry ::=
			SEQUENCE { 
				fkV2McastIPTvChannelPackageDescription
					OCTET STRING
			 }

		-- 1.3.6.1.4.1.10428 9 1.102.12.4.4.2.1.1
		fkV2McastIPTvChannelPackageDescription OBJECT-TYPE
			SYNTAX OCTET STRING
			MAX-ACCESS read-only
			STATUS current
			DESCRIPTION
				"The  description of package include this channel.
				packageId_user-description,  ex)  '1_Disney-channel'"
			::= { fkV2McastIPTvChannelPackageEntry 1 }

		
		-- 1.3.6.1.4.1.10428 9 1.102.12.4.4.3
		fkV2McastIPTvChannelControl OBJECT IDENTIFIER ::= { fkV2McastIPTvChannel 3 }

		
		-- 1.3.6.1.4.1.10428 9 1.102.12.4.4.3.1
		fkV2McastIPTvChannelControlRequest OBJECT-TYPE
			SYNTAX INTEGER
				{
				createChannel(1),
				updateChannel(2),
				deleteChannel(3)
				}
			MAX-ACCESS read-write
			STATUS current
			DESCRIPTION
				"The request of a user command"
			::= { fkV2McastIPTvChannelControl 1 }

		
		-- 1.3.6.1.4.1.10428 9 1.102.12.4.4.3.2
		fkV2McastIPTvChannelControlStatus OBJECT-TYPE
			SYNTAX FkControlStatusType
			MAX-ACCESS read-only
			STATUS current
			DESCRIPTION
				"The status of user command"
			::= { fkV2McastIPTvChannelControl 2 }

		
		-- 1.3.6.1.4.1.10428 9 1.102.12.4.4.3.3
		fkV2McastIPTvChannelControlTimer OBJECT-TYPE
			SYNTAX Gauge32
			MAX-ACCESS read-write
			STATUS current
			DESCRIPTION
				"The maximum time for the manager for a long running user command"
			::= { fkV2McastIPTvChannelControl 3 }

		
		-- 1.3.6.1.4.1.10428 9 1.102.12.4.4.3.4
		fkV2McastIPTvChannelControlTimeStamp OBJECT-TYPE
			SYNTAX TimeStamp
			MAX-ACCESS read-only
			STATUS current
			DESCRIPTION
				"The time stamp of the last command(end of command)"
			::= { fkV2McastIPTvChannelControl 4 }

		
		-- 1.3.6.1.4.1.10428 9 1.102.12.4.4.3.5
		fkV2McastIPTvChannelControlReqResult OBJECT-TYPE
			SYNTAX FkControlRequestResultType
			MAX-ACCESS read-only
			STATUS current
			DESCRIPTION
				"The result of the last user command"
			::= { fkV2McastIPTvChannelControl 5 }

		
		-- 1.3.6.1.4.1.10428 9 1.102.12.4.4.3.6
		fkV2McastIPTvChannelControlId OBJECT-TYPE
			SYNTAX INTEGER (0..65535)
			MAX-ACCESS read-write
			STATUS current
			DESCRIPTION
				"Channel id"
			::= { fkV2McastIPTvChannelControl 6 }

		
		-- 1.3.6.1.4.1.10428 9 1.102.12.4.4.3.7
		fkV2McastIPTvChannelControlSourceAddress OBJECT-TYPE
			SYNTAX IpAddress
			MAX-ACCESS read-write
			STATUS current
			DESCRIPTION
				"Multicast server address"
			::= { fkV2McastIPTvChannelControl 7 }

		
		-- 1.3.6.1.4.1.10428 9 1.102.12.4.4.3.8
		fkV2McastIPTvChannelControlGroupAddress OBJECT-TYPE
			SYNTAX IpAddress
			MAX-ACCESS read-write
			STATUS current
			DESCRIPTION
				"Multicast address (IP address of IGMP group)"
			::= { fkV2McastIPTvChannelControl 8 }

		
		-- 1.3.6.1.4.1.10428 9 1.102.12.4.4.3.9
		fkV2McastIPTvChannelControlBandwidth OBJECT-TYPE
			SYNTAX INTEGER (0..65535)
			MAX-ACCESS read-write
			STATUS current
			DESCRIPTION
				"Bandwidth of Channel"
			::= { fkV2McastIPTvChannelControl 9 }

		
		-- 1.3.6.1.4.1.10428 9 1.102.12.4.4.3.10
		fkV2McastIPTvChannelControlPreviewProfileId OBJECT-TYPE
			SYNTAX INTEGER (0..65535)
			MAX-ACCESS read-write
			STATUS current
			DESCRIPTION
				"Preview profile id"
			::= { fkV2McastIPTvChannelControl 10 }

		
		-- 1.3.6.1.4.1.10428 9 1.102.12.4.4.3.11
		fkV2McastIPTvChannelControlCacGroupId OBJECT-TYPE
			SYNTAX INTEGER (0..65535)
			MAX-ACCESS read-write
			STATUS current
			DESCRIPTION
				"The ID of CAC group"
			::= { fkV2McastIPTvChannelControl 11 }

		
		-- 1.3.6.1.4.1.10428 9 1.102.12.4.4.3.12
		fkV2McastIPTvChannelControlDescription OBJECT-TYPE
			SYNTAX OCTET STRING
			MAX-ACCESS read-write
			STATUS current
			DESCRIPTION
				"The description of Channel."
			::= { fkV2McastIPTvChannelControl 12 }

		
		-- 1.3.6.1.4.1.10428 9 1.102.12.4.4.4
		fkV2McastIPTvChannelNotification OBJECT IDENTIFIER ::= { fkV2McastIPTvChannel 4 }

		
		-- 1.3.6.1.4.1.10428 9 1.102.12.4.4.4.1
		fkV2McastIPTvChannelCreated NOTIFICATION-TYPE
			OBJECTS { fkV2McastIPTvChannelControlRequest, fkV2McastIPTvChannelControlTimeStamp, fkV2McastIPTvChannelControlReqResult, fkV2McastIPTvChannelControlId, fkV2McastIPTvChannelControlSourceAddress, 
				fkV2McastIPTvChannelControlGroupAddress, fkV2McastIPTvChannelControlBandwidth, fkV2McastIPTvChannelControlPreviewProfileId, fkV2McastIPTvChannelControlCacGroupId, fkV2McastIPTvChannelControlDescription
				 }
			STATUS current
			DESCRIPTION 
				"Description."
			::= { fkV2McastIPTvChannelNotification 1 }

		
		-- 1.3.6.1.4.1.10428 9 1.102.12.4.4.4.2
		fkV2McastIPTvChannelChanged NOTIFICATION-TYPE
			OBJECTS { fkV2McastIPTvChannelControlRequest, fkV2McastIPTvChannelControlTimeStamp, fkV2McastIPTvChannelControlReqResult, fkV2McastIPTvChannelControlId, fkV2McastIPTvChannelControlSourceAddress, 
				fkV2McastIPTvChannelControlGroupAddress, fkV2McastIPTvChannelControlBandwidth, fkV2McastIPTvChannelControlPreviewProfileId, fkV2McastIPTvChannelControlCacGroupId, fkV2McastIPTvChannelControlDescription
				 }
			STATUS current
			DESCRIPTION 
				"Description."
			::= { fkV2McastIPTvChannelNotification 2 }

		
		-- 1.3.6.1.4.1.10428 9 1.102.12.4.4.4.3
		fkV2McastIPTvChannelDeleted NOTIFICATION-TYPE
			OBJECTS { fkV2McastIPTvChannelControlRequest, fkV2McastIPTvChannelControlTimeStamp, fkV2McastIPTvChannelControlReqResult, fkV2McastIPTvChannelControlId }
			STATUS current
			DESCRIPTION 
				"Description."
			::= { fkV2McastIPTvChannelNotification 3 }

		
		-- 1.3.6.1.4.1.10428 9 1.102.12.4.4.5
		fkV2McastIPTvChannelCurrentJoined OBJECT IDENTIFIER ::= { fkV2McastIPTvChannel 5 }

		
		-- 1.3.6.1.4.1.10428 9 1.102.12.4.4.5.1
		fkV2McastIPTvChannelCurrentVlanPortTable OBJECT-TYPE
			SYNTAX SEQUENCE OF FkV2McastIPTvChannelCurrentVlanPortEntry
			MAX-ACCESS not-accessible
			STATUS current
			DESCRIPTION
				"multicast IPTV channel current vlan port table."
			::= { fkV2McastIPTvChannelCurrentJoined 1 }

		
		-- 1.3.6.1.4.1.10428 9 1.102.12.4.4.5.1.1
		fkV2McastIPTvChannelCurrentVlanPortEntry OBJECT-TYPE
			SYNTAX FkV2McastIPTvChannelCurrentVlanPortEntry
			MAX-ACCESS not-accessible
			STATUS current
			DESCRIPTION
				"key: fkV2McastIPTvChannelCurrentVlanId, fkV2McastIPTvChannelCurrentPortId, fkV2McastIPTvChannelCurrentVlanPortChannelId"
			INDEX { fkV2McastIPTvChannelCurrentVlanId, fkV2McastIPTvChannelCurrentPortId, fkV2McastIPTvChannelCurrentVlanPortChannelId }
			::= { fkV2McastIPTvChannelCurrentVlanPortTable 1 }

		
		FkV2McastIPTvChannelCurrentVlanPortEntry ::=
			SEQUENCE { 
				fkV2McastIPTvChannelCurrentVlanId
					Integer32,
				fkV2McastIPTvChannelCurrentPortId
					Integer32,
				fkV2McastIPTvChannelCurrentVlanPortChannelId
					Integer32,
				fkV2McastIPTvChannelCurrentVlanPortJoinedTime
					OCTET STRING
			 }

		-- 1.3.6.1.4.1.10428 9 1.102.12.4.4.5.1.1.1
		fkV2McastIPTvChannelCurrentVlanId OBJECT-TYPE
			SYNTAX Integer32 (1..65535)
			MAX-ACCESS read-only
			STATUS current
			DESCRIPTION
				"The Vlan Id"
			::= { fkV2McastIPTvChannelCurrentVlanPortEntry 1 }

		
		-- 1.3.6.1.4.1.10428 9 1.102.12.4.4.5.1.1.2
		fkV2McastIPTvChannelCurrentPortId OBJECT-TYPE
			SYNTAX Integer32 (1..65535)
			MAX-ACCESS read-only
			STATUS current
			DESCRIPTION
				"The port Id"
			::= { fkV2McastIPTvChannelCurrentVlanPortEntry 2 }

		
		-- 1.3.6.1.4.1.10428 9 1.102.12.4.4.5.1.1.3
		fkV2McastIPTvChannelCurrentVlanPortChannelId OBJECT-TYPE
			SYNTAX Integer32 (1..65535)
			MAX-ACCESS read-only
			STATUS current
			DESCRIPTION
				"same as  fkV2McastIPTvChannelId"
			::= { fkV2McastIPTvChannelCurrentVlanPortEntry 3 }

		
		-- 1.3.6.1.4.1.10428 9 1.102.12.4.4.5.1.1.4
		fkV2McastIPTvChannelCurrentVlanPortJoinedTime OBJECT-TYPE
			SYNTAX OCTET STRING
			MAX-ACCESS read-only
			STATUS current
			DESCRIPTION
				"The joined time of channel"
			::= { fkV2McastIPTvChannelCurrentVlanPortEntry 4 }

		
		-- 1.3.6.1.4.1.10428 9 1.102.12.4.4.5.2
		fkV2McastIPTvChannelCurrentSubscriberTable OBJECT-TYPE
			SYNTAX SEQUENCE OF FkV2McastIPTvChannelCurrentSubscriberEntry
			MAX-ACCESS not-accessible
			STATUS current
			DESCRIPTION
				"multicast IPTV channel current subscriber table."
			::= { fkV2McastIPTvChannelCurrentJoined 2 }

		
		-- 1.3.6.1.4.1.10428 9 1.102.12.4.4.5.2.1
		fkV2McastIPTvChannelCurrentSubscriberEntry OBJECT-TYPE
			SYNTAX FkV2McastIPTvChannelCurrentSubscriberEntry
			MAX-ACCESS not-accessible
			STATUS current
			DESCRIPTION
				"key: fkV2McastIPTvSubscriberId, fkV2McastIPTvChannelCurrentSubscriberChannelId"
			INDEX { fkV2McastIPTvSubscriberId, fkV2McastIPTvChannelCurrentSubscriberChannelId }
			::= { fkV2McastIPTvChannelCurrentSubscriberTable 1 }

		
		FkV2McastIPTvChannelCurrentSubscriberEntry ::=
			SEQUENCE { 
				fkV2McastIPTvChannelCurrentSubscriberChannelId
					Integer32,
				fkV2McastIPTvChannelCurrentSubscriberJoinedTime
					OCTET STRING,
				fkV2McastIPTvChannelCurrentSubscriberJoinDurationTime
					INTEGER
			 }

		-- 1.3.6.1.4.1.10428 9 1.102.12.4.4.5.2.1.1
		fkV2McastIPTvChannelCurrentSubscriberChannelId OBJECT-TYPE
			SYNTAX Integer32 (1..65535)
			MAX-ACCESS read-only
			STATUS current
			DESCRIPTION
				"same as  fkV2McastIPTvChannelId"
			::= { fkV2McastIPTvChannelCurrentSubscriberEntry 1 }

		
		-- 1.3.6.1.4.1.10428 9 1.102.12.4.4.5.2.1.2
		fkV2McastIPTvChannelCurrentSubscriberJoinedTime OBJECT-TYPE
			SYNTAX OCTET STRING
			MAX-ACCESS read-only
			STATUS current
			DESCRIPTION
				"indicate when subscriber joined the channel"
			::= { fkV2McastIPTvChannelCurrentSubscriberEntry 2 }

		
		-- 1.3.6.1.4.1.10428 9 1.102.12.4.4.5.2.1.3
		fkV2McastIPTvChannelCurrentSubscriberJoinDurationTime OBJECT-TYPE
			SYNTAX INTEGER (0..65535)
			MAX-ACCESS read-only
			STATUS current
			DESCRIPTION
				"indicate how long have subscriber joined the channel"
			::= { fkV2McastIPTvChannelCurrentSubscriberEntry 3 }

		
		-- 1.3.6.1.4.1.10428 9 1.102.12.4.5
		fkV2McastIPTvCacProfile OBJECT IDENTIFIER ::= { fkV2McastIPTvMgmt 5 }

		
		-- 1.3.6.1.4.1.10428 9 1.102.12.4.5.1
		fkV2McastIPTvCacProfileTable OBJECT-TYPE
			SYNTAX SEQUENCE OF FkV2McastIPTvCacProfileEntry
			MAX-ACCESS not-accessible
			STATUS current
			DESCRIPTION
				"multicast IPTV Cac profile table."
			::= { fkV2McastIPTvCacProfile 1 }

		
		-- 1.3.6.1.4.1.10428 9 1.102.12.4.5.1.1
		fkV2McastIPTvCacProfileEntry OBJECT-TYPE
			SYNTAX FkV2McastIPTvCacProfileEntry
			MAX-ACCESS not-accessible
			STATUS current
			DESCRIPTION
				"key: fkV2McastIPTvCacProfileId"
			INDEX { fkV2McastIPTvCacProfileId }
			::= { fkV2McastIPTvCacProfileTable 1 }

		
		FkV2McastIPTvCacProfileEntry ::=
			SEQUENCE { 
				fkV2McastIPTvCacProfileId
					Integer32,
				fkV2McastIPTvCacProfileMaxChannel
					INTEGER,
				fkV2McastIPTvCacProfileMaxBandwidth
					INTEGER,
				fkV2McastIPTvCacProfileCacGroupCnt
					INTEGER,
				fkV2McastIPTvCacProfileDescription
					OCTET STRING
			 }

		-- 1.3.6.1.4.1.10428 9 1.102.12.4.5.1.1.1
		fkV2McastIPTvCacProfileId OBJECT-TYPE
			SYNTAX Integer32 (1..65535)
			MAX-ACCESS read-only
			STATUS current
			DESCRIPTION
				"CAC profile id"
			::= { fkV2McastIPTvCacProfileEntry 1 }

		
		-- 1.3.6.1.4.1.10428 9 1.102.12.4.5.1.1.2
		fkV2McastIPTvCacProfileMaxChannel OBJECT-TYPE
			SYNTAX INTEGER (0..65535)
			MAX-ACCESS read-only
			STATUS current
			DESCRIPTION
				"The maximum number of channel which can be seen simultaneously"
			::= { fkV2McastIPTvCacProfileEntry 2 }

		
		-- 1.3.6.1.4.1.10428 9 1.102.12.4.5.1.1.3
		fkV2McastIPTvCacProfileMaxBandwidth OBJECT-TYPE
			SYNTAX INTEGER (0..65535)
			MAX-ACCESS read-only
			STATUS current
			DESCRIPTION
				"The maximum bandwidth which CAC Profile can use"
			::= { fkV2McastIPTvCacProfileEntry 3 }

		
		-- 1.3.6.1.4.1.10428 9 1.102.12.4.5.1.1.4
		fkV2McastIPTvCacProfileCacGroupCnt OBJECT-TYPE
			SYNTAX INTEGER (0..65535)
			MAX-ACCESS read-only
			STATUS current
			DESCRIPTION
				"The number of CAC group"
			::= { fkV2McastIPTvCacProfileEntry 4 }

		
		-- 1.3.6.1.4.1.10428 9 1.102.12.4.5.1.1.5
		fkV2McastIPTvCacProfileDescription OBJECT-TYPE
			SYNTAX OCTET STRING
			MAX-ACCESS read-only
			STATUS current
			DESCRIPTION
				"The description of CAC profile"
			::= { fkV2McastIPTvCacProfileEntry 5 }

		
		-- 1.3.6.1.4.1.10428 9 1.102.12.4.5.2
		fkV2McastIPTvCacProfileGroupTable OBJECT-TYPE
			SYNTAX SEQUENCE OF FkV2McastIPTvCacProfileGroupEntry
			MAX-ACCESS not-accessible
			STATUS current
			DESCRIPTION
				"multicast IPTV Cac profile group table."
			::= { fkV2McastIPTvCacProfile 2 }

		
		-- 1.3.6.1.4.1.10428 9 1.102.12.4.5.2.1
		fkV2McastIPTvCacProfileGroupEntry OBJECT-TYPE
			SYNTAX FkV2McastIPTvCacProfileGroupEntry
			MAX-ACCESS not-accessible
			STATUS current
			DESCRIPTION
				"key: fkV2McastIPTvCacProfileId, fkV2McastIPTvCacProfileGroupId"
			INDEX { fkV2McastIPTvCacProfileId, fkV2McastIPTvCacProfileGroupId }
			::= { fkV2McastIPTvCacProfileGroupTable 1 }

		
		FkV2McastIPTvCacProfileGroupEntry ::=
			SEQUENCE { 
				fkV2McastIPTvCacProfileGroupId
					Integer32,
				fkV2McastIPTvCacProfileGroupMaxChanNum
					INTEGER
			 }

		-- 1.3.6.1.4.1.10428 9 1.102.12.4.5.2.1.1
		fkV2McastIPTvCacProfileGroupId OBJECT-TYPE
			SYNTAX Integer32 (1..65535)
			MAX-ACCESS read-only
			STATUS current
			DESCRIPTION
				"CAC profile Group id"
			::= { fkV2McastIPTvCacProfileGroupEntry 1 }

		
		-- 1.3.6.1.4.1.10428 9 1.102.12.4.5.2.1.2
		fkV2McastIPTvCacProfileGroupMaxChanNum OBJECT-TYPE
			SYNTAX INTEGER (0..65535)
			MAX-ACCESS read-only
			STATUS current
			DESCRIPTION
				"The number of channel which can be seen in CAC Group simultaneously"
			::= { fkV2McastIPTvCacProfileGroupEntry 2 }

		
		-- 1.3.6.1.4.1.10428 9 1.102.12.4.5.3
		fkV2McastIPTvCacProfileControl OBJECT IDENTIFIER ::= { fkV2McastIPTvCacProfile 3 }

		
		-- 1.3.6.1.4.1.10428 9 1.102.12.4.5.3.1
		fkV2McastIPTvCacProfileControlRequest OBJECT-TYPE
			SYNTAX INTEGER
				{
				createCACProfile(1),
				updateCACProfile(2),
				deleteCACProfile(3),
				addCACProfileGroup(4),
				removeCACProfileGroup(5)
				}
			MAX-ACCESS read-write
			STATUS current
			DESCRIPTION
				"The request of a user command"
			::= { fkV2McastIPTvCacProfileControl 1 }

		
		-- 1.3.6.1.4.1.10428 9 1.102.12.4.5.3.2
		fkV2McastIPTvCacProfileControlStatus OBJECT-TYPE
			SYNTAX FkControlStatusType
			MAX-ACCESS read-only
			STATUS current
			DESCRIPTION
				"The status of user command"
			::= { fkV2McastIPTvCacProfileControl 2 }

		
		-- 1.3.6.1.4.1.10428 9 1.102.12.4.5.3.3
		fkV2McastIPTvCacProfileControlTimer OBJECT-TYPE
			SYNTAX Gauge32
			MAX-ACCESS read-write
			STATUS current
			DESCRIPTION
				"The maximum time for the manager for a long running user command"
			::= { fkV2McastIPTvCacProfileControl 3 }

		
		-- 1.3.6.1.4.1.10428 9 1.102.12.4.5.3.4
		fkV2McastIPTvCacProfileControlTimeStamp OBJECT-TYPE
			SYNTAX TimeStamp
			MAX-ACCESS read-only
			STATUS current
			DESCRIPTION
				"The time stamp of the last command(end of command)"
			::= { fkV2McastIPTvCacProfileControl 4 }

		
		-- 1.3.6.1.4.1.10428 9 1.102.12.4.5.3.5
		fkV2McastIPTvCacProfileControlReqResult OBJECT-TYPE
			SYNTAX FkControlRequestResultType
			MAX-ACCESS read-only
			STATUS current
			DESCRIPTION
				"The result of the last user command"
			::= { fkV2McastIPTvCacProfileControl 5 }

		
		-- 1.3.6.1.4.1.10428 9 1.102.12.4.5.3.6
		fkV2McastIPTvCacProfileControlId OBJECT-TYPE
			SYNTAX INTEGER (0..65535)
			MAX-ACCESS read-write
			STATUS current
			DESCRIPTION
				"CAC profile id"
			::= { fkV2McastIPTvCacProfileControl 6 }

		
		-- 1.3.6.1.4.1.10428 9 1.102.12.4.5.3.7
		fkV2McastIPTvCacProfileControlMaxStream OBJECT-TYPE
			SYNTAX INTEGER (0..65535)
			MAX-ACCESS read-write
			STATUS current
			DESCRIPTION
				"The maximum number of channel which can be seen simultaneously"
			::= { fkV2McastIPTvCacProfileControl 7 }

		
		-- 1.3.6.1.4.1.10428 9 1.102.12.4.5.3.8
		fkV2McastIPTvCacProfileControlMaxBandwidth OBJECT-TYPE
			SYNTAX INTEGER (0..65535)
			MAX-ACCESS read-write
			STATUS current
			DESCRIPTION
				"The maximum bandwidth which CAC Profile can use"
			::= { fkV2McastIPTvCacProfileControl 8 }

		
		-- 1.3.6.1.4.1.10428 9 1.102.12.4.5.3.9
		fkV2McastIPTvCacProfileControlCacGroupCnt OBJECT-TYPE
			SYNTAX INTEGER (0..65535)
			MAX-ACCESS read-write
			STATUS current
			DESCRIPTION
				"The number of CAC group"
			::= { fkV2McastIPTvCacProfileControl 9 }

		
		-- 1.3.6.1.4.1.10428 9 1.102.12.4.5.3.10
		fkV2McastIPTvCacProfileControlCacGroupList OBJECT-TYPE
			SYNTAX OCTET STRING
			MAX-ACCESS read-write
			STATUS current
			DESCRIPTION
				"CAC group list (each value length 4byte)"
			::= { fkV2McastIPTvCacProfileControl 10 }

		
		-- 1.3.6.1.4.1.10428 9 1.102.12.4.5.3.11
		fkV2McastIPTvCacProfileControlCacGroupMaxChanNumList OBJECT-TYPE
			SYNTAX OCTET STRING
			MAX-ACCESS read-write
			STATUS current
			DESCRIPTION
				"The number of channel which can be seen in CAC Group simultaneously
				*The number of CAC group has to correspond with Group Max Channel
				(each value length 4byte)"
			::= { fkV2McastIPTvCacProfileControl 11 }

		
		-- 1.3.6.1.4.1.10428 9 1.102.12.4.5.3.12
		fkV2McastIPTvCacProfileControlDescription OBJECT-TYPE
			SYNTAX OCTET STRING
			MAX-ACCESS read-write
			STATUS current
			DESCRIPTION
				"Description."
			::= { fkV2McastIPTvCacProfileControl 12 }

		
		-- 1.3.6.1.4.1.10428 9 1.102.12.4.5.4
		fkV2McastIPTvCacProfileNotification OBJECT IDENTIFIER ::= { fkV2McastIPTvCacProfile 4 }

		
		-- 1.3.6.1.4.1.10428 9 1.102.12.4.5.4.1
		fkV2McastIPTvCacProfileCreated NOTIFICATION-TYPE
			OBJECTS { fkV2McastIPTvCacProfileControlRequest, fkV2McastIPTvCacProfileControlTimeStamp, fkV2McastIPTvCacProfileControlReqResult, fkV2McastIPTvCacProfileControlId, fkV2McastIPTvCacProfileControlMaxStream, 
				fkV2McastIPTvCacProfileControlMaxBandwidth, fkV2McastIPTvCacProfileControlCacGroupCnt }
			STATUS current
			DESCRIPTION 
				"Description."
			::= { fkV2McastIPTvCacProfileNotification 1 }

		
		-- 1.3.6.1.4.1.10428 9 1.102.12.4.5.4.2
		fkV2McastIPTvCacProfileChanged NOTIFICATION-TYPE
			OBJECTS { fkV2McastIPTvCacProfileControlRequest, fkV2McastIPTvCacProfileControlTimeStamp, fkV2McastIPTvCacProfileControlReqResult, fkV2McastIPTvCacProfileControlId, fkV2McastIPTvCacProfileControlMaxStream, 
				fkV2McastIPTvCacProfileControlMaxBandwidth }
			STATUS current
			DESCRIPTION 
				"Description."
			::= { fkV2McastIPTvCacProfileNotification 2 }

		
		-- 1.3.6.1.4.1.10428 9 1.102.12.4.5.4.3
		fkV2McastIPTvCacProfileDeleted NOTIFICATION-TYPE
			OBJECTS { fkV2McastIPTvCacProfileControlRequest, fkV2McastIPTvCacProfileControlTimeStamp, fkV2McastIPTvCacProfileControlReqResult, fkV2McastIPTvCacProfileControlId }
			STATUS current
			DESCRIPTION 
				"Description."
			::= { fkV2McastIPTvCacProfileNotification 3 }

		
		-- 1.3.6.1.4.1.10428 9 1.102.12.4.5.4.4
		fkV2McastIPTvCacProfileAddGroup NOTIFICATION-TYPE
			OBJECTS { fkV2McastIPTvCacProfileControlRequest, fkV2McastIPTvCacProfileControlTimeStamp, fkV2McastIPTvCacProfileControlReqResult, fkV2McastIPTvCacProfileControlId, fkV2McastIPTvCacProfileControlCacGroupCnt
				 }
			STATUS current
			DESCRIPTION 
				"Description."
			::= { fkV2McastIPTvCacProfileNotification 4 }

		
		-- 1.3.6.1.4.1.10428 9 1.102.12.4.5.4.5
		fkV2McastIPTvCacProfileDelGroup NOTIFICATION-TYPE
			OBJECTS { fkV2McastIPTvCacProfileControlRequest, fkV2McastIPTvCacProfileControlTimeStamp, fkV2McastIPTvCacProfileControlReqResult, fkV2McastIPTvCacProfileControlId, fkV2McastIPTvCacProfileControlCacGroupCnt
				 }
			STATUS current
			DESCRIPTION 
				"Description."
			::= { fkV2McastIPTvCacProfileNotification 5 }

		
		-- 1.3.6.1.4.1.10428 9 1.102.12.4.6
		fkV2McastIPTvSubscriber OBJECT IDENTIFIER ::= { fkV2McastIPTvMgmt 6 }

		
		-- 1.3.6.1.4.1.10428 9 1.102.12.4.6.1
		fkV2McastIPTvSubscriberBase OBJECT IDENTIFIER ::= { fkV2McastIPTvSubscriber 1 }

		
		-- 1.3.6.1.4.1.10428 9 1.102.12.4.6.2
		fkV2McastIPTvSubscriberMgmt OBJECT IDENTIFIER ::= { fkV2McastIPTvSubscriber 2 }

		
		-- 1.3.6.1.4.1.10428 9 1.102.12.4.6.2.1
		fkV2McastIPTvSubscriberTable OBJECT-TYPE
			SYNTAX SEQUENCE OF FkV2McastIPTvSubscriberEntry
			MAX-ACCESS not-accessible
			STATUS current
			DESCRIPTION
				"multicast IPTV subscriber table."
			::= { fkV2McastIPTvSubscriberMgmt 1 }

		
		-- 1.3.6.1.4.1.10428 9 1.102.12.4.6.2.1.1
		fkV2McastIPTvSubscriberEntry OBJECT-TYPE
			SYNTAX FkV2McastIPTvSubscriberEntry
			MAX-ACCESS not-accessible
			STATUS current
			DESCRIPTION
				"key: fkV2McastIPTvSubscriberId"
			INDEX { fkV2McastIPTvSubscriberId }
			::= { fkV2McastIPTvSubscriberTable 1 }

		
		FkV2McastIPTvSubscriberEntry ::=
			SEQUENCE { 
				fkV2McastIPTvSubscriberId
					Integer32,
				fkV2McastIPTvSubscriberPortType
					INTEGER,
				fkV2McastIPTvSubscriberSlotId
					INTEGER,
				fkV2McastIPTvSubscriberPortId
					INTEGER,
				fkV2McastIPTvSubscriberCTag
					INTEGER,
				fkV2McastIPTvSubscriberIpAddr
					IpAddress,
				fkV2McastIPTvSubscriberStatus
					INTEGER,
				fkV2McastIPTvSubscriberCacProfileId
					INTEGER,
				fkV2McastIPTvSubscriberPackageCnt
					INTEGER,
				fkV2McastIPTvSubscriberDescription
					OCTET STRING
			 }

		-- 1.3.6.1.4.1.10428 9 1.102.12.4.6.2.1.1.1
		fkV2McastIPTvSubscriberId OBJECT-TYPE
			SYNTAX Integer32 (1..65535)
			MAX-ACCESS read-only
			STATUS current
			DESCRIPTION
				"The subscriber's ID"
			::= { fkV2McastIPTvSubscriberEntry 1 }

		
		-- 1.3.6.1.4.1.10428 9 1.102.12.4.6.2.1.1.2
		fkV2McastIPTvSubscriberPortType OBJECT-TYPE
			SYNTAX INTEGER
				{
				physical(1),
				logical(2)
				}
			MAX-ACCESS read-only
			STATUS current
			DESCRIPTION
				"The port type. Logical(2) means trunk."
			::= { fkV2McastIPTvSubscriberEntry 2 }

		
		-- 1.3.6.1.4.1.10428 9 1.102.12.4.6.2.1.1.3
		fkV2McastIPTvSubscriberSlotId OBJECT-TYPE
			SYNTAX INTEGER (0..65535)
			MAX-ACCESS read-only
			STATUS current
			DESCRIPTION
				"The slot number"
			::= { fkV2McastIPTvSubscriberEntry 3 }

		
		-- 1.3.6.1.4.1.10428 9 1.102.12.4.6.2.1.1.4
		fkV2McastIPTvSubscriberPortId OBJECT-TYPE
			SYNTAX INTEGER (0..65535)
			MAX-ACCESS read-only
			STATUS current
			DESCRIPTION
				"The port number of slot (1 ~ 65535)"
			::= { fkV2McastIPTvSubscriberEntry 4 }

		
		-- 1.3.6.1.4.1.10428 9 1.102.12.4.6.2.1.1.5
		fkV2McastIPTvSubscriberCTag OBJECT-TYPE
			SYNTAX INTEGER (0..65535)
			MAX-ACCESS read-only
			STATUS current
			DESCRIPTION
				"C-VLAN number"
			::= { fkV2McastIPTvSubscriberEntry 5 }

		
		-- 1.3.6.1.4.1.10428 9 1.102.12.4.6.2.1.1.6
		fkV2McastIPTvSubscriberIpAddr OBJECT-TYPE
			SYNTAX IpAddress
			MAX-ACCESS read-only
			STATUS current
			DESCRIPTION
				"Subscriber IP address"
			::= { fkV2McastIPTvSubscriberEntry 6 }

		
		-- 1.3.6.1.4.1.10428 9 1.102.12.4.6.2.1.1.7
		fkV2McastIPTvSubscriberStatus OBJECT-TYPE
			SYNTAX INTEGER
				{
				active(1),
				inactive(2)
				}
			MAX-ACCESS read-only
			STATUS current
			DESCRIPTION
				"The status of subscriber"
			::= { fkV2McastIPTvSubscriberEntry 7 }

		
		-- 1.3.6.1.4.1.10428 9 1.102.12.4.6.2.1.1.8
		fkV2McastIPTvSubscriberCacProfileId OBJECT-TYPE
			SYNTAX INTEGER (0..65535)
			MAX-ACCESS read-only
			STATUS current
			DESCRIPTION
				"CAC profile id"
			::= { fkV2McastIPTvSubscriberEntry 8 }

		
		-- 1.3.6.1.4.1.10428 9 1.102.12.4.6.2.1.1.9
		fkV2McastIPTvSubscriberPackageCnt OBJECT-TYPE
			SYNTAX INTEGER (0..65535)
			MAX-ACCESS read-only
			STATUS current
			DESCRIPTION
				"The number of subscriber package"
			::= { fkV2McastIPTvSubscriberEntry 9 }

		
		-- 1.3.6.1.4.1.10428 9 1.102.12.4.6.2.1.1.10
		fkV2McastIPTvSubscriberDescription OBJECT-TYPE
			SYNTAX OCTET STRING
			MAX-ACCESS read-write
			STATUS current
			DESCRIPTION
				"The description about subscriber."
			::= { fkV2McastIPTvSubscriberEntry 10 }

		
		-- 1.3.6.1.4.1.10428 9 1.102.12.4.6.2.2
		fkV2McastIPTvSubscriberPackageTable OBJECT-TYPE
			SYNTAX SEQUENCE OF FkV2McastIPTvSubscriberPackageEntry
			MAX-ACCESS not-accessible
			STATUS current
			DESCRIPTION
				"multicast IPTv subscriber package table."
			::= { fkV2McastIPTvSubscriberMgmt 2 }

		
		-- 1.3.6.1.4.1.10428 9 1.102.12.4.6.2.2.1
		fkV2McastIPTvSubscriberPackageEntry OBJECT-TYPE
			SYNTAX FkV2McastIPTvSubscriberPackageEntry
			MAX-ACCESS not-accessible
			STATUS current
			DESCRIPTION
				"key: fkV2McastIPTvSubscriberId, fkV2McastIPTvSubscriberPackageId"
			INDEX { fkV2McastIPTvSubscriberId, fkV2McastIPTvSubscriberPackageId }
			::= { fkV2McastIPTvSubscriberPackageTable 1 }

		
		FkV2McastIPTvSubscriberPackageEntry ::=
			SEQUENCE { 
				fkV2McastIPTvSubscriberPackageId
					Integer32,
				fkV2McastIPTvSubscriberPackageStart
					OCTET STRING,
				fkV2McastIPTvSubscriberPackageEnd
					OCTET STRING
			 }

		-- 1.3.6.1.4.1.10428 9 1.102.12.4.6.2.2.1.1
		fkV2McastIPTvSubscriberPackageId OBJECT-TYPE
			SYNTAX Integer32 (1..65535)
			MAX-ACCESS read-only
			STATUS current
			DESCRIPTION
				"The packageId of a certain subscriber"
			::= { fkV2McastIPTvSubscriberPackageEntry 1 }

		
		-- 1.3.6.1.4.1.10428 9 1.102.12.4.6.2.2.1.2
		fkV2McastIPTvSubscriberPackageStart OBJECT-TYPE
			SYNTAX OCTET STRING
			MAX-ACCESS read-only
			STATUS current
			DESCRIPTION
				"Start time when package list becomes effective to  subscriber
				Format : hh:mm"
			::= { fkV2McastIPTvSubscriberPackageEntry 2 }

		
		-- 1.3.6.1.4.1.10428 9 1.102.12.4.6.2.2.1.3
		fkV2McastIPTvSubscriberPackageEnd OBJECT-TYPE
			SYNTAX OCTET STRING
			MAX-ACCESS read-only
			STATUS current
			DESCRIPTION
				"End time when package list becomes invalid to subscriber
				Format : hh:mm"
			::= { fkV2McastIPTvSubscriberPackageEntry 3 }

		
		-- 1.3.6.1.4.1.10428 9 1.102.12.4.6.2.3
		fkV2McastIPTvSubscriberControl OBJECT IDENTIFIER ::= { fkV2McastIPTvSubscriberMgmt 3 }

		
		-- 1.3.6.1.4.1.10428 9 1.102.12.4.6.2.3.1
		fkV2McastIPTvSubscriberControlRequest OBJECT-TYPE
			SYNTAX INTEGER
				{
				createSubscriber(1),
				updateSubscriber(2),
				deleteSubscriber(3),
				addSubscriberPackage(4),
				removeSubscriberPackage(5),
				suspendSubscriber(6),
				resumeSubscriber(7),
				setSubscriberDescription(8)
				}
			MAX-ACCESS read-write
			STATUS current
			DESCRIPTION
				"The request of a user command"
			::= { fkV2McastIPTvSubscriberControl 1 }

		
		-- 1.3.6.1.4.1.10428 9 1.102.12.4.6.2.3.2
		fkV2McastIPTvSubscriberControlStatus OBJECT-TYPE
			SYNTAX FkControlStatusType
			MAX-ACCESS read-only
			STATUS current
			DESCRIPTION
				"The status of user command"
			::= { fkV2McastIPTvSubscriberControl 2 }

		
		-- 1.3.6.1.4.1.10428 9 1.102.12.4.6.2.3.3
		fkV2McastIPTvSubscriberControlTimer OBJECT-TYPE
			SYNTAX Gauge32
			MAX-ACCESS read-write
			STATUS current
			DESCRIPTION
				"The maximum time for the manager for a long running user command"
			::= { fkV2McastIPTvSubscriberControl 3 }

		
		-- 1.3.6.1.4.1.10428 9 1.102.12.4.6.2.3.4
		fkV2McastIPTvSubscriberControlTimeStamp OBJECT-TYPE
			SYNTAX TimeStamp
			MAX-ACCESS read-only
			STATUS current
			DESCRIPTION
				"The time stamp of the last command(end of command)"
			::= { fkV2McastIPTvSubscriberControl 4 }

		
		-- 1.3.6.1.4.1.10428 9 1.102.12.4.6.2.3.5
		fkV2McastIPTvSubscriberControlReqResult OBJECT-TYPE
			SYNTAX FkControlRequestResultType
			MAX-ACCESS read-only
			STATUS current
			DESCRIPTION
				"The result of the last user command"
			::= { fkV2McastIPTvSubscriberControl 5 }

		
		-- 1.3.6.1.4.1.10428 9 1.102.12.4.6.2.3.6
		fkV2McastIPTvSubscriberControlId OBJECT-TYPE
			SYNTAX INTEGER (0..65535)
			MAX-ACCESS read-write
			STATUS current
			DESCRIPTION
				"The subscriber's ID"
			::= { fkV2McastIPTvSubscriberControl 6 }

		
		-- 1.3.6.1.4.1.10428 9 1.102.12.4.6.2.3.7
		fkV2McastIPTvSubscriberControlPortType OBJECT-TYPE
			SYNTAX INTEGER
				{
				physical(1),
				logical(2)
				}
			MAX-ACCESS read-write
			STATUS current
			DESCRIPTION
				"The port type. Logical(2) means trunk."
			::= { fkV2McastIPTvSubscriberControl 7 }

		
		-- 1.3.6.1.4.1.10428 9 1.102.12.4.6.2.3.8
		fkV2McastIPTvSubscriberControlSlotId OBJECT-TYPE
			SYNTAX INTEGER (0..65535)
			MAX-ACCESS read-write
			STATUS current
			DESCRIPTION
				"The slot number"
			::= { fkV2McastIPTvSubscriberControl 8 }

		
		-- 1.3.6.1.4.1.10428 9 1.102.12.4.6.2.3.9
		fkV2McastIPTvSubscriberControlPortId OBJECT-TYPE
			SYNTAX INTEGER (0..65535)
			MAX-ACCESS read-write
			STATUS current
			DESCRIPTION
				"The port number of slot (1 ~ 65535)"
			::= { fkV2McastIPTvSubscriberControl 9 }

		
		-- 1.3.6.1.4.1.10428 9 1.102.12.4.6.2.3.10
		fkV2McastIPTvSubscriberControlCTag OBJECT-TYPE
			SYNTAX INTEGER (0..65535)
			MAX-ACCESS read-write
			STATUS current
			DESCRIPTION
				"C-VLAN number"
			::= { fkV2McastIPTvSubscriberControl 10 }

		
		-- 1.3.6.1.4.1.10428 9 1.102.12.4.6.2.3.11
		fkV2McastIPTvSubscriberControlIpAddr OBJECT-TYPE
			SYNTAX IpAddress
			MAX-ACCESS read-write
			STATUS current
			DESCRIPTION
				"Subscriber IP address"
			::= { fkV2McastIPTvSubscriberControl 11 }

		
		-- 1.3.6.1.4.1.10428 9 1.102.12.4.6.2.3.12
		fkV2McastIPTvSubscriberControlCacProfileId OBJECT-TYPE
			SYNTAX INTEGER (0..65535)
			MAX-ACCESS read-write
			STATUS current
			DESCRIPTION
				"CAC profile id"
			::= { fkV2McastIPTvSubscriberControl 12 }

		
		-- 1.3.6.1.4.1.10428 9 1.102.12.4.6.2.3.13
		fkV2McastIPTvSubscriberControlPackageCnt OBJECT-TYPE
			SYNTAX INTEGER (0..65535)
			MAX-ACCESS read-write
			STATUS current
			DESCRIPTION
				"The number of subscriber package"
			::= { fkV2McastIPTvSubscriberControl 13 }

		
		-- 1.3.6.1.4.1.10428 9 1.102.12.4.6.2.3.14
		fkV2McastIPTvSubscriberControlPackageList OBJECT-TYPE
			SYNTAX OCTET STRING
			MAX-ACCESS read-write
			STATUS current
			DESCRIPTION
				"Package list (each value length 4byte)"
			::= { fkV2McastIPTvSubscriberControl 14 }

		
		-- 1.3.6.1.4.1.10428 9 1.102.12.4.6.2.3.15
		fkV2McastIPTvSubscriberControlPackageTimeList OBJECT-TYPE
			SYNTAX OCTET STRING
			MAX-ACCESS read-write
			STATUS current
			DESCRIPTION
				"Start time when package list becomes effective to  subscriber (4byte)
				End time when package list becomes invalid to subscriber (4byte)
				(each value length 8byte)"
			::= { fkV2McastIPTvSubscriberControl 15 }

		
		-- 1.3.6.1.4.1.10428 9 1.102.12.4.6.2.3.16
		fkV2McastIPTvSubscriberControlDescription OBJECT-TYPE
			SYNTAX OCTET STRING
			MAX-ACCESS read-write
			STATUS current
			DESCRIPTION
				"The description about subscriber."
			::= { fkV2McastIPTvSubscriberControl 16 }

		
		-- 1.3.6.1.4.1.10428 9 1.102.12.4.6.2.4
		fkV2McastIPTvSubscriberNotification OBJECT IDENTIFIER ::= { fkV2McastIPTvSubscriberMgmt 4 }

		
		-- 1.3.6.1.4.1.10428 9 1.102.12.4.6.2.4.1
		fkV2McastIPTvSubscriberCreated NOTIFICATION-TYPE
			OBJECTS { fkV2McastIPTvSubscriberControlRequest, fkV2McastIPTvSubscriberControlTimeStamp, fkV2McastIPTvSubscriberControlReqResult, fkV2McastIPTvSubscriberControlId, fkV2McastIPTvSubscriberControlPortType, 
				fkV2McastIPTvSubscriberControlSlotId, fkV2McastIPTvSubscriberControlPortId, fkV2McastIPTvSubscriberControlCTag, fkV2McastIPTvSubscriberControlIpAddr, fkV2McastIPTvSubscriberControlCacProfileId, 
				fkV2McastIPTvSubscriberControlDescription }
			STATUS current
			DESCRIPTION 
				"Description."
			::= { fkV2McastIPTvSubscriberNotification 1 }

		
		-- 1.3.6.1.4.1.10428 9 1.102.12.4.6.2.4.2
		fkV2McastIPTvSubscriberChanged NOTIFICATION-TYPE
			OBJECTS { fkV2McastIPTvSubscriberControlRequest, fkV2McastIPTvSubscriberControlTimeStamp, fkV2McastIPTvSubscriberControlReqResult, fkV2McastIPTvSubscriberControlId, fkV2McastIPTvSubscriberControlPortType, 
				fkV2McastIPTvSubscriberControlSlotId, fkV2McastIPTvSubscriberControlPortId, fkV2McastIPTvSubscriberControlCTag, fkV2McastIPTvSubscriberControlIpAddr, fkV2McastIPTvSubscriberControlCacProfileId
				 }
			STATUS current
			DESCRIPTION 
				"Description."
			::= { fkV2McastIPTvSubscriberNotification 2 }

		
		-- 1.3.6.1.4.1.10428 9 1.102.12.4.6.2.4.3
		fkV2McastIPTvSubscriberDeleted NOTIFICATION-TYPE
			OBJECTS { fkV2McastIPTvSubscriberControlRequest, fkV2McastIPTvSubscriberControlTimeStamp, fkV2McastIPTvSubscriberControlReqResult, fkV2McastIPTvSubscriberControlId }
			STATUS current
			DESCRIPTION 
				"Description."
			::= { fkV2McastIPTvSubscriberNotification 3 }

		
		-- 1.3.6.1.4.1.10428 9 1.102.12.4.6.2.4.4
		fkV2McastIPTvSubscriberAddPackage NOTIFICATION-TYPE
			OBJECTS { fkV2McastIPTvSubscriberControlRequest, fkV2McastIPTvSubscriberControlTimeStamp, fkV2McastIPTvSubscriberControlPackageCnt, fkV2McastIPTvSubscriberControlReqResult, fkV2McastIPTvChannelControlId
				 }
			STATUS current
			DESCRIPTION 
				"Description."
			::= { fkV2McastIPTvSubscriberNotification 4 }

		
		-- 1.3.6.1.4.1.10428 9 1.102.12.4.6.2.4.5
		fkV2McastIPTvSubscriberRemovePackage NOTIFICATION-TYPE
			OBJECTS { fkV2McastIPTvSubscriberControlRequest, fkV2McastIPTvSubscriberControlTimeStamp, fkV2McastIPTvSubscriberControlReqResult, fkV2McastIPTvSubscriberControlId, fkV2McastIPTvSubscriberControlPackageCnt
				 }
			STATUS current
			DESCRIPTION 
				"Description."
			::= { fkV2McastIPTvSubscriberNotification 5 }

		
		-- 1.3.6.1.4.1.10428 9 1.102.12.4.6.2.4.6
		fkV2McastIPTvSubscriberSuspend NOTIFICATION-TYPE
			OBJECTS { fkV2McastIPTvSubscriberControlRequest, fkV2McastIPTvSubscriberControlTimeStamp, fkV2McastIPTvSubscriberControlReqResult, fkV2McastIPTvSubscriberControlId }
			STATUS current
			DESCRIPTION 
				"Description."
			::= { fkV2McastIPTvSubscriberNotification 6 }

		
		-- 1.3.6.1.4.1.10428 9 1.102.12.4.6.2.4.7
		fkV2McastIPTvSubscriberResume NOTIFICATION-TYPE
			OBJECTS { fkV2McastIPTvSubscriberControlRequest, fkV2McastIPTvSubscriberControlTimeStamp, fkV2McastIPTvSubscriberControlReqResult, fkV2McastIPTvSubscriberControlId }
			STATUS current
			DESCRIPTION 
				"Description."
			::= { fkV2McastIPTvSubscriberNotification 7 }

		
		-- 1.3.6.1.4.1.10428 9 1.102.12.4.6.2.4.8
		fkV2McastIPTvSubscriberDescChanged NOTIFICATION-TYPE
			OBJECTS { fkV2McastIPTvSubscriberControlRequest, fkV2McastIPTvSubscriberControlTimeStamp, fkV2McastIPTvSubscriberControlReqResult, fkV2McastIPTvSubscriberControlId, fkV2McastIPTvSubscriberControlDescription
				 }
			STATUS current
			DESCRIPTION 
				"Description."
			::= { fkV2McastIPTvSubscriberNotification 8 }

		
		-- 1.3.6.1.4.1.10428 9 1.102.12.4.6.3
		fkV2McastIPTvSubscriberHistory OBJECT IDENTIFIER ::= { fkV2McastIPTvSubscriber 3 }

		
		-- 1.3.6.1.4.1.10428 9 1.102.12.4.6.3.1
		fkV2McastIPTvSubscriberHistoryTable OBJECT-TYPE
			SYNTAX SEQUENCE OF FkV2McastIPTvSubscriberHistoryEntry
			MAX-ACCESS not-accessible
			STATUS current
			DESCRIPTION
				"multicast IPTV subscriber history table."
			::= { fkV2McastIPTvSubscriberHistory 1 }

		
		-- 1.3.6.1.4.1.10428 9 1.102.12.4.6.3.1.1
		fkV2McastIPTvSubscriberHistoryEntry OBJECT-TYPE
			SYNTAX FkV2McastIPTvSubscriberHistoryEntry
			MAX-ACCESS not-accessible
			STATUS current
			DESCRIPTION
				"key: fkV2McastIPTvSubscriberId, fkV2McastIPTvSubscriberHistoryIndex"
			INDEX { fkV2McastIPTvSubscriberId, fkV2McastIPTvSubscriberHistoryIndex }
			::= { fkV2McastIPTvSubscriberHistoryTable 1 }

		
		FkV2McastIPTvSubscriberHistoryEntry ::=
			SEQUENCE { 
				fkV2McastIPTvSubscriberHistoryIndex
					Integer32,
				fkV2McastIPTvSubscriberHistoryJoinedChannelId
					INTEGER,
				fkV2McastIPTvSubscriberHistoryJoinedTime
					OCTET STRING
			 }

		-- 1.3.6.1.4.1.10428 9 1.102.12.4.6.3.1.1.1
		fkV2McastIPTvSubscriberHistoryIndex OBJECT-TYPE
			SYNTAX Integer32 (1..65535)
			MAX-ACCESS read-only
			STATUS current
			DESCRIPTION
				"The index of subscriber's history.A25"
			::= { fkV2McastIPTvSubscriberHistoryEntry 1 }

		
		-- 1.3.6.1.4.1.10428 9 1.102.12.4.6.3.1.1.2
		fkV2McastIPTvSubscriberHistoryJoinedChannelId OBJECT-TYPE
			SYNTAX INTEGER (0..65535)
			MAX-ACCESS read-only
			STATUS current
			DESCRIPTION
				"same as fkV2McastIPTvChannelId"
			::= { fkV2McastIPTvSubscriberHistoryEntry 2 }

		
		-- 1.3.6.1.4.1.10428 9 1.102.12.4.6.3.1.1.3
		fkV2McastIPTvSubscriberHistoryJoinedTime OBJECT-TYPE
			SYNTAX OCTET STRING
			MAX-ACCESS read-only
			STATUS current
			DESCRIPTION
				"The Joined Time of channel."
			::= { fkV2McastIPTvSubscriberHistoryEntry 3 }

		
		-- 1.3.6.1.4.1.10428 9 1.102.12.4.6.3.2
		fkV2McastIPTvSubscriberHistoryControl OBJECT IDENTIFIER ::= { fkV2McastIPTvSubscriberHistory 2 }

		
		-- 1.3.6.1.4.1.10428 9 1.102.12.4.6.3.2.1
		fkV2McastIPTvSubscriberHistoryControlRequest OBJECT-TYPE
			SYNTAX INTEGER { clearSubscriberHistory(1) }
			MAX-ACCESS read-write
			STATUS current
			DESCRIPTION
				"The request of a user command"
			::= { fkV2McastIPTvSubscriberHistoryControl 1 }

		
		-- 1.3.6.1.4.1.10428 9 1.102.12.4.6.3.2.2
		fkV2McastIPTvSubscriberHistoryControlStatus OBJECT-TYPE
			SYNTAX FkControlStatusType
			MAX-ACCESS read-only
			STATUS current
			DESCRIPTION
				"The status of user command"
			::= { fkV2McastIPTvSubscriberHistoryControl 2 }

		
		-- 1.3.6.1.4.1.10428 9 1.102.12.4.6.3.2.3
		fkV2McastIPTvSubscriberHistoryControlTimer OBJECT-TYPE
			SYNTAX Gauge32
			MAX-ACCESS read-write
			STATUS current
			DESCRIPTION
				"The maximum time for the manager for a long running user command"
			::= { fkV2McastIPTvSubscriberHistoryControl 3 }

		
		-- 1.3.6.1.4.1.10428 9 1.102.12.4.6.3.2.4
		fkV2McastIPTvSubscriberHistoryControlTimeStamp OBJECT-TYPE
			SYNTAX TimeStamp
			MAX-ACCESS read-only
			STATUS current
			DESCRIPTION
				"The time stamp of the last command(end of command)"
			::= { fkV2McastIPTvSubscriberHistoryControl 4 }

		
		-- 1.3.6.1.4.1.10428 9 1.102.12.4.6.3.2.5
		fkV2McastIPTvSubscriberHistoryControlReqResult OBJECT-TYPE
			SYNTAX FkControlRequestResultType
			MAX-ACCESS read-only
			STATUS current
			DESCRIPTION
				"The result of the last user command"
			::= { fkV2McastIPTvSubscriberHistoryControl 5 }

		
		-- 1.3.6.1.4.1.10428 9 1.102.12.4.6.3.2.6
		fkV2McastIPTvSubscriberHistoryControlId OBJECT-TYPE
			SYNTAX INTEGER (0..65535)
			MAX-ACCESS read-write
			STATUS current
			DESCRIPTION
				"The index of subscriber's history.A25"
			::= { fkV2McastIPTvSubscriberHistoryControl 6 }

		
		-- 1.3.6.1.4.1.10428 9 1.102.12.4.6.3.4
		fkV2McastIPTvSubscriberHistoryNotification OBJECT IDENTIFIER ::= { fkV2McastIPTvSubscriberHistory 4 }

		
		-- 1.3.6.1.4.1.10428 9 1.102.12.4.6.3.4.1
		fkV2McastIPTvSubscriberHistoryCleared NOTIFICATION-TYPE
			OBJECTS { fkV2McastIPTvSubscriberHistoryControlRequest, fkV2McastIPTvSubscriberHistoryControlTimeStamp, fkV2McastIPTvSubscriberHistoryControlReqResult, fkV2McastIPTvSubscriberControlId }
			STATUS current
			DESCRIPTION 
				"Description."
			::= { fkV2McastIPTvSubscriberHistoryNotification 1 }

		
		-- 1.3.6.1.4.1.10428 9 1.102.12.4.7
		fkV2McastIPTvCDR OBJECT IDENTIFIER ::= { fkV2McastIPTvMgmt 7 }

		
		-- 1.3.6.1.4.1.10428 9 1.102.12.4.7.1
		fkV2McastIPTvCDRBase OBJECT IDENTIFIER ::= { fkV2McastIPTvCDR 1 }

		
		-- 1.3.6.1.4.1.10428 9 1.102.12.4.7.1.1
		fkV2McastIPTvCDRInfo OBJECT IDENTIFIER ::= { fkV2McastIPTvCDRBase 1 }

		
		-- 1.3.6.1.4.1.10428 9 1.102.12.4.7.1.1.1
		fkV2McastIPTvCDRInfoStatus OBJECT-TYPE
			SYNTAX INTEGER
				{
				enable(1),
				disable(2)
				}
			MAX-ACCESS read-only
			STATUS current
			DESCRIPTION
				"indicate if the CDR logging is enabled or not"
			::= { fkV2McastIPTvCDRInfo 1 }

		
		-- 1.3.6.1.4.1.10428 9 1.102.12.4.7.1.1.2
		fkV2McastIPTvCDRInfoKeepJoinInterval OBJECT-TYPE
			SYNTAX INTEGER (1..1440)
			UNITS "1 minute"
			MAX-ACCESS read-only
			STATUS current
			DESCRIPTION
				"keeped-join interval  <1-1440>"
			::= { fkV2McastIPTvCDRInfo 2 }

		
		-- 1.3.6.1.4.1.10428 9 1.102.12.4.7.1.1.3
		fkV2McastIPTvCDRInfoLogFileName OBJECT-TYPE
			SYNTAX OCTET STRING
			MAX-ACCESS read-only
			STATUS current
			DESCRIPTION
				"CDR DB file name."
			::= { fkV2McastIPTvCDRInfo 3 }

		
		-- 1.3.6.1.4.1.10428 9 1.102.12.4.7.1.1.4
		fkV2McastIPTvCDRInfoLogSize OBJECT-TYPE
			SYNTAX INTEGER (1..1000)
			UNITS "1 KB"
			MAX-ACCESS read-only
			STATUS current
			DESCRIPTION
				"CDR DB Log size <1-1000>"
			::= { fkV2McastIPTvCDRInfo 4 }

		
		-- 1.3.6.1.4.1.10428 9 1.102.12.4.7.1.1.5
		fkV2McastIPTvCDRInfoExportTimeThreshold OBJECT-TYPE
			SYNTAX OCTET STRING
			MAX-ACCESS read-only
			STATUS current
			DESCRIPTION
				"The time threshold of CDR export. Format: [0-52]w[0-6]d[0-23]h"
			::= { fkV2McastIPTvCDRInfo 5 }

		
		-- 1.3.6.1.4.1.10428 9 1.102.12.4.7.1.1.6
		fkV2McastIPTvCDRInfoExportTimeBegin OBJECT-TYPE
			SYNTAX OCTET STRING
			MAX-ACCESS read-only
			STATUS current
			DESCRIPTION
				"The begin time of CDR export.  Format : hh:mm"
			::= { fkV2McastIPTvCDRInfo 6 }

		
		-- 1.3.6.1.4.1.10428 9 1.102.12.4.7.1.1.7
		fkV2McastIPTvCDRInfoExportAmountThreshold OBJECT-TYPE
			SYNTAX INTEGER (1..100)
			UNITS "1 %"
			MAX-ACCESS read-only
			STATUS current
			DESCRIPTION
				"The amount threshold of CDR export. <1-100>  unit : 1 %"
			::= { fkV2McastIPTvCDRInfo 7 }

		
		-- 1.3.6.1.4.1.10428 9 1.102.12.4.7.1.1.8
		fkV2McastIPTvCDRInfoSyslogPriority OBJECT-TYPE
			SYNTAX INTEGER
				{
				none(0),
				emerg(1),
				alert(2),
				crit(3),
				err(4),
				warning(5),
				notice(6),
				info(7),
				debug(8)
				}
			MAX-ACCESS read-only
			STATUS current
			DESCRIPTION
				"The priority of CDR syslog.
				0 means syslog-disabled."
			::= { fkV2McastIPTvCDRInfo 8 }

		
		-- 1.3.6.1.4.1.10428 9 1.102.12.4.7.1.1.9
		fkV2McastIPTvCDRInfoANInfo OBJECT-TYPE
			SYNTAX OCTET STRING
			MAX-ACCESS read-only
			STATUS current
			DESCRIPTION
				"The interface that include AN(Exporter) IP address.  Always use a primary IP address.
				It can be IP address of exporter"
			::= { fkV2McastIPTvCDRInfo 9 }

		
		-- 1.3.6.1.4.1.10428 9 1.102.12.4.7.1.2
		fkV2McastIPTvCDRInfoControl OBJECT IDENTIFIER ::= { fkV2McastIPTvCDRBase 2 }

		
		-- 1.3.6.1.4.1.10428 9 1.102.12.4.7.1.2.1
		fkV2McastIPTvCDRInfoControlRequest OBJECT-TYPE
			SYNTAX INTEGER
				{
				setCDRStatus(1),
				setCDREventProfile(2),
				setCDRLogFileProfile(3),
				setCDRExportProfile(4),
				setCDRSyslogPriority(5)
				}
			MAX-ACCESS read-write
			STATUS current
			DESCRIPTION
				"The request of a user command"
			::= { fkV2McastIPTvCDRInfoControl 1 }

		
		-- 1.3.6.1.4.1.10428 9 1.102.12.4.7.1.2.2
		fkV2McastIPTvCDRInfoControlStatus OBJECT-TYPE
			SYNTAX FkControlStatusType
			MAX-ACCESS read-only
			STATUS current
			DESCRIPTION
				"The status of user command"
			::= { fkV2McastIPTvCDRInfoControl 2 }

		
		-- 1.3.6.1.4.1.10428 9 1.102.12.4.7.1.2.3
		fkV2McastIPTvCDRInfoControlTimer OBJECT-TYPE
			SYNTAX Gauge32
			MAX-ACCESS read-write
			STATUS current
			DESCRIPTION
				"The maximum time for the manager for a long running user command"
			::= { fkV2McastIPTvCDRInfoControl 3 }

		
		-- 1.3.6.1.4.1.10428 9 1.102.12.4.7.1.2.4
		fkV2McastIPTvCDRInfoControlTimeStamp OBJECT-TYPE
			SYNTAX TimeStamp
			MAX-ACCESS read-only
			STATUS current
			DESCRIPTION
				"The time stamp of the last command(end of command)"
			::= { fkV2McastIPTvCDRInfoControl 4 }

		
		-- 1.3.6.1.4.1.10428 9 1.102.12.4.7.1.2.5
		fkV2McastIPTvCDRInfoControlReqResult OBJECT-TYPE
			SYNTAX FkControlRequestResultType
			MAX-ACCESS read-only
			STATUS current
			DESCRIPTION
				"The result of the last user command"
			::= { fkV2McastIPTvCDRInfoControl 5 }

		
		-- 1.3.6.1.4.1.10428 9 1.102.12.4.7.1.2.6
		fkV2McastIPTvCDRInfoContorlStatus OBJECT-TYPE
			SYNTAX INTEGER
				{
				enable(1),
				disable(2)
				}
			MAX-ACCESS read-write
			STATUS current
			DESCRIPTION
				"indicate if the CDR logging is enabled or not"
			::= { fkV2McastIPTvCDRInfoControl 6 }

		
		-- 1.3.6.1.4.1.10428 9 1.102.12.4.7.1.2.7
		fkV2McastIPTvCDRInfoContorlKeepJoinInterval OBJECT-TYPE
			SYNTAX INTEGER (1..1440)
			UNITS "1 minute"
			MAX-ACCESS read-write
			STATUS current
			DESCRIPTION
				"keeped-join interval  <1-1440>"
			::= { fkV2McastIPTvCDRInfoControl 7 }

		
		-- 1.3.6.1.4.1.10428 9 1.102.12.4.7.1.2.8
		fkV2McastIPTvCDRInfoContorlLogFileName OBJECT-TYPE
			SYNTAX OCTET STRING
			MAX-ACCESS read-write
			STATUS current
			DESCRIPTION
				"CDR DB file name."
			::= { fkV2McastIPTvCDRInfoControl 8 }

		
		-- 1.3.6.1.4.1.10428 9 1.102.12.4.7.1.2.9
		fkV2McastIPTvCDRInfoControlLogSize OBJECT-TYPE
			SYNTAX INTEGER (1..1000)
			UNITS "1 KB"
			MAX-ACCESS read-write
			STATUS current
			DESCRIPTION
				"CDR DB Log size <1-1000>"
			::= { fkV2McastIPTvCDRInfoControl 9 }

		
		-- 1.3.6.1.4.1.10428 9 1.102.12.4.7.1.2.10
		fkV2McastIPTvCDRInfoControlExportTimeThreshold OBJECT-TYPE
			SYNTAX OCTET STRING
			MAX-ACCESS read-write
			STATUS current
			DESCRIPTION
				"The time threshold of CDR export. Format: [0-52]w[0-6]d[0-23]h"
			::= { fkV2McastIPTvCDRInfoControl 10 }

		
		-- 1.3.6.1.4.1.10428 9 1.102.12.4.7.1.2.11
		fkV2McastIPTvCDRInfoControlExportTimeBegin OBJECT-TYPE
			SYNTAX OCTET STRING
			MAX-ACCESS read-write
			STATUS current
			DESCRIPTION
				"The begin time of CDR export. Format : hh:mm"
			::= { fkV2McastIPTvCDRInfoControl 11 }

		
		-- 1.3.6.1.4.1.10428 9 1.102.12.4.7.1.2.12
		fkV2McastIPTvCDRInfoControlExportAmountThreshold OBJECT-TYPE
			SYNTAX INTEGER (1..100)
			UNITS "1 %"
			MAX-ACCESS read-write
			STATUS current
			DESCRIPTION
				"The amount threshold of CDR export. <1-100>  unit : 1 %"
			::= { fkV2McastIPTvCDRInfoControl 12 }

		
		-- 1.3.6.1.4.1.10428 9 1.102.12.4.7.1.2.13
		fkV2McastIPTvCDRInfoControlSyslogPriority OBJECT-TYPE
			SYNTAX INTEGER
				{
				none(0),
				emerg(1),
				alert(2),
				crit(3),
				err(4),
				warning(5),
				notice(6),
				info(7),
				debug(8)
				}
			MAX-ACCESS read-write
			STATUS current
			DESCRIPTION
				"The priority of CDR syslog.
				0 means syslog-disabled."
			::= { fkV2McastIPTvCDRInfoControl 13 }

		
		-- 1.3.6.1.4.1.10428 9 1.102.12.4.7.1.2.14
		fkV2McastIPTvCDRInfoControlANInfo OBJECT-TYPE
			SYNTAX OCTET STRING
			MAX-ACCESS read-write
			STATUS current
			DESCRIPTION
				"The interface that include AN(Exporter) IP address.  Always use a primary IP address.
				It can be IP address of exporter"
			::= { fkV2McastIPTvCDRInfoControl 14 }
-- The interface that include AN(Exporter) IP address. Always use a primary IP address.
-- It can be IP address of exporter
		
		-- 1.3.6.1.4.1.10428 9 1.102.12.4.7.1.3
		fkV2McastIPTvCDRInfoNotification OBJECT IDENTIFIER ::= { fkV2McastIPTvCDRBase 3 }

		
		-- 1.3.6.1.4.1.10428 9 1.102.12.4.7.1.3.1
		fkV2McastIPTvCDRInfoStatusChanged NOTIFICATION-TYPE
			OBJECTS { fkV2McastIPTvCDRInfoControlRequest, fkV2McastIPTvCDRInfoControlTimeStamp, fkV2McastIPTvCDRInfoControlReqResult, fkV2McastIPTvCDRInfoControlStatus }
			STATUS current
			DESCRIPTION 
				"Description."
			::= { fkV2McastIPTvCDRInfoNotification 1 }

		
		-- 1.3.6.1.4.1.10428 9 1.102.12.4.7.1.3.2
		fkV2McastIPTvCDRInfoEventProfileChanged NOTIFICATION-TYPE
			OBJECTS { fkV2McastIPTvCDRInfoControlRequest, fkV2McastIPTvCDRInfoControlTimeStamp, fkV2McastIPTvCDRInfoControlReqResult, fkV2McastIPTvCDRInfoContorlKeepJoinInterval }
			STATUS current
			DESCRIPTION 
				"Description."
			::= { fkV2McastIPTvCDRInfoNotification 2 }

		
		-- 1.3.6.1.4.1.10428 9 1.102.12.4.7.1.3.3
		fkV2McastIPTvCDRInfoLogFileProfileChanged NOTIFICATION-TYPE
			OBJECTS { fkV2McastIPTvCDRInfoControlRequest, fkV2McastIPTvCDRInfoControlTimeStamp, fkV2McastIPTvCDRInfoControlReqResult, fkV2McastIPTvCDRInfoContorlLogFileName, fkV2McastIPTvCDRInfoControlLogSize
				 }
			STATUS current
			DESCRIPTION 
				"Description."
			::= { fkV2McastIPTvCDRInfoNotification 3 }

		
		-- 1.3.6.1.4.1.10428 9 1.102.12.4.7.1.3.4
		fkV2McastIPTvCDRInfoExportProfileChanged NOTIFICATION-TYPE
			OBJECTS { fkV2McastIPTvCDRInfoControlRequest, fkV2McastIPTvCDRInfoControlTimeStamp, fkV2McastIPTvCDRInfoControlReqResult, fkV2McastIPTvCDRInfoControlExportTimeThreshold, fkV2McastIPTvCDRInfoControlExportTimeBegin, 
				fkV2McastIPTvCDRInfoControlExportAmountThreshold, fkV2McastIPTvCDRInfoControlANInfo }
			STATUS current
			DESCRIPTION 
				"Description."
			::= { fkV2McastIPTvCDRInfoNotification 4 }

		
		-- 1.3.6.1.4.1.10428 9 1.102.12.4.7.1.3.5
		fkV2McastIPTvCDRInfoSyslogPriorityChanged NOTIFICATION-TYPE
			OBJECTS { fkV2McastIPTvCDRInfoControlRequest, fkV2McastIPTvCDRInfoControlTimeStamp, fkV2McastIPTvCDRInfoControlReqResult, fkV2McastIPTvCDRInfoControlSyslogPriority }
			STATUS current
			DESCRIPTION 
				"Description."
			::= { fkV2McastIPTvCDRInfoNotification 5 }

		
		-- 1.3.6.1.4.1.10428 9 1.102.12.4.7.2
		fkV2McastIPTvCDRLogServer OBJECT IDENTIFIER ::= { fkV2McastIPTvCDR 2 }

		
		-- 1.3.6.1.4.1.10428 9 1.102.12.4.7.2.1
		fkV2McastIPTvCDRLogServerTable OBJECT-TYPE
			SYNTAX SEQUENCE OF FkV2McastIPTvCDRLogServerEntry
			MAX-ACCESS not-accessible
			STATUS current
			DESCRIPTION
				"multicast IPTV CDR log server table."
			::= { fkV2McastIPTvCDRLogServer 1 }

		
		-- 1.3.6.1.4.1.10428 9 1.102.12.4.7.2.1.1
		fkV2McastIPTvCDRLogServerEntry OBJECT-TYPE
			SYNTAX FkV2McastIPTvCDRLogServerEntry
			MAX-ACCESS not-accessible
			STATUS current
			DESCRIPTION
				"key: fkV2McastIPTvCDRLogServerId"
			INDEX { fkV2McastIPTvCDRLogServerId }
			::= { fkV2McastIPTvCDRLogServerTable 1 }

		
		FkV2McastIPTvCDRLogServerEntry ::=
			SEQUENCE { 
				fkV2McastIPTvCDRLogServerId
					Integer32,
				fkV2McastIPTvCDRLogServerIpAddress
					IpAddress,
				fkV2McastIPTvCDRLogServerPort
					INTEGER,
				fkV2McastIPTvCDRLogServerMode
					INTEGER,
				fkV2McastIPTvCDRLogServerUserId
					OCTET STRING,
				fkV2McastIPTvCDRLogServerUserPassword
					OCTET STRING
			 }

		-- 1.3.6.1.4.1.10428 9 1.102.12.4.7.2.1.1.1
		fkV2McastIPTvCDRLogServerId OBJECT-TYPE
			SYNTAX Integer32 (1..65535)
			MAX-ACCESS read-only
			STATUS current
			DESCRIPTION
				"LogServer Id"
			::= { fkV2McastIPTvCDRLogServerEntry 1 }

		
		-- 1.3.6.1.4.1.10428 9 1.102.12.4.7.2.1.1.2
		fkV2McastIPTvCDRLogServerIpAddress OBJECT-TYPE
			SYNTAX IpAddress
			MAX-ACCESS read-only
			STATUS current
			DESCRIPTION
				"LogServer IP address"
			::= { fkV2McastIPTvCDRLogServerEntry 2 }

		
		-- 1.3.6.1.4.1.10428 9 1.102.12.4.7.2.1.1.3
		fkV2McastIPTvCDRLogServerPort OBJECT-TYPE
			SYNTAX INTEGER (0..65535)
			MAX-ACCESS read-only
			STATUS current
			DESCRIPTION
				"LogServer Layer4 Port."
			::= { fkV2McastIPTvCDRLogServerEntry 3 }

		
		-- 1.3.6.1.4.1.10428 9 1.102.12.4.7.2.1.1.4
		fkV2McastIPTvCDRLogServerMode OBJECT-TYPE
			SYNTAX INTEGER
				{
				ftp(1),
				tftp(2)
				}
			MAX-ACCESS read-only
			STATUS current
			DESCRIPTION
				"LogServer trasferring mode."
			::= { fkV2McastIPTvCDRLogServerEntry 4 }

		
		-- 1.3.6.1.4.1.10428 9 1.102.12.4.7.2.1.1.5
		fkV2McastIPTvCDRLogServerUserId OBJECT-TYPE
			SYNTAX OCTET STRING
			MAX-ACCESS read-only
			STATUS current
			DESCRIPTION
				"LogServer User Id"
			::= { fkV2McastIPTvCDRLogServerEntry 5 }

		
		-- 1.3.6.1.4.1.10428 9 1.102.12.4.7.2.1.1.6
		fkV2McastIPTvCDRLogServerUserPassword OBJECT-TYPE
			SYNTAX OCTET STRING
			MAX-ACCESS read-only
			STATUS current
			DESCRIPTION
				"LogServer User Password
				If user id is 'anony', user password must be 'anony'"
			::= { fkV2McastIPTvCDRLogServerEntry 6 }

		
		-- 1.3.6.1.4.1.10428 9 1.102.12.4.7.2.2
		fkV2McastIPTvCDRLogServerControl OBJECT IDENTIFIER ::= { fkV2McastIPTvCDRLogServer 2 }

		
		-- 1.3.6.1.4.1.10428 9 1.102.12.4.7.2.2.1
		fkV2McastIPTvCDRLogServerControlRequest OBJECT-TYPE
			SYNTAX INTEGER
				{
				createLogServer(1),
				deleteLogServer(2),
				uploadCDR(3),
				uploadCDRManual(4)
				}
			MAX-ACCESS read-write
			STATUS current
			DESCRIPTION
				"The request of a user command"
			::= { fkV2McastIPTvCDRLogServerControl 1 }

		
		-- 1.3.6.1.4.1.10428 9 1.102.12.4.7.2.2.2
		fkV2McastIPTvCDRLogServerControlStatus OBJECT-TYPE
			SYNTAX FkControlStatusType
			MAX-ACCESS read-only
			STATUS current
			DESCRIPTION
				"The status of user command"
			::= { fkV2McastIPTvCDRLogServerControl 2 }

		
		-- 1.3.6.1.4.1.10428 9 1.102.12.4.7.2.2.3
		fkV2McastIPTvCDRLogServerControlTimer OBJECT-TYPE
			SYNTAX Gauge32
			MAX-ACCESS read-write
			STATUS current
			DESCRIPTION
				"The maximum time for the manager for a long running user command"
			::= { fkV2McastIPTvCDRLogServerControl 3 }

		
		-- 1.3.6.1.4.1.10428 9 1.102.12.4.7.2.2.4
		fkV2McastIPTvCDRLogServerControlTimeStamp OBJECT-TYPE
			SYNTAX TimeStamp
			MAX-ACCESS read-only
			STATUS current
			DESCRIPTION
				"The time stamp of the last command(end of command)"
			::= { fkV2McastIPTvCDRLogServerControl 4 }

		
		-- 1.3.6.1.4.1.10428 9 1.102.12.4.7.2.2.5
		fkV2McastIPTvCDRLogServerControlReqResult OBJECT-TYPE
			SYNTAX FkControlRequestResultType
			MAX-ACCESS read-only
			STATUS current
			DESCRIPTION
				"The result of the last user command"
			::= { fkV2McastIPTvCDRLogServerControl 5 }

		
		-- 1.3.6.1.4.1.10428 9 1.102.12.4.7.2.2.6
		fkV2McastIPTvCDRLogServerControlId OBJECT-TYPE
			SYNTAX INTEGER (0..65535)
			MAX-ACCESS read-write
			STATUS current
			DESCRIPTION
				"LogServer Id"
			::= { fkV2McastIPTvCDRLogServerControl 6 }

		
		-- 1.3.6.1.4.1.10428 9 1.102.12.4.7.2.2.7
		fkV2McastIPTvCDRLogServerControlIpAddress OBJECT-TYPE
			SYNTAX IpAddress
			MAX-ACCESS read-write
			STATUS current
			DESCRIPTION
				"LogServer IP address"
			::= { fkV2McastIPTvCDRLogServerControl 7 }

		
		-- 1.3.6.1.4.1.10428 9 1.102.12.4.7.2.2.8
		fkV2McastIPTvCDRLogServerControlPort OBJECT-TYPE
			SYNTAX INTEGER (0..65535)
			MAX-ACCESS read-write
			STATUS current
			DESCRIPTION
				"LogServer Layer4 Port."
			::= { fkV2McastIPTvCDRLogServerControl 8 }

		
		-- 1.3.6.1.4.1.10428 9 1.102.12.4.7.2.2.9
		fkV2McastIPTvCDRLogServerControlMode OBJECT-TYPE
			SYNTAX INTEGER
				{
				ftp(1),
				tftp(2)
				}
			MAX-ACCESS read-write
			STATUS current
			DESCRIPTION
				"LogServer trasferring mode."
			::= { fkV2McastIPTvCDRLogServerControl 9 }

		
		-- 1.3.6.1.4.1.10428 9 1.102.12.4.7.2.2.10
		fkV2McastIPTvCDRLogServerControlUserId OBJECT-TYPE
			SYNTAX OCTET STRING
			MAX-ACCESS read-write
			STATUS current
			DESCRIPTION
				"LogServer User Id"
			::= { fkV2McastIPTvCDRLogServerControl 10 }

		
		-- 1.3.6.1.4.1.10428 9 1.102.12.4.7.2.2.11
		fkV2McastIPTvCDRLogServerControlUserPassword OBJECT-TYPE
			SYNTAX OCTET STRING
			MAX-ACCESS read-write
			STATUS current
			DESCRIPTION
				"LogServer User Password
				If user id is 'anony', user password must be 'anony'"
			::= { fkV2McastIPTvCDRLogServerControl 11 }

		
		-- 1.3.6.1.4.1.10428 9 1.102.12.4.7.2.2.12
		fkV2McastIPTvCDRLogServerControlFileName OBJECT-TYPE
			SYNTAX OCTET STRING
			MAX-ACCESS read-write
			STATUS current
			DESCRIPTION
				"remote CDR DB filename (default NULL)"
			::= { fkV2McastIPTvCDRLogServerControl 12 }

		
		-- 1.3.6.1.4.1.10428 9 1.102.12.4.7.2.3
		fkV2McastIPTvCDRLogServerNotification OBJECT IDENTIFIER ::= { fkV2McastIPTvCDRLogServer 3 }

		
		-- 1.3.6.1.4.1.10428 9 1.102.12.4.7.2.3.1
		fkV2McastIPTvCDRLogServerCreated NOTIFICATION-TYPE
			OBJECTS { fkV2McastIPTvCDRLogServerControlRequest, fkV2McastIPTvCDRLogServerControlTimeStamp, fkV2McastIPTvCDRLogServerControlReqResult, fkV2McastIPTvCDRLogServerControlId, fkV2McastIPTvCDRLogServerControlIpAddress, 
				fkV2McastIPTvCDRLogServerControlPort, fkV2McastIPTvCDRLogServerControlMode, fkV2McastIPTvCDRLogServerControlUserId, fkV2McastIPTvCDRLogServerControlUserPassword }
			STATUS current
			DESCRIPTION 
				"Description."
			::= { fkV2McastIPTvCDRLogServerNotification 1 }

		
		-- 1.3.6.1.4.1.10428 9 1.102.12.4.7.2.3.2
		fkV2McastIPTvCDRLogServerDeleted NOTIFICATION-TYPE
			OBJECTS { fkV2McastIPTvCDRLogServerControlRequest, fkV2McastIPTvCDRLogServerControlTimeStamp, fkV2McastIPTvCDRLogServerControlReqResult, fkV2McastIPTvCDRLogServerControlId }
			STATUS current
			DESCRIPTION 
				"Description."
			::= { fkV2McastIPTvCDRLogServerNotification 2 }

		
		-- 1.3.6.1.4.1.10428 9 1.102.12.4.7.2.3.3
		fkV2McastIPTvCDRLogServerUploadCDR NOTIFICATION-TYPE
			OBJECTS { fkV2McastIPTvCDRLogServerControlRequest, fkV2McastIPTvCDRLogServerControlTimeStamp, fkV2McastIPTvCDRLogServerControlReqResult, fkV2McastIPTvCDRLogServerControlId }
			STATUS current
			DESCRIPTION 
				"Description."
			::= { fkV2McastIPTvCDRLogServerNotification 3 }

		
		-- 1.3.6.1.4.1.10428 9 1.102.12.4.7.2.3.4
		fkV2McastIPTvCDRLogServerUploadCDRManual NOTIFICATION-TYPE
			OBJECTS { fkV2McastIPTvCDRLogServerControlRequest, fkV2McastIPTvCDRLogServerControlTimeStamp, fkV2McastIPTvCDRLogServerControlReqResult, fkV2McastIPTvCDRLogServerControlIpAddress, fkV2McastIPTvCDRLogServerControlPort, 
				fkV2McastIPTvCDRLogServerControlMode, fkV2McastIPTvCDRLogServerControlUserId, fkV2McastIPTvCDRLogServerControlUserPassword, fkV2McastIPTvCDRLogServerControlFileName }
			STATUS current
			DESCRIPTION 
				"Description."
			::= { fkV2McastIPTvCDRLogServerNotification 4 }

		
		-- 1.3.6.1.4.1.10428 9 1.102.12.4.7.3
		fkV2McastIPTvCDRStatistics OBJECT IDENTIFIER ::= { fkV2McastIPTvCDR 3 }

		
		-- 1.3.6.1.4.1.10428 9 1.102.12.4.7.3.1
		fkV2McastIPTvCDRLogStats OBJECT IDENTIFIER ::= { fkV2McastIPTvCDRStatistics 1 }

		
		-- 1.3.6.1.4.1.10428 9 1.102.12.4.7.3.1.1
		fkV2McastIPTvCDRLogStatsTotalCount OBJECT-TYPE
			SYNTAX INTEGER (0..65535)
			MAX-ACCESS read-only
			STATUS current
			DESCRIPTION
				"The total count of CDR logging"
			::= { fkV2McastIPTvCDRLogStats 1 }

		
		-- 1.3.6.1.4.1.10428 9 1.102.12.4.7.3.1.2
		fkV2McastIPTvCDRLogStatsJoinCount OBJECT-TYPE
			SYNTAX INTEGER (0..65535)
			MAX-ACCESS read-only
			STATUS current
			DESCRIPTION
				"The total count of CDR Join-logging"
			::= { fkV2McastIPTvCDRLogStats 2 }

		
		-- 1.3.6.1.4.1.10428 9 1.102.12.4.7.3.1.3
		fkV2McastIPTvCDRLogStatsKeepJoinedCount OBJECT-TYPE
			SYNTAX INTEGER (0..65535)
			MAX-ACCESS read-only
			STATUS current
			DESCRIPTION
				"The total count of CDR Keep-Joined-logging"
			::= { fkV2McastIPTvCDRLogStats 3 }

		
		-- 1.3.6.1.4.1.10428 9 1.102.12.4.7.3.1.4
		fkV2McastIPTvCDRLogStatsLeaveCount OBJECT-TYPE
			SYNTAX INTEGER (0..65535)
			MAX-ACCESS read-only
			STATUS current
			DESCRIPTION
				"The total count of CDR Leave-logging"
			::= { fkV2McastIPTvCDRLogStats 4 }

		
		-- 1.3.6.1.4.1.10428 9 1.102.12.4.7.3.1.5
		fkV2McastIPTvCDRLogStatsLastExportDate OBJECT-TYPE
			SYNTAX OCTET STRING
			MAX-ACCESS read-only
			STATUS current
			DESCRIPTION
				"The last logging date"
			::= { fkV2McastIPTvCDRLogStats 5 }

		
		-- 1.3.6.1.4.1.10428 9 1.102.12.4.7.3.1.6
		fkV2McastIPTvCDRLogStatsLastExportReason OBJECT-TYPE
			SYNTAX INTEGER
				{
				time(1),
				amount(2),
				manual(3)
				}
			MAX-ACCESS read-only
			STATUS current
			DESCRIPTION
				"The last logging reason"
			::= { fkV2McastIPTvCDRLogStats 6 }

		
		-- 1.3.6.1.4.1.10428 9 1.102.12.4.7.3.1.7
		fkV2McastIPTvCDRLogStatsLastExportServerList OBJECT-TYPE
			SYNTAX OCTET STRING
			MAX-ACCESS read-only
			STATUS current
			DESCRIPTION
				"The last logging Server list.  (delimiter :  / )"
			::= { fkV2McastIPTvCDRLogStats 7 }

		
		-- 1.3.6.1.4.1.10428 9 1.102.12.4.7.4
		fkV2McastIPTvCDRFormat OBJECT IDENTIFIER ::= { fkV2McastIPTvCDR 4 }

		
		-- 1.3.6.1.4.1.10428 9 1.102.12.4.7.4.1
		fkV2McastIPTvCDRFormatTable OBJECT-TYPE
			SYNTAX SEQUENCE OF FkV2McastIPTvCDRFormatEntry
			MAX-ACCESS not-accessible
			STATUS current
			DESCRIPTION
				"multicast IPTV CDR format table."
			::= { fkV2McastIPTvCDRFormat 1 }

		
		-- 1.3.6.1.4.1.10428 9 1.102.12.4.7.4.1.1
		fkV2McastIPTvCDRFormatEntry OBJECT-TYPE
			SYNTAX FkV2McastIPTvCDRFormatEntry
			MAX-ACCESS not-accessible
			STATUS current
			DESCRIPTION
				"key: fkV2McastIPTvCDRFmtName"
			INDEX { fkV2McastIPTvCDRFmtName }
			::= { fkV2McastIPTvCDRFormatTable 1 }

		
		FkV2McastIPTvCDRFormatEntry ::=
			SEQUENCE { 
				fkV2McastIPTvCDRFmtName
					OCTET STRING,
				fkV2McastIPTvCDRFmtDelimiter
					OCTET STRING,
				fkV2McastIPTvCDRFmtOrderRecordType
					OCTET STRING,
				fkV2McastIPTvCDRFmtOrderReason
					OCTET STRING,
				fkV2McastIPTvCDRFmtOrderLogTime
					OCTET STRING,
				fkV2McastIPTvCDRFmtOrderAN
					OCTET STRING,
				fkV2McastIPTvCDRFmtOrderSubscriber
					OCTET STRING,
				fkV2McastIPTvCDRFmtOrderChannel
					OCTET STRING,
				fkV2McastIPTvCDRFmtOrderChannelType
					OCTET STRING,
				fkV2McastIPTvCDRFmtOrderStartTime
					OCTET STRING,
				fkV2McastIPTvCDRFmtOrderViewingDuration
					OCTET STRING,
				fkV2McastIPTvCDRFmtJPRecId
					OCTET STRING,
				fkV2McastIPTvCDRFmtJDRecId
					OCTET STRING,
				fkV2McastIPTvCDRFmtKJRecId
					OCTET STRING,
				fkV2McastIPTvCDRFmtLPRecId
					OCTET STRING,
				fkV2McastIPTvCDRFmtLDRecId
					OCTET STRING,
				fkV2McastIPTvCDRFmtJPChTypeFullView
					OCTET STRING,
				fkV2McastIPTvCDRFmtJPChTypePreView
					OCTET STRING,
				fkV2McastIPTvCDRFmtJPChTypePayPerView
					OCTET STRING,
				fkV2McastIPTvCDRFmtJDReasonNoSubscriber
					OCTET STRING,
				fkV2McastIPTvCDRFmtJDReasonNoChannel
					OCTET STRING,
				fkV2McastIPTvCDRFmtJDReasonNotSubscribed
					OCTET STRING,
				fkV2McastIPTvCDRFmtJDReasonOverQuota
					OCTET STRING,
				fkV2McastIPTvCDRFmtJDReasonOverMaxStream
					OCTET STRING,
				fkV2McastIPTvCDRFmtJDReasonOverMaxBw
					OCTET STRING,
				fkV2McastIPTvCDRFmtKJChTypeFullView
					OCTET STRING,
				fkV2McastIPTvCDRFmtKJChTypePreView
					OCTET STRING,
				fkV2McastIPTvCDRFmtKJChTypePayPerView
					OCTET STRING,
				fkV2McastIPTvCDRFmtLPReasonLeaveChannel
					OCTET STRING,
				fkV2McastIPTvCDRFmtLPReasonTimeout
					OCTET STRING,
				fkV2McastIPTvCDRFmtLPReasonRemoveChannel
					OCTET STRING,
				fkV2McastIPTvCDRFmtLPReasonRemoveSubscriber
					OCTET STRING,
				fkV2McastIPTvCDRFmtLDReasonNoSubscriber
					OCTET STRING,
				fkV2McastIPTvCDRFmtLDReasonNoChannel
					OCTET STRING,
				fkV2McastIPTvCDRFmtLDReasonNotSubscribed
					OCTET STRING,
				fkV2McastIPTvCDRFmtLDReasonNotJoined
					OCTET STRING,
				fkV2McastIPTvCDRFmtReasonNoSubscriber
					OCTET STRING,
				fkV2McastIPTvCDRFmtReasonNoChannel
					OCTET STRING,
				fkV2McastIPTvCDRFmtReasonNotSubscribed
					OCTET STRING,
				fkV2McastIPTvCDRFmtReasonOverQuota
					OCTET STRING,
				fkV2McastIPTvCDRFmtReasonOverMaxStream
					OCTET STRING,
				fkV2McastIPTvCDRFmtReasonOverMaxBw
					OCTET STRING,
				fkV2McastIPTvCDRFmtReasonLeaveChannel
					OCTET STRING,
				fkV2McastIPTvCDRFmtReasonTimeout
					OCTET STRING,
				fkV2McastIPTvCDRFmtReasonRemoveChannel
					OCTET STRING,
				fkV2McastIPTvCDRFmtReasonRemoveSubscriber
					OCTET STRING,
				fkV2McastIPTvCDRFmtReasonNotJoined
					OCTET STRING
			 }

		-- 1.3.6.1.4.1.10428 9 1.102.12.4.7.4.1.1.1
		fkV2McastIPTvCDRFmtName OBJECT-TYPE
			SYNTAX OCTET STRING
			MAX-ACCESS read-only
			STATUS current
			DESCRIPTION
				"The Log-format-profile name."
			::= { fkV2McastIPTvCDRFormatEntry 1 }

		
		-- 1.3.6.1.4.1.10428 9 1.102.12.4.7.4.1.1.2
		fkV2McastIPTvCDRFmtDelimiter OBJECT-TYPE
			SYNTAX OCTET STRING
			MAX-ACCESS read-only
			STATUS current
			DESCRIPTION
				"The log delimiter. Default ','"
			::= { fkV2McastIPTvCDRFormatEntry 2 }

		
		-- 1.3.6.1.4.1.10428 9 1.102.12.4.7.4.1.1.3
		fkV2McastIPTvCDRFmtOrderRecordType OBJECT-TYPE
			SYNTAX OCTET STRING
			MAX-ACCESS read-only
			STATUS current
			DESCRIPTION
				"<0/1-9>  0 : means omit. Default: 1"
			::= { fkV2McastIPTvCDRFormatEntry 3 }

		
		-- 1.3.6.1.4.1.10428 9 1.102.12.4.7.4.1.1.4
		fkV2McastIPTvCDRFmtOrderReason OBJECT-TYPE
			SYNTAX OCTET STRING
			MAX-ACCESS read-only
			STATUS current
			DESCRIPTION
				"<0/1-9>  0 : means omit. Default: 2"
			::= { fkV2McastIPTvCDRFormatEntry 4 }

		
		-- 1.3.6.1.4.1.10428 9 1.102.12.4.7.4.1.1.5
		fkV2McastIPTvCDRFmtOrderLogTime OBJECT-TYPE
			SYNTAX OCTET STRING
			MAX-ACCESS read-only
			STATUS current
			DESCRIPTION
				"<0/1-9>  0 : means omit. Default: 3"
			::= { fkV2McastIPTvCDRFormatEntry 5 }

		
		-- 1.3.6.1.4.1.10428 9 1.102.12.4.7.4.1.1.6
		fkV2McastIPTvCDRFmtOrderAN OBJECT-TYPE
			SYNTAX OCTET STRING
			MAX-ACCESS read-only
			STATUS current
			DESCRIPTION
				"<0/1-9>  0 : means omit. Default: 4"
			::= { fkV2McastIPTvCDRFormatEntry 6 }

		
		-- 1.3.6.1.4.1.10428 9 1.102.12.4.7.4.1.1.7
		fkV2McastIPTvCDRFmtOrderSubscriber OBJECT-TYPE
			SYNTAX OCTET STRING
			MAX-ACCESS read-only
			STATUS current
			DESCRIPTION
				"<0/1-9>  0 : means omit. Default: 5"
			::= { fkV2McastIPTvCDRFormatEntry 7 }

		
		-- 1.3.6.1.4.1.10428 9 1.102.12.4.7.4.1.1.8
		fkV2McastIPTvCDRFmtOrderChannel OBJECT-TYPE
			SYNTAX OCTET STRING
			MAX-ACCESS read-only
			STATUS current
			DESCRIPTION
				"<0/1-9>  0 : means omit. Default: 6"
			::= { fkV2McastIPTvCDRFormatEntry 8 }

		
		-- 1.3.6.1.4.1.10428 9 1.102.12.4.7.4.1.1.9
		fkV2McastIPTvCDRFmtOrderChannelType OBJECT-TYPE
			SYNTAX OCTET STRING
			MAX-ACCESS read-only
			STATUS current
			DESCRIPTION
				"<0/1-9>  0 : means omit. Default: 7"
			::= { fkV2McastIPTvCDRFormatEntry 9 }

		
		-- 1.3.6.1.4.1.10428 9 1.102.12.4.7.4.1.1.10
		fkV2McastIPTvCDRFmtOrderStartTime OBJECT-TYPE
			SYNTAX OCTET STRING
			MAX-ACCESS read-only
			STATUS current
			DESCRIPTION
				"<0/1-9>  0 : means omit. Default: 8"
			::= { fkV2McastIPTvCDRFormatEntry 10 }

		
		-- 1.3.6.1.4.1.10428 9 1.102.12.4.7.4.1.1.11
		fkV2McastIPTvCDRFmtOrderViewingDuration OBJECT-TYPE
			SYNTAX OCTET STRING
			MAX-ACCESS read-only
			STATUS current
			DESCRIPTION
				"<0/1-9>  0 : means omit. Default: 9"
			::= { fkV2McastIPTvCDRFormatEntry 11 }

		
		-- 1.3.6.1.4.1.10428 9 1.102.12.4.7.4.1.1.12
		fkV2McastIPTvCDRFmtJPRecId OBJECT-TYPE
			SYNTAX OCTET STRING (SIZE (0..32))
			MAX-ACCESS read-only
			STATUS current
			DESCRIPTION
				"record-id : <1-255>, 0 means 'no',  max 32 string , default: string : join-permit
				The Join-Permit record ID value"
			::= { fkV2McastIPTvCDRFormatEntry 12 }

		
		-- 1.3.6.1.4.1.10428 9 1.102.12.4.7.4.1.1.13
		fkV2McastIPTvCDRFmtJDRecId OBJECT-TYPE
			SYNTAX OCTET STRING (SIZE (0..32))
			MAX-ACCESS read-only
			STATUS current
			DESCRIPTION
				"record-id : <1-255>, 0 means 'no',  max 32 string, default: string : join-deny
				The Join-Deny record ID value"
			::= { fkV2McastIPTvCDRFormatEntry 13 }

		
		-- 1.3.6.1.4.1.10428 9 1.102.12.4.7.4.1.1.14
		fkV2McastIPTvCDRFmtKJRecId OBJECT-TYPE
			SYNTAX OCTET STRING (SIZE (0..32))
			MAX-ACCESS read-only
			STATUS current
			DESCRIPTION
				"record-id : <1-255>, 0 means 'no',  max 32 string, default: string : keep-joined
				The Keep-Joined record ID value"
			::= { fkV2McastIPTvCDRFormatEntry 14 }

		
		-- 1.3.6.1.4.1.10428 9 1.102.12.4.7.4.1.1.15
		fkV2McastIPTvCDRFmtLPRecId OBJECT-TYPE
			SYNTAX OCTET STRING (SIZE (0..32))
			MAX-ACCESS read-only
			STATUS current
			DESCRIPTION
				"record-id : <1-255>, 0 means 'no',  max 32 string, default: string : leave-permit
				The Leave-Permit record ID value"
			::= { fkV2McastIPTvCDRFormatEntry 15 }

		
		-- 1.3.6.1.4.1.10428 9 1.102.12.4.7.4.1.1.16
		fkV2McastIPTvCDRFmtLDRecId OBJECT-TYPE
			SYNTAX OCTET STRING (SIZE (0..32))
			MAX-ACCESS read-only
			STATUS current
			DESCRIPTION
				"record-id : <1-255>, 0 means 'no',  max 32 string, default: string : leave-deny
				The Leave-Deny record ID value"
			::= { fkV2McastIPTvCDRFormatEntry 16 }

		
		-- 1.3.6.1.4.1.10428 9 1.102.12.4.7.4.1.1.17
		fkV2McastIPTvCDRFmtJPChTypeFullView OBJECT-TYPE
			SYNTAX OCTET STRING (SIZE (0..32))
			MAX-ACCESS read-only
			STATUS current
			DESCRIPTION
				"record-id : <1-255>, 0 means 'no'  max 32 string   
				The Join-Permit channel-type preview record ID value
				This is prior to JoinPermitRecordId."
			::= { fkV2McastIPTvCDRFormatEntry 17 }

		
		-- 1.3.6.1.4.1.10428 9 1.102.12.4.7.4.1.1.18
		fkV2McastIPTvCDRFmtJPChTypePreView OBJECT-TYPE
			SYNTAX OCTET STRING (SIZE (0..32))
			MAX-ACCESS read-only
			STATUS current
			DESCRIPTION
				"record-id : <1-255>, 0 means 'no'  max 32 string   
				The Join-Permit channel-type preview record ID value
				This is prior to JoinPermitRecordId."
			::= { fkV2McastIPTvCDRFormatEntry 18 }

		
		-- 1.3.6.1.4.1.10428 9 1.102.12.4.7.4.1.1.19
		fkV2McastIPTvCDRFmtJPChTypePayPerView OBJECT-TYPE
			SYNTAX OCTET STRING (SIZE (0..32))
			MAX-ACCESS read-only
			STATUS current
			DESCRIPTION
				"record-id : <1-255>, 0 means 'no'  max 32 string   
				The Join-Permit channel-type payperview record ID value
				This is prior to JoinPermitRecordId."
			::= { fkV2McastIPTvCDRFormatEntry 19 }

		
		-- 1.3.6.1.4.1.10428 9 1.102.12.4.7.4.1.1.20
		fkV2McastIPTvCDRFmtJDReasonNoSubscriber OBJECT-TYPE
			SYNTAX OCTET STRING (SIZE (0..32))
			MAX-ACCESS read-only
			STATUS current
			DESCRIPTION
				"record-id : <1-255>, 0 means 'no'  max 32 string   
				The Join-Deny reason-noSubscriber record ID value
				This is prior to JoinDenyRecordId"
			::= { fkV2McastIPTvCDRFormatEntry 20 }

		
		-- 1.3.6.1.4.1.10428 9 1.102.12.4.7.4.1.1.21
		fkV2McastIPTvCDRFmtJDReasonNoChannel OBJECT-TYPE
			SYNTAX OCTET STRING (SIZE (0..32))
			MAX-ACCESS read-only
			STATUS current
			DESCRIPTION
				"record-id : <1-255>, 0 means 'no'  max 32 string   
				This is prior to JoinDenyRecordId"
			::= { fkV2McastIPTvCDRFormatEntry 21 }

		
		-- 1.3.6.1.4.1.10428 9 1.102.12.4.7.4.1.1.22
		fkV2McastIPTvCDRFmtJDReasonNotSubscribed OBJECT-TYPE
			SYNTAX OCTET STRING (SIZE (0..32))
			MAX-ACCESS read-only
			STATUS current
			DESCRIPTION
				"record-id : <1-255>, 0 means 'no'  max 32 string   
				This is prior to JoinDenyRecordId"
			::= { fkV2McastIPTvCDRFormatEntry 22 }

		
		-- 1.3.6.1.4.1.10428 9 1.102.12.4.7.4.1.1.23
		fkV2McastIPTvCDRFmtJDReasonOverQuota OBJECT-TYPE
			SYNTAX OCTET STRING (SIZE (0..32))
			MAX-ACCESS read-only
			STATUS current
			DESCRIPTION
				"record-id : <1-255>, 0 means 'no'  max 32 string   
				This is prior to JoinDenyRecordId"
			::= { fkV2McastIPTvCDRFormatEntry 23 }

		
		-- 1.3.6.1.4.1.10428 9 1.102.12.4.7.4.1.1.24
		fkV2McastIPTvCDRFmtJDReasonOverMaxStream OBJECT-TYPE
			SYNTAX OCTET STRING (SIZE (0..32))
			MAX-ACCESS read-only
			STATUS current
			DESCRIPTION
				"record-id : <1-255>, 0 means 'no'  max 32 string   
				This is prior to JoinDenyRecordId"
			::= { fkV2McastIPTvCDRFormatEntry 24 }

		
		-- 1.3.6.1.4.1.10428 9 1.102.12.4.7.4.1.1.25
		fkV2McastIPTvCDRFmtJDReasonOverMaxBw OBJECT-TYPE
			SYNTAX OCTET STRING (SIZE (0..32))
			MAX-ACCESS read-only
			STATUS current
			DESCRIPTION
				"record-id : <1-255>, 0 means 'no'  max 32 string   
				This is prior to JoinDenyRecordId"
			::= { fkV2McastIPTvCDRFormatEntry 25 }

		
		-- 1.3.6.1.4.1.10428 9 1.102.12.4.7.4.1.1.26
		fkV2McastIPTvCDRFmtKJChTypeFullView OBJECT-TYPE
			SYNTAX OCTET STRING (SIZE (0..32))
			MAX-ACCESS read-only
			STATUS current
			DESCRIPTION
				"record-id : <1-255>, 0 means 'no'  max 32 string   
				This is prior to KeepJoinedRecordId"
			::= { fkV2McastIPTvCDRFormatEntry 26 }

		
		-- 1.3.6.1.4.1.10428 9 1.102.12.4.7.4.1.1.27
		fkV2McastIPTvCDRFmtKJChTypePreView OBJECT-TYPE
			SYNTAX OCTET STRING (SIZE (0..32))
			MAX-ACCESS read-only
			STATUS current
			DESCRIPTION
				"record-id : <1-255>, 0 means 'no'  max 32 string   
				This  is prior to KeepJoinedRecordId"
			::= { fkV2McastIPTvCDRFormatEntry 27 }

		
		-- 1.3.6.1.4.1.10428 9 1.102.12.4.7.4.1.1.28
		fkV2McastIPTvCDRFmtKJChTypePayPerView OBJECT-TYPE
			SYNTAX OCTET STRING (SIZE (0..32))
			MAX-ACCESS read-only
			STATUS current
			DESCRIPTION
				"record-id : <1-255>, 0 means 'no'  max 32 string   
				This is prior to KeepJoinedRecordId"
			::= { fkV2McastIPTvCDRFormatEntry 28 }

		
		-- 1.3.6.1.4.1.10428 9 1.102.12.4.7.4.1.1.29
		fkV2McastIPTvCDRFmtLPReasonLeaveChannel OBJECT-TYPE
			SYNTAX OCTET STRING (SIZE (0..32))
			MAX-ACCESS read-only
			STATUS current
			DESCRIPTION
				"record-id : <1-255>, 0 means 'no'  max 32 string   
				This is prior to LeavePermit"
			::= { fkV2McastIPTvCDRFormatEntry 29 }

		
		-- 1.3.6.1.4.1.10428 9 1.102.12.4.7.4.1.1.30
		fkV2McastIPTvCDRFmtLPReasonTimeout OBJECT-TYPE
			SYNTAX OCTET STRING (SIZE (0..32))
			MAX-ACCESS read-only
			STATUS current
			DESCRIPTION
				"record-id : <1-255>, 0 means 'no'  max 32 string   
				This is prior to LeavePermit"
			::= { fkV2McastIPTvCDRFormatEntry 30 }

		
		-- 1.3.6.1.4.1.10428 9 1.102.12.4.7.4.1.1.31
		fkV2McastIPTvCDRFmtLPReasonRemoveChannel OBJECT-TYPE
			SYNTAX OCTET STRING (SIZE (0..32))
			MAX-ACCESS read-only
			STATUS current
			DESCRIPTION
				"record-id : <1-255>, 0 means 'no'  max 32 string   
				This  is prior to LeavePermit"
			::= { fkV2McastIPTvCDRFormatEntry 31 }

		
		-- 1.3.6.1.4.1.10428 9 1.102.12.4.7.4.1.1.32
		fkV2McastIPTvCDRFmtLPReasonRemoveSubscriber OBJECT-TYPE
			SYNTAX OCTET STRING (SIZE (0..32))
			MAX-ACCESS read-only
			STATUS current
			DESCRIPTION
				"record-id : <1-255>, 0 means 'no'  max 32 string   
				This is prior to LeavePermit"
			::= { fkV2McastIPTvCDRFormatEntry 32 }

		
		-- 1.3.6.1.4.1.10428 9 1.102.12.4.7.4.1.1.33
		fkV2McastIPTvCDRFmtLDReasonNoSubscriber OBJECT-TYPE
			SYNTAX OCTET STRING (SIZE (0..32))
			MAX-ACCESS read-only
			STATUS current
			DESCRIPTION
				"record-id : <1-255>, 0 means 'no'  max 32 string   
				This is prior to LeaveDeny"
			::= { fkV2McastIPTvCDRFormatEntry 33 }

		
		-- 1.3.6.1.4.1.10428 9 1.102.12.4.7.4.1.1.34
		fkV2McastIPTvCDRFmtLDReasonNoChannel OBJECT-TYPE
			SYNTAX OCTET STRING (SIZE (0..32))
			MAX-ACCESS read-only
			STATUS current
			DESCRIPTION
				"record-id : <1-255>, 0 means 'no'  max 32 string   
				This is prior to LeaveDeny"
			::= { fkV2McastIPTvCDRFormatEntry 34 }

		
		-- 1.3.6.1.4.1.10428 9 1.102.12.4.7.4.1.1.35
		fkV2McastIPTvCDRFmtLDReasonNotSubscribed OBJECT-TYPE
			SYNTAX OCTET STRING (SIZE (0..32))
			MAX-ACCESS read-only
			STATUS current
			DESCRIPTION
				"record-id : <1-255>, 0 means 'no'  max 32 string   
				This is prior to LeaveDeny"
			::= { fkV2McastIPTvCDRFormatEntry 35 }

		
		-- 1.3.6.1.4.1.10428 9 1.102.12.4.7.4.1.1.36
		fkV2McastIPTvCDRFmtLDReasonNotJoined OBJECT-TYPE
			SYNTAX OCTET STRING (SIZE (0..32))
			MAX-ACCESS read-only
			STATUS current
			DESCRIPTION
				"record-id : <1-255>, 0 means 'no'  max 32 string   
				This is prior to LeaveDeny"
			::= { fkV2McastIPTvCDRFormatEntry 36 }

		
		-- 1.3.6.1.4.1.10428 9 1.102.12.4.7.4.1.1.37
		fkV2McastIPTvCDRFmtReasonNoSubscriber OBJECT-TYPE
			SYNTAX OCTET STRING (SIZE (0..32))
			MAX-ACCESS read-only
			STATUS current
			DESCRIPTION
				"record-id : <1-255>, 0 means 'no'  max 32 string"
			::= { fkV2McastIPTvCDRFormatEntry 37 }

		
		-- 1.3.6.1.4.1.10428 9 1.102.12.4.7.4.1.1.38
		fkV2McastIPTvCDRFmtReasonNoChannel OBJECT-TYPE
			SYNTAX OCTET STRING (SIZE (0..32))
			MAX-ACCESS read-only
			STATUS current
			DESCRIPTION
				"record-id : <1-255>, 0 means 'no'  max 32 string"
			::= { fkV2McastIPTvCDRFormatEntry 38 }

		
		-- 1.3.6.1.4.1.10428 9 1.102.12.4.7.4.1.1.39
		fkV2McastIPTvCDRFmtReasonNotSubscribed OBJECT-TYPE
			SYNTAX OCTET STRING (SIZE (0..32))
			MAX-ACCESS read-only
			STATUS current
			DESCRIPTION
				"record-id : <1-255>, 0 means 'no'  max 32 string"
			::= { fkV2McastIPTvCDRFormatEntry 39 }

		
		-- 1.3.6.1.4.1.10428 9 1.102.12.4.7.4.1.1.40
		fkV2McastIPTvCDRFmtReasonOverQuota OBJECT-TYPE
			SYNTAX OCTET STRING (SIZE (0..32))
			MAX-ACCESS read-only
			STATUS current
			DESCRIPTION
				"record-id : <1-255>, 0 means 'no'  max 32 string"
			::= { fkV2McastIPTvCDRFormatEntry 40 }

		
		-- 1.3.6.1.4.1.10428 9 1.102.12.4.7.4.1.1.41
		fkV2McastIPTvCDRFmtReasonOverMaxStream OBJECT-TYPE
			SYNTAX OCTET STRING (SIZE (0..32))
			MAX-ACCESS read-only
			STATUS current
			DESCRIPTION
				"record-id : <1-255>, 0 means 'no'  max 32 string"
			::= { fkV2McastIPTvCDRFormatEntry 41 }

		
		-- 1.3.6.1.4.1.10428 9 1.102.12.4.7.4.1.1.42
		fkV2McastIPTvCDRFmtReasonOverMaxBw OBJECT-TYPE
			SYNTAX OCTET STRING (SIZE (0..32))
			MAX-ACCESS read-only
			STATUS current
			DESCRIPTION
				"record-id : <1-255>, 0 means 'no'  max 32 string"
			::= { fkV2McastIPTvCDRFormatEntry 42 }

		
		-- 1.3.6.1.4.1.10428 9 1.102.12.4.7.4.1.1.43
		fkV2McastIPTvCDRFmtReasonLeaveChannel OBJECT-TYPE
			SYNTAX OCTET STRING (SIZE (0..32))
			MAX-ACCESS read-only
			STATUS current
			DESCRIPTION
				"record-id : <1-255>, 0 means 'no'  max 32 string"
			::= { fkV2McastIPTvCDRFormatEntry 43 }

		
		-- 1.3.6.1.4.1.10428 9 1.102.12.4.7.4.1.1.44
		fkV2McastIPTvCDRFmtReasonTimeout OBJECT-TYPE
			SYNTAX OCTET STRING (SIZE (0..32))
			MAX-ACCESS read-only
			STATUS current
			DESCRIPTION
				"record-id : <1-255>, 0 means 'no'  max 32 string"
			::= { fkV2McastIPTvCDRFormatEntry 44 }

		
		-- 1.3.6.1.4.1.10428 9 1.102.12.4.7.4.1.1.45
		fkV2McastIPTvCDRFmtReasonRemoveChannel OBJECT-TYPE
			SYNTAX OCTET STRING (SIZE (0..32))
			MAX-ACCESS read-only
			STATUS current
			DESCRIPTION
				"record-id : <1-255>, 0 means 'no'  max 32 string"
			::= { fkV2McastIPTvCDRFormatEntry 45 }

		
		-- 1.3.6.1.4.1.10428 9 1.102.12.4.7.4.1.1.46
		fkV2McastIPTvCDRFmtReasonRemoveSubscriber OBJECT-TYPE
			SYNTAX OCTET STRING (SIZE (0..32))
			MAX-ACCESS read-only
			STATUS current
			DESCRIPTION
				"record-id : <1-255>, 0 means 'no'  max 32 string"
			::= { fkV2McastIPTvCDRFormatEntry 46 }

		
		-- 1.3.6.1.4.1.10428 9 1.102.12.4.7.4.1.1.47
		fkV2McastIPTvCDRFmtReasonNotJoined OBJECT-TYPE
			SYNTAX OCTET STRING (SIZE (0..32))
			MAX-ACCESS read-only
			STATUS current
			DESCRIPTION
				"record-id : <1-255>, 0 means 'no'  max 32 string"
			::= { fkV2McastIPTvCDRFormatEntry 47 }

		
		-- 1.3.6.1.4.1.10428 9 1.102.12.4.7.4.2
		fkV2McastIPTvCDRLogFormatControl OBJECT IDENTIFIER ::= { fkV2McastIPTvCDRFormat 2 }

		
		-- 1.3.6.1.4.1.10428 9 1.102.12.4.7.4.2.1
		fkV2McastIPTvCDRFmtControlRequest OBJECT-TYPE
			SYNTAX INTEGER
				{
				createCDRFormat(1),
				deleteCDRFormat(2),
				setCDROrder(3),
				setCDRRecordTypeProfile(4),
				setCDRReasonProfile(5)
				}
			MAX-ACCESS read-write
			STATUS current
			DESCRIPTION
				"The request of a user command"
			::= { fkV2McastIPTvCDRLogFormatControl 1 }

		
		-- 1.3.6.1.4.1.10428 9 1.102.12.4.7.4.2.2
		fkV2McastIPTvCDRFmtControlStatus OBJECT-TYPE
			SYNTAX FkControlStatusType
			MAX-ACCESS read-only
			STATUS current
			DESCRIPTION
				"The status of user command"
			::= { fkV2McastIPTvCDRLogFormatControl 2 }

		
		-- 1.3.6.1.4.1.10428 9 1.102.12.4.7.4.2.3
		fkV2McastIPTvCDRFmtControlTimer OBJECT-TYPE
			SYNTAX Gauge32
			MAX-ACCESS read-write
			STATUS current
			DESCRIPTION
				"The maximum time for the manager for a long running user command"
			::= { fkV2McastIPTvCDRLogFormatControl 3 }

		
		-- 1.3.6.1.4.1.10428 9 1.102.12.4.7.4.2.4
		fkV2McastIPTvCDRFmtControlTimeStamp OBJECT-TYPE
			SYNTAX TimeStamp
			MAX-ACCESS read-only
			STATUS current
			DESCRIPTION
				"The time stamp of the last command(end of command)"
			::= { fkV2McastIPTvCDRLogFormatControl 4 }

		
		-- 1.3.6.1.4.1.10428 9 1.102.12.4.7.4.2.5
		fkV2McastIPTvCDRFmtControlReqResult OBJECT-TYPE
			SYNTAX FkControlRequestResultType
			MAX-ACCESS read-only
			STATUS current
			DESCRIPTION
				"The result of the last user command"
			::= { fkV2McastIPTvCDRLogFormatControl 5 }

		
		-- 1.3.6.1.4.1.10428 9 1.102.12.4.7.4.2.6
		fkV2McastIPTvCDRFmtControlName OBJECT-TYPE
			SYNTAX OCTET STRING
			MAX-ACCESS read-write
			STATUS current
			DESCRIPTION
				"The Log-format-profile name."
			::= { fkV2McastIPTvCDRLogFormatControl 6 }

		
		-- 1.3.6.1.4.1.10428 9 1.102.12.4.7.4.2.7
		fkV2McastIPTvCDRFmtControlDelimiter OBJECT-TYPE
			SYNTAX OCTET STRING
			MAX-ACCESS read-write
			STATUS current
			DESCRIPTION
				"The log delimiter.  Default ','"
			::= { fkV2McastIPTvCDRLogFormatControl 7 }

		
		-- 1.3.6.1.4.1.10428 9 1.102.12.4.7.4.2.8
		fkV2McastIPTvCDRFmtControlOrderRecordType OBJECT-TYPE
			SYNTAX OCTET STRING
			MAX-ACCESS read-write
			STATUS current
			DESCRIPTION
				"<0/1-9>  0 : means omit. Default: 1"
			::= { fkV2McastIPTvCDRLogFormatControl 8 }

		
		-- 1.3.6.1.4.1.10428 9 1.102.12.4.7.4.2.9
		fkV2McastIPTvCDRFmtControlOrderReason OBJECT-TYPE
			SYNTAX OCTET STRING
			MAX-ACCESS read-write
			STATUS current
			DESCRIPTION
				"<0/1-9>  0 : means omit. Default: 2"
			::= { fkV2McastIPTvCDRLogFormatControl 9 }

		
		-- 1.3.6.1.4.1.10428 9 1.102.12.4.7.4.2.10
		fkV2McastIPTvCDRFmtControlOrderLogTime OBJECT-TYPE
			SYNTAX OCTET STRING
			MAX-ACCESS read-write
			STATUS current
			DESCRIPTION
				"<0/1-9>  0 : means omit. Default: 3"
			::= { fkV2McastIPTvCDRLogFormatControl 10 }

		
		-- 1.3.6.1.4.1.10428 9 1.102.12.4.7.4.2.11
		fkV2McastIPTvCDRFmtControlOrderAN OBJECT-TYPE
			SYNTAX OCTET STRING
			MAX-ACCESS read-write
			STATUS current
			DESCRIPTION
				"<0/1-9>  0 : means omit. Default: 4"
			::= { fkV2McastIPTvCDRLogFormatControl 11 }

		
		-- 1.3.6.1.4.1.10428 9 1.102.12.4.7.4.2.12
		fkV2McastIPTvCDRFmtControlOrderSubscriber OBJECT-TYPE
			SYNTAX OCTET STRING
			MAX-ACCESS read-write
			STATUS current
			DESCRIPTION
				"<0/1-9>  0 : means omit. Default: 5"
			::= { fkV2McastIPTvCDRLogFormatControl 12 }

		
		-- 1.3.6.1.4.1.10428 9 1.102.12.4.7.4.2.13
		fkV2McastIPTvCDRFmtControlOrderChannel OBJECT-TYPE
			SYNTAX OCTET STRING
			MAX-ACCESS read-write
			STATUS current
			DESCRIPTION
				"<0/1-9>  0 : means omit. Default: 6"
			::= { fkV2McastIPTvCDRLogFormatControl 13 }

		
		-- 1.3.6.1.4.1.10428 9 1.102.12.4.7.4.2.14
		fkV2McastIPTvCDRFmtControlOrderChannelType OBJECT-TYPE
			SYNTAX OCTET STRING
			MAX-ACCESS read-write
			STATUS current
			DESCRIPTION
				"<0/1-9>  0 : means omit. Default: 7"
			::= { fkV2McastIPTvCDRLogFormatControl 14 }

		
		-- 1.3.6.1.4.1.10428 9 1.102.12.4.7.4.2.15
		fkV2McastIPTvCDRFmtControlOrderStartTime OBJECT-TYPE
			SYNTAX OCTET STRING
			MAX-ACCESS read-write
			STATUS current
			DESCRIPTION
				"<0/1-9>  0 : means omit. Default: 8"
			::= { fkV2McastIPTvCDRLogFormatControl 15 }

		
		-- 1.3.6.1.4.1.10428 9 1.102.12.4.7.4.2.16
		fkV2McastIPTvCDRFmtControlOrderViewingDuration OBJECT-TYPE
			SYNTAX OCTET STRING
			MAX-ACCESS read-write
			STATUS current
			DESCRIPTION
				"<0/1-9>  0 : means omit. Default: 9"
			::= { fkV2McastIPTvCDRLogFormatControl 16 }

		
		-- 1.3.6.1.4.1.10428 9 1.102.12.4.7.4.2.17
		fkV2McastIPTvCDRFmtControlJPRecId OBJECT-TYPE
			SYNTAX OCTET STRING (SIZE (0..32))
			MAX-ACCESS read-write
			STATUS current
			DESCRIPTION
				"record-id : <1-255>, 0 means 'no',  max 32 string , default: string : join-permit
				The Join-Permit record ID value"
			::= { fkV2McastIPTvCDRLogFormatControl 17 }

		
		-- 1.3.6.1.4.1.10428 9 1.102.12.4.7.4.2.18
		fkV2McastIPTvCDRFmtControlJDRecId OBJECT-TYPE
			SYNTAX OCTET STRING (SIZE (0..32))
			MAX-ACCESS read-write
			STATUS current
			DESCRIPTION
				"record-id : <1-255>, 0 means 'no',  max 32 string, default: string : join-deny
				The Join-Deny record ID value"
			::= { fkV2McastIPTvCDRLogFormatControl 18 }

		
		-- 1.3.6.1.4.1.10428 9 1.102.12.4.7.4.2.19
		fkV2McastIPTvCDRFmtControlKJRecId OBJECT-TYPE
			SYNTAX OCTET STRING (SIZE (0..32))
			MAX-ACCESS read-write
			STATUS current
			DESCRIPTION
				"record-id : <1-255>, 0 means 'no',  max 32 string, default: string : keep-joined
				The Keep-Joined record ID value"
			::= { fkV2McastIPTvCDRLogFormatControl 19 }

		
		-- 1.3.6.1.4.1.10428 9 1.102.12.4.7.4.2.20
		fkV2McastIPTvCDRFmtControlLPRecId OBJECT-TYPE
			SYNTAX OCTET STRING (SIZE (0..32))
			MAX-ACCESS read-write
			STATUS current
			DESCRIPTION
				"record-id : <1-255>, 0 means 'no',  max 32 string, default: string : leave-permit
				The Leave-Permit record ID value"
			::= { fkV2McastIPTvCDRLogFormatControl 20 }

		
		-- 1.3.6.1.4.1.10428 9 1.102.12.4.7.4.2.21
		fkV2McastIPTvCDRFmtControlLDRecId OBJECT-TYPE
			SYNTAX OCTET STRING (SIZE (0..32))
			MAX-ACCESS read-write
			STATUS current
			DESCRIPTION
				"record-id : <1-255>, 0 means 'no',  max 32 string, default: string : leave-deny
				The Leave-Deny record ID value"
			::= { fkV2McastIPTvCDRLogFormatControl 21 }

		
		-- 1.3.6.1.4.1.10428 9 1.102.12.4.7.4.2.22
		fkV2McastIPTvCDRFmtControlJPChTypeFullView OBJECT-TYPE
			SYNTAX OCTET STRING (SIZE (0..32))
			MAX-ACCESS read-write
			STATUS current
			DESCRIPTION
				"record-id : <1-255>, 0 means 'no'  max 32 string"
			::= { fkV2McastIPTvCDRLogFormatControl 22 }

		
		-- 1.3.6.1.4.1.10428 9 1.102.12.4.7.4.2.23
		fkV2McastIPTvCDRFmtControlJPChTypePreView OBJECT-TYPE
			SYNTAX OCTET STRING (SIZE (0..32))
			MAX-ACCESS read-write
			STATUS current
			DESCRIPTION
				"record-id : <1-255>, 0 means 'no'  max 32 string"
			::= { fkV2McastIPTvCDRLogFormatControl 23 }

		
		-- 1.3.6.1.4.1.10428 9 1.102.12.4.7.4.2.24
		fkV2McastIPTvCDRFmtControlJPChTypePayPerView OBJECT-TYPE
			SYNTAX OCTET STRING (SIZE (0..32))
			MAX-ACCESS read-write
			STATUS current
			DESCRIPTION
				"record-id : <1-255>, 0 means 'no'  max 32 string"
			::= { fkV2McastIPTvCDRLogFormatControl 24 }

		
		-- 1.3.6.1.4.1.10428 9 1.102.12.4.7.4.2.25
		fkV2McastIPTvCDRFmtControlJDReasonNoSubscriber OBJECT-TYPE
			SYNTAX OCTET STRING (SIZE (0..32))
			MAX-ACCESS read-write
			STATUS current
			DESCRIPTION
				"record-id : <1-255>, 0 means 'no'  max 32 string"
			::= { fkV2McastIPTvCDRLogFormatControl 25 }

		
		-- 1.3.6.1.4.1.10428 9 1.102.12.4.7.4.2.26
		fkV2McastIPTvCDRFmtControlJDReasonNoChannel OBJECT-TYPE
			SYNTAX OCTET STRING (SIZE (0..32))
			MAX-ACCESS read-write
			STATUS current
			DESCRIPTION
				"record-id : <1-255>, 0 means 'no'  max 32 string"
			::= { fkV2McastIPTvCDRLogFormatControl 26 }

		
		-- 1.3.6.1.4.1.10428 9 1.102.12.4.7.4.2.27
		fkV2McastIPTvCDRFmtControlJDReasonNotSubscribed OBJECT-TYPE
			SYNTAX OCTET STRING (SIZE (0..32))
			MAX-ACCESS read-write
			STATUS current
			DESCRIPTION
				"record-id : <1-255>, 0 means 'no'  max 32 string"
			::= { fkV2McastIPTvCDRLogFormatControl 27 }

		
		-- 1.3.6.1.4.1.10428 9 1.102.12.4.7.4.2.28
		fkV2McastIPTvCDRFmtControlJDReasonOverQuota OBJECT-TYPE
			SYNTAX OCTET STRING (SIZE (0..32))
			MAX-ACCESS read-write
			STATUS current
			DESCRIPTION
				"record-id : <1-255>, 0 means 'no'  max 32 string"
			::= { fkV2McastIPTvCDRLogFormatControl 28 }

		
		-- 1.3.6.1.4.1.10428 9 1.102.12.4.7.4.2.29
		fkV2McastIPTvCDRFmtControlJDReasonOverMaxStream OBJECT-TYPE
			SYNTAX OCTET STRING (SIZE (0..32))
			MAX-ACCESS read-write
			STATUS current
			DESCRIPTION
				"record-id : <1-255>, 0 means 'no'  max 32 string"
			::= { fkV2McastIPTvCDRLogFormatControl 29 }

		
		-- 1.3.6.1.4.1.10428 9 1.102.12.4.7.4.2.30
		fkV2McastIPTvCDRFmtControlJDReasonOverMaxBw OBJECT-TYPE
			SYNTAX OCTET STRING (SIZE (0..32))
			MAX-ACCESS read-write
			STATUS current
			DESCRIPTION
				"record-id : <1-255>, 0 means 'no'  max 32 string"
			::= { fkV2McastIPTvCDRLogFormatControl 30 }

		
		-- 1.3.6.1.4.1.10428 9 1.102.12.4.7.4.2.31
		fkV2McastIPTvCDRFmtControlKJChTypeFullView OBJECT-TYPE
			SYNTAX OCTET STRING (SIZE (0..32))
			MAX-ACCESS read-write
			STATUS current
			DESCRIPTION
				"record-id : <1-255>, 0 means 'no'  max 32 string"
			::= { fkV2McastIPTvCDRLogFormatControl 31 }

		
		-- 1.3.6.1.4.1.10428 9 1.102.12.4.7.4.2.32
		fkV2McastIPTvCDRFmtControlKJChTypePreview OBJECT-TYPE
			SYNTAX OCTET STRING (SIZE (0..32))
			MAX-ACCESS read-write
			STATUS current
			DESCRIPTION
				"record-id : <1-255>, 0 means 'no'  max 32 string"
			::= { fkV2McastIPTvCDRLogFormatControl 32 }

		
		-- 1.3.6.1.4.1.10428 9 1.102.12.4.7.4.2.33
		fkV2McastIPTvCDRFmtControlKJChTypePayPerView OBJECT-TYPE
			SYNTAX OCTET STRING (SIZE (0..32))
			MAX-ACCESS read-write
			STATUS current
			DESCRIPTION
				"record-id : <1-255>, 0 means 'no'  max 32 string"
			::= { fkV2McastIPTvCDRLogFormatControl 33 }

		
		-- 1.3.6.1.4.1.10428 9 1.102.12.4.7.4.2.34
		fkV2McastIPTvCDRFmtControlLPReasonLeaveChannel OBJECT-TYPE
			SYNTAX OCTET STRING (SIZE (0..32))
			MAX-ACCESS read-write
			STATUS current
			DESCRIPTION
				"record-id : <1-255>, 0 means 'no'  max 32 string"
			::= { fkV2McastIPTvCDRLogFormatControl 34 }

		
		-- 1.3.6.1.4.1.10428 9 1.102.12.4.7.4.2.35
		fkV2McastIPTvCDRFmtControlLPReasonTimeout OBJECT-TYPE
			SYNTAX OCTET STRING (SIZE (0..32))
			MAX-ACCESS read-write
			STATUS current
			DESCRIPTION
				"record-id : <1-255>, 0 means 'no'  max 32 string"
			::= { fkV2McastIPTvCDRLogFormatControl 35 }

		
		-- 1.3.6.1.4.1.10428 9 1.102.12.4.7.4.2.36
		fkV2McastIPTvCDRFmtControlLPReasonRemoveChannel OBJECT-TYPE
			SYNTAX OCTET STRING (SIZE (0..32))
			MAX-ACCESS read-write
			STATUS current
			DESCRIPTION
				"record-id : <1-255>, 0 means 'no'  max 32 string"
			::= { fkV2McastIPTvCDRLogFormatControl 36 }

		
		-- 1.3.6.1.4.1.10428 9 1.102.12.4.7.4.2.37
		fkV2McastIPTvCDRFmtControlLPReasonRemoveSubscriber OBJECT-TYPE
			SYNTAX OCTET STRING (SIZE (0..32))
			MAX-ACCESS read-write
			STATUS current
			DESCRIPTION
				"record-id : <1-255>, 0 means 'no'  max 32 string"
			::= { fkV2McastIPTvCDRLogFormatControl 37 }

		
		-- 1.3.6.1.4.1.10428 9 1.102.12.4.7.4.2.38
		fkV2McastIPTvCDRFmtControlLDReasonNoSubscriber OBJECT-TYPE
			SYNTAX OCTET STRING (SIZE (0..32))
			MAX-ACCESS read-write
			STATUS current
			DESCRIPTION
				"record-id : <1-255>, 0 means 'no'  max 32 string"
			::= { fkV2McastIPTvCDRLogFormatControl 38 }

		
		-- 1.3.6.1.4.1.10428 9 1.102.12.4.7.4.2.39
		fkV2McastIPTvCDRFmtControlLDReasonNoChannel OBJECT-TYPE
			SYNTAX OCTET STRING (SIZE (0..32))
			MAX-ACCESS read-write
			STATUS current
			DESCRIPTION
				"record-id : <1-255>, 0 means 'no'  max 32 string"
			::= { fkV2McastIPTvCDRLogFormatControl 39 }

		
		-- 1.3.6.1.4.1.10428 9 1.102.12.4.7.4.2.40
		fkV2McastIPTvCDRFmtControlLDReasonNotSubscriber OBJECT-TYPE
			SYNTAX OCTET STRING (SIZE (0..32))
			MAX-ACCESS read-write
			STATUS current
			DESCRIPTION
				"record-id : <1-255>, 0 means 'no'  max 32 string"
			::= { fkV2McastIPTvCDRLogFormatControl 40 }

		
		-- 1.3.6.1.4.1.10428 9 1.102.12.4.7.4.2.41
		fkV2McastIPTvCDRFmtControlLDReasonNotJoined OBJECT-TYPE
			SYNTAX OCTET STRING (SIZE (0..32))
			MAX-ACCESS read-write
			STATUS current
			DESCRIPTION
				"record-id : <1-255>, 0 means 'no'  max 32 string"
			::= { fkV2McastIPTvCDRLogFormatControl 41 }

		
		-- 1.3.6.1.4.1.10428 9 1.102.12.4.7.4.2.42
		fkV2McastIPTvCDRFmtControlReasonNoSubscriber OBJECT-TYPE
			SYNTAX OCTET STRING (SIZE (0..32))
			MAX-ACCESS read-write
			STATUS current
			DESCRIPTION
				"record-id : <1-255>, 0 means 'no'  max 32 string"
			::= { fkV2McastIPTvCDRLogFormatControl 42 }

		
		-- 1.3.6.1.4.1.10428 9 1.102.12.4.7.4.2.43
		fkV2McastIPTvCDRFmtControlReasonNoChannel OBJECT-TYPE
			SYNTAX OCTET STRING (SIZE (0..32))
			MAX-ACCESS read-write
			STATUS current
			DESCRIPTION
				"record-id : <1-255>, 0 means 'no'  max 32 string"
			::= { fkV2McastIPTvCDRLogFormatControl 43 }

		
		-- 1.3.6.1.4.1.10428 9 1.102.12.4.7.4.2.44
		fkV2McastIPTvCDRFmtControlReasonNotSubscribed OBJECT-TYPE
			SYNTAX OCTET STRING (SIZE (0..32))
			MAX-ACCESS read-write
			STATUS current
			DESCRIPTION
				"record-id : <1-255>, 0 means 'no'  max 32 string"
			::= { fkV2McastIPTvCDRLogFormatControl 44 }

		
		-- 1.3.6.1.4.1.10428 9 1.102.12.4.7.4.2.45
		fkV2McastIPTvCDRFmtControlReasonOverQuota OBJECT-TYPE
			SYNTAX OCTET STRING (SIZE (0..32))
			MAX-ACCESS read-write
			STATUS current
			DESCRIPTION
				"record-id : <1-255>, 0 means 'no'  max 32 string"
			::= { fkV2McastIPTvCDRLogFormatControl 45 }

		
		-- 1.3.6.1.4.1.10428 9 1.102.12.4.7.4.2.46
		fkV2McastIPTvCDRFmtControlReasonOverMaxStream OBJECT-TYPE
			SYNTAX OCTET STRING (SIZE (0..32))
			MAX-ACCESS read-write
			STATUS current
			DESCRIPTION
				"record-id : <1-255>, 0 means 'no'  max 32 string"
			::= { fkV2McastIPTvCDRLogFormatControl 46 }

		
		-- 1.3.6.1.4.1.10428 9 1.102.12.4.7.4.2.47
		fkV2McastIPTvCDRFmtControlReasonOverMaxBx OBJECT-TYPE
			SYNTAX OCTET STRING (SIZE (0..32))
			MAX-ACCESS read-write
			STATUS current
			DESCRIPTION
				"record-id : <1-255>, 0 means 'no'  max 32 string"
			::= { fkV2McastIPTvCDRLogFormatControl 47 }

		
		-- 1.3.6.1.4.1.10428 9 1.102.12.4.7.4.2.48
		fkV2McastIPTvCDRFmtControlReasonLeaveChannel OBJECT-TYPE
			SYNTAX OCTET STRING (SIZE (0..32))
			MAX-ACCESS read-write
			STATUS current
			DESCRIPTION
				"record-id : <1-255>, 0 means 'no'  max 32 string"
			::= { fkV2McastIPTvCDRLogFormatControl 48 }

		
		-- 1.3.6.1.4.1.10428 9 1.102.12.4.7.4.2.49
		fkV2McastIPTvCDRFmtControlReasonTimeout OBJECT-TYPE
			SYNTAX OCTET STRING (SIZE (0..32))
			MAX-ACCESS read-write
			STATUS current
			DESCRIPTION
				"record-id : <1-255>, 0 means 'no'  max 32 string"
			::= { fkV2McastIPTvCDRLogFormatControl 49 }

		
		-- 1.3.6.1.4.1.10428 9 1.102.12.4.7.4.2.50
		fkV2McastIPTvCDRFmtControlReasonRemoveChannel OBJECT-TYPE
			SYNTAX OCTET STRING (SIZE (0..32))
			MAX-ACCESS read-write
			STATUS current
			DESCRIPTION
				"record-id : <1-255>, 0 means 'no'  max 32 string"
			::= { fkV2McastIPTvCDRLogFormatControl 50 }

		
		-- 1.3.6.1.4.1.10428 9 1.102.12.4.7.4.2.51
		fkV2McastIPTvCDRFmtControlReasonRemoveSubscriber OBJECT-TYPE
			SYNTAX OCTET STRING (SIZE (0..32))
			MAX-ACCESS read-write
			STATUS current
			DESCRIPTION
				"record-id : <1-255>, 0 means 'no'  max 32 string"
			::= { fkV2McastIPTvCDRLogFormatControl 51 }

		
		-- 1.3.6.1.4.1.10428 9 1.102.12.4.7.4.2.52
		fkV2McastIPTvCDRFmtControlReasonNotJoined OBJECT-TYPE
			SYNTAX OCTET STRING (SIZE (0..32))
			MAX-ACCESS read-write
			STATUS current
			DESCRIPTION
				"record-id : <1-255>, 0 means 'no'  max 32 string"
			::= { fkV2McastIPTvCDRLogFormatControl 52 }

		
		-- 1.3.6.1.4.1.10428 9 1.102.12.4.7.4.3
		fkV2McastIPTvCDRLogFormatNotification OBJECT IDENTIFIER ::= { fkV2McastIPTvCDRFormat 3 }

		
		-- 1.3.6.1.4.1.10428 9 1.102.12.4.7.4.3.1
		fkV2McastIPTvCDRLogFormatCreated NOTIFICATION-TYPE
			OBJECTS { fkV2McastIPTvCDRFmtControlRequest, fkV2McastIPTvCDRFmtControlTimeStamp, fkV2McastIPTvCDRFmtControlReqResult, fkV2McastIPTvCDRFmtControlName, fkV2McastIPTvCDRFmtControlDelimiter
				 }
			STATUS current
			DESCRIPTION 
				"Description."
			::= { fkV2McastIPTvCDRLogFormatNotification 1 }

		
		-- 1.3.6.1.4.1.10428 9 1.102.12.4.7.4.3.2
		fkV2McastIPTvCDRLogFormatDeleted NOTIFICATION-TYPE
			OBJECTS { fkV2McastIPTvCDRFmtControlRequest, fkV2McastIPTvCDRFmtControlTimeStamp, fkV2McastIPTvCDRFmtControlReqResult, fkV2McastIPTvCDRFmtControlName }
			STATUS current
			DESCRIPTION 
				"Description."
			::= { fkV2McastIPTvCDRLogFormatNotification 2 }

		
		-- 1.3.6.1.4.1.10428 9 1.102.12.4.7.4.3.3
		fkV2McastIPTvCDRLogFormatChanged NOTIFICATION-TYPE
			OBJECTS { fkV2McastIPTvCDRFmtControlRequest, fkV2McastIPTvCDRFmtControlTimeStamp, fkV2McastIPTvCDRFmtControlReqResult, fkV2McastIPTvCDRFmtControlOrderRecordType, fkV2McastIPTvCDRFmtControlOrderReason, 
				fkV2McastIPTvCDRFmtControlOrderLogTime, fkV2McastIPTvCDRFmtControlOrderAN, fkV2McastIPTvCDRFmtControlOrderSubscriber, fkV2McastIPTvCDRFmtControlOrderChannel, fkV2McastIPTvCDRFmtControlOrderChannelType, 
				fkV2McastIPTvCDRFmtControlOrderStartTime, fkV2McastIPTvCDRFmtControlOrderViewingDuration }
			STATUS current
			DESCRIPTION 
				"Description."
			::= { fkV2McastIPTvCDRLogFormatNotification 3 }

		
		-- 1.3.6.1.4.1.10428 9 1.102.12.4.7.4.3.4
		fkV2McastIPTvCDRLogFormatRecordTypeChanged NOTIFICATION-TYPE
			OBJECTS { fkV2McastIPTvCDRFmtControlRequest, fkV2McastIPTvCDRFmtControlTimer, fkV2McastIPTvCDRFmtControlTimeStamp, fkV2McastIPTvCDRFmtControlJPRecId, fkV2McastIPTvCDRFmtControlJDRecId, 
				fkV2McastIPTvCDRFmtControlKJRecId, fkV2McastIPTvCDRFmtControlLPRecId, fkV2McastIPTvCDRFmtControlLDRecId, fkV2McastIPTvCDRFmtControlJPChTypeFullView, fkV2McastIPTvCDRFmtControlJPChTypePreView, 
				fkV2McastIPTvCDRFmtControlJPChTypePayPerView, fkV2McastIPTvCDRFmtControlJDReasonNoSubscriber, fkV2McastIPTvCDRFmtControlJDReasonNoChannel, fkV2McastIPTvCDRFmtControlJDReasonNotSubscribed, fkV2McastIPTvCDRFmtControlJDReasonOverQuota, 
				fkV2McastIPTvCDRFmtControlJDReasonOverMaxStream, fkV2McastIPTvCDRFmtControlJDReasonOverMaxBw, fkV2McastIPTvCDRFmtControlKJChTypeFullView, fkV2McastIPTvCDRFmtControlKJChTypePreview, fkV2McastIPTvCDRFmtControlKJChTypePayPerView, 
				fkV2McastIPTvCDRFmtControlLPReasonLeaveChannel, fkV2McastIPTvCDRFmtControlLPReasonTimeout, fkV2McastIPTvCDRFmtControlLPReasonRemoveChannel, fkV2McastIPTvCDRFmtControlLPReasonRemoveSubscriber, fkV2McastIPTvCDRFmtControlLDReasonNoSubscriber, 
				fkV2McastIPTvCDRFmtControlLDReasonNoChannel, fkV2McastIPTvCDRFmtControlLDReasonNotSubscriber, fkV2McastIPTvCDRFmtControlLDReasonNotJoined }
			STATUS current
			DESCRIPTION 
				"Description."
			::= { fkV2McastIPTvCDRLogFormatNotification 4 }

		
		-- 1.3.6.1.4.1.10428 9 1.102.12.4.7.4.3.5
		fkV2McastIPTvCDRLogFormatReasonChanged NOTIFICATION-TYPE
			OBJECTS { fkV2McastIPTvCDRFmtControlRequest, fkV2McastIPTvCDRFmtControlTimeStamp, fkV2McastIPTvCDRFmtControlReqResult, fkV2McastIPTvCDRFmtControlReasonNoSubscriber, fkV2McastIPTvCDRFmtControlReasonNoChannel, 
				fkV2McastIPTvCDRFmtControlReasonNotSubscribed, fkV2McastIPTvCDRFmtControlReasonOverQuota, fkV2McastIPTvCDRFmtControlReasonOverMaxStream, fkV2McastIPTvCDRFmtControlReasonOverMaxBx, fkV2McastIPTvCDRFmtControlReasonLeaveChannel, 
				fkV2McastIPTvCDRFmtControlReasonTimeout, fkV2McastIPTvCDRFmtControlReasonRemoveChannel, fkV2McastIPTvCDRFmtControlReasonRemoveSubscriber, fkV2McastIPTvCDRFmtControlReasonNotJoined }
			STATUS current
			DESCRIPTION 
				"Description."
			::= { fkV2McastIPTvCDRLogFormatNotification 5 }

		
--  1.3.6.1.4.1.10428 9 1.102.12.4
		-- 1.3.6.1.4.1.10428 9 1.102.12.5
		fkV2McastGroup OBJECT-GROUP
			OBJECTS { fkV2M4RouteGroup, fkV2M4RouteSource, fkV2M4RouteSrcMask, fkV2M4RouteInInterface, fkV2M4RouteUpstreamNeighbor, 
				fkV2M4RouteUpTime, fkV2MRouteExpiryTime, fkV2M4RouteMcProtocol, fkV2M4RouteRtProtocol, fkV2M4RouteRtAddress, 
				fkV2M4RouteRtMask, fkV2M4RouteRtType, fkV2M4RouteOutIfCount, fkV2M4RouteOutInterface, fkV2M4RouteFlags, 
				fkV2M4RouteStsFwdPkts, fkV2M4RouteStsFwdBytes, fkV2M4RouteStsRegSentPkts, fkV2M4RouteNextHopIfIndex, fkV2M4RouteNextHopAddress, 
				fkV2M4RouteNextHopState, fkV2M4RouteNextHopUpTime, fkV2M4RouteNextHopExpiryTime, fkV2M4RouteNextHopProtocol, fkV2M4RouteNextHopClosestMemberHops, 
				fkV2M4RouteNextHopPkts, fkV2M4RouteIfIndex, fkV2M4RouteIfName, fkV2M4RouteIfTtl, fkV2M4RouteIfRateLimit, 
				fkV2M4RouteIfProtocol, fkV2M4RouteIfInMcastOctets, fkV2M4RouteIfOutMcastOctets, fkV2IgmpIfIndex, fkV2IgmpIfActivity, 
				fkV2IgmpIfVersion, fkV2IgmpIfQueryInterval, fkV2IgmpIfQuerierTimeOut, fkV2IgmpIfMaxResponseTime, fkV2IgmpIfLastMembQueryCount, 
				fkV2IgmpIfLastMembQueryIntvl, fkV2IgmpIfFastLeaveGroupList, fkV2IgmpIfQuerierUptime, fkV2IgmpIfQuerierExpireTime, fkV2IgmpIfWrongVersionQueriers, 
				fkV2IgmpIfGroupMembIntvl, fkV2IgmpIfAccessGroup, fkV2IgmpIfRobustness, fkV2IgmpIfJoins, fkV2IgmpIfGroups, 
				fkV2IgmpCacheGroup, fkV2IgmpCacheLastReporter, fkV2IgmpCacheVersion, fkV2IgmpCacheSourceFilterMode, fkV2IgmpCacheExcludeModeExpiryTimer, 
				fkV2IgmpCacheUpTime, fkV2IgmpCacheExpiryTime, fkV2IgmpCacheVersion1HostTimer, fkV2IgmpCacheVersion2HostTimer, fkV2IgmpSsmMapGroup, 
				fkV2IgmpSsmMapSource, fkV2IgmpSsmMapType, fkV2IgmpSsmMapExpire, fkV2Mvr4PortIndex, fkV2Mvr4PortType, 
				fkV2Mvr4GroupAddress, fkV2Mvr4GroupVlanIndex, fkV2Pim4VlanIndex, fkV2Pim4VlanAdminActivity, fkV2Pim4VlanOperActivity, 
				fkV2M4RouteStsWrongIfPkts, fkV2IghVlanIndex, fkV2IghVlanHelperAddress, fkV2IghVlanOperAddress, fkV2IghGroupAddress, 
				fkV2IghGroupSource, fkV2IghGroupPortIndex, fkV2IgmpIfQuerierState, fkV2IgmpIfQuerierAddress, fkV2IgsVlanIndex, 
				fkV2IgsVlanActivity, fkV2IgsVlanVersion, fkV2IgsVlanFastLeave, fkV2IgsVlanFastBlock, fkV2IgsVlanMRtLearningMode, 
				fkV2IgsVlanMRtDynamicPortMap, fkV2IgsVlanMRtStaticPortMap, fkV2IgsVlanReportSuppression, fkV2IgsVlanQuerierActivity, fkV2IgsVlanQueryInterval, 
				fkV2IgfPortIndex, fkV2IgfPortProfileIndex, fkV2IgfPortMaxGroupCount, fkV2IgfPortMaxGroupAction, fkV2IgfpRangeStartAddress, 
				fkV2IgfpRangeEndAddress, fkV2IgsGroupAddress, fkV2IgsGroupPortIndex, fkV2IgsGroupSourceFilterMode, fkV2IgsGroupExcludeModeExpiryTimer, 
				fkV2IgsGroupUpTime, fkV2IgsGroupExpiryTime, fkV2IgsReporterAddress, fkV2IgsReporterExpiryTime, fkV2IgsReporterMac, 
				fkV2IgfProfileIndex, fkV2IgfProfilePermission, fkV2IgsVlanRobustness, fkV2IgsVlanMaxResponseTime, fkV2IgsVlanQuerierTimeOut, 
				fkV2IgsVlanLastMembQueryIntvl, fkV2IgsVlanLastMembQueryCount, fkV2IgsVlanQuerierState, fkV2IgsVlanQuerierVersion, fkV2IgsVlanQuerierAddress, 
				fkV2IgsVlanQuerierPortIndex, fkV2IgsVlanQuerierUptime, fkV2IgsVlanQuerierExpireTime, fkV2IgsVlanTcnFloodActivity, fkV2IgsVlanExplicitTracking, 
				fkV2IgsVlanTxGeneralQueries, fkV2IgsVlanTxSpecialQueries, fkV2IgsVlanTxReportMessages, fkV2IgsVlanTxLeaveMessages, fkV2IgsVlanRxGeneralQueries, 
				fkV2IgsVlanRxSpecialQueries, fkV2IgsVlanRxReportMessages, fkV2IgsVlanRxLeaveMessages, fkV2IgsVlanRxValidMessages, fkV2IgsVlanRxWrongMessages, 
				fkV2IgmpSourceAddress, fkV2IgmpSourceType, fkV2IgsSourceAddress, fkV2IgsSourceType, fkV2IgsSourceUpTime, 
				fkV2IgsSourceExpiryTime, fkV2M4RouteStsRegNackRecvMsg, fkV2M4RouteStsRegAckRecvMsg, fkV2M4RouteStsImmediateSentMsg, fkV2M4RouteStsTimedSentMsg, 
				fkV2M4RouteStsWrongvifSentMsg, fkV2M4RouteStsWholepktSentMsg, fkV2M4RouteStsWrongvifRecvMsg, fkV2M4RouteStsWholepktRecvMsg, fkV2IgsVlanVersionMode, 
				fkV2IgfProfileName, fkV2IgmpIfMRouteProxyIfIndex, fkV2IgmpIfMRouteProxyStatus, fkV2IgmpIfStartupQueryInterval, fkV2IgmpIfUnsolictedReportInterval, 
				fkV2IgsPortIndex, fkV2IgsPortFastLeave, fkV2IgmpIfExceptGroup, fkV2IgmpIfLimit, fkV2IgmpIfLeaves, 
				fkV2IgsStatsRxTopoNotifications, fkV2IgsStatsv3ToIncluded, fkV2IgsStatsv3ToExcluded, fkV2IgsStatsRxFilteredPackets, fkV2IgsStatsv3Allows, 
				fkV2IgsStatsv3Blocks, fkV2IgsStatsv3IsIncluded, fkV2IgsStatsv3IsExcluded, fkV2IgsStatsRxLeaves, fkV2IgsStatsRxValidPackets, 
				fkV2IgsStatsRxInvalidPackets, fkV2IgsStatsRxOtherPackets, fkV2IgsStatsRxMacGeneralQueries, fkV2IgsStatsTxLeaves, fkV2IgsStatsRxGeneralQueries, 
				fkV2IgsStatsRxGroupSpecificQueies, fkV2IgsStatsRxReports, fkV2IgsStatsPortIndex, fkV2IgsStatsTxGeneralQueries, fkV2IgsStatsTxGroupSpecificQueies, 
				fkV2IgsStatsTxReports, fkV2IgmpSRunningState, fkV2IgmpSRunningLastLeaved, fkV2IgmpSRunningLastJoined, fkV2IgmpSRunningTotalUptime, 
				fkV2IgmpSRunningSourceAddr, fkV2IgmpSRunningGroupAddr, fkV2IgmpGRunningState, fkV2IgmpGRunningLastLeaved, fkV2IgmpGRunningLastJoined, 
				fkV2IgmpGRunningTotalUptime, fkV2IgmpGRunningGroupAddr, fkV2M4RouteInfoActivity, fkV2M4RouteInfoLimit, fkV2M4RouteInfoThreshold, 
				fkV2M4RouteInfoUnknownFlood, fkV2M4RouteInfoEntryCount, fkV2M4RouteInfoNocacheRecvMsg, fkV2M4RouteInfoWholepktRecvMsg, fkV2M4RouteInfoWrongvifRecvMsg, 
				fkV2M4RouteInfoNocacheSentMsg, fkV2M4RouteInfoWholepktSentMsg, fkV2M4RouteInfoWrongvifSentMsg, fkV2M4RouteInfoControlRequest, fkV2M4RouteInfoControlStatus, 
				fkV2M4RouteInfoControlTimer, fkV2M4RouteInfoControlTimeStamp, fkV2M4RouteInfoControlReqResult, fkV2M4RouteInfoControlActivity, fkV2M4RouteInfoControlLimit, 
				fkV2M4RouteInfoControlThreshold, fkV2M4RouteInfoControlUnknownFlood, fkV2M4RouteControlRequest, fkV2M4RouteControlStatus, fkV2M4RouteControlTimer, 
				fkV2M4RouteControlTimeStamp, fkV2M4RouteControlReqResult, fkV2M4RouteControlGroup, fkV2M4RouteControlSource, fkV2M4RouteControlSrcMask, 
				fkV2M4RouteControlMcastProtocol, fkV2M4RouteIfControlRequest, fkV2M4RouteIfControlStatus, fkV2M4RouteIfControlTimer, fkV2M4RouteIfControlTimeStamp, 
				fkV2M4RouteIfControlReqResult, fkV2M4RouteIfControlIndex, fkV2M4RouteIfControlTtl, fkV2M4RouteIfControlRateLimit, fkV2IgmpInfoSnoopActivity, 
				fkV2IgmpInfoSnoopVersion, fkV2IgmpInfoSnoopVersionMode, fkV2IgmpInfoSnoopFastLeave, fkV2IgmpInfoSnoopFastBlock, fkV2IgmpInfoSnoopReportSuppression, 
				fkV2IgmpInfoSnoopQuerierActivity, fkV2IgmpInfoSnoopQueryInterval, fkV2IgmpInfoSnoopMaxResponseTime, fkV2IgmpInfoSnoopLastMembQueryIntvl, fkV2IgmpInfoTcnFloodActivity, 
				fkV2IgmpInfoTcnQuerySolicitActivity, fkV2IgmpInfoTcnFloodQueryCount, fkV2IgmpInfoExplicitTracking, fkV2IgmpInfoMvrActivity, fkV2IgmpInfoTcnQuerySolicitAddress, 
				fkV2IgmpInfoControlRequest, fkV2IgmpInfoControlStatus, fkV2IgmpInfoControlTimer, fkV2IgmpInfoControlTimeStamp, fkV2IgmpInfoControlReqResult, 
				fkV2IgmpInfoControlSnoopActivity, fkV2IgmpInfoControlSnoopVersion, fkV2IgmpInfoControlSnoopFastLeave, fkV2IgmpInfoControlSnoopFastBlock, fkV2IgmpInfoControlSnoopReportSuppression, 
				fkV2IgmpInfoControlSnoopQuerierActivity, fkV2IgmpInfoControlSnoopQueryInterval, fkV2IgmpInfoControlSnoopMaxResponseTime, fkV2IgmpInfoControlSnoopLastMembQueryIntvl, fkV2IgmpInfoControlTcnFloodActivity, 
				fkV2IgmpInfoControlTcnQuerySolicitActivity, fkV2IgmpInfoControlTcnFloodQueryCount, fkV2IgmpInfoControlExplicitTracking, fkV2IgmpInfoControlMvrActivity, fkV2IgmpInfoControlTcnQuerySolicitAddress, 
				fkV2IghVlanControlRequest, fkV2IghVlanControlStatus, fkV2IghVlanControlTimer, fkV2IghVlanControlTimeStamp, fkV2IghVlanControlReqResult, 
				fkV2IghVlanControlIndex, fkV2IghVlanControlHelperAddress, fkV2IghGroupControlRequest, fkV2IghGroupControlStatus, fkV2IghGroupControlTimer, 
				fkV2IghGroupControlTimeStamp, fkV2IghGroupControlReqResult, fkV2IghGroupControlVlanIndex, fkV2IghGroupControlAddress, fkV2IghGroupControlSource, 
				fkV2IghGroupControlPortIndex, fkV2IgmpSsmMapControlRequest, fkV2IgmpSsmMapControlStatus, fkV2IgmpSsmMapControlTimer, fkV2IgmpSsmMapControlTimeStamp, 
				fkV2IgmpSsmMapControlReqResult, fkV2IgmpSsmMapControlGroup, fkV2IgmpSsmMapControlSource, fkV2IgmpIfControlRequest, fkV2IgmpIfControlStatus, 
				fkV2IgmpIfControlTimer, fkV2IgmpIfControlTimeStamp, fkV2IgmpIfControlReqResult, fkV2IgmpIfControlIndex, fkV2IgmpIfControlActivity, 
				fkV2IgmpIfControlVersion, fkV2IgmpIfControlQueryInterval, fkV2IgmpIfControlQuerierTimeOut, fkV2IgmpIfControlMaxResponseTime, fkV2IgmpIfControlLastMembQueryCount, 
				fkV2IgmpIfControlLastMembQueryIntvl, fkV2IgmpIfControlFastLeaveGroupList, fkV2IgmpIfControlAccessGroup, fkV2IgmpIfControlRobustness, fkV2IgmpIfControlMRouteProxyIfIndex, 
				fkV2IgmpIfControlProxyStatus, fkV2IgmpIfControlStartupQueryInterval, fkV2IgmpIfControlUnsolictedReportInterval, fkV2IgmpIfControlLimit, fkV2IgmpIfControlExceptGroup, 
				fkV2IgmpSourceControlRequest, fkV2IgmpSourceControlStatus, fkV2IgmpSourceControlTimer, fkV2IgmpSourceControlTimeStamp, fkV2IgmpSourceControlReqResult, 
				fkV2IgmpSourceControlIfIndex, fkV2IgmpSourceControlGroup, fkV2IgmpSourceControlAddress, fkV2IgmpGStateControlRequest, fkV2IgmpGStateControlStatus, 
				fkV2IgmpGStateControlTimer, fkV2IgmpGStateControlTimeStamp, fkV2IgmpGStateControlRequestResult, fkV2IgmpGStateControlGroupAddr, fkV2IgmpGStateControlSourceAddr, 
				fkV2IgsVlanControlRequest, fkV2IgsVlanControlStatus, fkV2IgsVlanControlTimer, fkV2IgsVlanControlTimeStamp, fkV2IgsVlanControlReqResult, 
				fkV2IgsVlanControlIndex, fkV2IgsVlanControlActivity, fkV2IgsVlanControlVersion, fkV2IgsVlanControlFastLeave, fkV2IgsVlanControlFastBlock, 
				fkV2IgsVlanControlMRtLearningMode, fkV2IgsVlanControlMRtStaticPortMap, fkV2IgsVlanControlReportSuppression, fkV2IgsVlanControlQuerierActivity, fkV2IgsVlanControlQueryInterval, 
				fkV2IgsVlanControlRobustness, fkV2IgsVlanControlMaxResponseTime, fkV2IgsVlanControlQuerierTimeOut, fkV2IgsVlanControlLastMembQueryIntvl, fkV2IgsVlanControlTcnFloodActivity, 
				fkV2IgsVlanControlExplicitTracking, fkV2IgsSourceControlRequest, fkV2IgsSourceControlStatus, fkV2IgsSourceControlTimer, fkV2IgsSourceControlTimeStamp, 
				fkV2IgsSourceControlReqResult, fkV2IgsSourceControlVlanIndex, fkV2IgsSourceControlGroup, fkV2IgsSourceControlPortIndex, fkV2IgsSourceControlAddress, 
				fkV2IgsPortControlRequest, fkV2IgsPortControlStatus, fkV2IgsPortControlTimer, fkV2IgsPortControlTimeStamp, fkV2IgsPortControlReqResult, 
				fkV2IgsPortControlIndex, fkV2IgsPortControlFastLeave, fkV2IgsStatsControlRequest, fkV2IgsStatsControlStatus, fkV2IgsStatsControlControlTimer, 
				fkV2IgsStatsControlTimeStamp, fkV2IgsStatsControlReqResult, fkV2IgsStatsControlIndex, fkV2IgfProfileControlRequest, fkV2IgfProfileControlStatus, 
				fkV2IgfProfileControlTimer, fkV2IgfProfileControlTimeStamp, fkV2IgfProfileControlReqResult, fkV2IgfProfileControlIndex, fkV2IgfProfileControlPermission, 
				fkV2IgfProfileControlName, fkV2IgfpRangeControlRequest, fkV2IgfpRangeControlStatus, fkV2IgfpRangeControlTimer, fkV2IgfpRangeControlTimeStamp, 
				fkV2IgfpRangeControlReqResult, fkV2IgfpRangeControlProfileIndex, fkV2IgfpRangeControlStartAddress, fkV2IgfpRangeControlEndAddress, fkV2IgfPortControlRequest, 
				fkV2IgfPortControlStatus, fkV2IgfPortControlTimer, fkV2IgfPortControlTimeStamp, fkV2IgfPortControlReqResult, fkV2IgfPortControlIndex, 
				fkV2IgfPortControlProfileIndex, fkV2IgfPortControlMaxGroupCount, fkV2IgfPortControlMaxGroupAction, fkV2Mvr4PortControlRequest, fkV2Mvr4PortControlStatus, 
				fkV2Mvr4PortControlTimer, fkV2Mvr4PortControlTimeStamp, fkV2Mvr4PortControlReqResult, fkV2Mvr4PortControlIndex, fkV2Mvr4PortControlType, 
				fkV2Mvr4GroupControlRequest, fkV2Mvr4GroupControlStatus, fkV2Mvr4GroupControlTimer, fkV2Mvr4GroupControlTimeStamp, fkV2Mvr4GroupControlReqResult, 
				fkV2Mvr4GroupControlAddress, fkV2Mvr4GroupControlVlanIndex, fkV2Pim4InfoSnoopActivity, fkV2Pim4InfoControlRequest, fkV2Pim4InfoControlStatus, 
				fkV2Pim4InfoControlTimer, fkV2Pim4InfoControlTimeStamp, fkV2Pim4InfoControlReqResult, fkV2Pim4InfoControlSnoopActivity, fkV2Pim4VlanControlRequest, 
				fkV2Pim4VlanControlStatus, fkV2Pim4VlanControlTimer, fkV2Pim4VlanControlTimeStamp, fkV2Pim4VlanControlReqResult, fkV2Pim4VlanControlIndex, 
				fkV2Pim4VlanControlAdminActivity, fkV2IgmpInfoTcnQueryInterval, fkV2IgmpInfoControlTcnQueryInterval, fkV2IgsPortControlExplicitTrackingMaxHosts, fkV2IgsPortExplicitTrackingMaxHosts, 
				fkV2IgsReporterMode, fkV2IgsReporterVersion, fkV2IgmpProxyIfIndex, fkV2IgmpProxyIfMRouteIfIndex, fkV2IgmpProxyIfControlRequest, 
				fkV2IgmpProxyIfControlStatus, fkV2IgmpProxyIfControlTimer, fkV2IgmpProxyIfControlTimeStamp, fkV2IgmpProxyIfControlReqResult, fkV2IgmpProxyIfControlIndex, 
				fkV2IgmpProxyIfControlMrouteIfIndex, fkV2IgsSourceSsmMapped, fkV2IgmpSourceUpTime, fkV2IgmpSourceExpiryTime, fkV2IgmpSourceSsmMapped, 
				fkV2IgmpProxyIfService, fkV2IgmpProxyIfMRouteQuerySIpMode, fkV2IgmpProxyIfMRouteQuerySIpAddr, fkV2IgmpProxyIfServiceSIpMode, fkV2IgmpProxyIfServiceSIpAddr, 
				fkV2IgfPortDhcpSnoopBindingPermission, fkV2IgfPortControlDhcpSnoopBindingPermission, fkV2IgmpIfVerifySrcIp, fkV2IgmpIfControlVerifySrcIp, fkV2IgmpInfoVerifyTTL, 
				fkV2IgmpInfoControlVerifyTTL, fkV2IgmpProxyIfControlService, fkV2IgmpProxyIfControlMrouteQuerySIpMode, fkV2IgmpProxyIfControlServiceSIpMode, fkV2IgfPortPacketType, 
				fkV2IgfPortControlPacketType, fkV2McastIPTvSubscriberDescription, fkV2McastIPTvSubscriberControlDescription, fkV2IgmpProxyIfServicePriority, fkV2IgmpProxyMultipath, 
				fkV2IgmpProxyInfoControlRequest, fkV2IgmpProxyInfoControlStatus, fkV2IgmpProxyInfoControlTimer, fkV2IgmpProxyInfoControlTimeStamp, fkV2IgmpProxyInfoControlReqResult, 
				fkV2IgmpProxyInfoControlMultipath, fkV2IgsSourceVId, fkV2IgsSourcenGrpAddr, fkV2IgsSourcePort, fkV2IgsVlanStatsVlanIndex, 
				fkV2IgsVlanStatsTxGeneralQueries, fkV2IgsVlanStatsTxGroupSpecificQueies, fkV2IgsVlanStatsTxReports, fkV2IgsVlanStatsTxLeaves, fkV2IgsVlanStatsRxGeneralQueries, 
				fkV2IgsVlanStatsRxGroupSpecificQueies, fkV2IgsVlanStatsRxReports, fkV2IgsVlanStatsRxLeaves, fkV2IgsVlanStatsRxValidPackets, fkV2IgsVlanStatsRxInvalidPackets, 
				fkV2IgsVlanStatsRxOtherPackets, fkV2IgsVlanStatsRxMacGeneralQueries, fkV2IgsVlanStatsRxTopoNotifications, fkV2IgsVlanStatsv3Allows, fkV2IgsVlanStatsv3Blocks, 
				fkV2IgsVlanStatsv3IsIncluded, fkV2IgsVlanStatsv3IsExcluded, fkV2IgsVlanStatsv3ToIncluded, fkV2IgsVlanStatsv3ToExcluded, fkV2IgsVlanStatsRxFilteredPackets, 
				fkV2IgsVlanStatsControlRequest, fkV2IgsVlanStatsControlStatus, fkV2IgsVlanStatsControlControlTimer, fkV2IgsVlanStatsControlTimeStamp, fkV2IgsVlanStatsControlReqResult, 
				fkV2IgsVlanStatsControlIndex, fkV2IgsPortMrouter, fkV2IgsPortControlMrouter, fkV2IgmpInfoSnoopTcnQueryGeneralStatus, fkV2IgmpInfoSnoopTcnQueryGeneralMaxResponseTime, 
				fkV2IgmpInfoControlSnoopTcnQueryGeneralStatus, fkV2IgmpInfoControlSnoopTcnQueryGeneralMaxResponseTime, fkV2IgsGroupPortInfo, fkV2IgsSourcePortInfo, fkV2IgsReporterPortInfo, 
				fkV2IgsVlanStatsTotalRxReports, fkV2IgsVlanStatsUnsuccessRxReports, fkV2IgmpinfoSnoopMrouterCpu, fkV2IgmpinfoControlSnoopMrouterCpu, fkV2IgmpInfoMaxGroupSystemCnt, 
				fkV2IgmpInfoControlMaxGroupSystemCnt, fkV2IgmpInfoSnoopMRtLearningMode, fkV2IgmpInfoControlSnoopMRtLearningMode, fkV2IgmpProxyIfControlServiceSIpAddr, fkV2M4RoutInfoIpMrouteJoinedCount, 
				fkV2IgmpInfoSnoopExplicitTrackingMacBased, fkV2IgmpInfoControlSnoopExplicitTrackingMacBased, fkV2IghJoinAddress, fkV2IghJoinSource, fkV2IghJoinPortIndex, 
				fkV2IghJoinReporter, fkV2IghJoinControlRequest, fkV2IghJoinControlStatus, fkV2IghJoinControlTimer, fkV2IghJoinControlTimeStamp, 
				fkV2IghJoinControlReqResult, fkV2IghJoinControlVlanIndex, fkV2IghJoinControlAddress, fkV2IghJoinControlSource, fkV2IghJoinControlPortIndex, 
				fkV2IghJoinControlReporter, fkV2IghJoinProfilePortIndex, fkV2IghJoinProfileId, fkV2IghJoinProfileReporter, fkV2IghJoinProfileControlRequest, 
				fkV2IghJoinProfileControlStatus, fkV2IghJoinProfileControlTimer, fkV2IghJoinProfileControlTimeStamp, fkV2IghJoinProfileControlReqResult, fkV2IghJoinProfileControlVlanIndex, 
				fkV2IghJoinProfileControlPortIndex, fkV2IghJoinProfileControlId, fkV2IghJoinProfileControlReporter, fkV2IghGroupProfilePortIndex, fkV2IghGroupProfileId, 
				fkV2IghGroupProfileControlRequest, fkV2IghGroupProfileControlStatus, fkV2IghGroupProfileControlTimer, fkV2IghGroupProfileControlTimeStamp, fkV2IghGroupProfileControlReqResult, 
				fkV2IghGroupProfileControlVlanIndex, fkV2IghGroupProfileControlPortIndex, fkV2IghGroupProfileControlId, fkV2IgsPortExplicitTrackingMacBased, fkV2IgsPortDot1qSelection, 
				fkV2IgsPortControlExplicitTrackingMacBased, fkV2IgsPortControlDot1qSelection, fkV2IgmpCounterInfoGroupCount, fkV2IgmpCounterInfoSnoopingCount, fkV2McastIPTvInfoCacState, 
				fkV2McastIPTvInfoPackageLimit, fkV2McastIPTvInfoPreviewProfileLimit, fkV2McastIPTvInfoChannelLimit, fkV2McastIPTvInfoCacProfileLimit, fkV2McastIPTvInfoSubscriberLimit, 
				fkV2McastIPTvInfoSubscriberHistoryLimit, fkV2McastIPTvInfoFullviewRecogTime, fkV2McastIPTvInfoControlRequest, fkV2McastIPTvInfoControlStatus, fkV2McastIPTvInfoControlTimer, 
				fkV2McastIPTvInfoControlTimeStamp, fkV2McastIPTvInfoControlReqResult, fkV2McastIPTvInfoControlCacState, fkV2McastIPTvInfoControlPackageLimit, fkV2McastIPTvInfoControlPreviewProfileLimit, 
				fkV2McastIPTvInfoControlChannelLimit, fkV2McastIPTvInfoControlCacProfileLimit, fkV2McastIPTvInfoControlSubscriberLimit, fkV2McastIPTvInfoContorlSubscriberHistoryLimit, fkV2McastIPTvInfoControlFullviewRecogTime, 
				fkV2McastIPTvPackageId, fkV2McastIPTvPackageDescription, fkV2McastIPTvPackagePreviewChannelCnt, fkV2McastIPTvPackageFullviewChannelCnt, fkV2McastIPTvPackageChannelId, 
				fkV2McastIPTvPackageChannelEntitlement, fkV2McastIPTvPackageControlRequest, fkV2McastIPTvPackageControlStatus, fkV2McastIPTvPackageControlTimer, fkV2McastIPTvPackageControlTimeStamp, 
				fkV2McastIPTvPackageControlReqResult, fkV2McastIPTvPackageControlId, fkV2McastIPTvPackageControlDescription, fkV2McastIPTvPackageControlPreviewChannelCnt, fkV2McastIPTvPackageControlPreviewChannelList, 
				fkV2McastIPTvPackageControlFullviewChannelCnt, fkV2McastIPTvPackageControlFullviewChannelList, fkV2McastIPTvPreviewProfileId, fkV2McastIPTvPreviewProfileMaxDuration, fkV2McastIPTvPreviewProfileMaxPreviews, 
				fkV2McastIPTvPreviewProfileBlackoutDuration, fkV2McastIPTvPreviewProfileRecognitionTime, fkV2McastIPTvPreviewProfileResetTimePeriod, fkV2McastIPTvPreviewProfileResetTime, fkV2McastIPTvPreviewProfileControlRequest, 
				fkV2McastIPTvPreviewProfileControlStatus, fkV2McastIPTvPreviewProfileControlTimer, fkV2McastIPTvPreviewProfileControlTimeStamp, fkV2McastIPTvPreviewProfileControlReqResult, fkV2McastIPTvPreviewProfileControlId, 
				fkV2McastIPTvPreviewProfileControlMaxDuration, fkV2McastIPTvPreviewProfileControlMaxPreviews, fkV2McastIPTvPreviewProfileControlBlackoutDuration, fkV2McastIPTvPreviewProfileControlRecognitionTime, fkV2McastIPTvPreviewProfileControlResetTimePeriod, 
				fkV2McastIPTvPreviewProfileControlResetTime, fkV2McastIPTvChannelId, fkV2McastIPTvChannelSourceAddress, fkV2McastIPTvChannelGroupAddress, fkV2McastIPTvChannelBandwidth, 
				fkV2McastIPTvChannelPreviewProfileId, fkV2McastIPTvChannelCacGroupId, fkV2McastIPTvChannelDescription, fkV2McastIPTvChannelPackageDescription, fkV2McastIPTvChannelControlRequest, 
				fkV2McastIPTvChannelControlStatus, fkV2McastIPTvChannelControlTimer, fkV2McastIPTvChannelControlTimeStamp, fkV2McastIPTvChannelControlReqResult, fkV2McastIPTvChannelControlId, 
				fkV2McastIPTvChannelControlSourceAddress, fkV2McastIPTvChannelControlGroupAddress, fkV2McastIPTvChannelControlBandwidth, fkV2McastIPTvChannelControlPreviewProfileId, fkV2McastIPTvChannelControlCacGroupId, 
				fkV2McastIPTvChannelControlDescription, fkV2McastIPTvChannelCurrentVlanId, fkV2McastIPTvChannelCurrentPortId, fkV2McastIPTvChannelCurrentVlanPortChannelId, fkV2McastIPTvChannelCurrentVlanPortJoinedTime, 
				fkV2McastIPTvChannelCurrentSubscriberChannelId, fkV2McastIPTvChannelCurrentSubscriberJoinedTime, fkV2McastIPTvChannelCurrentSubscriberJoinDurationTime, fkV2McastIPTvCacProfileId, fkV2McastIPTvCacProfileMaxChannel, 
				fkV2McastIPTvCacProfileMaxBandwidth, fkV2McastIPTvCacProfileCacGroupCnt, fkV2McastIPTvCacProfileDescription, fkV2McastIPTvCacProfileGroupId, fkV2McastIPTvCacProfileGroupMaxChanNum, 
				fkV2McastIPTvCacProfileControlRequest, fkV2McastIPTvCacProfileControlStatus, fkV2McastIPTvCacProfileControlTimer, fkV2McastIPTvCacProfileControlTimeStamp, fkV2McastIPTvCacProfileControlReqResult, 
				fkV2McastIPTvCacProfileControlId, fkV2McastIPTvCacProfileControlMaxStream, fkV2McastIPTvCacProfileControlMaxBandwidth, fkV2McastIPTvCacProfileControlCacGroupCnt, fkV2McastIPTvCacProfileControlCacGroupList, 
				fkV2McastIPTvCacProfileControlCacGroupMaxChanNumList, fkV2McastIPTvCacProfileControlDescription, fkV2McastIPTvSubscriberId, fkV2McastIPTvSubscriberPortType, fkV2McastIPTvSubscriberSlotId, 
				fkV2McastIPTvSubscriberPortId, fkV2McastIPTvSubscriberCTag, fkV2McastIPTvSubscriberIpAddr, fkV2McastIPTvSubscriberStatus, fkV2McastIPTvSubscriberCacProfileId, 
				fkV2McastIPTvSubscriberPackageCnt, fkV2McastIPTvSubscriberPackageId, fkV2McastIPTvSubscriberPackageStart, fkV2McastIPTvSubscriberPackageEnd, fkV2McastIPTvSubscriberControlRequest, 
				fkV2McastIPTvSubscriberControlStatus, fkV2McastIPTvSubscriberControlTimer, fkV2McastIPTvSubscriberControlTimeStamp, fkV2McastIPTvSubscriberControlReqResult, fkV2McastIPTvSubscriberControlId, 
				fkV2McastIPTvSubscriberControlPortType, fkV2McastIPTvSubscriberControlSlotId, fkV2McastIPTvSubscriberControlPortId, fkV2McastIPTvSubscriberControlCTag, fkV2McastIPTvSubscriberControlIpAddr, 
				fkV2McastIPTvSubscriberControlCacProfileId, fkV2McastIPTvSubscriberControlPackageCnt, fkV2McastIPTvSubscriberControlPackageList, fkV2McastIPTvSubscriberControlPackageTimeList, fkV2McastIPTvSubscriberHistoryIndex, 
				fkV2McastIPTvSubscriberHistoryJoinedChannelId, fkV2McastIPTvSubscriberHistoryJoinedTime, fkV2McastIPTvSubscriberHistoryControlRequest, fkV2McastIPTvSubscriberHistoryControlStatus, fkV2McastIPTvSubscriberHistoryControlTimer, 
				fkV2McastIPTvSubscriberHistoryControlTimeStamp, fkV2McastIPTvSubscriberHistoryControlReqResult, fkV2McastIPTvSubscriberHistoryControlId, fkV2McastIPTvCDRInfoStatus, fkV2McastIPTvCDRInfoKeepJoinInterval, 
				fkV2McastIPTvCDRInfoLogFileName, fkV2McastIPTvCDRInfoLogSize, fkV2McastIPTvCDRInfoExportTimeThreshold, fkV2McastIPTvCDRInfoExportTimeBegin, fkV2McastIPTvCDRInfoExportAmountThreshold, 
				fkV2McastIPTvCDRInfoSyslogPriority, fkV2McastIPTvCDRInfoANInfo, fkV2McastIPTvCDRInfoControlRequest, fkV2McastIPTvCDRInfoControlStatus, fkV2McastIPTvCDRInfoControlTimer, 
				fkV2McastIPTvCDRInfoControlTimeStamp, fkV2McastIPTvCDRInfoControlReqResult, fkV2McastIPTvCDRInfoContorlStatus, fkV2McastIPTvCDRInfoContorlKeepJoinInterval, fkV2McastIPTvCDRInfoContorlLogFileName, 
				fkV2McastIPTvCDRInfoControlLogSize, fkV2McastIPTvCDRInfoControlExportTimeThreshold, fkV2McastIPTvCDRInfoControlExportTimeBegin, fkV2McastIPTvCDRInfoControlExportAmountThreshold, fkV2McastIPTvCDRInfoControlSyslogPriority, 
				fkV2McastIPTvCDRInfoControlANInfo, fkV2McastIPTvCDRLogServerId, fkV2McastIPTvCDRLogServerIpAddress, fkV2McastIPTvCDRLogServerPort, fkV2McastIPTvCDRLogServerMode, 
				fkV2McastIPTvCDRLogServerUserId, fkV2McastIPTvCDRLogServerUserPassword, fkV2McastIPTvCDRLogServerControlRequest, fkV2McastIPTvCDRLogServerControlStatus, fkV2McastIPTvCDRLogServerControlTimer, 
				fkV2McastIPTvCDRLogServerControlTimeStamp, fkV2McastIPTvCDRLogServerControlReqResult, fkV2McastIPTvCDRLogServerControlId, fkV2McastIPTvCDRLogServerControlIpAddress, fkV2McastIPTvCDRLogServerControlPort, 
				fkV2McastIPTvCDRLogServerControlMode, fkV2McastIPTvCDRLogServerControlUserId, fkV2McastIPTvCDRLogServerControlUserPassword, fkV2McastIPTvCDRLogServerControlFileName, fkV2McastIPTvCDRLogStatsTotalCount, 
				fkV2McastIPTvCDRLogStatsJoinCount, fkV2McastIPTvCDRLogStatsKeepJoinedCount, fkV2McastIPTvCDRLogStatsLeaveCount, fkV2McastIPTvCDRLogStatsLastExportDate, fkV2McastIPTvCDRLogStatsLastExportReason, 
				fkV2McastIPTvCDRLogStatsLastExportServerList, fkV2McastIPTvCDRFmtName, fkV2McastIPTvCDRFmtDelimiter, fkV2McastIPTvCDRFmtOrderRecordType, fkV2McastIPTvCDRFmtOrderReason, 
				fkV2McastIPTvCDRFmtOrderLogTime, fkV2McastIPTvCDRFmtOrderAN, fkV2McastIPTvCDRFmtOrderSubscriber, fkV2McastIPTvCDRFmtOrderChannel, fkV2McastIPTvCDRFmtOrderChannelType, 
				fkV2McastIPTvCDRFmtOrderStartTime, fkV2McastIPTvCDRFmtOrderViewingDuration, fkV2McastIPTvCDRFmtJPRecId, fkV2McastIPTvCDRFmtJDRecId, fkV2McastIPTvCDRFmtKJRecId, 
				fkV2McastIPTvCDRFmtLPRecId, fkV2McastIPTvCDRFmtLDRecId, fkV2McastIPTvCDRFmtJPChTypeFullView, fkV2McastIPTvCDRFmtJPChTypePreView, fkV2McastIPTvCDRFmtJPChTypePayPerView, 
				fkV2McastIPTvCDRFmtJDReasonNoSubscriber, fkV2McastIPTvCDRFmtJDReasonNoChannel, fkV2McastIPTvCDRFmtJDReasonNotSubscribed, fkV2McastIPTvCDRFmtJDReasonOverQuota, fkV2McastIPTvCDRFmtJDReasonOverMaxStream, 
				fkV2McastIPTvCDRFmtJDReasonOverMaxBw, fkV2McastIPTvCDRFmtKJChTypeFullView, fkV2McastIPTvCDRFmtKJChTypePreView, fkV2McastIPTvCDRFmtKJChTypePayPerView, fkV2McastIPTvCDRFmtLPReasonLeaveChannel, 
				fkV2McastIPTvCDRFmtLPReasonTimeout, fkV2McastIPTvCDRFmtLPReasonRemoveChannel, fkV2McastIPTvCDRFmtLPReasonRemoveSubscriber, fkV2McastIPTvCDRFmtLDReasonNoSubscriber, fkV2McastIPTvCDRFmtLDReasonNoChannel, 
				fkV2McastIPTvCDRFmtLDReasonNotSubscribed, fkV2McastIPTvCDRFmtLDReasonNotJoined, fkV2McastIPTvCDRFmtReasonNoSubscriber, fkV2McastIPTvCDRFmtReasonNoChannel, fkV2McastIPTvCDRFmtReasonNotSubscribed, 
				fkV2McastIPTvCDRFmtReasonOverQuota, fkV2McastIPTvCDRFmtReasonOverMaxStream, fkV2McastIPTvCDRFmtReasonOverMaxBw, fkV2McastIPTvCDRFmtReasonLeaveChannel, fkV2McastIPTvCDRFmtReasonTimeout, 
				fkV2McastIPTvCDRFmtReasonRemoveChannel, fkV2McastIPTvCDRFmtReasonRemoveSubscriber, fkV2McastIPTvCDRFmtReasonNotJoined, fkV2McastIPTvCDRFmtControlRequest, fkV2McastIPTvCDRFmtControlStatus, 
				fkV2McastIPTvCDRFmtControlTimer, fkV2McastIPTvCDRFmtControlTimeStamp, fkV2McastIPTvCDRFmtControlReqResult, fkV2McastIPTvCDRFmtControlName, fkV2McastIPTvCDRFmtControlDelimiter, 
				fkV2McastIPTvCDRFmtControlOrderRecordType, fkV2McastIPTvCDRFmtControlOrderReason, fkV2McastIPTvCDRFmtControlOrderLogTime, fkV2McastIPTvCDRFmtControlOrderAN, fkV2McastIPTvCDRFmtControlOrderSubscriber, 
				fkV2McastIPTvCDRFmtControlOrderChannel, fkV2McastIPTvCDRFmtControlOrderChannelType, fkV2McastIPTvCDRFmtControlOrderStartTime, fkV2McastIPTvCDRFmtControlOrderViewingDuration, fkV2McastIPTvCDRFmtControlJPRecId, 
				fkV2McastIPTvCDRFmtControlJDRecId, fkV2McastIPTvCDRFmtControlKJRecId, fkV2McastIPTvCDRFmtControlLPRecId, fkV2McastIPTvCDRFmtControlLDRecId, fkV2McastIPTvCDRFmtControlJPChTypeFullView, 
				fkV2McastIPTvCDRFmtControlJPChTypePreView, fkV2McastIPTvCDRFmtControlJPChTypePayPerView, fkV2McastIPTvCDRFmtControlJDReasonNoSubscriber, fkV2McastIPTvCDRFmtControlJDReasonNoChannel, fkV2McastIPTvCDRFmtControlJDReasonNotSubscribed, 
				fkV2McastIPTvCDRFmtControlJDReasonOverQuota, fkV2McastIPTvCDRFmtControlJDReasonOverMaxStream, fkV2McastIPTvCDRFmtControlJDReasonOverMaxBw, fkV2McastIPTvCDRFmtControlKJChTypeFullView, fkV2McastIPTvCDRFmtControlKJChTypePreview, 
				fkV2McastIPTvCDRFmtControlKJChTypePayPerView, fkV2McastIPTvCDRFmtControlLPReasonLeaveChannel, fkV2McastIPTvCDRFmtControlLPReasonTimeout, fkV2McastIPTvCDRFmtControlLPReasonRemoveChannel, fkV2McastIPTvCDRFmtControlLPReasonRemoveSubscriber, 
				fkV2McastIPTvCDRFmtControlLDReasonNoSubscriber, fkV2McastIPTvCDRFmtControlLDReasonNoChannel, fkV2McastIPTvCDRFmtControlLDReasonNotSubscriber, fkV2McastIPTvCDRFmtControlLDReasonNotJoined, fkV2McastIPTvCDRFmtControlReasonNoSubscriber, 
				fkV2McastIPTvCDRFmtControlReasonNoChannel, fkV2McastIPTvCDRFmtControlReasonNotSubscribed, fkV2McastIPTvCDRFmtControlReasonOverQuota, fkV2McastIPTvCDRFmtControlReasonOverMaxStream, fkV2McastIPTvCDRFmtControlReasonOverMaxBx, 
				fkV2McastIPTvCDRFmtControlReasonLeaveChannel, fkV2McastIPTvCDRFmtControlReasonTimeout, fkV2McastIPTvCDRFmtControlReasonRemoveChannel, fkV2McastIPTvCDRFmtControlReasonRemoveSubscriber, fkV2McastIPTvCDRFmtControlReasonNotJoined
				 }
			STATUS current
			DESCRIPTION 
				"Description."
			::= { fkV2Multicast 5 }

		
--  1.3.6.1.4.1.10428 9 1.102.12.5
		-- 1.3.6.1.4.1.10428 9 1.102.12.6
		fkV2McastNotificationGroup NOTIFICATION-GROUP
			NOTIFICATIONS { fkV2IghVlanProfileChanged, fkV2IghGroupCreated, fkV2IghGroupDestroyed, fkV2IgmpInterfaceActivityChanged, fkV2IgmpInterfaceProfileChanged, 
				fkV2IgsVlanCreated, fkV2IgsVlanDestroyed, fkV2IgsVlanProfileChanged, fkV2IgsVlanMRouteProfileChanged, fkV2IgsVlanQuerierProfileChanced, 
				fkV2IgsVlanTcnProfileChanced, fkV2IgsVlanStatisticsCleared, fkV2IgfPortProfileChanged, fkV2IgfPortMaxGroupChanged, fkV2M4RouteInfoActivityChanged, 
				fkV2M4RouteInfoLimitChanged, fkV2M4RouteInfoUnkwonFloodChanged, fkV2IgmpInfoSnoopActivityChanged, fkV2IgmpInfoTcnProfileChanged, fkV2IgmpInfoMvrActivityChanged, 
				fkV2IgmpSsmMapCreated, fkV2IgmpSsmMapDestroyed, fkV2Pim4InfoSnoopingActivityChanged, fkV2Pim4VlanActivityChanged, fkV2Mvr4GroupCreated, 
				fkV2Mvr4GroupDestroyed, fkV2M4RouteEntryDestroyed, fkV2M4RouteInterfaceProfileChanged, fkV2IgmpInfoQuerierProfileChanged, fkV2Mvr4PortProfileChanged, 
				fkV2IgmpSourceCreated, fkV2IgmpSourceDestroyed, fkV2IgsSourceCreated, fkV2IgsSourceDestroyed, fkV2IghGroupCleared, 
				fkV2IgfpRangeAdded, fkV2IgfpRangeDeleted, fkV2M4RoutAllStatisticsCleared, fkV2IgmpInterfaceMrouteChanged, fkV2IgmpInterfaceProxyServiceChanged, 
				fkV2IgsPortrofileChanged, fkV2IgmpInterfaceStatsCleared, fkV2IgsStatsCleared, fkV2IgmpGStateAllCleared, fkV2IgmpGStateSessionCleared, 
				fkV2IgmpGStateGroupCleared, fkV2IgmpInfoTcnProfileSolicitAddressChanged, fkV2IgmpInfoTcnProfileQueryIntervalChanged, fkV2IgsPortExplicitTrackingMaxHostsChanged, fkV2IgmpProxyInterfaceMrouteChanged, 
				fkV2IgmpProxyInterfaceServiceChanged, fkV2IgfPortDhcpSnoopBindingPermissionChanged, fkV2IgmpInterfaceVerifySrcIpChanged, fkV2IgmpInfoVerifyTTLChanged, fkV2IgmpInfoSnoopExplicitTrackingMacBasedChanged, 
				fkV2IghJoinCreated, fkV2IghJoinDestroyed, fkV2IghJoinCleared, fkV2IghJoinProfileCreated, fkV2IghJoinProfileDestroyed, 
				fkV2IghGroupProfileCreated, fkV2IghGroupProfileDestroyed, fkV2IgsPortExplicitTrackingMacBasedChanged, fkV2IgsPortDot1qChanged, fkV2McastIPTvInfoCacStateChanged, 
				fkV2McastIPTvInfoLimitChanged, fkV2McastIPTvInfoFullviewRecogTimeChanged, fkV2McastIPTvPackageCreated, fkV2McastIPTvPackageChanged, fkV2McastIPTvPackageDeleted, 
				fkV2McastIPTvPackageAddChannel, fkV2McastIPTvPackageRemoveChannel, fkV2McastIPTvPreviewProfileCreated, fkV2McastIPTvPreviewProfileChanged, fkV2McastIPTvPreviewProfileDeleted, 
				fkV2McastIPTvPreviewProfileResetChanged, fkV2McastIPTvPreviewInstantReset, fkV2McastIPTvChannelCreated, fkV2McastIPTvChannelChanged, fkV2McastIPTvChannelDeleted, 
				fkV2McastIPTvCacProfileCreated, fkV2McastIPTvCacProfileChanged, fkV2McastIPTvCacProfileDeleted, fkV2McastIPTvCacProfileAddGroup, fkV2McastIPTvCacProfileDelGroup, 
				fkV2McastIPTvSubscriberCreated, fkV2McastIPTvSubscriberChanged, fkV2McastIPTvSubscriberDeleted, fkV2McastIPTvSubscriberAddPackage, fkV2McastIPTvSubscriberRemovePackage, 
				fkV2McastIPTvSubscriberSuspend, fkV2McastIPTvSubscriberResume, fkV2McastIPTvSubscriberHistoryCleared, fkV2McastIPTvCDRInfoStatusChanged, fkV2McastIPTvCDRInfoEventProfileChanged, 
				fkV2McastIPTvCDRInfoLogFileProfileChanged, fkV2McastIPTvCDRInfoExportProfileChanged, fkV2McastIPTvCDRInfoSyslogPriorityChanged, fkV2McastIPTvCDRLogServerCreated, fkV2McastIPTvCDRLogServerDeleted, 
				fkV2McastIPTvCDRLogServerUploadCDR, fkV2McastIPTvCDRLogServerUploadCDRManual, fkV2McastIPTvCDRLogFormatCreated, fkV2McastIPTvCDRLogFormatDeleted, fkV2McastIPTvCDRLogFormatChanged, 
				fkV2McastIPTvCDRLogFormatRecordTypeChanged, fkV2McastIPTvCDRLogFormatReasonChanged, fkV2IgfPortPacketTypeChanged, fkV2McastIPTvSubscriberDescChanged, fkV2IgmpProxyMultipathChanged, 
				fkV2IgmpProxyInterfaceMrouteDeleted, fkV2IgsVlanStatsCleared, fkV2IgsPortMrouterchanged, fkV2IgmpInfoSnoopTcnQueryGeneralChanged, fkV2IgmpinfoSnoopMrouterCpuChanged, 
				fkV2IgmpInfoMaxGroupSystemCntChanged, fkV2IgmpInfoMaxGroupSystemCntDeleted, fkV2IgmpInfoSnoopMRouteProfileChanged, fkV2M4RoutStatisticsCleared, fkV2M4RoutAllEntriesCleared, 
				fkV2IgfProfileCreated, fkV2IgfProfileDestroyed, fkV2IgfProfileChanged, fkV2IgfProfileByNameCreated, fkV2IgmpProxyInterfaceMrouteSourceIpChanged, 
				fkV2IgmpProxyInterfaceServiceSourceIpChanged }
			STATUS current
			DESCRIPTION 
				"Description."
			::= { fkV2Multicast 6 }

		
	
	END

--
-- fkv2-multicast-mib.mib
--
