-- *****************************************************************
-- FKOLTG1040-NOTIFICATION.mib:  Fkoltg1040 Enterprise Notifications
--
-- Copyright (c) 2001 by Furukawa Industrial S.A
-- All rights reserved.
-- 
-- *****************************************************************
--

FKOLTG1040-NOTIFICATION-V1 DEFINITIONS ::= BEGIN

IMPORTS
        MODULE-IDENTITY,
        OBJECT-IDENTITY,
    enterprises
        FROM SNMPv2-SMI
    fkoltg1040Events
        FROM FKOLTG1040-SMI
    dsPortInstallStatus, dsPowerIndex, dsPowerstatus, dsFanIndex, dsFanstatus, dsTemperatureStatus, dsSwitchAtMacAddress, dsSwitchAtNetAddress, dsSwitchAtVID, dsUserMacAddress1, dsUserMacAddress2, dsUserMacAddress3, dsUserMacAddress4, dsFreeMem, dsSystemUpgradePath, dsSystemUpgradeStorage, dsPortModuleIndex, dsPortPortIndex, dsVdslPortIndex, dsSerialNumber
        FROM FKOLTG1040-SWITCH-MIB
    dsUserLoginName, dsUserLoginIpAddress
        FROM FKOLTG1040-USER-MANAGEMENT-MIB
    dsPonOltIndex, dsPonOnuIndex, dsPonOnuMacAddress, dsPonTaggedLabel, dsPonQueueIndex, dsPonPortIndex, dsPonDirection, dsPonState, dsPonCount, dsPonOltIndex, dsPonPortIndex
        FROM FKOLTG1040-GEPON-MIB
    ifIndex, ifDescr, ifAdminStatus
        FROM IF-MIB
    sysDescr, sysUpTime
        FROM SNMPv2-MIB
    dsSubnetConfName
        FROM FKOLTG1040-DHCP-MIB
    fkGponOltTransceiverPort, fkGponOltId, fkGponOnuId, fkGponOntFirmwareOltId, fkGponOnuPortId, fkGponOnuIsFirst, fkGponOnuAuthenticationStatus, fkGponOnuBatteryStatus, fkGponOnuSerial, fkGponOntFirmwareOntOsStatus, fkGponOntFirmwareOntId, fkGponOnuPortOperStatus
        FROM FK-GPON-MIB
    fkSlotSystemIndex, fkClockModuleInitStatus, fkSlotStatusCurrentInstallCardType, fkClockModuleInstallStatus, fkClockInfoInSrcLoSStatus, fkClockModuleIndex, fkClockInfoInSrcStatus, fkClockModuleOPMode, fkClockInfoInSrcNtrClockType, fkFanUnitIndex, fkClockInfoInSrcAISStatus, fkSlotStatusActionEvent, fkSlotStatusState, fkSlotPowerMonStatus, fkClockInfoInSrcType, fkFanUnitSpeed, fkClockModuleBoardId, fkSlotPowerMonIndex
        FROM FK-DEVICE-MIB
    fkArpInspectInvalidLogSrcIpAddr, fkArpInspectInvalidLogPortNumber, fkArpInspectInvalidLogVlanId, fkArpInspectInvalidLogReason, fkArpInspectInvalidLogOpcode, fkArpInspectInvalidLogLastRecvTime, fkArpInspectInvalidLogSamePktCnt, fkArpInspectInvalidLogDstMacAddr, fkArpInspectInvalidLogDstIpAddr, fkArpInspectInvalidLogSrcMacAddr
        FROM FK-SECURITY-MIB
    fkBFDSessionStatus, fkBFDSessionNeighAddrType, fkBFDSessionNeighAddrValue
        FROM FK-NETWORK-MIB
    fkSnmpConnectionType, fkAgentAddress
        FROM FK-SNMP-MIB
    fkRedActiveCurrState, fkRedActivePrevState, fkRedActiveBoard
        FROM FK-RED-MIB
    fkNTPServerName, fkSwWatchdogType
        FROM FK-SYSTEMMAINTENANCE-MIB
    dsIgmpSnoopingEnabled
        FROM FKOLTG1040-MCAST-MIB
    ipAdEntAddr
        FROM IP-MIB;
        
--
-- V1 TRAP-TYPE  
--

portInstalled TRAP-TYPE
    ENTERPRISE  fkoltg1040Events
    VARIABLES   { ifIndex , dsPortInstallStatus }
    DESCRIPTION
             "portInstalled trap send when portInstallStatus is enabled."
    ::= 1

portRemoved   TRAP-TYPE
    ENTERPRISE  fkoltg1040Events
    VARIABLES   { ifIndex , dsPortInstallStatus }
    DESCRIPTION
             "portInstalled trap send when portInstallStatus is disabled."
    ::= 2                                         
         
powerOk TRAP-TYPE
    ENTERPRISE  fkoltg1040Events
    VARIABLES   { dsPowerIndex , dsPowerstatus }
    DESCRIPTION
             "Power status OK trap when powerStatus change from disable to enable."
    ::= 3                                         
    
powerFail TRAP-TYPE
    ENTERPRISE  fkoltg1040Events
    VARIABLES   { dsPowerIndex , dsPowerstatus }
    DESCRIPTION
             "Power status fail trap when powerStatus change from enable to disable."
    ::= 4

fanOk TRAP-TYPE
    ENTERPRISE  fkoltg1040Events
    VARIABLES   { dsFanIndex , dsFanstatus }
    DESCRIPTION
             "Fan status OK trap when fanStatus change from disable to enable."
    ::= 5
         
fanFail TRAP-TYPE
    ENTERPRISE  fkoltg1040Events
    VARIABLES   { dsFanIndex , dsFanstatus }
    DESCRIPTION
             "Fan status fail trap when fanStatus change from enable to disable."
    ::= 6                

powerInstalled TRAP-TYPE
    ENTERPRISE  fkoltg1040Events
    VARIABLES   { dsPowerIndex }
    DESCRIPTION
             "Power Installed trap when power was installed."
    ::= 7                

powerRemoved TRAP-TYPE
    ENTERPRISE  fkoltg1040Events
    VARIABLES   { dsPowerIndex }
    DESCRIPTION
             "Power removed trap when power was removed."
    ::= 8                

fanInstalled TRAP-TYPE
    ENTERPRISE  fkoltg1040Events
    VARIABLES   { dsFanIndex }
    DESCRIPTION
             "Fan Installed trap when fan was installed."
    ::= 9                

fanRemoved TRAP-TYPE
    ENTERPRISE  fkoltg1040Events
    VARIABLES   { dsFanIndex }
    DESCRIPTION
             "Fan removed trap when fan was removed."
    ::= 10
   
bcastOver   TRAP-TYPE
    ENTERPRISE  fkoltg1040Events
    VARIABLES   { sysDescr }
    DESCRIPTION
             "Broadcast packet over trap when Rx broadcast packet is over the given limit."
    ::= 11
    
cpuLoadOverThreshold   TRAP-TYPE
    ENTERPRISE  fkoltg1040Events
    VARIABLES   { sysDescr }
    DESCRIPTION
             "The cpuLoadoverThreshold trap is sentwhen cpuLoad is over the given limit."
    ::= 12
    
cpuLoadFallThreshold   TRAP-TYPE
    ENTERPRISE  fkoltg1040Events
    VARIABLES   { sysDescr }
    DESCRIPTION
             "The cpuLoadfallThreshold trap is sent when cpuLoad fall under the given limit."
    ::= 13                       

dhcpLeaseShortage   TRAP-TYPE
        ENTERPRISE      fkoltg1040Events
        VARIABLES       { sysDescr, dsSubnetConfName }
        DESCRIPTION     
                        "DHCP User IP pool shortage when User's DHCPDISCOVER message arrive."
        ::= 14 
        
portOverThreshold   TRAP-TYPE
    ENTERPRISE  fkoltg1040Events
    VARIABLES   { ifIndex }
    DESCRIPTION
             "Port traffic over HighThreshold trap when port traffic is over the given limit."
    ::= 15
    
portFallThreshold   TRAP-TYPE
    ENTERPRISE  fkoltg1040Events
    VARIABLES   { ifIndex }
    DESCRIPTION
             "Port traffic fall under HighThreshold trap when port traffic fall under the given limit."
    ::= 16                                     

temperatureOverThreshold TRAP-TYPE
        ENTERPRISE fkoltg1040Events
        VARIABLES  { dsTemperatureStatus }
        DESCRIPTION
                        "TemperatureOverThreshold trap is sent when temperature is over the certain threshold."
        ::= 17

systemRestart TRAP-TYPE
        ENTERPRISE fkoltg1040Events
        VARIABLES  { sysDescr }
        DESCRIPTION
                        "SystemRestart trap is sent when system is restarted by user."
        ::= 18                                
        
mfgdBlocked TRAP-TYPE
        ENTERPRISE fkoltg1040Events
        VARIABLES { dsSwitchAtMacAddress, dsSwitchAtNetAddress, dsSwitchAtVID }
        DESCRIPTION
                        "mfgdblocked trap is sent when a certain mac address is denied by mac-flood-guard mechanism." 
    ::= 19

mfgdReleased TRAP-TYPE
        ENTERPRISE fkoltg1040Events
        VARIABLES { dsSwitchAtMacAddress, dsSwitchAtNetAddress, dsSwitchAtVID }
        DESCRIPTION
                        "mfgdblocked trap is sent when a certain mac address is permitted again by mac-flood-guard mechanism." 
    ::= 20
    
ipConflict TRAP-TYPE
        ENTERPRISE fkoltg1040Events
        VARIABLES {dsSwitchAtNetAddress, dsSwitchAtMacAddress}
        DESCRIPTION
                        "ipConflict trap is sent when a certain IP address is shared among different users." 
    ::= 21  

dhcpIllegalEntry   TRAP-TYPE
    ENTERPRISE  fkoltg1040Events
    VARIABLES   { sysDescr }
    DESCRIPTION
             "dhcpIllegalEntry trap is sent when illegal dhcp user is found."
    ::= 22     
    
optionModuleInstalled   TRAP-TYPE
    ENTERPRISE  fkoltg1040Events
    VARIABLES   { ifIndex }
    DESCRIPTION
             "optionModuleInstalled trap is sent when option Module was installed."
    ::= 23
 
optionModuleRemoved   TRAP-TYPE
    ENTERPRISE  fkoltg1040Events
    VARIABLES   { ifIndex }
    DESCRIPTION
             "optionModuleRemoved trap is sent when option Module was removed."
    ::= 24
 
memoryOverThreshold   TRAP-TYPE
    ENTERPRISE  fkoltg1040Events
    VARIABLES   { sysDescr }
    DESCRIPTION
             "Memory over HighThreshold trap when used memory size is over the given limit."
    ::= 25
    
memoryFallThreshold   TRAP-TYPE
    ENTERPRISE  fkoltg1040Events
    VARIABLES   { sysDescr }
    DESCRIPTION
             "Memory fall under HighThreshold trap when used memory size fall under the given limit."
    ::= 26                       

slotInstalled   TRAP-TYPE
    ENTERPRISE  fkoltg1040Events
    VARIABLES   { ifIndex }
    DESCRIPTION
             "slotInstalled trap is sent when Board was installed."
    ::= 27
 
slotRemoved   TRAP-TYPE
    ENTERPRISE  fkoltg1040Events
    VARIABLES   { ifIndex }
    DESCRIPTION
             "slotRemoved trap is sent when Board was removed."
    ::= 28
 
slotStateChange   TRAP-TYPE
    ENTERPRISE  fkoltg1040Events
    VARIABLES   { ifIndex }
    DESCRIPTION
             "slotStateChange trap is sent when Board State change."
    ::= 29

portCRCOverThreshold   TRAP-TYPE
    ENTERPRISE  fkoltg1040Events
    VARIABLES   { ifIndex }
    DESCRIPTION
             "CRC Load over HighThreshold trap when crcLoad is over the given limit."
    ::= 30

portCRCFallThreshold   TRAP-TYPE
    ENTERPRISE  fkoltg1040Events
    VARIABLES   { ifIndex }
    DESCRIPTION
             "CRC Load fall under HighThreshold trap when crcLoad fall under the given limit."
    ::= 31                                        

temperatureHighOverThreshold TRAP-TYPE
        ENTERPRISE  fkoltg1040Events
        VARIABLES   { dsTemperatureStatus }
        DESCRIPTION
                        "The temperatureHighOverThreshold trap is sent when temperature is over the high-threshold."
        ::= 32

temperatureHighFallThreshold TRAP-TYPE
        ENTERPRISE  fkoltg1040Events
        VARIABLES   { dsTemperatureStatus }
        DESCRIPTION
                        "The temperatureHighFallThreshold trap is sent when temperature fall the high-threshold."
        ::= 33
    
temperatureLowOverThreshold TRAP-TYPE
        ENTERPRISE  fkoltg1040Events
        VARIABLES   { dsTemperatureStatus }
        DESCRIPTION
                        "The temperatureLowOverThreshold trap is sent when 1st temperature is over the low-threshold."
        ::= 34

temperatureLowFallThreshold TRAP-TYPE
        ENTERPRISE  fkoltg1040Events
        VARIABLES   { dsTemperatureStatus }
        DESCRIPTION
                        "The temperatureLowFallThreshold trap is sent when temperature fall under the low-threshold."
        ::= 35
    
userLogIn TRAP-TYPE
        ENTERPRISE  fkoltg1040Events
        VARIABLES   { dsUserLoginName, dsUserLoginIpAddress }
        DESCRIPTION
                        "The user-login trap is sent when user login."
        ::= 36
        
userLogOut TRAP-TYPE
        ENTERPRISE  fkoltg1040Events
        VARIABLES   { dsUserLoginName, dsUserLoginIpAddress }
        DESCRIPTION
                        "The user-logout trap is sent when user logout."
        ::= 37    

restoreFactory TRAP-TYPE
        ENTERPRISE  fkoltg1040Events
        VARIABLES   { sysDescr }
        DESCRIPTION
                        "The restoreFactory trap is sent when user initialize as factory defaults."
        ::= 38
        
cpuLoadHighOverThreshold TRAP-TYPE
        ENTERPRISE  fkoltg1040Events
        VARIABLES   { sysDescr }
        DESCRIPTION
                        "The cpuloadHighOverThreshold trap is sent when cpuload is over the high-threshold."
        ::= 39

cpuLoadHighFallThreshold TRAP-TYPE
        ENTERPRISE  fkoltg1040Events
        VARIABLES   { sysDescr }
        DESCRIPTION
                        "The cpuloadHighFallThreshold trap is sent when cpuload fall the high-threshold."
        ::= 40
    
cpuLoadLowOverThreshold TRAP-TYPE
        ENTERPRISE  fkoltg1040Events
        VARIABLES   { sysDescr }
        DESCRIPTION
                        "The cpuloadLowOverThreshold trap is sent when 1st cpuload is over the low-threshold."
        ::= 41

cpuLoadLowFallThreshold TRAP-TYPE
        ENTERPRISE  fkoltg1040Events
        VARIABLES   { sysDescr }
        DESCRIPTION
                        "The cpuloadLowFallThreshold trap is sent when cpuload fall under the low-threshold."
        ::= 42            
                
igmpSnoopingChanged TRAP-TYPE
        ENTERPRISE fkoltg1040Events
        VARIABLES { dsIgmpSnoopingEnabled }
        DESCRIPTION 
                    " "
        ::= 43

 
dsSystemUpgradeChanged TRAP-TYPE
        ENTERPRISE      fkoltg1040Events
        VARIABLES   { sysDescr }
        DESCRIPTION
                        "System NOS Upgrade status"
        ::= 44


 
adslAtucPerfLofsThresh TRAP-TYPE
        ENTERPRISE      fkoltg1040Events
        VARIABLES   { sysUpTime }
        DESCRIPTION
                        "Loss of Framing threshold reached(ATUC)"
        ::= 51
        
adslAtucPerfLossThresh TRAP-TYPE
        ENTERPRISE      fkoltg1040Events
        VARIABLES   { sysUpTime }
        DESCRIPTION
                        "Loss of signal threshold reached(ATUC)"
        ::= 52
             
adslAtucPerfLprsThresh TRAP-TYPE
        ENTERPRISE      fkoltg1040Events
        VARIABLES   { sysUpTime }
        DESCRIPTION
                        "Loss of power threshold reached (ATUC)"
        ::= 53

adslAtucPerfESsThresh TRAP-TYPE
        ENTERPRISE      fkoltg1040Events
        VARIABLES   { sysUpTime }
        DESCRIPTION
                        "Errored Seconds threshold reached (ATUC)"
        ::= 54

adslAtucRateChange TRAP-TYPE
        ENTERPRISE      fkoltg1040Events
        VARIABLES   { sysUpTime }
        DESCRIPTION
                        "Changed atuc rate"
        ::= 55

adslAtucPerfLolsThresh TRAP-TYPE
        ENTERPRISE      fkoltg1040Events
        VARIABLES   { sysUpTime }
        DESCRIPTION
                        "Loss of Link threshold reached (ATUC)"
        ::= 56


adslAturPerfLofsThresh TRAP-TYPE
        ENTERPRISE      fkoltg1040Events
        VARIABLES   { sysUpTime }
        DESCRIPTION
                        "Loss of Framing threshold reached(ATUR) "
        ::= 61

adslAturPerfLossThresh TRAP-TYPE
        ENTERPRISE      fkoltg1040Events
        VARIABLES   { sysUpTime }
        DESCRIPTION
                        "Loss of signal threshold reached(ATUR)"
        ::= 62

adslAturPerfLprsThresh TRAP-TYPE
        ENTERPRISE      fkoltg1040Events
        VARIABLES   { sysUpTime }
        DESCRIPTION
                        "Loss of power threshold reached (ATUR)"
        ::= 63

adslAturPerfESsThresh TRAP-TYPE
        ENTERPRISE      fkoltg1040Events
        VARIABLES   { sysUpTime }
        DESCRIPTION
                        "Errored Seconds threshold reached (ATUR)"
        ::= 64


vdslCPEChangeInfo TRAP-TYPE
        ENTERPRISE      fkoltg1040Events
        VARIABLES   { sysDescr, ipAdEntAddr, dsVdslPortIndex, dsSerialNumber, dsUserMacAddress1, dsUserMacAddress2, dsUserMacAddress3, dsUserMacAddress4}
        DESCRIPTION
                        "trap is sent with CPE Serial No., Mac Address of CPE, after CPE serial change.  "
        ::= 65

--
-- Flood-guard
--  
cfgdBlocked TRAP-TYPE
        ENTERPRISE      fkoltg1040Events
        VARIABLES { ifIndex }
        DESCRIPTION
                        "Cfgdblocked trap is sent when a certain port is blocked by cpu-flood-guard mechanism." 
        ::= 71

cfgdReleased TRAP-TYPE
        ENTERPRISE      fkoltg1040Events
        VARIABLES { ifIndex }
        DESCRIPTION
                        "CfgdReleased trap is sent when a certain port is non-blocked by cpu-flood-guard mechanism." 
        ::= 72
        
cfgdOverThreshold TRAP-TYPE
        ENTERPRISE      fkoltg1040Events
        VARIABLES { ifIndex }
        DESCRIPTION
                        "CfgdOverThreshold trap is sent when a certain port is over the threshold by cpu-flood-guard mechanism." 
        ::= 73

cfgdUnderThreshold TRAP-TYPE
        ENTERPRISE      fkoltg1040Events
        VARIABLES { ifIndex }
        DESCRIPTION
                        "CfgdUnderThreshold trap is sent when a certain port fall under the threshold by cpu-flood-guard mechanism" 
        ::= 74

sfgdBlocked TRAP-TYPE
        ENTERPRISE      fkoltg1040Events
        VARIABLES { ifIndex }
        DESCRIPTION
                        "Sfgdblocked trap is sent when a certain port is blocked by system-flood-guard mechanism." 
        ::= 75

sfgdReleased TRAP-TYPE
        ENTERPRISE      fkoltg1040Events
        VARIABLES { ifIndex }
        DESCRIPTION
                        "SfgdReleased trap is sent when a certain port is non-blocked by system-flood-guard mechanism." 
        ::= 76

        
sfgdOverThreshold TRAP-TYPE
        ENTERPRISE      fkoltg1040Events
        VARIABLES { ifIndex }
        DESCRIPTION
                        "SfgdOverThreshold trap is sent when a certain port is over the threshold by system-flood-guard mechanism." 
        ::= 77

sfgdUnderThreshold TRAP-TYPE
        ENTERPRISE      fkoltg1040Events
        VARIABLES { ifIndex }
        DESCRIPTION
                        "SfgdUnderThreshold trap is sent when a certain port fall under the threshold by system-flood-guard mechanism" 
        ::= 78

ppsControlBlocked TRAP-TYPE
        ENTERPRISE      fkoltg1040Events
        VARIABLES { ifIndex }
        DESCRIPTION
                        "ppsControlBlocked trap is sent when a certain port is blocked by PPS-Control mechanism." 
        ::= 79

ppsControlReleased TRAP-TYPE
        ENTERPRISE      fkoltg1040Events
        VARIABLES { ifIndex }
        DESCRIPTION
                        "ppsControlReleased trap is sent when a certain port is non-blocked by PPS-Control mechanism." 
        ::= 80

        
ppsControlOverThreshold TRAP-TYPE
        ENTERPRISE      fkoltg1040Events
        VARIABLES { ifIndex }
        DESCRIPTION
                        "ppsControlOverThreshold trap is sent when a certain port is over the threshold by PPS-Control mechanism." 
        ::= 81

ppsontrolUnderThreshold TRAP-TYPE
        ENTERPRISE      fkoltg1040Events
        VARIABLES { ifIndex }
        DESCRIPTION
                        "ppsControlUnderThreshold trap is sent when a certain port fall under the threshold by PPS-Control mechanism" 
        ::= 82
 

nosRemoteUpgradeRequest TRAP-TYPE
        ENTERPRISE      fkoltg1040Events
        VARIABLES { sysDescr, dsSystemUpgradePath, dsSystemUpgradeStorage }
        DESCRIPTION
        "This trap indicates that the system received nos-remote-upgrade command."
        ::= 83

nosRemoteUpgradeSuccess TRAP-TYPE
        ENTERPRISE      fkoltg1040Events
        VARIABLES { sysDescr, dsSystemUpgradePath, dsSystemUpgradeStorage }
        DESCRIPTION
        "This trap indicates that the NOS succeeded to upgrade NOS."
        ::= 84

nosRemoteUpgradeFailAbort TRAP-TYPE
        ENTERPRISE      fkoltg1040Events
        VARIABLES { sysDescr, dsSystemUpgradePath, dsSystemUpgradeStorage }
        DESCRIPTION
        "This trap indicates that the system failed to download NOS by user interrup."
        ::= 85

nosRemoteUpgradeFailHeaderError TRAP-TYPE
        ENTERPRISE      fkoltg1040Events
        VARIABLES { sysDescr, dsSystemUpgradePath, dsSystemUpgradeStorage }
        DESCRIPTION
        "This trap indicates that the system failed to download NOS, for NOS header-error."
        ::= 86

nosRemoteUpgradeFailDownloadError TRAP-TYPE
        ENTERPRISE      fkoltg1040Events
        VARIABLES { sysDescr, dsSystemUpgradePath, dsSystemUpgradeStorage }
        DESCRIPTION
        "This trap indicates that the system failed to download NOS, for NOS checksum-error."
        ::= 87

nosRemoteUpgradeFailFlashError TRAP-TYPE
        ENTERPRISE      fkoltg1040Events
        VARIABLES { sysDescr, dsSystemUpgradePath, dsSystemUpgradeStorage }
        DESCRIPTION
        "This trap indicates that the system failed to download NOS, for flash operation."
        ::= 88

nosRemoteUpgradeStart TRAP-TYPE
        ENTERPRISE      fkoltg1040Events
        VARIABLES { sysDescr, dsSystemUpgradePath, dsSystemUpgradeStorage  }
        DESCRIPTION
        "This trap indicates that the upgrade NOS process was started."
        ::= 89

-- Dying gasp for power fault 
systemDyingGasp TRAP-TYPE
        ENTERPRISE      fkoltg1040Events
        VARIABLES { sysDescr }
        DESCRIPTION
        "This trap indicates that Dying-gasp for power fault."
        ::= 90

-- Attack-Guard 
attackGuardBlock TRAP-TYPE
        ENTERPRISE      fkoltg1040Events
        VARIABLES { dsPortModuleIndex, dsPortPortIndex }
        DESCRIPTION
        "This trap indicates that some port is blocked by attack-guard." 
        ::= 91

attackGuardUnBlock TRAP-TYPE
        ENTERPRISE      fkoltg1040Events
        VARIABLES { dsPortModuleIndex, dsPortPortIndex }
        DESCRIPTION
        "This trap indicates that some port is unblocked by attack-guard." 
        ::= 92

fanPeriodicFault  TRAP-TYPE
        ENTERPRISE      fkoltg1040Events
        VARIABLES { dsFanIndex, dsFanstatus }
        DESCRIPTION
        "This trap indicates the fan status is fault in some period."
        ::=  93 

remoteOamDyingGasp  TRAP-TYPE
        ENTERPRISE      fkoltg1040Events
        VARIABLES { ifIndex }
        DESCRIPTION
        "This trap indicates the remote oam entity is in dying-gasp."
        ::=  94

remoteOamDyingGaspRestoration  TRAP-TYPE
        ENTERPRISE      fkoltg1040Events
        VARIABLES { ifIndex }
        DESCRIPTION
        "This trap indicates the remote oam entity is restored."
        ::=  95

arpInspectInvalid  TRAP-TYPE
        ENTERPRISE      fkoltg1040Events
        VARIABLES { fkArpInspectInvalidLogReason, fkArpInspectInvalidLogSamePktCnt, fkArpInspectInvalidLogOpcode, fkArpInspectInvalidLogPortNumber, fkArpInspectInvalidLogVlanId, fkArpInspectInvalidLogSrcMacAddr, fkArpInspectInvalidLogSrcIpAddr, fkArpInspectInvalidLogDstMacAddr, fkArpInspectInvalidLogDstIpAddr, fkArpInspectInvalidLogLastRecvTime }
        DESCRIPTION
        "This trap indicates the ARP inspection is invalided."
        ::=  96

systemSwitchover  TRAP-TYPE
        ENTERPRISE      fkoltg1040Events
        VARIABLES { sysDescr }
        DESCRIPTION
        "This trap indicates the system is switchover."
        ::=  97

boardChangeState  TRAP-TYPE
        ENTERPRISE      fkoltg1040Events
        VARIABLES { fkRedActiveBoard, fkRedActivePrevState, fkRedActiveCurrState }
        DESCRIPTION
        "This trap indicates the board state is changed."
        ::=  98

clockModuleInstalled  TRAP-TYPE
        ENTERPRISE      fkoltg1040Events
        VARIABLES { fkClockModuleIndex, fkClockModuleBoardId, fkClockModuleInstallStatus }
        DESCRIPTION
        "clockModuleInstalled trap send when fkClockModuleInstallStatus is installed."
        ::=  105

clockModuleRemoved  TRAP-TYPE
        ENTERPRISE      fkoltg1040Events
        VARIABLES { fkClockModuleIndex, fkClockModuleBoardId, fkClockModuleInstallStatus }
        DESCRIPTION
        "clockModuleRemoved trap send when fkClockModuleInstallStatus is removed."
        ::=  106

clockModuleInitOk  TRAP-TYPE
        ENTERPRISE      fkoltg1040Events
        VARIABLES { fkClockModuleIndex, fkClockModuleBoardId, fkClockModuleInitStatus }
        DESCRIPTION
        "clockModuleInitOk trap send when fkClockModuleInitStatus is ok."
        ::=  107

clockModuleInitFail  TRAP-TYPE
        ENTERPRISE      fkoltg1040Events
        VARIABLES { fkClockModuleIndex, fkClockModuleBoardId, fkClockModuleInitStatus }
        DESCRIPTION
        "clockModuleInitFail trap send when fkClockModuleInitStatus is failure."
        ::=  108

interfaceAdminUp  TRAP-TYPE
        ENTERPRISE      fkoltg1040Events
        VARIABLES { ifIndex, ifDescr, ifAdminStatus }
        DESCRIPTION
        "This trap indicates the interface admin up."
        ::=  109

interfaceAdminDown  TRAP-TYPE
        ENTERPRISE      fkoltg1040Events
        VARIABLES { ifIndex, ifDescr, ifAdminStatus }
        DESCRIPTION
        "This trap indicates the interface admin down."
        ::=  110

powerMonEventDetected TRAP-TYPE
        ENTERPRISE      fkoltg1040Events
        VARIABLES { fkSlotPowerMonIndex, fkSlotPowerMonStatus }
        DESCRIPTION
        "This trap indicates the power monitoring detects voltage change of slot."
        ::= 111

ntpConnectionFail   TRAP-TYPE
        ENTERPRISE      fkoltg1040Events
        VARIABLES { fkNTPServerName }
        DESCRIPTION
        "This trap indicates the ntp connection is lost."
        ::=  112

fanSpeedFallUnderThreshold   TRAP-TYPE
        ENTERPRISE      fkoltg1040Events
        VARIABLES { fkFanUnitIndex, fkFanUnitSpeed }
        DESCRIPTION
        "This trap indicates the fan speed is under the threshold."
        ::=  113

fanSpeedRisingOverThreshold   TRAP-TYPE
        ENTERPRISE      fkoltg1040Events
        VARIABLES { fkFanUnitIndex, fkFanUnitSpeed }
        DESCRIPTION
        "This trap indicates the fan speed is over the threshold."
        ::=  114

userLoginFail  TRAP-TYPE
        ENTERPRISE      fkoltg1040Events
        VARIABLES { dsUserLoginName, dsUserLoginIpAddress }
        DESCRIPTION     "This trap indicates the user fail to login."
        ::=  115

bfdSessionStateChanged TRAP-TYPE  
        ENTERPRISE      fkoltg1040Events
        VARIABLES { ifIndex, fkBFDSessionNeighAddrType, fkBFDSessionNeighAddrValue, fkBFDSessionStatus}
        DESCRIPTION     "This trap indicates that BFD session state is changed."
        ::=  116

clockModuleOPModeChanged TRAP-TYPE
        ENTERPRISE      fkoltg1040Events
        VARIABLES { fkClockModuleIndex, fkClockModuleOPMode, fkSlotSystemIndex }
        DESCRIPTION     "This trap indicate that slot Operation mode is changed."
        ::=  117

clockModuleRefrencesChanged TRAP-TYPE
        ENTERPRISE      fkoltg1040Events
        VARIABLES { fkClockModuleIndex, fkSlotSystemIndex }
        DESCRIPTION     "This trap indicate that slot reference ntr is changed."
        ::=  118

portRxOverThreshold TRAP-TYPE
        ENTERPRISE      fkoltg1040Events
        VARIABLES { ifIndex }
        DESCRIPTION 
                "Port Rx traffic over HighThreshold trap when port traffic is over the given limit."
        ::=  121

portRxFallThreshold TRAP-TYPE
        ENTERPRISE      fkoltg1040Events
        VARIABLES { ifIndex }
        DESCRIPTION 
                "Port Rx traffic fall under HighThreshold trap when port traffic falls below the given limit."
        ::= 122


portTxOverThreshold TRAP-TYPE
        ENTERPRISE      fkoltg1040Events
        VARIABLES { ifIndex }
        DESCRIPTION 
                "Port Tx traffic over HighThreshold trap when port traffic is over the given limit."
        ::= 123


portTxFallThreshold TRAP-TYPE
        ENTERPRISE      fkoltg1040Events
        VARIABLES { ifIndex }
        DESCRIPTION 
                "Port Tx traffic fall under HighThreshold trap when port traffic falls below the given limit."
        ::= 124

clockModuleInSrcStatusChanged TRAP-TYPE
        ENTERPRISE      fkoltg1040Events
        VARIABLES { fkClockModuleIndex, fkClockInfoInSrcType,fkClockInfoInSrcStatus }
        DESCRIPTION     "This trap indicate that BFD reference ntr is changed."
        ::=  125

clockModuleInSrcAISStatusChanged TRAP-TYPE
        ENTERPRISE      fkoltg1040Events
        VARIABLES { fkClockModuleIndex,fkClockInfoInSrcType,fkClockInfoInSrcAISStatus }
        DESCRIPTION     "This trap indicate that BFD reference ntr is changed."
        ::=  126

clockModuleInSrcLoSStatusChanged TRAP-TYPE
        ENTERPRISE      fkoltg1040Events
        VARIABLES { fkClockModuleIndex,fkClockInfoInSrcType,fkClockInfoInSrcLoSStatus }
        DESCRIPTION     "This trap indicate that BFD reference ntr is changed."
        ::=  127

clockModuleInSrcLDSCStatus TRAP-TYPE
        ENTERPRISE      fkoltg1040Events
        VARIABLES { fkClockModuleIndex,fkClockInfoInSrcType,fkClockInfoInSrcLoSStatus }
        DESCRIPTION     "This trap indicate that BFD reference ntr is changed."
        ::=  128

clockModuleInSrcNtrClockchanged TRAP-TYPE
        ENTERPRISE      fkoltg1040Events
        VARIABLES { fkClockModuleIndex,fkClockInfoInSrcType,fkClockInfoInSrcNtrClockType }
        DESCRIPTION     "This trap indicate that BFD reference ntr is changed."
        ::=  129

-- GEPON
ponLinkFault  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        "ONU reports a Link Fault via the flag in the 802.3ah OAM header.No further information about the fault is available.."
        ::= 151

ponLos  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " Loss of Signal is detected by the PHY device for OLT Network  interface, and PON interfaces on  the OLT and ONU. "
        ::= 152

ponTransmitFail  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " Transmitted output does not match input, as reported by EPON optics "
        ::= 153

ponTransmitDegrade  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " Transmitted output has a high error level, but not so high as to cause - Failure. Optionallyreported by EPON optical module.."
        ::= 154

ponQueueOverflow  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " One of the queues for the link has dropped frames due to becoming full "
        ::= 155

ponMacLearningTableOverflow  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " MAC address learning table is full, not in overwrite mode, and a new MAC address wasencountered "
        ::= 156

ponDuplicateMacRegistration  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " MPCP register request received for MAC that is registered and in-service "
        ::= 157

ponReportTimeout  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " ONU does not respond to grants from the OLT "
        ::= 158

ponGateTimeout  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " Excessive interval between MPCP gates. "
        ::= 159

ponOAMKeepaliveTimeout  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " OAM KeepaliveTimeout - OAM layer does not receive periodic messages from its peer "
        ::= 160

ponKeyExchangeFailure  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " The link peer has failed to generate a new key message, or to switch to the new key, in the timeallotted by the key exchange timer for this link. Encryption remains in force using the old key, and the key exchange process continues.The alarm will clear when a new key is established. "
        ::= 161

ponAutoNegotiation  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " OLT Network port fails to auto-negotiate with the peer (if auto-negotiation feature is enabled)."
        ::= 162

ponLinkLoopback  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " The link is currently in the loopback state "
        ::= 163

ponStandardDyingGasp  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " ONU reports Dying Gasp via that bit in 802.3ah OAM header "
        ::= 164

ponPowerFail  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " Power supply failure "
        ::= 165

ponTemperature  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " Operating temperature range exceeded "
        ::= 166

ponAuthenticationInformationUnavailable  TRAP-TYPE
        ENTERPRISE      fkoltg1040Events
        VARIABLES   { dsPonOltIndex, dsPonOnuIndex, dsPonOnuMacAddress, dsPonTaggedLabel, dsPonPortIndex, dsPonQueueIndex, dsPonState, dsPonCount }
        DESCRIPTION
                        " ONU is configured to use external authentication device, and that device is not present "
        ::= 167

-- statistics 

ponOctetsTransferred  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Octets Transferred "
        ::= 171
 
ponTotalFramesTransferred  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Total frames transferred "
        ::= 172

ponUnicastFramesTransferred  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Unicast frames transferred "
        ::= 173

ponBroadcastFramesTransferred  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Broadcast frames transferred "
        ::= 174

ponMulticastFramesTransferred  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Multicast frames transferred "
        ::= 175

ponCRC32Errors  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " CRC-32 Errors "
        ::= 176

ponUndersizeFrames  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Undersize Frames "
        ::= 177

ponOversizeFrames  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Oversize Frames "
        ::= 178

ponCollisions  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Collisions "
        ::= 179

pon64OctetFrames  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " 64 Octet Frames "
        ::= 180

pon127OctetFrames  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " 65-127 Octet Frames "
        ::= 181

pon255OctetFrames  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " 128-255 Octet Frames "
        ::= 182

pon511OctetFrames  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " 256-511 Octet Frames "
        ::= 183

pon1023OctetFrames  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " 512-1023 Octet Frames "
        ::= 184

pon1518OctetFrames  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " 1024-1518 Octet Frames "
        ::= 185

pon1519OverOctetFrames  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " 1519+ Octet Frames "
        ::= 186

ponFramesDropped  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Frames dropped "
        ::= 187

ponOctetsDropped  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Octets dropped "
        ::= 188

ponOctetsDelayed  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Octets delayed "
        ::= 189

ponOctetsGranted  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Octets granted "
        ::= 190

ponOctetsGrantedButUnused  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Octets granted but unused "
        ::= 191

ponMaximumDelay  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Maximum Delay (units of 100usec) "
        ::= 192

ponCRC8Errors  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " CRC-8 (preamble) Errors "
        ::= 193

ponLineCodeErrors  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Line code errors "
        ::= 194

ponPauseFrames  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Pause Frames "
        ::= 195

ponErroredFrameSeconds  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Errored Frame Seconds "
        ::= 196

ponErroredFramePeriod  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Errored Frame Period "
        ::= 197

ponErroredFrameSecondsSummary  TRAP-TYPE
        ENTERPRISE      fkoltg1040Events
        VARIABLES   { dsPonOltIndex, dsPonOnuIndex, dsPonOnuMacAddress, dsPonTaggedLabel, dsPonPortIndex, dsPonQueueIndex, dsPonDirection, dsPonState, dsPonCount }
        DESCRIPTION
                        " Errored Frame Seconds Summary "
        ::= 198

gponOnuRegistered  TRAP-TYPE
        ENTERPRISE      fkoltg1040Events
        VARIABLES   { sysDescr, fkAgentAddress, fkGponOltId, fkGponOnuId, fkGponOnuSerial, fkGponOnuIsFirst }
        DESCRIPTION
                        " Registered Onu Information "
        ::= 200

gponOnuDeregistered  TRAP-TYPE
        ENTERPRISE      fkoltg1040Events
        VARIABLES   { sysDescr, fkAgentAddress, fkGponOltId, fkGponOnuId, fkGponOnuSerial }
        DESCRIPTION
                        " Deregistered Onu Information "
        ::= 201

swWatchdogDetectError  TRAP-TYPE
        ENTERPRISE      fkoltg1040Events
        VARIABLES   { fkSwWatchdogType }
        DESCRIPTION
                        " S/W Watchdog Detect Error "
        ::= 202
             
swWatchdogClearError  TRAP-TYPE
        ENTERPRISE      fkoltg1040Events
        VARIABLES   { fkSwWatchdogType }
        DESCRIPTION
                        " S/W Watchdog Clear Error "
        ::= 203
             
swWatchdogNormalState  TRAP-TYPE
        ENTERPRISE      fkoltg1040Events
        VARIABLES   { fkSwWatchdogType }
        DESCRIPTION
                        " S/W Watchdog Normal State "
        ::= 204
             
swWatchdogAbnormalState  TRAP-TYPE
        ENTERPRISE      fkoltg1040Events
        VARIABLES   { fkSwWatchdogType }
        DESCRIPTION
                        " S/W Watchdog Abnormal State "
        ::= 205
             
gponOnuUpgradeCompleted  TRAP-TYPE
        ENTERPRISE      fkoltg1040Events
        VARIABLES   { fkGponOltId, fkGponOnuId, fkGponOnuSerial }
        DESCRIPTION
                        " Upgrade Completed Onu Informations "
        ::= 206

gponOltCableDown  TRAP-TYPE
        ENTERPRISE      fkoltg1040Events
        VARIABLES   { fkGponOltId }
        DESCRIPTION
                        " GPON Cable down event is detected "
        ::= 207

gponOnuAutoToManual  TRAP-TYPE
        ENTERPRISE      fkoltg1040Events
        VARIABLES   { fkGponOltId, fkGponOnuId, fkGponOnuSerial }
        DESCRIPTION
                        " GPON Onu is auto-to-manual "
        ::= 208

slotActionEvent  TRAP-TYPE
        ENTERPRISE      fkoltg1040Events
        VARIABLES   { fkSlotSystemIndex, fkSlotStatusCurrentInstallCardType, fkSlotStatusActionEvent }
        DESCRIPTION
                        " This trap indicates the slot action event "
        ::= 209

slotStateChanged  TRAP-TYPE
        ENTERPRISE      fkoltg1040Events
        VARIABLES   { fkSlotSystemIndex, fkSlotStatusCurrentInstallCardType, fkSlotStatusState }
        DESCRIPTION
                        " This trap indicates the slot state is changed "
        ::= 210

gponNoAuthONU  TRAP-TYPE
        ENTERPRISE      fkoltg1040Events
        VARIABLES   { fkGponOltId, fkGponOnuId, fkGponOnuAuthenticationStatus }
        DESCRIPTION
                        " No authenticated ONU "
        ::= 211
             
gponDuplicateONU  TRAP-TYPE
        ENTERPRISE      fkoltg1040Events
        VARIABLES   { fkGponOltId, fkGponOnuId, fkGponOnuSerial }
        DESCRIPTION
                        " Duplicated ONU "
        ::= 212

gponDyingGasp  TRAP-TYPE
        ENTERPRISE      fkoltg1040Events
        VARIABLES   { fkGponOltId, fkGponOnuId, fkGponOnuSerial }
        DESCRIPTION
                        " Dying Gasp of GPON ONU"
        ::= 213

gponRogueOnu  TRAP-TYPE
        ENTERPRISE      fkoltg1040Events
        VARIABLES   { fkGponOltId, fkGponOnuId, fkGponOnuSerial }
        DESCRIPTION
                        "Found Rogue ONU."
        ::= 214

gponOnuBatteryEvent TRAP-TYPE
        ENTERPRISE      fkoltg1040Events
        VARIABLES   { fkGponOltId, fkGponOnuId, fkGponOnuBatteryStatus }
        DESCRIPTION
                        "Battery Event."
        ::= 215

gponOnuBatteryEventCleared TRAP-TYPE
        ENTERPRISE      fkoltg1040Events
        VARIABLES   { fkGponOltId, fkGponOnuId, fkGponOnuBatteryStatus }
        DESCRIPTION
                        "Battery Event is cleared."
        ::= 216

gponOnuPortOperStatus  TRAP-TYPE
        ENTERPRISE      fkoltg1040Events
        VARIABLES   { fkGponOltId, fkGponOnuId, fkGponOnuSerial, fkGponOnuPortId, fkGponOnuPortOperStatus }
        DESCRIPTION
                        " This trap indicates state of ONU Port Operation. "
        ::= 217

gponTransceiverChanged TRAP-TYPE
        ENTERPRISE      fkoltg1040Events
        VARIABLES   { fkGponOltId, fkGponOltTransceiverPort }
        DESCRIPTION
                        " This trap indicates GPON transceiver changed. "
        ::= 218

gponOltLosOn TRAP-TYPE
        ENTERPRISE      fkoltg1040Events
        VARIABLES   { fkGponOltId }
        DESCRIPTION
                        " This trap indicates state of OLT Log Of Signal (on). "
        ::= 219

gponOltLosOff TRAP-TYPE
        ENTERPRISE      fkoltg1040Events
        VARIABLES   { fkGponOltId }
        DESCRIPTION
                        " This trap indicates state of OLT Log Of Signal (off). "
        ::= 220

gponOltLosiOn TRAP-TYPE
        ENTERPRISE      fkoltg1040Events
        VARIABLES   { fkGponOltId, fkGponOnuId }
        DESCRIPTION
                        " This trap indicates state of OLT Log Of Signal for ONUi (on). "
        ::= 221

gponOltLosiOff TRAP-TYPE
        ENTERPRISE      fkoltg1040Events
        VARIABLES   { fkGponOltId, fkGponOnuId }
        DESCRIPTION
                        " This trap indicates state of OLT Log Of Signal for ONUi (off). "
        ::= 222

gponDyingGaspOn  TRAP-TYPE
        ENTERPRISE      fkoltg1040Events
        VARIABLES   { fkGponOltId, fkGponOnuId, fkGponOnuSerial }
        DESCRIPTION
                        " This trap indicates Dying Gasp of GPON ONU (on). "
        ::= 223

gponDyingGaspOff  TRAP-TYPE
        ENTERPRISE      fkoltg1040Events
        VARIABLES   { fkGponOltId, fkGponOnuId, fkGponOnuSerial }
        DESCRIPTION
                        " This trap indicates Dying Gasp of GPON ONU (off). "
        ::= 224

slotErrorLEDChanged  TRAP-TYPE
        ENTERPRISE      fkoltg1040Events
        VARIABLES   { fkSlotSystemIndex }
        DESCRIPTION
                        " This trap indicates slot error LED changed. "
        ::= 225
             
nmsConnectionTypeChanged  TRAP-TYPE
        ENTERPRISE      fkoltg1040Events
        VARIABLES   { fkSnmpConnectionType }
        DESCRIPTION
                        " This trap indicates NMS connection type changed. "
        ::= 226
             
gponOntOSUpgradeStatus  TRAP-TYPE
        ENTERPRISE      fkoltg1040Events
        VARIABLES   { fkGponOntFirmwareOltId, fkGponOntFirmwareOntId, fkGponOntFirmwareOntOsStatus }
        DESCRIPTION
                        " This trap indicates ONT OS upgrade status changes. "
        ::= 227
             
gponOntBLUpgradeStatus  TRAP-TYPE
        ENTERPRISE      fkoltg1040Events
        VARIABLES   { fkGponOntFirmwareOltId, fkGponOntFirmwareOntId, fkGponOntFirmwareOntOsStatus }
        DESCRIPTION
                        " This trap indicates ONT BL upgrade status changes. "
        ::= 228

gponOntRxPowerLoss  TRAP-TYPE
        ENTERPRISE      fkoltg1040Events
        VARIABLES { fkGponOltId }
        DESCRIPTION 
        "This trap indicates ONT port failed to detect Rx Power. "
        ::= 229

gponOntRxPowerDetected  TRAP-TYPE
        ENTERPRISE      fkoltg1040Events
        VARIABLES { fkGponOltId }
        DESCRIPTION "This trap indicates ONT port detected Rx Power. "
        ::= 230

gponOnuTemperatureHighOverThreshold  TRAP-TYPE
        ENTERPRISE      fkoltg1040Events
        VARIABLES { fkGponOltId, fkGponOnuId }
        DESCRIPTION "This trap indicates the temperature of ONU is over high threshold. "
        ::= 231

gponOnuTemperatureHighFallThreshold  TRAP-TYPE
        ENTERPRISE      fkoltg1040Events
        VARIABLES { fkGponOltId, fkGponOnuId }
        DESCRIPTION "This trap indicates the temperature of ONU falls under high threshold. "
        ::= 232

gponOnuTemperatureLowOverThreshold  TRAP-TYPE
        ENTERPRISE      fkoltg1040Events
        VARIABLES { fkGponOltId, fkGponOnuId }
        DESCRIPTION "This trap indicates the temperature of ONU is over low threshold. "
        ::= 233

gponOnuTemperatureLowFallThreshold  TRAP-TYPE
        ENTERPRISE      fkoltg1040Events
        VARIABLES { fkGponOltId, fkGponOnuId }
        DESCRIPTION "This trap indicates the temperature of ONU falls under low threshold. "
        ::= 234

gponOnuCpuOverThreshold  TRAP-TYPE
        ENTERPRISE      fkoltg1040Events
        VARIABLES { fkGponOltId, fkGponOnuId }
        DESCRIPTION "This trap indicates the CPU-load of ONU is over threshold. "
        ::= 235

gponOnuCpuFallThreshold  TRAP-TYPE
        ENTERPRISE      fkoltg1040Events
        VARIABLES { fkGponOltId, fkGponOnuId }
        DESCRIPTION "This trap indicates the CPU-load of ONU falls under threshold. "
        ::= 236

gponOnuMemoryOverThreshold  TRAP-TYPE
        ENTERPRISE      fkoltg1040Events
        VARIABLES { fkGponOltId, fkGponOnuId }
        DESCRIPTION "This trap indicates the memory-utilization of ONU is over threshold. "
        ::= 237

gponOnuMemoryFallThreshold  TRAP-TYPE
        ENTERPRISE      fkoltg1040Events
        VARIABLES { fkGponOltId, fkGponOnuId }
        DESCRIPTION "This trap indicates the memory-utilization of ONU falls under threshold. "
        ::= 238

gponOnuI2cFail  TRAP-TYPE
        ENTERPRISE      fkoltg1040Events
        VARIABLES { fkGponOltId, fkGponOnuId }
        DESCRIPTION "This trap indicates that detect ONU's i2c fail."
        ::= 239

gponOnuRxOpticPowerLowThreshAlarmOn  TRAP-TYPE
        ENTERPRISE      fkoltg1040Events
        VARIABLES { fkGponOltId, fkGponOnuId }
        DESCRIPTION "This trap indicates that ONU's low threshold Rx Optic power Alarm is On."
        ::= 240 

gponOnuRxOpticPowerLowThreshAlarmOff  TRAP-TYPE
        ENTERPRISE      fkoltg1040Events
        VARIABLES { fkGponOltId, fkGponOnuId }
        DESCRIPTION "This trap indicates that ONU's low threshold Rx Optic power Alarm is Off."
        ::= 241

gponOnuRxOpticPowerHighThreshAlarmOn  TRAP-TYPE
        ENTERPRISE      fkoltg1040Events
        VARIABLES { fkGponOltId, fkGponOnuId }
        DESCRIPTION "This trap indicates that ONU's high threshold Rx Optic power Alarm is On."
        ::= 242

gponOnuRxOpticPowerHighThreshAlarmOff  TRAP-TYPE
        ENTERPRISE      fkoltg1040Events
        VARIABLES { fkGponOltId, fkGponOnuId }
        DESCRIPTION "This trap indicates that ONU's high threshold Rx Optic power Alarm is Off."
        ::= 243

gponOltLOFIOn  TRAP-TYPE
        ENTERPRISE      fkoltg1040Events
        VARIABLES { fkGponOltId, fkGponOnuId }
        DESCRIPTION "Description"
        ::= 244

gponOltLOFIOff  TRAP-TYPE
        ENTERPRISE      fkoltg1040Events
        VARIABLES { fkGponOltId, fkGponOnuId }
        DESCRIPTION "Description"
        ::= 245
gponOltDOWOn  TRAP-TYPE
        ENTERPRISE      fkoltg1040Events
        VARIABLES { fkGponOltId, fkGponOnuId }
        DESCRIPTION "Description"
        ::= 246
gponOltDOWOff  TRAP-TYPE
        ENTERPRISE      fkoltg1040Events
        VARIABLES { fkGponOltId, fkGponOnuId }
        DESCRIPTION "Description"
        ::= 247

gponOltSFOn  TRAP-TYPE
        ENTERPRISE      fkoltg1040Events
        VARIABLES { fkGponOltId, fkGponOnuId }
        DESCRIPTION "Description"
        ::= 248

gponOltSFOff  TRAP-TYPE
        ENTERPRISE      fkoltg1040Events
        VARIABLES { fkGponOltId, fkGponOnuId }
        DESCRIPTION "Description"
        ::= 249
gponOltSDOn  TRAP-TYPE
        ENTERPRISE      fkoltg1040Events
        VARIABLES { fkGponOltId, fkGponOnuId }
        DESCRIPTION "Description"
        ::= 250

gponOltSDOff  TRAP-TYPE
        ENTERPRISE      fkoltg1040Events
        VARIABLES { fkGponOltId, fkGponOnuId }
        DESCRIPTION "Description"
        ::= 251

gponOltLCDGIOn  TRAP-TYPE
        ENTERPRISE      fkoltg1040Events
        VARIABLES { fkGponOltId, fkGponOnuId }
        DESCRIPTION "Description"
        ::= 252


gponOltLCDGIOff  TRAP-TYPE
        ENTERPRISE      fkoltg1040Events
        VARIABLES { fkGponOltId, fkGponOnuId }
        DESCRIPTION "Description"
        ::= 253


gponOltRDOn  TRAP-TYPE
        ENTERPRISE      fkoltg1040Events
        VARIABLES { fkGponOltId, fkGponOnuId }
        DESCRIPTION "Description"
        ::= 254


gponOltRDOff  TRAP-TYPE
        ENTERPRISE      fkoltg1040Events
        VARIABLES { fkGponOltId, fkGponOnuId }
        DESCRIPTION "Description"
        ::= 255

gponOltSUFOn  TRAP-TYPE
        ENTERPRISE      fkoltg1040Events
        VARIABLES { fkGponOltId, fkGponOnuId }
        DESCRIPTION "Description"
        ::= 256

gponOltSUFOff  TRAP-TYPE
        ENTERPRISE      fkoltg1040Events
        VARIABLES { fkGponOltId, fkGponOnuId }
        DESCRIPTION "Description"
        ::= 257


gponOltLOAOn  TRAP-TYPE
        ENTERPRISE      fkoltg1040Events
        VARIABLES { fkGponOltId, fkGponOnuId }
        DESCRIPTION "Description"
        ::= 258

gponOltLOAOff  TRAP-TYPE
        ENTERPRISE      fkoltg1040Events
        VARIABLES { fkGponOltId, fkGponOnuId }
        DESCRIPTION "Description"
        ::= 259

gponOltLOAMIOn  TRAP-TYPE
        ENTERPRISE      fkoltg1040Events
        VARIABLES { fkGponOltId, fkGponOnuId }
        DESCRIPTION "Description"

        ::= 260
gponOltLOAMIOff  TRAP-TYPE
        ENTERPRISE      fkoltg1040Events
        VARIABLES { fkGponOltId, fkGponOnuId }
        DESCRIPTION "Description"
        ::= 261

gponOltMEMOn  TRAP-TYPE
        ENTERPRISE      fkoltg1040Events
        VARIABLES { fkGponOltId, fkGponOnuId }
        DESCRIPTION "Description"
        ::= 262

gponOltMEMOff  TRAP-TYPE
        ENTERPRISE      fkoltg1040Events
        VARIABLES { fkGponOltId, fkGponOnuId }
        DESCRIPTION "Description"
        ::= 263

gponOltPEEOn  TRAP-TYPE
        ENTERPRISE      fkoltg1040Events
        VARIABLES { fkGponOltId, fkGponOnuId }
        DESCRIPTION "Description"
        ::= 264

gponOltPEEOff  TRAP-TYPE
        ENTERPRISE      fkoltg1040Events
        VARIABLES { fkGponOltId, fkGponOnuId }
        DESCRIPTION "Description"
        ::= 265

gponOltPSTOn  TRAP-TYPE
        ENTERPRISE      fkoltg1040Events
        VARIABLES { fkGponOltId, fkGponOnuId }
        DESCRIPTION "Description"
        ::= 266

gponOltPSTOff  TRAP-TYPE
        ENTERPRISE      fkoltg1040Events
        VARIABLES { fkGponOltId, fkGponOnuId }
        DESCRIPTION "Description"
        ::= 267

gponOltERROn  TRAP-TYPE
        ENTERPRISE      fkoltg1040Events
        VARIABLES { fkGponOltId, fkGponOnuId }
        DESCRIPTION "Description"
        ::= 268

gponOltERROff  TRAP-TYPE
        ENTERPRISE      fkoltg1040Events
        VARIABLES { fkGponOltId, fkGponOnuId }
        DESCRIPTION "Description"
        ::= 269

gponOltREIOn  TRAP-TYPE
        ENTERPRISE      fkoltg1040Events
        VARIABLES { fkGponOltId, fkGponOnuId }
        DESCRIPTION "Description"
        ::= 270

gponOltREIOff   TRAP-TYPE
        ENTERPRISE      fkoltg1040Events
        VARIABLES { fkGponOltId, fkGponOnuId }
        DESCRIPTION "Description"
        ::= 271
             
END
