--
-- FK-MVQOS-MIB.my
-- MIB generated by MG-SOFT Visual MIB Builder Version 3.0 Build 285
-- Tuesday, June 27, 2006 at 09:04:53
--

	FK-MVQOS-MIB DEFINITIONS ::= BEGIN
 
		IMPORTS
			fkMgmt			
				FROM FKOLTG1040-SMI			
			InterfaceIndex			
				FROM IF-MIB			
			FkControlStatusType, FkControlRequestResultType			
				FROM FK-TC-MIB			
			OBJECT-GROUP, NOTIFICATION-GROUP			
				FROM SNMPv2-CONF			
			TimeTicks, IpAddress, Gauge32, OBJECT-TYPE, MODULE-IDENTITY, 
			NOTIFICATION-TYPE			
				FROM SNMPv2-SMI;
	
	
		-- 1.3.6.1.4.1.6.101.14
		fkMVQoS MODULE-IDENTITY 
			LAST-UPDATED "200605102253Z"		-- May 10, 2006 at 22:53 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkMgmt 14 }

		
	
--
-- Type definitions
--
	
		IntQueue ::= INTEGER (-1 | 0..7)

		IntQueueIndex ::= INTEGER (1..8)

		IntEtherType ::= INTEGER (-1 | 0..65535)

		IntEtherTypeIndex ::= INTEGER (1..65535)

		IntIpAddressMask ::= INTEGER (1..31)

		IntQueueDirection ::= INTEGER
			{
			nothing(-1),
			source(1),
			destination(2)
			}

		IntCoS ::= INTEGER (-1 | 0..7)

		IntCoSIndex ::= INTEGER (1..8)

		IntDp ::= INTEGER (-1 | 0..2)

		IntDSCP ::= INTEGER (-1 | 0..63)

	
	
--
-- Node definitions
--
	
		-- 1.3.6.1.4.1.6.101.14.1
		fkMVQoSBase OBJECT IDENTIFIER::= { fkMVQoS 1 }

		
		-- 1.3.6.1.4.1.6.101.14.2
		fkMVQoS4 OBJECT IDENTIFIER::= { fkMVQoS 2 }

		
		-- 1.3.6.1.4.1.6.101.14.2.1
		fkMVQoS4Base OBJECT IDENTIFIER::= { fkMVQoS4 1 }

		
		-- 1.3.6.1.4.1.6.101.14.2.2
		fkMVQoS4BridgeBase OBJECT IDENTIFIER::= { fkMVQoS4 2 }

		
		-- 1.3.6.1.4.1.6.101.14.2.2.1
		fkMVQoS4BridgePort2TCMark OBJECT IDENTIFIER::= { fkMVQoS4BridgeBase 1 }

		
		-- 1.3.6.1.4.1.6.101.14.2.2.1.1
		fkMVQoS4BridgePort2TCMarkTable OBJECT-TYPE
			SYNTAX SEQUENCE OF FkMVQoS4BridgePort2TCMarkEntry
			MAX-ACCESS not-accessible
			STATUS current
			DESCRIPTION
				"Description."
			::= { fkMVQoS4BridgePort2TCMark 1 }

		
		-- 1.3.6.1.4.1.6.101.14.3.2.1.1.1
		fkMVQoS4BridgePort2TCMarkEntry OBJECT-TYPE
			SYNTAX FkMVQoS4BridgePort2TCMarkEntry
			MAX-ACCESS not-accessible
			STATUS current
			DESCRIPTION
				"Description."
			INDEX { fkMVQoS4BridgePort2TCMarkPortIndex }
			::= { fkMVQoS4BridgePort2TCMarkTable 1 }

		
		FkMVQoS4BridgePort2TCMarkEntry ::=
			SEQUENCE { 
				fkMVQoS4BridgePort2TCMarkPortIndex
					InterfaceIndex,
				fkMVQoS4BridgePort2TCMarkQueue
					IntQueue
			 }

		-- 1.3.6.1.4.1.6.101.14.3.2.1.1.1.1
		fkMVQoS4BridgePort2TCMarkPortIndex OBJECT-TYPE
			SYNTAX InterfaceIndex
			MAX-ACCESS read-only
			STATUS current
			DESCRIPTION
				"Description."
			::= { fkMVQoS4BridgePort2TCMarkEntry 1 }

		
		-- 1.3.6.1.4.1.6.101.14.3.2.1.1.1.2
		fkMVQoS4BridgePort2TCMarkQueue OBJECT-TYPE
			SYNTAX IntQueue
			MAX-ACCESS read-only
			STATUS current
			DESCRIPTION
				"Description."
			::= { fkMVQoS4BridgePort2TCMarkEntry 2 }

		
		-- 1.3.6.1.4.1.6.101.14.2.2.1.2
		fkMVQoS4BridgePort2TCMarkControl OBJECT IDENTIFIER::= { fkMVQoS4BridgePort2TCMark 2 }

		
		-- 1.3.6.1.4.1.6.101.14.2.2.1.2.1
		fkMVQoS4BridgePort2TCMarkControlRequest OBJECT-TYPE
			SYNTAX INTEGER { setBridgePort2TCMark(1) }
			MAX-ACCESS read-write
			STATUS current
			DESCRIPTION
				"Description."
			::= { fkMVQoS4BridgePort2TCMarkControl 1 }

		
		-- 1.3.6.1.4.1.6.101.14.2.2.1.2.2
		fkMVQoS4BridgePort2TCMarkControlStatus OBJECT-TYPE
			SYNTAX FkControlStatusType
			MAX-ACCESS read-write
			STATUS current
			DESCRIPTION
				"Description."
			::= { fkMVQoS4BridgePort2TCMarkControl 2 }

		
		-- 1.3.6.1.4.1.6.101.14.2.2.1.2.3
		fkMVQoS4BridgePort2TCMarkControlTimer OBJECT-TYPE
			SYNTAX Gauge32
			MAX-ACCESS read-write
			STATUS current
			DESCRIPTION
				"Description."
			::= { fkMVQoS4BridgePort2TCMarkControl 3 }

		
		-- 1.3.6.1.4.1.6.101.14.2.2.1.2.4
		fkMVQoS4BridgePort2TCMarkControlTmeStamp OBJECT-TYPE
			SYNTAX TimeTicks
			MAX-ACCESS read-write
			STATUS current
			DESCRIPTION
				"Description."
			::= { fkMVQoS4BridgePort2TCMarkControl 4 }

		
		-- 1.3.6.1.4.1.6.101.14.2.2.1.2.5
		fkMVQoS4BridgePort2TCMarkControlReqResult OBJECT-TYPE
			SYNTAX FkControlRequestResultType
			MAX-ACCESS read-write
			STATUS current
			DESCRIPTION
				"Description."
			::= { fkMVQoS4BridgePort2TCMarkControl 5 }

		
		-- 1.3.6.1.4.1.6.101.14.2.2.1.2.6
		fkMVQoS4BridgePort2TCMarkControlPortIndex OBJECT-TYPE
			SYNTAX InterfaceIndex
			MAX-ACCESS read-write
			STATUS current
			DESCRIPTION
				"Description."
			::= { fkMVQoS4BridgePort2TCMarkControl 6 }

		
		-- 1.3.6.1.4.1.6.101.14.2.2.1.2.7
		fkMVQoS4BridgePort2TCMarkControlQueue OBJECT-TYPE
			SYNTAX IntQueue
			MAX-ACCESS read-write
			STATUS current
			DESCRIPTION
				"Description."
			::= { fkMVQoS4BridgePort2TCMarkControl 7 }

		
		-- 1.3.6.1.4.1.6.101.14.2.2.1.3
		fkMVQoS4BridgePort2TCMarkNotification OBJECT IDENTIFIER::= { fkMVQoS4BridgePort2TCMark 3 }

		
		-- 1.3.6.1.4.1.6.101.14.2.2.1.3.1
		fkBridgePort2TCMarkChanged NOTIFICATION-TYPE
			OBJECTS { fkMVQoS4BridgePort2TCMarkControlRequest, fkMVQoS4BridgePort2TCMarkControlTmeStamp, fkMVQoS4BridgePort2TCMarkControlReqResult, fkMVQoS4BridgePort2TCMarkQueue }
			STATUS current
			DESCRIPTION 
				"Description."
			::= { fkMVQoS4BridgePort2TCMarkNotification 1 }

		
		-- 1.3.6.1.4.1.6.101.14.2.3
		fkMVQoS4InLIF OBJECT IDENTIFIER::= { fkMVQoS4 3 }

		
		-- 1.3.6.1.4.1.6.101.14.2.3.1
		fkMVQoS4InLIFMark OBJECT IDENTIFIER::= { fkMVQoS4InLIF 1 }

		
		-- 1.3.6.1.4.1.6.101.14.2.3.1.1
		fkMVQoS4InLIFMarkTable OBJECT-TYPE
			SYNTAX SEQUENCE OF FkMVQoS4InLIFMarkEntry
			MAX-ACCESS not-accessible
			STATUS current
			DESCRIPTION
				"Description."
			::= { fkMVQoS4InLIFMark 1 }

		
		-- 1.3.6.1.4.1.6.101.14.3.3.1.1.1
		fkMVQoS4InLIFMarkEntry OBJECT-TYPE
			SYNTAX FkMVQoS4InLIFMarkEntry
			MAX-ACCESS not-accessible
			STATUS current
			DESCRIPTION
				"Description."
			INDEX { fkMVQoS4InLIFMarkPortIndex }
			::= { fkMVQoS4InLIFMarkTable 1 }

		
		FkMVQoS4InLIFMarkEntry ::=
			SEQUENCE { 
				fkMVQoS4InLIFMarkPortIndex
					InterfaceIndex,
				fkMVQoS4InLIFMarkCoS
					IntCoS,
				fkMVQoS4InLIFMarkDSCP
					IntDSCP
			 }

		-- 1.3.6.1.4.1.6.101.14.3.3.1.1.1.1
		fkMVQoS4InLIFMarkPortIndex OBJECT-TYPE
			SYNTAX InterfaceIndex
			MAX-ACCESS read-only
			STATUS current
			DESCRIPTION
				"Description."
			::= { fkMVQoS4InLIFMarkEntry 1 }

		
		-- 1.3.6.1.4.1.6.101.14.3.3.1.1.1.2
		fkMVQoS4InLIFMarkCoS OBJECT-TYPE
			SYNTAX IntCoS
			MAX-ACCESS read-only
			STATUS current
			DESCRIPTION
				"Description."
			::= { fkMVQoS4InLIFMarkEntry 2 }

		
		-- 1.3.6.1.4.1.6.101.14.3.3.1.1.1.3
		fkMVQoS4InLIFMarkDSCP OBJECT-TYPE
			SYNTAX IntDSCP
			MAX-ACCESS read-only
			STATUS current
			DESCRIPTION
				"Description."
			::= { fkMVQoS4InLIFMarkEntry 3 }

		
		-- 1.3.6.1.4.1.6.101.14.2.3.1.2
		fkMVQoS4InLIFMarkControl OBJECT IDENTIFIER::= { fkMVQoS4InLIFMark 2 }

		
		-- 1.3.6.1.4.1.6.101.14.2.3.1.2.1
		fkMVQoS4InLIFMarkControlRequest OBJECT-TYPE
			SYNTAX INTEGER
				{
				setInLIFUp(1),
				setInLIFDscp(2)
				}
			MAX-ACCESS read-write
			STATUS current
			DESCRIPTION
				"Description."
			::= { fkMVQoS4InLIFMarkControl 1 }

		
		-- 1.3.6.1.4.1.6.101.14.2.3.1.2.2
		fkMVQoS4InLIFMarkControlStatus OBJECT-TYPE
			SYNTAX FkControlStatusType
			MAX-ACCESS read-write
			STATUS current
			DESCRIPTION
				"Description."
			::= { fkMVQoS4InLIFMarkControl 2 }

		
		-- 1.3.6.1.4.1.6.101.14.2.3.1.2.3
		fkMVQoS4InLIFMarkControlTimer OBJECT-TYPE
			SYNTAX Gauge32
			MAX-ACCESS read-write
			STATUS current
			DESCRIPTION
				"Description."
			::= { fkMVQoS4InLIFMarkControl 3 }

		
		-- 1.3.6.1.4.1.6.101.14.2.3.1.2.4
		fkMVQoS4InLIFMarkControlTimeStamp OBJECT-TYPE
			SYNTAX TimeTicks
			MAX-ACCESS read-write
			STATUS current
			DESCRIPTION
				"Description."
			::= { fkMVQoS4InLIFMarkControl 4 }

		
		-- 1.3.6.1.4.1.6.101.14.2.3.1.2.5
		fkMVQoS4InLIFMarkControlReqResult OBJECT-TYPE
			SYNTAX FkControlRequestResultType
			MAX-ACCESS read-write
			STATUS current
			DESCRIPTION
				"Description."
			::= { fkMVQoS4InLIFMarkControl 5 }

		
		-- 1.3.6.1.4.1.6.101.14.2.3.1.2.6
		fkMVQoS4InLIFMarkControlPortIndex OBJECT-TYPE
			SYNTAX InterfaceIndex
			MAX-ACCESS read-write
			STATUS current
			DESCRIPTION
				"Description."
			::= { fkMVQoS4InLIFMarkControl 6 }

		
		-- 1.3.6.1.4.1.6.101.14.2.3.1.2.7
		fkMVQoS4InLIFMarkControlCoS OBJECT-TYPE
			SYNTAX IntCoS
			MAX-ACCESS read-write
			STATUS current
			DESCRIPTION
				"Description."
			::= { fkMVQoS4InLIFMarkControl 7 }

		
		-- 1.3.6.1.4.1.6.101.14.2.3.1.2.8
		fkMVQoS4InLIFMarkControlDSCP OBJECT-TYPE
			SYNTAX IntDSCP
			MAX-ACCESS read-write
			STATUS current
			DESCRIPTION
				"Description."
			::= { fkMVQoS4InLIFMarkControl 8 }

		
		-- 1.3.6.1.4.1.6.101.14.2.3.1.3
		fkMVQoS4InLIFMarkNotification OBJECT IDENTIFIER::= { fkMVQoS4InLIFMark 3 }

		
		-- 1.3.6.1.4.1.6.101.14.2.3.1.3.1
		fkInLIFMarkUpChanged NOTIFICATION-TYPE
			OBJECTS { fkMVQoS4InLIFMarkControlRequest, fkMVQoS4InLIFMarkControlTimeStamp, fkMVQoS4InLIFMarkControlReqResult, fkMVQoS4InLIFMarkCoS }
			STATUS current
			DESCRIPTION 
				"Description."
			::= { fkMVQoS4InLIFMarkNotification 1 }

		
		-- 1.3.6.1.4.1.6.101.14.2.3.1.3.2
		fkInLIFMarkDscpChanged NOTIFICATION-TYPE
			OBJECTS { fkMVQoS4InLIFMarkControlRequest, fkMVQoS4InLIFMarkControlTimeStamp, fkMVQoS4InLIFMarkControlReqResult, fkMVQoS4InLIFMarkDSCP }
			STATUS current
			DESCRIPTION 
				"Description."
			::= { fkMVQoS4InLIFMarkNotification 2 }

		
		-- 1.3.6.1.4.1.6.101.14.2.4
		fkMVQoS4Router OBJECT IDENTIFIER::= { fkMVQoS4 4 }

		
		-- 1.3.6.1.4.1.6.101.14.2.4.1
		fkMVQoS4RouterMark OBJECT IDENTIFIER::= { fkMVQoS4Router 1 }

		
		-- 1.3.6.1.4.1.6.101.14.2.4.1.1
		fkMVQoS4RouterMarkTable OBJECT-TYPE
			SYNTAX SEQUENCE OF FkMVQoS4RouterMarkEntry
			MAX-ACCESS not-accessible
			STATUS current
			DESCRIPTION
				"Description."
			::= { fkMVQoS4RouterMark 1 }

		
		-- 1.3.6.1.4.1.6.101.14.3.4.1.1.1
		fkMVQoS4RouterMarkEntry OBJECT-TYPE
			SYNTAX FkMVQoS4RouterMarkEntry
			MAX-ACCESS not-accessible
			STATUS current
			DESCRIPTION
				"Description."
			INDEX { fkMVQoS4RouterMarkNextHop }
			::= { fkMVQoS4RouterMarkTable 1 }

		
		FkMVQoS4RouterMarkEntry ::=
			SEQUENCE { 
				fkMVQoS4RouterMarkNextHop
					IpAddress,
				fkMVQoS4RouterMarkQueue
					IntQueue,
				fkMVQoS4RouterMarkDp
					IntDp,
				fkMVQoS4RouterMarkCoS
					IntCoS
			 }

		-- 1.3.6.1.4.1.6.101.14.3.4.1.1.1.1
		fkMVQoS4RouterMarkNextHop OBJECT-TYPE
			SYNTAX IpAddress
			MAX-ACCESS read-only
			STATUS current
			DESCRIPTION
				"Description."
			::= { fkMVQoS4RouterMarkEntry 1 }

		
		-- 1.3.6.1.4.1.6.101.14.3.4.1.1.1.2
		fkMVQoS4RouterMarkQueue OBJECT-TYPE
			SYNTAX IntQueue
			MAX-ACCESS read-only
			STATUS current
			DESCRIPTION
				"Description."
			::= { fkMVQoS4RouterMarkEntry 2 }

		
		-- 1.3.6.1.4.1.6.101.14.3.4.1.1.1.3
		fkMVQoS4RouterMarkDp OBJECT-TYPE
			SYNTAX IntDp
			MAX-ACCESS read-only
			STATUS current
			DESCRIPTION
				"Description."
			::= { fkMVQoS4RouterMarkEntry 3 }

		
		-- 1.3.6.1.4.1.6.101.14.3.4.1.1.1.4
		fkMVQoS4RouterMarkCoS OBJECT-TYPE
			SYNTAX IntCoS
			MAX-ACCESS read-only
			STATUS current
			DESCRIPTION
				"Description."
			::= { fkMVQoS4RouterMarkEntry 4 }

		
		-- 1.3.6.1.4.1.6.101.14.2.4.1.2
		fkMVQoS4RouterMarkControl OBJECT IDENTIFIER::= { fkMVQoS4RouterMark 2 }

		
		-- 1.3.6.1.4.1.6.101.14.2.4.1.2.1
		fkMVQoS4RouterMarkControlRequest OBJECT-TYPE
			SYNTAX INTEGER
				{
				createRouterMarkEntry(1),
				setRouterMarkEntry(2),
				destroyRouterMarkEntry(3)
				}
			MAX-ACCESS read-write
			STATUS current
			DESCRIPTION
				"Description."
			::= { fkMVQoS4RouterMarkControl 1 }

		
		-- 1.3.6.1.4.1.6.101.14.2.4.1.2.2
		fkMVQoS4RouterMarkControlStatus OBJECT-TYPE
			SYNTAX FkControlStatusType
			MAX-ACCESS read-write
			STATUS current
			DESCRIPTION
				"Description."
			::= { fkMVQoS4RouterMarkControl 2 }

		
		-- 1.3.6.1.4.1.6.101.14.2.4.1.2.3
		fkMVQoS4RouterMarkControlTimer OBJECT-TYPE
			SYNTAX Gauge32
			MAX-ACCESS read-write
			STATUS current
			DESCRIPTION
				"Description."
			::= { fkMVQoS4RouterMarkControl 3 }

		
		-- 1.3.6.1.4.1.6.101.14.2.4.1.2.4
		fkMVQoS4RouterMarkControlTimeStamp OBJECT-TYPE
			SYNTAX TimeTicks
			MAX-ACCESS read-write
			STATUS current
			DESCRIPTION
				"Description."
			::= { fkMVQoS4RouterMarkControl 4 }

		
		-- 1.3.6.1.4.1.6.101.14.2.4.1.2.5
		fkMVQoS4RouterMarkControlReqResult OBJECT-TYPE
			SYNTAX FkControlRequestResultType
			MAX-ACCESS read-write
			STATUS current
			DESCRIPTION
				"Description."
			::= { fkMVQoS4RouterMarkControl 5 }

		
		-- 1.3.6.1.4.1.6.101.14.2.4.1.2.6
		fkMVQoS4RouterMarkControlNextHop OBJECT-TYPE
			SYNTAX IpAddress
			MAX-ACCESS read-only
			STATUS current
			DESCRIPTION
				"Description."
			::= { fkMVQoS4RouterMarkControl 6 }

		
		-- 1.3.6.1.4.1.6.101.14.2.4.1.2.7
		fkMVQoS4RouterMarkControlQueue OBJECT-TYPE
			SYNTAX IntQueue
			MAX-ACCESS read-write
			STATUS current
			DESCRIPTION
				"Description."
			::= { fkMVQoS4RouterMarkControl 7 }

		
		-- 1.3.6.1.4.1.6.101.14.2.4.1.2.8
		fkMVQoS4RouterMarkControlDp OBJECT-TYPE
			SYNTAX IntDp
			MAX-ACCESS read-write
			STATUS current
			DESCRIPTION
				"Description."
			::= { fkMVQoS4RouterMarkControl 8 }

		
		-- 1.3.6.1.4.1.6.101.14.2.4.1.2.9
		fkMVQoS4RouterMarkControlCoS OBJECT-TYPE
			SYNTAX IntCoS
			MAX-ACCESS read-write
			STATUS current
			DESCRIPTION
				"Description."
			::= { fkMVQoS4RouterMarkControl 9 }

		
		-- 1.3.6.1.4.1.6.101.14.2.4.1.3
		fkMVQoS4RouterMarkNotification OBJECT IDENTIFIER::= { fkMVQoS4RouterMark 3 }

		
		-- 1.3.6.1.4.1.6.101.14.2.4.1.3.1
		fkRouterMarkEntryCreated NOTIFICATION-TYPE
			OBJECTS { fkMVQoS4RouterMarkControlRequest, fkMVQoS4RouterMarkControlTimeStamp, fkMVQoS4RouterMarkControlReqResult, fkMVQoS4RouterMarkQueue, fkMVQoS4RouterMarkDp, 
				fkMVQoS4RouterMarkCoS }
			STATUS current
			DESCRIPTION 
				"Description."
			::= { fkMVQoS4RouterMarkNotification 1 }

		
		-- 1.3.6.1.4.1.6.101.14.2.4.1.3.2
		fkRouterMarkEntryChanged NOTIFICATION-TYPE
			OBJECTS { fkMVQoS4RouterMarkControlRequest, fkMVQoS4RouterMarkControlTimeStamp, fkMVQoS4RouterMarkControlReqResult, fkMVQoS4RouterMarkQueue, fkMVQoS4RouterMarkDp, 
				fkMVQoS4RouterMarkCoS }
			STATUS current
			DESCRIPTION 
				"Description."
			::= { fkMVQoS4RouterMarkNotification 2 }

		
		-- 1.3.6.1.4.1.6.101.14.2.4.1.3.3
		fkRouterMarkEntryDestroyed NOTIFICATION-TYPE
			OBJECTS { fkMVQoS4RouterMarkControlRequest, fkMVQoS4RouterMarkControlTimeStamp, fkMVQoS4RouterMarkControlReqResult, fkMVQoS4RouterMarkControlNextHop }
			STATUS current
			DESCRIPTION 
				"Description."
			::= { fkMVQoS4RouterMarkNotification 3 }

		
		-- 1.3.6.1.4.1.6.101.14.3
		fkMVQoS6 OBJECT IDENTIFIER::= { fkMVQoS 3 }

		
		-- 1.3.6.1.4.1.6.101.14.4
		fkMVQoSGroup OBJECT-GROUP
			OBJECTS { fkMVQoS4BridgePort2TCMarkPortIndex, fkMVQoS4BridgePort2TCMarkQueue, fkMVQoS4InLIFMarkPortIndex, fkMVQoS4InLIFMarkCoS, fkMVQoS4InLIFMarkDSCP, 
				fkMVQoS4RouterMarkNextHop, fkMVQoS4RouterMarkQueue, fkMVQoS4RouterMarkDp, fkMVQoS4RouterMarkCoS }
			STATUS current
			DESCRIPTION 
				"Description."
			::= { fkMVQoS 4 }

		
		-- 1.3.6.1.4.1.6.101.14.5
		fkMVQoSControlGroup OBJECT-GROUP
			OBJECTS { fkMVQoS4BridgePort2TCMarkControlRequest, fkMVQoS4BridgePort2TCMarkControlStatus, fkMVQoS4BridgePort2TCMarkControlTimer, fkMVQoS4BridgePort2TCMarkControlTmeStamp, fkMVQoS4BridgePort2TCMarkControlReqResult, 
				fkMVQoS4BridgePort2TCMarkControlPortIndex, fkMVQoS4BridgePort2TCMarkControlQueue, fkMVQoS4RouterMarkControlRequest, fkMVQoS4RouterMarkControlStatus, fkMVQoS4RouterMarkControlTimer, 
				fkMVQoS4RouterMarkControlTimeStamp, fkMVQoS4RouterMarkControlReqResult, fkMVQoS4RouterMarkControlNextHop, fkMVQoS4RouterMarkControlQueue, fkMVQoS4RouterMarkControlDp, 
				fkMVQoS4RouterMarkControlCoS, fkMVQoS4InLIFMarkControlRequest, fkMVQoS4InLIFMarkControlStatus, fkMVQoS4InLIFMarkControlTimer, fkMVQoS4InLIFMarkControlTimeStamp, 
				fkMVQoS4InLIFMarkControlReqResult, fkMVQoS4InLIFMarkControlPortIndex, fkMVQoS4InLIFMarkControlCoS, fkMVQoS4InLIFMarkControlDSCP }
			STATUS current
			DESCRIPTION 
				"Description."
			::= { fkMVQoS 5 }

		
		-- 1.3.6.1.4.1.6.101.14.6
		fkMVQoSNotificationGroup NOTIFICATION-GROUP
			NOTIFICATIONS { fkBridgePort2TCMarkChanged, fkInLIFMarkUpChanged, fkInLIFMarkDscpChanged, fkRouterMarkEntryDestroyed, fkRouterMarkEntryCreated, 
				fkRouterMarkEntryChanged }
			STATUS current
			DESCRIPTION 
				"Description."
			::= { fkMVQoS 6 }

		
	
	END

--
-- FK-MVQOS-MIB.my
--
