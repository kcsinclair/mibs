--
-- FK-DHCP-MIB.my
-- MIB generated by MG-SOFT Visual MIB Builder Version 3.0 Build 285
-- Wednesday, February 14, 2007 at 11:27:52
--

        FK-DHCP-MIB DEFINITIONS ::= BEGIN
 
                IMPORTS
                        fkMgmt                  
                                FROM FKOLTG1040-SMI                     
                        InterfaceIndex                  
                                FROM IF-MIB                     
                        FkControlStatusType, FkControlRequestResultType                 
                                FROM FK-TC-MIB                  
                        OBJECT-GROUP, NOTIFICATION-GROUP                        
                                FROM SNMPv2-CONF                        
                        TimeTicks, IpAddress, Integer32, Unsigned32, Gauge32, OBJECT-TYPE, MODULE-IDENTITY, NOTIFICATION-TYPE                   
                                FROM SNMPv2-SMI                 
                        MacAddress                      
                                FROM SNMPv2-TC;
        
        
                -- 1.3.6.1.4.1.10428 9 1.101.6
                fkDhcp MODULE-IDENTITY 
                        LAST-UPDATED "200412291441Z"            -- December 29, 2004 at 14:41 GMT
                        ORGANIZATION 
                                "Furukawa Industrial S.A."
                        CONTACT-INFO 
                                "Furukawa Industrial S.A. Produtos Eletricos
        Rua Hasdrubal Bellegard, 820 - CIC
        CEP 81460-120 - Curitiba - Parana - Brasil
        CSC 0800-41-2100
        E-mail: fisa@furukawa.com.br"
                        DESCRIPTION 
                                "The MIB module for Furukawa GPON OLT FK-OLT-G1040."
                        ::= { fkMgmt 6 }

                
        
        
        
--
-- Node definitions
--
        
                -- 1.3.6.1.4.1.10428 9 1.101.6.1
                fkDhcpBase OBJECT IDENTIFIER::= { fkDhcp 1 }

                
                -- 1.3.6.1.4.1.10428 9 1.101.6.1.1
                fkDhcpBaseInfo OBJECT IDENTIFIER::= { fkDhcpBase 1 }

                
                -- 1.3.6.1.4.1.10428 9 1.101.6.1.1.1
                fkDhcpDefaultLeaseTime OBJECT-TYPE
                        SYNTAX INTEGER (0 | 120..2147483637)
                        MAX-ACCESS read-only
                        STATUS current
                        DESCRIPTION
                                "The default time assigned to Lease in Dhcp server. 
                                The unit is second.
                                If 0, the default time was not set."
                        ::= { fkDhcpBaseInfo 1 }

                
                -- 1.3.6.1.4.1.10428 9 1.101.6.1.1.2
                fkDhcpMaxLeaseTime OBJECT-TYPE
                        SYNTAX INTEGER (0 | 120..2147483637)
                        MAX-ACCESS read-only
                        STATUS current
                        DESCRIPTION
                                "The max time assigned to Lease in Dhcp server. 
                                The unit is second.
                                If 0, the max time was not set."
                        ::= { fkDhcpBaseInfo 2 }

                
                -- 1.3.6.1.4.1.10428 9 1.101.6.1.1.3
                fkDhcpDnsIp1 OBJECT-TYPE
                        SYNTAX IpAddress
                        MAX-ACCESS read-only
                        STATUS current
                        DESCRIPTION
                                "The default Dns IP of the Dhcp daemon"
                        ::= { fkDhcpBaseInfo 3 }

                
                -- 1.3.6.1.4.1.10428 9 1.101.6.1.1.4
                fkDhcpDnsIp2 OBJECT-TYPE
                        SYNTAX IpAddress
                        MAX-ACCESS read-only
                        STATUS current
                        DESCRIPTION
                                "The default Dns IP of the Dhcp daemon"
                        ::= { fkDhcpBaseInfo 4 }

                
                -- 1.3.6.1.4.1.10428 9 1.101.6.1.1.5
                fkDhcpDnsIp3 OBJECT-TYPE
                        SYNTAX IpAddress
                        MAX-ACCESS read-only
                        STATUS current
                        DESCRIPTION
                                "The default Dns IP of the Dhcp daemon"
                        ::= { fkDhcpBaseInfo 5 }

                
                -- 1.3.6.1.4.1.10428 9 1.101.6.1.1.6
                fkDhcpMode OBJECT-TYPE
                        SYNTAX INTEGER
                                {
                                noOperation(0),
                                serverMode(1),
                                relayMode(2)
                                }
                        MAX-ACCESS read-only
                        STATUS current
                        DESCRIPTION
                                "The Dhcp operation mode."
                        ::= { fkDhcpBaseInfo 6 }

                
                -- 1.3.6.1.4.1.10428 9 1.101.6.1.1.7
                fkDhcpLeasedbBackupIp OBJECT-TYPE
                        SYNTAX IpAddress
                        MAX-ACCESS read-only
                        STATUS current
                        DESCRIPTION
                                "The Ip address of LeaseDB backup server.
                                If 0.0.0.0, it is not set."
                        ::= { fkDhcpBaseInfo 7 }

                
                -- 1.3.6.1.4.1.10428 9 1.101.6.1.1.8
                fkDhcpLeasedbBackupInterval OBJECT-TYPE
                        SYNTAX INTEGER (0..2147483637)
                        MAX-ACCESS read-only
                        STATUS current
                        DESCRIPTION
                                "The interval time assigned to LeaseDB backup.
                                The unit is second.
                                If 0, it is not set."
                        ::= { fkDhcpBaseInfo 8 }

                
                -- 1.3.6.1.4.1.10428 9 1.101.6.1.1.9
                fkDhcpDatabaseKey OBJECT-TYPE
                        SYNTAX INTEGER
                                {
                                clientid(0),
                                hwaddress(1)
                                }
                        MAX-ACCESS read-only
                        STATUS current
                        DESCRIPTION
                                "The Database-key Setting for dhcp daemon.
                                "
                        ::= { fkDhcpBaseInfo 9 }

                
                -- 1.3.6.1.4.1.10428 9 1.101.6.1.1.10
                fkDhcpDebugStatus OBJECT-TYPE
                        SYNTAX BITS
                                {
                                debugFilter(0),
                                debugLease(1),
                                debugPacket(2),
                                debugServices(3)
                                }
                        MAX-ACCESS read-write
                        STATUS current
                        DESCRIPTION
                                "The  debug option setting of dhcp daemon.
                                debugNo(0)
                                debugFilter(1)
                                debugLease(2)
                                debugPacket(4)
                                debugService(8)
                                The above value is denotes by 'or'.
                                debugAll(16)
                                
                                "
                        ::= { fkDhcpBaseInfo 10 }

                
                -- 1.3.6.1.4.1.10428 9 1.101.6.1.1.11
                fkDhcpOption82 OBJECT-TYPE
                        SYNTAX INTEGER
                                {
                                disable(0),
                                enable(1)
                                }
                        MAX-ACCESS read-only
                        STATUS current
                        DESCRIPTION
                                "The Option82 is set or not.
                                0 : not set
                                1 : set"
                        ::= { fkDhcpBaseInfo 11 }

                
                -- 1.3.6.1.4.1.10428 9 1.101.6.1.1.12
                fkDhcpOption82Policy OBJECT-TYPE
                        SYNTAX INTEGER
                                {
                                keep(0),
                                replace(1),
                                drop(2)
                                }
                        MAX-ACCESS read-only
                        STATUS current
                        DESCRIPTION
                                "The Option82 policy
                                1 - keep
                                2 - replace
                                3 - drop"
                        ::= { fkDhcpBaseInfo 12 }

                
                -- 1.3.6.1.4.1.10428 9 1.101.6.1.1.13
                fkDhcpOption82SystemRtype OBJECT-TYPE
                        SYNTAX INTEGER
                                {
                                invalid(0),
                                ipaddress(1),
                                binary(2),
                                text(3)
                                }
                        MAX-ACCESS read-only
                        STATUS current
                        DESCRIPTION
                                "Value type of  fkDhcpOption82SystemRid
                                invalid : The value of fkDhcpOption82SystemRid is invalid.
                                ipaddress : denotes such as 'A.B.C.D'.
                                binary : denotes such as '89:AB:CD:EF:01:02'.
                                text : denotes such as 'TextString'.
                                
                                "
                        ::= { fkDhcpBaseInfo 13 }

                
                -- 1.3.6.1.4.1.10428 9 1.101.6.1.1.14
                fkDhcpOption82SystemRid OBJECT-TYPE
                        SYNTAX OCTET STRING (SIZE (0..63))
                        MAX-ACCESS read-only
                        STATUS current
                        DESCRIPTION
                                "This value is the system remote index 
                                for option82 function."
                        ::= { fkDhcpBaseInfo 14 }

                
                -- 1.3.6.1.4.1.10428 9 1.101.6.1.1.15
                fkDhcpAuthorizedArp OBJECT-TYPE
                        SYNTAX INTEGER
                                {
                                noSet(0),
                                defaultLeaseTime(1),
                                halfLeaseTime(2),
                                maxLeaseTime(3)
                                }
                        MAX-ACCESS read-only
                        STATUS current
                        DESCRIPTION
                                "The set of starting time for secure ARP function.
                                0:no set
                                1:default-lease-time
                                2:half-lease-time
                                3:max-lease-time"
                        ::= { fkDhcpBaseInfo 15 }

                
                -- 1.3.6.1.4.1.10428 9 1.101.6.1.1.16
                fkDhcpAuthArpStarted OBJECT-TYPE
                        SYNTAX OCTET STRING
                        MAX-ACCESS read-only
                        STATUS current
                        DESCRIPTION
                                "The Time when authorized-arp function has started.
                                It denotes such as '2004/12/20 10:20:30'."
                        ::= { fkDhcpBaseInfo 16 }

                
                -- 1.3.6.1.4.1.10428 9 1.101.6.1.1.17
                fkDhcpAuthArpLeft OBJECT-TYPE
                        SYNTAX OCTET STRING
                        MAX-ACCESS read-only
                        STATUS current
                        DESCRIPTION
                                "The left time until authorized-arp function will be start.
                                It denotes such as '01:20:31'"
                        ::= { fkDhcpBaseInfo 17 }

                
                -- 1.3.6.1.4.1.10428 9 1.101.6.1.1.18
                fkDhcpStatisticReceived OBJECT-TYPE
                        SYNTAX Unsigned32
                        MAX-ACCESS read-only
                        STATUS current
                        DESCRIPTION
                                "The number of received DHCP packets."
                        ::= { fkDhcpBaseInfo 18 }

                
                -- 1.3.6.1.4.1.10428 9 1.101.6.1.1.19
                fkDhcpStatisticSent OBJECT-TYPE
                        SYNTAX Unsigned32
                        MAX-ACCESS read-only
                        STATUS current
                        DESCRIPTION
                                "The number of sent DHCP packets."
                        ::= { fkDhcpBaseInfo 19 }

                
                -- 1.3.6.1.4.1.10428 9 1.101.6.1.1.20
                fkDhcpStatisticReceivedErrors OBJECT-TYPE
                        SYNTAX Unsigned32
                        MAX-ACCESS read-only
                        STATUS current
                        DESCRIPTION
                                "The number of received DHCP Error packets."
                        ::= { fkDhcpBaseInfo 20 }

                
                -- 1.3.6.1.4.1.10428 9 1.101.6.1.1.21
                fkDhcpStatisticSentErrors OBJECT-TYPE
                        SYNTAX Unsigned32
                        MAX-ACCESS read-only
                        STATUS current
                        DESCRIPTION
                                "The number of sent DHCP Error packets."
                        ::= { fkDhcpBaseInfo 21 }

                
                -- 1.3.6.1.4.1.10428 9 1.101.6.1.1.22
                fkDhcpStatisticBootpReceivedRequests OBJECT-TYPE
                        SYNTAX Unsigned32
                        MAX-ACCESS read-only
                        STATUS current
                        DESCRIPTION
                                "The number of received DHCP Bootp Request packets."
                        ::= { fkDhcpBaseInfo 22 }

                
                -- 1.3.6.1.4.1.10428 9 1.101.6.1.1.23
                fkDhcpStatisticBootpReceivedReplies OBJECT-TYPE
                        SYNTAX Unsigned32
                        MAX-ACCESS read-only
                        STATUS current
                        DESCRIPTION
                                "The number of received DHCP Bootp Reply packets."
                        ::= { fkDhcpBaseInfo 23 }

                
                -- 1.3.6.1.4.1.10428 9 1.101.6.1.1.24
                fkDhcpStatisticBootpSentRequests OBJECT-TYPE
                        SYNTAX Unsigned32
                        MAX-ACCESS read-only
                        STATUS current
                        DESCRIPTION
                                "The number of sent DHCP Bootp Request packets."
                        ::= { fkDhcpBaseInfo 24 }

                
                -- 1.3.6.1.4.1.10428 9 1.101.6.1.1.25
                fkDhcpStatisticBootpSentReplies OBJECT-TYPE
                        SYNTAX Unsigned32
                        MAX-ACCESS read-only
                        STATUS current
                        DESCRIPTION
                                "The number of sent DHCP Bootp Reply packets."
                        ::= { fkDhcpBaseInfo 25 }

                
                -- 1.3.6.1.4.1.10428 9 1.101.6.1.1.26
                fkDhcpStatisticReceivedDiscover OBJECT-TYPE
                        SYNTAX Unsigned32
                        MAX-ACCESS read-only
                        STATUS current
                        DESCRIPTION
                                "The number of received Discover packets."
                        ::= { fkDhcpBaseInfo 26 }

                
                -- 1.3.6.1.4.1.10428 9 1.101.6.1.1.27
                fkDhcpStatisticReceivedRequest OBJECT-TYPE
                        SYNTAX Unsigned32
                        MAX-ACCESS read-only
                        STATUS current
                        DESCRIPTION
                                "The number of received DHCP Request packets."
                        ::= { fkDhcpBaseInfo 27 }

                
                -- 1.3.6.1.4.1.10428 9 1.101.6.1.1.28
                fkDhcpStatisticReceivedRelease OBJECT-TYPE
                        SYNTAX Unsigned32
                        MAX-ACCESS read-only
                        STATUS current
                        DESCRIPTION
                                "The number of received DHCP Release packets."
                        ::= { fkDhcpBaseInfo 28 }

                
                -- 1.3.6.1.4.1.10428 9 1.101.6.1.1.29
                fkDhcpStatisticReceivedInform OBJECT-TYPE
                        SYNTAX Unsigned32
                        MAX-ACCESS read-only
                        STATUS current
                        DESCRIPTION
                                "The number of received DHCP Inform packets."
                        ::= { fkDhcpBaseInfo 29 }

                
                -- 1.3.6.1.4.1.10428 9 1.101.6.1.1.30
                fkDhcpStatisticReceivedDecline OBJECT-TYPE
                        SYNTAX Unsigned32
                        MAX-ACCESS read-only
                        STATUS current
                        DESCRIPTION
                                "The number of received DHCP Decline packets."
                        ::= { fkDhcpBaseInfo 30 }

                
                -- 1.3.6.1.4.1.10428 9 1.101.6.1.1.31
                fkDhcpStatisticSentOffer OBJECT-TYPE
                        SYNTAX Unsigned32
                        MAX-ACCESS read-only
                        STATUS current
                        DESCRIPTION
                                "The number of sent DHCP Offer packets."
                        ::= { fkDhcpBaseInfo 31 }

                
                -- 1.3.6.1.4.1.10428 9 1.101.6.1.1.32
                fkDhcpStatisticSentAck OBJECT-TYPE
                        SYNTAX Unsigned32
                        MAX-ACCESS read-only
                        STATUS current
                        DESCRIPTION
                                "The number of sent DHCP Ack packets."
                        ::= { fkDhcpBaseInfo 32 }

                
                -- 1.3.6.1.4.1.10428 9 1.101.6.1.1.33
                fkDhcpStatisticSentNak OBJECT-TYPE
                        SYNTAX Unsigned32
                        MAX-ACCESS read-only
                        STATUS current
                        DESCRIPTION
                                "The number of sent DHCP Nak packets."
                        ::= { fkDhcpBaseInfo 33 }

                
                -- 1.3.6.1.4.1.10428 9 1.101.6.1.1.34
                fkDhcpSummaryPoolCnt OBJECT-TYPE
                        SYNTAX Unsigned32
                        MAX-ACCESS read-only
                        STATUS current
                        DESCRIPTION
                                "The number of Pools.to be set."
                        ::= { fkDhcpBaseInfo 34 }

                
                -- 1.3.6.1.4.1.10428 9 1.101.6.1.1.35
                fkDhcpSummaryTotal OBJECT-TYPE
                        SYNTAX Unsigned32
                        MAX-ACCESS read-only
                        STATUS current
                        DESCRIPTION
                                "The number of Total leases to be set."
                        ::= { fkDhcpBaseInfo 35 }

                
                -- 1.3.6.1.4.1.10428 9 1.101.6.1.1.36
                fkDhcpSummaryAvailable OBJECT-TYPE
                        SYNTAX Unsigned32
                        MAX-ACCESS read-only
                        STATUS current
                        DESCRIPTION
                                "The number of Available leases to be set."
                        ::= { fkDhcpBaseInfo 36 }

                
                -- 1.3.6.1.4.1.10428 9 1.101.6.1.1.37
                fkDhcpSummaryAbandon OBJECT-TYPE
                        SYNTAX Unsigned32
                        MAX-ACCESS read-only
                        STATUS current
                        DESCRIPTION
                                "The number of Abandon leases to be set."
                        ::= { fkDhcpBaseInfo 37 }

                
                -- 1.3.6.1.4.1.10428 9 1.101.6.1.1.38
                fkDhcpSummaryBound OBJECT-TYPE
                        SYNTAX Unsigned32
                        MAX-ACCESS read-only
                        STATUS current
                        DESCRIPTION
                                "The number of Bound leases to be set."
                        ::= { fkDhcpBaseInfo 38 }

                
                -- 1.3.6.1.4.1.10428 9 1.101.6.1.1.39
                fkDhcpSummaryOffered OBJECT-TYPE
                        SYNTAX Unsigned32
                        MAX-ACCESS read-only
                        STATUS current
                        DESCRIPTION
                                "The number of Offered leases to be set."
                        ::= { fkDhcpBaseInfo 39 }

                
                -- 1.3.6.1.4.1.10428 9 1.101.6.1.1.40
                fkDhcpSummaryFixed OBJECT-TYPE
                        SYNTAX Unsigned32
                        MAX-ACCESS read-only
                        STATUS current
                        DESCRIPTION
                                "The number of Fixed leases to be set."
                        ::= { fkDhcpBaseInfo 40 }

                
                -- 1.3.6.1.4.1.10428 9 1.101.6.1.1.41
                fkDhcpClientHardwareAddress OBJECT-TYPE
                        SYNTAX INTEGER
                                {
                                disable(0),
                                enable(1)
                                }
                        MAX-ACCESS read-only
                        STATUS current
                        DESCRIPTION
                                "Description."
                        ::= { fkDhcpBaseInfo 41 }

                
                -- 1.3.6.1.4.1.10428 9 1.101.6.1.1.42
                fkDhcpSimplifiedOption82 OBJECT-TYPE
                        SYNTAX INTEGER
                                {
                                disable(0),
                                enable(1)
                                }
                        MAX-ACCESS read-only
                        STATUS current
                        DESCRIPTION
                                "Description."
                        ::= { fkDhcpBaseInfo 42 }

                
                -- 1.3.6.1.4.1.10428 9 1.101.6.1.1.43
                fkDhcpSummaryAllocated OBJECT-TYPE
                        SYNTAX Unsigned32
                        MAX-ACCESS read-only
                        STATUS current
                        DESCRIPTION
                                "Description."
                        ::= { fkDhcpBaseInfo 43 }

                
                -- 1.3.6.1.4.1.10428 9 1.101.6.1.2
                fkDhcpBaseControl OBJECT IDENTIFIER::= { fkDhcpBase 2 }

                
                -- 1.3.6.1.4.1.10428 9 1.101.6.1.2.1
                fkDhcpControlRequest OBJECT-TYPE
                        SYNTAX INTEGER
                                {
                                setDhcpLeaseTimeProfile(1),
                                setDhcpDnsIpProfile(2),
                                setDhcpServerMode(3),
                                setDhcpLeasedbBackupProfile(4),
                                setDhcpDatabaseKey(5),
                                setDhcpDebugStatus(6),
                                setDhcpOption82SystemProfile(7),
                                setDhcpAuthorizedArp(8),
                                clearDhcpStatistics(9),
                                setDhcpClientHardwareAddress(10),
                                setSimplifiedOption82(11)
                                }
                        MAX-ACCESS read-write
                        STATUS current
                        DESCRIPTION
                                "The request of a user command."
                        ::= { fkDhcpBaseControl 1 }

                
                -- 1.3.6.1.4.1.10428 9 1.101.6.1.2.2
                fkDhcpControlStatus OBJECT-TYPE
                        SYNTAX FkControlStatusType
                        MAX-ACCESS read-only
                        STATUS current
                        DESCRIPTION
                                "The status of a user command."
                        ::= { fkDhcpBaseControl 2 }

                
                -- 1.3.6.1.4.1.10428 9 1.101.6.1.2.3
                fkDhcpControlTimer OBJECT-TYPE
                        SYNTAX Gauge32
                        MAX-ACCESS read-write
                        STATUS current
                        DESCRIPTION
                                "The maximum wait time for the manager for a long running user command."
                        ::= { fkDhcpBaseControl 3 }

                
                -- 1.3.6.1.4.1.10428 9 1.101.6.1.2.4
                fkDhcpControlTimeStamp OBJECT-TYPE
                        SYNTAX TimeTicks
                        MAX-ACCESS read-only
                        STATUS current
                        DESCRIPTION
                                "The time stamp of the last command (end of command)."
                        ::= { fkDhcpBaseControl 4 }

                
                -- 1.3.6.1.4.1.10428 9 1.101.6.1.2.5
                fkDhcpControlReqResult OBJECT-TYPE
                        SYNTAX FkControlRequestResultType
                        MAX-ACCESS read-only
                        STATUS current
                        DESCRIPTION
                                "The result of the last user command."
                        ::= { fkDhcpBaseControl 5 }

                
                -- 1.3.6.1.4.1.10428 9 1.101.6.1.2.6
                fkDhcpControlDefaultLeaseTime OBJECT-TYPE
                        SYNTAX INTEGER (0 | 120..2147483637)
                        MAX-ACCESS read-write
                        STATUS current
                        DESCRIPTION
                                "Description."
                        ::= { fkDhcpBaseControl 6 }

                
                -- 1.3.6.1.4.1.10428 9 1.101.6.1.2.7
                fkDhcpControlMaxLeaseTime OBJECT-TYPE
                        SYNTAX INTEGER (0 | 120..2147483637)
                        MAX-ACCESS read-write
                        STATUS current
                        DESCRIPTION
                                "Description."
                        ::= { fkDhcpBaseControl 7 }

                
                -- 1.3.6.1.4.1.10428 9 1.101.6.1.2.8
                fkDhcpControlDnsIp1 OBJECT-TYPE
                        SYNTAX IpAddress
                        MAX-ACCESS read-write
                        STATUS current
                        DESCRIPTION
                                "Description."
                        ::= { fkDhcpBaseControl 8 }

                
                -- 1.3.6.1.4.1.10428 9 1.101.6.1.2.9
                fkDhcpControlDnsIp2 OBJECT-TYPE
                        SYNTAX IpAddress
                        MAX-ACCESS read-write
                        STATUS current
                        DESCRIPTION
                                "Description."
                        ::= { fkDhcpBaseControl 9 }

                
                -- 1.3.6.1.4.1.10428 9 1.101.6.1.2.10
                fkDhcpControlDnsIp3 OBJECT-TYPE
                        SYNTAX IpAddress
                        MAX-ACCESS read-write
                        STATUS current
                        DESCRIPTION
                                "Description."
                        ::= { fkDhcpBaseControl 10 }

                
                -- 1.3.6.1.4.1.10428 9 1.101.6.1.2.11
                fkDhcpControlServerMode OBJECT-TYPE
                        SYNTAX INTEGER
                                {
                                clear(0),
                                set(1)
                                }
                        MAX-ACCESS read-write
                        STATUS current
                        DESCRIPTION
                                "Description."
                        ::= { fkDhcpBaseControl 11 }

                
                -- 1.3.6.1.4.1.10428 9 1.101.6.1.2.12
                fkDhcpControlLeasedbBackupIp OBJECT-TYPE
                        SYNTAX IpAddress
                        MAX-ACCESS read-write
                        STATUS current
                        DESCRIPTION
                                "Description."
                        ::= { fkDhcpBaseControl 12 }

                
                -- 1.3.6.1.4.1.10428 9 1.101.6.1.2.13
                fkDhcpControlLeasedbBackupInterval OBJECT-TYPE
                        SYNTAX INTEGER (0..2147483637)
                        MAX-ACCESS read-write
                        STATUS current
                        DESCRIPTION
                                "Description."
                        ::= { fkDhcpBaseControl 13 }

                
                -- 1.3.6.1.4.1.10428 9 1.101.6.1.2.14
                fkDhcpControlDatabaseKey OBJECT-TYPE
                        SYNTAX INTEGER
                                {
                                clientid(0),
                                hwaddress(1)
                                }
                        MAX-ACCESS read-write
                        STATUS current
                        DESCRIPTION
                                "Description."
                        ::= { fkDhcpBaseControl 14 }

                
                -- 1.3.6.1.4.1.10428 9 1.101.6.1.2.15
                fkDhcpControlDebugStatus OBJECT-TYPE
                        SYNTAX BITS
                                {
                                debugFilter(0),
                                debugLease(1),
                                debugPacket(2),
                                debugServices(3)
                                }
                        MAX-ACCESS read-write
                        STATUS current
                        DESCRIPTION
                                "The  debug option setting of dhcp daemon.
                                The  debug option setting of dhcp daemon.
                                debugNo(0)
                                debugFilter(1)
                                debugLease(2)
                                debugPacket(4)
                                debugService(8)
                                The above value is denotes by 'or'.
                                debugAll(16)
                                
                                "
                        ::= { fkDhcpBaseControl 15 }

                
                -- 1.3.6.1.4.1.10428 9 1.101.6.1.2.16
                fkDhcpControlOption82 OBJECT-TYPE
                        SYNTAX INTEGER
                                {
                                disable(0),
                                enable(1)
                                }
                        MAX-ACCESS read-write
                        STATUS current
                        DESCRIPTION
                                "Description."
                        ::= { fkDhcpBaseControl 16 }

                
                -- 1.3.6.1.4.1.10428 9 1.101.6.1.2.17
                fkDhcpControlOption82Policy OBJECT-TYPE
                        SYNTAX INTEGER
                                {
                                keep(0),
                                replace(1),
                                drop(2)
                                }
                        MAX-ACCESS read-write
                        STATUS current
                        DESCRIPTION
                                "Description."
                        ::= { fkDhcpBaseControl 17 }

                
                -- 1.3.6.1.4.1.10428 9 1.101.6.1.2.18
                fkDhcpControlOption82SystemRtype OBJECT-TYPE
                        SYNTAX INTEGER
                                {
                                invalid(0),
                                ipaddress(1),
                                binary(2),
                                text(3)
                                }
                        MAX-ACCESS read-write
                        STATUS current
                        DESCRIPTION
                                "Value type of  fkDhcpOption82SystemRid
                                invalid : it is cleared.
                                ipaddress : denotes such as 'A.B.C.D'.
                                binary : denotes such as '89:AB:CD:EF:01:02'.
                                text : denotes such as 'TextString'.
                                "
                        ::= { fkDhcpBaseControl 18 }

                
                -- 1.3.6.1.4.1.10428 9 1.101.6.1.2.19
                fkDhcpControlOption82SystemRid OBJECT-TYPE
                        SYNTAX OCTET STRING (SIZE (0..63))
                        MAX-ACCESS read-write
                        STATUS current
                        DESCRIPTION
                                "This value is the system remote index 
                                for option82 function.
                                If the size is 0, it is cleared."
                        ::= { fkDhcpBaseControl 19 }

                
                -- 1.3.6.1.4.1.10428 9 1.101.6.1.2.20
                fkDhcpControlAuthorizedArp OBJECT-TYPE
                        SYNTAX INTEGER
                                {
                                noSet(0),
                                defaultLeaseTime(1),
                                halfLeaseTime(2),
                                maxLeaseTime(3)
                                }
                        MAX-ACCESS read-write
                        STATUS current
                        DESCRIPTION
                                "Description."
                        ::= { fkDhcpBaseControl 20 }

                
                -- 1.3.6.1.4.1.10428 9 1.101.6.1.2.21
                fkDhcpControlClientHardwareAddress OBJECT-TYPE
                        SYNTAX INTEGER
                                {
                                disable(0),
                                enable(1)
                                }
                        MAX-ACCESS read-write
                        STATUS current
                        DESCRIPTION
                                "Description."
                        ::= { fkDhcpBaseControl 21 }

                
                -- 1.3.6.1.4.1.10428 9 1.101.6.1.2.22
                fkDhcpControlSimplifiedOption82 OBJECT-TYPE
                        SYNTAX INTEGER
                                {
                                disable(0),
                                enable(1)
                                }
                        MAX-ACCESS read-write
                        STATUS current
                        DESCRIPTION
                                "Description."
                        ::= { fkDhcpBaseControl 22 }

                
                -- 1.3.6.1.4.1.10428 9 1.101.6.1.3
                fkDhcpBaseNotification OBJECT IDENTIFIER::= { fkDhcpBase 3 }

                
                -- 1.3.6.1.4.1.10428 9 1.101.6.1.3.1
                fkDhcpLeaseTimeProfileChanged NOTIFICATION-TYPE
                        OBJECTS { fkDhcpDefaultLeaseTime, fkDhcpMaxLeaseTime, fkDhcpControlRequest, fkDhcpControlTimeStamp, fkDhcpControlReqResult
                                 }
                        STATUS current
                        DESCRIPTION 
                                "Description."
                        ::= { fkDhcpBaseNotification 1 }

                
                -- 1.3.6.1.4.1.10428 9 1.101.6.1.3.2
                fkDhcpDnsIpProfileChanged NOTIFICATION-TYPE
                        OBJECTS { fkDhcpDnsIp1, fkDhcpDnsIp2, fkDhcpDnsIp3, fkDhcpControlRequest, fkDhcpControlTimeStamp, 
                                fkDhcpControlReqResult }
                        STATUS current
                        DESCRIPTION 
                                "Description."
                        ::= { fkDhcpBaseNotification 2 }

                
                -- 1.3.6.1.4.1.10428 9 1.101.6.1.3.3
                fkDhcpServerModeChanged NOTIFICATION-TYPE
                        OBJECTS { fkDhcpMode, fkDhcpControlRequest, fkDhcpControlTimeStamp, fkDhcpControlReqResult }
                        STATUS current
                        DESCRIPTION 
                                "Description."
                        ::= { fkDhcpBaseNotification 3 }

                
                -- 1.3.6.1.4.1.10428 9 1.101.6.1.3.4
                fkDhcpLeasedbBackupProfileChanged NOTIFICATION-TYPE
                        OBJECTS { fkDhcpLeasedbBackupIp, fkDhcpLeasedbBackupInterval, fkDhcpControlRequest, fkDhcpControlTimeStamp, fkDhcpControlReqResult
                                 }
                        STATUS current
                        DESCRIPTION 
                                "Description."
                        ::= { fkDhcpBaseNotification 4 }

                
                -- 1.3.6.1.4.1.10428 9 1.101.6.1.3.5
                fkDhcpDatabaseKeyChanged NOTIFICATION-TYPE
                        OBJECTS { fkDhcpDatabaseKey, fkDhcpControlRequest, fkDhcpControlTimeStamp, fkDhcpControlReqResult }
                        STATUS current
                        DESCRIPTION 
                                "Description."
                        ::= { fkDhcpBaseNotification 5 }

                
                -- 1.3.6.1.4.1.10428 9 1.101.6.1.3.6
                fkDhcpDebugStatusChanged NOTIFICATION-TYPE
                        OBJECTS { fkDhcpDebugStatus, fkDhcpControlRequest, fkDhcpControlTimeStamp, fkDhcpControlReqResult }
                        STATUS current
                        DESCRIPTION 
                                "Description."
                        ::= { fkDhcpBaseNotification 6 }

                
                -- 1.3.6.1.4.1.10428 9 1.101.6.1.3.7
                fkDhcpOption82SystemProfileChanged NOTIFICATION-TYPE
                        OBJECTS { fkDhcpControlRequest, fkDhcpControlTimeStamp, fkDhcpControlReqResult, fkDhcpOption82, fkDhcpOption82Policy, 
                                fkDhcpOption82SystemRtype, fkDhcpOption82SystemRid }
                        STATUS current
                        DESCRIPTION 
                                "Description."
                        ::= { fkDhcpBaseNotification 7 }

                
                -- 1.3.6.1.4.1.10428 9 1.101.6.1.3.8
                fkDhcpAuthorizedArpChanged NOTIFICATION-TYPE
                        OBJECTS { fkDhcpAuthorizedArp, fkDhcpControlRequest, fkDhcpControlTimeStamp, fkDhcpControlReqResult }
                        STATUS current
                        DESCRIPTION 
                                "Description."
                        ::= { fkDhcpBaseNotification 8 }

                
                -- 1.3.6.1.4.1.10428 9 1.101.6.1.3.9
                fkDhcpStatisticsCleared NOTIFICATION-TYPE
                        OBJECTS { fkDhcpControlRequest, fkDhcpControlTimeStamp, fkDhcpControlReqResult }
                        STATUS current
                        DESCRIPTION 
                                "Description."
                        ::= { fkDhcpBaseNotification 9 }

                
                -- 1.3.6.1.4.1.10428 9 1.101.6.1.3.10
                fkDhcpClientHardwareAddressChanged NOTIFICATION-TYPE
                        OBJECTS { fkDhcpControlRequest, fkDhcpControlTimeStamp, fkDhcpControlReqResult, fkDhcpControlClientHardwareAddress }
                        STATUS current
                        DESCRIPTION 
                                "Description."
                        ::= { fkDhcpBaseNotification 10 }

                
                -- 1.3.6.1.4.1.10428 9 1.101.6.1.3.11
                fkDhcpSimplifiedOption82Changed NOTIFICATION-TYPE
                        OBJECTS { fkDhcpControlRequest, fkDhcpControlTimeStamp, fkDhcpControlReqResult, fkDhcpControlSimplifiedOption82 }
                        STATUS current
                        DESCRIPTION 
                                "Description."
                        ::= { fkDhcpBaseNotification 11 }

                
                -- 1.3.6.1.4.1.10428 9 1.101.6.2
                fkFilterPort OBJECT IDENTIFIER::= { fkDhcp 2 }

                
                -- 1.3.6.1.4.1.10428 9 1.101.6.2.1
                fkFilterPortTable OBJECT-TYPE
                        SYNTAX SEQUENCE OF FkFilterPortEntry
                        MAX-ACCESS not-accessible
                        STATUS current
                        DESCRIPTION
                                "Description."
                        ::= { fkFilterPort 1 }

                
                -- 1.3.6.1.4.1.10428 9 1.101.6.2.1.1
                fkFilterPortEntry OBJECT-TYPE
                        SYNTAX FkFilterPortEntry
                        MAX-ACCESS not-accessible
                        STATUS current
                        DESCRIPTION
                                "Description."
                        INDEX { fkFilterPortIndex }
                        ::= { fkFilterPortTable 1 }

                
                FkFilterPortEntry ::=
                        SEQUENCE { 
                                fkFilterPortIndex
                                        InterfaceIndex,
                                fkFilterPortMode
                                        INTEGER
                         }

                -- 1.3.6.1.4.1.10428 9 1.101.6.2.1.1.1
                fkFilterPortIndex OBJECT-TYPE
                        SYNTAX InterfaceIndex
                        MAX-ACCESS read-only
                        STATUS current
                        DESCRIPTION
                                "Description."
                        ::= { fkFilterPortEntry 1 }

                
                -- 1.3.6.1.4.1.10428 9 1.101.6.2.1.1.2
                fkFilterPortMode OBJECT-TYPE
                        SYNTAX INTEGER (0 | 1)
                        MAX-ACCESS read-only
                        STATUS current
                        DESCRIPTION
                                "Description."
                        ::= { fkFilterPortEntry 2 }

                
                -- 1.3.6.1.4.1.10428 9 1.101.6.2.2
                fkFilterPortControl OBJECT IDENTIFIER::= { fkFilterPort 2 }

                
                -- 1.3.6.1.4.1.10428 9 1.101.6.2.2.1
                fkFilterPortControlRequest OBJECT-TYPE
                        SYNTAX INTEGER { setFilterPortMode(1) }
                        MAX-ACCESS read-write
                        STATUS current
                        DESCRIPTION
                                "The request of a user command."
                        ::= { fkFilterPortControl 1 }

                
                -- 1.3.6.1.4.1.10428 9 1.101.6.2.2.2
                fkFilterPortControlStatus OBJECT-TYPE
                        SYNTAX FkControlStatusType
                        MAX-ACCESS read-only
                        STATUS current
                        DESCRIPTION
                                "The status of a user command."
                        ::= { fkFilterPortControl 2 }

                
                -- 1.3.6.1.4.1.10428 9 1.101.6.2.2.3
                fkFilterPortControlTimer OBJECT-TYPE
                        SYNTAX Gauge32
                        MAX-ACCESS read-write
                        STATUS current
                        DESCRIPTION
                                "The maximum wait time for the manager for a long running user command."
                        ::= { fkFilterPortControl 3 }

                
                -- 1.3.6.1.4.1.10428 9 1.101.6.2.2.4
                fkFilterPortControlTImeStamp OBJECT-TYPE
                        SYNTAX TimeTicks
                        MAX-ACCESS read-only
                        STATUS current
                        DESCRIPTION
                                "The time stamp of the last command (end of command)."
                        ::= { fkFilterPortControl 4 }

                
                -- 1.3.6.1.4.1.10428 9 1.101.6.2.2.5
                fkFilterPortControlReqResult OBJECT-TYPE
                        SYNTAX FkControlRequestResultType
                        MAX-ACCESS read-only
                        STATUS current
                        DESCRIPTION
                                "The result of the last user command."
                        ::= { fkFilterPortControl 5 }

                
                -- 1.3.6.1.4.1.10428 9 1.101.6.2.2.6
                fkFilterPortControlIndex OBJECT-TYPE
                        SYNTAX INTEGER (1..255)
                        MAX-ACCESS read-write
                        STATUS current
                        DESCRIPTION
                                "Description."
                        ::= { fkFilterPortControl 6 }

                
                -- 1.3.6.1.4.1.10428 9 1.101.6.2.2.7
                fkFilterPortControlMode OBJECT-TYPE
                        SYNTAX INTEGER
                                {
                                clear(0),
                                set(1)
                                }
                        MAX-ACCESS read-write
                        STATUS current
                        DESCRIPTION
                                "Description."
                        ::= { fkFilterPortControl 7 }

                
                -- 1.3.6.1.4.1.10428 9 1.101.6.2.3
                fkFilterPortNotification OBJECT IDENTIFIER::= { fkFilterPort 3 }

                
                -- 1.3.6.1.4.1.10428 9 1.101.6.2.3.1
                fkFilterPortChanged NOTIFICATION-TYPE
                        OBJECTS { fkFilterPortMode, fkFilterPortControlRequest, fkFilterPortControlTImeStamp, fkFilterPortControlReqResult }
                        STATUS current
                        DESCRIPTION 
                                "Description."
                        ::= { fkFilterPortNotification 1 }

                
                -- 1.3.6.1.4.1.10428 9 1.101.6.3
                fkFilterAddress OBJECT IDENTIFIER::= { fkDhcp 3 }

                
                -- 1.3.6.1.4.1.10428 9 1.101.6.3.1
                fkFilterAddressTable OBJECT-TYPE
                        SYNTAX SEQUENCE OF FkFilterAddressEntry
                        MAX-ACCESS not-accessible
                        STATUS current
                        DESCRIPTION
                                "Description."
                        ::= { fkFilterAddress 1 }

                
                -- 1.3.6.1.4.1.10428 9 1.101.6.3.1.1
                fkFilterAddressEntry OBJECT-TYPE
                        SYNTAX FkFilterAddressEntry
                        MAX-ACCESS not-accessible
                        STATUS current
                        DESCRIPTION
                                "Description."
                        INDEX { fkFilterAddressMac }
                        ::= { fkFilterAddressTable 1 }

                
                FkFilterAddressEntry ::=
                        SEQUENCE { 
                                fkFilterAddressMac
                                        MacAddress
                         }

                -- 1.3.6.1.4.1.10428 9 1.101.6.3.1.1.1
                fkFilterAddressMac OBJECT-TYPE
                        SYNTAX MacAddress
                        MAX-ACCESS read-only
                        STATUS current
                        DESCRIPTION
                                "Description."
                        ::= { fkFilterAddressEntry 1 }

                
                -- 1.3.6.1.4.1.10428 9 1.101.6.3.2
                fkFilterAddressControl OBJECT IDENTIFIER::= { fkFilterAddress 2 }

                
                -- 1.3.6.1.4.1.10428 9 1.101.6.3.2.1
                fkFilterAddressControlRequest OBJECT-TYPE
                        SYNTAX INTEGER
                                {
                                createFilterAddress(1),
                                destroyFilterAddress(2)
                                }
                        MAX-ACCESS read-write
                        STATUS current
                        DESCRIPTION
                                "The request of a user command."
                        ::= { fkFilterAddressControl 1 }

                
                -- 1.3.6.1.4.1.10428 9 1.101.6.3.2.2
                fkFilterAddressControlStatus OBJECT-TYPE
                        SYNTAX FkControlStatusType
                        MAX-ACCESS read-only
                        STATUS current
                        DESCRIPTION
                                "The status of a user command."
                        ::= { fkFilterAddressControl 2 }

                
                -- 1.3.6.1.4.1.10428 9 1.101.6.3.2.3
                fkFilterAddressControlTimer OBJECT-TYPE
                        SYNTAX Gauge32
                        MAX-ACCESS read-write
                        STATUS current
                        DESCRIPTION
                                "The maximum wait time for the manager for a long running user command."
                        ::= { fkFilterAddressControl 3 }

                
                -- 1.3.6.1.4.1.10428 9 1.101.6.3.2.4
                fkFilterAddressControlTImeStamp OBJECT-TYPE
                        SYNTAX TimeTicks
                        MAX-ACCESS read-only
                        STATUS current
                        DESCRIPTION
                                "The time stamp of the last command (end of command)."
                        ::= { fkFilterAddressControl 4 }

                
                -- 1.3.6.1.4.1.10428 9 1.101.6.3.2.5
                fkFilterAddressControlReqResult OBJECT-TYPE
                        SYNTAX FkControlRequestResultType
                        MAX-ACCESS read-only
                        STATUS current
                        DESCRIPTION
                                "The result of the last user command."
                        ::= { fkFilterAddressControl 5 }

                
                -- 1.3.6.1.4.1.10428 9 1.101.6.3.2.6
                fkFilterAddressControlMac OBJECT-TYPE
                        SYNTAX MacAddress
                        MAX-ACCESS read-write
                        STATUS current
                        DESCRIPTION
                                "The MAC Address for the Deny Host."
                        ::= { fkFilterAddressControl 6 }

                
                -- 1.3.6.1.4.1.10428 9 1.101.6.3.3
                fkFilterAddressNotification OBJECT IDENTIFIER::= { fkFilterAddress 3 }

                
                -- 1.3.6.1.4.1.10428 9 1.101.6.3.3.1
                fkFilterAddressCreated NOTIFICATION-TYPE
                        OBJECTS { fkFilterAddressMac, fkFilterAddressControlRequest, fkFilterAddressControlTImeStamp, fkFilterAddressControlReqResult }
                        STATUS current
                        DESCRIPTION 
                                "Description."
                        ::= { fkFilterAddressNotification 1 }

                
                -- 1.3.6.1.4.1.10428 9 1.101.6.3.3.2
                fkFilterAddressDestroyed NOTIFICATION-TYPE
                        OBJECTS { fkFilterAddressMac, fkFilterAddressControlRequest, fkFilterAddressControlTImeStamp, fkFilterAddressControlReqResult }
                        STATUS current
                        DESCRIPTION 
                                "Description."
                        ::= { fkFilterAddressNotification 2 }

                
                -- 1.3.6.1.4.1.10428 9 1.101.6.4
                fkRelayServer OBJECT IDENTIFIER::= { fkDhcp 4 }

                
                -- 1.3.6.1.4.1.10428 9 1.101.6.4.1
                fkRelayServerTable OBJECT-TYPE
                        SYNTAX SEQUENCE OF FkRelayServerEntry
                        MAX-ACCESS not-accessible
                        STATUS current
                        DESCRIPTION
                                "Description."
                        ::= { fkRelayServer 1 }

                
                -- 1.3.6.1.4.1.10428 9 1.101.6.4.1.1
                fkRelayServerEntry OBJECT-TYPE
                        SYNTAX FkRelayServerEntry
                        MAX-ACCESS not-accessible
                        STATUS current
                        DESCRIPTION
                                "Description."
                        INDEX { fkRelayServerIndex }
                        ::= { fkRelayServerTable 1 }

                
                FkRelayServerEntry ::=
                        SEQUENCE { 
                                fkRelayServerIndex
                                        Integer32,
                                fkRelayServerIp
                                        IpAddress,
                                fkRelayServerVid
                                        INTEGER,
                                fkRelayServerOUI
                                        OCTET STRING
                         }

                -- 1.3.6.1.4.1.10428 9 1.101.6.4.1.1.1
                fkRelayServerIndex OBJECT-TYPE
                        SYNTAX Integer32 (1..3)
                        MAX-ACCESS read-only
                        STATUS current
                        DESCRIPTION
                                "Description."
                        ::= { fkRelayServerEntry 1 }

                
                -- 1.3.6.1.4.1.10428 9 1.101.6.4.1.1.2
                fkRelayServerIp OBJECT-TYPE
                        SYNTAX IpAddress
                        MAX-ACCESS read-only
                        STATUS current
                        DESCRIPTION
                                "The DHCP Server IP creating in the Relay Daemon."
                        ::= { fkRelayServerEntry 2 }

                
                -- 1.3.6.1.4.1.10428 9 1.101.6.4.1.1.3
                fkRelayServerVid OBJECT-TYPE
                        SYNTAX INTEGER (1..4094)
                        MAX-ACCESS read-only
                        STATUS current
                        DESCRIPTION
                                "Description."
                        ::= { fkRelayServerEntry 3 }

                
                -- 1.3.6.1.4.1.10428 9 1.101.6.4.1.1.4
                fkRelayServerOUI OBJECT-TYPE
                        SYNTAX OCTET STRING (SIZE (1..3))
                        MAX-ACCESS read-only
                        STATUS current
                        DESCRIPTION
                                "Description."
                        ::= { fkRelayServerEntry 4 }

                
                -- 1.3.6.1.4.1.10428 9 1.101.6.4.2
                fkRelayServerControl OBJECT IDENTIFIER::= { fkRelayServer 2 }

                
                -- 1.3.6.1.4.1.10428 9 1.101.6.4.2.1
                fkRelayServerControlRequest OBJECT-TYPE
                        SYNTAX INTEGER
                                {
                                createRelayServer(1),
                                destroyRelayServer(2),
                                createRelayServerOUI(3),
                                destroyRelayServerOUI(4)
                                }
                        MAX-ACCESS read-write
                        STATUS current
                        DESCRIPTION
                                "The request of a user command.
                                1 - createRelayServer
                                2 - destroyRelayServer"
                        ::= { fkRelayServerControl 1 }

                
                -- 1.3.6.1.4.1.10428 9 1.101.6.4.2.2
                fkRelayServerControlStatus OBJECT-TYPE
                        SYNTAX FkControlStatusType
                        MAX-ACCESS read-only
                        STATUS current
                        DESCRIPTION
                                "The status of a user command."
                        ::= { fkRelayServerControl 2 }

                
                -- 1.3.6.1.4.1.10428 9 1.101.6.4.2.3
                fkRelayServerControlTimer OBJECT-TYPE
                        SYNTAX Gauge32
                        MAX-ACCESS read-write
                        STATUS current
                        DESCRIPTION
                                "The maximum wait time for the manager for a long running user command."
                        ::= { fkRelayServerControl 3 }

                
                -- 1.3.6.1.4.1.10428 9 1.101.6.4.2.4
                fkRelayServerControlTImeStamp OBJECT-TYPE
                        SYNTAX TimeTicks
                        MAX-ACCESS read-only
                        STATUS current
                        DESCRIPTION
                                "The time stamp of the last command (end of command)."
                        ::= { fkRelayServerControl 4 }

                
                -- 1.3.6.1.4.1.10428 9 1.101.6.4.2.5
                fkRelayServerControlReqResult OBJECT-TYPE
                        SYNTAX FkControlRequestResultType
                        MAX-ACCESS read-only
                        STATUS current
                        DESCRIPTION
                                "The result of the last user command."
                        ::= { fkRelayServerControl 5 }

                
                -- 1.3.6.1.4.1.10428 9 1.101.6.4.2.6
                fkRelayServerControlIndex OBJECT-TYPE
                        SYNTAX Integer32 (1..3)
                        MAX-ACCESS read-write
                        STATUS current
                        DESCRIPTION
                                "Description."
                        ::= { fkRelayServerControl 6 }

                
                -- 1.3.6.1.4.1.10428 9 1.101.6.4.2.7
                fkRelayServerControlIp OBJECT-TYPE
                        SYNTAX IpAddress
                        MAX-ACCESS read-write
                        STATUS current
                        DESCRIPTION
                                "Description."
                        ::= { fkRelayServerControl 7 }

                
                -- 1.3.6.1.4.1.10428 9 1.101.6.4.2.8
                fkRelayServerControlVid OBJECT-TYPE
                        SYNTAX INTEGER (1..4094)
                        MAX-ACCESS read-write
                        STATUS current
                        DESCRIPTION
                                "Description."
                        ::= { fkRelayServerControl 8 }

                
                -- 1.3.6.1.4.1.10428 9 1.101.6.4.2.9
                fkRelayServerControlOUI OBJECT-TYPE
                        SYNTAX OCTET STRING (SIZE (1..3))
                        MAX-ACCESS read-write
                        STATUS current
                        DESCRIPTION
                                "Description."
                        ::= { fkRelayServerControl 9 }

                
                -- 1.3.6.1.4.1.10428 9 1.101.6.4.3
                fkRelayServerNotification OBJECT IDENTIFIER::= { fkRelayServer 3 }

                
                -- 1.3.6.1.4.1.10428 9 1.101.6.4.3.1
                fkRelayServerCreated NOTIFICATION-TYPE
                        OBJECTS { fkRelayServerControlRequest, fkRelayServerControlTImeStamp, fkRelayServerControlReqResult, fkRelayServerIp, fkRelayServerVid
                                 }
                        STATUS current
                        DESCRIPTION 
                                "Description."
                        ::= { fkRelayServerNotification 1 }

                
                -- 1.3.6.1.4.1.10428 9 1.101.6.4.3.2
                fkRelayServerDestroyed NOTIFICATION-TYPE
                        OBJECTS { fkRelayServerControlRequest, fkRelayServerControlTImeStamp, fkRelayServerControlReqResult, fkRelayServerIp, fkRelayServerVid
                                 }
                        STATUS current
                        DESCRIPTION 
                                "The fkRelayServerIp is 0.0.0.0 for CLI 
                                'no ip dhcp mode relay all'"
                        ::= { fkRelayServerNotification 2 }

                
                -- 1.3.6.1.4.1.10428 9 1.101.6.4.3.3
                fkRelayServerOUICreated NOTIFICATION-TYPE
                        OBJECTS { fkRelayServerControlRequest, fkRelayServerControlTImeStamp, fkRelayServerControlReqResult, fkRelayServerIp, fkRelayServerVid, 
                                fkRelayServerOUI }
                        STATUS current
                        DESCRIPTION 
                                "Description."
                        ::= { fkRelayServerNotification 3 }

                
                -- 1.3.6.1.4.1.10428 9 1.101.6.4.3.4
                fkRelayServerOUIDestroyed NOTIFICATION-TYPE
                        OBJECTS { fkRelayServerControlRequest, fkRelayServerControlTImeStamp, fkRelayServerControlReqResult, fkRelayServerIp, fkRelayServerVid, 
                                fkRelayServerOUI }
                        STATUS current
                        DESCRIPTION 
                                "Description."
                        ::= { fkRelayServerNotification 4 }

                
                -- 1.3.6.1.4.1.10428 9 1.101.6.5
                fkPool OBJECT IDENTIFIER::= { fkDhcp 5 }

                
                -- 1.3.6.1.4.1.10428 9 1.101.6.5.1
                fkPoolTable OBJECT-TYPE
                        SYNTAX SEQUENCE OF FkPoolEntry
                        MAX-ACCESS not-accessible
                        STATUS current
                        DESCRIPTION
                                "Description."
                        ::= { fkPool 1 }

                
                -- 1.3.6.1.4.1.10428 9 1.101.6.5.1.1
                fkPoolEntry OBJECT-TYPE
                        SYNTAX FkPoolEntry
                        MAX-ACCESS not-accessible
                        STATUS current
                        DESCRIPTION
                                "Description."
                        INDEX { fkPoolIndex }
                        ::= { fkPoolTable 1 }

                
                FkPoolEntry ::=
                        SEQUENCE { 
                                fkPoolIndex
                                        INTEGER,
                                fkPoolName
                                        OCTET STRING,
                                fkPoolDefaultLeaseTime
                                        INTEGER,
                                fkPoolMaxLeaseTime
                                        INTEGER,
                                fkPoolSummaryTotal
                                        Unsigned32,
                                fkPoolSummaryAllocated
                                        Unsigned32,
                                fkPoolSummaryBound
                                        Unsigned32,
                                fkPoolSummaryOffered
                                        Unsigned32,
                                fkPoolSummaryFixed
                                        Unsigned32,
                                fkPoolSummaryAbandon
                                        Unsigned32,
                                fkPoolSummaryAvailable
                                        Unsigned32,
                                fkPoolSummarySubnet
                                        Unsigned32,
                                fkPoolDomainName
                                        OCTET STRING
                         }

                -- 1.3.6.1.4.1.10428 9 1.101.6.5.1.1.1
                fkPoolIndex OBJECT-TYPE
                        SYNTAX INTEGER (1..255)
                        MAX-ACCESS read-only
                        STATUS current
                        DESCRIPTION
                                "The Pool index"
                        ::= { fkPoolEntry 1 }

                
                -- 1.3.6.1.4.1.10428 9 1.101.6.5.1.1.2
                fkPoolName OBJECT-TYPE
                        SYNTAX OCTET STRING
                        MAX-ACCESS read-only
                        STATUS current
                        DESCRIPTION
                                "The Pool name."
                        ::= { fkPoolEntry 2 }

                
                -- 1.3.6.1.4.1.10428 9 1.101.6.5.1.1.3
                fkPoolDefaultLeaseTime OBJECT-TYPE
                        SYNTAX INTEGER (120..2147483637)
                        MAX-ACCESS read-only
                        STATUS current
                        DESCRIPTION
                                "The default time assigned to Lease in Pool.
                                The value of 0 denotes that the default time was not set."
                        ::= { fkPoolEntry 3 }

                
                -- 1.3.6.1.4.1.10428 9 1.101.6.5.1.1.4
                fkPoolMaxLeaseTime OBJECT-TYPE
                        SYNTAX INTEGER (120..2147483637)
                        MAX-ACCESS read-only
                        STATUS current
                        DESCRIPTION
                                "The max time assigned to Lease in Pool.
                                The value of 0 denotes that the max time was not set"
                        ::= { fkPoolEntry 4 }

                
                -- 1.3.6.1.4.1.10428 9 1.101.6.5.1.1.5
                fkPoolSummaryTotal OBJECT-TYPE
                        SYNTAX Unsigned32
                        MAX-ACCESS read-only
                        STATUS current
                        DESCRIPTION
                                "The number of Total Leases in Pool."
                        ::= { fkPoolEntry 5 }

                
                -- 1.3.6.1.4.1.10428 9 1.101.6.5.1.1.6
                fkPoolSummaryAllocated OBJECT-TYPE
                        SYNTAX Unsigned32
                        MAX-ACCESS read-only
                        STATUS current
                        DESCRIPTION
                                "The number of Allocated Leases in Pool."
                        ::= { fkPoolEntry 6 }

                
                -- 1.3.6.1.4.1.10428 9 1.101.6.5.1.1.7
                fkPoolSummaryBound OBJECT-TYPE
                        SYNTAX Unsigned32
                        MAX-ACCESS read-only
                        STATUS current
                        DESCRIPTION
                                "The number of Bound Leases in Pool."
                        ::= { fkPoolEntry 7 }

                
                -- 1.3.6.1.4.1.10428 9 1.101.6.5.1.1.8
                fkPoolSummaryOffered OBJECT-TYPE
                        SYNTAX Unsigned32
                        MAX-ACCESS read-only
                        STATUS current
                        DESCRIPTION
                                "The number of Offered Leases in Pool."
                        ::= { fkPoolEntry 8 }

                
                -- 1.3.6.1.4.1.10428 9 1.101.6.5.1.1.9
                fkPoolSummaryFixed OBJECT-TYPE
                        SYNTAX Unsigned32
                        MAX-ACCESS read-only
                        STATUS current
                        DESCRIPTION
                                "The number of Fixed Leases in Pool."
                        ::= { fkPoolEntry 9 }

                
                -- 1.3.6.1.4.1.10428 9 1.101.6.5.1.1.10
                fkPoolSummaryAbandon OBJECT-TYPE
                        SYNTAX Unsigned32
                        MAX-ACCESS read-only
                        STATUS current
                        DESCRIPTION
                                "The number of Abandon Leases in Pool."
                        ::= { fkPoolEntry 10 }

                
                -- 1.3.6.1.4.1.10428 9 1.101.6.5.1.1.11
                fkPoolSummaryAvailable OBJECT-TYPE
                        SYNTAX Unsigned32
                        MAX-ACCESS read-only
                        STATUS current
                        DESCRIPTION
                                "The number of Available Leases in Pool."
                        ::= { fkPoolEntry 11 }

                
                -- 1.3.6.1.4.1.10428 9 1.101.6.5.1.1.12
                fkPoolSummarySubnet OBJECT-TYPE
                        SYNTAX Unsigned32
                        MAX-ACCESS read-only
                        STATUS current
                        DESCRIPTION
                                "Description."
                        ::= { fkPoolEntry 12 }

                
                -- 1.3.6.1.4.1.10428 9 1.101.6.5.1.1.13
                fkPoolDomainName OBJECT-TYPE
                        SYNTAX OCTET STRING (SIZE (0 | 1..64))
                        MAX-ACCESS read-only
                        STATUS current
                        DESCRIPTION
                                "Description."
                        ::= { fkPoolEntry 13 }

                
                -- 1.3.6.1.4.1.10428 9 1.101.6.5.2
                fkPoolControl OBJECT IDENTIFIER::= { fkPool 2 }

                
                -- 1.3.6.1.4.1.10428 9 1.101.6.5.2.1
                fkPoolControlRequest OBJECT-TYPE
                        SYNTAX INTEGER
                                {
                                createPool(1),
                                destroyPool(2),
                                setPoolLeaseTimeProfile(3),
                                setPoolDomainName(4)
                                }
                        MAX-ACCESS read-write
                        STATUS current
                        DESCRIPTION
                                "The request of a user command."
                        ::= { fkPoolControl 1 }

                
                -- 1.3.6.1.4.1.10428 9 1.101.6.5.2.2
                fkPoolControlStatus OBJECT-TYPE
                        SYNTAX FkControlStatusType
                        MAX-ACCESS read-only
                        STATUS current
                        DESCRIPTION
                                "The status of a user command."
                        ::= { fkPoolControl 2 }

                
                -- 1.3.6.1.4.1.10428 9 1.101.6.5.2.3
                fkPoolControlTimer OBJECT-TYPE
                        SYNTAX Gauge32
                        MAX-ACCESS read-write
                        STATUS current
                        DESCRIPTION
                                "The maximum wait time for the manager for a long running user command."
                        ::= { fkPoolControl 3 }

                
                -- 1.3.6.1.4.1.10428 9 1.101.6.5.2.4
                fkPoolControlTImeStamp OBJECT-TYPE
                        SYNTAX TimeTicks
                        MAX-ACCESS read-only
                        STATUS current
                        DESCRIPTION
                                "The time stamp of the last command (end of command)."
                        ::= { fkPoolControl 4 }

                
                -- 1.3.6.1.4.1.10428 9 1.101.6.5.2.5
                fkPoolControlReqResult OBJECT-TYPE
                        SYNTAX FkControlRequestResultType
                        MAX-ACCESS read-only
                        STATUS current
                        DESCRIPTION
                                "The result of the last user command."
                        ::= { fkPoolControl 5 }

                
                -- 1.3.6.1.4.1.10428 9 1.101.6.5.2.6
                fkPoolControlIndex OBJECT-TYPE
                        SYNTAX INTEGER (1..255)
                        MAX-ACCESS read-write
                        STATUS current
                        DESCRIPTION
                                "Description."
                        ::= { fkPoolControl 6 }

                
                -- 1.3.6.1.4.1.10428 9 1.101.6.5.2.7
                fkPoolControlName OBJECT-TYPE
                        SYNTAX OCTET STRING
                        MAX-ACCESS read-write
                        STATUS current
                        DESCRIPTION
                                "The Pool name."
                        ::= { fkPoolControl 7 }

                
                -- 1.3.6.1.4.1.10428 9 1.101.6.5.2.8
                fkPoolControlDefaultLeaseTime OBJECT-TYPE
                        SYNTAX INTEGER (0 | 120..2147483637)
                        MAX-ACCESS read-write
                        STATUS current
                        DESCRIPTION
                                "The default time assigned to Lease in Pool.
                                If 0, the default time is clear"
                        ::= { fkPoolControl 8 }

                
                -- 1.3.6.1.4.1.10428 9 1.101.6.5.2.9
                fkPoolControlMaxLeaseTime OBJECT-TYPE
                        SYNTAX INTEGER (0 | 120..2147483637)
                        MAX-ACCESS read-write
                        STATUS current
                        DESCRIPTION
                                "The max time assigned to Lease in Pool.
                                If 0, the max time is clear."
                        ::= { fkPoolControl 9 }

                
                -- 1.3.6.1.4.1.10428 9 1.101.6.5.2.10
                fkPoolControlDomainName OBJECT-TYPE
                        SYNTAX OCTET STRING (SIZE (0 | 1..64))
                        MAX-ACCESS read-write
                        STATUS current
                        DESCRIPTION
                                "Description."
                        ::= { fkPoolControl 10 }

                
                -- 1.3.6.1.4.1.10428 9 1.101.6.5.3
                fkPoolNotification OBJECT IDENTIFIER::= { fkPool 3 }

                
                -- 1.3.6.1.4.1.10428 9 1.101.6.5.3.1
                fkPoolCreated NOTIFICATION-TYPE
                        OBJECTS { fkPoolName, fkPoolDefaultLeaseTime, fkPoolMaxLeaseTime, fkPoolControlRequest, fkPoolControlTImeStamp, 
                                fkPoolControlReqResult }
                        STATUS current
                        DESCRIPTION 
                                "Description."
                        ::= { fkPoolNotification 1 }

                
                -- 1.3.6.1.4.1.10428 9 1.101.6.5.3.2
                fkPoolDestroyed NOTIFICATION-TYPE
                        OBJECTS { fkPoolIndex, fkPoolControlRequest, fkPoolControlTImeStamp, fkPoolControlReqResult }
                        STATUS current
                        DESCRIPTION 
                                "Description."
                        ::= { fkPoolNotification 2 }

                
                -- 1.3.6.1.4.1.10428 9 1.101.6.5.3.3
                fkPoolLeaseTimeProfileChanged NOTIFICATION-TYPE
                        OBJECTS { fkPoolDefaultLeaseTime, fkPoolMaxLeaseTime, fkPoolControlRequest, fkPoolControlTImeStamp, fkPoolControlReqResult
                                 }
                        STATUS current
                        DESCRIPTION 
                                "Description."
                        ::= { fkPoolNotification 3 }

                
                -- 1.3.6.1.4.1.10428 9 1.101.6.5.3.4
                fkPoolDomainNameChanged NOTIFICATION-TYPE
                        OBJECTS { fkPoolControlRequest, fkPoolControlTImeStamp, fkPoolControlReqResult, fkPoolDomainName }
                        STATUS current
                        DESCRIPTION 
                                "Description."
                        ::= { fkPoolNotification 4 }

                
                -- 1.3.6.1.4.1.10428 9 1.101.6.6
                fkDns OBJECT IDENTIFIER::= { fkDhcp 6 }

                
                -- 1.3.6.1.4.1.10428 9 1.101.6.6.1
                fkDnsTable OBJECT-TYPE
                        SYNTAX SEQUENCE OF FkDnsEntry
                        MAX-ACCESS not-accessible
                        STATUS current
                        DESCRIPTION
                                "Description."
                        ::= { fkDns 1 }

                
                -- 1.3.6.1.4.1.10428 9 1.101.6.6.1.1
                fkDnsEntry OBJECT-TYPE
                        SYNTAX FkDnsEntry
                        MAX-ACCESS not-accessible
                        STATUS current
                        DESCRIPTION
                                "Description."
                        INDEX { fkPoolIndex, fkDnsIndex }
                        ::= { fkDnsTable 1 }

                
                FkDnsEntry ::=
                        SEQUENCE { 
                                fkDnsIndex
                                        Integer32,
                                fkDnsIp
                                        IpAddress
                         }

                -- 1.3.6.1.4.1.10428 9 1.101.6.6.1.1.1
                fkDnsIndex OBJECT-TYPE
                        SYNTAX Integer32 (1..3)
                        MAX-ACCESS read-only
                        STATUS current
                        DESCRIPTION
                                "Description."
                        ::= { fkDnsEntry 1 }

                
                -- 1.3.6.1.4.1.10428 9 1.101.6.6.1.1.2
                fkDnsIp OBJECT-TYPE
                        SYNTAX IpAddress
                        MAX-ACCESS read-only
                        STATUS current
                        DESCRIPTION
                                "The Ip address of Dns setting in Dhcp server daemon.
                                "
                        ::= { fkDnsEntry 2 }

                
                -- 1.3.6.1.4.1.10428 9 1.101.6.6.2
                fkDnsControl OBJECT IDENTIFIER::= { fkDns 2 }

                
                -- 1.3.6.1.4.1.10428 9 1.101.6.6.2.1
                fkDnsControlRequest OBJECT-TYPE
                        SYNTAX INTEGER
                                {
                                createDns(1),
                                destroyDns(2)
                                }
                        MAX-ACCESS read-write
                        STATUS current
                        DESCRIPTION
                                "The request of a user command."
                        ::= { fkDnsControl 1 }

                
                -- 1.3.6.1.4.1.10428 9 1.101.6.6.2.2
                fkDnsControlStatus OBJECT-TYPE
                        SYNTAX FkControlStatusType
                        MAX-ACCESS read-only
                        STATUS current
                        DESCRIPTION
                                "The status of a user command."
                        ::= { fkDnsControl 2 }

                
                -- 1.3.6.1.4.1.10428 9 1.101.6.6.2.3
                fkDnsControlTimer OBJECT-TYPE
                        SYNTAX Gauge32
                        MAX-ACCESS read-write
                        STATUS current
                        DESCRIPTION
                                "The maximum wait time for the manager for a long running user command."
                        ::= { fkDnsControl 3 }

                
                -- 1.3.6.1.4.1.10428 9 1.101.6.6.2.4
                fkDnsControlTImeStamp OBJECT-TYPE
                        SYNTAX TimeTicks
                        MAX-ACCESS read-only
                        STATUS current
                        DESCRIPTION
                                "The time stamp of the last command (end of command)."
                        ::= { fkDnsControl 4 }

                
                -- 1.3.6.1.4.1.10428 9 1.101.6.6.2.5
                fkDnsControlReqResult OBJECT-TYPE
                        SYNTAX FkControlRequestResultType
                        MAX-ACCESS read-write
                        STATUS current
                        DESCRIPTION
                                "The result of the last user command."
                        ::= { fkDnsControl 5 }

                
                -- 1.3.6.1.4.1.10428 9 1.101.6.6.2.6
                fkDnsControlPoolIndex OBJECT-TYPE
                        SYNTAX INTEGER (1..255)
                        MAX-ACCESS read-write
                        STATUS current
                        DESCRIPTION
                                "Description."
                        ::= { fkDnsControl 6 }

                
                -- 1.3.6.1.4.1.10428 9 1.101.6.6.2.7
                fkDnsControlIndex OBJECT-TYPE
                        SYNTAX Integer32 (1..3)
                        MAX-ACCESS read-write
                        STATUS current
                        DESCRIPTION
                                "Description."
                        ::= { fkDnsControl 7 }

                
                -- 1.3.6.1.4.1.10428 9 1.101.6.6.2.8
                fkDnsControlIp OBJECT-TYPE
                        SYNTAX IpAddress
                        MAX-ACCESS read-write
                        STATUS current
                        DESCRIPTION
                                "Description."
                        ::= { fkDnsControl 8 }

                
                -- 1.3.6.1.4.1.10428 9 1.101.6.6.3
                fkDnsNotification OBJECT IDENTIFIER::= { fkDns 3 }

                
                -- 1.3.6.1.4.1.10428 9 1.101.6.6.3.1
                fkDnsCreated NOTIFICATION-TYPE
                        OBJECTS { fkDnsIp, fkDnsControlRequest, fkDnsControlTImeStamp, fkDnsControlReqResult }
                        STATUS current
                        DESCRIPTION 
                                "Description."
                        ::= { fkDnsNotification 1 }

                
                -- 1.3.6.1.4.1.10428 9 1.101.6.6.3.2
                fkDnsDestroyed NOTIFICATION-TYPE
                        OBJECTS { fkDnsIndex, fkDnsControlRequest, fkDnsControlTImeStamp, fkDnsControlReqResult }
                        STATUS current
                        DESCRIPTION 
                                "The fkDnsIp is 0.0.0.0 for CLI 
                                'no ip dhcp default-config dns-server'"
                        ::= { fkDnsNotification 2 }

                
                -- 1.3.6.1.4.1.10428 9 1.101.6.7
                fkSubnet OBJECT IDENTIFIER::= { fkDhcp 7 }

                
                -- 1.3.6.1.4.1.10428 9 1.101.6.7.1
                fkSubnetTable OBJECT-TYPE
                        SYNTAX SEQUENCE OF FkSubnetEntry
                        MAX-ACCESS not-accessible
                        STATUS current
                        DESCRIPTION
                                "Description."
                        ::= { fkSubnet 1 }

                
                -- 1.3.6.1.4.1.10428 9 1.101.6.7.1.1
                fkSubnetEntry OBJECT-TYPE
                        SYNTAX FkSubnetEntry
                        MAX-ACCESS not-accessible
                        STATUS current
                        DESCRIPTION
                                "Description."
                        INDEX { fkPoolIndex, fkSubnetIp, fkSubnetMask }
                        ::= { fkSubnetTable 1 }

                
                FkSubnetEntry ::=
                        SEQUENCE { 
                                fkSubnetIp
                                        IpAddress,
                                fkSubnetMask
                                        INTEGER,
                                fkSubnetDefaultGateway
                                        IpAddress
                         }

                -- 1.3.6.1.4.1.10428 9 1.101.6.7.1.1.1
                fkSubnetIp OBJECT-TYPE
                        SYNTAX IpAddress
                        MAX-ACCESS read-only
                        STATUS current
                        DESCRIPTION
                                "The Subnet IP Address."
                        ::= { fkSubnetEntry 1 }

                
                -- 1.3.6.1.4.1.10428 9 1.101.6.7.1.1.2
                fkSubnetMask OBJECT-TYPE
                        SYNTAX INTEGER (1..32)
                        MAX-ACCESS read-only
                        STATUS current
                        DESCRIPTION
                                "The Subnet Mask prefix length."
                        ::= { fkSubnetEntry 2 }

                
                -- 1.3.6.1.4.1.10428 9 1.101.6.7.1.1.3
                fkSubnetDefaultGateway OBJECT-TYPE
                        SYNTAX IpAddress
                        MAX-ACCESS read-only
                        STATUS current
                        DESCRIPTION
                                "The Gateway IP assigned to SubnetMask."
                        ::= { fkSubnetEntry 3 }

                
                -- 1.3.6.1.4.1.10428 9 1.101.6.7.2
                fkSubnetControl OBJECT IDENTIFIER::= { fkSubnet 2 }

                
                -- 1.3.6.1.4.1.10428 9 1.101.6.7.2.1
                fkSubnetControlRequest OBJECT-TYPE
                        SYNTAX INTEGER
                                {
                                createSubnet(1),
                                destroySubnet(2)
                                }
                        MAX-ACCESS read-write
                        STATUS current
                        DESCRIPTION
                                "The request of a user command."
                        ::= { fkSubnetControl 1 }

                
                -- 1.3.6.1.4.1.10428 9 1.101.6.7.2.2
                fkSubnetControlStatus OBJECT-TYPE
                        SYNTAX FkControlStatusType
                        MAX-ACCESS read-only
                        STATUS current
                        DESCRIPTION
                                "The status of a user command."
                        ::= { fkSubnetControl 2 }

                
                -- 1.3.6.1.4.1.10428 9 1.101.6.7.2.3
                fkSubnetControlTimer OBJECT-TYPE
                        SYNTAX Gauge32
                        MAX-ACCESS read-write
                        STATUS current
                        DESCRIPTION
                                "The maximum wait time for the manager for a long running user command."
                        ::= { fkSubnetControl 3 }

                
                -- 1.3.6.1.4.1.10428 9 1.101.6.7.2.4
                fkSubnetControlTImeStamp OBJECT-TYPE
                        SYNTAX TimeTicks
                        MAX-ACCESS read-only
                        STATUS current
                        DESCRIPTION
                                "The time stamp of the last command (end of command)."
                        ::= { fkSubnetControl 4 }

                
                -- 1.3.6.1.4.1.10428 9 1.101.6.7.2.5
                fkSubnetControlReqResult OBJECT-TYPE
                        SYNTAX FkControlRequestResultType
                        MAX-ACCESS read-only
                        STATUS current
                        DESCRIPTION
                                "The result of the last user command."
                        ::= { fkSubnetControl 5 }

                
                -- 1.3.6.1.4.1.10428 9 1.101.6.7.2.6
                fkSubnetControlPoolIndex OBJECT-TYPE
                        SYNTAX INTEGER (1..255)
                        MAX-ACCESS read-write
                        STATUS current
                        DESCRIPTION
                                "Description."
                        ::= { fkSubnetControl 6 }

                
                -- 1.3.6.1.4.1.10428 9 1.101.6.7.2.7
                fkSubnetControlIp OBJECT-TYPE
                        SYNTAX IpAddress
                        MAX-ACCESS read-write
                        STATUS current
                        DESCRIPTION
                                "Description."
                        ::= { fkSubnetControl 7 }

                
                -- 1.3.6.1.4.1.10428 9 1.101.6.7.2.8
                fkSubnetControlMask OBJECT-TYPE
                        SYNTAX INTEGER (1..32)
                        MAX-ACCESS read-write
                        STATUS current
                        DESCRIPTION
                                "Description."
                        ::= { fkSubnetControl 8 }

                
                -- 1.3.6.1.4.1.10428 9 1.101.6.7.3
                fkSubnetNotification OBJECT IDENTIFIER::= { fkSubnet 3 }

                
                -- 1.3.6.1.4.1.10428 9 1.101.6.7.3.1
                fkSubnetCreated NOTIFICATION-TYPE
                        OBJECTS { fkSubnetMask, fkSubnetControlRequest, fkSubnetControlTImeStamp, fkSubnetControlReqResult }
                        STATUS current
                        DESCRIPTION 
                                "Description."
                        ::= { fkSubnetNotification 1 }

                
                -- 1.3.6.1.4.1.10428 9 1.101.6.7.3.2
                fkSubnetDestroyed NOTIFICATION-TYPE
                        OBJECTS { fkSubnetMask, fkSubnetControlRequest, fkSubnetControlTImeStamp, fkSubnetControlReqResult }
                        STATUS current
                        DESCRIPTION 
                                "Description."
                        ::= { fkSubnetNotification 2 }

                
                -- 1.3.6.1.4.1.10428 9 1.101.6.8
                fkDefaultGateway OBJECT IDENTIFIER::= { fkDhcp 8 }

                
                -- 1.3.6.1.4.1.10428 9 1.101.6.8.1
                fkDefaultGatewayTable OBJECT-TYPE
                        SYNTAX SEQUENCE OF FkDefaultGatewayEntry
                        MAX-ACCESS not-accessible
                        STATUS current
                        DESCRIPTION
                                "Description."
                        ::= { fkDefaultGateway 1 }

                
                -- 1.3.6.1.4.1.10428 9 1.101.6.8.1.1
                fkDefaultGatewayEntry OBJECT-TYPE
                        SYNTAX FkDefaultGatewayEntry
                        MAX-ACCESS not-accessible
                        STATUS current
                        DESCRIPTION
                                "Description."
                        INDEX { fkPoolIndex, fkDefaultGatewayIndex }
                        ::= { fkDefaultGatewayTable 1 }

                
                FkDefaultGatewayEntry ::=
                        SEQUENCE { 
                                fkDefaultGatewayIndex
                                        Integer32,
                                fkDefaultGatewayIp
                                        IpAddress
                         }

                -- 1.3.6.1.4.1.10428 9 1.101.6.8.1.1.1
                fkDefaultGatewayIndex OBJECT-TYPE
                        SYNTAX Integer32 (1..48)
                        MAX-ACCESS read-only
                        STATUS current
                        DESCRIPTION
                                "Description."
                        ::= { fkDefaultGatewayEntry 1 }

                
                -- 1.3.6.1.4.1.10428 9 1.101.6.8.1.1.2
                fkDefaultGatewayIp OBJECT-TYPE
                        SYNTAX IpAddress
                        MAX-ACCESS read-only
                        STATUS current
                        DESCRIPTION
                                "The Gateway IP assigned to leases of the Subnet."
                        ::= { fkDefaultGatewayEntry 2 }

                
                -- 1.3.6.1.4.1.10428 9 1.101.6.8.2
                fkDefaultGatewayControl OBJECT IDENTIFIER::= { fkDefaultGateway 2 }

                
                -- 1.3.6.1.4.1.10428 9 1.101.6.8.2.1
                fkDefaultGatewayControlRequest OBJECT-TYPE
                        SYNTAX INTEGER
                                {
                                createDefaultGateway(1),
                                destroyDefaultGateway(2)
                                }
                        MAX-ACCESS read-write
                        STATUS current
                        DESCRIPTION
                                "The request of a user command."
                        ::= { fkDefaultGatewayControl 1 }

                
                -- 1.3.6.1.4.1.10428 9 1.101.6.8.2.2
                fkDefaultGatewayControlStatus OBJECT-TYPE
                        SYNTAX FkControlStatusType
                        MAX-ACCESS read-only
                        STATUS current
                        DESCRIPTION
                                "The status of a user command."
                        ::= { fkDefaultGatewayControl 2 }

                
                -- 1.3.6.1.4.1.10428 9 1.101.6.8.2.3
                fkDefaultGatewayControlTimer OBJECT-TYPE
                        SYNTAX Gauge32
                        MAX-ACCESS read-write
                        STATUS current
                        DESCRIPTION
                                "The maximum wait time for the manager for a long running user command."
                        ::= { fkDefaultGatewayControl 3 }

                
                -- 1.3.6.1.4.1.10428 9 1.101.6.8.2.4
                fkDefaultGatewayControlTImeStamp OBJECT-TYPE
                        SYNTAX TimeTicks
                        MAX-ACCESS read-only
                        STATUS current
                        DESCRIPTION
                                "The time stamp of the last command (end of command)."
                        ::= { fkDefaultGatewayControl 4 }

                
                -- 1.3.6.1.4.1.10428 9 1.101.6.8.2.5
                fkDefaultGatewayControlReqResult OBJECT-TYPE
                        SYNTAX FkControlRequestResultType
                        MAX-ACCESS read-only
                        STATUS current
                        DESCRIPTION
                                "The result of the last user command."
                        ::= { fkDefaultGatewayControl 5 }

                
                -- 1.3.6.1.4.1.10428 9 1.101.6.8.2.6
                fkDefaultGatewayControlPoolIndex OBJECT-TYPE
                        SYNTAX INTEGER (1..255)
                        MAX-ACCESS read-write
                        STATUS current
                        DESCRIPTION
                                "The Pool name."
                        ::= { fkDefaultGatewayControl 6 }

                
                -- 1.3.6.1.4.1.10428 9 1.101.6.8.2.7
                fkDefaultGatewayControlIndex OBJECT-TYPE
                        SYNTAX Integer32 (1..48)
                        MAX-ACCESS read-write
                        STATUS current
                        DESCRIPTION
                                "Description."
                        ::= { fkDefaultGatewayControl 7 }

                
                -- 1.3.6.1.4.1.10428 9 1.101.6.8.2.8
                fkDefaultGatewayControlIp OBJECT-TYPE
                        SYNTAX IpAddress
                        MAX-ACCESS read-write
                        STATUS current
                        DESCRIPTION
                                "The Gateway IP assigned to Subnet."
                        ::= { fkDefaultGatewayControl 8 }

                
                -- 1.3.6.1.4.1.10428 9 1.101.6.8.3
                fkDefaultGatewayNotification OBJECT IDENTIFIER::= { fkDefaultGateway 3 }

                
                -- 1.3.6.1.4.1.10428 9 1.101.6.8.3.1
                fkDefaultGatewayCreated NOTIFICATION-TYPE
                        OBJECTS { fkDefaultGatewayIp, fkDefaultGatewayControlRequest, fkDefaultGatewayControlTImeStamp, fkDefaultGatewayControlReqResult }
                        STATUS current
                        DESCRIPTION 
                                "Description."
                        ::= { fkDefaultGatewayNotification 1 }

                
                -- 1.3.6.1.4.1.10428 9 1.101.6.8.3.2
                fkDefaultGatewayDestroyed NOTIFICATION-TYPE
                        OBJECTS { fkDefaultGatewayIndex, fkDefaultGatewayControlRequest, fkDefaultGatewayControlTImeStamp, fkDefaultGatewayControlReqResult }
                        STATUS current
                        DESCRIPTION 
                                "The fkDefaultGatewayIp is 0.0.0.0 for CLI 
                                'no default-gateway all'"
                        ::= { fkDefaultGatewayNotification 2 }

                
                -- 1.3.6.1.4.1.10428 9 1.101.6.9
                fkRange OBJECT IDENTIFIER::= { fkDhcp 9 }

                
                -- 1.3.6.1.4.1.10428 9 1.101.6.9.1
                fkRangeTable OBJECT-TYPE
                        SYNTAX SEQUENCE OF FkRangeEntry
                        MAX-ACCESS not-accessible
                        STATUS current
                        DESCRIPTION
                                "Description."
                        ::= { fkRange 1 }

                
                -- 1.3.6.1.4.1.10428 9 1.101.6.9.1.1
                fkRangeEntry OBJECT-TYPE
                        SYNTAX FkRangeEntry
                        MAX-ACCESS not-accessible
                        STATUS current
                        DESCRIPTION
                                "Description."
                        INDEX { fkPoolIndex, fkRangeStart, fkRangeEnd }
                        ::= { fkRangeTable 1 }

                
                FkRangeEntry ::=
                        SEQUENCE { 
                                fkRangeStart
                                        IpAddress,
                                fkRangeEnd
                                        IpAddress,
                                fkRangeSubnetIP
                                        IpAddress,
                                fkRangeSubnetMask
                                        INTEGER
                         }

                -- 1.3.6.1.4.1.10428 9 1.101.6.9.1.1.1
                fkRangeStart OBJECT-TYPE
                        SYNTAX IpAddress
                        MAX-ACCESS read-only
                        STATUS current
                        DESCRIPTION
                                "The start IP of subnet's range."
                        ::= { fkRangeEntry 1 }

                
                -- 1.3.6.1.4.1.10428 9 1.101.6.9.1.1.2
                fkRangeEnd OBJECT-TYPE
                        SYNTAX IpAddress
                        MAX-ACCESS read-only
                        STATUS current
                        DESCRIPTION
                                "The end IP of subnet's range."
                        ::= { fkRangeEntry 2 }

                
                -- 1.3.6.1.4.1.10428 9 1.101.6.9.1.1.3
                fkRangeSubnetIP OBJECT-TYPE
                        SYNTAX IpAddress
                        MAX-ACCESS read-only
                        STATUS current
                        DESCRIPTION
                                "The IP Address of the parent Subnet that the static Lease belongs to."
                        ::= { fkRangeEntry 3 }

                
                -- 1.3.6.1.4.1.10428 9 1.101.6.9.1.1.4
                fkRangeSubnetMask OBJECT-TYPE
                        SYNTAX INTEGER (1..32)
                        MAX-ACCESS read-only
                        STATUS current
                        DESCRIPTION
                                "The Mask prefix length of the parent Subnet that the range belongs to."
                        ::= { fkRangeEntry 4 }

                
                -- 1.3.6.1.4.1.10428 9 1.101.6.9.2
                fkRangeControl OBJECT IDENTIFIER::= { fkRange 2 }

                
                -- 1.3.6.1.4.1.10428 9 1.101.6.9.2.1
                fkRangeControlRequest OBJECT-TYPE
                        SYNTAX INTEGER
                                {
                                createRange(1),
                                destroyRange(2)
                                }
                        MAX-ACCESS read-write
                        STATUS current
                        DESCRIPTION
                                "The request of a user command."
                        ::= { fkRangeControl 1 }

                
                -- 1.3.6.1.4.1.10428 9 1.101.6.9.2.2
                fkRangeControlStatus OBJECT-TYPE
                        SYNTAX FkControlStatusType
                        MAX-ACCESS read-only
                        STATUS current
                        DESCRIPTION
                                "The status of a user command."
                        ::= { fkRangeControl 2 }

                
                -- 1.3.6.1.4.1.10428 9 1.101.6.9.2.3
                fkRangeControlTimer OBJECT-TYPE
                        SYNTAX Gauge32
                        MAX-ACCESS read-write
                        STATUS current
                        DESCRIPTION
                                "The maximum wait time for the manager for a long running user command."
                        ::= { fkRangeControl 3 }

                
                -- 1.3.6.1.4.1.10428 9 1.101.6.9.2.4
                fkRangeControlTImeStamp OBJECT-TYPE
                        SYNTAX TimeTicks
                        MAX-ACCESS read-only
                        STATUS current
                        DESCRIPTION
                                "The time stamp of the last command (end of command)."
                        ::= { fkRangeControl 4 }

                
                -- 1.3.6.1.4.1.10428 9 1.101.6.9.2.5
                fkRangeControlReqResult OBJECT-TYPE
                        SYNTAX FkControlRequestResultType
                        MAX-ACCESS read-only
                        STATUS current
                        DESCRIPTION
                                "The result of the last user command."
                        ::= { fkRangeControl 5 }

                
                -- 1.3.6.1.4.1.10428 9 1.101.6.9.2.6
                fkRangeControlPoolIndex OBJECT-TYPE
                        SYNTAX INTEGER (1..255)
                        MAX-ACCESS read-write
                        STATUS current
                        DESCRIPTION
                                "Description."
                        ::= { fkRangeControl 6 }

                
                -- 1.3.6.1.4.1.10428 9 1.101.6.9.2.7
                fkRangeControlStart OBJECT-TYPE
                        SYNTAX IpAddress
                        MAX-ACCESS read-write
                        STATUS current
                        DESCRIPTION
                                "Description."
                        ::= { fkRangeControl 7 }

                
                -- 1.3.6.1.4.1.10428 9 1.101.6.9.2.8
                fkRangeControlEnd OBJECT-TYPE
                        SYNTAX IpAddress
                        MAX-ACCESS read-write
                        STATUS current
                        DESCRIPTION
                                "Description."
                        ::= { fkRangeControl 8 }

                
                -- 1.3.6.1.4.1.10428 9 1.101.6.9.3
                fkRangeNotification OBJECT IDENTIFIER::= { fkRange 3 }

                
                -- 1.3.6.1.4.1.10428 9 1.101.6.9.3.1
                fkRangeCreated NOTIFICATION-TYPE
                        OBJECTS { fkRangeSubnetIP, fkRangeSubnetMask, fkRangeControlRequest, fkRangeControlTImeStamp, fkRangeControlReqResult
                                 }
                        STATUS current
                        DESCRIPTION 
                                "Description."
                        ::= { fkRangeNotification 1 }

                
                -- 1.3.6.1.4.1.10428 9 1.101.6.9.3.2
                fkRangeDestroyed NOTIFICATION-TYPE
                        OBJECTS { fkRangeEnd, fkRangeControlRequest, fkRangeControlTImeStamp, fkRangeControlReqResult }
                        STATUS current
                        DESCRIPTION 
                                "Description."
                        ::= { fkRangeNotification 2 }

                
                -- 1.3.6.1.4.1.10428 9 1.101.6.10
                fkFixed OBJECT IDENTIFIER::= { fkDhcp 10 }

                
                -- 1.3.6.1.4.1.10428 9 1.101.6.10.1
                fkFixedTable OBJECT-TYPE
                        SYNTAX SEQUENCE OF FkFixedEntry
                        MAX-ACCESS not-accessible
                        STATUS current
                        DESCRIPTION
                                "Description."
                        ::= { fkFixed 1 }

                
                -- 1.3.6.1.4.1.10428 9 1.101.6.10.1.1
                fkFixedEntry OBJECT-TYPE
                        SYNTAX FkFixedEntry
                        MAX-ACCESS not-accessible
                        STATUS current
                        DESCRIPTION
                                "Description."
                        INDEX { fkPoolIndex, fkFixedIp, fkFixedMac }
                        ::= { fkFixedTable 1 }

                
                FkFixedEntry ::=
                        SEQUENCE { 
                                fkFixedIp
                                        IpAddress,
                                fkFixedMac
                                        MacAddress
                         }

                -- 1.3.6.1.4.1.10428 9 1.101.6.10.1.1.1
                fkFixedIp OBJECT-TYPE
                        SYNTAX IpAddress
                        MAX-ACCESS read-only
                        STATUS current
                        DESCRIPTION
                                "The IP address for the fixed Lease."
                        ::= { fkFixedEntry 1 }

                
                -- 1.3.6.1.4.1.10428 9 1.101.6.10.1.1.2
                fkFixedMac OBJECT-TYPE
                        SYNTAX MacAddress
                        MAX-ACCESS read-only
                        STATUS current
                        DESCRIPTION
                                "The MAC address for the fixed Lease."
                        ::= { fkFixedEntry 2 }

                
                -- 1.3.6.1.4.1.10428 9 1.101.6.10.2
                fkFixedControl OBJECT IDENTIFIER::= { fkFixed 2 }

                
                -- 1.3.6.1.4.1.10428 9 1.101.6.10.2.1
                fkFixedControlRequest OBJECT-TYPE
                        SYNTAX INTEGER
                                {
                                createFixed(1),
                                destroyFixed(2)
                                }
                        MAX-ACCESS read-write
                        STATUS current
                        DESCRIPTION
                                "The request of a user command."
                        ::= { fkFixedControl 1 }

                
                -- 1.3.6.1.4.1.10428 9 1.101.6.10.2.2
                fkFixedControlStatus OBJECT-TYPE
                        SYNTAX FkControlStatusType
                        MAX-ACCESS read-only
                        STATUS current
                        DESCRIPTION
                                "The status of a user command."
                        ::= { fkFixedControl 2 }

                
                -- 1.3.6.1.4.1.10428 9 1.101.6.10.2.3
                fkFixedControlTimer OBJECT-TYPE
                        SYNTAX Gauge32
                        MAX-ACCESS read-write
                        STATUS current
                        DESCRIPTION
                                "The maximum wait time for the manager for a long running user command."
                        ::= { fkFixedControl 3 }

                
                -- 1.3.6.1.4.1.10428 9 1.101.6.10.2.4
                fkFixedControlTImeStamp OBJECT-TYPE
                        SYNTAX TimeTicks
                        MAX-ACCESS read-only
                        STATUS current
                        DESCRIPTION
                                "The time stamp of the last command (end of command)."
                        ::= { fkFixedControl 4 }

                
                -- 1.3.6.1.4.1.10428 9 1.101.6.10.2.5
                fkFixedControlReqResult OBJECT-TYPE
                        SYNTAX FkControlRequestResultType
                        MAX-ACCESS read-only
                        STATUS current
                        DESCRIPTION
                                "The result of the last user command."
                        ::= { fkFixedControl 5 }

                
                -- 1.3.6.1.4.1.10428 9 1.101.6.10.2.6
                fkFixedControlPoolIndex OBJECT-TYPE
                        SYNTAX INTEGER (1..255)
                        MAX-ACCESS read-write
                        STATUS current
                        DESCRIPTION
                                "Description."
                        ::= { fkFixedControl 6 }

                
                -- 1.3.6.1.4.1.10428 9 1.101.6.10.2.7
                fkFixedControlIp OBJECT-TYPE
                        SYNTAX IpAddress
                        MAX-ACCESS read-write
                        STATUS current
                        DESCRIPTION
                                "Description."
                        ::= { fkFixedControl 7 }

                
                -- 1.3.6.1.4.1.10428 9 1.101.6.10.2.8
                fkFixedControlMac OBJECT-TYPE
                        SYNTAX MacAddress
                        MAX-ACCESS read-write
                        STATUS current
                        DESCRIPTION
                                "Description."
                        ::= { fkFixedControl 8 }

                
                -- 1.3.6.1.4.1.10428 9 1.101.6.10.3
                fkFixedNotification OBJECT IDENTIFIER::= { fkFixed 3 }

                
                -- 1.3.6.1.4.1.10428 9 1.101.6.10.3.1
                fkFixedCreated NOTIFICATION-TYPE
                        OBJECTS { fkFixedMac, fkFixedControlRequest, fkFixedControlTImeStamp, fkFixedControlReqResult }
                        STATUS current
                        DESCRIPTION 
                                "Description."
                        ::= { fkFixedNotification 1 }

                
                -- 1.3.6.1.4.1.10428 9 1.101.6.10.3.2
                fkFixedDestroyed NOTIFICATION-TYPE
                        OBJECTS { fkFixedMac, fkFixedControlRequest, fkFixedControlTImeStamp, fkFixedControlReqResult }
                        STATUS current
                        DESCRIPTION 
                                "Description."
                        ::= { fkFixedNotification 2 }

                
                -- 1.3.6.1.4.1.10428 9 1.101.6.11
                fkOption82 OBJECT IDENTIFIER::= { fkDhcp 11 }

                
                -- 1.3.6.1.4.1.10428 9 1.101.6.11.1
                fkOption82Table OBJECT-TYPE
                        SYNTAX SEQUENCE OF FkOption82Entry
                        MAX-ACCESS not-accessible
                        STATUS current
                        DESCRIPTION
                                "Description."
                        ::= { fkOption82 1 }

                
                -- 1.3.6.1.4.1.10428 9 1.101.6.11.1.1
                fkOption82Entry OBJECT-TYPE
                        SYNTAX FkOption82Entry
                        MAX-ACCESS not-accessible
                        STATUS current
                        DESCRIPTION
                                "Description."
                        INDEX { fkOption82RemoteType, fkOption82RemoteId, fkOption82CircuitType, fkOption82CircuitId }
                        ::= { fkOption82Table 1 }

                
                FkOption82Entry ::=
                        SEQUENCE { 
                                fkOption82RemoteType
                                        INTEGER,
                                fkOption82RemoteId
                                        OCTET STRING,
                                fkOption82CircuitType
                                        INTEGER,
                                fkOption82CircuitId
                                        OCTET STRING,
                                fkOption82Limit
                                        INTEGER,
                                fkOption82PoolName
                                        OCTET STRING
                         }

                -- 1.3.6.1.4.1.10428 9 1.101.6.11.1.1.1
                fkOption82RemoteType OBJECT-TYPE
                        SYNTAX INTEGER
                                {
                                ipaddress(1),
                                binary(2),
                                text(3)
                                }
                        MAX-ACCESS read-only
                        STATUS current
                        DESCRIPTION
                                "Value type of fkOption82RemoteId
                                ipaddress : denotes such as 'A.B.C.D'.
                                binary : denotes such as '89:AB:CD:EF:01:02'.
                                text : denotes such as 'TextString'."
                        ::= { fkOption82Entry 1 }

                
                -- 1.3.6.1.4.1.10428 9 1.101.6.11.1.1.2
                fkOption82RemoteId OBJECT-TYPE
                        SYNTAX OCTET STRING (SIZE (1..48))
                        MAX-ACCESS read-only
                        STATUS current
                        DESCRIPTION
                                "The remote id for the Option82 Lease limit."
                        ::= { fkOption82Entry 2 }

                
                -- 1.3.6.1.4.1.10428 9 1.101.6.11.1.1.3
                fkOption82CircuitType OBJECT-TYPE
                        SYNTAX INTEGER
                                {
                                invalid(0),
                                index(1),
                                binary(2),
                                text(3)
                                }
                        MAX-ACCESS read-only
                        STATUS current
                        DESCRIPTION
                                "Value type of fkOption82CircuitId
                                invalid : The fkOption82CircuitId is invalid.
                                index : This string denotes value in the range (0..65535).
                                binary : denotes such as '89:AB:CD:EF:01:02'.
                                text : denotes such as 'TextString'.
                                "
                        ::= { fkOption82Entry 3 }

                
                -- 1.3.6.1.4.1.10428 9 1.101.6.11.1.1.4
                fkOption82CircuitId OBJECT-TYPE
                        SYNTAX OCTET STRING (SIZE (0..48))
                        MAX-ACCESS read-only
                        STATUS current
                        DESCRIPTION
                                "The circuit id for the Option82 Lease limit."
                        ::= { fkOption82Entry 4 }

                
                -- 1.3.6.1.4.1.10428 9 1.101.6.11.1.1.5
                fkOption82Limit OBJECT-TYPE
                        SYNTAX INTEGER (-1..2147483637)
                        MAX-ACCESS read-only
                        STATUS current
                        DESCRIPTION
                                "The Option82 Lease limit count for the remote system and the corresponding port.
                                -1 : default value(un set value)
                                0-2147483637 : set value"
                        ::= { fkOption82Entry 5 }

                
                -- 1.3.6.1.4.1.10428 9 1.101.6.11.1.1.6
                fkOption82PoolName OBJECT-TYPE
                        SYNTAX OCTET STRING
                        MAX-ACCESS read-only
                        STATUS current
                        DESCRIPTION
                                "The Pool Name.
                                NULL: unset value"
                        ::= { fkOption82Entry 6 }

                
                -- 1.3.6.1.4.1.10428 9 1.101.6.11.2
                fkOption82Control OBJECT IDENTIFIER::= { fkOption82 2 }

                
                -- 1.3.6.1.4.1.10428 9 1.101.6.11.2.1
                fkOption82ControlRequest OBJECT-TYPE
                        SYNTAX INTEGER
                                {
                                createOption82(1),
                                destroyOption82(2),
                                setOption82Profile(3)
                                }
                        MAX-ACCESS read-write
                        STATUS current
                        DESCRIPTION
                                "The request of a user command."
                        ::= { fkOption82Control 1 }

                
                -- 1.3.6.1.4.1.10428 9 1.101.6.11.2.2
                fkOption82ControlStatus OBJECT-TYPE
                        SYNTAX FkControlStatusType
                        MAX-ACCESS read-only
                        STATUS current
                        DESCRIPTION
                                "The status of a user command."
                        ::= { fkOption82Control 2 }

                
                -- 1.3.6.1.4.1.10428 9 1.101.6.11.2.3
                fkOption82ControlTimer OBJECT-TYPE
                        SYNTAX Gauge32
                        MAX-ACCESS read-write
                        STATUS current
                        DESCRIPTION
                                "The maximum wait time for the manager for a long running user command."
                        ::= { fkOption82Control 3 }

                
                -- 1.3.6.1.4.1.10428 9 1.101.6.11.2.4
                fkOption82ControlTImeStamp OBJECT-TYPE
                        SYNTAX TimeTicks
                        MAX-ACCESS read-only
                        STATUS current
                        DESCRIPTION
                                "The time stamp of the last command (end of command)."
                        ::= { fkOption82Control 4 }

                
                -- 1.3.6.1.4.1.10428 9 1.101.6.11.2.5
                fkOption82ControlReqResult OBJECT-TYPE
                        SYNTAX FkControlRequestResultType
                        MAX-ACCESS read-only
                        STATUS current
                        DESCRIPTION
                                "The result of the last user command."
                        ::= { fkOption82Control 5 }

                
                -- 1.3.6.1.4.1.10428 9 1.101.6.11.2.6
                fkOption82ControlRemoteType OBJECT-TYPE
                        SYNTAX INTEGER
                                {
                                ipaddress(1),
                                binary(2),
                                text(3)
                                }
                        MAX-ACCESS read-write
                        STATUS current
                        DESCRIPTION
                                "The Value Type of fkOption82ControlRemoteId
                                ipaddress : denotes such as 'A.B.C.D'.
                                binary : denotes such as '89:AB:CD:EF:01:02'.
                                text : denotes such as 'TextString'."
                        ::= { fkOption82Control 6 }

                
                -- 1.3.6.1.4.1.10428 9 1.101.6.11.2.7
                fkOption82ControlRemoteId OBJECT-TYPE
                        SYNTAX OCTET STRING (SIZE (1..48))
                        MAX-ACCESS read-write
                        STATUS current
                        DESCRIPTION
                                "Description."
                        ::= { fkOption82Control 7 }

                
                -- 1.3.6.1.4.1.10428 9 1.101.6.11.2.8
                fkOption82ControlCircuitType OBJECT-TYPE
                        SYNTAX INTEGER
                                {
                                invalid(0),
                                index(1),
                                binary(2),
                                text(3)
                                }
                        MAX-ACCESS read-write
                        STATUS current
                        DESCRIPTION
                                "The Value Type of fkOption82ControlCircuitId
                                invalid : The fkOption82ControlCircuitId is invalid.
                                index : This string denotes value in the range (0..65535).
                                binary : it denotes such as '89:AB:CD:EF:01:02'.
                                text : it denotes such as 'TextString'.
                                "
                        ::= { fkOption82Control 8 }

                
                -- 1.3.6.1.4.1.10428 9 1.101.6.11.2.9
                fkOption82ControlCircuitId OBJECT-TYPE
                        SYNTAX OCTET STRING (SIZE (0..48))
                        MAX-ACCESS read-write
                        STATUS current
                        DESCRIPTION
                                "Description."
                        ::= { fkOption82Control 9 }

                
                -- 1.3.6.1.4.1.10428 9 1.101.6.11.2.10
                fkOption82ControlLimit OBJECT-TYPE
                        SYNTAX INTEGER (-2..2147483637)
                        MAX-ACCESS read-write
                        STATUS current
                        DESCRIPTION
                                "-2 : invalid value.
                                -1 : default value(clear value).
                                0-2147483637 : set value"
                        ::= { fkOption82Control 10 }

                
                -- 1.3.6.1.4.1.10428 9 1.101.6.11.2.11
                fkOption82ControlPoolName OBJECT-TYPE
                        SYNTAX OCTET STRING
                        MAX-ACCESS read-write
                        STATUS current
                        DESCRIPTION
                                "The Pool Name.
                                NULL: default default value (clear)
                                {0xff, 0x00}: default value (clear)
                                {0xfe, 0x00}: not avaliable
                                "
                        ::= { fkOption82Control 11 }

                
                -- 1.3.6.1.4.1.10428 9 1.101.6.11.3
                fkOption82Notification OBJECT IDENTIFIER::= { fkOption82 3 }

                
                -- 1.3.6.1.4.1.10428 9 1.101.6.11.3.1
                fkOption82Created NOTIFICATION-TYPE
                        OBJECTS { fkOption82ControlRequest, fkOption82ControlTImeStamp, fkOption82ControlReqResult, fkOption82ControlLimit, fkOption82ControlPoolName
                                 }
                        STATUS current
                        DESCRIPTION 
                                "Description."
                        ::= { fkOption82Notification 1 }

                
                -- 1.3.6.1.4.1.10428 9 1.101.6.11.3.2
                fkOption82Destroyed NOTIFICATION-TYPE
                        OBJECTS { fkOption82ControlRequest, fkOption82ControlTImeStamp, fkOption82ControlReqResult, fkOption82ControlCircuitId }
                        STATUS current
                        DESCRIPTION 
                                "Description."
                        ::= { fkOption82Notification 2 }

                
                -- 1.3.6.1.4.1.10428 9 1.101.6.11.3.3
                fkOption82ProfileChanged NOTIFICATION-TYPE
                        OBJECTS { fkOption82ControlRequest, fkOption82ControlTImeStamp, fkOption82ControlReqResult, fkOption82ControlLimit, fkOption82ControlPoolName
                                 }
                        STATUS current
                        DESCRIPTION 
                                "Description."
                        ::= { fkOption82Notification 3 }

                
                -- 1.3.6.1.4.1.10428 9 1.101.6.12
                fkOption82System OBJECT IDENTIFIER::= { fkDhcp 12 }

                
                -- 1.3.6.1.4.1.10428 9 1.101.6.12.1
                fkOption82SystemTable OBJECT-TYPE
                        SYNTAX SEQUENCE OF FkOption82SystemEntry
                        MAX-ACCESS not-accessible
                        STATUS current
                        DESCRIPTION
                                "Description."
                        ::= { fkOption82System 1 }

                
                -- 1.3.6.1.4.1.10428 9 1.101.6.12.1.1
                fkOption82SystemEntry OBJECT-TYPE
                        SYNTAX FkOption82SystemEntry
                        MAX-ACCESS not-accessible
                        STATUS current
                        DESCRIPTION
                                "Description."
                        INDEX { fkOption82SystemIndex }
                        ::= { fkOption82SystemTable 1 }

                
                FkOption82SystemEntry ::=
                        SEQUENCE { 
                                fkOption82SystemIndex
                                        InterfaceIndex,
                                fkOption82SystemCtype
                                        INTEGER,
                                fkOption82SystemCid
                                        OCTET STRING
                         }

                -- 1.3.6.1.4.1.10428 9 1.101.6.12.1.1.1
                fkOption82SystemIndex OBJECT-TYPE
                        SYNTAX InterfaceIndex
                        MAX-ACCESS read-only
                        STATUS current
                        DESCRIPTION
                                "PortIndex"
                        ::= { fkOption82SystemEntry 1 }

                
                -- 1.3.6.1.4.1.10428 9 1.101.6.12.1.1.2
                fkOption82SystemCtype OBJECT-TYPE
                        SYNTAX INTEGER
                                {
                                invalid(0),
                                index(1),
                                binary(2),
                                text(3)
                                }
                        MAX-ACCESS read-only
                        STATUS current
                        DESCRIPTION
                                "Value type of fkOption82SystemCid.
                                invalid : The fkOption82SystemCid is invalid.
                                index : This string denotes value in the range (0..65535).
                                binary : it denotes such as '89:AB:CD:EF:01:02'.
                                text : it denotes such as 'TextString'.
                                "
                        ::= { fkOption82SystemEntry 2 }

                
                -- 1.3.6.1.4.1.10428 9 1.101.6.12.1.1.3
                fkOption82SystemCid OBJECT-TYPE
                        SYNTAX OCTET STRING (SIZE (0..63))
                        MAX-ACCESS read-only
                        STATUS current
                        DESCRIPTION
                                "The circuit id for the Option82 Lease limit.
                                If Null, it is not set."
                        ::= { fkOption82SystemEntry 3 }

                
                -- 1.3.6.1.4.1.10428 9 1.101.6.12.2
                fkOption82SystemControl OBJECT IDENTIFIER::= { fkOption82System 2 }

                
                -- 1.3.6.1.4.1.10428 9 1.101.6.12.2.1
                fkOption82SystemControlRequest OBJECT-TYPE
                        SYNTAX INTEGER { setOption82SystemCircuit(1) }
                        MAX-ACCESS read-write
                        STATUS current
                        DESCRIPTION
                                "The request of a user command."
                        ::= { fkOption82SystemControl 1 }

                
                -- 1.3.6.1.4.1.10428 9 1.101.6.12.2.2
                fkOption82SystemControlStatus OBJECT-TYPE
                        SYNTAX FkControlStatusType
                        MAX-ACCESS read-only
                        STATUS current
                        DESCRIPTION
                                "The status of a user command."
                        ::= { fkOption82SystemControl 2 }

                
                -- 1.3.6.1.4.1.10428 9 1.101.6.12.2.3
                fkOption82SystemControlTimer OBJECT-TYPE
                        SYNTAX Gauge32
                        MAX-ACCESS read-write
                        STATUS current
                        DESCRIPTION
                                "The maximum wait time for the manager for a long running user command."
                        ::= { fkOption82SystemControl 3 }

                
                -- 1.3.6.1.4.1.10428 9 1.101.6.12.2.4
                fkOption82SystemControlTImeStamp OBJECT-TYPE
                        SYNTAX TimeTicks
                        MAX-ACCESS read-only
                        STATUS current
                        DESCRIPTION
                                "The time stamp of the last command (end of command)."
                        ::= { fkOption82SystemControl 4 }

                
                -- 1.3.6.1.4.1.10428 9 1.101.6.12.2.5
                fkOption82SystemControlReqResult OBJECT-TYPE
                        SYNTAX FkControlRequestResultType
                        MAX-ACCESS read-only
                        STATUS current
                        DESCRIPTION
                                "The result of the last user command."
                        ::= { fkOption82SystemControl 5 }

                
                -- 1.3.6.1.4.1.10428 9 1.101.6.12.2.6
                fkOption82SystemControlIndex OBJECT-TYPE
                        SYNTAX INTEGER (1..255)
                        MAX-ACCESS read-write
                        STATUS current
                        DESCRIPTION
                                "InterfaceIndex"
                        ::= { fkOption82SystemControl 6 }

                
                -- 1.3.6.1.4.1.10428 9 1.101.6.12.2.7
                fkOption82SystemControlCtype OBJECT-TYPE
                        SYNTAX INTEGER
                                {
                                invalid(0),
                                index(1),
                                binary(2),
                                text(3)
                                }
                        MAX-ACCESS read-write
                        STATUS current
                        DESCRIPTION
                                "Value type of fkOption82SystemControlCid.
                                invalid : The fkOption82SystemControlCid is invalid.
                                          In this case, it is cleared.
                                index : This string denotes value in the range (0..65535).
                                binary : it denotes such as '89:AB:CD:EF:01:02'.
                                text : it denotes such as 'TextString'.
                                "
                        ::= { fkOption82SystemControl 7 }

                
                -- 1.3.6.1.4.1.10428 9 1.101.6.12.2.8
                fkOption82SystemControlCid OBJECT-TYPE
                        SYNTAX OCTET STRING (SIZE (0..63))
                        MAX-ACCESS read-write
                        STATUS current
                        DESCRIPTION
                                "The circuit id of the port for the Option82.
                                "
                        ::= { fkOption82SystemControl 8 }

                
                -- 1.3.6.1.4.1.10428 9 1.101.6.12.3
                fkOption82CircuitNotification OBJECT IDENTIFIER::= { fkOption82System 3 }

                
                -- 1.3.6.1.4.1.10428 9 1.101.6.12.3.1
                setOption82SystemCircuit NOTIFICATION-TYPE
                        OBJECTS { fkOption82SystemControlRequest, fkOption82SystemControlTImeStamp, fkOption82SystemControlReqResult, fkOption82SystemControlCtype, fkOption82SystemControlCid
                                 }
                        STATUS current
                        DESCRIPTION 
                                "Description."
                        ::= { fkOption82CircuitNotification 1 }

                
                -- 1.3.6.1.4.1.10428 9 1.101.6.13
                fkIllegal OBJECT IDENTIFIER::= { fkDhcp 13 }

                
                -- 1.3.6.1.4.1.10428 9 1.101.6.13.1
                fkIllegalTable OBJECT-TYPE
                        SYNTAX SEQUENCE OF FkIllegalEntry
                        MAX-ACCESS not-accessible
                        STATUS current
                        DESCRIPTION
                                "Description."
                        ::= { fkIllegal 1 }

                
                -- 1.3.6.1.4.1.10428 9 1.101.6.13.1.1
                fkIllegalEntry OBJECT-TYPE
                        SYNTAX FkIllegalEntry
                        MAX-ACCESS not-accessible
                        STATUS current
                        DESCRIPTION
                                "Description."
                        INDEX { fkIllegalIp, fkIllegalMac }
                        ::= { fkIllegalTable 1 }

                
                FkIllegalEntry ::=
                        SEQUENCE { 
                                fkIllegalIp
                                        IpAddress,
                                fkIllegalMac
                                        MacAddress,
                                fkIllegalTime
                                        OCTET STRING
                         }

                -- 1.3.6.1.4.1.10428 9 1.101.6.13.1.1.1
                fkIllegalIp OBJECT-TYPE
                        SYNTAX IpAddress
                        MAX-ACCESS read-only
                        STATUS current
                        DESCRIPTION
                                "The illegal IP address."
                        ::= { fkIllegalEntry 1 }

                
                -- 1.3.6.1.4.1.10428 9 1.101.6.13.1.1.2
                fkIllegalMac OBJECT-TYPE
                        SYNTAX MacAddress
                        MAX-ACCESS read-only
                        STATUS current
                        DESCRIPTION
                                "The MAC Address of this illegal address."
                        ::= { fkIllegalEntry 2 }

                
                -- 1.3.6.1.4.1.10428 9 1.101.6.13.1.1.3
                fkIllegalTime OBJECT-TYPE
                        SYNTAX OCTET STRING
                        MAX-ACCESS read-only
                        STATUS current
                        DESCRIPTION
                                "The Time that the illegal Ip was found.
                                It denotes such as '2004/12/20 10:20:30'"
                        ::= { fkIllegalEntry 3 }

                
                -- 1.3.6.1.4.1.10428 9 1.101.6.13.2
                fkIllegalControl OBJECT IDENTIFIER::= { fkIllegal 2 }

                
                -- 1.3.6.1.4.1.10428 9 1.101.6.13.2.1
                fkIllegalControlRequest OBJECT-TYPE
                        SYNTAX INTEGER { clearIllegal(1) }
                        MAX-ACCESS read-write
                        STATUS current
                        DESCRIPTION
                                "The request of a user command."
                        ::= { fkIllegalControl 1 }

                
                -- 1.3.6.1.4.1.10428 9 1.101.6.13.2.2
                fkIllegalControlStatus OBJECT-TYPE
                        SYNTAX FkControlStatusType
                        MAX-ACCESS read-only
                        STATUS current
                        DESCRIPTION
                                "The status of a user command."
                        ::= { fkIllegalControl 2 }

                
                -- 1.3.6.1.4.1.10428 9 1.101.6.13.2.3
                fkIllegalControlTimer OBJECT-TYPE
                        SYNTAX Gauge32
                        MAX-ACCESS read-write
                        STATUS current
                        DESCRIPTION
                                "The maximum wait time for the manager for a long running user command."
                        ::= { fkIllegalControl 3 }

                
                -- 1.3.6.1.4.1.10428 9 1.101.6.13.2.4
                fkIllegalControlTImeStamp OBJECT-TYPE
                        SYNTAX TimeTicks
                        MAX-ACCESS read-only
                        STATUS current
                        DESCRIPTION
                                "The time stamp of the last command (end of command)."
                        ::= { fkIllegalControl 4 }

                
                -- 1.3.6.1.4.1.10428 9 1.101.6.13.2.5
                fkIllegalControlReqResult OBJECT-TYPE
                        SYNTAX FkControlRequestResultType
                        MAX-ACCESS read-only
                        STATUS current
                        DESCRIPTION
                                "The result of the last user command."
                        ::= { fkIllegalControl 5 }

                
                -- 1.3.6.1.4.1.10428 9 1.101.6.13.3
                fkIllegalNotification OBJECT IDENTIFIER::= { fkIllegal 3 }

                
                -- 1.3.6.1.4.1.10428 9 1.101.6.13.3.1
                fkIllegalCleared NOTIFICATION-TYPE
                        OBJECTS { fkIllegalControlRequest, fkIllegalControlTImeStamp, fkIllegalControlReqResult }
                        STATUS current
                        DESCRIPTION 
                                "Description."
                        ::= { fkIllegalNotification 1 }

                
                -- 1.3.6.1.4.1.10428 9 1.101.6.14
                fkLeased OBJECT IDENTIFIER::= { fkDhcp 14 }

                
                -- 1.3.6.1.4.1.10428 9 1.101.6.14.1
                fkLeasedTable OBJECT-TYPE
                        SYNTAX SEQUENCE OF FkLeasedEntry
                        MAX-ACCESS not-accessible
                        STATUS current
                        DESCRIPTION
                                "Description."
                        ::= { fkLeased 1 }

                
                -- 1.3.6.1.4.1.10428 9 1.101.6.14.1.1
                fkLeasedEntry OBJECT-TYPE
                        SYNTAX FkLeasedEntry
                        MAX-ACCESS not-accessible
                        STATUS current
                        DESCRIPTION
                                "Description."
                        INDEX { fkLeasedIp }
                        ::= { fkLeasedTable 1 }

                
                FkLeasedEntry ::=
                        SEQUENCE { 
                                fkLeasedIp
                                        IpAddress,
                                fkLeasedPoolIndex
                                        INTEGER,
                                fkLeasedPoolName
                                        OCTET STRING,
                                fkLeasedTime
                                        OCTET STRING,
                                fkLeasedHwaddr
                                        OCTET STRING,
                                fkLeasedHostname
                                        OCTET STRING,
                                fkLeasedUid
                                        OCTET STRING,
                                fkLeasedRid
                                        OCTET STRING,
                                fkLeasedCid
                                        OCTET STRING
                         }

                -- 1.3.6.1.4.1.10428 9 1.101.6.14.1.1.1
                fkLeasedIp OBJECT-TYPE
                        SYNTAX IpAddress
                        MAX-ACCESS read-only
                        STATUS current
                        DESCRIPTION
                                "The leased IP address."
                        ::= { fkLeasedEntry 1 }

                
                -- 1.3.6.1.4.1.10428 9 1.101.6.14.1.1.2
                fkLeasedPoolIndex OBJECT-TYPE
                        SYNTAX INTEGER (1..255)
                        MAX-ACCESS read-write
                        STATUS current
                        DESCRIPTION
                                "The Pool Index."
                        ::= { fkLeasedEntry 2 }

                
                -- 1.3.6.1.4.1.10428 9 1.101.6.14.1.1.3
                fkLeasedPoolName OBJECT-TYPE
                        SYNTAX OCTET STRING
                        MAX-ACCESS read-only
                        STATUS current
                        DESCRIPTION
                                "The Pool name."
                        ::= { fkLeasedEntry 3 }

                
                -- 1.3.6.1.4.1.10428 9 1.101.6.14.1.1.4
                fkLeasedTime OBJECT-TYPE
                        SYNTAX OCTET STRING
                        MAX-ACCESS read-only
                        STATUS current
                        DESCRIPTION
                                "The Lease's TimeStamp.
                                It denotes such as '2004/12/20 10:20:30 - 2004/12/22 10:24:32'."
                        ::= { fkLeasedEntry 4 }

                
                -- 1.3.6.1.4.1.10428 9 1.101.6.14.1.1.5
                fkLeasedHwaddr OBJECT-TYPE
                        SYNTAX OCTET STRING
                        MAX-ACCESS read-only
                        STATUS current
                        DESCRIPTION
                                "The Hardware Address of the allocated Lease."
                        ::= { fkLeasedEntry 5 }

                
                -- 1.3.6.1.4.1.10428 9 1.101.6.14.1.1.6
                fkLeasedHostname OBJECT-TYPE
                        SYNTAX OCTET STRING
                        MAX-ACCESS read-only
                        STATUS current
                        DESCRIPTION
                                "The Host name of the allocated Lease."
                        ::= { fkLeasedEntry 6 }

                
                -- 1.3.6.1.4.1.10428 9 1.101.6.14.1.1.7
                fkLeasedUid OBJECT-TYPE
                        SYNTAX OCTET STRING
                        MAX-ACCESS read-only
                        STATUS current
                        DESCRIPTION
                                "The Client-ID of the allocated Lease."
                        ::= { fkLeasedEntry 7 }

                
                -- 1.3.6.1.4.1.10428 9 1.101.6.14.1.1.8
                fkLeasedRid OBJECT-TYPE
                        SYNTAX OCTET STRING
                        MAX-ACCESS read-only
                        STATUS current
                        DESCRIPTION
                                "The Option82 Remote-ID of the allocated Lease."
                        ::= { fkLeasedEntry 8 }

                
                -- 1.3.6.1.4.1.10428 9 1.101.6.14.1.1.9
                fkLeasedCid OBJECT-TYPE
                        SYNTAX OCTET STRING
                        MAX-ACCESS read-only
                        STATUS current
                        DESCRIPTION
                                "The Option82 Circuit-ID of the allocated Lease."
                        ::= { fkLeasedEntry 9 }

                
                -- 1.3.6.1.4.1.10428 9 1.101.6.14.2
                fkLeasedControl OBJECT IDENTIFIER::= { fkLeased 2 }

                
                -- 1.3.6.1.4.1.10428 9 1.101.6.14.2.1
                fkLeasedControlRequest OBJECT-TYPE
                        SYNTAX INTEGER
                                {
                                flushLeasedIpMask(1),
                                flushLeasedPool(2)
                                }
                        MAX-ACCESS read-write
                        STATUS current
                        DESCRIPTION
                                "The request of a user command."
                        ::= { fkLeasedControl 1 }

                
                -- 1.3.6.1.4.1.10428 9 1.101.6.14.2.2
                fkLeasedControlStatus OBJECT-TYPE
                        SYNTAX FkControlStatusType
                        MAX-ACCESS read-only
                        STATUS current
                        DESCRIPTION
                                "The status of a user command."
                        ::= { fkLeasedControl 2 }

                
                -- 1.3.6.1.4.1.10428 9 1.101.6.14.2.3
                fkLeasedControlTimer OBJECT-TYPE
                        SYNTAX Gauge32
                        MAX-ACCESS read-write
                        STATUS current
                        DESCRIPTION
                                "The maximum wait time for the manager for a long running user command."
                        ::= { fkLeasedControl 3 }

                
                -- 1.3.6.1.4.1.10428 9 1.101.6.14.2.4
                fkLeasedControlTImeStamp OBJECT-TYPE
                        SYNTAX TimeTicks
                        MAX-ACCESS read-only
                        STATUS current
                        DESCRIPTION
                                "The time stamp of the last command (end of command)."
                        ::= { fkLeasedControl 4 }

                
                -- 1.3.6.1.4.1.10428 9 1.101.6.14.2.5
                fkLeasedControlReqResult OBJECT-TYPE
                        SYNTAX FkControlRequestResultType
                        MAX-ACCESS read-only
                        STATUS current
                        DESCRIPTION
                                "The result of the last user command."
                        ::= { fkLeasedControl 5 }

                
                -- 1.3.6.1.4.1.10428 9 1.101.6.14.2.6
                fkLeasedControlIp OBJECT-TYPE
                        SYNTAX IpAddress
                        MAX-ACCESS read-write
                        STATUS current
                        DESCRIPTION
                                "The lease IP address."
                        ::= { fkLeasedControl 6 }

                
                -- 1.3.6.1.4.1.10428 9 1.101.6.14.2.7
                fkLeasedControlMask OBJECT-TYPE
                        SYNTAX INTEGER (1..32)
                        MAX-ACCESS read-write
                        STATUS current
                        DESCRIPTION
                                "The lease IP Mask"
                        ::= { fkLeasedControl 7 }

                
                -- 1.3.6.1.4.1.10428 9 1.101.6.14.2.8
                fkLeasedControlPoolIndex OBJECT-TYPE
                        SYNTAX INTEGER (1..255)
                        MAX-ACCESS read-write
                        STATUS current
                        DESCRIPTION
                                "fkLeasedPoolIndex"
                        ::= { fkLeasedControl 8 }

                
                -- 1.3.6.1.4.1.10428 9 1.101.6.14.3
                fkLeasedNotification OBJECT IDENTIFIER::= { fkLeased 3 }

                
                -- 1.3.6.1.4.1.10428 9 1.101.6.14.3.1
                fkLeasedIpMaskFlushed NOTIFICATION-TYPE
                        OBJECTS { fkLeasedControlRequest, fkLeasedControlTImeStamp, fkLeasedControlReqResult, fkLeasedControlIp, fkLeasedControlMask
                                 }
                        STATUS current
                        DESCRIPTION 
                                "Description."
                        ::= { fkLeasedNotification 1 }

                
                -- 1.3.6.1.4.1.10428 9 1.101.6.14.3.2
                fkLeasedPoolFlushed NOTIFICATION-TYPE
                        OBJECTS { fkLeasedControlRequest, fkLeasedControlTImeStamp, fkLeasedControlReqResult, fkLeasedControlPoolIndex }
                        STATUS current
                        DESCRIPTION 
                                "Description."
                        ::= { fkLeasedNotification 2 }

                
                -- 1.3.6.1.4.1.10428 9 1.101.6.15
                fkDhcpGroup OBJECT-GROUP
                        OBJECTS { fkDhcpDefaultLeaseTime, fkDhcpMaxLeaseTime, fkDhcpDnsIp1, fkDhcpDnsIp2, fkDhcpDnsIp3, 
                                fkDhcpMode, fkDhcpLeasedbBackupIp, fkDhcpLeasedbBackupInterval, fkDhcpDatabaseKey, fkDhcpDebugStatus, 
                                fkDhcpOption82, fkDhcpOption82Policy, fkDhcpOption82SystemRid, fkDhcpAuthorizedArp, fkDhcpAuthArpStarted, 
                                fkDhcpAuthArpLeft, fkDhcpStatisticReceived, fkDhcpStatisticSent, fkDhcpStatisticReceivedErrors, fkDhcpStatisticSentErrors, 
                                fkDhcpStatisticBootpReceivedRequests, fkDhcpStatisticBootpReceivedReplies, fkDhcpStatisticBootpSentRequests, fkDhcpStatisticBootpSentReplies, fkDhcpStatisticReceivedDiscover, 
                                fkDhcpStatisticReceivedRequest, fkDhcpStatisticReceivedRelease, fkDhcpStatisticReceivedInform, fkDhcpStatisticReceivedDecline, fkDhcpStatisticSentOffer, 
                                fkDhcpStatisticSentAck, fkDhcpStatisticSentNak, fkDhcpSummaryPoolCnt, fkDhcpSummaryTotal, fkDhcpSummaryAvailable, 
                                fkDhcpSummaryAbandon, fkDhcpSummaryBound, fkDhcpSummaryOffered, fkDhcpSummaryFixed, fkDhcpControlRequest, 
                                fkDhcpControlStatus, fkDhcpControlTimer, fkDhcpControlTimeStamp, fkDhcpControlReqResult, fkDhcpControlDefaultLeaseTime, 
                                fkDhcpControlMaxLeaseTime, fkDhcpControlDnsIp1, fkDhcpControlDnsIp2, fkDhcpControlDnsIp3, fkDhcpControlServerMode, 
                                fkDhcpControlLeasedbBackupIp, fkDhcpControlLeasedbBackupInterval, fkDhcpControlDatabaseKey, fkDhcpControlDebugStatus, fkDhcpControlOption82, 
                                fkDhcpControlOption82Policy, fkDhcpControlOption82SystemRid, fkDhcpControlAuthorizedArp, fkFilterPortIndex, fkFilterPortMode, 
                                fkFilterPortControlRequest, fkFilterPortControlStatus, fkFilterPortControlTimer, fkFilterPortControlTImeStamp, fkFilterPortControlReqResult, 
                                fkFilterPortControlIndex, fkFilterPortControlMode, fkFilterAddressMac, fkFilterAddressControlRequest, fkFilterAddressControlStatus, 
                                fkFilterAddressControlTimer, fkFilterAddressControlTImeStamp, fkFilterAddressControlReqResult, fkFilterAddressControlMac, fkRelayServerIp, 
                                fkRelayServerControlRequest, fkRelayServerControlStatus, fkRelayServerControlTimer, fkRelayServerControlTImeStamp, fkRelayServerControlReqResult, 
                                fkRelayServerControlIp, fkPoolIndex, fkPoolName, fkPoolDefaultLeaseTime, fkPoolMaxLeaseTime, 
                                fkPoolSummaryTotal, fkPoolSummaryAllocated, fkPoolSummaryBound, fkPoolSummaryOffered, fkPoolSummaryFixed, 
                                fkPoolSummaryAbandon, fkPoolSummaryAvailable, fkPoolControlRequest, fkPoolControlStatus, fkPoolControlTimer, 
                                fkPoolControlTImeStamp, fkPoolControlReqResult, fkPoolControlIndex, fkPoolControlName, fkPoolControlDefaultLeaseTime, 
                                fkPoolControlMaxLeaseTime, fkDnsIp, fkDnsControlRequest, fkDnsControlStatus, fkDnsControlTimer, 
                                fkDnsControlTImeStamp, fkDnsControlReqResult, fkDnsControlPoolIndex, fkDnsControlIp, fkSubnetIp, 
                                fkSubnetMask, fkSubnetDefaultGateway, fkSubnetControlRequest, fkSubnetControlStatus, fkSubnetControlTimer, 
                                fkSubnetControlTImeStamp, fkSubnetControlReqResult, fkSubnetControlPoolIndex, fkSubnetControlIp, fkSubnetControlMask, 
                                fkDefaultGatewayIp, fkDefaultGatewayControlRequest, fkDefaultGatewayControlStatus, fkDefaultGatewayControlTimer, fkDefaultGatewayControlTImeStamp, 
                                fkDefaultGatewayControlReqResult, fkDefaultGatewayControlPoolIndex, fkDefaultGatewayControlIp, fkRangeStart, fkRangeEnd, 
                                fkRangeSubnetIP, fkRangeSubnetMask, fkRangeControlRequest, fkRangeControlStatus, fkRangeControlTimer, 
                                fkRangeControlTImeStamp, fkRangeControlReqResult, fkRangeControlPoolIndex, fkRangeControlStart, fkRangeControlEnd, 
                                fkFixedIp, fkFixedMac, fkFixedControlRequest, fkFixedControlStatus, fkFixedControlTimer, 
                                fkFixedControlTImeStamp, fkFixedControlReqResult, fkFixedControlPoolIndex, fkFixedControlIp, fkFixedControlMac, 
                                fkOption82RemoteType, fkIllegalIp, fkIllegalControlRequest, fkIllegalControlStatus, fkIllegalControlTimer, 
                                fkIllegalControlTImeStamp, fkIllegalControlReqResult, fkLeasedControlRequest, fkLeasedControlStatus, fkLeasedControlTimer, 
                                fkLeasedControlTImeStamp, fkLeasedControlReqResult, fkLeasedControlIp, fkLeasedControlMask, fkRelayServerIndex, 
                                fkRelayServerControlIndex, fkDnsIndex, fkDnsControlIndex, fkDefaultGatewayIndex, fkDefaultGatewayControlIndex, 
                                fkOption82CircuitType, fkDhcpOption82SystemRtype, fkDhcpControlOption82SystemRtype, fkOption82RemoteId, fkOption82CircuitId, 
                                fkOption82Limit, fkOption82PoolName, fkOption82ControlRequest, fkOption82ControlStatus, fkOption82ControlTimer, 
                                fkOption82ControlTImeStamp, fkOption82ControlReqResult, fkOption82ControlRemoteType, fkOption82ControlRemoteId, fkOption82ControlCircuitType, 
                                fkOption82ControlCircuitId, fkOption82ControlLimit, fkOption82ControlPoolName, fkOption82SystemIndex, fkOption82SystemCtype, 
                                fkOption82SystemCid, fkOption82SystemControlRequest, fkOption82SystemControlStatus, fkOption82SystemControlTimer, fkOption82SystemControlTImeStamp, 
                                fkOption82SystemControlReqResult, fkOption82SystemControlIndex, fkOption82SystemControlCtype, fkOption82SystemControlCid, fkLeasedHostname, 
                                fkLeasedUid, fkLeasedRid, fkLeasedCid, fkDhcpClientHardwareAddress, fkDhcpControlClientHardwareAddress, 
                                fkDhcpSimplifiedOption82, fkDhcpControlSimplifiedOption82, fkRelayServerVid, fkRelayServerOUI, fkRelayServerControlVid, 
                                fkRelayServerControlOUI, fkDhcpSummaryAllocated, fkPoolSummarySubnet, fkPoolDomainName, fkPoolControlDomainName, 
                                fkLeasedControlPoolIndex, fkIllegalMac, fkIllegalTime, fkLeasedIp, fkLeasedPoolIndex, 
                                fkLeasedPoolName, fkLeasedTime, fkLeasedHwaddr }
                        STATUS current
                        DESCRIPTION 
                                "Description."
                        ::= { fkDhcp 15 }

                
                -- 1.3.6.1.4.1.10428 9 1.101.6.16
                fkDhcpNotificationGroup NOTIFICATION-GROUP
                        NOTIFICATIONS { fkFilterPortChanged, fkFilterAddressCreated, fkFilterAddressDestroyed, fkRelayServerCreated, fkRelayServerDestroyed, 
                                fkPoolCreated, fkPoolDestroyed, fkPoolLeaseTimeProfileChanged, fkDnsCreated, fkDnsDestroyed, 
                                fkSubnetCreated, fkSubnetDestroyed, fkDefaultGatewayCreated, fkDefaultGatewayDestroyed, fkRangeCreated, 
                                fkRangeDestroyed, fkFixedCreated, fkFixedDestroyed, fkIllegalCleared, fkLeasedIpMaskFlushed, 
                                fkLeasedPoolFlushed, fkDhcpLeaseTimeProfileChanged, fkDhcpDnsIpProfileChanged, fkDhcpServerModeChanged, fkDhcpLeasedbBackupProfileChanged, 
                                fkDhcpDatabaseKeyChanged, fkOption82Created, fkOption82Destroyed, fkOption82ProfileChanged, setOption82SystemCircuit, 
                                fkDhcpDebugStatusChanged, fkDhcpAuthorizedArpChanged, fkDhcpClientHardwareAddressChanged, fkDhcpSimplifiedOption82Changed, fkRelayServerOUICreated, 
                                fkRelayServerOUIDestroyed, fkPoolDomainNameChanged, fkDhcpStatisticsCleared, fkDhcpOption82SystemProfileChanged }
                        STATUS current
                        DESCRIPTION 
                                "Description."
                        ::= { fkDhcp 16 }

                
        
        END

--
-- FK-DHCP-MIB.my
--
