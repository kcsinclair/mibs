--
-- fkv2-qos-mib.mib
-- MIB generated by MG-SOFT Visual MIB Builder Version 6.0  Build 88
-- Tuesday, January 22, 2013 at 03:26:13
--

	FKV2-QOS-MIB DEFINITIONS ::= BEGIN
 
		IMPORTS
			fkV2Mgmt			
				FROM FKOLTG1040-SMI			
			InterfaceIndex			
				FROM IF-MIB			
			FkControlStatusType, FkControlRequestResultType			
				FROM FK-TC-MIB			
			OBJECT-GROUP, NOTIFICATION-GROUP			
				FROM SNMPv2-CONF			
			TimeTicks, IpAddress, Integer32, Gauge32, Counter32, 
			Counter64, BITS, OBJECT-TYPE, MODULE-IDENTITY, NOTIFICATION-TYPE			
				FROM SNMPv2-SMI			
			MacAddress, TEXTUAL-CONVENTION			
				FROM SNMPv2-TC;
	
	
		-- 1.3.6.1.4.1.10428 9 1.102.10
		fkV2QoS MODULE-IDENTITY 
			LAST-UPDATED "200605051406Z"		-- May 05, 2006 at 14:06 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkV2Mgmt 10 }

		
	
--
-- Type definitions
--
	
		IntFlowIndex ::= INTEGER (1..1024)

		IntClassIndex ::= INTEGER (1..1024)

		IntPolicerIndex ::= INTEGER (1..1024)

		IntPolicyIndex ::= INTEGER (1..1024)

		OctetName ::= OCTET STRING (SIZE (1..64))

		IntEthernetType ::= INTEGER (-1 | 0..65535)

		Int8021p ::= INTEGER (-1 | 0..7)

		IntIpAddrMask ::= INTEGER (0..32)

		IntToS ::= INTEGER (-1 | 0..255)

		IntPktLen ::= INTEGER (-1 | 21..65535)

		IntProtocolType ::= INTEGER (-1 | 0..255)

		IntL4Port ::= INTEGER (-1 | 0..65535)

		IntIcmpType ::= INTEGER (-1 | 0..255)

		IntIcmpCode ::= INTEGER (-1 | 0..255)

		IntInternetProtocolFlag ::= INTEGER
			{
			nothing(-1),
			tcp(1),
			ucp(2),
			icmp(3)
			}

		IntRulePriority ::= INTEGER
			{
			nothing(-1),
			low(1),
			medium(2),
			high(3),
			highest(4),
			lowest(5)
			}

		IntFlowClass ::= INTEGER
			{
			nothing(-1),
			flow(1),
			class(2),
			both(4)
			}

		IntVlanID ::= INTEGER (-1 | 1..4094)

		IntQueue ::= INTEGER (-1 | 0..7)

		IntDP ::= INTEGER (-1 | 0..2)

		IntCoS ::= INTEGER (-1 | 0..7)

		IntDscp ::= INTEGER (-1 | 0..63)

		IntIpPrecedence ::= INTEGER (-1 | 0..7)

		IntDstMacOrEgressPorts ::= INTEGER
			{
			nothing(-1),
			dstMac(1),
			egressPorts(2)
			}

		IntMarkMode ::= INTEGER
			{
			nothing(-1),
			markByEntry(1),
			dSCPAttribute(2),
			entryDSCP(3)
			}

		IntMeterMode ::= INTEGER
			{
			nothing(-1),
			rateLimit(1),
			color(2),
			minmaxbandwidth(3)
			}

		IntColorType ::= INTEGER
			{
			nothing(-1),
			srTCM(1),
			trTCM(2)
			}

		IntColorMode ::= INTEGER
			{
			nothing(-1),
			blind(1),
			aware(2)
			}

		IntColorAwareMode ::= INTEGER
			{
			nothing(-1),
			unprotected(1),
			protected(2)
			}

		IntColorCIR ::= INTEGER (-1 | 1..1000000)

		IntColorCBS ::= INTEGER (-1 | 1..4000)

		IntColorPIR ::= INTEGER (-1 | 1..1000000)

		IntColorPBS ::= INTEGER (-1 | 1..4000)

		IntColorEBS ::= INTEGER (-1 | 1..4000)

		IntColorAction ::= INTEGER
			{
			nothing(-1),
			drop(1),
			marking(2),
			dropPrecedence(3),
			dropPrecedenceRed(4),
			dropPrecedenceYellow(5),
			dropPrecedenceGreen(6)
			}

		IntCounterMode ::= INTEGER
			{
			nothing(-1),
			byte(1),
			packet(2)
			}

		IntInterfaceIndex ::= INTEGER (-1 | 1..512)

		IntFlowOrClass ::= INTEGER
			{
			flow(1),
			class(2)
			}

		IntL2BaseRemarkMode ::= INTEGER
			{
			remarkByQueue(1),
			remarkByPriority(2)
			}

		IntColorIndex ::= INTEGER
			{
			green(1),
			yellow(2),
			red(3)
			}

		IntDSCPIndex ::= INTEGER (1..64)

		IntQueueCoSIndex ::= INTEGER (1..8)

		IntIpPktPriorityType ::= INTEGER
			{
			nothing(-1),
			iPPrecedence(1),
			diffServ(2),
			ipToS(3)
			}

		IntEnableFlag ::= INTEGER
			{
			enable(1),
			disable(2)
			}

		IntAvrgCounterMode ::= INTEGER
			{
			nothing(-1),
			byte(1)
			}

	
--
-- Textual conventions
--
	

--
-- Node definitions
--
	
		-- 1.3.6.1.4.1.10428 9 1.102.10.1
		fkV2QoSBase OBJECT IDENTIFIER ::= { fkV2QoS 1 }

		
		-- 1.3.6.1.4.1.10428 9 1.102.10.2
		fkV2QoS4 OBJECT IDENTIFIER ::= { fkV2QoS 2 }

		
		-- 1.3.6.1.4.1.10428 9 1.102.10.2.1
		fkV2QoS4Base OBJECT IDENTIFIER ::= { fkV2QoS4 1 }

		
		-- 1.3.6.1.4.1.10428 9 1.102.10.2.1.1
		fkV2QoS4BaseInfo OBJECT IDENTIFIER ::= { fkV2QoS4Base 1 }

		
		-- 1.3.6.1.4.1.10428 9 1.102.10.2.1.1.1
		fkV2QoS4BaseFlowMode OBJECT-TYPE
			SYNTAX INTEGER
				{
				default(1),
				extension(2)
				}
			MAX-ACCESS read-only
			STATUS current
			DESCRIPTION
				"flow mode
				default : double mode, extension : triple mode"
			::= { fkV2QoS4BaseInfo 1 }

		
		-- 1.3.6.1.4.1.10428 9 1.102.10.2.1.2
		fkV2QoS4BaseControl OBJECT IDENTIFIER ::= { fkV2QoS4Base 2 }

		
		-- 1.3.6.1.4.1.10428 9 1.102.10.2.1.2.1
		fkV2QoS4BaseControlRequest OBJECT-TYPE
			SYNTAX INTEGER { setFlowMode(1) }
			MAX-ACCESS read-write
			STATUS current
			DESCRIPTION
				"The request of a user command"
			::= { fkV2QoS4BaseControl 1 }

		
		-- 1.3.6.1.4.1.10428 9 1.102.10.2.1.2.2
		fkV2QoS4BaseControlStatus OBJECT-TYPE
			SYNTAX FkControlStatusType
			MAX-ACCESS read-only
			STATUS current
			DESCRIPTION
				"The status of user command"
			::= { fkV2QoS4BaseControl 2 }

		
		-- 1.3.6.1.4.1.10428 9 1.102.10.2.1.2.3
		fkV2QoS4BaseControlTimer OBJECT-TYPE
			SYNTAX Gauge32
			MAX-ACCESS read-write
			STATUS current
			DESCRIPTION
				"The maximum time for the manager for a long running user command"
			::= { fkV2QoS4BaseControl 3 }

		
		-- 1.3.6.1.4.1.10428 9 1.102.10.2.1.2.4
		fkV2QoS4BaseControlTimeStamp OBJECT-TYPE
			SYNTAX TimeTicks
			MAX-ACCESS read-only
			STATUS current
			DESCRIPTION
				"The time stamp of the last command(end of command)"
			::= { fkV2QoS4BaseControl 4 }

		
		-- 1.3.6.1.4.1.10428 9 1.102.10.2.1.2.5
		fkV2QoS4BaseControlResult OBJECT-TYPE
			SYNTAX FkControlRequestResultType
			MAX-ACCESS read-only
			STATUS current
			DESCRIPTION
				"The result of the last user command"
			::= { fkV2QoS4BaseControl 5 }

		
		-- 1.3.6.1.4.1.10428 9 1.102.10.2.1.2.6
		fkV2QoS4BaseControlFlowMode OBJECT-TYPE
			SYNTAX INTEGER
				{
				default(1),
				extension(2)
				}
			MAX-ACCESS read-write
			STATUS current
			DESCRIPTION
				"flow mode
				default : double mode, extension : triple "
			::= { fkV2QoS4BaseControl 6 }

		
		-- 1.3.6.1.4.1.10428 9 1.102.10.2.1.3
		fkV2QoS4BaseNotification OBJECT IDENTIFIER ::= { fkV2QoS4Base 3 }

		
		-- 1.3.6.1.4.1.10428 9 1.102.10.2.1.3.1
		fkV2QoS4BaseFlowModeChanged NOTIFICATION-TYPE
			OBJECTS { fkV2QoS4BaseControlRequest, fkV2QoS4BaseControlTimeStamp, fkV2QoS4BaseControlResult, fkV2QoS4BaseControlFlowMode }
			STATUS current
			DESCRIPTION 
				"Description."
			::= { fkV2QoS4BaseNotification 1 }

		
		-- 1.3.6.1.4.1.10428 9 1.102.10.2.2
		fkV2QoS4Flow OBJECT IDENTIFIER ::= { fkV2QoS4 2 }

		
		-- 1.3.6.1.4.1.10428 9 1.102.10.2.2.1
		fkV2QoS4FlowInfo OBJECT IDENTIFIER ::= { fkV2QoS4Flow 1 }

		
		-- 1.3.6.1.4.1.10428 9 1.102.10.2.2.1.1
		fkV2QoS4FlowTable OBJECT-TYPE
			SYNTAX SEQUENCE OF FkV2QoS4FlowEntry
			MAX-ACCESS not-accessible
			STATUS current
			DESCRIPTION
				"flow table."
			::= { fkV2QoS4FlowInfo 1 }

		
		-- 1.3.6.1.4.1.10428 9 1.102.10.2.2.1.1.1
		fkV2QoS4FlowEntry OBJECT-TYPE
			SYNTAX FkV2QoS4FlowEntry
			MAX-ACCESS not-accessible
			STATUS current
			DESCRIPTION
				"key: fkV2QoS4FlowIndex"
			INDEX { fkV2QoS4FlowIndex }
			::= { fkV2QoS4FlowTable 1 }

		
		FkV2QoS4FlowEntry ::=
			SEQUENCE { 
				fkV2QoS4FlowIndex
					INTEGER,
				fkV2QoS4FlowName
					OctetName,
				fkV2QoS4FlowEthernetType
					IntEthernetType,
				fkV2QoS4FlowSrcMacAddr
					MacAddress,
				fkV2QoS4FlowSrcMacAddrMask
					MacAddressMask,
				fkV2QoS4FlowDstMacAddr
					MacAddress,
				fkV2QoS4FlowDstMacAddrMask
					MacAddressMask,
				fkV2QoS4Flow8021p
					Int8021p,
				fkV2QoS4FlowSrcIpAddr
					IpAddress,
				fkV2QoS4FlowSrcIpAddrMask
					IntIpAddrMask,
				fkV2QoS4FlowDstIpAddr
					IpAddress,
				fkV2QoS4FlowDstIpAddrMask
					IntIpAddrMask,
				fkV2QoS4FlowIpPktPriorityType
					IntIpPktPriorityType,
				fkV2QoS4FlowIpPktPriority
					Integer32,
				fkV2QoS4FlowPktLen
					IntPktLen,
				fkV2QoS4FlowProtocolType
					IntProtocolType,
				fkV2QoS4FlowTcpSrcStartPort
					IntL4Port,
				fkV2QoS4FlowTcpSrcEndPort
					IntL4Port,
				fkV2QoS4FlowTcpDstStartPort
					IntL4Port,
				fkV2QoS4FlowTcpDstEndPort
					IntL4Port,
				fkV2QoS4FlowTcpFlag
					BITS,
				fkV2QoS4FlowUdpSrcStartPort
					IntL4Port,
				fkV2QoS4FlowUdpSrcEndPort
					IntL4Port,
				fkV2QoS4FlowUdpDstStartPort
					IntL4Port,
				fkV2QoS4FlowUdpDstEndPort
					IntL4Port,
				fkV2QoS4FlowIcmpType
					IntIcmpType,
				fkV2QoS4FlowIcmpCode
					IntIcmpCode,
				fkV2QoS4FlowHdrlen
					INTEGER,
				fkV2QoS4FlowHdrError
					IntEnableFlag,
				fkV2QoS4FlowInnerVlan
					Integer32,
				fkV2QoS4FlowInner8021p
					Integer32,
				fkV2QoS4FlowMacFlag
					INTEGER,
				fkV2QoS4FlowIpFlag
					INTEGER,
				fkV2QoS4FlowMacDlf
					INTEGER,
				fkV2QoS4FlowTagType
					INTEGER,
				fkV2QoS4FlowInPktTagVid
					Integer32,
				fkV2QoS4FlowInPktTagCfi
					Integer32,
				fkV2QoS4FlowInPktTagCoS
					Integer32,
				fkV2QoS4FlowOutPktTagVid
					Integer32,
				fkV2QoS4FlowOutPktTagCfi
					Integer32,
				fkV2QoS4FlowOutPktTagCoS
					Integer32,
				fkV2QoS4FlowFlowAlias
					OCTET STRING
			 }

		-- 1.3.6.1.4.1.10428 9 1.102.10.2.2.1.1.1.1
		fkV2QoS4FlowIndex OBJECT-TYPE
			SYNTAX INTEGER (1..1024)
			MAX-ACCESS read-only
			STATUS current
			DESCRIPTION
				"The index of flow"
			::= { fkV2QoS4FlowEntry 1 }

		
		-- 1.3.6.1.4.1.10428 9 1.102.10.2.2.1.1.1.2
		fkV2QoS4FlowName OBJECT-TYPE
			SYNTAX OctetName
			MAX-ACCESS read-only
			STATUS current
			DESCRIPTION
				"The name of flow"
			::= { fkV2QoS4FlowEntry 2 }

		
		-- 1.3.6.1.4.1.10428 9 1.102.10.2.2.1.1.1.3
		fkV2QoS4FlowEthernetType OBJECT-TYPE
			SYNTAX IntEthernetType
			MAX-ACCESS read-only
			STATUS current
			DESCRIPTION
				"The ethernet type value in incoming frames
				The value of -1 means any(not set).
				"
			::= { fkV2QoS4FlowEntry 3 }

		
		-- 1.3.6.1.4.1.10428 9 1.102.10.2.2.1.1.1.4
		fkV2QoS4FlowSrcMacAddr OBJECT-TYPE
			SYNTAX MacAddress
			MAX-ACCESS read-only
			STATUS current
			DESCRIPTION
				"The source mac address
				The value of 00:00:00:00:00:00 is any(not set)
				"
			::= { fkV2QoS4FlowEntry 4 }

		
		-- 1.3.6.1.4.1.10428 9 1.102.10.2.2.1.1.1.5
		fkV2QoS4FlowSrcMacAddrMask OBJECT-TYPE
			SYNTAX MacAddressMask
			MAX-ACCESS read-only
			STATUS current
			DESCRIPTION
				"The mask of the source mac address
				The value of 00:00:00:00:00:00 is any(not set)
				"
			::= { fkV2QoS4FlowEntry 5 }

		
		-- 1.3.6.1.4.1.10428 9 1.102.10.2.2.1.1.1.6
		fkV2QoS4FlowDstMacAddr OBJECT-TYPE
			SYNTAX MacAddress
			MAX-ACCESS read-only
			STATUS current
			DESCRIPTION
				"The destination mac address
				The value of 00:00:00:00:00:00 is any(not set)
				"
			::= { fkV2QoS4FlowEntry 6 }

		
		-- 1.3.6.1.4.1.10428 9 1.102.10.2.2.1.1.1.7
		fkV2QoS4FlowDstMacAddrMask OBJECT-TYPE
			SYNTAX MacAddressMask
			MAX-ACCESS read-only
			STATUS current
			DESCRIPTION
				"The mask of the destination mac address
				The value of 00:00:00:00:00:00 is any(not set)
				"
			::= { fkV2QoS4FlowEntry 7 }

		
		-- 1.3.6.1.4.1.10428 9 1.102.10.2.2.1.1.1.8
		fkV2QoS4Flow8021p OBJECT-TYPE
			SYNTAX Int8021p
			MAX-ACCESS read-only
			STATUS current
			DESCRIPTION
				"The value of the IEEE802.1p priority in the packet
				The value of -1 means any(not set)
				"
			::= { fkV2QoS4FlowEntry 8 }

		
		-- 1.3.6.1.4.1.10428 9 1.102.10.2.2.1.1.1.9
		fkV2QoS4FlowSrcIpAddr OBJECT-TYPE
			SYNTAX IpAddress
			MAX-ACCESS read-only
			STATUS current
			DESCRIPTION
				"The IP address to match against the packet's source IP address.
				The value of 0.0.0.0 means any(not set)
				"
			::= { fkV2QoS4FlowEntry 9 }

		
		-- 1.3.6.1.4.1.10428 9 1.102.10.2.2.1.1.1.10
		fkV2QoS4FlowSrcIpAddrMask OBJECT-TYPE
			SYNTAX IntIpAddrMask
			MAX-ACCESS read-only
			STATUS current
			DESCRIPTION
				"The mask of source IP address
				The value of -1 means any(not set)
				"
			::= { fkV2QoS4FlowEntry 10 }

		
		-- 1.3.6.1.4.1.10428 9 1.102.10.2.2.1.1.1.11
		fkV2QoS4FlowDstIpAddr OBJECT-TYPE
			SYNTAX IpAddress
			MAX-ACCESS read-only
			STATUS current
			DESCRIPTION
				"The IP address to match against the packet's destination IP address.
				The value of 0.0.0.0 means any(not set)
				"
			::= { fkV2QoS4FlowEntry 11 }

		
		-- 1.3.6.1.4.1.10428 9 1.102.10.2.2.1.1.1.12
		fkV2QoS4FlowDstIpAddrMask OBJECT-TYPE
			SYNTAX IntIpAddrMask
			MAX-ACCESS read-only
			STATUS current
			DESCRIPTION
				"The mask of destination IP address
				The value of -1 means any(not set)
				"
			::= { fkV2QoS4FlowEntry 12 }

		
		-- 1.3.6.1.4.1.10428 9 1.102.10.2.2.1.1.1.13
		fkV2QoS4FlowIpPktPriorityType OBJECT-TYPE
			SYNTAX IntIpPktPriorityType
			MAX-ACCESS read-only
			STATUS current
			DESCRIPTION
				"The Priority type of incoming IP packet
				(specify a type of fkUserFlowIpPktPriority)
				"
			::= { fkV2QoS4FlowEntry 13 }

		
		-- 1.3.6.1.4.1.10428 9 1.102.10.2.2.1.1.1.14
		fkV2QoS4FlowIpPktPriority OBJECT-TYPE
			SYNTAX Integer32
			MAX-ACCESS read-only
			STATUS current
			DESCRIPTION
				"The Priority value of incoming IP packet
				If type is 1, this value's range is 0-7.
				If type is 2, this value's range is 0-63.
				If type is 3, this value's range is 0-255.
				"
			::= { fkV2QoS4FlowEntry 14 }

		
		-- 1.3.6.1.4.1.10428 9 1.102.10.2.2.1.1.1.15
		fkV2QoS4FlowPktLen OBJECT-TYPE
			SYNTAX IntPktLen
			MAX-ACCESS read-only
			STATUS current
			DESCRIPTION
				"The packet length of the incoming packet
				The value of -1 means any(not set)
				"
			::= { fkV2QoS4FlowEntry 15 }

		
		-- 1.3.6.1.4.1.10428 9 1.102.10.2.2.1.1.1.16
		fkV2QoS4FlowProtocolType OBJECT-TYPE
			SYNTAX IntProtocolType
			MAX-ACCESS read-only
			STATUS current
			DESCRIPTION
				"The type of IP protocol
				The flat internet protocol is from fkV2QoS4FlowTcpSrcStartPort to fkV2QoS4FlowIcmpCode
				If the value is tcp(6),
				From fkV2QoS4FlowTcpSrcStartPort to fkV2QoS4FlowTcpFlag value is available
				If the value is u¿¡(17),
				From fkV2QoS4FlowUdpSrcStartPort to fkV2QoS4FlowUdpDstEndPort value is available
				If the value is icmp(1),
				The value of fkV2QoS4FlowIcmpType and fkV2QoS4FlowIcmpCode is available
				The value of -1 means any(not set)
				Otherwise, from fkV2QoS4FlowTcpSrcStartPort to fkV2QoS4FlowIcmpCode value is not available
				The value of -1 means any(not set)
				"
			::= { fkV2QoS4FlowEntry 16 }

		
		-- 1.3.6.1.4.1.10428 9 1.102.10.2.2.1.1.1.17
		fkV2QoS4FlowTcpSrcStartPort OBJECT-TYPE
			SYNTAX IntL4Port
			MAX-ACCESS read-only
			STATUS current
			DESCRIPTION
				"The start source port in range of source port in TCP packet
				The value of -1 means any(not set)
				"
			::= { fkV2QoS4FlowEntry 17 }

		
		-- 1.3.6.1.4.1.10428 9 1.102.10.2.2.1.1.1.18
		fkV2QoS4FlowTcpSrcEndPort OBJECT-TYPE
			SYNTAX IntL4Port
			MAX-ACCESS read-only
			STATUS current
			DESCRIPTION
				"The end source port in range of source port in TCP packet
				The value of -1 means any(not set)
				"
			::= { fkV2QoS4FlowEntry 18 }

		
		-- 1.3.6.1.4.1.10428 9 1.102.10.2.2.1.1.1.19
		fkV2QoS4FlowTcpDstStartPort OBJECT-TYPE
			SYNTAX IntL4Port
			MAX-ACCESS read-only
			STATUS current
			DESCRIPTION
				"The start destination port in range of source port in TCP packet. The value of -1 means any(not set)"
			::= { fkV2QoS4FlowEntry 19 }

		
		-- 1.3.6.1.4.1.10428 9 1.102.10.2.2.1.1.1.20
		fkV2QoS4FlowTcpDstEndPort OBJECT-TYPE
			SYNTAX IntL4Port
			MAX-ACCESS read-only
			STATUS current
			DESCRIPTION
				"The end destination port in range of destination port in TCP packet. The value of -1 means any(not set)"
			::= { fkV2QoS4FlowEntry 20 }

		
		-- 1.3.6.1.4.1.10428 9 1.102.10.2.2.1.1.1.21
		fkV2QoS4FlowTcpFlag OBJECT-TYPE
			SYNTAX BITS
				{
				reserv0(0),
				reserv1(1),
				urg(2),
				ack(3),
				psh(4),
				rst(5),
				syn(6),
				fin(7)
				}
			MAX-ACCESS read-only
			STATUS current
			DESCRIPTION
				"The flag in TCP packet"
			::= { fkV2QoS4FlowEntry 21 }

		
		-- 1.3.6.1.4.1.10428 9 1.102.10.2.2.1.1.1.22
		fkV2QoS4FlowUdpSrcStartPort OBJECT-TYPE
			SYNTAX IntL4Port
			MAX-ACCESS read-only
			STATUS current
			DESCRIPTION
				"The start source port in range of source port in UDP packet
				The value of -1 means any(not set)
				"
			::= { fkV2QoS4FlowEntry 22 }

		
		-- 1.3.6.1.4.1.10428 9 1.102.10.2.2.1.1.1.23
		fkV2QoS4FlowUdpSrcEndPort OBJECT-TYPE
			SYNTAX IntL4Port
			MAX-ACCESS read-only
			STATUS current
			DESCRIPTION
				"The end source port in range of source port in UDP packet
				The value of -1 means any(not set)
				"
			::= { fkV2QoS4FlowEntry 23 }

		
		-- 1.3.6.1.4.1.10428 9 1.102.10.2.2.1.1.1.24
		fkV2QoS4FlowUdpDstStartPort OBJECT-TYPE
			SYNTAX IntL4Port
			MAX-ACCESS read-only
			STATUS current
			DESCRIPTION
				"The start destination port in range of destination port in UDP packet. The value of -1 means any(not set)"
			::= { fkV2QoS4FlowEntry 24 }

		
		-- 1.3.6.1.4.1.10428 9 1.102.10.2.2.1.1.1.25
		fkV2QoS4FlowUdpDstEndPort OBJECT-TYPE
			SYNTAX IntL4Port
			MAX-ACCESS read-only
			STATUS current
			DESCRIPTION
				"The end destination port in range of destination port in UDP packet. The value of -1 means any(not set)"
			::= { fkV2QoS4FlowEntry 25 }

		
		-- 1.3.6.1.4.1.10428 9 1.102.10.2.2.1.1.1.26
		fkV2QoS4FlowIcmpType OBJECT-TYPE
			SYNTAX IntIcmpType
			MAX-ACCESS read-only
			STATUS current
			DESCRIPTION
				"The type of ICMP message
				The value of -1 means any(not set)
				"
			::= { fkV2QoS4FlowEntry 26 }

		
		-- 1.3.6.1.4.1.10428 9 1.102.10.2.2.1.1.1.27
		fkV2QoS4FlowIcmpCode OBJECT-TYPE
			SYNTAX IntIcmpCode
			MAX-ACCESS read-only
			STATUS current
			DESCRIPTION
				"The code of ICMP message
				The value of -1 means any(not set)
				"
			::= { fkV2QoS4FlowEntry 27 }

		
		-- 1.3.6.1.4.1.10428 9 1.102.10.2.2.1.1.1.28
		fkV2QoS4FlowHdrlen OBJECT-TYPE
			SYNTAX INTEGER (0 | 1..15)
			MAX-ACCESS read-only
			STATUS current
			DESCRIPTION
				"The IP header length.
				The value of 0 means any(not set)"
			::= { fkV2QoS4FlowEntry 28 }

		
		-- 1.3.6.1.4.1.10428 9 1.102.10.2.2.1.1.1.29
		fkV2QoS4FlowHdrError OBJECT-TYPE
			SYNTAX IntEnableFlag
			MAX-ACCESS read-only
			STATUS current
			DESCRIPTION
				"The IP header error check "
			::= { fkV2QoS4FlowEntry 29 }

		
		-- 1.3.6.1.4.1.10428 9 1.102.10.2.2.1.1.1.30
		fkV2QoS4FlowInnerVlan OBJECT-TYPE
			SYNTAX Integer32 (1..4094)
			MAX-ACCESS read-only
			STATUS current
			DESCRIPTION
				"The index of inner vlan.
				The value of -1 is nothing(not set)
				"
			::= { fkV2QoS4FlowEntry 30 }

		
		-- 1.3.6.1.4.1.10428 9 1.102.10.2.2.1.1.1.31
		fkV2QoS4FlowInner8021p OBJECT-TYPE
			SYNTAX Integer32 (0..7)
			MAX-ACCESS read-only
			STATUS current
			DESCRIPTION
				"The value of the Inner IEEE802.1p priority in the packet.
				The value of -1 means any(not set)
				"
			::= { fkV2QoS4FlowEntry 31 }

		
		-- 1.3.6.1.4.1.10428 9 1.102.10.2.2.1.1.1.32
		fkV2QoS4FlowMacFlag OBJECT-TYPE
			SYNTAX INTEGER
				{
				none(0),
				srcAny(1),
				dstAny(2),
				srcDstAny(3)
				}
			MAX-ACCESS read-only
			STATUS current
			DESCRIPTION
				"The any flag of mac address"
			::= { fkV2QoS4FlowEntry 32 }

		
		-- 1.3.6.1.4.1.10428 9 1.102.10.2.2.1.1.1.33
		fkV2QoS4FlowIpFlag OBJECT-TYPE
			SYNTAX INTEGER
				{
				none(0),
				srcAny(1),
				dstAny(2),
				srcDstAny(3)
				}
			MAX-ACCESS read-only
			STATUS current
			DESCRIPTION
				"The any flag of IP address."
			::= { fkV2QoS4FlowEntry 33 }

		
		-- 1.3.6.1.4.1.10428 9 1.102.10.2.2.1.1.1.34
		fkV2QoS4FlowMacDlf OBJECT-TYPE
			SYNTAX INTEGER
				{
				none(0),
				dstFound(1),
				dstNotFound(2)
				}
			MAX-ACCESS read-only
			STATUS current
			DESCRIPTION
				"The destination mac address is found or not."
			::= { fkV2QoS4FlowEntry 34 }

		
		-- 1.3.6.1.4.1.10428 9 1.102.10.2.2.1.1.1.35
		fkV2QoS4FlowTagType OBJECT-TYPE
			SYNTAX INTEGER
				{
				untag(1),
				custom(2),
				service(3),
				both(4)
				}
			MAX-ACCESS read-only
			STATUS current
			DESCRIPTION
				"The packet tag type"
			::= { fkV2QoS4FlowEntry 35 }

		
		-- 1.3.6.1.4.1.10428 9 1.102.10.2.2.1.1.1.36
		fkV2QoS4FlowInPktTagVid OBJECT-TYPE
			SYNTAX Integer32 (1..4094 | 4095)
			MAX-ACCESS read-only
			STATUS current
			DESCRIPTION
				"VID, 4095 : any"
			::= { fkV2QoS4FlowEntry 36 }

		
		-- 1.3.6.1.4.1.10428 9 1.102.10.2.2.1.1.1.37
		fkV2QoS4FlowInPktTagCfi OBJECT-TYPE
			SYNTAX Integer32 (0..1 | 255)
			MAX-ACCESS read-only
			STATUS current
			DESCRIPTION
				"CFI,  255:any"
			::= { fkV2QoS4FlowEntry 37 }

		
		-- 1.3.6.1.4.1.10428 9 1.102.10.2.2.1.1.1.38
		fkV2QoS4FlowInPktTagCoS OBJECT-TYPE
			SYNTAX Integer32 (0..7 | 255)
			MAX-ACCESS read-only
			STATUS current
			DESCRIPTION
				"802.1p, 255:any"
			::= { fkV2QoS4FlowEntry 38 }

		
		-- 1.3.6.1.4.1.10428 9 1.102.10.2.2.1.1.1.39
		fkV2QoS4FlowOutPktTagVid OBJECT-TYPE
			SYNTAX Integer32 (1..4094 | 4095)
			MAX-ACCESS read-only
			STATUS current
			DESCRIPTION
				"VID, 4095 : any"
			::= { fkV2QoS4FlowEntry 39 }

		
		-- 1.3.6.1.4.1.10428 9 1.102.10.2.2.1.1.1.40
		fkV2QoS4FlowOutPktTagCfi OBJECT-TYPE
			SYNTAX Integer32 (0..1 | 255)
			MAX-ACCESS read-only
			STATUS current
			DESCRIPTION
				"CFI,  255:any"
			::= { fkV2QoS4FlowEntry 40 }

		
		-- 1.3.6.1.4.1.10428 9 1.102.10.2.2.1.1.1.41
		fkV2QoS4FlowOutPktTagCoS OBJECT-TYPE
			SYNTAX Integer32 (0..7 | 255)
			MAX-ACCESS read-only
			STATUS current
			DESCRIPTION
				"802.1p, 255:any"
			::= { fkV2QoS4FlowEntry 41 }

		
		-- 1.3.6.1.4.1.10428 9 1.102.10.2.2.1.1.1.42
		fkV2QoS4FlowFlowAlias OBJECT-TYPE
			SYNTAX OCTET STRING
			MAX-ACCESS read-only
			STATUS current
			DESCRIPTION
				"flow alias"
			::= { fkV2QoS4FlowEntry 42 }

		
		-- 1.3.6.1.4.1.10428 9 1.102.10.2.2.1.2
		fkV2QoS4FlowControl OBJECT IDENTIFIER ::= { fkV2QoS4FlowInfo 2 }

		
		-- 1.3.6.1.4.1.10428 9 1.102.10.2.2.1.2.1
		fkV2QoS4FlowControlRequest OBJECT-TYPE
			SYNTAX INTEGER
				{
				createFlow(1),
				modifyFlow(2),
				destroyFlow(3),
				destroyAllFlow(4),
				setInPktTag(5),
				setOutPktTag(6),
				setFlowAlias(7)
				}
			MAX-ACCESS read-write
			STATUS current
			DESCRIPTION
				"The request of a user command"
			::= { fkV2QoS4FlowControl 1 }

		
		-- 1.3.6.1.4.1.10428 9 1.102.10.2.2.1.2.2
		fkV2QoS4FlowControlStatus OBJECT-TYPE
			SYNTAX FkControlStatusType
			MAX-ACCESS read-only
			STATUS current
			DESCRIPTION
				"The status of user command"
			::= { fkV2QoS4FlowControl 2 }

		
		-- 1.3.6.1.4.1.10428 9 1.102.10.2.2.1.2.3
		fkV2QoS4FlowControlTimer OBJECT-TYPE
			SYNTAX Gauge32
			MAX-ACCESS read-write
			STATUS current
			DESCRIPTION
				"The maximum time for the manager for a long running user command"
			::= { fkV2QoS4FlowControl 3 }

		
		-- 1.3.6.1.4.1.10428 9 1.102.10.2.2.1.2.4
		fkV2QoS4FlowControlTimeStamp OBJECT-TYPE
			SYNTAX TimeTicks
			MAX-ACCESS read-only
			STATUS current
			DESCRIPTION
				"The time stamp of the last command(end of command)"
			::= { fkV2QoS4FlowControl 4 }

		
		-- 1.3.6.1.4.1.10428 9 1.102.10.2.2.1.2.5
		fkV2QoS4FlowControlReqResult OBJECT-TYPE
			SYNTAX FkControlRequestResultType
			MAX-ACCESS read-only
			STATUS current
			DESCRIPTION
				"The result of the last user command"
			::= { fkV2QoS4FlowControl 5 }

		
		-- 1.3.6.1.4.1.10428 9 1.102.10.2.2.1.2.6
		fkV2QoS4FlowControlIndex OBJECT-TYPE
			SYNTAX IntFlowIndex
			MAX-ACCESS read-write
			STATUS current
			DESCRIPTION
				"The index of flow"
			::= { fkV2QoS4FlowControl 6 }

		
		-- 1.3.6.1.4.1.10428 9 1.102.10.2.2.1.2.7
		fkV2QoS4FlowControlName OBJECT-TYPE
			SYNTAX OctetName
			MAX-ACCESS read-write
			STATUS current
			DESCRIPTION
				"The name of flow"
			::= { fkV2QoS4FlowControl 7 }

		
		-- 1.3.6.1.4.1.10428 9 1.102.10.2.2.1.2.8
		fkV2QoS4FlowControlEthernetType OBJECT-TYPE
			SYNTAX IntEthernetType
			MAX-ACCESS read-write
			STATUS current
			DESCRIPTION
				"The ethernet type value in incoming frames
				The value of -1 means any(not set).
				"
			::= { fkV2QoS4FlowControl 8 }

		
		-- 1.3.6.1.4.1.10428 9 1.102.10.2.2.1.2.9
		fkV2QoS4FlowControlSrcMacAddr OBJECT-TYPE
			SYNTAX MacAddress
			MAX-ACCESS read-write
			STATUS current
			DESCRIPTION
				"The source mac address
				The value of 00:00:00:00:00:00 is any(not set)
				"
			::= { fkV2QoS4FlowControl 9 }

		
		-- 1.3.6.1.4.1.10428 9 1.102.10.2.2.1.2.10
		fkV2QoS4FlowControlSrcMacAddrMask OBJECT-TYPE
			SYNTAX MacAddressMask
			MAX-ACCESS read-write
			STATUS current
			DESCRIPTION
				"The mask of the source mac address
				The value of 00:00:00:00:00:00 is any(not set)
				"
			::= { fkV2QoS4FlowControl 10 }

		
		-- 1.3.6.1.4.1.10428 9 1.102.10.2.2.1.2.11
		fkV2QoS4FlowControlDstMacAddr OBJECT-TYPE
			SYNTAX MacAddress
			MAX-ACCESS read-write
			STATUS current
			DESCRIPTION
				"The destination mac address
				The value of 00:00:00:00:00:00 is any(not set)
				"
			::= { fkV2QoS4FlowControl 11 }

		
		-- 1.3.6.1.4.1.10428 9 1.102.10.2.2.1.2.12
		fkV2QoS4FlowControlDstMacAddrMask OBJECT-TYPE
			SYNTAX MacAddressMask
			MAX-ACCESS read-write
			STATUS current
			DESCRIPTION
				"The mask of the destination mac address
				The value of 00:00:00:00:00:00 is any(not set)
				"
			::= { fkV2QoS4FlowControl 12 }

		
		-- 1.3.6.1.4.1.10428 9 1.102.10.2.2.1.2.13
		fkV2QoS4FlowControl8021p OBJECT-TYPE
			SYNTAX Int8021p
			MAX-ACCESS read-write
			STATUS current
			DESCRIPTION
				"The value of the IEEE802.1p priority in the packet
				The value of -1 means any(not set)
				"
			::= { fkV2QoS4FlowControl 13 }

		
		-- 1.3.6.1.4.1.10428 9 1.102.10.2.2.1.2.14
		fkV2QoS4FlowControlSrcIpAddr OBJECT-TYPE
			SYNTAX IpAddress
			MAX-ACCESS read-write
			STATUS current
			DESCRIPTION
				"The IP address to match against the packet's source IP address.
				The value of 0.0.0.0 means any(not set)
				"
			::= { fkV2QoS4FlowControl 14 }

		
		-- 1.3.6.1.4.1.10428 9 1.102.10.2.2.1.2.15
		fkV2QoS4FlowControlSrcIpAddrMask OBJECT-TYPE
			SYNTAX IntIpAddrMask
			MAX-ACCESS read-write
			STATUS current
			DESCRIPTION
				"The mask of source IP address
				The value of -1 means any(not set)
				"
			::= { fkV2QoS4FlowControl 15 }

		
		-- 1.3.6.1.4.1.10428 9 1.102.10.2.2.1.2.16
		fkV2QoS4FlowControlDstIpAddr OBJECT-TYPE
			SYNTAX IpAddress
			MAX-ACCESS read-write
			STATUS current
			DESCRIPTION
				"The IP address to match against the packet's destination IP address.
				The value of 0.0.0.0 means any(not set)
				"
			::= { fkV2QoS4FlowControl 16 }

		
		-- 1.3.6.1.4.1.10428 9 1.102.10.2.2.1.2.17
		fkV2QoS4FlowControlDstIpAddrMask OBJECT-TYPE
			SYNTAX IntIpAddrMask
			MAX-ACCESS read-write
			STATUS current
			DESCRIPTION
				"The mask of destination IP address
				The value of -1 means any(not set)
				"
			::= { fkV2QoS4FlowControl 17 }

		
		-- 1.3.6.1.4.1.10428 9 1.102.10.2.2.1.2.18
		fkV2QoS4FlowControlIpPktPriorityType OBJECT-TYPE
			SYNTAX IntIpPktPriorityType
			MAX-ACCESS read-write
			STATUS current
			DESCRIPTION
				"The Priority type of incoming IP packet
				(specify a type of fkUserFlowIpPktPriority)
				The value of -1 means any(not set)
				"
			::= { fkV2QoS4FlowControl 18 }

		
		-- 1.3.6.1.4.1.10428 9 1.102.10.2.2.1.2.19
		fkV2QoS4FlowControlIpPktPriority OBJECT-TYPE
			SYNTAX Integer32
			MAX-ACCESS read-write
			STATUS current
			DESCRIPTION
				"The Priority value of incoming IP packet
				If type is 1, this value's range is 0-7.
				If type is 2, this value's range is 0-63.
				If type is 3, this value's range is 0-255.
				The value of -1 means any(not set)
				"
			::= { fkV2QoS4FlowControl 19 }

		
		-- 1.3.6.1.4.1.10428 9 1.102.10.2.2.1.2.20
		fkV2QoS4FlowControlPktLen OBJECT-TYPE
			SYNTAX IntPktLen
			MAX-ACCESS read-write
			STATUS current
			DESCRIPTION
				"The packet length of the incoming packet
				The value of -1 means any(not set)
				"
			::= { fkV2QoS4FlowControl 20 }

		
		-- 1.3.6.1.4.1.10428 9 1.102.10.2.2.1.2.21
		fkV2QoS4FlowControlProtocolType OBJECT-TYPE
			SYNTAX IntProtocolType
			MAX-ACCESS read-write
			STATUS current
			DESCRIPTION
				"The type of IP protocol
				The flat internet protocol is from fkV2QoS4FlowTcpSrcStartPort to fkV2QoS4FlowIcmpCode
				If the value is tcp(6),
				From fkV2QoS4FlowControlTcpSrcStartPort to fkV2QoS4FlowControlTcpFlag value is available
				If the value is u¿¡(17),
				From fkV2QoS4FlowControlUdpSrcStartPort to fkV2QoS4FlowControlUdpDstEndPort value is available
				If the value is icmp(1),
				The value of fkV2QoS4FlowControlIcmpType and fkV2QoS4FlowControlIcmpCode is available
				The value of -1 means any(not set)
				Otherwise, from fkV2QoS4FlowControlTcpSrcStartPort to fkV2QoS4FlowControlIcmpCode value is not available
				The value of -1 means any(not set)
				"
			::= { fkV2QoS4FlowControl 21 }

		
		-- 1.3.6.1.4.1.10428 9 1.102.10.2.2.1.2.22
		fkV2QoS4FlowControlTcpSrcStartPort OBJECT-TYPE
			SYNTAX IntL4Port
			MAX-ACCESS read-write
			STATUS current
			DESCRIPTION
				"The start source port in range of source port in TCP packet
				The value of -1 means any(not set)
				"
			::= { fkV2QoS4FlowControl 22 }

		
		-- 1.3.6.1.4.1.10428 9 1.102.10.2.2.1.2.23
		fkV2QoS4FlowControlTcpSrcEndPort OBJECT-TYPE
			SYNTAX IntL4Port
			MAX-ACCESS read-write
			STATUS current
			DESCRIPTION
				"The end source port in range of source port in TCP packet
				The value of -1 means any(not set)
				"
			::= { fkV2QoS4FlowControl 23 }

		
		-- 1.3.6.1.4.1.10428 9 1.102.10.2.2.1.2.24
		fkV2QoS4FlowControlTcpDstStartPort OBJECT-TYPE
			SYNTAX IntL4Port
			MAX-ACCESS read-write
			STATUS current
			DESCRIPTION
				"The start destination port in range of source port in TCP packet. The value of -1 means any(not set)"
			::= { fkV2QoS4FlowControl 24 }

		
		-- 1.3.6.1.4.1.10428 9 1.102.10.2.2.1.2.25
		fkV2QoS4FlowControlTcpDstEndPort OBJECT-TYPE
			SYNTAX IntL4Port
			MAX-ACCESS read-write
			STATUS current
			DESCRIPTION
				"The end destination port in range of destination port in TCP packet. The value of -1 means any(not set)"
			::= { fkV2QoS4FlowControl 25 }

		
		-- 1.3.6.1.4.1.10428 9 1.102.10.2.2.1.2.26
		fkV2QoS4FlowControlTcpFlag OBJECT-TYPE
			SYNTAX BITS
				{
				reserv0(0),
				reserv1(1),
				urg(2),
				ack(3),
				psh(4),
				rst(5),
				syn(6),
				fin(7)
				}
			MAX-ACCESS read-write
			STATUS current
			DESCRIPTION
				"The flag in TCP packet"
			::= { fkV2QoS4FlowControl 26 }

		
		-- 1.3.6.1.4.1.10428 9 1.102.10.2.2.1.2.27
		fkV2QoS4FlowControlUdpSrcStartPort OBJECT-TYPE
			SYNTAX IntL4Port
			MAX-ACCESS read-write
			STATUS current
			DESCRIPTION
				"The start source port in range of source port in UDP packet
				The value of -1 means any(not set)
				"
			::= { fkV2QoS4FlowControl 27 }

		
		-- 1.3.6.1.4.1.10428 9 1.102.10.2.2.1.2.28
		fkV2QoS4FlowControlUdpSrcEndPort OBJECT-TYPE
			SYNTAX IntL4Port
			MAX-ACCESS read-write
			STATUS current
			DESCRIPTION
				"The end source port in range of source port in UDP packet
				The value of -1 means any(not set)
				"
			::= { fkV2QoS4FlowControl 28 }

		
		-- 1.3.6.1.4.1.10428 9 1.102.10.2.2.1.2.29
		fkV2QoS4FlowControlUdpDstStartPort OBJECT-TYPE
			SYNTAX IntL4Port
			MAX-ACCESS read-write
			STATUS current
			DESCRIPTION
				"The start destination port in range of destination port in UDP packet. The value of -1 means any(not set)"
			::= { fkV2QoS4FlowControl 29 }

		
		-- 1.3.6.1.4.1.10428 9 1.102.10.2.2.1.2.30
		fkV2QoS4FlowControlUdpDstEndPort OBJECT-TYPE
			SYNTAX IntL4Port
			MAX-ACCESS read-write
			STATUS current
			DESCRIPTION
				"The end destination port in range of destination port in UDP packet. The value of -1 means any(not set)"
			::= { fkV2QoS4FlowControl 30 }

		
		-- 1.3.6.1.4.1.10428 9 1.102.10.2.2.1.2.31
		fkV2QoS4FlowControlIcmpType OBJECT-TYPE
			SYNTAX IntIcmpType
			MAX-ACCESS read-write
			STATUS current
			DESCRIPTION
				"The type of ICMP message
				The value of -1 means any(not set)
				"
			::= { fkV2QoS4FlowControl 31 }

		
		-- 1.3.6.1.4.1.10428 9 1.102.10.2.2.1.2.32
		fkV2QoS4FlowControlIcmpCode OBJECT-TYPE
			SYNTAX IntIcmpCode
			MAX-ACCESS read-write
			STATUS current
			DESCRIPTION
				"The code of ICMP message
				The value of -1 means any(not set)
				"
			::= { fkV2QoS4FlowControl 32 }

		
		-- 1.3.6.1.4.1.10428 9 1.102.10.2.2.1.2.33
		fkV2QoS4FlowControlHdrlen OBJECT-TYPE
			SYNTAX INTEGER (0 | 1..15)
			MAX-ACCESS read-write
			STATUS current
			DESCRIPTION
				"The IP header error check "
			::= { fkV2QoS4FlowControl 33 }

		
		-- 1.3.6.1.4.1.10428 9 1.102.10.2.2.1.2.34
		fkV2QoS4FlowControlHdrError OBJECT-TYPE
			SYNTAX IntEnableFlag
			MAX-ACCESS read-write
			STATUS current
			DESCRIPTION
				"The IP header error check "
			::= { fkV2QoS4FlowControl 34 }

		
		-- 1.3.6.1.4.1.10428 9 1.102.10.2.2.1.2.35
		fkV2QoS4FlowControlInnerVlan OBJECT-TYPE
			SYNTAX Integer32 (1..4094)
			MAX-ACCESS read-write
			STATUS current
			DESCRIPTION
				"The index of inner vlan.
				The value of -1 is nothing(not set)
				"
			::= { fkV2QoS4FlowControl 35 }

		
		-- 1.3.6.1.4.1.10428 9 1.102.10.2.2.1.2.36
		fkV2QoS4FlowControlInner8021p OBJECT-TYPE
			SYNTAX Integer32 (0..7)
			MAX-ACCESS read-write
			STATUS current
			DESCRIPTION
				"The value of the Inner IEEE802.1p priority in the packet.
				The value of -1 means any(not set)
				"
			::= { fkV2QoS4FlowControl 36 }

		
		-- 1.3.6.1.4.1.10428 9 1.102.10.2.2.1.2.37
		fkV2QoS4FlowControlMacFlag OBJECT-TYPE
			SYNTAX INTEGER
				{
				none(0),
				srcAny(1),
				dstAny(2),
				srcDstAny(3)
				}
			MAX-ACCESS read-write
			STATUS current
			DESCRIPTION
				"The any flag of mac address"
			::= { fkV2QoS4FlowControl 37 }

		
		-- 1.3.6.1.4.1.10428 9 1.102.10.2.2.1.2.38
		fkV2QoS4FlowControlIpFlag OBJECT-TYPE
			SYNTAX INTEGER
				{
				none(0),
				srcAny(1),
				dstAny(2),
				srcDstAny(3)
				}
			MAX-ACCESS read-write
			STATUS current
			DESCRIPTION
				"The any flag of IP address."
			::= { fkV2QoS4FlowControl 38 }

		
		-- 1.3.6.1.4.1.10428 9 1.102.10.2.2.1.2.39
		fkV2QoS4FlowControlMacDlf OBJECT-TYPE
			SYNTAX INTEGER
				{
				none(0),
				dstFound(1),
				dstNotFound(2)
				}
			MAX-ACCESS read-write
			STATUS current
			DESCRIPTION
				"The destination MAC address found or not"
			::= { fkV2QoS4FlowControl 39 }

		
		-- 1.3.6.1.4.1.10428 9 1.102.10.2.2.1.2.40
		fkV2QoS4FlowControlTagType OBJECT-TYPE
			SYNTAX INTEGER
				{
				untag(1),
				custom(2),
				service(3),
				both(4)
				}
			MAX-ACCESS read-write
			STATUS current
			DESCRIPTION
				"The packet tag type"
			::= { fkV2QoS4FlowControl 40 }

		
		-- 1.3.6.1.4.1.10428 9 1.102.10.2.2.1.2.41
		fkV2QoS4FlowControlPktTagVid OBJECT-TYPE
			SYNTAX Integer32 (-1 | 1..4094 | 4095)
			MAX-ACCESS read-only
			STATUS current
			DESCRIPTION
				"VID, 4095 : any
				All VID, CFI, CoS are -1 : clear command "
			::= { fkV2QoS4FlowControl 41 }

		
		-- 1.3.6.1.4.1.10428 9 1.102.10.2.2.1.2.42
		fkV2QoS4FlowControlPktTagCfi OBJECT-TYPE
			SYNTAX Integer32 (-1 | 0..1 | 255)
			MAX-ACCESS read-only
			STATUS current
			DESCRIPTION
				"CFI,  255:any
				All VID, CFI, CoS are -1 : clear command"
			::= { fkV2QoS4FlowControl 42 }

		
		-- 1.3.6.1.4.1.10428 9 1.102.10.2.2.1.2.43
		fkV2QoS4FlowControlPktTagCoS OBJECT-TYPE
			SYNTAX Integer32 (-1 | 0..7 | 255)
			MAX-ACCESS read-only
			STATUS current
			DESCRIPTION
				"802.1p, 255:any
				All VID, CFI, CoS are -1 : clear command"
			::= { fkV2QoS4FlowControl 43 }

		
		-- 1.3.6.1.4.1.10428 9 1.102.10.2.2.1.2.44
		fkV2QoS4FlowControlFlowAlias OBJECT-TYPE
			SYNTAX OCTET STRING
			MAX-ACCESS read-only
			STATUS current
			DESCRIPTION
				"flow alias"
			::= { fkV2QoS4FlowControl 44 }

		
		-- 1.3.6.1.4.1.10428 9 1.102.10.2.2.1.3
		fkV2QoS4FlowNotification OBJECT IDENTIFIER ::= { fkV2QoS4FlowInfo 3 }

		
		-- 1.3.6.1.4.1.10428 9 1.102.10.2.2.1.3.1
		fkFlowCreated NOTIFICATION-TYPE
			OBJECTS { fkV2QoS4FlowControlRequest, fkV2QoS4FlowControlTimeStamp, fkV2QoS4FlowHdrError, fkV2QoS4FlowInner8021p, fkV2QoS4FlowInnerVlan, 
				fkV2QoS4FlowMacDlf, fkV2QoS4FlowMacFlag, fkV2QoS4FlowIpFlag, fkV2QoS4FlowTagType, fkV2QoS4FlowControlReqResult, 
				fkV2QoS4FlowName, fkV2QoS4FlowEthernetType, fkV2QoS4FlowSrcMacAddr, fkV2QoS4FlowSrcMacAddrMask, fkV2QoS4FlowDstMacAddr, 
				fkV2QoS4FlowDstMacAddrMask, fkV2QoS4Flow8021p, fkV2QoS4FlowSrcIpAddr, fkV2QoS4FlowSrcIpAddrMask, fkV2QoS4FlowDstIpAddr, 
				fkV2QoS4FlowDstIpAddrMask, fkV2QoS4FlowIpPktPriorityType, fkV2QoS4FlowIpPktPriority, fkV2QoS4FlowPktLen, fkV2QoS4FlowProtocolType, 
				fkV2QoS4FlowTcpSrcStartPort, fkV2QoS4FlowTcpSrcEndPort, fkV2QoS4FlowTcpDstStartPort, fkV2QoS4FlowTcpDstEndPort, fkV2QoS4FlowTcpFlag, 
				fkV2QoS4FlowUdpSrcStartPort, fkV2QoS4FlowUdpSrcEndPort, fkV2QoS4FlowUdpDstStartPort, fkV2QoS4FlowUdpDstEndPort, fkV2QoS4FlowIcmpType, 
				fkV2QoS4FlowIcmpCode, fkV2QoS4FlowHdrlen }
			STATUS current
			DESCRIPTION 
				"Description."
			::= { fkV2QoS4FlowNotification 1 }

		
		-- 1.3.6.1.4.1.10428 9 1.102.10.2.2.1.3.2
		fkFlowChanged NOTIFICATION-TYPE
			OBJECTS { fkV2QoS4FlowControlRequest, fkV2QoS4FlowControlTimeStamp, fkV2QoS4BaseControlFlowMode, fkV2QoS4FlowControlIndex, fkV2QoS4FlowControlEthernetType, 
				fkV2QoS4FlowControlSrcMacAddr, fkV2QoS4FlowControlSrcMacAddrMask, fkV2QoS4FlowControlDstMacAddr, fkV2QoS4FlowControlDstMacAddrMask, fkV2QoS4FlowControl8021p, 
				fkV2QoS4FlowControlSrcIpAddr, fkV2QoS4FlowControlSrcIpAddrMask, fkV2QoS4FlowControlDstIpAddr, fkV2QoS4FlowControlDstIpAddrMask, fkV2QoS4FlowControlIpPktPriorityType, 
				fkV2QoS4FlowControlIpPktPriority, fkV2QoS4FlowControlPktLen, fkV2QoS4FlowControlProtocolType, fkV2QoS4FlowControlTcpSrcStartPort, fkV2QoS4FlowControlTcpSrcEndPort, 
				fkV2QoS4FlowControlTcpDstStartPort, fkV2QoS4FlowControlTcpDstEndPort, fkV2QoS4FlowControlTcpFlag, fkV2QoS4FlowControlUdpSrcStartPort, fkV2QoS4FlowControlUdpSrcEndPort, 
				fkV2QoS4FlowControlUdpDstStartPort, fkV2QoS4FlowControlUdpDstEndPort, fkV2QoS4FlowControlIcmpType, fkV2QoS4FlowControlIcmpCode, fkV2QoS4FlowControlHdrlen, 
				fkV2QoS4FlowControlHdrError, fkV2QoS4FlowControlInnerVlan, fkV2QoS4FlowControlInner8021p, fkV2QoS4FlowControlMacFlag, fkV2QoS4FlowControlIpFlag, 
				fkV2QoS4FlowControlTagType, fkV2QoS4FlowControlMacDlf, fkV2QoS4FlowControlReqResult }
			STATUS current
			DESCRIPTION 
				"Description."
			::= { fkV2QoS4FlowNotification 2 }

		
		-- 1.3.6.1.4.1.10428 9 1.102.10.2.2.1.3.3
		fkFlowDestroyed NOTIFICATION-TYPE
			OBJECTS { fkV2QoS4FlowControlRequest, fkV2QoS4FlowControlTimeStamp, fkV2QoS4FlowControlReqResult, fkV2QoS4FlowControlIndex }
			STATUS current
			DESCRIPTION 
				"Description."
			::= { fkV2QoS4FlowNotification 3 }

		
		-- 1.3.6.1.4.1.10428 9 1.102.10.2.2.1.3.4
		fkFlowAllDestroyed NOTIFICATION-TYPE
			OBJECTS { fkV2QoS4FlowControlRequest, fkV2QoS4FlowControlTimeStamp, fkV2QoS4FlowControlReqResult }
			STATUS current
			DESCRIPTION 
				"Description."
			::= { fkV2QoS4FlowNotification 4 }

		
		-- 1.3.6.1.4.1.10428 9 1.102.10.2.2.1.3.5
		fkFlowInPktTagChanged NOTIFICATION-TYPE
			OBJECTS { fkV2QoS4FlowControlRequest, fkV2QoS4FlowControlTimeStamp, fkV2QoS4FlowControlReqResult, fkV2QoS4FlowControlIndex, fkV2QoS4FlowControlPktTagVid, 
				fkV2QoS4FlowControlPktTagCfi, fkV2QoS4FlowControlPktTagCoS }
			STATUS current
			DESCRIPTION 
				"Description."
			::= { fkV2QoS4FlowNotification 5 }

		
		-- 1.3.6.1.4.1.10428 9 1.102.10.2.2.1.3.6
		fkFlowOutPktTagChanged NOTIFICATION-TYPE
			OBJECTS { fkV2QoS4FlowControlRequest, fkV2QoS4FlowControlTimeStamp, fkV2QoS4FlowControlReqResult, fkV2QoS4FlowControlIndex, fkV2QoS4FlowControlPktTagVid, 
				fkV2QoS4FlowControlPktTagCfi, fkV2QoS4FlowControlPktTagCoS }
			STATUS current
			DESCRIPTION 
				"setOutPktTag"
			::= { fkV2QoS4FlowNotification 6 }

		
		-- 1.3.6.1.4.1.10428 9 1.102.10.2.2.1.3.7
		fkFlowAliasChanged NOTIFICATION-TYPE
			OBJECTS { fkV2QoS4FlowControlRequest, fkV2QoS4FlowControlTimeStamp, fkV2QoS4FlowControlReqResult, fkV2QoS4FlowControlIndex, fkV2QoS4FlowControlFlowAlias
				 }
			STATUS current
			DESCRIPTION 
				"setFlowAlias"
			::= { fkV2QoS4FlowNotification 7 }

		
		-- 1.3.6.1.4.1.10428 9 1.102.10.2.2.2
		fkV2QoS4FlowClass OBJECT IDENTIFIER ::= { fkV2QoS4Flow 2 }

		
		-- 1.3.6.1.4.1.10428 9 1.102.10.2.2.2.1
		fkV2QoS4FlowClassTable OBJECT-TYPE
			SYNTAX SEQUENCE OF FkV2QoS4FlowClassEntry
			MAX-ACCESS not-accessible
			STATUS current
			DESCRIPTION
				"flow class table."
			::= { fkV2QoS4FlowClass 1 }

		
		-- 1.3.6.1.4.1.10428 9 1.102.10.2.2.2.1.1
		fkV2QoS4FlowClassEntry OBJECT-TYPE
			SYNTAX FkV2QoS4FlowClassEntry
			MAX-ACCESS not-accessible
			STATUS current
			DESCRIPTION
				"key: fkV2QoS4FlowIndex, fkV2QoS4FlowClassIndex"
			INDEX { fkV2QoS4FlowIndex, fkV2QoS4FlowClassIndex }
			::= { fkV2QoS4FlowClassTable 1 }

		
		FkV2QoS4FlowClassEntry ::=
			SEQUENCE { 
				fkV2QoS4FlowClassIndex
					IntClassIndex,
				fkV2QoS4FlowClassID
					IntClassIndex,
				fkV2QoS4FlowClassName
					OctetName
			 }

		-- 1.3.6.1.4.1.10428 9 1.102.10.2.2.2.1.1.1
		fkV2QoS4FlowClassIndex OBJECT-TYPE
			SYNTAX IntClassIndex
			MAX-ACCESS read-only
			STATUS current
			DESCRIPTION
				"The index of the class for the flow"
			::= { fkV2QoS4FlowClassEntry 1 }

		
		-- 1.3.6.1.4.1.10428 9 1.102.10.2.2.2.1.1.2
		fkV2QoS4FlowClassID OBJECT-TYPE
			SYNTAX IntClassIndex
			MAX-ACCESS read-only
			STATUS current
			DESCRIPTION
				"The identifier of the class"
			::= { fkV2QoS4FlowClassEntry 2 }

		
		-- 1.3.6.1.4.1.10428 9 1.102.10.2.2.2.1.1.3
		fkV2QoS4FlowClassName OBJECT-TYPE
			SYNTAX OctetName
			MAX-ACCESS read-only
			STATUS current
			DESCRIPTION
				"The name of the class"
			::= { fkV2QoS4FlowClassEntry 3 }

		
		-- 1.3.6.1.4.1.10428 9 1.102.10.2.2.3
		fkV2QoS4FlowPolicy OBJECT IDENTIFIER ::= { fkV2QoS4Flow 3 }

		
		-- 1.3.6.1.4.1.10428 9 1.102.10.2.2.3.1
		fkV2QoS4FlowPolicyTable OBJECT-TYPE
			SYNTAX SEQUENCE OF FkV2QoS4FlowPolicyEntry
			MAX-ACCESS not-accessible
			STATUS current
			DESCRIPTION
				"flow policy table."
			::= { fkV2QoS4FlowPolicy 1 }

		
		-- 1.3.6.1.4.1.10428 9 1.102.10.2.2.3.1.1
		fkV2QoS4FlowPolicyEntry OBJECT-TYPE
			SYNTAX FkV2QoS4FlowPolicyEntry
			MAX-ACCESS not-accessible
			STATUS current
			DESCRIPTION
				"key: fkV2QoS4FlowIndex, fkV2QoS4FlowPolicyIndex"
			INDEX { fkV2QoS4FlowIndex, fkV2QoS4FlowPolicyIndex }
			::= { fkV2QoS4FlowPolicyTable 1 }

		
		FkV2QoS4FlowPolicyEntry ::=
			SEQUENCE { 
				fkV2QoS4FlowPolicyIndex
					IntPolicyIndex,
				fkV2QoS4FlowPolicyID
					IntPolicyIndex,
				fkV2QoS4FlowPolicyName
					OctetName
			 }

		-- 1.3.6.1.4.1.10428 9 1.102.10.2.2.3.1.1.1
		fkV2QoS4FlowPolicyIndex OBJECT-TYPE
			SYNTAX IntPolicyIndex
			MAX-ACCESS read-only
			STATUS current
			DESCRIPTION
				"The index of the policy for the flow"
			::= { fkV2QoS4FlowPolicyEntry 1 }

		
		-- 1.3.6.1.4.1.10428 9 1.102.10.2.2.3.1.1.2
		fkV2QoS4FlowPolicyID OBJECT-TYPE
			SYNTAX IntPolicyIndex
			MAX-ACCESS read-only
			STATUS current
			DESCRIPTION
				"The identifier of the policy"
			::= { fkV2QoS4FlowPolicyEntry 2 }

		
		-- 1.3.6.1.4.1.10428 9 1.102.10.2.2.3.1.1.3
		fkV2QoS4FlowPolicyName OBJECT-TYPE
			SYNTAX OctetName
			MAX-ACCESS read-only
			STATUS current
			DESCRIPTION
				"The name of the policy"
			::= { fkV2QoS4FlowPolicyEntry 3 }

		
		-- 1.3.6.1.4.1.10428 9 1.102.10.2.3
		fkV2QoS4Class OBJECT IDENTIFIER ::= { fkV2QoS4 3 }

		
		-- 1.3.6.1.4.1.10428 9 1.102.10.2.3.1
		fkV2QoS4ClassInfo OBJECT IDENTIFIER ::= { fkV2QoS4Class 1 }

		
		-- 1.3.6.1.4.1.10428 9 1.102.10.2.3.1.1
		fkV2QoS4ClassTable OBJECT-TYPE
			SYNTAX SEQUENCE OF FkV2QoS4ClassEntry
			MAX-ACCESS not-accessible
			STATUS current
			DESCRIPTION
				"class table."
			::= { fkV2QoS4ClassInfo 1 }

		
		-- 1.3.6.1.4.1.10428 9 1.102.10.2.4.1.1.1
		fkV2QoS4ClassEntry OBJECT-TYPE
			SYNTAX FkV2QoS4ClassEntry
			MAX-ACCESS not-accessible
			STATUS current
			DESCRIPTION
				"key: fkV2QoS4ClassIndex"
			INDEX { fkV2QoS4ClassIndex }
			::= { fkV2QoS4ClassTable 1 }

		
		FkV2QoS4ClassEntry ::=
			SEQUENCE { 
				fkV2QoS4ClassIndex
					IntClassIndex,
				fkV2QoS4ClassName
					OctetName,
				fkV2QoS4ClassFlowCnt
					Counter32
			 }

		-- 1.3.6.1.4.1.10428 9 1.102.10.2.4.1.1.1.1
		fkV2QoS4ClassIndex OBJECT-TYPE
			SYNTAX IntClassIndex
			MAX-ACCESS read-only
			STATUS current
			DESCRIPTION
				"The index of class"
			::= { fkV2QoS4ClassEntry 1 }

		
		-- 1.3.6.1.4.1.10428 9 1.102.10.2.4.1.1.1.2
		fkV2QoS4ClassName OBJECT-TYPE
			SYNTAX OctetName
			MAX-ACCESS read-only
			STATUS current
			DESCRIPTION
				"The name of class"
			::= { fkV2QoS4ClassEntry 2 }

		
		-- 1.3.6.1.4.1.10428 9 1.102.10.2.4.1.1.1.3
		fkV2QoS4ClassFlowCnt OBJECT-TYPE
			SYNTAX Counter32
			MAX-ACCESS read-only
			STATUS current
			DESCRIPTION
				"The counter of flow in class"
			::= { fkV2QoS4ClassEntry 3 }

		
		-- 1.3.6.1.4.1.10428 9 1.102.10.2.3.1.2
		fkV2QoS4ClassControl OBJECT IDENTIFIER ::= { fkV2QoS4ClassInfo 2 }

		
		-- 1.3.6.1.4.1.10428 9 1.102.10.2.3.1.2.1
		fkV2QoS4ClassControlRequest OBJECT-TYPE
			SYNTAX INTEGER
				{
				createClass(1),
				destroyClass(2),
				destroyAllClass(3)
				}
			MAX-ACCESS read-write
			STATUS current
			DESCRIPTION
				"The request of a user command"
			::= { fkV2QoS4ClassControl 1 }

		
		-- 1.3.6.1.4.1.10428 9 1.102.10.2.3.1.2.2
		fkV2QoS4ClassControlStatus OBJECT-TYPE
			SYNTAX FkControlStatusType
			MAX-ACCESS read-only
			STATUS current
			DESCRIPTION
				"The status of user command"
			::= { fkV2QoS4ClassControl 2 }

		
		-- 1.3.6.1.4.1.10428 9 1.102.10.2.3.1.2.3
		fkV2QoS4ClassControlTimer OBJECT-TYPE
			SYNTAX Gauge32
			MAX-ACCESS read-write
			STATUS current
			DESCRIPTION
				"The maximum time for the manager for a long running user command"
			::= { fkV2QoS4ClassControl 3 }

		
		-- 1.3.6.1.4.1.10428 9 1.102.10.2.3.1.2.4
		fkV2QoS4ClassControlTimeStamp OBJECT-TYPE
			SYNTAX TimeTicks
			MAX-ACCESS read-only
			STATUS current
			DESCRIPTION
				"The time stamp of the last command(end of command)"
			::= { fkV2QoS4ClassControl 4 }

		
		-- 1.3.6.1.4.1.10428 9 1.102.10.2.3.1.2.5
		fkV2QoS4ClassControlReqResult OBJECT-TYPE
			SYNTAX FkControlRequestResultType
			MAX-ACCESS read-only
			STATUS current
			DESCRIPTION
				"The result of the last user command"
			::= { fkV2QoS4ClassControl 5 }

		
		-- 1.3.6.1.4.1.10428 9 1.102.10.2.3.1.2.6
		fkV2QoS4ClassControlIndex OBJECT-TYPE
			SYNTAX IntClassIndex
			MAX-ACCESS read-write
			STATUS current
			DESCRIPTION
				"The index of class"
			::= { fkV2QoS4ClassControl 6 }

		
		-- 1.3.6.1.4.1.10428 9 1.102.10.2.3.1.2.7
		fkV2QoS4ClassControlName OBJECT-TYPE
			SYNTAX OctetName
			MAX-ACCESS read-write
			STATUS current
			DESCRIPTION
				"The name of class"
			::= { fkV2QoS4ClassControl 7 }

		
		-- 1.3.6.1.4.1.10428 9 1.102.10.2.3.1.3
		fkV2QoS4ClassNotification OBJECT IDENTIFIER ::= { fkV2QoS4ClassInfo 3 }

		
		-- 1.3.6.1.4.1.10428 9 1.102.10.2.3.1.3.1
		fkClassCreated NOTIFICATION-TYPE
			OBJECTS { fkV2QoS4ClassControlRequest, fkV2QoS4ClassControlTimeStamp, fkV2QoS4ClassControlReqResult }
			STATUS current
			DESCRIPTION 
				"Description."
			::= { fkV2QoS4ClassNotification 1 }

		
		-- 1.3.6.1.4.1.10428 9 1.102.10.2.3.1.3.2
		fkClassDestroyed NOTIFICATION-TYPE
			OBJECTS { fkV2QoS4ClassControlRequest, fkV2QoS4ClassControlTimeStamp, fkV2QoS4ClassControlReqResult, fkV2QoS4ClassControlIndex }
			STATUS current
			DESCRIPTION 
				"Description."
			::= { fkV2QoS4ClassNotification 2 }

		
		-- 1.3.6.1.4.1.10428 9 1.102.10.2.3.1.3.3
		fkClassAllDestroyed NOTIFICATION-TYPE
			OBJECTS { fkV2QoS4ClassControlRequest, fkV2QoS4ClassControlTimeStamp, fkV2QoS4ClassControlReqResult }
			STATUS current
			DESCRIPTION 
				"Description."
			::= { fkV2QoS4ClassNotification 3 }

		
		-- 1.3.6.1.4.1.10428 9 1.102.10.2.3.2
		fkV2QoS4ClassFlow OBJECT IDENTIFIER ::= { fkV2QoS4Class 2 }

		
		-- 1.3.6.1.4.1.10428 9 1.102.10.2.3.2.1
		fkV2QoS4ClassFlowTable OBJECT-TYPE
			SYNTAX SEQUENCE OF FkV2QoS4ClassFlowEntry
			MAX-ACCESS not-accessible
			STATUS current
			DESCRIPTION
				"class flow table."
			::= { fkV2QoS4ClassFlow 1 }

		
		-- 1.3.6.1.4.1.10428 9 1.102.10.2.4.2.1.1
		fkV2QoS4ClassFlowEntry OBJECT-TYPE
			SYNTAX FkV2QoS4ClassFlowEntry
			MAX-ACCESS not-accessible
			STATUS current
			DESCRIPTION
				"key: fkV2QoS4ClassIndex, fkV2QoS4ClassFlowIndex"
			INDEX { fkV2QoS4ClassIndex, fkV2QoS4ClassFlowIndex }
			::= { fkV2QoS4ClassFlowTable 1 }

		
		FkV2QoS4ClassFlowEntry ::=
			SEQUENCE { 
				fkV2QoS4ClassFlowIndex
					IntFlowIndex,
				fkV2QoS4ClassFlowID
					IntFlowIndex,
				fkV2QoS4ClassFlowName
					OctetName
			 }

		-- 1.3.6.1.4.1.10428 9 1.102.10.2.4.2.1.1.1
		fkV2QoS4ClassFlowIndex OBJECT-TYPE
			SYNTAX IntFlowIndex
			MAX-ACCESS read-only
			STATUS current
			DESCRIPTION
				"The index of flow in class"
			::= { fkV2QoS4ClassFlowEntry 1 }

		
		-- 1.3.6.1.4.1.10428 9 1.102.10.2.4.2.1.1.2
		fkV2QoS4ClassFlowID OBJECT-TYPE
			SYNTAX IntFlowIndex
			MAX-ACCESS read-only
			STATUS current
			DESCRIPTION
				"The identifier of flow"
			::= { fkV2QoS4ClassFlowEntry 2 }

		
		-- 1.3.6.1.4.1.10428 9 1.102.10.2.4.2.1.1.3
		fkV2QoS4ClassFlowName OBJECT-TYPE
			SYNTAX OctetName
			MAX-ACCESS read-only
			STATUS current
			DESCRIPTION
				"The name of the flow"
			::= { fkV2QoS4ClassFlowEntry 3 }

		
		-- 1.3.6.1.4.1.10428 9 1.102.10.2.3.2.2
		fkV2QoS4ClassFlowControl OBJECT IDENTIFIER ::= { fkV2QoS4ClassFlow 2 }

		
		-- 1.3.6.1.4.1.10428 9 1.102.10.2.3.2.2.1
		fkV2QoS4ClassFlowControlRequest OBJECT-TYPE
			SYNTAX INTEGER
				{
				addFlow(1),
				deleteFlow(2),
				deleteAllFlow(3)
				}
			MAX-ACCESS read-write
			STATUS current
			DESCRIPTION
				"The request of a user command"
			::= { fkV2QoS4ClassFlowControl 1 }

		
		-- 1.3.6.1.4.1.10428 9 1.102.10.2.3.2.2.2
		fkV2QoS4ClassFlowControlStatus OBJECT-TYPE
			SYNTAX FkControlStatusType
			MAX-ACCESS read-only
			STATUS current
			DESCRIPTION
				"The status of user command"
			::= { fkV2QoS4ClassFlowControl 2 }

		
		-- 1.3.6.1.4.1.10428 9 1.102.10.2.3.2.2.3
		fkV2QoS4ClassFlowControlTimer OBJECT-TYPE
			SYNTAX Gauge32
			MAX-ACCESS read-write
			STATUS current
			DESCRIPTION
				"The maximum time for the manager for a long running user command"
			::= { fkV2QoS4ClassFlowControl 3 }

		
		-- 1.3.6.1.4.1.10428 9 1.102.10.2.3.2.2.4
		fkV2QoS4ClassFlowControlTimeStamp OBJECT-TYPE
			SYNTAX TimeTicks
			MAX-ACCESS read-only
			STATUS current
			DESCRIPTION
				"The time stamp of the last command(end of command)"
			::= { fkV2QoS4ClassFlowControl 4 }

		
		-- 1.3.6.1.4.1.10428 9 1.102.10.2.3.2.2.5
		fkV2QoS4ClassFlowControlReqResult OBJECT-TYPE
			SYNTAX FkControlRequestResultType
			MAX-ACCESS read-only
			STATUS current
			DESCRIPTION
				"The result of the last user command"
			::= { fkV2QoS4ClassFlowControl 5 }

		
		-- 1.3.6.1.4.1.10428 9 1.102.10.2.3.2.2.6
		fkV2QoS4ClassFlowControlClassIndex OBJECT-TYPE
			SYNTAX IntClassIndex
			MAX-ACCESS read-write
			STATUS current
			DESCRIPTION
				"The index of class"
			::= { fkV2QoS4ClassFlowControl 6 }

		
		-- 1.3.6.1.4.1.10428 9 1.102.10.2.3.2.2.7
		fkV2QoS4ClassFlowControlFlowIndex OBJECT-TYPE
			SYNTAX IntFlowIndex
			MAX-ACCESS read-write
			STATUS current
			DESCRIPTION
				"The index of flow in this class"
			::= { fkV2QoS4ClassFlowControl 7 }

		
		-- 1.3.6.1.4.1.10428 9 1.102.10.2.3.2.2.8
		fkV2QoS4ClassFlowControlFlowID OBJECT-TYPE
			SYNTAX IntFlowIndex
			MAX-ACCESS read-write
			STATUS current
			DESCRIPTION
				"The index of flow
				Refer to fkV2QoS4FlowIndex
				"
			::= { fkV2QoS4ClassFlowControl 8 }

		
		-- 1.3.6.1.4.1.10428 9 1.102.10.2.3.2.3
		fkV2QoS4ClassFlowNotification OBJECT IDENTIFIER ::= { fkV2QoS4ClassFlow 3 }

		
		-- 1.3.6.1.4.1.10428 9 1.102.10.2.3.2.3.1
		fkClassFlowAdded NOTIFICATION-TYPE
			OBJECTS { fkV2QoS4ClassFlowControlRequest, fkV2QoS4ClassFlowControlTimeStamp, fkV2QoS4ClassFlowControlReqResult, fkV2QoS4ClassFlowID }
			STATUS current
			DESCRIPTION 
				"Description."
			::= { fkV2QoS4ClassFlowNotification 1 }

		
		-- 1.3.6.1.4.1.10428 9 1.102.10.2.3.2.3.2
		fkClassFlowDeleted NOTIFICATION-TYPE
			OBJECTS { fkV2QoS4ClassFlowControlRequest, fkV2QoS4ClassFlowControlTimeStamp, fkV2QoS4ClassFlowControlReqResult, fkV2QoS4ClassFlowControlClassIndex, fkV2QoS4ClassFlowControlFlowIndex
				 }
			STATUS current
			DESCRIPTION 
				"Description."
			::= { fkV2QoS4ClassFlowNotification 2 }

		
		-- 1.3.6.1.4.1.10428 9 1.102.10.2.3.2.3.3
		fkClassFlowAllDeleted NOTIFICATION-TYPE
			OBJECTS { fkV2QoS4ClassFlowControlRequest, fkV2QoS4ClassFlowControlTimeStamp, fkV2QoS4ClassFlowControlReqResult, fkV2QoS4ClassFlowControlClassIndex }
			STATUS current
			DESCRIPTION 
				"Description."
			::= { fkV2QoS4ClassFlowNotification 3 }

		
		-- 1.3.6.1.4.1.10428 9 1.102.10.2.3.3
		fkV2QoS4ClassPolicy OBJECT IDENTIFIER ::= { fkV2QoS4Class 3 }

		
		-- 1.3.6.1.4.1.10428 9 1.102.10.2.3.3.1
		fkV2QoS4ClassPolicyTable OBJECT-TYPE
			SYNTAX SEQUENCE OF FkV2QoS4ClassPolicyEntry
			MAX-ACCESS not-accessible
			STATUS current
			DESCRIPTION
				"class policy table."
			::= { fkV2QoS4ClassPolicy 1 }

		
		-- 1.3.6.1.4.1.10428 9 1.102.10.2.4.3.1.1
		fkV2QoS4ClassPolicyEntry OBJECT-TYPE
			SYNTAX FkV2QoS4ClassPolicyEntry
			MAX-ACCESS not-accessible
			STATUS current
			DESCRIPTION
				"key: fkV2QoS4ClassIndex, fkV2QoS4ClassPolicyIndex"
			INDEX { fkV2QoS4ClassIndex, fkV2QoS4ClassPolicyIndex }
			::= { fkV2QoS4ClassPolicyTable 1 }

		
		FkV2QoS4ClassPolicyEntry ::=
			SEQUENCE { 
				fkV2QoS4ClassPolicyIndex
					IntPolicyIndex,
				fkV2QoS4ClassPolicyID
					IntPolicyIndex,
				fkV2QoS4ClassPolicyName
					OctetName
			 }

		-- 1.3.6.1.4.1.10428 9 1.102.10.2.4.3.1.1.1
		fkV2QoS4ClassPolicyIndex OBJECT-TYPE
			SYNTAX IntPolicyIndex
			MAX-ACCESS read-only
			STATUS current
			DESCRIPTION
				"The index of the policy for the class"
			::= { fkV2QoS4ClassPolicyEntry 1 }

		
		-- 1.3.6.1.4.1.10428 9 1.102.10.2.4.3.1.1.2
		fkV2QoS4ClassPolicyID OBJECT-TYPE
			SYNTAX IntPolicyIndex
			MAX-ACCESS read-only
			STATUS current
			DESCRIPTION
				"The identifier of the policy"
			::= { fkV2QoS4ClassPolicyEntry 2 }

		
		-- 1.3.6.1.4.1.10428 9 1.102.10.2.4.3.1.1.3
		fkV2QoS4ClassPolicyName OBJECT-TYPE
			SYNTAX OctetName
			MAX-ACCESS read-only
			STATUS current
			DESCRIPTION
				"The name of the policy"
			::= { fkV2QoS4ClassPolicyEntry 3 }

		
		-- 1.3.6.1.4.1.10428 9 1.102.10.2.4
		fkV2QoS4Policer OBJECT IDENTIFIER ::= { fkV2QoS4 4 }

		
		-- 1.3.6.1.4.1.10428 9 1.102.10.2.4.1
		fkV2QoS4PolicerInfo OBJECT IDENTIFIER ::= { fkV2QoS4Policer 1 }

		
		-- 1.3.6.1.4.1.10428 9 1.102.10.2.4.1.1
		fkV2QoS4PolicerTable OBJECT-TYPE
			SYNTAX SEQUENCE OF FkV2QoS4PolicerEntry
			MAX-ACCESS not-accessible
			STATUS current
			DESCRIPTION
				"policer table."
			::= { fkV2QoS4PolicerInfo 1 }

		
		-- 1.3.6.1.4.1.10428 9 1.102.10.2.4.1.1.1
		fkV2QoS4PolicerEntry OBJECT-TYPE
			SYNTAX FkV2QoS4PolicerEntry
			MAX-ACCESS not-accessible
			STATUS current
			DESCRIPTION
				"key: fkV2QoS4PolicerIndex"
			INDEX { fkV2QoS4PolicerIndex }
			::= { fkV2QoS4PolicerTable 1 }

		
		FkV2QoS4PolicerEntry ::=
			SEQUENCE { 
				fkV2QoS4PolicerIndex
					IntPolicerIndex,
				fkV2QoS4PolicerName
					OctetName,
				fkV2QoS4PolicerMeterMode
					IntMeterMode,
				fkV2QoS4PolicerRateLimit
					Integer32,
				fkV2QoS4PolicerColorType
					IntColorType,
				fkV2QoS4PolicerColorMode
					IntColorMode,
				fkV2QoS4PolicerColorAwareMode
					IntColorAwareMode,
				fkV2QoS4PolicerColorCIR
					IntColorCIR,
				fkV2QoS4PolicerColorCBS
					IntColorCBS,
				fkV2QoS4PolicerColorPIR
					IntColorPIR,
				fkV2QoS4PolicerColorPBS
					IntColorPBS,
				fkV2QoS4PolicerColorEBS
					IntColorEBS,
				fkV2QoS4PolicerColorRedAction
					IntColorAction,
				fkV2QoS4PolicerColorYellowAction
					IntColorAction,
				fkV2QoS4PolicerColorGreenAction
					IntColorAction,
				fkV2QoS4PolicerRemarkLayerMode
					BITS,
				fkV2QoS4PolicerRemarkMode
					BITS,
				fkV2QoS4PolicerCounterMode
					IntCounterMode,
				fkV2QoS4PolicerAvrgCounterMode
					IntAvrgCounterMode,
				fkV2QoS4PolicerMinBandwidth
					Integer32,
				fkV2QoS4PolicerMaxBandwidth
					Integer32,
				fkV2QoS4PolicerColorRedDscp
					IntDscp,
				fkV2QoS4PolicerColorYellowDscp
					IntDscp,
				fkV2QoS4PolicerColorGreenDscp
					IntDscp,
				fkV2QoS4PolicerColorRedCosType
					INTEGER,
				fkV2QoS4PolicerColorRedCos
					IntCoS,
				fkV2QoS4PolicerColorYellowCosType
					INTEGER,
				fkV2QoS4PolicerColorYellowCos
					IntToS,
				fkV2QoS4PolicerColorGreenCosType
					INTEGER,
				fkV2QoS4PolicerColorGreenCos
					IntToS
			 }

		-- 1.3.6.1.4.1.10428 9 1.102.10.2.4.1.1.1.1
		fkV2QoS4PolicerIndex OBJECT-TYPE
			SYNTAX IntPolicerIndex
			MAX-ACCESS read-only
			STATUS current
			DESCRIPTION
				"The index of policer"
			::= { fkV2QoS4PolicerEntry 1 }

		
		-- 1.3.6.1.4.1.10428 9 1.102.10.2.4.1.1.1.2
		fkV2QoS4PolicerName OBJECT-TYPE
			SYNTAX OctetName
			MAX-ACCESS read-only
			STATUS current
			DESCRIPTION
				"The name of policer"
			::= { fkV2QoS4PolicerEntry 2 }

		
		-- 1.3.6.1.4.1.10428 9 1.102.10.2.4.1.1.1.3
		fkV2QoS4PolicerMeterMode OBJECT-TYPE
			SYNTAX IntMeterMode
			MAX-ACCESS read-only
			STATUS current
			DESCRIPTION
				"The meter mode.
				*) According to this value, rate-limit, color-marking and min-max-bandwidth exclusively activated.
				The value of -1 means nothing(not set)
				"
			::= { fkV2QoS4PolicerEntry 3 }

		
		-- 1.3.6.1.4.1.10428 9 1.102.10.2.4.1.1.1.4
		fkV2QoS4PolicerRateLimit OBJECT-TYPE
			SYNTAX Integer32
			MAX-ACCESS read-write
			STATUS current
			DESCRIPTION
				"The packet rate limit
				The value of -1 unlimit(not set)
				"
			::= { fkV2QoS4PolicerEntry 4 }

		
		-- 1.3.6.1.4.1.10428 9 1.102.10.2.4.1.1.1.5
		fkV2QoS4PolicerColorType OBJECT-TYPE
			SYNTAX IntColorType
			MAX-ACCESS read-only
			STATUS current
			DESCRIPTION
				"Color marking type
				Available Value : srTCM or trTCM
				srTCM = Single Rate Three Color Marking
				trTCM = Two Rate Three Color Marking
				The value of -1 means nothing(not set)
				"
			::= { fkV2QoS4PolicerEntry 5 }

		
		-- 1.3.6.1.4.1.10428 9 1.102.10.2.4.1.1.1.6
		fkV2QoS4PolicerColorMode OBJECT-TYPE
			SYNTAX IntColorMode
			MAX-ACCESS read-only
			STATUS current
			DESCRIPTION
				"Color marking mode.
				The value of -1 means nothing(not set)
				"
			::= { fkV2QoS4PolicerEntry 6 }

		
		-- 1.3.6.1.4.1.10428 9 1.102.10.2.4.1.1.1.7
		fkV2QoS4PolicerColorAwareMode OBJECT-TYPE
			SYNTAX IntColorAwareMode
			MAX-ACCESS read-only
			STATUS current
			DESCRIPTION
				"Color marking aware mode
				*) Used only when fkV2QoS4PolicerColorMode is aware
				The value of -1 is nothing(not set)
				"
			::= { fkV2QoS4PolicerEntry 7 }

		
		-- 1.3.6.1.4.1.10428 9 1.102.10.2.4.1.1.1.8
		fkV2QoS4PolicerColorCIR OBJECT-TYPE
			SYNTAX IntColorCIR
			MAX-ACCESS read-only
			STATUS current
			DESCRIPTION
				"Committed Information Rate.
				The value is in unit for 64 kbps.
				The value of -1 is nothing(not set)
				"
			::= { fkV2QoS4PolicerEntry 8 }

		
		-- 1.3.6.1.4.1.10428 9 1.102.10.2.4.1.1.1.9
		fkV2QoS4PolicerColorCBS OBJECT-TYPE
			SYNTAX IntColorCBS
			MAX-ACCESS read-only
			STATUS current
			DESCRIPTION
				"Committed Burst Size.
				The value is in unit for square of 2 bits
				The value of -1 is nothing(not set)
				"
			::= { fkV2QoS4PolicerEntry 9 }

		
		-- 1.3.6.1.4.1.10428 9 1.102.10.2.4.1.1.1.10
		fkV2QoS4PolicerColorPIR OBJECT-TYPE
			SYNTAX IntColorPIR
			MAX-ACCESS read-only
			STATUS current
			DESCRIPTION
				"Peak Information Rate. 
				*) Used only when fkV2QoS4PolicerColorType is trTCM.
				The value is in unit for 64 kbps.
				The value of -1 is nothing(not set)
				"
			::= { fkV2QoS4PolicerEntry 10 }

		
		-- 1.3.6.1.4.1.10428 9 1.102.10.2.4.1.1.1.11
		fkV2QoS4PolicerColorPBS OBJECT-TYPE
			SYNTAX IntColorPBS
			MAX-ACCESS read-only
			STATUS current
			DESCRIPTION
				"Peak Burst Size. 
				*) Used only when fkV2QoS4PolicerColorType is trTCM.
				The value is in unit for square of 2 bits.
				The value of -1 is nothing(not set)
				"
			::= { fkV2QoS4PolicerEntry 11 }

		
		-- 1.3.6.1.4.1.10428 9 1.102.10.2.4.1.1.1.12
		fkV2QoS4PolicerColorEBS OBJECT-TYPE
			SYNTAX IntColorEBS
			MAX-ACCESS read-only
			STATUS current
			DESCRIPTION
				"Excess Burst Size. 
				*) Used only when fkV2QoS4PolicerColorType is srTCM.
				The value is in unit for square of 2 bits.
				The value of -1 is nothing(not set)
				"
			::= { fkV2QoS4PolicerEntry 12 }

		
		-- 1.3.6.1.4.1.10428 9 1.102.10.2.4.1.1.1.13
		fkV2QoS4PolicerColorRedAction OBJECT-TYPE
			SYNTAX IntColorAction
			MAX-ACCESS read-only
			STATUS current
			DESCRIPTION
				"The action to be apply when incoming packet is colored in red.
				The value of -1 is nothing(not set)
				"
			::= { fkV2QoS4PolicerEntry 13 }

		
		-- 1.3.6.1.4.1.10428 9 1.102.10.2.4.1.1.1.14
		fkV2QoS4PolicerColorYellowAction OBJECT-TYPE
			SYNTAX IntColorAction
			MAX-ACCESS read-only
			STATUS current
			DESCRIPTION
				"The action to be apply when incoming packet is colored in yellow.
				The value of -1 is nothing(not set)
				"
			::= { fkV2QoS4PolicerEntry 14 }

		
		-- 1.3.6.1.4.1.10428 9 1.102.10.2.4.1.1.1.15
		fkV2QoS4PolicerColorGreenAction OBJECT-TYPE
			SYNTAX IntColorAction
			MAX-ACCESS read-only
			STATUS current
			DESCRIPTION
				"The action to be apply when incoming packet is colored in green. (not supported)
				The value of -1 is nothing(not set)
				"
			::= { fkV2QoS4PolicerEntry 15 }

		
		-- 1.3.6.1.4.1.10428 9 1.102.10.2.4.1.1.1.16
		fkV2QoS4PolicerRemarkLayerMode OBJECT-TYPE
			SYNTAX BITS
				{
				remarkByDSCP(0),
				remarkByQueueOrCoS(1)
				}
			MAX-ACCESS read-only
			STATUS current
			DESCRIPTION
				"The remark mode
				0 : Layer3
				1 : Layer2
				"
			::= { fkV2QoS4PolicerEntry 16 }

		
		-- 1.3.6.1.4.1.10428 9 1.102.10.2.4.1.1.1.17
		fkV2QoS4PolicerRemarkMode OBJECT-TYPE
			SYNTAX BITS
				{
				remarkQueue(0),
				remarkExtCoS(1)
				}
			MAX-ACCESS read-only
			STATUS current
			DESCRIPTION
				"This value is available when fkV2QoS4PolicerRemarkLayerMode bit was checked(one or more)
				0 : remark Queue
				1 : remark External CoS
				"
			::= { fkV2QoS4PolicerEntry 17 }

		
		-- 1.3.6.1.4.1.10428 9 1.102.10.2.4.1.1.1.18
		fkV2QoS4PolicerCounterMode OBJECT-TYPE
			SYNTAX IntCounterMode
			MAX-ACCESS read-only
			STATUS current
			DESCRIPTION
				"The counter mode
				The value of -1 is nothing(not set)
				"
			::= { fkV2QoS4PolicerEntry 18 }

		
		-- 1.3.6.1.4.1.10428 9 1.102.10.2.4.1.1.1.19
		fkV2QoS4PolicerAvrgCounterMode OBJECT-TYPE
			SYNTAX IntAvrgCounterMode
			MAX-ACCESS read-only
			STATUS current
			DESCRIPTION
				"The average counter mode
				The value of -1 is nothing(not set)
				"
			::= { fkV2QoS4PolicerEntry 19 }

		
		-- 1.3.6.1.4.1.10428 9 1.102.10.2.4.1.1.1.20
		fkV2QoS4PolicerMinBandwidth OBJECT-TYPE
			SYNTAX Integer32
			MAX-ACCESS read-only
			STATUS current
			DESCRIPTION
				"The minium bandwidth"
			::= { fkV2QoS4PolicerEntry 20 }

		
		-- 1.3.6.1.4.1.10428 9 1.102.10.2.4.1.1.1.21
		fkV2QoS4PolicerMaxBandwidth OBJECT-TYPE
			SYNTAX Integer32
			MAX-ACCESS read-only
			STATUS current
			DESCRIPTION
				"The maximum bandwidth"
			::= { fkV2QoS4PolicerEntry 21 }

		
		-- 1.3.6.1.4.1.10428 9 1.102.10.2.4.1.1.1.22
		fkV2QoS4PolicerColorRedDscp OBJECT-TYPE
			SYNTAX IntDscp
			MAX-ACCESS read-only
			STATUS current
			DESCRIPTION
				"The desc value to be apply when incoming packet is colored in red.
				Default : 30(0x1e)
				"
			DEFVAL { 30 }
			::= { fkV2QoS4PolicerEntry 22 }

		
		-- 1.3.6.1.4.1.10428 9 1.102.10.2.4.1.1.1.23
		fkV2QoS4PolicerColorYellowDscp OBJECT-TYPE
			SYNTAX IntDscp
			MAX-ACCESS read-only
			STATUS current
			DESCRIPTION
				"The desc value to be apply when incoming packet is colored in yellow.
				Default : 28(0x1c)
				"
			DEFVAL { 28 }
			::= { fkV2QoS4PolicerEntry 23 }

		
		-- 1.3.6.1.4.1.10428 9 1.102.10.2.4.1.1.1.24
		fkV2QoS4PolicerColorGreenDscp OBJECT-TYPE
			SYNTAX IntDscp
			MAX-ACCESS read-only
			STATUS current
			DESCRIPTION
				"The desc value to be apply when incoming packet is colored in green.
				Default : 30(0x1a)
				"
			DEFVAL { 26 }
			::= { fkV2QoS4PolicerEntry 24 }

		
		-- 1.3.6.1.4.1.10428 9 1.102.10.2.4.1.1.1.25
		fkV2QoS4PolicerColorRedCosType OBJECT-TYPE
			SYNTAX INTEGER
				{
				none(0),
				mark(1),
				overwrite(2)
				}
			MAX-ACCESS read-only
			STATUS current
			DESCRIPTION
				"The CoS type colored in red."
			::= { fkV2QoS4PolicerEntry 25 }

		
		-- 1.3.6.1.4.1.10428 9 1.102.10.2.4.1.1.1.26
		fkV2QoS4PolicerColorRedCos OBJECT-TYPE
			SYNTAX IntCoS
			MAX-ACCESS read-only
			STATUS current
			DESCRIPTION
				"The CoS colored in red."
			::= { fkV2QoS4PolicerEntry 26 }

		
		-- 1.3.6.1.4.1.10428 9 1.102.10.2.4.1.1.1.27
		fkV2QoS4PolicerColorYellowCosType OBJECT-TYPE
			SYNTAX INTEGER
				{
				none(0),
				mark(1),
				overwrite(2)
				}
			MAX-ACCESS read-only
			STATUS current
			DESCRIPTION
				"The CoS type colored in yellow"
			::= { fkV2QoS4PolicerEntry 27 }

		
		-- 1.3.6.1.4.1.10428 9 1.102.10.2.4.1.1.1.28
		fkV2QoS4PolicerColorYellowCos OBJECT-TYPE
			SYNTAX IntToS
			MAX-ACCESS read-only
			STATUS current
			DESCRIPTION
				"The CoS colored in yellow."
			::= { fkV2QoS4PolicerEntry 28 }

		
		-- 1.3.6.1.4.1.10428 9 1.102.10.2.4.1.1.1.29
		fkV2QoS4PolicerColorGreenCosType OBJECT-TYPE
			SYNTAX INTEGER
				{
				none(0),
				mark(1),
				overwrite(2)
				}
			MAX-ACCESS read-only
			STATUS current
			DESCRIPTION
				"The CoS type colored in yellow"
			::= { fkV2QoS4PolicerEntry 29 }

		
		-- 1.3.6.1.4.1.10428 9 1.102.10.2.4.1.1.1.30
		fkV2QoS4PolicerColorGreenCos OBJECT-TYPE
			SYNTAX IntToS
			MAX-ACCESS read-only
			STATUS current
			DESCRIPTION
				"The CoS colored in green."
			::= { fkV2QoS4PolicerEntry 30 }

		
		-- 1.3.6.1.4.1.10428 9 1.102.10.2.4.1.2
		fkV2QoS4PolicerControl OBJECT IDENTIFIER ::= { fkV2QoS4PolicerInfo 2 }

		
		-- 1.3.6.1.4.1.10428 9 1.102.10.2.4.1.2.1
		fkV2QoS4PolicerControlRequest OBJECT-TYPE
			SYNTAX INTEGER
				{
				createPolicer(1),
				modifyPolicer(2),
				destroyPolicer(3)
				}
			MAX-ACCESS read-write
			STATUS current
			DESCRIPTION
				"The request of a user command"
			::= { fkV2QoS4PolicerControl 1 }

		
		-- 1.3.6.1.4.1.10428 9 1.102.10.2.4.1.2.2
		fkV2QoS4PolicerControlStatus OBJECT-TYPE
			SYNTAX FkControlStatusType
			MAX-ACCESS read-only
			STATUS current
			DESCRIPTION
				"The status of user command"
			::= { fkV2QoS4PolicerControl 2 }

		
		-- 1.3.6.1.4.1.10428 9 1.102.10.2.4.1.2.3
		fkV2QoS4PolicerControlTimer OBJECT-TYPE
			SYNTAX Gauge32
			MAX-ACCESS read-write
			STATUS current
			DESCRIPTION
				"The maximum time for the manager for a long running user command"
			::= { fkV2QoS4PolicerControl 3 }

		
		-- 1.3.6.1.4.1.10428 9 1.102.10.2.4.1.2.4
		fkV2QoS4PolicerControlTimeStamp OBJECT-TYPE
			SYNTAX TimeTicks
			MAX-ACCESS read-only
			STATUS current
			DESCRIPTION
				"The time stamp of the last command(end of command)"
			::= { fkV2QoS4PolicerControl 4 }

		
		-- 1.3.6.1.4.1.10428 9 1.102.10.2.4.1.2.5
		fkV2QoS4PolicerControlReqResult OBJECT-TYPE
			SYNTAX FkControlRequestResultType
			MAX-ACCESS read-only
			STATUS current
			DESCRIPTION
				"The result of the last user command"
			::= { fkV2QoS4PolicerControl 5 }

		
		-- 1.3.6.1.4.1.10428 9 1.102.10.2.4.1.2.6
		fkV2QoS4PolicerControlIndex OBJECT-TYPE
			SYNTAX IntPolicerIndex
			MAX-ACCESS read-write
			STATUS current
			DESCRIPTION
				"The index of policer"
			::= { fkV2QoS4PolicerControl 6 }

		
		-- 1.3.6.1.4.1.10428 9 1.102.10.2.4.1.2.7
		fkV2QoS4PolicerControlName OBJECT-TYPE
			SYNTAX OctetName
			MAX-ACCESS read-write
			STATUS current
			DESCRIPTION
				"The name of policer"
			::= { fkV2QoS4PolicerControl 7 }

		
		-- 1.3.6.1.4.1.10428 9 1.102.10.2.4.1.2.8
		fkV2QoS4PolicerControlMeterMode OBJECT-TYPE
			SYNTAX IntMeterMode
			MAX-ACCESS read-write
			STATUS current
			DESCRIPTION
				"The meter mode.
				*) According to this value, rate-limit and color-marking exclusively activated.
				The value of -1 means nothing(not set)
				"
			::= { fkV2QoS4PolicerControl 8 }

		
		-- 1.3.6.1.4.1.10428 9 1.102.10.2.4.1.2.9
		fkV2QoS4PolicerControlRateLimit OBJECT-TYPE
			SYNTAX Integer32
			MAX-ACCESS read-write
			STATUS current
			DESCRIPTION
				"The packet rate limit
				The value of -1 unlimit(not set)
				"
			::= { fkV2QoS4PolicerControl 9 }

		
		-- 1.3.6.1.4.1.10428 9 1.102.10.2.4.1.2.10
		fkV2QoS4PolicerControlColorType OBJECT-TYPE
			SYNTAX IntColorType
			MAX-ACCESS read-write
			STATUS current
			DESCRIPTION
				"Color marking type
				Available Value : srTCM or trTCM
				srTCM = Single Rate Three Color Marking
				trTCM = Two Rate Three Color Marking
				The value of -1 is nothing(not set)
				"
			::= { fkV2QoS4PolicerControl 10 }

		
		-- 1.3.6.1.4.1.10428 9 1.102.10.2.4.1.2.11
		fkV2QoS4PolicerControlColorMode OBJECT-TYPE
			SYNTAX IntColorMode
			MAX-ACCESS read-write
			STATUS current
			DESCRIPTION
				"Color marking mode.
				*) Used only when fkColorMarkingMode is aware
				The value of -1 means nothing(not set)
				"
			::= { fkV2QoS4PolicerControl 11 }

		
		-- 1.3.6.1.4.1.10428 9 1.102.10.2.4.1.2.12
		fkV2QoS4PolicerControlColorAwareMode OBJECT-TYPE
			SYNTAX IntColorAwareMode
			MAX-ACCESS read-write
			STATUS current
			DESCRIPTION
				"Color marking aware mode
				The value of -1 is nothing(not set)
				"
			::= { fkV2QoS4PolicerControl 12 }

		
		-- 1.3.6.1.4.1.10428 9 1.102.10.2.4.1.2.13
		fkV2QoS4PolicerControlColorCIR OBJECT-TYPE
			SYNTAX IntColorCIR
			MAX-ACCESS read-write
			STATUS current
			DESCRIPTION
				"Committed Information Rate.
				The value is in unit for 64 kbps.
				The value of -1 is nothing(not set)
				
				"
			::= { fkV2QoS4PolicerControl 13 }

		
		-- 1.3.6.1.4.1.10428 9 1.102.10.2.4.1.2.14
		fkV2QoS4PolicerControlColorCBS OBJECT-TYPE
			SYNTAX IntColorCBS
			MAX-ACCESS read-write
			STATUS current
			DESCRIPTION
				"Committed Burst Size.
				The value is in unit for square of 2 bits
				The value of -1 is nothing(not set)
				"
			::= { fkV2QoS4PolicerControl 14 }

		
		-- 1.3.6.1.4.1.10428 9 1.102.10.2.4.1.2.15
		fkV2QoS4PolicerControlColorPIR OBJECT-TYPE
			SYNTAX IntColorPIR
			MAX-ACCESS read-write
			STATUS current
			DESCRIPTION
				"Peak Information Rate. 
				*) Used only when fkV2QoS4PolicerColorMode is Aware.
				The value is in unit for 64 kbps.
				The value of -1 is nothing(not set)
				"
			::= { fkV2QoS4PolicerControl 15 }

		
		-- 1.3.6.1.4.1.10428 9 1.102.10.2.4.1.2.16
		fkV2QoS4PolicerControlColorPBS OBJECT-TYPE
			SYNTAX IntColorPBS
			MAX-ACCESS read-write
			STATUS current
			DESCRIPTION
				"Peak Burst Size. 
				*) Used only when fkV2QoS4PolicerColorMode is Aware.
				The value is in unit for square of 2 bits.
				The value of -1 is nothing(not set)
				"
			::= { fkV2QoS4PolicerControl 16 }

		
		-- 1.3.6.1.4.1.10428 9 1.102.10.2.4.1.2.17
		fkV2QoS4PolicerControlColorEBS OBJECT-TYPE
			SYNTAX IntColorEBS
			MAX-ACCESS read-write
			STATUS current
			DESCRIPTION
				"Excess Burst Size. 
				*) Used only when fkV2QoS4PolicerColorMode is Blind.
				The value is in unit for square of 2 bits.
				The value of -1 is nothing(not set)
				"
			::= { fkV2QoS4PolicerControl 17 }

		
		-- 1.3.6.1.4.1.10428 9 1.102.10.2.4.1.2.18
		fkV2QoS4PolicerControlColorRedAction OBJECT-TYPE
			SYNTAX IntColorAction
			MAX-ACCESS read-write
			STATUS current
			DESCRIPTION
				"The action to be apply when incoming packet is colored in red.
				The value of -1 is nothing(not set)
				"
			::= { fkV2QoS4PolicerControl 18 }

		
		-- 1.3.6.1.4.1.10428 9 1.102.10.2.4.1.2.19
		fkV2QoS4PolicerControlColorYellowAction OBJECT-TYPE
			SYNTAX IntColorAction
			MAX-ACCESS read-write
			STATUS current
			DESCRIPTION
				"The action to be apply when incoming packet is colored in yellow.
				The value of -1 is nothing(not set)
				"
			::= { fkV2QoS4PolicerControl 19 }

		
		-- 1.3.6.1.4.1.10428 9 1.102.10.2.4.1.2.20
		fkV2QoS4PolicerControlColorGreenAction OBJECT-TYPE
			SYNTAX IntColorAction
			MAX-ACCESS read-write
			STATUS current
			DESCRIPTION
				"The action to be apply when incoming packet is colored in green. (not supported)
				The value of -1 is nothing(not set)
				"
			::= { fkV2QoS4PolicerControl 20 }

		
		-- 1.3.6.1.4.1.10428 9 1.102.10.2.4.1.2.21
		fkV2QoS4PolicerControlRemarkLayerMode OBJECT-TYPE
			SYNTAX BITS
				{
				remarkByDSCP(0),
				remarkByQueueOrCoS(1)
				}
			MAX-ACCESS read-write
			STATUS current
			DESCRIPTION
				"The remark mode
				0 : Layer3
				1 : Layer2
				"
			::= { fkV2QoS4PolicerControl 21 }

		
		-- 1.3.6.1.4.1.10428 9 1.102.10.2.4.1.2.22
		fkV2QoS4PolicerControlRemarkMode OBJECT-TYPE
			SYNTAX BITS
				{
				remarkQueue(0),
				remarkExtCoS(1)
				}
			MAX-ACCESS read-only
			STATUS current
			DESCRIPTION
				"This value is available when fkV2QoS4PolicerControlRemarkLayerMode bit was checked(one or more)
				0 : remark to Queue
				1 : remark to External CoS
				"
			::= { fkV2QoS4PolicerControl 22 }

		
		-- 1.3.6.1.4.1.10428 9 1.102.10.2.4.1.2.23
		fkV2QoS4PolicerControlCounterMode OBJECT-TYPE
			SYNTAX IntCounterMode
			MAX-ACCESS read-write
			STATUS current
			DESCRIPTION
				"The counter mode
				The value of -1 is nothing(not set)
				"
			::= { fkV2QoS4PolicerControl 23 }

		
		-- 1.3.6.1.4.1.10428 9 1.102.10.2.4.1.2.24
		fkV2QoS4PolicerControlAvrgCounterMode OBJECT-TYPE
			SYNTAX IntAvrgCounterMode
			MAX-ACCESS read-write
			STATUS current
			DESCRIPTION
				"The average counter mode
				The value of -1 is nothing(not set)
				"
			::= { fkV2QoS4PolicerControl 24 }

		
		-- 1.3.6.1.4.1.10428 9 1.102.10.2.4.1.2.25
		fkV2QoS4PolicerControlMinBandwidth OBJECT-TYPE
			SYNTAX Integer32
			MAX-ACCESS read-write
			STATUS current
			DESCRIPTION
				"The minimum bandwidth"
			::= { fkV2QoS4PolicerControl 25 }

		
		-- 1.3.6.1.4.1.10428 9 1.102.10.2.4.1.2.26
		fkV2QoS4PolicerControlMaxBandwidth OBJECT-TYPE
			SYNTAX Integer32
			MAX-ACCESS read-write
			STATUS current
			DESCRIPTION
				"The maximum bandwidth"
			::= { fkV2QoS4PolicerControl 26 }

		
		-- 1.3.6.1.4.1.10428 9 1.102.10.2.4.1.2.27
		fkV2QoS4PolicerControlColorRedDscp OBJECT-TYPE
			SYNTAX IntDscp
			MAX-ACCESS read-write
			STATUS current
			DESCRIPTION
				"The dscp value to be apply when incoming packet is colored in red"
			::= { fkV2QoS4PolicerControl 27 }

		
		-- 1.3.6.1.4.1.10428 9 1.102.10.2.4.1.2.28
		fkV2QoS4PolicerControlColorYellowDscp OBJECT-TYPE
			SYNTAX IntDscp
			MAX-ACCESS read-write
			STATUS current
			DESCRIPTION
				"The dscp value to be apply when incoming packet is colored in yellow"
			::= { fkV2QoS4PolicerControl 28 }

		
		-- 1.3.6.1.4.1.10428 9 1.102.10.2.4.1.2.29
		fkV2QoS4PolicerControlColorGreenDscp OBJECT-TYPE
			SYNTAX IntDscp
			MAX-ACCESS read-write
			STATUS current
			DESCRIPTION
				"The dscp value to be apply when incoming packet is colored in green"
			::= { fkV2QoS4PolicerControl 29 }

		
		-- 1.3.6.1.4.1.10428 9 1.102.10.2.4.1.2.30
		fkV2QoS4PolicerControlColorRedCosType OBJECT-TYPE
			SYNTAX INTEGER
				{
				none(0),
				mark(1),
				overwrite(2)
				}
			MAX-ACCESS read-write
			STATUS current
			DESCRIPTION
				"The CoS type colored in red."
			::= { fkV2QoS4PolicerControl 30 }

		
		-- 1.3.6.1.4.1.10428 9 1.102.10.2.4.1.2.31
		fkV2QoS4PolicerControlColorRedCos OBJECT-TYPE
			SYNTAX IntCoS
			MAX-ACCESS read-write
			STATUS current
			DESCRIPTION
				"The CoS colored in red."
			::= { fkV2QoS4PolicerControl 31 }

		
		-- 1.3.6.1.4.1.10428 9 1.102.10.2.4.1.2.32
		fkV2QoS4PolicerControlColorYellowCosType OBJECT-TYPE
			SYNTAX INTEGER
				{
				none(0),
				mark(1),
				overwrite(2)
				}
			MAX-ACCESS read-write
			STATUS current
			DESCRIPTION
				"The CoS type colored in yellow"
			::= { fkV2QoS4PolicerControl 32 }

		
		-- 1.3.6.1.4.1.10428 9 1.102.10.2.4.1.2.33
		fkV2QoS4PolicerControlColorYellowCos OBJECT-TYPE
			SYNTAX IntToS
			MAX-ACCESS read-write
			STATUS current
			DESCRIPTION
				"The CoS colored in yellow."
			::= { fkV2QoS4PolicerControl 33 }

		
		-- 1.3.6.1.4.1.10428 9 1.102.10.2.4.1.2.34
		fkV2QoS4PolicerControlColorGreenCosType OBJECT-TYPE
			SYNTAX INTEGER
				{
				none(0),
				mark(1),
				overwrite(2)
				}
			MAX-ACCESS read-write
			STATUS current
			DESCRIPTION
				"The CoS type colored in yellow"
			::= { fkV2QoS4PolicerControl 34 }

		
		-- 1.3.6.1.4.1.10428 9 1.102.10.2.4.1.2.35
		fkV2QoS4PolicerControlColorGreenCos OBJECT-TYPE
			SYNTAX IntToS
			MAX-ACCESS read-write
			STATUS current
			DESCRIPTION
				"The CoS colored in green."
			::= { fkV2QoS4PolicerControl 35 }

		
		-- 1.3.6.1.4.1.10428 9 1.102.10.2.4.1.3
		fkV2QoS4PolicerNotification OBJECT IDENTIFIER ::= { fkV2QoS4PolicerInfo 3 }

		
		-- 1.3.6.1.4.1.10428 9 1.102.10.2.4.1.3.1
		fkPolicerCreated NOTIFICATION-TYPE
			OBJECTS { fkV2QoS4PolicerControlRequest, fkV2QoS4PolicerControlTimeStamp, fkV2QoS4PolicerControlReqResult, fkV2QoS4PolicerColorGreenDscp, fkV2QoS4PolicerColorYellowDscp, 
				fkV2QoS4PolicerColorRedDscp, fkV2QoS4PolicerMaxBandwidth, fkV2QoS4PolicerMinBandwidth, fkV2QoS4PolicerAvrgCounterMode, fkV2QoS4PolicerName, 
				fkV2QoS4PolicerMeterMode, fkV2QoS4PolicerRateLimit, fkV2QoS4PolicerColorType, fkV2QoS4PolicerColorMode, fkV2QoS4PolicerColorAwareMode, 
				fkV2QoS4PolicerColorCIR, fkV2QoS4PolicerColorCBS, fkV2QoS4PolicerColorPIR, fkV2QoS4PolicerColorPBS, fkV2QoS4PolicerColorEBS, 
				fkV2QoS4PolicerColorRedAction, fkV2QoS4PolicerColorYellowAction, fkV2QoS4PolicerColorGreenAction, fkV2QoS4PolicerRemarkLayerMode, fkV2QoS4PolicerRemarkMode, 
				fkV2QoS4PolicerCounterMode }
			STATUS current
			DESCRIPTION 
				"Description."
			::= { fkV2QoS4PolicerNotification 1 }

		
		-- 1.3.6.1.4.1.10428 9 1.102.10.2.4.1.3.2
		fkPolicerChanged NOTIFICATION-TYPE
			OBJECTS { fkV2QoS4PolicerControlRequest, fkV2QoS4PolicerControlTimeStamp, fkV2QoS4PolicerControlReqResult, fkV2QoS4PolicerAvrgCounterMode, fkV2QoS4PolicerMeterMode, 
				fkV2QoS4PolicerRateLimit, fkV2QoS4PolicerColorType, fkV2QoS4PolicerColorMode, fkV2QoS4PolicerColorAwareMode, fkV2QoS4PolicerColorCIR, 
				fkV2QoS4PolicerColorCBS, fkV2QoS4PolicerColorPIR, fkV2QoS4PolicerColorPBS, fkV2QoS4PolicerColorEBS, fkV2QoS4PolicerColorRedAction, 
				fkV2QoS4PolicerColorYellowAction, fkV2QoS4PolicerColorGreenAction, fkV2QoS4PolicerRemarkLayerMode, fkV2QoS4PolicerRemarkMode, fkV2QoS4PolicerCounterMode, 
				fkV2QoS4PolicerMinBandwidth, fkV2QoS4PolicerMaxBandwidth, fkV2QoS4PolicerColorRedDscp, fkV2QoS4PolicerColorYellowDscp, fkV2QoS4PolicerColorGreenDscp
				 }
			STATUS current
			DESCRIPTION 
				"Description."
			::= { fkV2QoS4PolicerNotification 2 }

		
		-- 1.3.6.1.4.1.10428 9 1.102.10.2.4.1.3.3
		fkPolicerDestroyed NOTIFICATION-TYPE
			OBJECTS { fkV2QoS4PolicerControlRequest, fkV2QoS4PolicerControlTimeStamp, fkV2QoS4PolicerControlReqResult, fkV2QoS4PolicerControlIndex }
			STATUS current
			DESCRIPTION 
				"Description."
			::= { fkV2QoS4PolicerNotification 3 }

		
		-- 1.3.6.1.4.1.10428 9 1.102.10.2.4.2
		fkV2QoS4PolicerMatchCounter OBJECT IDENTIFIER ::= { fkV2QoS4Policer 2 }

		
		-- 1.3.6.1.4.1.10428 9 1.102.10.2.4.2.1
		fkV2QoS4PolicerMatchCounterTable OBJECT-TYPE
			SYNTAX SEQUENCE OF FkV2QoS4PolicerMatchCounterEntry
			MAX-ACCESS not-accessible
			STATUS current
			DESCRIPTION
				"policer match counter table."
			::= { fkV2QoS4PolicerMatchCounter 1 }

		
		-- 1.3.6.1.4.1.10428 9 1.102.10.2.4.2.1.1
		fkV2QoS4PolicerMatchCounterEntry OBJECT-TYPE
			SYNTAX FkV2QoS4PolicerMatchCounterEntry
			MAX-ACCESS not-accessible
			STATUS current
			DESCRIPTION
				"key: fkV2QoS4PolicerMatchCounterName"
			INDEX { fkV2QoS4PolicerMatchCounterName }
			::= { fkV2QoS4PolicerMatchCounterTable 1 }

		
		FkV2QoS4PolicerMatchCounterEntry ::=
			SEQUENCE { 
				fkV2QoS4PolicerMatchCounterName
					OCTET STRING,
				fkV2QoS4PolicerMatchCounterDesc
					OCTET STRING,
				fkV2QoS4PolicerMatchCounterValue
					Counter64
			 }

		-- 1.3.6.1.4.1.10428 9 1.102.10.2.4.2.1.1.1
		fkV2QoS4PolicerMatchCounterName OBJECT-TYPE
			SYNTAX OCTET STRING (SIZE (1..63))
			MAX-ACCESS read-only
			STATUS current
			DESCRIPTION
				"The rule-counter policer name"
			::= { fkV2QoS4PolicerMatchCounterEntry 1 }

		
		-- 1.3.6.1.4.1.10428 9 1.102.10.2.4.2.1.1.2
		fkV2QoS4PolicerMatchCounterDesc OBJECT-TYPE
			SYNTAX OCTET STRING (SIZE (1..63))
			MAX-ACCESS read-only
			STATUS current
			DESCRIPTION
				"The rule-counter policer description.
				"
			::= { fkV2QoS4PolicerMatchCounterEntry 2 }

		
		-- 1.3.6.1.4.1.10428 9 1.102.10.2.4.2.1.1.3
		fkV2QoS4PolicerMatchCounterValue OBJECT-TYPE
			SYNTAX Counter64
			MAX-ACCESS read-only
			STATUS current
			DESCRIPTION
				"The  counter-value of matched policer.
				"
			::= { fkV2QoS4PolicerMatchCounterEntry 3 }

		
		-- 1.3.6.1.4.1.10428 9 1.102.10.2.5
		fkV2QoS4Policy OBJECT IDENTIFIER ::= { fkV2QoS4 5 }

		
		-- 1.3.6.1.4.1.10428 9 1.102.10.2.5.1
		fkV2QoS4PolicyInfo OBJECT IDENTIFIER ::= { fkV2QoS4Policy 1 }

		
		-- 1.3.6.1.4.1.10428 9 1.102.10.2.5.1.1
		fkV2QoS4PolicyTable OBJECT-TYPE
			SYNTAX SEQUENCE OF FkV2QoS4PolicyEntry
			MAX-ACCESS not-accessible
			STATUS current
			DESCRIPTION
				"policy table."
			::= { fkV2QoS4PolicyInfo 1 }

		
		-- 1.3.6.1.4.1.10428 9 1.102.10.2.6.1.1.1
		fkV2QoS4PolicyEntry OBJECT-TYPE
			SYNTAX FkV2QoS4PolicyEntry
			MAX-ACCESS not-accessible
			STATUS current
			DESCRIPTION
				"key: fkV2QoS4PolicyIndex"
			INDEX { fkV2QoS4PolicyIndex }
			::= { fkV2QoS4PolicyTable 1 }

		
		FkV2QoS4PolicyEntry ::=
			SEQUENCE { 
				fkV2QoS4PolicyIndex
					IntPolicyIndex,
				fkV2QoS4PolicyName
					OctetName,
				fkV2QoS4PolicyFlowCnt
					Integer32,
				fkV2QoS4PolicyClassCnt
					Integer32,
				fkV2QoS4PolicyPolicerIndex
					INTEGER,
				fkV2QoS4PolicyPriority
					IntRulePriority,
				fkV2QoS4PolicyIngressPorts
					OCTET STRING,
				fkV2QoS4PolicyEgressPorts
					OCTET STRING,
				fkV2QoS4PolicyVlan
					IntVlanID,
				fkV2QoS4PolicyMatchFlag
					BITS,
				fkV2QoS4PolicyMatchVlan
					IntVlanID,
				fkV2QoS4PolicyMatchRedirectVlan
					IntVlanID,
				fkV2QoS4PolicyMatchRedirectPort
					IntInterfaceIndex,
				fkV2QoS4PolicyMatchMarkMode
					IntMarkMode,
				fkV2QoS4PolicyMatchQueue
					IntQueue,
				fkV2QoS4PolicyMatchDp
					IntDP,
				fkV2QoS4PolicyMatchCoS
					IntCoS,
				fkV2QoS4PolicyMatchDscp
					IntDscp,
				fkV2QoS4PolicyMatchIpPrecedence
					IntIpPrecedence,
				fkV2QoS4PolicyMatchDstMacOrEgressPorts
					IntDstMacOrEgressPorts,
				fkV2QoS4PolicyMatchDstMac
					MacAddress,
				fkV2QoS4PolicyMatchEgressPorts
					OCTET STRING,
				fkV2QoS4PolicyNomatchFlag
					BITS,
				fkV2QoS4PolicyNomatchRedirectPort
					IntInterfaceIndex,
				fkV2QoS4PolicyNomatchCoS
					IntCoS,
				fkV2QoS4PolicyNomatchDscp
					IntDscp,
				fkV2QoS4PolicyNomatchIpPrecedence
					IntIpPrecedence,
				fkV2QoS4PolicyCounterValue
					Counter64,
				fkV2QoS4PolicyCounterGreenBytes
					Counter64,
				fkV2QoS4PolicyCounterYellowBytes
					Counter64,
				fkV2QoS4PolicyCounterRedBytes
					Counter64,
				fkV2QoS4PolicyRedirBlackhole
					IntEnableFlag,
				fkV2QoS4PolicyAvrg5SecCounterValue
					Counter64,
				fkV2QoS4PolicyAvrg1minCounterValue
					Counter64,
				fkV2QoS4PolicyAvrg10minCounterValue
					Counter64,
				fkV2QoS4PolicyIngressTunnelIfIndex
					Integer32,
				fkV2QoS4PolicyEgressTunnelIfIndex
					Integer32,
				fkV2QoS4PolicyCounterElapsedTimeAfterClear
					TimeTicks,
				fkV2QoS4PolicyMatchPbrNextHop
					IpAddress,
				fkV2QoS4PolicyStage
					INTEGER,
				fkV2QoS4PolicyIngressPortsFlag
					INTEGER,
				fkV2QoS4PolicyEgressPortsFlag
					INTEGER,
				fkV2QoS4PolicyInnerVlanAction
					INTEGER,
				fkV2QoS4PolicyOuterVlanAction
					INTEGER,
				fkV2QoS4PolicyInnerVlan
					INTEGER,
				fkV2QoS4PolicyOuterVlan
					INTEGER,
				fkV2QoS4PolicyMatchPbrNextHopSecondary
					IpAddress,
				fkV2QoS4PolicyMatchPbrNextHopVerifyReach
					INTEGER,
				fkV2QoS4PolicyMatchFlowAlias
					OCTET STRING,
				fkV2QoS4PolicyMatchInnerVlanCosReplace
					Integer32,
				fkV2QoS4PolicyMatchInnerVlanCfiReplace
					Integer32,
				fkV2QoS4PolicyMatchOuterVlanCosReplace
					Integer32,
				fkV2QoS4PolicyMatchOuterVlanCfiReplace
					Integer32
			 }

		-- 1.3.6.1.4.1.10428 9 1.102.10.2.6.1.1.1.1
		fkV2QoS4PolicyIndex OBJECT-TYPE
			SYNTAX IntPolicyIndex
			MAX-ACCESS read-only
			STATUS current
			DESCRIPTION
				"The index of policy"
			::= { fkV2QoS4PolicyEntry 1 }

		
		-- 1.3.6.1.4.1.10428 9 1.102.10.2.6.1.1.1.2
		fkV2QoS4PolicyName OBJECT-TYPE
			SYNTAX OctetName
			MAX-ACCESS read-only
			STATUS current
			DESCRIPTION
				"The name of policy"
			::= { fkV2QoS4PolicyEntry 2 }

		
		-- 1.3.6.1.4.1.10428 9 1.102.10.2.6.1.1.1.3
		fkV2QoS4PolicyFlowCnt OBJECT-TYPE
			SYNTAX Integer32
			MAX-ACCESS read-only
			STATUS current
			DESCRIPTION
				"The counter of flow that was included to policy"
			::= { fkV2QoS4PolicyEntry 3 }

		
		-- 1.3.6.1.4.1.10428 9 1.102.10.2.6.1.1.1.4
		fkV2QoS4PolicyClassCnt OBJECT-TYPE
			SYNTAX Integer32
			MAX-ACCESS read-only
			STATUS current
			DESCRIPTION
				"The counter of class that was included to policy"
			::= { fkV2QoS4PolicyEntry 4 }

		
		-- 1.3.6.1.4.1.10428 9 1.102.10.2.6.1.1.1.5
		fkV2QoS4PolicyPolicerIndex OBJECT-TYPE
			SYNTAX INTEGER (0 | 1..1024)
			MAX-ACCESS read-only
			STATUS current
			DESCRIPTION
				"The index of policer
				0: no policer
				"
			::= { fkV2QoS4PolicyEntry 5 }

		
		-- 1.3.6.1.4.1.10428 9 1.102.10.2.6.1.1.1.6
		fkV2QoS4PolicyPriority OBJECT-TYPE
			SYNTAX IntRulePriority
			MAX-ACCESS read-only
			STATUS current
			DESCRIPTION
				"The priority of the policy
				
				low : default value
				"
			::= { fkV2QoS4PolicyEntry 6 }

		
		-- 1.3.6.1.4.1.10428 9 1.102.10.2.6.1.1.1.7
		fkV2QoS4PolicyIngressPorts OBJECT-TYPE
			SYNTAX OCTET STRING
			MAX-ACCESS read-only
			STATUS current
			DESCRIPTION
				"The ingress port map"
			::= { fkV2QoS4PolicyEntry 7 }

		
		-- 1.3.6.1.4.1.10428 9 1.102.10.2.6.1.1.1.8
		fkV2QoS4PolicyEgressPorts OBJECT-TYPE
			SYNTAX OCTET STRING
			MAX-ACCESS read-only
			STATUS current
			DESCRIPTION
				"The egress port map"
			::= { fkV2QoS4PolicyEntry 8 }

		
		-- 1.3.6.1.4.1.10428 9 1.102.10.2.6.1.1.1.9
		fkV2QoS4PolicyVlan OBJECT-TYPE
			SYNTAX IntVlanID
			MAX-ACCESS read-only
			STATUS current
			DESCRIPTION
				"The index of vlan 
				The value of -1 is nothing(not set)
				"
			::= { fkV2QoS4PolicyEntry 9 }

		
		-- 1.3.6.1.4.1.10428 9 1.102.10.2.6.1.1.1.10
		fkV2QoS4PolicyMatchFlag OBJECT-TYPE
			SYNTAX BITS
				{
				deny(0),
				mirror(1),
				copyToCPU(2),
				sameAsTos(3),
				sameAsCos(4),
				cos(5),
				tos(6),
				permit(7)
				}
			MAX-ACCESS read-write
			STATUS current
			DESCRIPTION
				"The action to be apply for matched packets.
				bit 0: deny the matched packets
				bit 1: mirror the matched packets
				bit 2: copy to CPU
				bit 3: set 802.1p value to ToS precedence 
				bit 4: set ToS precedence to 802.1p value
				bit 5 : set 802.1p value from flow
				bit 6 : set TaoS precedence from flow
				bit 7 : permit the matched packets
				bit 8 : set inner VLAN value
				bit 9 : set outer VLAN value"
			::= { fkV2QoS4PolicyEntry 10 }

		
		-- 1.3.6.1.4.1.10428 9 1.102.10.2.6.1.1.1.11
		fkV2QoS4PolicyMatchVlan OBJECT-TYPE
			SYNTAX IntVlanID
			MAX-ACCESS read-only
			STATUS current
			DESCRIPTION
				"The vlan id to be assigned for the matched packets
				The value of -1 is nothing(not set)
				"
			::= { fkV2QoS4PolicyEntry 11 }

		
		-- 1.3.6.1.4.1.10428 9 1.102.10.2.6.1.1.1.12
		fkV2QoS4PolicyMatchRedirectVlan OBJECT-TYPE
			SYNTAX IntVlanID
			MAX-ACCESS read-only
			STATUS current
			DESCRIPTION
				"If the value of fkV2QoS4PolicyMatchRedirectVlan is set
				the value of fkV2QoS4PolicyMatchRedirectPort must be set."
			::= { fkV2QoS4PolicyEntry 12 }

		
		-- 1.3.6.1.4.1.10428 9 1.102.10.2.6.1.1.1.13
		fkV2QoS4PolicyMatchRedirectPort OBJECT-TYPE
			SYNTAX IntInterfaceIndex
			MAX-ACCESS read-only
			STATUS current
			DESCRIPTION
				"If the value of fkV2QoS4PolicyMatchRedirectPort is set
				the value of fkV2QoS4PolicyMatchRedirectVlan must be set."
			::= { fkV2QoS4PolicyEntry 13 }

		
		-- 1.3.6.1.4.1.10428 9 1.102.10.2.6.1.1.1.14
		fkV2QoS4PolicyMatchMarkMode OBJECT-TYPE
			SYNTAX IntMarkMode
			MAX-ACCESS read-only
			STATUS current
			DESCRIPTION
				"The match mark mode
				The value of -1 is nothing(not set)
				"
			::= { fkV2QoS4PolicyEntry 14 }

		
		-- 1.3.6.1.4.1.10428 9 1.102.10.2.6.1.1.1.15
		fkV2QoS4PolicyMatchQueue OBJECT-TYPE
			SYNTAX IntQueue
			MAX-ACCESS read-only
			STATUS current
			DESCRIPTION
				"The queue value to be apply for the matched packets
				The value of -1 is nothing(not set)
				"
			::= { fkV2QoS4PolicyEntry 15 }

		
		-- 1.3.6.1.4.1.10428 9 1.102.10.2.6.1.1.1.16
		fkV2QoS4PolicyMatchDp OBJECT-TYPE
			SYNTAX IntDP
			MAX-ACCESS read-only
			STATUS current
			DESCRIPTION
				"The drop precedence
				The value of -1 is nothing(not set)
				"
			::= { fkV2QoS4PolicyEntry 16 }

		
		-- 1.3.6.1.4.1.10428 9 1.102.10.2.6.1.1.1.17
		fkV2QoS4PolicyMatchCoS OBJECT-TYPE
			SYNTAX IntCoS
			MAX-ACCESS read-only
			STATUS current
			DESCRIPTION
				"The Class of Service
				The value of -1 is nothing(not set)
				"
			::= { fkV2QoS4PolicyEntry 17 }

		
		-- 1.3.6.1.4.1.10428 9 1.102.10.2.6.1.1.1.18
		fkV2QoS4PolicyMatchDscp OBJECT-TYPE
			SYNTAX IntDscp
			MAX-ACCESS read-only
			STATUS current
			DESCRIPTION
				"The DSCP
				The value of -1 is nothing(not set)
				"
			::= { fkV2QoS4PolicyEntry 18 }

		
		-- 1.3.6.1.4.1.10428 9 1.102.10.2.6.1.1.1.19
		fkV2QoS4PolicyMatchIpPrecedence OBJECT-TYPE
			SYNTAX IntIpPrecedence
			MAX-ACCESS read-only
			STATUS current
			DESCRIPTION
				"The IP precedence
				The value of -1 is nothing(not set)
				"
			::= { fkV2QoS4PolicyEntry 19 }

		
		-- 1.3.6.1.4.1.10428 9 1.102.10.2.6.1.1.1.20
		fkV2QoS4PolicyMatchDstMacOrEgressPorts OBJECT-TYPE
			SYNTAX IntDstMacOrEgressPorts
			MAX-ACCESS read-only
			STATUS current
			DESCRIPTION
				"If the value is nothing, fkV2QoS4PolicyMatchDstMac and fkV2QoS4PolicyMatchEgressPorts value is not available
				If the value is dstMac, the value of fkV2QoS4PolicyMatchDstMac is available
				If the value is egressPorts, the value of fkV2QoS4PolicyMatchEgressPorts is avalible
				"
			::= { fkV2QoS4PolicyEntry 20 }

		
		-- 1.3.6.1.4.1.10428 9 1.102.10.2.6.1.1.1.21
		fkV2QoS4PolicyMatchDstMac OBJECT-TYPE
			SYNTAX MacAddress
			MAX-ACCESS read-only
			STATUS current
			DESCRIPTION
				"Destination MAC Address of the matched packets
				The value of 00:00:00:00:00:00 is nothing(not set)
				"
			::= { fkV2QoS4PolicyEntry 21 }

		
		-- 1.3.6.1.4.1.10428 9 1.102.10.2.6.1.1.1.22
		fkV2QoS4PolicyMatchEgressPorts OBJECT-TYPE
			SYNTAX OCTET STRING
			MAX-ACCESS read-only
			STATUS current
			DESCRIPTION
				"The egress port map of the matched packets"
			::= { fkV2QoS4PolicyEntry 22 }

		
		-- 1.3.6.1.4.1.10428 9 1.102.10.2.6.1.1.1.23
		fkV2QoS4PolicyNomatchFlag OBJECT-TYPE
			SYNTAX BITS
				{
				deny(0),
				mirror(1),
				copyToCPU(2),
				sameAsTos(3),
				sameAsCos(4),
				cos(5),
				tos(6),
				permit(7)
				}
			MAX-ACCESS read-only
			STATUS current
			DESCRIPTION
				"The action to be apply for matched packets.
				bit 0: deny the nomatched packets
				bit 1: mirror the nomatched packets
				bit 2: copy to CPU
				bit 3: set 802.1p value to ToS precedence 
				bit 4: set ToS precedence to 802.1p value
				bit 5 : set 802.1p value from flow
				bit 6 : set TaoS precedence from flow
				"
			::= { fkV2QoS4PolicyEntry 23 }

		
		-- 1.3.6.1.4.1.10428 9 1.102.10.2.6.1.1.1.24
		fkV2QoS4PolicyNomatchRedirectPort OBJECT-TYPE
			SYNTAX IntInterfaceIndex
			MAX-ACCESS read-only
			STATUS current
			DESCRIPTION
				"The port to redirect to a nomatched packet.
				The value of -1 is nothing(not set)
				
				"
			::= { fkV2QoS4PolicyEntry 24 }

		
		-- 1.3.6.1.4.1.10428 9 1.102.10.2.6.1.1.1.25
		fkV2QoS4PolicyNomatchCoS OBJECT-TYPE
			SYNTAX IntCoS
			MAX-ACCESS read-only
			STATUS current
			DESCRIPTION
				"The Class of Service
				The value of -1 is nothing(not set)
				
				"
			::= { fkV2QoS4PolicyEntry 25 }

		
		-- 1.3.6.1.4.1.10428 9 1.102.10.2.6.1.1.1.26
		fkV2QoS4PolicyNomatchDscp OBJECT-TYPE
			SYNTAX IntDscp
			MAX-ACCESS read-only
			STATUS current
			DESCRIPTION
				"The DSCP
				The value of -1 is nothing(not set)
				"
			::= { fkV2QoS4PolicyEntry 26 }

		
		-- 1.3.6.1.4.1.10428 9 1.102.10.2.6.1.1.1.27
		fkV2QoS4PolicyNomatchIpPrecedence OBJECT-TYPE
			SYNTAX IntIpPrecedence
			MAX-ACCESS read-write
			STATUS current
			DESCRIPTION
				"The IP precedence
				The value of -1 is nothing(not set)
				"
			::= { fkV2QoS4PolicyEntry 27 }

		
		-- 1.3.6.1.4.1.10428 9 1.102.10.2.6.1.1.1.28
		fkV2QoS4PolicyCounterValue OBJECT-TYPE
			SYNTAX Counter64
			MAX-ACCESS read-only
			STATUS current
			DESCRIPTION
				"The value of the counter
				Packet count or bytes according to policer's counter mode.
				The value of 0 is no matched count.
				"
			::= { fkV2QoS4PolicyEntry 28 }

		
		-- 1.3.6.1.4.1.10428 9 1.102.10.2.6.1.1.1.29
		fkV2QoS4PolicyCounterGreenBytes OBJECT-TYPE
			SYNTAX Counter64
			MAX-ACCESS read-only
			STATUS current
			DESCRIPTION
				"The value of the octet counter for green-marked packets.
				Available only when fkV2QoS4PolicerMeterMode's value is color.
				The value of 0 is no matched count.
				"
			::= { fkV2QoS4PolicyEntry 29 }

		
		-- 1.3.6.1.4.1.10428 9 1.102.10.2.6.1.1.1.30
		fkV2QoS4PolicyCounterYellowBytes OBJECT-TYPE
			SYNTAX Counter64
			MAX-ACCESS read-only
			STATUS current
			DESCRIPTION
				"The value of the octet counter for yellow-marked packets.
				Available only when fkV2QoS4PolicerMeterMode's value is color.
				The value of 0 is no matched count.
				"
			::= { fkV2QoS4PolicyEntry 30 }

		
		-- 1.3.6.1.4.1.10428 9 1.102.10.2.6.1.1.1.31
		fkV2QoS4PolicyCounterRedBytes OBJECT-TYPE
			SYNTAX Counter64
			MAX-ACCESS read-only
			STATUS current
			DESCRIPTION
				"The value of the octet counter for red-marked packets.
				Available only when fkV2QoS4PolicerMeterMode's value is color.
				The value of 0 is no matched count.
				"
			::= { fkV2QoS4PolicyEntry 31 }

		
		-- 1.3.6.1.4.1.10428 9 1.102.10.2.6.1.1.1.32
		fkV2QoS4PolicyRedirBlackhole OBJECT-TYPE
			SYNTAX IntEnableFlag
			MAX-ACCESS read-only
			STATUS current
			DESCRIPTION
				"The packet discard"
			::= { fkV2QoS4PolicyEntry 32 }

		
		-- 1.3.6.1.4.1.10428 9 1.102.10.2.6.1.1.1.33
		fkV2QoS4PolicyAvrg5SecCounterValue OBJECT-TYPE
			SYNTAX Counter64
			MAX-ACCESS read-only
			STATUS current
			DESCRIPTION
				"The value of the average counter of 5 second.
				The bytes according to policer¡¯s average counter mode.
				The value of 0 is no matched count.
				"
			::= { fkV2QoS4PolicyEntry 33 }

		
		-- 1.3.6.1.4.1.10428 9 1.102.10.2.6.1.1.1.34
		fkV2QoS4PolicyAvrg1minCounterValue OBJECT-TYPE
			SYNTAX Counter64
			MAX-ACCESS read-only
			STATUS current
			DESCRIPTION
				"The value of the average counter of 1 minute.
				The bytes according to policer¡¯s average counter mode.
				The value of 0 is no matched count.
				"
			::= { fkV2QoS4PolicyEntry 34 }

		
		-- 1.3.6.1.4.1.10428 9 1.102.10.2.6.1.1.1.35
		fkV2QoS4PolicyAvrg10minCounterValue OBJECT-TYPE
			SYNTAX Counter64
			MAX-ACCESS read-only
			STATUS current
			DESCRIPTION
				"The value of the average counter of 10 minute.
				The bytes according to policer¡¯s average counter mode.
				The value of 0 is no matched count.
				"
			::= { fkV2QoS4PolicyEntry 35 }

		
		-- 1.3.6.1.4.1.10428 9 1.102.10.2.6.1.1.1.36
		fkV2QoS4PolicyIngressTunnelIfIndex OBJECT-TYPE
			SYNTAX Integer32 (10000..11023)
			MAX-ACCESS read-only
			STATUS current
			DESCRIPTION
				"Ingress tunnel interface index."
			::= { fkV2QoS4PolicyEntry 36 }

		
		-- 1.3.6.1.4.1.10428 9 1.102.10.2.6.1.1.1.37
		fkV2QoS4PolicyEgressTunnelIfIndex OBJECT-TYPE
			SYNTAX Integer32 (10000..11023)
			MAX-ACCESS read-only
			STATUS current
			DESCRIPTION
				"Egress tunnel interface index."
			::= { fkV2QoS4PolicyEntry 37 }

		
		-- 1.3.6.1.4.1.10428 9 1.102.10.2.6.1.1.1.38
		fkV2QoS4PolicyCounterElapsedTimeAfterClear OBJECT-TYPE
			SYNTAX TimeTicks
			MAX-ACCESS read-only
			STATUS current
			DESCRIPTION
				"The elapsed time after clearing counter."
			::= { fkV2QoS4PolicyEntry 38 }

		
		-- 1.3.6.1.4.1.10428 9 1.102.10.2.6.1.1.1.39
		fkV2QoS4PolicyMatchPbrNextHop OBJECT-TYPE
			SYNTAX IpAddress
			MAX-ACCESS read-only
			STATUS current
			DESCRIPTION
				"The PBR(Policy-Based_routing) nexthop address."
			::= { fkV2QoS4PolicyEntry 39 }

		
		-- 1.3.6.1.4.1.10428 9 1.102.10.2.6.1.1.1.40
		fkV2QoS4PolicyStage OBJECT-TYPE
			SYNTAX INTEGER
				{
				ingress(1),
				prio(2),
				egress(3),
				external(4)
				}
			MAX-ACCESS read-only
			STATUS current
			DESCRIPTION
				"The rule-policy-stage."
			::= { fkV2QoS4PolicyEntry 40 }

		
		-- 1.3.6.1.4.1.10428 9 1.102.10.2.6.1.1.1.41
		fkV2QoS4PolicyIngressPortsFlag OBJECT-TYPE
			SYNTAX INTEGER
				{
				none(0),
				any(1),
				cpu(2)
				}
			MAX-ACCESS read-only
			STATUS current
			DESCRIPTION
				"The interface-binding ingress-port flag of policy."
			::= { fkV2QoS4PolicyEntry 41 }

		
		-- 1.3.6.1.4.1.10428 9 1.102.10.2.6.1.1.1.42
		fkV2QoS4PolicyEgressPortsFlag OBJECT-TYPE
			SYNTAX INTEGER
				{
				none(0),
				any(1),
				cpu(2)
				}
			MAX-ACCESS read-only
			STATUS current
			DESCRIPTION
				"The interface-binding egress-port flag of policy."
			::= { fkV2QoS4PolicyEntry 42 }

		
		-- 1.3.6.1.4.1.10428 9 1.102.10.2.6.1.1.1.43
		fkV2QoS4PolicyInnerVlanAction OBJECT-TYPE
			SYNTAX INTEGER
				{
				nothing(-1),
				add(1),
				replace(2),
				del(3)
				}
			MAX-ACCESS read-only
			STATUS current
			DESCRIPTION
				"The InnerVlan Action Mode
				The Value of -1 is nothing(not set)"
			::= { fkV2QoS4PolicyEntry 43 }

		
		-- 1.3.6.1.4.1.10428 9 1.102.10.2.6.1.1.1.44
		fkV2QoS4PolicyOuterVlanAction OBJECT-TYPE
			SYNTAX INTEGER
				{
				nothing(-1),
				add(1),
				replace(2)
				}
			MAX-ACCESS read-only
			STATUS current
			DESCRIPTION
				"The OuterVlan Action Mode
				The Value of -1 is nothing(not set)"
			::= { fkV2QoS4PolicyEntry 44 }

		
		-- 1.3.6.1.4.1.10428 9 1.102.10.2.6.1.1.1.45
		fkV2QoS4PolicyInnerVlan OBJECT-TYPE
			SYNTAX INTEGER (-1 | 1..4094)
			MAX-ACCESS read-only
			STATUS current
			DESCRIPTION
				"The inner vlan id to be assigned for the matched packets
				The value of -1 is nothing(not set)
				"
			::= { fkV2QoS4PolicyEntry 45 }

		
		-- 1.3.6.1.4.1.10428 9 1.102.10.2.6.1.1.1.46
		fkV2QoS4PolicyOuterVlan OBJECT-TYPE
			SYNTAX INTEGER (-1 | 1..4094)
			MAX-ACCESS read-only
			STATUS current
			DESCRIPTION
				"The outer vlan id to be assigned for the matched packets
				The value of -1 is nothing(not set)"
			::= { fkV2QoS4PolicyEntry 46 }

		
		-- 1.3.6.1.4.1.10428 9 1.102.10.2.6.1.1.1.47
		fkV2QoS4PolicyMatchPbrNextHopSecondary OBJECT-TYPE
			SYNTAX IpAddress
			MAX-ACCESS read-only
			STATUS current
			DESCRIPTION
				"The PBR(Policy-Based_routing) nexthop secondary address."
			::= { fkV2QoS4PolicyEntry 47 }

		
		-- 1.3.6.1.4.1.10428 9 1.102.10.2.6.1.1.1.48
		fkV2QoS4PolicyMatchPbrNextHopVerifyReach OBJECT-TYPE
			SYNTAX INTEGER
				{
				false(0),
				true(1)
				}
			MAX-ACCESS read-only
			STATUS current
			DESCRIPTION
				"The PBR(Policy-Based_routing) Verify-Reachability."
			::= { fkV2QoS4PolicyEntry 48 }

		
		-- 1.3.6.1.4.1.10428 9 1.102.10.2.6.1.1.1.49
		fkV2QoS4PolicyMatchFlowAlias OBJECT-TYPE
			SYNTAX OCTET STRING
			MAX-ACCESS read-only
			STATUS current
			DESCRIPTION
				"The action match flowAlias"
			::= { fkV2QoS4PolicyEntry 49 }

		
		-- 1.3.6.1.4.1.10428 9 1.102.10.2.6.1.1.1.50
		fkV2QoS4PolicyMatchInnerVlanCosReplace OBJECT-TYPE
			SYNTAX Integer32 (-1 | 0..7)
			MAX-ACCESS read-only
			STATUS current
			DESCRIPTION
				"The inner vlan COS replace (-1: delete)"
			::= { fkV2QoS4PolicyEntry 50 }

		
		-- 1.3.6.1.4.1.10428 9 1.102.10.2.6.1.1.1.51
		fkV2QoS4PolicyMatchInnerVlanCfiReplace OBJECT-TYPE
			SYNTAX Integer32 (-1 | 0..1)
			MAX-ACCESS read-only
			STATUS current
			DESCRIPTION
				"The inner vlan CFI replace (-1: delete)"
			::= { fkV2QoS4PolicyEntry 51 }

		
		-- 1.3.6.1.4.1.10428 9 1.102.10.2.6.1.1.1.52
		fkV2QoS4PolicyMatchOuterVlanCosReplace OBJECT-TYPE
			SYNTAX Integer32 (-1 | 0..7)
			MAX-ACCESS read-only
			STATUS current
			DESCRIPTION
				"The outer vlan COS replace (-1: delete)"
			::= { fkV2QoS4PolicyEntry 52 }

		
		-- 1.3.6.1.4.1.10428 9 1.102.10.2.6.1.1.1.53
		fkV2QoS4PolicyMatchOuterVlanCfiReplace OBJECT-TYPE
			SYNTAX Integer32 (-1 | 0..1)
			MAX-ACCESS read-only
			STATUS current
			DESCRIPTION
				"The outer vlan CFI replace (-1: delete)"
			::= { fkV2QoS4PolicyEntry 53 }

		
		-- 1.3.6.1.4.1.10428 9 1.102.10.2.5.1.2
		fkV2QoS4PolicyControl OBJECT IDENTIFIER ::= { fkV2QoS4PolicyInfo 2 }

		
		-- 1.3.6.1.4.1.10428 9 1.102.10.2.5.1.2.1
		fkV2QoS4PolicyControlRequest OBJECT-TYPE
			SYNTAX INTEGER
				{
				createPolicy(1),
				setPolicyInfo(2),
				setMatchAction(3),
				setNomatchAction(4),
				destroyPolicy(5),
				clearCounter(6),
				createEmptyPolicy(7),
				setPolicyIngressTunnel(8),
				unsetPolicyIngressTunnel(9),
				setPolicyEgressTunnel(10),
				unsetPolicyEgressTunnel(11),
				setMatchActionFlowAlias(12),
				setMatchInnerVlanCosReplace(13),
				setMatchInnerVlanCfiReplace(14),
				setMatchOuterVlanCosReplace(15),
				setMatchOuterVlanCfiReplace(16)
				}
			MAX-ACCESS read-write
			STATUS current
			DESCRIPTION
				"The request of a user command"
			::= { fkV2QoS4PolicyControl 1 }

		
		-- 1.3.6.1.4.1.10428 9 1.102.10.2.5.1.2.2
		fkV2QoS4PolicyControlStatus OBJECT-TYPE
			SYNTAX FkControlStatusType
			MAX-ACCESS read-only
			STATUS current
			DESCRIPTION
				"The status of user command"
			::= { fkV2QoS4PolicyControl 2 }

		
		-- 1.3.6.1.4.1.10428 9 1.102.10.2.5.1.2.3
		fkV2QoS4PolicyControlTimer OBJECT-TYPE
			SYNTAX Gauge32
			MAX-ACCESS read-write
			STATUS current
			DESCRIPTION
				"The maximum time for the manager for a long running user command"
			::= { fkV2QoS4PolicyControl 3 }

		
		-- 1.3.6.1.4.1.10428 9 1.102.10.2.5.1.2.4
		fkV2QoS4PolicyControlTimeStamp OBJECT-TYPE
			SYNTAX TimeTicks
			MAX-ACCESS read-only
			STATUS current
			DESCRIPTION
				"The time stamp of the last command(end of command)"
			::= { fkV2QoS4PolicyControl 4 }

		
		-- 1.3.6.1.4.1.10428 9 1.102.10.2.5.1.2.5
		fkV2QoS4PolicyControlReqResult OBJECT-TYPE
			SYNTAX FkControlRequestResultType
			MAX-ACCESS read-only
			STATUS current
			DESCRIPTION
				"The result of the last user command"
			::= { fkV2QoS4PolicyControl 5 }

		
		-- 1.3.6.1.4.1.10428 9 1.102.10.2.5.1.2.6
		fkV2QoS4PolicyControlIndex OBJECT-TYPE
			SYNTAX IntPolicyIndex
			MAX-ACCESS read-write
			STATUS current
			DESCRIPTION
				"The index of policy"
			::= { fkV2QoS4PolicyControl 6 }

		
		-- 1.3.6.1.4.1.10428 9 1.102.10.2.5.1.2.7
		fkV2QoS4PolicyControlName OBJECT-TYPE
			SYNTAX OctetName
			MAX-ACCESS read-write
			STATUS current
			DESCRIPTION
				"The name of policy"
			::= { fkV2QoS4PolicyControl 7 }

		
		-- 1.3.6.1.4.1.10428 9 1.102.10.2.5.1.2.8
		fkV2QoS4PolicyControlPolicerIndex OBJECT-TYPE
			SYNTAX INTEGER (0 | 1..1024)
			MAX-ACCESS read-write
			STATUS current
			DESCRIPTION
				"The index of policer
				0: no policer
				"
			::= { fkV2QoS4PolicyControl 8 }

		
		-- 1.3.6.1.4.1.10428 9 1.102.10.2.5.1.2.9
		fkV2QoS4PolicyControlPriority OBJECT-TYPE
			SYNTAX IntRulePriority
			MAX-ACCESS read-write
			STATUS current
			DESCRIPTION
				"The priority of the policy
				
				low : default
				"
			::= { fkV2QoS4PolicyControl 9 }

		
		-- 1.3.6.1.4.1.10428 9 1.102.10.2.5.1.2.10
		fkV2QoS4PolicyControlIngressPorts OBJECT-TYPE
			SYNTAX OCTET STRING
			MAX-ACCESS read-write
			STATUS current
			DESCRIPTION
				"The ingress port map"
			::= { fkV2QoS4PolicyControl 10 }

		
		-- 1.3.6.1.4.1.10428 9 1.102.10.2.5.1.2.11
		fkV2QoS4PolicyControlEgressPorts OBJECT-TYPE
			SYNTAX OCTET STRING
			MAX-ACCESS read-write
			STATUS current
			DESCRIPTION
				"The egress port map"
			::= { fkV2QoS4PolicyControl 11 }

		
		-- 1.3.6.1.4.1.10428 9 1.102.10.2.5.1.2.12
		fkV2QoS4PolicyControlVlan OBJECT-TYPE
			SYNTAX IntVlanID
			MAX-ACCESS read-write
			STATUS current
			DESCRIPTION
				"The index of vlan 
				The value of -1 is nothing(not set)
				"
			::= { fkV2QoS4PolicyControl 12 }

		
		-- 1.3.6.1.4.1.10428 9 1.102.10.2.5.1.2.13
		fkV2QoS4PolicyControlMatchFlag OBJECT-TYPE
			SYNTAX BITS
				{
				deny(0),
				mirror(1),
				copyToCPU(2),
				sameAsTos(3),
				sameAsCos(4),
				cos(5),
				tos(6),
				permit(7)
				}
			MAX-ACCESS read-write
			STATUS current
			DESCRIPTION
				"The action to be apply for matched packets.
				bit 0: deny the matched packets
				bit 1: mirror the matched packets
				bit 2: copy to CPU
				bit 3: set 802.1p value to ToS precedence 
				bit 4: set ToS precedence to 802.1p value
				bit 5 : set 802.1p value from flow
				bit 6 : set TaoS precedence from flow
				bit 7 : permit the matched packets
				bit 8 : set inner VLAN value
				bit 9 : set outer VLAN value
				"
			::= { fkV2QoS4PolicyControl 13 }

		
		-- 1.3.6.1.4.1.10428 9 1.102.10.2.5.1.2.14
		fkV2QoS4PolicyControlMatchVlan OBJECT-TYPE
			SYNTAX IntVlanID
			MAX-ACCESS read-write
			STATUS current
			DESCRIPTION
				"The vlan id to be assigned for the matched packets
				The value of -1 is nothing(not set)
				"
			::= { fkV2QoS4PolicyControl 14 }

		
		-- 1.3.6.1.4.1.10428 9 1.102.10.2.5.1.2.15
		fkV2QoS4PolicyControlMatchRedirectVlan OBJECT-TYPE
			SYNTAX IntVlanID
			MAX-ACCESS read-write
			STATUS current
			DESCRIPTION
				"The valn id to redirect to a matched packet
				If the value of fkV2QoS4PolicyMatchRedirectVlan is set
				the value of fkV2QoS4PolicyMatchRedirectPort must be set.
				The value of -1 is nothing(not set)
				"
			::= { fkV2QoS4PolicyControl 15 }

		
		-- 1.3.6.1.4.1.10428 9 1.102.10.2.5.1.2.16
		fkV2QoS4PolicyControlMatchRedirectPort OBJECT-TYPE
			SYNTAX IntInterfaceIndex
			MAX-ACCESS read-write
			STATUS current
			DESCRIPTION
				"The port to redirect to a matched packet.
				If the value of fkV2QoS4PolicyMatchRedirectPort is set
				the value of fkV2QoS4PolicyMatchRedirectVlan must be set.
				The value of -1 is nothing(not set)
				"
			::= { fkV2QoS4PolicyControl 16 }

		
		-- 1.3.6.1.4.1.10428 9 1.102.10.2.5.1.2.17
		fkV2QoS4PolicyControlMatchMarkMode OBJECT-TYPE
			SYNTAX IntMarkMode
			MAX-ACCESS read-write
			STATUS current
			DESCRIPTION
				"The match mark mode
				The value of -1 is nothing(not set)
				"
			::= { fkV2QoS4PolicyControl 17 }

		
		-- 1.3.6.1.4.1.10428 9 1.102.10.2.5.1.2.18
		fkV2QoS4PolicyControlMatchQueue OBJECT-TYPE
			SYNTAX IntQueue
			MAX-ACCESS read-write
			STATUS current
			DESCRIPTION
				"The queue value to be apply for the matched packets
				The value of -1 is nothing(not set)
				"
			::= { fkV2QoS4PolicyControl 18 }

		
		-- 1.3.6.1.4.1.10428 9 1.102.10.2.5.1.2.19
		fkV2QoS4PolicyControlMatchDp OBJECT-TYPE
			SYNTAX IntDP
			MAX-ACCESS read-write
			STATUS current
			DESCRIPTION
				"The drop precedence
				The value of -1 is nothing(not set)
				"
			::= { fkV2QoS4PolicyControl 19 }

		
		-- 1.3.6.1.4.1.10428 9 1.102.10.2.5.1.2.20
		fkV2QoS4PolicyControlMatchCoS OBJECT-TYPE
			SYNTAX Integer32
			MAX-ACCESS read-write
			STATUS current
			DESCRIPTION
				"The Class of Service
				The value of -1 is nothing(not set)
				"
			::= { fkV2QoS4PolicyControl 20 }

		
		-- 1.3.6.1.4.1.10428 9 1.102.10.2.5.1.2.21
		fkV2QoS4PolicyControlMatchDscp OBJECT-TYPE
			SYNTAX IntDscp
			MAX-ACCESS read-write
			STATUS current
			DESCRIPTION
				"The DSCP
				The value of -1 is nothing(not set)
				"
			::= { fkV2QoS4PolicyControl 21 }

		
		-- 1.3.6.1.4.1.10428 9 1.102.10.2.5.1.2.22
		fkV2QoS4PolicyControlMatchIpPrecedence OBJECT-TYPE
			SYNTAX IntIpPrecedence
			MAX-ACCESS read-write
			STATUS current
			DESCRIPTION
				"The IP precedence
				The value of -1 is nothing(not set)
				"
			::= { fkV2QoS4PolicyControl 22 }

		
		-- 1.3.6.1.4.1.10428 9 1.102.10.2.5.1.2.23
		fkV2QoS4PolicyControlMatchDstMacOrEgressPorts OBJECT-TYPE
			SYNTAX IntDstMacOrEgressPorts
			MAX-ACCESS read-write
			STATUS current
			DESCRIPTION
				"If the value is nothing, fkV2QoS4PolicyControlMatchDstMac and fkV2QoS4PolicyControlMatchEgressPorts value is not available
				If the value is dstMac, the value of fkV2QoS4PolicyControlMatchDstMac is available
				If the value is egressPorts, the value of fkV2QoS4PolicyControlMatchEgressPorts is avalible
				"
			::= { fkV2QoS4PolicyControl 23 }

		
		-- 1.3.6.1.4.1.10428 9 1.102.10.2.5.1.2.24
		fkV2QoS4PolicyControlMatchDstMac OBJECT-TYPE
			SYNTAX MacAddress
			MAX-ACCESS read-write
			STATUS current
			DESCRIPTION
				"Destination MAC Address of the matched packets
				The value of 00:00:00:00:00:00 is nothing(not set)
				"
			::= { fkV2QoS4PolicyControl 24 }

		
		-- 1.3.6.1.4.1.10428 9 1.102.10.2.5.1.2.25
		fkV2QoS4PolicyControlMatchEgressPorts OBJECT-TYPE
			SYNTAX OCTET STRING
			MAX-ACCESS read-write
			STATUS current
			DESCRIPTION
				"The egress port map of the matched packets"
			::= { fkV2QoS4PolicyControl 25 }

		
		-- 1.3.6.1.4.1.10428 9 1.102.10.2.5.1.2.26
		fkV2QoS4PolicyControlNomatchFlag OBJECT-TYPE
			SYNTAX BITS
				{
				deny(0),
				mirror(1),
				copyToCPU(2),
				sameAsTos(3),
				sameAsCos(4),
				cos(5),
				tos(6),
				permit(7)
				}
			MAX-ACCESS read-write
			STATUS current
			DESCRIPTION
				"The action to be apply for matched packets.
				bit 0: deny the nomatched packets
				bit 1: mirror the nomatched packets
				bit 2: copy to CPU
				bit 3: set 802.1p value to ToS precedence 
				bit 4: set ToS precedence to 802.1p value
				bit 5 : set 802.1p value from flow
				bit 6 : set TaoS precedence from flow
				"
			::= { fkV2QoS4PolicyControl 26 }

		
		-- 1.3.6.1.4.1.10428 9 1.102.10.2.5.1.2.27
		fkV2QoS4PolicyControlNomatchRedirectPort OBJECT-TYPE
			SYNTAX IntInterfaceIndex
			MAX-ACCESS read-write
			STATUS current
			DESCRIPTION
				"The port to redirect to a nomatched packet.
				The value of -1 is nothing(not set)
				"
			::= { fkV2QoS4PolicyControl 27 }

		
		-- 1.3.6.1.4.1.10428 9 1.102.10.2.5.1.2.28
		fkV2QoS4PolicyControlNomatchCoS OBJECT-TYPE
			SYNTAX IntCoS
			MAX-ACCESS read-write
			STATUS current
			DESCRIPTION
				"The Class of Service
				The value of -1 is nothing(not set)
				"
			::= { fkV2QoS4PolicyControl 28 }

		
		-- 1.3.6.1.4.1.10428 9 1.102.10.2.5.1.2.29
		fkV2QoS4PolicyControlNomatchDscp OBJECT-TYPE
			SYNTAX IntDscp
			MAX-ACCESS read-write
			STATUS current
			DESCRIPTION
				"The DSCP
				The value of -1 is nothing(not set)
				"
			::= { fkV2QoS4PolicyControl 29 }

		
		-- 1.3.6.1.4.1.10428 9 1.102.10.2.5.1.2.30
		fkV2QoS4PolicyControlNomatchIpPrecedence OBJECT-TYPE
			SYNTAX IntIpPrecedence
			MAX-ACCESS read-write
			STATUS current
			DESCRIPTION
				"The IP precedence
				The value of -1 is nothing(not set)
				"
			::= { fkV2QoS4PolicyControl 30 }

		
		-- 1.3.6.1.4.1.10428 9 1.102.10.2.5.1.2.31
		fkV2QoS4PolicyControlMatchRedirBlackhole OBJECT-TYPE
			SYNTAX IntEnableFlag
			MAX-ACCESS read-write
			STATUS current
			DESCRIPTION
				"The packet discard"
			::= { fkV2QoS4PolicyControl 31 }

		
		-- 1.3.6.1.4.1.10428 9 1.102.10.2.5.1.2.32
		fkV2QoS4PolicyControlIngressTunnelIfIndex OBJECT-TYPE
			SYNTAX Integer32 (10000..11023)
			MAX-ACCESS read-write
			STATUS current
			DESCRIPTION
				"Ingress tunnel interface index."
			::= { fkV2QoS4PolicyControl 32 }

		
		-- 1.3.6.1.4.1.10428 9 1.102.10.2.5.1.2.33
		fkV2Qo4SPolicyControlEgressTunnelIfIndex OBJECT-TYPE
			SYNTAX Integer32 (10000..11023)
			MAX-ACCESS read-write
			STATUS current
			DESCRIPTION
				"Egress tunnel interface index."
			::= { fkV2QoS4PolicyControl 33 }

		
		-- 1.3.6.1.4.1.10428 9 1.102.10.2.5.1.2.34
		fkV2QoS4PolicyControlMatchPbrNextHop OBJECT-TYPE
			SYNTAX IpAddress
			MAX-ACCESS read-write
			STATUS current
			DESCRIPTION
				"The PBR(Policy-Based_routing) nexthop address."
			::= { fkV2QoS4PolicyControl 34 }

		
		-- 1.3.6.1.4.1.10428 9 1.102.10.2.5.1.2.35
		fkV2QoS4PolicyControlStage OBJECT-TYPE
			SYNTAX INTEGER
				{
				ingress(1),
				prio(2),
				egress(3),
				external(4)
				}
			MAX-ACCESS read-write
			STATUS current
			DESCRIPTION
				"The rule-policy-stage."
			::= { fkV2QoS4PolicyControl 35 }

		
		-- 1.3.6.1.4.1.10428 9 1.102.10.2.5.1.2.36
		fkV2QoS4PolicyControlIngressPortsFlag OBJECT-TYPE
			SYNTAX INTEGER
				{
				none(0),
				any(1),
				cpu(2)
				}
			MAX-ACCESS read-write
			STATUS current
			DESCRIPTION
				"The interface-binding ingress-port flag of policy."
			::= { fkV2QoS4PolicyControl 36 }

		
		-- 1.3.6.1.4.1.10428 9 1.102.10.2.5.1.2.37
		fkV2QoS4PolicyControlEgressPortsFlag OBJECT-TYPE
			SYNTAX INTEGER
				{
				none(0),
				any(1),
				cpu(2)
				}
			MAX-ACCESS read-write
			STATUS current
			DESCRIPTION
				"The interface-binding egress-port flag of policy."
			::= { fkV2QoS4PolicyControl 37 }

		
		-- 1.3.6.1.4.1.10428 9 1.102.10.2.5.1.2.38
		fkV2QoS4PolicyControlInnerVlanAction OBJECT-TYPE
			SYNTAX INTEGER
				{
				nothing(-1),
				add(1),
				replace(2),
				del(3)
				}
			MAX-ACCESS read-write
			STATUS current
			DESCRIPTION
				"The InnerVlan Action Mode
				The Value of -1 is nothing(not set)"
			::= { fkV2QoS4PolicyControl 38 }

		
		-- 1.3.6.1.4.1.10428 9 1.102.10.2.5.1.2.39
		fkV2QoS4PolicyControlOuterVlanAction OBJECT-TYPE
			SYNTAX INTEGER
				{
				nothing(-1),
				add(1),
				replace(2)
				}
			MAX-ACCESS read-write
			STATUS current
			DESCRIPTION
				"The OuterVlan Action Mode
				The Value of -1 is nothing(not set)"
			::= { fkV2QoS4PolicyControl 39 }

		
		-- 1.3.6.1.4.1.10428 9 1.102.10.2.5.1.2.40
		fkV2QoS4PolicyControlInnerVlan OBJECT-TYPE
			SYNTAX INTEGER (-1 | 1..4094)
			MAX-ACCESS read-write
			STATUS current
			DESCRIPTION
				"The inner vlan id to be assigned for the matched packets
				The value of -1 is nothing(not set)
				"
			::= { fkV2QoS4PolicyControl 40 }

		
		-- 1.3.6.1.4.1.10428 9 1.102.10.2.5.1.2.41
		fkV2QoS4PolicyControlOuterVlan OBJECT-TYPE
			SYNTAX INTEGER (-1 | 1..4094)
			MAX-ACCESS read-write
			STATUS current
			DESCRIPTION
				"The outer vlan id to be assigned for the matched packets
				The value of -1 is nothing(not set)"
			::= { fkV2QoS4PolicyControl 41 }

		
		-- 1.3.6.1.4.1.10428 9 1.102.10.2.5.1.2.42
		fkV2QoS4PolicyControlMatchPbrNextHopSecondary OBJECT-TYPE
			SYNTAX IpAddress
			MAX-ACCESS read-write
			STATUS current
			DESCRIPTION
				"The PBR(Policy-Based_routing) nexthop secondary address."
			::= { fkV2QoS4PolicyControl 42 }

		
		-- 1.3.6.1.4.1.10428 9 1.102.10.2.5.1.2.43
		fkV2QoS4PolicyControlMatchPbrNextHopVerifyReach OBJECT-TYPE
			SYNTAX INTEGER
				{
				false(0),
				true(1)
				}
			MAX-ACCESS read-write
			STATUS current
			DESCRIPTION
				"The PBR(Policy-Based_routing) Verify-Reachability."
			::= { fkV2QoS4PolicyControl 43 }

		
		-- 1.3.6.1.4.1.10428 9 1.102.10.2.5.1.2.44
		fkV2QoS4PolicyControlMatchFlowAlias OBJECT-TYPE
			SYNTAX OCTET STRING
			MAX-ACCESS read-only
			STATUS current
			DESCRIPTION
				"The action match flowAlias"
			::= { fkV2QoS4PolicyControl 44 }

		
		-- 1.3.6.1.4.1.10428 9 1.102.10.2.5.1.2.45
		fkV2QoS4PolicyControlMatchInnerVlanCosReplace OBJECT-TYPE
			SYNTAX Integer32 (-1 | 0..7)
			MAX-ACCESS read-write
			STATUS current
			DESCRIPTION
				"The inner vlan COS replace (-1: delete)"
			::= { fkV2QoS4PolicyControl 45 }

		
		-- 1.3.6.1.4.1.10428 9 1.102.10.2.5.1.2.46
		fkV2QoS4PolicyControlMatchInnerVlanCfiReplace OBJECT-TYPE
			SYNTAX Integer32 (-1 | 0..1)
			MAX-ACCESS read-write
			STATUS current
			DESCRIPTION
				"The inner vlan CFI replace (-1: delete)"
			::= { fkV2QoS4PolicyControl 46 }

		
		-- 1.3.6.1.4.1.10428 9 1.102.10.2.5.1.2.47
		fkV2QoS4PolicyControlMatchOuterVlanCosReplace OBJECT-TYPE
			SYNTAX Integer32 (-1 | 0..7)
			MAX-ACCESS read-write
			STATUS current
			DESCRIPTION
				"The outer vlan COS replace (-1: delete)"
			::= { fkV2QoS4PolicyControl 47 }

		
		-- 1.3.6.1.4.1.10428 9 1.102.10.2.5.1.2.48
		fkV2QoS4PolicyControlMatchOuterVlanCfiReplace OBJECT-TYPE
			SYNTAX Integer32 (-1 | 0..1)
			MAX-ACCESS read-write
			STATUS current
			DESCRIPTION
				"The outer vlan CFI replace (-1: delete)"
			::= { fkV2QoS4PolicyControl 48 }

		
		-- 1.3.6.1.4.1.10428 9 1.102.10.2.5.1.3
		fkV2QoSPolicyNotification OBJECT IDENTIFIER ::= { fkV2QoS4PolicyInfo 3 }

		
		-- 1.3.6.1.4.1.10428 9 1.102.10.2.5.1.3.1
		fkPolicyCreated NOTIFICATION-TYPE
			OBJECTS { fkV2QoS4PolicyControlRequest, fkV2QoS4PolicyControlTimeStamp, fkV2QoS4PolicyRedirBlackhole, fkV2QoS4PolicyMatchPbrNextHop, fkV2QoS4PolicyStage, 
				fkV2QoS4PolicyIngressPortsFlag, fkV2QoS4PolicyEgressPortsFlag, fkV2QoS4PolicyInnerVlanAction, fkV2QoS4PolicyOuterVlanAction, fkV2QoS4PolicyInnerVlan, 
				fkV2QoS4PolicyOuterVlan, fkV2QoS4PolicyControlReqResult, fkV2QoS4PolicyName, fkV2QoS4PolicyFlowCnt, fkV2QoS4PolicyClassCnt, 
				fkV2QoS4PolicyPolicerIndex, fkV2QoS4PolicyPriority, fkV2QoS4PolicyIngressPorts, fkV2QoS4PolicyEgressPorts, fkV2QoS4PolicyVlan, 
				fkV2QoS4PolicyMatchFlag, fkV2QoS4PolicyMatchVlan, fkV2QoS4PolicyMatchRedirectVlan, fkV2QoS4PolicyMatchRedirectPort, fkV2QoS4PolicyMatchMarkMode, 
				fkV2QoS4PolicyMatchQueue, fkV2QoS4PolicyMatchDp, fkV2QoS4PolicyMatchCoS, fkV2QoS4PolicyMatchDscp, fkV2QoS4PolicyMatchIpPrecedence, 
				fkV2QoS4PolicyMatchDstMacOrEgressPorts, fkV2QoS4PolicyMatchDstMac, fkV2QoS4PolicyMatchEgressPorts, fkV2QoS4PolicyNomatchFlag, fkV2QoS4PolicyNomatchRedirectPort, 
				fkV2QoS4PolicyNomatchCoS, fkV2QoS4PolicyNomatchDscp, fkV2QoS4PolicyNomatchIpPrecedence, fkV2QoS4PolicyCounterValue, fkV2QoS4PolicyCounterGreenBytes, 
				fkV2QoS4PolicyCounterYellowBytes, fkV2QoS4PolicyCounterRedBytes, fkV2QoS4PolicyMatchPbrNextHopSecondary, fkV2QoS4PolicyMatchPbrNextHopVerifyReach }
			STATUS current
			DESCRIPTION 
				"Description."
			::= { fkV2QoSPolicyNotification 1 }

		
		-- 1.3.6.1.4.1.10428 9 1.102.10.2.5.1.3.2
		fkPolicyInfoChanged NOTIFICATION-TYPE
			OBJECTS { fkV2QoS4PolicyControlRequest, fkV2QoS4PolicyControlTimeStamp, fkV2QoS4PolicyStage, fkV2QoS4PolicyControlReqResult, fkV2QoS4PolicyPolicerIndex, 
				fkV2QoS4PolicyIngressPorts, fkV2QoS4PolicyEgressPorts, fkV2QoS4PolicyIngressPortsFlag, fkV2QoS4PolicyEgressPortsFlag, fkV2QoS4PolicyVlan, 
				fkV2QoS4PolicyPriority }
			STATUS current
			DESCRIPTION 
				"Description."
			::= { fkV2QoSPolicyNotification 2 }

		
		-- 1.3.6.1.4.1.10428 9 1.102.10.2.5.1.3.3
		fkPolicyMatchActionChanged NOTIFICATION-TYPE
			OBJECTS { fkV2QoS4PolicyControlRequest, fkV2QoS4PolicyControlTimeStamp, fkV2QoS4PolicyRedirBlackhole, fkV2QoS4PolicyInnerVlanAction, fkV2QoS4PolicyOuterVlanAction, 
				fkV2QoS4PolicyInnerVlan, fkV2QoS4PolicyOuterVlan, fkV2QoS4PolicyControlReqResult, fkV2QoS4PolicyMatchFlag, fkV2QoS4PolicyMatchVlan, 
				fkV2QoS4PolicyMatchRedirectVlan, fkV2QoS4PolicyMatchRedirectPort, fkV2QoS4PolicyMatchMarkMode, fkV2QoS4PolicyMatchQueue, fkV2QoS4PolicyMatchDp, 
				fkV2QoS4PolicyMatchCoS, fkV2QoS4PolicyMatchDscp, fkV2QoS4PolicyMatchIpPrecedence, fkV2QoS4PolicyMatchDstMacOrEgressPorts, fkV2QoS4PolicyMatchDstMac, 
				fkV2QoS4PolicyMatchEgressPorts, fkV2QoS4PolicyMatchPbrNextHop, fkV2QoS4PolicyMatchPbrNextHopSecondary, fkV2QoS4PolicyMatchPbrNextHopVerifyReach }
			STATUS current
			DESCRIPTION 
				"Description."
			::= { fkV2QoSPolicyNotification 3 }

		
		-- 1.3.6.1.4.1.10428 9 1.102.10.2.5.1.3.4
		fkPolicyNomatchActionChanged NOTIFICATION-TYPE
			OBJECTS { fkV2QoS4PolicyControlRequest, fkV2QoS4PolicyControlTimeStamp, fkV2QoS4PolicyControlReqResult, fkV2QoS4PolicyNomatchFlag, fkV2QoS4PolicyNomatchRedirectPort, 
				fkV2QoS4PolicyNomatchCoS, fkV2QoS4PolicyNomatchDscp, fkV2QoS4PolicyNomatchIpPrecedence }
			STATUS current
			DESCRIPTION 
				"Description."
			::= { fkV2QoSPolicyNotification 4 }

		
		-- 1.3.6.1.4.1.10428 9 1.102.10.2.5.1.3.5
		fkPolicyDestroyed NOTIFICATION-TYPE
			OBJECTS { fkV2QoS4PolicyControlRequest, fkV2QoS4PolicyControlTimeStamp, fkV2QoS4PolicyControlReqResult, fkV2QoS4PolicyControlIndex }
			STATUS current
			DESCRIPTION 
				"Description."
			::= { fkV2QoSPolicyNotification 5 }

		
		-- 1.3.6.1.4.1.10428 9 1.102.10.2.5.1.3.6
		fkPolicyCounterCleared NOTIFICATION-TYPE
			OBJECTS { fkV2QoS4PolicyControlRequest, fkV2QoS4PolicyControlTimeStamp, fkV2QoS4PolicyControlReqResult, fkV2QoS4PolicyControlIndex, fkV2QoS4PolicyCounterValue, 
				fkV2QoS4PolicyCounterGreenBytes, fkV2QoS4PolicyCounterYellowBytes, fkV2QoS4PolicyCounterRedBytes }
			STATUS current
			DESCRIPTION 
				"Description."
			::= { fkV2QoSPolicyNotification 6 }

		
		-- 1.3.6.1.4.1.10428 9 1.102.10.2.5.1.3.7
		fkPolicyEmptyCreated NOTIFICATION-TYPE
			OBJECTS { fkV2QoS4PolicyControlRequest, fkV2QoS4PolicyControlTimeStamp, fkV2QoS4PolicyControlReqResult, fkV2QoS4PolicyName }
			STATUS current
			DESCRIPTION 
				"Description."
			::= { fkV2QoSPolicyNotification 7 }

		
		-- 1.3.6.1.4.1.10428 9 1.102.10.2.5.1.3.8
		fkPolicyIngressTunnelSet NOTIFICATION-TYPE
			OBJECTS { fkV2QoS4PolicyControlRequest, fkV2QoS4PolicyControlTimeStamp, fkV2QoS4PolicyControlReqResult, fkV2QoS4PolicyControlIndex, fkV2QoS4PolicyControlIngressTunnelIfIndex
				 }
			STATUS current
			DESCRIPTION 
				"Description."
			::= { fkV2QoSPolicyNotification 8 }

		
		-- 1.3.6.1.4.1.10428 9 1.102.10.2.5.1.3.9
		fkPolicyIngressTunnelUnset NOTIFICATION-TYPE
			OBJECTS { fkV2QoS4PolicyControlRequest, fkV2QoS4PolicyControlTimeStamp, fkV2QoS4PolicyControlReqResult, fkV2QoS4PolicyControlIndex, fkV2QoS4PolicyControlIngressTunnelIfIndex
				 }
			STATUS current
			DESCRIPTION 
				"Description."
			::= { fkV2QoSPolicyNotification 9 }

		
		-- 1.3.6.1.4.1.10428 9 1.102.10.2.5.1.3.10
		fkPolicyEgressTunnelSet NOTIFICATION-TYPE
			OBJECTS { fkV2QoS4PolicyControlRequest, fkV2QoS4PolicyControlTimeStamp, fkV2QoS4PolicyControlReqResult, fkV2QoS4PolicyControlIndex, fkV2Qo4SPolicyControlEgressTunnelIfIndex
				 }
			STATUS current
			DESCRIPTION 
				"Description."
			::= { fkV2QoSPolicyNotification 10 }

		
		-- 1.3.6.1.4.1.10428 9 1.102.10.2.5.1.3.11
		fkPolicyEgressTunnelUnset NOTIFICATION-TYPE
			OBJECTS { fkV2QoS4PolicyControlRequest, fkV2QoS4PolicyControlTimeStamp, fkV2QoS4PolicyControlReqResult, fkV2QoS4PolicyControlIndex, fkV2Qo4SPolicyControlEgressTunnelIfIndex
				 }
			STATUS current
			DESCRIPTION 
				"Description."
			::= { fkV2QoSPolicyNotification 11 }

		
		-- 1.3.6.1.4.1.10428 9 1.102.10.2.5.1.3.12
		fkPolicyActionMatchFlowAliasChanged NOTIFICATION-TYPE
			OBJECTS { fkV2QoS4PolicyControlRequest, fkV2QoS4PolicyControlTimeStamp, fkV2QoS4PolicyControlReqResult, fkV2QoS4PolicyControlIndex, fkV2QoS4PolicyControlMatchFlowAlias
				 }
			STATUS current
			DESCRIPTION 
				"setMatchActionFlowAlias"
			::= { fkV2QoSPolicyNotification 12 }

		
		-- 1.3.6.1.4.1.10428 9 1.102.10.2.5.1.3.13
		fkPolicyMatchInnerVlanCosReplaceChanged NOTIFICATION-TYPE
			OBJECTS { fkV2QoS4PolicyControlRequest, fkV2QoS4PolicyControlTimeStamp, fkV2QoS4PolicyControlReqResult, fkV2QoS4PolicyControlIndex, fkV2QoS4PolicyControlMatchInnerVlanCosReplace
				 }
			STATUS current
			DESCRIPTION 
				"setMatchInnerVlanCosReplace"
			::= { fkV2QoSPolicyNotification 13 }

		
		-- 1.3.6.1.4.1.10428 9 1.102.10.2.5.1.3.14
		fkPolicyMatchInnerVlanCfiReplaceChanged NOTIFICATION-TYPE
			OBJECTS { fkV2QoS4PolicyControlRequest, fkV2QoS4PolicyControlTimeStamp, fkV2QoS4PolicyControlReqResult, fkV2QoS4PolicyControlIndex, fkV2QoS4PolicyControlMatchInnerVlanCfiReplace
				 }
			STATUS current
			DESCRIPTION 
				"setMatchInnerVlanCfiReplace"
			::= { fkV2QoSPolicyNotification 14 }

		
		-- 1.3.6.1.4.1.10428 9 1.102.10.2.5.1.3.15
		fkPolicyMatchOuterVlanCosReplaceChanged NOTIFICATION-TYPE
			OBJECTS { fkV2QoS4PolicyControlRequest, fkV2QoS4PolicyControlTimeStamp, fkV2QoS4PolicyControlReqResult, fkV2QoS4PolicyControlIndex, fkV2QoS4PolicyControlMatchOuterVlanCosReplace
				 }
			STATUS current
			DESCRIPTION 
				"setMatchOuterVlanCosReplace"
			::= { fkV2QoSPolicyNotification 15 }

		
		-- 1.3.6.1.4.1.10428 9 1.102.10.2.5.1.3.16
		fkPolicyMatchOuterVlanCfiReplaceChanged NOTIFICATION-TYPE
			OBJECTS { fkV2QoS4PolicyControlRequest, fkV2QoS4PolicyControlTimeStamp, fkV2QoS4PolicyControlReqResult, fkV2QoS4PolicyControlIndex, fkV2QoS4PolicyControlMatchOuterVlanCfiReplace
				 }
			STATUS current
			DESCRIPTION 
				"setMatchOuterVlanCfiReplace"
			::= { fkV2QoSPolicyNotification 16 }

		
		-- 1.3.6.1.4.1.10428 9 1.102.10.2.5.2
		fkV2QoS4PolicyFlowClass OBJECT IDENTIFIER ::= { fkV2QoS4Policy 2 }

		
		-- 1.3.6.1.4.1.10428 9 1.102.10.2.5.2.1
		fkV2QoS4PolicyFlowClassTable OBJECT-TYPE
			SYNTAX SEQUENCE OF FkV2QoS4PolicyFlowClassEntry
			MAX-ACCESS not-accessible
			STATUS current
			DESCRIPTION
				"flow class table."
			::= { fkV2QoS4PolicyFlowClass 1 }

		
		-- 1.3.6.1.4.1.10428 9 1.102.10.2.6.2.1.1
		fkV2QoS4PolicyFlowClassEntry OBJECT-TYPE
			SYNTAX FkV2QoS4PolicyFlowClassEntry
			MAX-ACCESS not-accessible
			STATUS current
			DESCRIPTION
				"key: fkV2QoS4PolicyIndex, fkV2QoS4PolicyFlowClassIndex"
			INDEX { fkV2QoS4PolicyIndex, fkV2QoS4PolicyFlowClassIndex }
			::= { fkV2QoS4PolicyFlowClassTable 1 }

		
		FkV2QoS4PolicyFlowClassEntry ::=
			SEQUENCE { 
				fkV2QoS4PolicyFlowClassIndex
					IntFlowIndex,
				fkV2QoS4PolicyFlowClassType
					IntFlowOrClass,
				fkV2QoS4PolicyFlowClassID
					IntFlowIndex,
				fkV2QoS4PolicyFlowClassName
					OctetName
			 }

		-- 1.3.6.1.4.1.10428 9 1.102.10.2.6.2.1.1.1
		fkV2QoS4PolicyFlowClassIndex OBJECT-TYPE
			SYNTAX IntFlowIndex
			MAX-ACCESS read-only
			STATUS current
			DESCRIPTION
				"The index of flow or class in policy"
			::= { fkV2QoS4PolicyFlowClassEntry 1 }

		
		-- 1.3.6.1.4.1.10428 9 1.102.10.2.6.2.1.1.2
		fkV2QoS4PolicyFlowClassType OBJECT-TYPE
			SYNTAX IntFlowOrClass
			MAX-ACCESS read-only
			STATUS current
			DESCRIPTION
				"The flag about flow or class"
			::= { fkV2QoS4PolicyFlowClassEntry 2 }

		
		-- 1.3.6.1.4.1.10428 9 1.102.10.2.6.2.1.1.3
		fkV2QoS4PolicyFlowClassID OBJECT-TYPE
			SYNTAX IntFlowIndex
			MAX-ACCESS read-only
			STATUS current
			DESCRIPTION
				"The identifier of class or flow"
			::= { fkV2QoS4PolicyFlowClassEntry 3 }

		
		-- 1.3.6.1.4.1.10428 9 1.102.10.2.6.2.1.1.4
		fkV2QoS4PolicyFlowClassName OBJECT-TYPE
			SYNTAX OctetName
			MAX-ACCESS read-only
			STATUS current
			DESCRIPTION
				"The name of class or flow"
			::= { fkV2QoS4PolicyFlowClassEntry 4 }

		
		-- 1.3.6.1.4.1.10428 9 1.102.10.2.5.2.2
		fkV2QoS4PolicyFlowClassControl OBJECT IDENTIFIER ::= { fkV2QoS4PolicyFlowClass 2 }

		
		-- 1.3.6.1.4.1.10428 9 1.102.10.2.5.2.2.1
		fkV2QoS4PolicyFlowClassControlRequest OBJECT-TYPE
			SYNTAX INTEGER
				{
				addFlowClass(1),
				deleteFlowClass(2),
				deleteAllFlow(3),
				deleteAllClass(4),
				deleteAllFlowClass(5)
				}
			MAX-ACCESS read-write
			STATUS current
			DESCRIPTION
				"The request of a user command"
			::= { fkV2QoS4PolicyFlowClassControl 1 }

		
		-- 1.3.6.1.4.1.10428 9 1.102.10.2.5.2.2.2
		fkV2QoS4PolicyFlowClassControlStatus OBJECT-TYPE
			SYNTAX FkControlStatusType
			MAX-ACCESS read-write
			STATUS current
			DESCRIPTION
				"The status of user command"
			::= { fkV2QoS4PolicyFlowClassControl 2 }

		
		-- 1.3.6.1.4.1.10428 9 1.102.10.2.5.2.2.3
		fkV2QoS4PolicyFlowClassControlTimer OBJECT-TYPE
			SYNTAX Gauge32
			MAX-ACCESS read-write
			STATUS current
			DESCRIPTION
				"The maximum time for the manager for a long running user command"
			::= { fkV2QoS4PolicyFlowClassControl 3 }

		
		-- 1.3.6.1.4.1.10428 9 1.102.10.2.5.2.2.4
		fkV2QoS4PolicyFlowClassControlTimeStamp OBJECT-TYPE
			SYNTAX TimeTicks
			MAX-ACCESS read-write
			STATUS current
			DESCRIPTION
				"The time stamp of the last command(end of command)"
			::= { fkV2QoS4PolicyFlowClassControl 4 }

		
		-- 1.3.6.1.4.1.10428 9 1.102.10.2.5.2.2.5
		fkV2QoS4PolicyFlowClassControlReqResult OBJECT-TYPE
			SYNTAX FkControlRequestResultType
			MAX-ACCESS read-write
			STATUS current
			DESCRIPTION
				"The result of the last user command"
			::= { fkV2QoS4PolicyFlowClassControl 5 }

		
		-- 1.3.6.1.4.1.10428 9 1.102.10.2.5.2.2.6
		fkV2QoS4PolicyFlowClassControlPolicyIndex OBJECT-TYPE
			SYNTAX IntPolicyIndex
			MAX-ACCESS read-write
			STATUS current
			DESCRIPTION
				"The index of Policy"
			::= { fkV2QoS4PolicyFlowClassControl 6 }

		
		-- 1.3.6.1.4.1.10428 9 1.102.10.2.5.2.2.7
		fkV2QoS4PolicyFlowClassControlIndex OBJECT-TYPE
			SYNTAX IntFlowIndex
			MAX-ACCESS read-write
			STATUS current
			DESCRIPTION
				"The index of flow or class in this policy"
			::= { fkV2QoS4PolicyFlowClassControl 7 }

		
		-- 1.3.6.1.4.1.10428 9 1.102.10.2.5.2.2.8
		fkV2QoS4PolicyFlowClassControlType OBJECT-TYPE
			SYNTAX IntFlowOrClass
			MAX-ACCESS read-write
			STATUS current
			DESCRIPTION
				"The type of flow or class"
			::= { fkV2QoS4PolicyFlowClassControl 8 }

		
		-- 1.3.6.1.4.1.10428 9 1.102.10.2.5.2.2.9
		fkV2QoS4PolicyFlowClassControlFlowID OBJECT-TYPE
			SYNTAX IntFlowIndex
			MAX-ACCESS read-write
			STATUS current
			DESCRIPTION
				"The index of flow
				Available according to fkV2QoS4PolicyFlowClassControlType.
				"
			::= { fkV2QoS4PolicyFlowClassControl 9 }

		
		-- 1.3.6.1.4.1.10428 9 1.102.10.2.5.2.2.10
		fkV2QoS4PolicyFlowClassControlClassID OBJECT-TYPE
			SYNTAX IntClassIndex
			MAX-ACCESS read-write
			STATUS current
			DESCRIPTION
				"The index of class
				Available according to fkV2QoS4PolicyFlowClassControlType.
				"
			::= { fkV2QoS4PolicyFlowClassControl 10 }

		
		-- 1.3.6.1.4.1.10428 9 1.102.10.2.5.2.3
		fkV2QoS4PolicyFlowClassNotification OBJECT IDENTIFIER ::= { fkV2QoS4PolicyFlowClass 3 }

		
		-- 1.3.6.1.4.1.10428 9 1.102.10.2.5.2.3.1
		fkPolicyFlowAdded NOTIFICATION-TYPE
			OBJECTS { fkV2QoS4PolicyFlowClassControlRequest, fkV2QoS4PolicyFlowClassControlTimeStamp, fkV2QoS4PolicyFlowClassControlReqResult, fkV2QoS4PolicyFlowClassType, fkV2QoS4PolicyFlowClassID
				 }
			STATUS current
			DESCRIPTION 
				"Description."
			::= { fkV2QoS4PolicyFlowClassNotification 1 }

		
		-- 1.3.6.1.4.1.10428 9 1.102.10.2.5.2.3.2
		fkPolicyFlowDeleted NOTIFICATION-TYPE
			OBJECTS { fkV2QoS4PolicyFlowClassControlRequest, fkV2QoS4PolicyFlowClassControlTimeStamp, fkV2QoS4PolicyFlowClassControlReqResult, fkV2QoS4PolicyFlowClassControlPolicyIndex, fkV2QoS4PolicyFlowClassControlIndex
				 }
			STATUS current
			DESCRIPTION 
				"Description."
			::= { fkV2QoS4PolicyFlowClassNotification 2 }

		
		-- 1.3.6.1.4.1.10428 9 1.102.10.2.5.2.3.3
		fkPolicyAllFlowDeleted NOTIFICATION-TYPE
			OBJECTS { fkV2QoS4PolicyFlowClassControlRequest, fkV2QoS4PolicyFlowClassControlTimeStamp, fkV2QoS4PolicyFlowClassControlReqResult, fkV2QoS4PolicyFlowClassControlPolicyIndex }
			STATUS current
			DESCRIPTION 
				"Description."
			::= { fkV2QoS4PolicyFlowClassNotification 3 }

		
		-- 1.3.6.1.4.1.10428 9 1.102.10.2.5.2.3.4
		fkPolicyAllClassDeleted NOTIFICATION-TYPE
			OBJECTS { fkV2QoS4PolicyFlowClassControlRequest, fkV2QoS4PolicyFlowClassControlTimeStamp, fkV2QoS4PolicyFlowClassControlReqResult, fkV2QoS4PolicyFlowClassControlPolicyIndex }
			STATUS current
			DESCRIPTION 
				"Description."
			::= { fkV2QoS4PolicyFlowClassNotification 4 }

		
		-- 1.3.6.1.4.1.10428 9 1.102.10.2.5.2.3.5
		fkPolicyAllFlowClassDeleted NOTIFICATION-TYPE
			OBJECTS { fkV2QoS4PolicyFlowClassControlRequest, fkV2QoS4PolicyFlowClassControlTimeStamp, fkV2QoS4PolicyFlowClassControlReqResult, fkV2QoS4PolicyFlowClassControlPolicyIndex }
			STATUS current
			DESCRIPTION 
				"Description."
			::= { fkV2QoS4PolicyFlowClassNotification 5 }

		
		-- 1.3.6.1.4.1.10428 9 1.102.10.2.5.3
		fkV2QoS4PolicyIF OBJECT IDENTIFIER ::= { fkV2QoS4Policy 3 }

		
--  1.3.6.1.4.1.10428 9 1.102.10.2.5.3.1
		-- 1.3.6.1.4.1.10428 9 1.102.10.2.5.3.1
		fkV2QoS4PolicyIFTable OBJECT-TYPE
			SYNTAX SEQUENCE OF FkV2QoS4PolicyIFEntry
			MAX-ACCESS not-accessible
			STATUS current
			DESCRIPTION
				"Description."
			::= { fkV2QoS4PolicyIF 1 }

		
--  1.3.6.1.4.1.10428 9 1.102.10.2.5.3.1.1
		-- 1.3.6.1.4.1.10428 9 1.102.10.2.5.3.1.1
		fkV2QoS4PolicyIFEntry OBJECT-TYPE
			SYNTAX FkV2QoS4PolicyIFEntry
			MAX-ACCESS not-accessible
			STATUS current
			DESCRIPTION
				"Description."
			INDEX { ifindex, fkV2QoS4PolicyIndex, fkV2QoS4PolicyIFDirection }
			::= { fkV2QoS4PolicyIFTable 1 }

		
		FkV2QoS4PolicyIFEntry ::=
			SEQUENCE { 
				fkV2QoS4PolicyIFDirection
					INTEGER
			 }

--  1.3.6.1.4.1.10428 9 1.102.10.2.5.3.1.1.1
		-- 1.3.6.1.4.1.10428 9 1.102.10.2.5.3.1.1.1
		fkV2QoS4PolicyIFDirection OBJECT-TYPE
			SYNTAX INTEGER
				{
				input(1),
				output(2)
				}
			MAX-ACCESS read-only
			STATUS current
			DESCRIPTION
				"Packet input/output direction"
			::= { fkV2QoS4PolicyIFEntry 1 }

		
		-- 1.3.6.1.4.1.10428 9 1.102.10.2.5.3.2
		fkV2QoS4PolicyIFControl OBJECT IDENTIFIER ::= { fkV2QoS4PolicyIF 2 }

		
		-- 1.3.6.1.4.1.10428 9 1.102.10.2.5.3.2.1
		fkV2QoS4PolicyIFControlRequest OBJECT-TYPE
			SYNTAX INTEGER
				{
				setServicePolicy(1),
				clearServicePolicy(2)
				}
			MAX-ACCESS read-write
			STATUS current
			DESCRIPTION
				"The request of a user command"
			::= { fkV2QoS4PolicyIFControl 1 }

		
		-- 1.3.6.1.4.1.10428 9 1.102.10.2.5.3.2.2
		fkV2QoS4PolicyIFControlStatus OBJECT-TYPE
			SYNTAX FkControlStatusType
			MAX-ACCESS read-only
			STATUS current
			DESCRIPTION
				"The status of user command"
			::= { fkV2QoS4PolicyIFControl 2 }

		
		-- 1.3.6.1.4.1.10428 9 1.102.10.2.5.3.2.3
		fkV2QoS4PolicyIFControlTimer OBJECT-TYPE
			SYNTAX Gauge32
			MAX-ACCESS read-write
			STATUS current
			DESCRIPTION
				"The maximum time for the manager for a long running user command"
			::= { fkV2QoS4PolicyIFControl 3 }

		
		-- 1.3.6.1.4.1.10428 9 1.102.10.2.5.3.2.4
		fkV2QoS4PolicyIFControlTimeStamp OBJECT-TYPE
			SYNTAX TimeTicks
			MAX-ACCESS read-only
			STATUS current
			DESCRIPTION
				"The time stamp of the last command(end of command)"
			::= { fkV2QoS4PolicyIFControl 4 }

		
		-- 1.3.6.1.4.1.10428 9 1.102.10.2.5.3.2.5
		fkV2QoS4PolicyIFControlReqResult OBJECT-TYPE
			SYNTAX FkControlRequestResultType
			MAX-ACCESS read-only
			STATUS current
			DESCRIPTION
				"The result of the last user command"
			::= { fkV2QoS4PolicyIFControl 5 }

		
		-- 1.3.6.1.4.1.10428 9 1.102.10.2.5.3.2.6
		fkV2QoS4PolicyIFControlIfindex OBJECT-TYPE
			SYNTAX Integer32
			MAX-ACCESS read-write
			STATUS current
			DESCRIPTION
				"The interface index."
			::= { fkV2QoS4PolicyIFControl 6 }

		
		-- 1.3.6.1.4.1.10428 9 1.102.10.2.5.3.2.7
		fkV2QoS4PolicyIFControlPolicyIndex OBJECT-TYPE
			SYNTAX IntPolicerIndex
			MAX-ACCESS read-write
			STATUS current
			DESCRIPTION
				"The Policy index."
			::= { fkV2QoS4PolicyIFControl 7 }

		
		-- 1.3.6.1.4.1.10428 9 1.102.10.2.5.3.2.8
		fkV2QoS4PolicyIFControlDirection OBJECT-TYPE
			SYNTAX INTEGER
				{
				input(1),
				output(2)
				}
			MAX-ACCESS read-write
			STATUS current
			DESCRIPTION
				"Packet input/output direction"
			::= { fkV2QoS4PolicyIFControl 8 }

		
		-- 1.3.6.1.4.1.10428 9 1.102.10.2.5.3.3
		fkV2QoS4PolicyIFNotification OBJECT IDENTIFIER ::= { fkV2QoS4PolicyIF 3 }

		
		-- 1.3.6.1.4.1.10428 9 1.102.10.2.5.3.3.1
		fkV2QosPolicyIFServicePolicyChanged NOTIFICATION-TYPE
			OBJECTS { fkV2QoS4PolicyIFControlRequest, fkV2QoS4PolicyIFControlTimeStamp, fkV2QoS4PolicyIFControlReqResult, fkV2QoS4PolicyIFControlIfindex, fkV2QoS4PolicyIFControlPolicyIndex, 
				fkV2QoS4PolicyIFControlDirection }
			STATUS current
			DESCRIPTION 
				"setServicePolicy"
			::= { fkV2QoS4PolicyIFNotification 1 }

		
		-- 1.3.6.1.4.1.10428 9 1.102.10.2.5.3.3.2
		fkV2QosPolicyIFServicePolicyCleared NOTIFICATION-TYPE
			OBJECTS { fkV2QoS4PolicyIFControlRequest, fkV2QoS4PolicyIFControlTimeStamp, fkV2QoS4PolicyIFControlReqResult, fkV2QoS4PolicyIFControlIfindex, fkV2QoS4PolicyIFControlPolicyIndex, 
				fkV2QoS4PolicyIFControlDirection }
			STATUS current
			DESCRIPTION 
				"setServicePolicy"
			::= { fkV2QoS4PolicyIFNotification 2 }

		
		-- 1.3.6.1.4.1.10428 9 1.102.10.2.6
		fkV2QoS4Remark OBJECT IDENTIFIER ::= { fkV2QoS4 6 }

		
		-- 1.3.6.1.4.1.10428 9 1.102.10.2.6.1
		fkV2QoS4RemarkBase OBJECT IDENTIFIER ::= { fkV2QoS4Remark 1 }

		
		-- 1.3.6.1.4.1.10428 9 1.102.10.2.6.1.1
		fkV2QoS4RemarkInfo OBJECT IDENTIFIER ::= { fkV2QoS4RemarkBase 1 }

		
		-- 1.3.6.1.4.1.10428 9 1.102.10.2.6.1.1.1
		fkV2QoS4RemarkLayer2Mode OBJECT-TYPE
			SYNTAX IntL2BaseRemarkMode
			MAX-ACCESS read-only
			STATUS current
			DESCRIPTION
				"The layer2 remark mode
				1 : remark based on queue (default)
				2 : remark based on 802.1p priority
				"
			::= { fkV2QoS4RemarkInfo 1 }

		
		-- 1.3.6.1.4.1.10428 9 1.102.10.2.6.1.1.2
		fkV2QoS4RemarkMode OBJECT-TYPE
			SYNTAX BITS
				{
				remarkPriorityIP(0),
				remarkByQueueOrCoS(1)
				}
			MAX-ACCESS read-only
			STATUS current
			DESCRIPTION
				"The remark mode
				0 : enable 801.1p-remark for IP packets
				1 : enable 801.1p-remark for Non-IP packets
				"
			::= { fkV2QoS4RemarkInfo 2 }

		
		-- 1.3.6.1.4.1.10428 9 1.102.10.2.6.1.2
		fkV2QoS4RemarkControl OBJECT IDENTIFIER ::= { fkV2QoS4RemarkBase 2 }

		
		-- 1.3.6.1.4.1.10428 9 1.102.10.2.6.1.2.1
		fkV2QoS4RemarkControlRequest OBJECT-TYPE
			SYNTAX INTEGER { setRemarkMode(1) }
			MAX-ACCESS read-write
			STATUS current
			DESCRIPTION
				"The request of a user command"
			::= { fkV2QoS4RemarkControl 1 }

		
		-- 1.3.6.1.4.1.10428 9 1.102.10.2.6.1.2.2
		fkV2QoS4RemarkControlStatus OBJECT-TYPE
			SYNTAX FkControlStatusType
			MAX-ACCESS read-write
			STATUS current
			DESCRIPTION
				"The status of user command"
			::= { fkV2QoS4RemarkControl 2 }

		
		-- 1.3.6.1.4.1.10428 9 1.102.10.2.6.1.2.3
		fkV2QoS4RemarkControlTimer OBJECT-TYPE
			SYNTAX Gauge32
			MAX-ACCESS read-write
			STATUS current
			DESCRIPTION
				"The maximum time for the manager for a long running user command"
			::= { fkV2QoS4RemarkControl 3 }

		
		-- 1.3.6.1.4.1.10428 9 1.102.10.2.6.1.2.4
		fkV2QoS4RemarkControlTimStamp OBJECT-TYPE
			SYNTAX TimeTicks
			MAX-ACCESS read-write
			STATUS current
			DESCRIPTION
				"The time stamp of the last command(end of command)"
			::= { fkV2QoS4RemarkControl 4 }

		
		-- 1.3.6.1.4.1.10428 9 1.102.10.2.6.1.2.5
		fkV2QoS4RemarkControlReqResult OBJECT-TYPE
			SYNTAX FkControlRequestResultType
			MAX-ACCESS read-write
			STATUS current
			DESCRIPTION
				"The result of the last user command"
			::= { fkV2QoS4RemarkControl 5 }

		
		-- 1.3.6.1.4.1.10428 9 1.102.10.2.6.1.2.6
		fkV2QoS4RemarkControlLayer2Mode OBJECT-TYPE
			SYNTAX IntL2BaseRemarkMode
			MAX-ACCESS read-write
			STATUS current
			DESCRIPTION
				"The layer2 remark mode
				-1: default (remarkByQueue)
				1 : remark by queue
				2 : remark by priority
				"
			::= { fkV2QoS4RemarkControl 6 }

		
		-- 1.3.6.1.4.1.10428 9 1.102.10.2.6.1.2.7
		fkV2QoS4RemarkControlMode OBJECT-TYPE
			SYNTAX BITS
				{
				remarkByDSCP(0),
				remarkByQueueOrCoS(1)
				}
			MAX-ACCESS read-write
			STATUS current
			DESCRIPTION
				"The remark mode
				0 : enable 801.1p-remark for IP packets
				1 : enable 801.1p-remark for Non-IP packets
				"
			::= { fkV2QoS4RemarkControl 7 }

		
		-- 1.3.6.1.4.1.10428 9 1.102.10.2.6.1.3
		fkV2QoS4RemarkNotification OBJECT IDENTIFIER ::= { fkV2QoS4RemarkBase 3 }

		
		-- 1.3.6.1.4.1.10428 9 1.102.10.2.6.1.3.1
		fkRemarkChanged NOTIFICATION-TYPE
			OBJECTS { fkV2QoS4RemarkControlRequest, fkV2QoS4RemarkControlTimStamp, fkV2QoS4RemarkControlReqResult, fkV2QoS4RemarkLayer2Mode, fkV2QoS4RemarkMode
				 }
			STATUS current
			DESCRIPTION 
				"Description."
			::= { fkV2QoS4RemarkNotification 1 }

		
		-- 1.3.6.1.4.1.10428 9 1.102.10.2.6.2
		fkV2QoS4RemarkL3 OBJECT IDENTIFIER ::= { fkV2QoS4Remark 2 }

		
		-- 1.3.6.1.4.1.10428 9 1.102.10.2.6.2.1
		fkV2QoS4RemarkL3Table OBJECT-TYPE
			SYNTAX SEQUENCE OF FkV2QoS4RemarkL3Entry
			MAX-ACCESS not-accessible
			STATUS current
			DESCRIPTION
				"remark L3 table."
			::= { fkV2QoS4RemarkL3 1 }

		
		-- 1.3.6.1.4.1.10428 9 1.102.10.2.7.2.1.1
		fkV2QoS4RemarkL3Entry OBJECT-TYPE
			SYNTAX FkV2QoS4RemarkL3Entry
			MAX-ACCESS not-accessible
			STATUS current
			DESCRIPTION
				"key: fkV2QoS4RemarkL3ColorIndex, fkV2QoS4RemarkL3DSCPIndex"
			INDEX { fkV2QoS4RemarkL3ColorIndex, fkV2QoS4RemarkL3DSCPIndex }
			::= { fkV2QoS4RemarkL3Table 1 }

		
		FkV2QoS4RemarkL3Entry ::=
			SEQUENCE { 
				fkV2QoS4RemarkL3ColorIndex
					IntColorIndex,
				fkV2QoS4RemarkL3DSCPIndex
					IntDSCPIndex,
				fkV2QoS4RemarkL3Queue
					IntQueue,
				fkV2QoS4RemarkL3Dp
					IntDP,
				fkV2QoS4RemarkL3CoS
					IntCoS,
				fkV2QoS4RemarkL3Dscp
					IntDscp
			 }

		-- 1.3.6.1.4.1.10428 9 1.102.10.2.7.2.1.1.1
		fkV2QoS4RemarkL3ColorIndex OBJECT-TYPE
			SYNTAX IntColorIndex
			MAX-ACCESS read-only
			STATUS current
			DESCRIPTION
				"The index of color"
			::= { fkV2QoS4RemarkL3Entry 1 }

		
		-- 1.3.6.1.4.1.10428 9 1.102.10.2.7.2.1.1.2
		fkV2QoS4RemarkL3DSCPIndex OBJECT-TYPE
			SYNTAX IntDSCPIndex
			MAX-ACCESS read-only
			STATUS current
			DESCRIPTION
				"The index of DSCP
				The index value of 1~ 64 mean 0 ~ 63 of the DSCP
				"
			::= { fkV2QoS4RemarkL3Entry 2 }

		
		-- 1.3.6.1.4.1.10428 9 1.102.10.2.7.2.1.1.3
		fkV2QoS4RemarkL3Queue OBJECT-TYPE
			SYNTAX IntQueue
			MAX-ACCESS read-only
			STATUS current
			DESCRIPTION
				"This is remarking to queue by Color and DSCP
				0 : default
				"
			::= { fkV2QoS4RemarkL3Entry 3 }

		
		-- 1.3.6.1.4.1.10428 9 1.102.10.2.7.2.1.1.4
		fkV2QoS4RemarkL3Dp OBJECT-TYPE
			SYNTAX IntDP
			MAX-ACCESS read-only
			STATUS current
			DESCRIPTION
				"This is remarking to drop precednece by Color and DSCP
				0 : default
				"
			::= { fkV2QoS4RemarkL3Entry 4 }

		
		-- 1.3.6.1.4.1.10428 9 1.102.10.2.7.2.1.1.5
		fkV2QoS4RemarkL3CoS OBJECT-TYPE
			SYNTAX IntCoS
			MAX-ACCESS read-only
			STATUS current
			DESCRIPTION
				"This is remarking to CoS by Color and DSCP
				0 : default
				"
			::= { fkV2QoS4RemarkL3Entry 5 }

		
		-- 1.3.6.1.4.1.10428 9 1.102.10.2.7.2.1.1.6
		fkV2QoS4RemarkL3Dscp OBJECT-TYPE
			SYNTAX IntDscp
			MAX-ACCESS read-only
			STATUS current
			DESCRIPTION
				"This is remarking to DSCP by Color and DSCP
				0 : default
				"
			::= { fkV2QoS4RemarkL3Entry 6 }

		
		-- 1.3.6.1.4.1.10428 9 1.102.10.2.6.2.2
		fkV2QoS4RemarkL3Control OBJECT IDENTIFIER ::= { fkV2QoS4RemarkL3 2 }

		
		-- 1.3.6.1.4.1.10428 9 1.102.10.2.6.2.2.1
		fkV2QoS4RemarkL3ControlRequest OBJECT-TYPE
			SYNTAX INTEGER { setL3Remark(1) }
			MAX-ACCESS read-write
			STATUS current
			DESCRIPTION
				"The request of a user command"
			::= { fkV2QoS4RemarkL3Control 1 }

		
		-- 1.3.6.1.4.1.10428 9 1.102.10.2.6.2.2.2
		fkV2QoS4RemarkL3ControlStatus OBJECT-TYPE
			SYNTAX FkControlStatusType
			MAX-ACCESS read-write
			STATUS current
			DESCRIPTION
				"The status of user command"
			::= { fkV2QoS4RemarkL3Control 2 }

		
		-- 1.3.6.1.4.1.10428 9 1.102.10.2.6.2.2.3
		fkV2QoS4RemarkL3ControlTimer OBJECT-TYPE
			SYNTAX Gauge32
			MAX-ACCESS read-write
			STATUS current
			DESCRIPTION
				"The maximum time for the manager for a long running user command"
			::= { fkV2QoS4RemarkL3Control 3 }

		
		-- 1.3.6.1.4.1.10428 9 1.102.10.2.6.2.2.4
		fkV2QoS4RemarkL3ControlTimeStamp OBJECT-TYPE
			SYNTAX TimeTicks
			MAX-ACCESS read-write
			STATUS current
			DESCRIPTION
				"The time stamp of the last command(end of command)"
			::= { fkV2QoS4RemarkL3Control 4 }

		
		-- 1.3.6.1.4.1.10428 9 1.102.10.2.6.2.2.5
		fkV2QoS4RemarkL3ControlReqResult OBJECT-TYPE
			SYNTAX FkControlRequestResultType
			MAX-ACCESS read-write
			STATUS current
			DESCRIPTION
				"The result of the last user command"
			::= { fkV2QoS4RemarkL3Control 5 }

		
		-- 1.3.6.1.4.1.10428 9 1.102.10.2.6.2.2.6
		fkV2QoS4RemarkL3ControlColorIndex OBJECT-TYPE
			SYNTAX IntColorIndex
			MAX-ACCESS read-write
			STATUS current
			DESCRIPTION
				"The index of color marking"
			::= { fkV2QoS4RemarkL3Control 6 }

		
		-- 1.3.6.1.4.1.10428 9 1.102.10.2.6.2.2.7
		fkV2QoS4RemarkL3ControlDSCPIndex OBJECT-TYPE
			SYNTAX IntDSCPIndex
			MAX-ACCESS read-write
			STATUS current
			DESCRIPTION
				"The index of DSCP
				The index value of 1~ 64 mean 0 ~ 63 of the DSCP
				"
			::= { fkV2QoS4RemarkL3Control 7 }

		
		-- 1.3.6.1.4.1.10428 9 1.102.10.2.6.2.2.8
		fkV2QoS4RemarkL3ControlQueue OBJECT-TYPE
			SYNTAX IntQueue
			MAX-ACCESS read-write
			STATUS current
			DESCRIPTION
				"This is remarking to queue by Color and DSCP
				The value of -1 means nothing(not set)
				"
			::= { fkV2QoS4RemarkL3Control 8 }

		
		-- 1.3.6.1.4.1.10428 9 1.102.10.2.6.2.2.9
		fkV2QoS4RemarkL3ControlDp OBJECT-TYPE
			SYNTAX IntDP
			MAX-ACCESS read-write
			STATUS current
			DESCRIPTION
				"This is remarking to drop precednece by Color and DSCP
				The value of -1 means nothing(not set)
				"
			::= { fkV2QoS4RemarkL3Control 9 }

		
		-- 1.3.6.1.4.1.10428 9 1.102.10.2.6.2.2.10
		fkV2QoS4RemarkL3ControlCoS OBJECT-TYPE
			SYNTAX IntCoS
			MAX-ACCESS read-write
			STATUS current
			DESCRIPTION
				"This is remarking to CoS by Color and DSCP
				The value of -1 means nothing(not set)
				"
			::= { fkV2QoS4RemarkL3Control 10 }

		
		-- 1.3.6.1.4.1.10428 9 1.102.10.2.6.2.2.11
		fkV2QoS4RemarkL3ControlDscp OBJECT-TYPE
			SYNTAX IntDscp
			MAX-ACCESS read-write
			STATUS current
			DESCRIPTION
				"This is remarking to DSCP by Color and DSCP
				The value of -1 means nothing(not set)
				"
			::= { fkV2QoS4RemarkL3Control 11 }

		
		-- 1.3.6.1.4.1.10428 9 1.102.10.2.6.2.3
		fkV2QoS4RemarkL3Notification OBJECT IDENTIFIER ::= { fkV2QoS4RemarkL3 3 }

		
		-- 1.3.6.1.4.1.10428 9 1.102.10.2.6.2.3.1
		fkRemarkL3Changed NOTIFICATION-TYPE
			OBJECTS { fkV2QoS4RemarkL3ControlRequest, fkV2QoS4RemarkL3ControlTimeStamp, fkV2QoS4RemarkL3ControlReqResult, fkV2QoS4RemarkL3Queue, fkV2QoS4RemarkL3Dp, 
				fkV2QoS4RemarkL3CoS, fkV2QoS4RemarkL3Dscp }
			STATUS current
			DESCRIPTION 
				"Description."
			::= { fkV2QoS4RemarkL3Notification 1 }

		
		-- 1.3.6.1.4.1.10428 9 1.102.10.2.6.3
		fkV2QoS4RemarkL2 OBJECT IDENTIFIER ::= { fkV2QoS4Remark 3 }

		
		-- 1.3.6.1.4.1.10428 9 1.102.10.2.6.3.1
		fkV2QoS4RemarkL2Table OBJECT-TYPE
			SYNTAX SEQUENCE OF FkV2QoS4RemarkL2Entry
			MAX-ACCESS not-accessible
			STATUS current
			DESCRIPTION
				"remark L2 table."
			::= { fkV2QoS4RemarkL2 1 }

		
		-- 1.3.6.1.4.1.10428 9 1.102.10.2.7.3.1.1
		fkV2QoS4RemarkL2Entry OBJECT-TYPE
			SYNTAX FkV2QoS4RemarkL2Entry
			MAX-ACCESS not-accessible
			STATUS current
			DESCRIPTION
				"key: fkV2QoS4RemarkL2ColorIndex, fkV2QoS4RemarkL2QueueCoSIndex"
			INDEX { fkV2QoS4RemarkL2ColorIndex, fkV2QoS4RemarkL2QueueCoSIndex }
			::= { fkV2QoS4RemarkL2Table 1 }

		
		FkV2QoS4RemarkL2Entry ::=
			SEQUENCE { 
				fkV2QoS4RemarkL2ColorIndex
					IntColorIndex,
				fkV2QoS4RemarkL2QueueCoSIndex
					IntQueueCoSIndex,
				fkV2QoS4RemarkL2Queue
					IntQueue,
				fkV2QoS4RemarkL2Dp
					IntDP,
				fkV2QoS4RemarkL2CoS
					IntCoS,
				fkV2QoS4RemarkL2Dscp
					IntDscp
			 }

		-- 1.3.6.1.4.1.10428 9 1.102.10.2.7.3.1.1.1
		fkV2QoS4RemarkL2ColorIndex OBJECT-TYPE
			SYNTAX IntColorIndex
			MAX-ACCESS read-only
			STATUS current
			DESCRIPTION
				"The index of color marking"
			::= { fkV2QoS4RemarkL2Entry 1 }

		
		-- 1.3.6.1.4.1.10428 9 1.102.10.2.7.3.1.1.2
		fkV2QoS4RemarkL2QueueCoSIndex OBJECT-TYPE
			SYNTAX IntQueueCoSIndex
			MAX-ACCESS read-only
			STATUS current
			DESCRIPTION
				"The index of queue or CoS
				The index value of 1~ 8 mean 0 ~ 7 of the queue and CoS
				Refer to fkV2QoS4RemarkLayer2Mode
				"
			::= { fkV2QoS4RemarkL2Entry 2 }

		
		-- 1.3.6.1.4.1.10428 9 1.102.10.2.7.3.1.1.3
		fkV2QoS4RemarkL2Queue OBJECT-TYPE
			SYNTAX IntQueue
			MAX-ACCESS read-only
			STATUS current
			DESCRIPTION
				"This is remarking to queue by Color and L2(queue or CoS)
				0 : default
				"
			::= { fkV2QoS4RemarkL2Entry 3 }

		
		-- 1.3.6.1.4.1.10428 9 1.102.10.2.7.3.1.1.4
		fkV2QoS4RemarkL2Dp OBJECT-TYPE
			SYNTAX IntDP
			MAX-ACCESS read-only
			STATUS current
			DESCRIPTION
				"This is remarking to drop precednece by L2(queue or CoS)
				0 : default
				"
			::= { fkV2QoS4RemarkL2Entry 4 }

		
		-- 1.3.6.1.4.1.10428 9 1.102.10.2.7.3.1.1.5
		fkV2QoS4RemarkL2CoS OBJECT-TYPE
			SYNTAX IntCoS
			MAX-ACCESS read-only
			STATUS current
			DESCRIPTION
				"This is remarking to CoS by Color and L2(queue or CoS)
				0 : default
				"
			::= { fkV2QoS4RemarkL2Entry 5 }

		
		-- 1.3.6.1.4.1.10428 9 1.102.10.2.7.3.1.1.6
		fkV2QoS4RemarkL2Dscp OBJECT-TYPE
			SYNTAX IntDscp
			MAX-ACCESS read-only
			STATUS current
			DESCRIPTION
				"This is remarking to DSCP by Color and L2(queue or CoS)
				0 : default
				"
			::= { fkV2QoS4RemarkL2Entry 6 }

		
		-- 1.3.6.1.4.1.10428 9 1.102.10.2.6.3.2
		fkV2QoS4RemarkL2Control OBJECT IDENTIFIER ::= { fkV2QoS4RemarkL2 2 }

		
		-- 1.3.6.1.4.1.10428 9 1.102.10.2.6.3.2.1
		fkV2QoS4RemarkL2ControlRequest OBJECT-TYPE
			SYNTAX INTEGER { setL2Remark(1) }
			MAX-ACCESS read-write
			STATUS current
			DESCRIPTION
				"The request of a user command"
			::= { fkV2QoS4RemarkL2Control 1 }

		
		-- 1.3.6.1.4.1.10428 9 1.102.10.2.6.3.2.2
		fkV2QoS4RemarkL2ControlStatus OBJECT-TYPE
			SYNTAX FkControlStatusType
			MAX-ACCESS read-write
			STATUS current
			DESCRIPTION
				"The status of user command"
			::= { fkV2QoS4RemarkL2Control 2 }

		
		-- 1.3.6.1.4.1.10428 9 1.102.10.2.6.3.2.3
		fkV2QoS4RemarkL2ControlTimer OBJECT-TYPE
			SYNTAX Gauge32
			MAX-ACCESS read-write
			STATUS current
			DESCRIPTION
				"The maximum time for the manager for a long running user command"
			::= { fkV2QoS4RemarkL2Control 3 }

		
		-- 1.3.6.1.4.1.10428 9 1.102.10.2.6.3.2.4
		fkV2QoS4RemarkL2ControlTimeStamp OBJECT-TYPE
			SYNTAX TimeTicks
			MAX-ACCESS read-write
			STATUS current
			DESCRIPTION
				"The time stamp of the last command(end of command)"
			::= { fkV2QoS4RemarkL2Control 4 }

		
		-- 1.3.6.1.4.1.10428 9 1.102.10.2.6.3.2.5
		fkV2QoS4RemarkL2ControlReqResult OBJECT-TYPE
			SYNTAX FkControlRequestResultType
			MAX-ACCESS read-write
			STATUS current
			DESCRIPTION
				"The result of the last user command"
			::= { fkV2QoS4RemarkL2Control 5 }

		
		-- 1.3.6.1.4.1.10428 9 1.102.10.2.6.3.2.6
		fkV2QoS4RemarkL2ControlColorIndex OBJECT-TYPE
			SYNTAX IntColorIndex
			MAX-ACCESS read-write
			STATUS current
			DESCRIPTION
				"The index of color marking"
			::= { fkV2QoS4RemarkL2Control 6 }

		
		-- 1.3.6.1.4.1.10428 9 1.102.10.2.6.3.2.7
		fkV2QoS4RemarkL2ControlQueueCoSIndex OBJECT-TYPE
			SYNTAX IntQueueCoSIndex
			MAX-ACCESS read-write
			STATUS current
			DESCRIPTION
				"The index of queue or CoS
				The index value of 1~ 8 mean 0 ~ 7 of the queue and CoS
				Refer to fkV2QoS4RemarkLayer2Mod
				"
			::= { fkV2QoS4RemarkL2Control 7 }

		
		-- 1.3.6.1.4.1.10428 9 1.102.10.2.6.3.2.8
		fkV2QoS4RemarkL2ControlQueue OBJECT-TYPE
			SYNTAX IntQueue
			MAX-ACCESS read-write
			STATUS current
			DESCRIPTION
				"This is remarking to queue by Color and L2(queue or CoS)
				The value of -1 means nothing(not set)
				"
			::= { fkV2QoS4RemarkL2Control 8 }

		
		-- 1.3.6.1.4.1.10428 9 1.102.10.2.6.3.2.9
		fkV2QoS4RemarkL2ControlDp OBJECT-TYPE
			SYNTAX IntDP
			MAX-ACCESS read-write
			STATUS current
			DESCRIPTION
				"This is remarking to drop precednece by L2(queue or CoS)
				The value of -1 means nothing(not set)
				"
			::= { fkV2QoS4RemarkL2Control 9 }

		
		-- 1.3.6.1.4.1.10428 9 1.102.10.2.6.3.2.10
		fkV2QoS4RemarkL2ControlCoS OBJECT-TYPE
			SYNTAX IntCoS
			MAX-ACCESS read-write
			STATUS current
			DESCRIPTION
				"This is remarking to CoS by Color and L2(queue or CoS)
				The value of -1 means nothing(not set)
				"
			::= { fkV2QoS4RemarkL2Control 10 }

		
		-- 1.3.6.1.4.1.10428 9 1.102.10.2.6.3.2.11
		fkV2QoS4RemarkL2ControlDscp OBJECT-TYPE
			SYNTAX IntDscp
			MAX-ACCESS read-write
			STATUS current
			DESCRIPTION
				"This is remarking to DSCP by Color and L2(queue or CoS)
				The value of -1 means nothing(not set)
				"
			::= { fkV2QoS4RemarkL2Control 11 }

		
		-- 1.3.6.1.4.1.10428 9 1.102.10.2.6.3.3
		fkV2QoS4RemarkL2Notification OBJECT IDENTIFIER ::= { fkV2QoS4RemarkL2 3 }

		
		-- 1.3.6.1.4.1.10428 9 1.102.10.2.6.3.3.1
		fkRemarkL2Changed NOTIFICATION-TYPE
			OBJECTS { fkV2QoS4RemarkL2ControlRequest, fkV2QoS4RemarkL2ControlTimeStamp, fkV2QoS4RemarkL2ControlReqResult, fkV2QoS4RemarkL2Queue, fkV2QoS4RemarkL2Dp, 
				fkV2QoS4RemarkL2CoS, fkV2QoS4RemarkL2Dscp }
			STATUS current
			DESCRIPTION 
				"Description."
			::= { fkV2QoS4RemarkL2Notification 1 }

		
		-- 1.3.6.1.4.1.10428 9 1.102.10.2.7
		fkV2QoS4RED OBJECT IDENTIFIER ::= { fkV2QoS4 7 }

		
		-- 1.3.6.1.4.1.10428 9 1.102.10.2.7.1
		fkV2QoS4REDProfile OBJECT IDENTIFIER ::= { fkV2QoS4RED 1 }

		
		-- 1.3.6.1.4.1.10428 9 1.102.10.2.7.1.1
		fkV2QoS4REDProfileTable OBJECT-TYPE
			SYNTAX SEQUENCE OF FkV2QoS4REDProfileEntry
			MAX-ACCESS not-accessible
			STATUS current
			DESCRIPTION
				"redundancy profile table."
			::= { fkV2QoS4REDProfile 1 }

		
		-- 1.3.6.1.4.1.10428 9 1.102.10.2.8.1.1.1
		fkV2QoS4REDProfileEntry OBJECT-TYPE
			SYNTAX FkV2QoS4REDProfileEntry
			MAX-ACCESS not-accessible
			STATUS current
			DESCRIPTION
				"key: fkV2QoS4REDProfileId, fkV2QoS4REDProfileQueueId"
			INDEX { fkV2QoS4REDProfileId, fkV2QoS4REDProfileQueueId }
			::= { fkV2QoS4REDProfileTable 1 }

		
		FkV2QoS4REDProfileEntry ::=
			SEQUENCE { 
				fkV2QoS4REDProfileId
					INTEGER,
				fkV2QoS4REDProfileQueueId
					INTEGER,
				fkV2QoS4REDProfileDp0MinThres
					INTEGER,
				fkV2QoS4REDProfileDp0MaxThres
					INTEGER,
				fkV2QoS4REDProfileDp0Prob
					INTEGER,
				fkV2QoS4REDProfileDp1MinThres
					INTEGER,
				fkV2QoS4REDProfileDp1MaxThres
					INTEGER,
				fkV2QoS4REDProfileDp1Prob
					INTEGER,
				fkV2QoS4REDProfileDp2MinThres
					INTEGER,
				fkV2QoS4REDProfileDp2MaxThres
					INTEGER,
				fkV2QoS4REDProfileDp2Prob
					INTEGER,
				fkV2QoS4REDProfileWeight
					INTEGER
			 }

		-- 1.3.6.1.4.1.10428 9 1.102.10.2.8.1.1.1.1
		fkV2QoS4REDProfileId OBJECT-TYPE
			SYNTAX INTEGER (1..255)
			MAX-ACCESS read-only
			STATUS current
			DESCRIPTION
				"The index of RED profile.
				Marvell : (1..4), BCM : number of ports."
			::= { fkV2QoS4REDProfileEntry 1 }

		
		-- 1.3.6.1.4.1.10428 9 1.102.10.2.8.1.1.1.2
		fkV2QoS4REDProfileQueueId OBJECT-TYPE
			SYNTAX INTEGER (1..8)
			MAX-ACCESS read-only
			STATUS current
			DESCRIPTION
				"The index of queue."
			::= { fkV2QoS4REDProfileEntry 2 }

		
		-- 1.3.6.1.4.1.10428 9 1.102.10.2.8.1.1.1.3
		fkV2QoS4REDProfileDp0MinThres OBJECT-TYPE
			SYNTAX INTEGER (-1 | 0..65535)
			MAX-ACCESS read-only
			STATUS current
			DESCRIPTION
				"DP0 min threshold.
				In case RED, used as RED min threshold.
				Marvell : (1..65535), BCM : (0..127)"
			::= { fkV2QoS4REDProfileEntry 3 }

		
		-- 1.3.6.1.4.1.10428 9 1.102.10.2.8.1.1.1.4
		fkV2QoS4REDProfileDp0MaxThres OBJECT-TYPE
			SYNTAX INTEGER (-1 | 0..65535)
			MAX-ACCESS read-only
			STATUS current
			DESCRIPTION
				"DP0 max threshold.
				Used only in case WRED.
				Marvell : (1..65535), BCM : not supported."
			::= { fkV2QoS4REDProfileEntry 4 }

		
		-- 1.3.6.1.4.1.10428 9 1.102.10.2.8.1.1.1.5
		fkV2QoS4REDProfileDp0Prob OBJECT-TYPE
			SYNTAX INTEGER (-1 | 1..15)
			MAX-ACCESS read-only
			STATUS current
			DESCRIPTION
				"DP0 drop probability.
				In case RED, used as RED prob"
			::= { fkV2QoS4REDProfileEntry 5 }

		
		-- 1.3.6.1.4.1.10428 9 1.102.10.2.8.1.1.1.6
		fkV2QoS4REDProfileDp1MinThres OBJECT-TYPE
			SYNTAX INTEGER (-1 | 0..65535)
			MAX-ACCESS read-only
			STATUS current
			DESCRIPTION
				"DP1 min threshold. Used only in case WRED
				Marvell : (1..65535), BCM : not supported."
			::= { fkV2QoS4REDProfileEntry 6 }

		
		-- 1.3.6.1.4.1.10428 9 1.102.10.2.8.1.1.1.7
		fkV2QoS4REDProfileDp1MaxThres OBJECT-TYPE
			SYNTAX INTEGER (-1 | 0..65535)
			MAX-ACCESS read-only
			STATUS current
			DESCRIPTION
				"DP1 max threshold. Used only in case WRED
				Marvell : (1..65535), BCM : not supported."
			::= { fkV2QoS4REDProfileEntry 7 }

		
		-- 1.3.6.1.4.1.10428 9 1.102.10.2.8.1.1.1.8
		fkV2QoS4REDProfileDp1Prob OBJECT-TYPE
			SYNTAX INTEGER (-1 | 1..15)
			MAX-ACCESS read-only
			STATUS current
			DESCRIPTION
				"DP1 drop probability."
			::= { fkV2QoS4REDProfileEntry 8 }

		
		-- 1.3.6.1.4.1.10428 9 1.102.10.2.8.1.1.1.9
		fkV2QoS4REDProfileDp2MinThres OBJECT-TYPE
			SYNTAX INTEGER (-1 | 0..65535)
			MAX-ACCESS read-only
			STATUS current
			DESCRIPTION
				"DP2 min threshold. Used only in case WRED
				Marvell : (1..65535), BCM : not supported."
			::= { fkV2QoS4REDProfileEntry 9 }

		
		-- 1.3.6.1.4.1.10428 9 1.102.10.2.8.1.1.1.10
		fkV2QoS4REDProfileDp2MaxThres OBJECT-TYPE
			SYNTAX INTEGER (-1 | 0..65535)
			MAX-ACCESS read-only
			STATUS current
			DESCRIPTION
				"DP2 max threshold. Used only in case WRED
				Marvell : (1..65535), BCM : not supported."
			::= { fkV2QoS4REDProfileEntry 10 }

		
		-- 1.3.6.1.4.1.10428 9 1.102.10.2.8.1.1.1.11
		fkV2QoS4REDProfileDp2Prob OBJECT-TYPE
			SYNTAX INTEGER (-1 | 1..15)
			MAX-ACCESS read-only
			STATUS current
			DESCRIPTION
				"DP2 drop probability."
			::= { fkV2QoS4REDProfileEntry 11 }

		
		-- 1.3.6.1.4.1.10428 9 1.102.10.2.8.1.1.1.12
		fkV2QoS4REDProfileWeight OBJECT-TYPE
			SYNTAX INTEGER (-1 | 1..15)
			MAX-ACCESS read-only
			STATUS current
			DESCRIPTION
				"Drop weight, Used only in case WRED.
				BCM : not supported."
			::= { fkV2QoS4REDProfileEntry 12 }

		
		-- 1.3.6.1.4.1.10428 9 1.102.10.2.7.1.2
		fkV2QoS4REDProfileControl OBJECT IDENTIFIER ::= { fkV2QoS4REDProfile 2 }

		
		-- 1.3.6.1.4.1.10428 9 1.102.10.2.7.1.2.1
		fkV2QoS4REDProfileControlRequest OBJECT-TYPE
			SYNTAX INTEGER
				{
				setREDProfile(1),
				clearREDProfile(2)
				}
			MAX-ACCESS read-write
			STATUS current
			DESCRIPTION
				"The request of a user command"
			::= { fkV2QoS4REDProfileControl 1 }

		
		-- 1.3.6.1.4.1.10428 9 1.102.10.2.7.1.2.2
		fkV2QoS4REDProfileControlStatus OBJECT-TYPE
			SYNTAX FkControlStatusType
			MAX-ACCESS read-only
			STATUS current
			DESCRIPTION
				"The status of user command"
			::= { fkV2QoS4REDProfileControl 2 }

		
		-- 1.3.6.1.4.1.10428 9 1.102.10.2.7.1.2.3
		fkV2QoS4REDProfileControlTimer OBJECT-TYPE
			SYNTAX Gauge32
			MAX-ACCESS read-write
			STATUS current
			DESCRIPTION
				"The maximum time for the manager for a long running user command"
			::= { fkV2QoS4REDProfileControl 3 }

		
		-- 1.3.6.1.4.1.10428 9 1.102.10.2.7.1.2.4
		fkV2QoS4REDProfileControlTimeStamp OBJECT-TYPE
			SYNTAX TimeTicks
			MAX-ACCESS read-only
			STATUS current
			DESCRIPTION
				"The time stamp of the last command(end of command)"
			::= { fkV2QoS4REDProfileControl 4 }

		
		-- 1.3.6.1.4.1.10428 9 1.102.10.2.7.1.2.5
		fkV2QoS4REDProfileControlReqResult OBJECT-TYPE
			SYNTAX FkControlRequestResultType
			MAX-ACCESS read-only
			STATUS current
			DESCRIPTION
				"The result of the last user command"
			::= { fkV2QoS4REDProfileControl 5 }

		
		-- 1.3.6.1.4.1.10428 9 1.102.10.2.7.1.2.6
		fkV2QoS4REDProfileControlId OBJECT-TYPE
			SYNTAX INTEGER (1..255)
			MAX-ACCESS read-write
			STATUS current
			DESCRIPTION
				"The index of RED profile.
				Marvell (1..4), BCM : number of ports"
			::= { fkV2QoS4REDProfileControl 6 }

		
		-- 1.3.6.1.4.1.10428 9 1.102.10.2.7.1.2.7
		fkV2QoS4REDProfileControlQueueId OBJECT-TYPE
			SYNTAX INTEGER (1..8)
			MAX-ACCESS read-write
			STATUS current
			DESCRIPTION
				"The index of queues"
			::= { fkV2QoS4REDProfileControl 7 }

		
		-- 1.3.6.1.4.1.10428 9 1.102.10.2.7.1.2.8
		fkV2QoS4REDProfileControlDp0MinThres OBJECT-TYPE
			SYNTAX INTEGER (-1 | 0..65535)
			MAX-ACCESS read-write
			STATUS current
			DESCRIPTION
				"DP0 min threshold.
				In case RED, used as RED min threshold.
				Marvell (1..65535), BCM (0..127)"
			::= { fkV2QoS4REDProfileControl 8 }

		
		-- 1.3.6.1.4.1.10428 9 1.102.10.2.7.1.2.9
		fkV2QoS4REDProfileControlDp0MaxThres OBJECT-TYPE
			SYNTAX INTEGER (-1 | 0..65535)
			MAX-ACCESS read-write
			STATUS current
			DESCRIPTION
				"DP0 max threshold.
				Used only in case WRED.
				Marvell (1..65535), BCM: not supported"
			::= { fkV2QoS4REDProfileControl 9 }

		
		-- 1.3.6.1.4.1.10428 9 1.102.10.2.7.1.2.10
		fkV2QoS4REDProfileControlDp0Prob OBJECT-TYPE
			SYNTAX INTEGER (-1 | 1..15)
			MAX-ACCESS read-write
			STATUS current
			DESCRIPTION
				"DP0 Drop Probability
				In case RED, used as RED prob."
			::= { fkV2QoS4REDProfileControl 10 }

		
		-- 1.3.6.1.4.1.10428 9 1.102.10.2.7.1.2.11
		fkV2QoS4REDProfileControlDp1MinThres OBJECT-TYPE
			SYNTAX INTEGER (-1 | 0..65535)
			MAX-ACCESS read-write
			STATUS current
			DESCRIPTION
				"DP1 min threshold.
				Used only in case WRED.
				Marvell (1..65535), BCM: not supported"
			::= { fkV2QoS4REDProfileControl 11 }

		
		-- 1.3.6.1.4.1.10428 9 1.102.10.2.7.1.2.12
		fkV2QoS4REDProfileControlDp1MaxThres OBJECT-TYPE
			SYNTAX INTEGER (-1 | 0..65535)
			MAX-ACCESS read-write
			STATUS current
			DESCRIPTION
				"DP1 max threshold.
				Used only in case WRED
				Marvell (1..65535), BCM: not supported"
			::= { fkV2QoS4REDProfileControl 12 }

		
		-- 1.3.6.1.4.1.10428 9 1.102.10.2.7.1.2.13
		fkV2QoS4REDProfileControlDp1Prob OBJECT-TYPE
			SYNTAX INTEGER (-1 | 1..15)
			MAX-ACCESS read-write
			STATUS current
			DESCRIPTION
				"DP1 Drop Probability. Used only in case WRED.
				BCM: not supported"
			::= { fkV2QoS4REDProfileControl 13 }

		
		-- 1.3.6.1.4.1.10428 9 1.102.10.2.7.1.2.14
		fkV2QoS4REDProfileControlDp2MinThres OBJECT-TYPE
			SYNTAX INTEGER (-1 | 0..65535)
			MAX-ACCESS read-write
			STATUS current
			DESCRIPTION
				"DP2 min threshold. Used only in case WRED
				Marvell (1..65535), BCM: not supported"
			::= { fkV2QoS4REDProfileControl 14 }

		
		-- 1.3.6.1.4.1.10428 9 1.102.10.2.7.1.2.15
		fkV2QoS4REDProfileControlDp2MaxThres OBJECT-TYPE
			SYNTAX INTEGER (-1 | 0..65535)
			MAX-ACCESS read-write
			STATUS current
			DESCRIPTION
				"DP2 max threshold.
				Marvell (1..65535), BCM: not supported"
			::= { fkV2QoS4REDProfileControl 15 }

		
		-- 1.3.6.1.4.1.10428 9 1.102.10.2.7.1.2.16
		fkV2QoS4REDProfileControlDp2Prob OBJECT-TYPE
			SYNTAX INTEGER (-1 | 1..15)
			MAX-ACCESS read-write
			STATUS current
			DESCRIPTION
				"DP2 Drop Probability. Used only in case WRED.
				BCM: not supported"
			::= { fkV2QoS4REDProfileControl 16 }

		
		-- 1.3.6.1.4.1.10428 9 1.102.10.2.7.1.2.17
		fkV2QoS4REDProfileControlWeight OBJECT-TYPE
			SYNTAX INTEGER (-1 | 1..15)
			MAX-ACCESS read-write
			STATUS current
			DESCRIPTION
				"Drop weight. Used only in case WRED.
				BCM: not supported"
			::= { fkV2QoS4REDProfileControl 17 }

		
		-- 1.3.6.1.4.1.10428 9 1.102.10.2.7.1.3
		fkV2QoS4REDProfileNotification OBJECT IDENTIFIER ::= { fkV2QoS4REDProfile 3 }

		
		-- 1.3.6.1.4.1.10428 9 1.102.10.2.7.1.3.1
		fkV2QS4REDProfileChanged NOTIFICATION-TYPE
			OBJECTS { fkV2QoS4REDProfileControlRequest, fkV2QoS4REDProfileControlTimeStamp, fkV2QoS4REDProfileControlReqResult, fkV2QoS4REDProfileDp0MinThres, fkV2QoS4REDProfileDp0MaxThres, 
				fkV2QoS4REDProfileDp0Prob, fkV2QoS4REDProfileDp1MinThres, fkV2QoS4REDProfileDp1MaxThres, fkV2QoS4REDProfileDp1Prob, fkV2QoS4REDProfileDp2MinThres, 
				fkV2QoS4REDProfileDp2MaxThres, fkV2QoS4REDProfileDp2Prob, fkV2QoS4REDProfileWeight }
			STATUS current
			DESCRIPTION 
				"Description."
			::= { fkV2QoS4REDProfileNotification 1 }

		
		-- 1.3.6.1.4.1.10428 9 1.102.10.2.7.1.3.2
		fkV2QS4REDProfileCleared NOTIFICATION-TYPE
			OBJECTS { fkV2QoS4REDProfileControlRequest, fkV2QoS4REDProfileControlTimeStamp, fkV2QoS4REDProfileControlReqResult, fkV2QoS4REDProfileControlId }
			STATUS current
			DESCRIPTION 
				"Description."
			::= { fkV2QoS4REDProfileNotification 2 }

		
		-- 1.3.6.1.4.1.10428 9 1.102.10.2.7.2
		fkV2QoS4PortREDInfo OBJECT IDENTIFIER ::= { fkV2QoS4RED 2 }

		
		-- 1.3.6.1.4.1.10428 9 1.102.10.2.7.2.1
		fkV2QoS4PortREDInfoTable OBJECT-TYPE
			SYNTAX SEQUENCE OF FkV2QoS4PortREDInfoEntry
			MAX-ACCESS not-accessible
			STATUS current
			DESCRIPTION
				"port redundancy info table."
			::= { fkV2QoS4PortREDInfo 1 }

		
		-- 1.3.6.1.4.1.10428 9 1.102.10.2.8.2.1.1
		fkV2QoS4PortREDInfoEntry OBJECT-TYPE
			SYNTAX FkV2QoS4PortREDInfoEntry
			MAX-ACCESS not-accessible
			STATUS current
			DESCRIPTION
				"key: fkV2QoS4PortREDInfoInterfaceIndex"
			INDEX { fkV2QoS4PortREDInfoInterfaceIndex }
			::= { fkV2QoS4PortREDInfoTable 1 }

		
		FkV2QoS4PortREDInfoEntry ::=
			SEQUENCE { 
				fkV2QoS4PortREDInfoInterfaceIndex
					InterfaceIndex,
				fkV2QoS4PortREDInfoEnable
					INTEGER,
				fkV2QoS4PortREDInfoProfileId
					INTEGER
			 }

		-- 1.3.6.1.4.1.10428 9 1.102.10.2.8.2.1.1.1
		fkV2QoS4PortREDInfoInterfaceIndex OBJECT-TYPE
			SYNTAX InterfaceIndex
			MAX-ACCESS read-only
			STATUS current
			DESCRIPTION
				"Inrterface Index"
			::= { fkV2QoS4PortREDInfoEntry 1 }

		
		-- 1.3.6.1.4.1.10428 9 1.102.10.2.8.2.1.1.2
		fkV2QoS4PortREDInfoEnable OBJECT-TYPE
			SYNTAX INTEGER
				{
				disable(0),
				red(1),
				wred(2)
				}
			MAX-ACCESS read-only
			STATUS current
			DESCRIPTION
				"RED/WRED enable flag
				BCM: only available RED, Marvell: only available WRED"
			::= { fkV2QoS4PortREDInfoEntry 2 }

		
		-- 1.3.6.1.4.1.10428 9 1.102.10.2.8.2.1.1.3
		fkV2QoS4PortREDInfoProfileId OBJECT-TYPE
			SYNTAX INTEGER (-1 | 1..255)
			MAX-ACCESS read-only
			STATUS current
			DESCRIPTION
				"RED profile index.
				In case fkV2QoS4PortREDInfoEnable == disable, invalid
				Marvell : (1..4), BCM : number of ports
				In case BCM, this value is equal to port index. (read-only)"
			::= { fkV2QoS4PortREDInfoEntry 3 }

		
		-- 1.3.6.1.4.1.10428 9 1.102.10.2.7.2.2
		fkV2QoS4PortREDInfoControl OBJECT IDENTIFIER ::= { fkV2QoS4PortREDInfo 2 }

		
		-- 1.3.6.1.4.1.10428 9 1.102.10.2.7.2.2.1
		fkV2QoS4PortREDInfoControlRequest OBJECT-TYPE
			SYNTAX INTEGER { setPortREDInfo(1) }
			MAX-ACCESS read-write
			STATUS current
			DESCRIPTION
				"The request of a user command"
			::= { fkV2QoS4PortREDInfoControl 1 }

		
		-- 1.3.6.1.4.1.10428 9 1.102.10.2.7.2.2.2
		fkV2QoS4PortREDInfoControlStatus OBJECT-TYPE
			SYNTAX FkControlStatusType
			MAX-ACCESS read-only
			STATUS current
			DESCRIPTION
				"The status of user command"
			::= { fkV2QoS4PortREDInfoControl 2 }

		
		-- 1.3.6.1.4.1.10428 9 1.102.10.2.7.2.2.3
		fkV2QoS4PortREDInfoControlTimer OBJECT-TYPE
			SYNTAX Gauge32
			MAX-ACCESS read-write
			STATUS current
			DESCRIPTION
				"The maximum time for the manager for a long running user command"
			::= { fkV2QoS4PortREDInfoControl 3 }

		
		-- 1.3.6.1.4.1.10428 9 1.102.10.2.7.2.2.4
		fkV2QoS4PortREDInfoControlTimeStamp OBJECT-TYPE
			SYNTAX TimeTicks
			MAX-ACCESS read-only
			STATUS current
			DESCRIPTION
				"The time stamp of the last command(end of command)"
			::= { fkV2QoS4PortREDInfoControl 4 }

		
		-- 1.3.6.1.4.1.10428 9 1.102.10.2.7.2.2.5
		fkV2QoS4PortREDInfoControlReqResult OBJECT-TYPE
			SYNTAX FkControlRequestResultType
			MAX-ACCESS read-only
			STATUS current
			DESCRIPTION
				"The result of the last user command"
			::= { fkV2QoS4PortREDInfoControl 5 }

		
		-- 1.3.6.1.4.1.10428 9 1.102.10.2.7.2.2.6
		fkV2QoS4PortREDInfoControlInterfaceIndex OBJECT-TYPE
			SYNTAX InterfaceIndex
			MAX-ACCESS read-write
			STATUS current
			DESCRIPTION
				"Inrterface Index"
			::= { fkV2QoS4PortREDInfoControl 6 }

		
		-- 1.3.6.1.4.1.10428 9 1.102.10.2.7.2.2.7
		fkV2QoS4PortREDInfoControlEnable OBJECT-TYPE
			SYNTAX INTEGER
				{
				disable(0),
				red(1),
				wred(2)
				}
			MAX-ACCESS read-write
			STATUS current
			DESCRIPTION
				"RED/WRED enable flag"
			::= { fkV2QoS4PortREDInfoControl 7 }

		
		-- 1.3.6.1.4.1.10428 9 1.102.10.2.7.2.2.8
		fkV2QoS4PortREDInfoControlProfileId OBJECT-TYPE
			SYNTAX INTEGER (-1 | 1..255)
			MAX-ACCESS read-write
			STATUS current
			DESCRIPTION
				"RED profile index.
				This value is valid only when  fkV2QoS4PortREDInfoEnable is 
				equal to RED or WRED only, valid.
				Marvell : (1..4), BCM : number of ports
				In case BCM, this value is equal to port index. (read-only)"
			::= { fkV2QoS4PortREDInfoControl 8 }

		
		-- 1.3.6.1.4.1.10428 9 1.102.10.2.7.2.3
		fkV2QoS4PortREDInfoNotification OBJECT IDENTIFIER ::= { fkV2QoS4PortREDInfo 3 }

		
		-- 1.3.6.1.4.1.10428 9 1.102.10.2.7.2.3.1
		fkV2QoS4PortREDInfoChanged NOTIFICATION-TYPE
			OBJECTS { fkV2QoS4PortREDInfoControlRequest, fkV2QoS4PortREDInfoControlTimeStamp, fkV2QoS4PortREDInfoControlReqResult, fkV2QoS4PortREDInfoEnable, fkV2QoS4PortREDInfoProfileId
				 }
			STATUS current
			DESCRIPTION 
				"setPortREDInfo"
			::= { fkV2QoS4PortREDInfoNotification 1 }

		
		-- 1.3.6.1.4.1.10428 9 1.102.10.2.8
		fkV2QoS4Queue OBJECT IDENTIFIER ::= { fkV2QoS4 8 }

		
		-- 1.3.6.1.4.1.10428 9 1.102.10.2.8.1
		fkV2QoS4QueueInfo OBJECT IDENTIFIER ::= { fkV2QoS4Queue 1 }

		
		-- 1.3.6.1.4.1.10428 9 1.102.10.2.8.1.1
		fkV2QoS4QueueInfoTable OBJECT-TYPE
			SYNTAX SEQUENCE OF FkV2QoS4QueueInfoEntry
			MAX-ACCESS not-accessible
			STATUS current
			DESCRIPTION
				"queue info table."
			::= { fkV2QoS4QueueInfo 1 }

		
		-- 1.3.6.1.4.1.10428 9 1.102.10.2.9.1.1.1
		fkV2QoS4QueueInfoEntry OBJECT-TYPE
			SYNTAX FkV2QoS4QueueInfoEntry
			MAX-ACCESS not-accessible
			STATUS current
			DESCRIPTION
				"key: fkV2QoS4QueueInfoInterfaceIndex, fkV2QoS4QueueInfoId"
			INDEX { fkV2QoS4QueueInfoInterfaceIndex, fkV2QoS4QueueInfoId }
			::= { fkV2QoS4QueueInfoTable 1 }

		
		FkV2QoS4QueueInfoEntry ::=
			SEQUENCE { 
				fkV2QoS4QueueInfoInterfaceIndex
					InterfaceIndex,
				fkV2QoS4QueueInfoId
					INTEGER,
				fkV2QoS4QueueInfoScheduleMode
					INTEGER,
				fkV2QoS4QueueInfoDWRRGroup
					INTEGER,
				fkV2QoS4QueueInfoMinBandwidth
					Integer32,
				fkV2QoS4QueueInfoMaxBandwidth
					Integer32,
				fkV2QoS4QueueInfoWeight
					INTEGER,
				fkV2QoS4QueueMappedCoS
					INTEGER
			 }

		-- 1.3.6.1.4.1.10428 9 1.102.10.2.9.1.1.1.1
		fkV2QoS4QueueInfoInterfaceIndex OBJECT-TYPE
			SYNTAX InterfaceIndex
			MAX-ACCESS read-only
			STATUS current
			DESCRIPTION
				"Inrterface Index"
			::= { fkV2QoS4QueueInfoEntry 1 }

		
		-- 1.3.6.1.4.1.10428 9 1.102.10.2.9.1.1.1.2
		fkV2QoS4QueueInfoId OBJECT-TYPE
			SYNTAX INTEGER (1..8)
			MAX-ACCESS read-only
			STATUS current
			DESCRIPTION
				"The index of queue"
			::= { fkV2QoS4QueueInfoEntry 2 }

		
		-- 1.3.6.1.4.1.10428 9 1.102.10.2.9.1.1.1.3
		fkV2QoS4QueueInfoScheduleMode OBJECT-TYPE
			SYNTAX INTEGER
				{
				sp(1),
				rr(2),
				wrr(3),
				wfq(4),
				drr(5),
				bd(6)
				}
			MAX-ACCESS read-only
			STATUS current
			DESCRIPTION
				"Schedule mode of queue."
			::= { fkV2QoS4QueueInfoEntry 3 }

		
		-- 1.3.6.1.4.1.10428 9 1.102.10.2.9.1.1.1.4
		fkV2QoS4QueueInfoDWRRGroup OBJECT-TYPE
			SYNTAX INTEGER
				{
				undefined(0),
				group0(1),
				group1(2)
				}
			MAX-ACCESS read-only
			STATUS current
			DESCRIPTION
				"Queue dwrr group"
			::= { fkV2QoS4QueueInfoEntry 4 }

		
		-- 1.3.6.1.4.1.10428 9 1.102.10.2.9.1.1.1.5
		fkV2QoS4QueueInfoMinBandwidth OBJECT-TYPE
			SYNTAX Integer32
			MAX-ACCESS read-only
			STATUS current
			DESCRIPTION
				"Min bandwidth of queue"
			::= { fkV2QoS4QueueInfoEntry 5 }

		
		-- 1.3.6.1.4.1.10428 9 1.102.10.2.9.1.1.1.6
		fkV2QoS4QueueInfoMaxBandwidth OBJECT-TYPE
			SYNTAX Integer32
			MAX-ACCESS read-only
			STATUS current
			DESCRIPTION
				"Max bandwidth of queue"
			::= { fkV2QoS4QueueInfoEntry 6 }

		
		-- 1.3.6.1.4.1.10428 9 1.102.10.2.9.1.1.1.7
		fkV2QoS4QueueInfoWeight OBJECT-TYPE
			SYNTAX INTEGER (-1 | 1..255)
			MAX-ACCESS read-only
			STATUS current
			DESCRIPTION
				"Weight of queue
				BCM (1..15), Marvell (6..255)"
			::= { fkV2QoS4QueueInfoEntry 7 }

		
		-- 1.3.6.1.4.1.10428 9 1.102.10.2.9.1.1.1.8
		fkV2QoS4QueueMappedCoS OBJECT-TYPE
			SYNTAX INTEGER (0..7)
			MAX-ACCESS read-only
			STATUS current
			DESCRIPTION
				"Mapped cos"
			::= { fkV2QoS4QueueInfoEntry 8 }

		
		-- 1.3.6.1.4.1.10428 9 1.102.10.2.8.1.2
		fkV2QoS4QueueInfoControl OBJECT IDENTIFIER ::= { fkV2QoS4QueueInfo 2 }

		
		-- 1.3.6.1.4.1.10428 9 1.102.10.2.8.1.2.1
		fkV2QoS4QueueInfoControlRequest OBJECT-TYPE
			SYNTAX INTEGER
				{
				setQueueInfo(1),
				setScheduleMode(2),
				setMaxBandwidth(3),
				setMinBandwidth(4),
				setWeight(5)
				}
			MAX-ACCESS read-write
			STATUS current
			DESCRIPTION
				"The request of a user command"
			::= { fkV2QoS4QueueInfoControl 1 }

		
		-- 1.3.6.1.4.1.10428 9 1.102.10.2.8.1.2.2
		fkV2QoS4QueueInfoControlStatus OBJECT-TYPE
			SYNTAX FkControlStatusType
			MAX-ACCESS read-only
			STATUS current
			DESCRIPTION
				"The status of user command"
			::= { fkV2QoS4QueueInfoControl 2 }

		
		-- 1.3.6.1.4.1.10428 9 1.102.10.2.8.1.2.3
		fkV2QoS4QueueInfoControlTimer OBJECT-TYPE
			SYNTAX Gauge32
			MAX-ACCESS read-write
			STATUS current
			DESCRIPTION
				"The maximum time for the manager for a long running user command"
			::= { fkV2QoS4QueueInfoControl 3 }

		
		-- 1.3.6.1.4.1.10428 9 1.102.10.2.8.1.2.4
		fkV2QoS4QueueInfoControlTimeStamp OBJECT-TYPE
			SYNTAX TimeTicks
			MAX-ACCESS read-only
			STATUS current
			DESCRIPTION
				"The time stamp of the last command(end of command)"
			::= { fkV2QoS4QueueInfoControl 4 }

		
		-- 1.3.6.1.4.1.10428 9 1.102.10.2.8.1.2.5
		fkV2QoS4QueueInfoControlReqResult OBJECT-TYPE
			SYNTAX FkControlRequestResultType
			MAX-ACCESS read-only
			STATUS current
			DESCRIPTION
				"The result of the last user command"
			::= { fkV2QoS4QueueInfoControl 5 }

		
		-- 1.3.6.1.4.1.10428 9 1.102.10.2.8.1.2.6
		fkV2QoS4QueueInfoControlInterfaceIndex OBJECT-TYPE
			SYNTAX InterfaceIndex
			MAX-ACCESS read-write
			STATUS current
			DESCRIPTION
				"Inrterface Index"
			::= { fkV2QoS4QueueInfoControl 6 }

		
		-- 1.3.6.1.4.1.10428 9 1.102.10.2.8.1.2.7
		fkV2QoS4QueueInfoControlId OBJECT-TYPE
			SYNTAX INTEGER (1..8)
			MAX-ACCESS read-write
			STATUS current
			DESCRIPTION
				"The index of queue"
			::= { fkV2QoS4QueueInfoControl 7 }

		
		-- 1.3.6.1.4.1.10428 9 1.102.10.2.8.1.2.8
		fkV2QoS4QueueInfoControlScheduleMode OBJECT-TYPE
			SYNTAX INTEGER
				{
				sp(1),
				rr(2),
				wrr(3),
				wfq(4),
				drr(5),
				bd(6)
				}
			MAX-ACCESS read-write
			STATUS current
			DESCRIPTION
				"Schedule mode of queue.
				( V5524  : sp, wrr, wfq,
				 V5212G : sp, wrr,
				 V5424G : sp, wrr, drr
				 V6424  : sp, dwrr )
				"
			::= { fkV2QoS4QueueInfoControl 8 }

		
		-- 1.3.6.1.4.1.10428 9 1.102.10.2.8.1.2.9
		fkV2QoS4QueueInfoControlDWRRGroup OBJECT-TYPE
			SYNTAX INTEGER
				{
				undefined(0),
				group0(1),
				group1(2)
				}
			MAX-ACCESS read-write
			STATUS current
			DESCRIPTION
				"Queue dwrr group
				( V6424 )"
			::= { fkV2QoS4QueueInfoControl 9 }

		
		-- 1.3.6.1.4.1.10428 9 1.102.10.2.8.1.2.10
		fkV2QoS4QueueInfoControlMinBandwidth OBJECT-TYPE
			SYNTAX Integer32
			MAX-ACCESS read-write
			STATUS current
			DESCRIPTION
				"Min bandwidth of queue.
				( V5524  : wfq,
				 V5424G : drr,
				 V6424  : dwrr )"
			::= { fkV2QoS4QueueInfoControl 10 }

		
		-- 1.3.6.1.4.1.10428 9 1.102.10.2.8.1.2.11
		fkV2QoS4QueueInfoControlMaxBandwidth OBJECT-TYPE
			SYNTAX Integer32
			MAX-ACCESS read-write
			STATUS current
			DESCRIPTION
				"Max bandwidth of queue"
			::= { fkV2QoS4QueueInfoControl 11 }

		
		-- 1.3.6.1.4.1.10428 9 1.102.10.2.8.1.2.12
		fkV2QoS4QueueInfoControlWeight OBJECT-TYPE
			SYNTAX INTEGER (1..255)
			MAX-ACCESS read-write
			STATUS current
			DESCRIPTION
				"Weight of queue
				BCM (1..15), Marvell (6..255) 
				
				( V5524, V5212G, V5424G : wrr,
				 V6424 : dwrr )"
			::= { fkV2QoS4QueueInfoControl 12 }

		
		-- 1.3.6.1.4.1.10428 9 1.102.10.2.8.1.2.13
		fkV2QoS4QueueInfoControlMappedCoS OBJECT-TYPE
			SYNTAX INTEGER (0..7)
			MAX-ACCESS read-write
			STATUS current
			DESCRIPTION
				"Mapped cos"
			::= { fkV2QoS4QueueInfoControl 13 }

		
		-- 1.3.6.1.4.1.10428 9 1.102.10.2.8.1.3
		fkV2QoS4QueueInfoNotification OBJECT IDENTIFIER ::= { fkV2QoS4QueueInfo 3 }

		
		-- 1.3.6.1.4.1.10428 9 1.102.10.2.8.1.3.1
		fkV2QoS4QueueInfoChanged NOTIFICATION-TYPE
			OBJECTS { fkV2QoS4QueueInfoControlRequest, fkV2QoS4QueueInfoControlTimeStamp, fkV2QoS4QueueInfoControlReqResult, fkV2QoS4QueueInfoScheduleMode, fkV2QoS4QueueInfoDWRRGroup, 
				fkV2QoS4QueueInfoMinBandwidth, fkV2QoS4QueueInfoMaxBandwidth, fkV2QoS4QueueInfoWeight, fkV2QoS4QueueMappedCoS }
			STATUS current
			DESCRIPTION 
				"setQueueInfo"
			::= { fkV2QoS4QueueInfoNotification 1 }

		
		-- 1.3.6.1.4.1.10428 9 1.102.10.2.8.1.3.2
		fkV2QoS4QueueInfoScheduleModeChanged NOTIFICATION-TYPE
			OBJECTS { fkV2QoS4QueueInfoControlRequest, fkV2QoS4QueueInfoControlTimeStamp, fkV2QoS4QueueInfoControlReqResult, fkV2QoS4QueueInfoScheduleMode, fkV2QoS4QueueInfoDWRRGroup
				 }
			STATUS current
			DESCRIPTION 
				"setScheduleMode"
			::= { fkV2QoS4QueueInfoNotification 2 }

		
		-- 1.3.6.1.4.1.10428 9 1.102.10.2.8.1.3.3
		fkV2QoS4QueueInfoMaxBandwidthChanged NOTIFICATION-TYPE
			OBJECTS { fkV2QoS4QueueInfoControlRequest, fkV2QoS4QueueInfoControlTimeStamp, fkV2QoS4QueueInfoControlReqResult, fkV2QoS4QueueInfoControlMaxBandwidth }
			STATUS current
			DESCRIPTION 
				"setMaxBandwidth"
			::= { fkV2QoS4QueueInfoNotification 3 }

		
		-- 1.3.6.1.4.1.10428 9 1.102.10.2.8.1.3.4
		fkV2QoS4QueueInfoMinBandwidthChanged NOTIFICATION-TYPE
			OBJECTS { fkV2QoS4QueueInfoControlRequest, fkV2QoS4QueueInfoControlTimeStamp, fkV2QoS4QueueInfoControlReqResult, fkV2QoS4QueueInfoControlMinBandwidth }
			STATUS current
			DESCRIPTION 
				"setMinBandwidth"
			::= { fkV2QoS4QueueInfoNotification 4 }

		
		-- 1.3.6.1.4.1.10428 9 1.102.10.2.8.1.3.5
		fkV2QoS4QueueInfoWeightChanged NOTIFICATION-TYPE
			OBJECTS { fkV2QoS4QueueInfoControlRequest, fkV2QoS4QueueInfoControlTimeStamp, fkV2QoS4QueueInfoControlReqResult, fkV2QoS4QueueInfoWeight }
			STATUS current
			DESCRIPTION 
				"setWeight"
			::= { fkV2QoS4QueueInfoNotification 5 }

		
		-- 1.3.6.1.4.1.10428 9 1.102.10.2.9
		fkV2QoS4DscpMap OBJECT IDENTIFIER ::= { fkV2QoS4 9 }

		
		-- 1.3.6.1.4.1.10428 9 1.102.10.2.9.1
		fkV2QoS4DscpMapIngress OBJECT IDENTIFIER ::= { fkV2QoS4DscpMap 1 }

		
		-- 1.3.6.1.4.1.10428 9 1.102.10.2.9.1.1
		fkV2QoS4DscpMapIngressTable OBJECT-TYPE
			SYNTAX SEQUENCE OF FkV2QoS4DscpMapIngressEntry
			MAX-ACCESS not-accessible
			STATUS current
			DESCRIPTION
				"DSCP map ingress table."
			::= { fkV2QoS4DscpMapIngress 1 }

		
		-- 1.3.6.1.4.1.10428 9 1.102.10.2.9.1.1.1
		fkV2QoS4DscpMapIngressEntry OBJECT-TYPE
			SYNTAX FkV2QoS4DscpMapIngressEntry
			MAX-ACCESS not-accessible
			STATUS current
			DESCRIPTION
				"key: fkV2QoS4DscpMapIngressDscpIndex"
			INDEX { fkV2QoS4DscpMapIngressDscpIndex }
			::= { fkV2QoS4DscpMapIngressTable 1 }

		
		FkV2QoS4DscpMapIngressEntry ::=
			SEQUENCE { 
				fkV2QoS4DscpMapIngressDscpIndex
					INTEGER,
				fkV2QoS4DscpMapIngressDscp
					OCTET STRING,
				fkV2QoS4DscpMapIngressCos
					INTEGER,
				fkV2QoS4DscpMapIngressColor
					INTEGER
			 }

		-- 1.3.6.1.4.1.10428 9 1.102.10.2.9.1.1.1.1
		fkV2QoS4DscpMapIngressDscpIndex OBJECT-TYPE
			SYNTAX INTEGER (1..64)
			MAX-ACCESS read-only
			STATUS current
			DESCRIPTION
				"Ingress DSCP mapping index.
				The index value of 1~ 64 mean 0 ~ 63 of the DSCP."
			::= { fkV2QoS4DscpMapIngressEntry 1 }

		
		-- 1.3.6.1.4.1.10428 9 1.102.10.2.9.1.1.1.2
		fkV2QoS4DscpMapIngressDscp OBJECT-TYPE
			SYNTAX OCTET STRING (SIZE (0..63))
			MAX-ACCESS read-only
			STATUS current
			DESCRIPTION
				"DSCP value."
			::= { fkV2QoS4DscpMapIngressEntry 2 }

		
		-- 1.3.6.1.4.1.10428 9 1.102.10.2.9.1.1.1.3
		fkV2QoS4DscpMapIngressCos OBJECT-TYPE
			SYNTAX INTEGER (0..7)
			MAX-ACCESS read-only
			STATUS current
			DESCRIPTION
				"The Class of Service."
			::= { fkV2QoS4DscpMapIngressEntry 3 }

		
		-- 1.3.6.1.4.1.10428 9 1.102.10.2.9.1.1.1.4
		fkV2QoS4DscpMapIngressColor OBJECT-TYPE
			SYNTAX INTEGER
				{
				green(1),
				yellow(2),
				red(3)
				}
			MAX-ACCESS read-only
			STATUS current
			DESCRIPTION
				"Specify color by Internal DP."
			::= { fkV2QoS4DscpMapIngressEntry 4 }

		
		-- 1.3.6.1.4.1.10428 9 1.102.10.2.9.1.2
		fkV2QoS4DscpMapIngressControl OBJECT IDENTIFIER ::= { fkV2QoS4DscpMapIngress 2 }

		
		-- 1.3.6.1.4.1.10428 9 1.102.10.2.9.1.2.1
		fkV2QoS4DscpMapIngressControlRequest OBJECT-TYPE
			SYNTAX INTEGER { setDscpMapIngress(1) }
			MAX-ACCESS read-write
			STATUS current
			DESCRIPTION
				"The request of a user command"
			::= { fkV2QoS4DscpMapIngressControl 1 }

		
		-- 1.3.6.1.4.1.10428 9 1.102.10.2.9.1.2.2
		fkV2QoS4DscpMapIngressControlStatus OBJECT-TYPE
			SYNTAX FkControlStatusType
			MAX-ACCESS read-only
			STATUS current
			DESCRIPTION
				"The status of user command"
			::= { fkV2QoS4DscpMapIngressControl 2 }

		
		-- 1.3.6.1.4.1.10428 9 1.102.10.2.9.1.2.3
		fkV2QoS4DscpMapIngressControlTimer OBJECT-TYPE
			SYNTAX Gauge32
			MAX-ACCESS read-write
			STATUS current
			DESCRIPTION
				"The maximum time for the manager for a long running user command"
			::= { fkV2QoS4DscpMapIngressControl 3 }

		
		-- 1.3.6.1.4.1.10428 9 1.102.10.2.9.1.2.4
		fkV2QoS4DscpMapIngressControlTimeStamp OBJECT-TYPE
			SYNTAX TimeTicks
			MAX-ACCESS read-only
			STATUS current
			DESCRIPTION
				"The time stamp of the last command(end of command)"
			::= { fkV2QoS4DscpMapIngressControl 4 }

		
		-- 1.3.6.1.4.1.10428 9 1.102.10.2.9.1.2.5
		fkV2QoS4DscpMapIngressControlReqResult OBJECT-TYPE
			SYNTAX FkControlRequestResultType
			MAX-ACCESS read-only
			STATUS current
			DESCRIPTION
				"The result of the last user command"
			::= { fkV2QoS4DscpMapIngressControl 5 }

		
		-- 1.3.6.1.4.1.10428 9 1.102.10.2.9.1.2.6
		fkV2QoS4DscpMapIngressControlDscpIndex OBJECT-TYPE
			SYNTAX INTEGER (1..64)
			MAX-ACCESS read-write
			STATUS current
			DESCRIPTION
				"Ingress DSCP mapping index.
				The index value of 1~ 64 mean 0 ~ 63 of the DSCP."
			::= { fkV2QoS4DscpMapIngressControl 6 }

		
		-- 1.3.6.1.4.1.10428 9 1.102.10.2.9.1.2.7
		fkV2QoS4DscpMapIngressControlDscp OBJECT-TYPE
			SYNTAX INTEGER (0..63)
			MAX-ACCESS read-write
			STATUS current
			DESCRIPTION
				"DSCP value."
			::= { fkV2QoS4DscpMapIngressControl 7 }

		
		-- 1.3.6.1.4.1.10428 9 1.102.10.2.9.1.2.8
		fkV2QoS4DscpMapIngressControlCos OBJECT-TYPE
			SYNTAX INTEGER (0..7)
			MAX-ACCESS read-write
			STATUS current
			DESCRIPTION
				"The Class of Service."
			::= { fkV2QoS4DscpMapIngressControl 8 }

		
		-- 1.3.6.1.4.1.10428 9 1.102.10.2.9.1.2.9
		fkV2QoS4DscpMapIngressControlColor OBJECT-TYPE
			SYNTAX INTEGER
				{
				green(1),
				yellow(2),
				red(3)
				}
			MAX-ACCESS read-write
			STATUS current
			DESCRIPTION
				"Specify color by Internal DP."
			::= { fkV2QoS4DscpMapIngressControl 9 }

		
		-- 1.3.6.1.4.1.10428 9 1.102.10.2.9.1.3
		fkV2QoS4DscpMapIngressNotification OBJECT IDENTIFIER ::= { fkV2QoS4DscpMapIngress 3 }

		
		-- 1.3.6.1.4.1.10428 9 1.102.10.2.9.1.3.1
		fkV2QoS4DscpMapIngressChanged NOTIFICATION-TYPE
			OBJECTS { fkV2QoS4DscpMapIngressControlRequest, fkV2QoS4DscpMapIngressControlTimeStamp, fkV2QoS4DscpMapIngressControlReqResult, fkV2QoS4DscpMapIngressControlDscpIndex, fkV2QoS4DscpMapIngressControlDscp, 
				fkV2QoS4DscpMapIngressControlCos, fkV2QoS4DscpMapIngressControlColor }
			STATUS current
			DESCRIPTION 
				"Description."
			::= { fkV2QoS4DscpMapIngressNotification 1 }

		
		-- 1.3.6.1.4.1.10428 9 1.102.10.2.9.2
		fkV2QoS4DscpMapTunnel OBJECT IDENTIFIER ::= { fkV2QoS4DscpMap 2 }

		
		-- 1.3.6.1.4.1.10428 9 1.102.10.2.9.2.1
		fkV2QoS4DscpMapTunnelTable OBJECT-TYPE
			SYNTAX SEQUENCE OF FkV2QoS4DscpMapTunnelEntry
			MAX-ACCESS not-accessible
			STATUS current
			DESCRIPTION
				"DSCP map tunnel table."
			::= { fkV2QoS4DscpMapTunnel 1 }

		
		-- 1.3.6.1.4.1.10428 9 1.102.10.2.9.2.1.1
		fkV2QoS4DscpMapTunnelEntry OBJECT-TYPE
			SYNTAX FkV2QoS4DscpMapTunnelEntry
			MAX-ACCESS not-accessible
			STATUS current
			DESCRIPTION
				"key: fkV2QoS4DscpMapTunnelPriority, fkV2QoS4DscpMapTunnelColor"
			INDEX { fkV2QoS4DscpMapTunnelPriority, fkV2QoS4DscpMapTunnelColor }
			::= { fkV2QoS4DscpMapTunnelTable 1 }

		
		FkV2QoS4DscpMapTunnelEntry ::=
			SEQUENCE { 
				fkV2QoS4DscpMapTunnelPriority
					INTEGER,
				fkV2QoS4DscpMapTunnelColor
					INTEGER,
				fkV2QoS4DscpMapTunnelDscp
					INTEGER
			 }

		-- 1.3.6.1.4.1.10428 9 1.102.10.2.9.2.1.1.1
		fkV2QoS4DscpMapTunnelPriority OBJECT-TYPE
			SYNTAX INTEGER (1..8)
			MAX-ACCESS read-only
			STATUS current
			DESCRIPTION
				"Internal packet priority.
				The index value of 1 ~ 8 mean 0 ~ 7 of the priority."
			::= { fkV2QoS4DscpMapTunnelEntry 1 }

		
		-- 1.3.6.1.4.1.10428 9 1.102.10.2.9.2.1.1.2
		fkV2QoS4DscpMapTunnelColor OBJECT-TYPE
			SYNTAX INTEGER
				{
				green(1),
				yellow(2),
				red(3)
				}
			MAX-ACCESS read-only
			STATUS current
			DESCRIPTION
				"Specify color by Internal DP."
			::= { fkV2QoS4DscpMapTunnelEntry 2 }

		
		-- 1.3.6.1.4.1.10428 9 1.102.10.2.9.2.1.1.3
		fkV2QoS4DscpMapTunnelDscp OBJECT-TYPE
			SYNTAX INTEGER (0..63)
			MAX-ACCESS read-only
			STATUS current
			DESCRIPTION
				"DSCP value."
			::= { fkV2QoS4DscpMapTunnelEntry 3 }

		
		-- 1.3.6.1.4.1.10428 9 1.102.10.2.9.2.2
		fkV2QoS4DscpMapTunnelControl OBJECT IDENTIFIER ::= { fkV2QoS4DscpMapTunnel 2 }

		
		-- 1.3.6.1.4.1.10428 9 1.102.10.2.9.2.2.1
		fkV2QoS4DscpMapTunnelControlRequest OBJECT-TYPE
			SYNTAX INTEGER { setDscpMapTunnel(1) }
			MAX-ACCESS read-write
			STATUS current
			DESCRIPTION
				"The request of a user command"
			::= { fkV2QoS4DscpMapTunnelControl 1 }

		
		-- 1.3.6.1.4.1.10428 9 1.102.10.2.9.2.2.2
		fkV2QoS4DscpMapTunnelControlStatus OBJECT-TYPE
			SYNTAX FkControlStatusType
			MAX-ACCESS read-only
			STATUS current
			DESCRIPTION
				"The status of user command"
			::= { fkV2QoS4DscpMapTunnelControl 2 }

		
		-- 1.3.6.1.4.1.10428 9 1.102.10.2.9.2.2.3
		fkV2QoS4DscpMapTunnelControlTimer OBJECT-TYPE
			SYNTAX Gauge32
			MAX-ACCESS read-write
			STATUS current
			DESCRIPTION
				"The maximum time for the manager for a long running user command"
			::= { fkV2QoS4DscpMapTunnelControl 3 }

		
		-- 1.3.6.1.4.1.10428 9 1.102.10.2.9.2.2.4
		fkV2QoS4DscpMapTunnelControlTimeStamp OBJECT-TYPE
			SYNTAX TimeTicks
			MAX-ACCESS read-only
			STATUS current
			DESCRIPTION
				"The time stamp of the last command(end of command)"
			::= { fkV2QoS4DscpMapTunnelControl 4 }

		
		-- 1.3.6.1.4.1.10428 9 1.102.10.2.9.2.2.5
		fkV2QoS4DscpMapTunnelControlReqResult OBJECT-TYPE
			SYNTAX FkControlRequestResultType
			MAX-ACCESS read-only
			STATUS current
			DESCRIPTION
				"The result of the last user command"
			::= { fkV2QoS4DscpMapTunnelControl 5 }

		
		-- 1.3.6.1.4.1.10428 9 1.102.10.2.9.2.2.6
		fkV2QoS4DscpMapTunnelControlPriority OBJECT-TYPE
			SYNTAX INTEGER (1..8)
			MAX-ACCESS read-write
			STATUS current
			DESCRIPTION
				"Internal packet priority.
				The index value of 1 ~ 8 mean 0 ~ 7 of the priority."
			::= { fkV2QoS4DscpMapTunnelControl 6 }

		
		-- 1.3.6.1.4.1.10428 9 1.102.10.2.9.2.2.7
		fkV2QoS4DscpMapTunnelControlColor OBJECT-TYPE
			SYNTAX INTEGER
				{
				green(1),
				yellow(2),
				red(3)
				}
			MAX-ACCESS read-write
			STATUS current
			DESCRIPTION
				"Specify color by Internal DP."
			::= { fkV2QoS4DscpMapTunnelControl 7 }

		
		-- 1.3.6.1.4.1.10428 9 1.102.10.2.9.2.2.8
		fkV2QoS4DscpMapTunnelControlDscp OBJECT-TYPE
			SYNTAX INTEGER (0..63)
			MAX-ACCESS read-write
			STATUS current
			DESCRIPTION
				"DSCP value."
			::= { fkV2QoS4DscpMapTunnelControl 8 }

		
		-- 1.3.6.1.4.1.10428 9 1.102.10.2.9.2.3
		fkV2QoS4DscpMapTunnelNotification OBJECT IDENTIFIER ::= { fkV2QoS4DscpMapTunnel 3 }

		
		-- 1.3.6.1.4.1.10428 9 1.102.10.2.9.2.3.1
		fkV2QoS4DscpMapTunnelChanged NOTIFICATION-TYPE
			OBJECTS { fkV2QoS4DscpMapTunnelControlRequest, fkV2QoS4DscpMapTunnelControlTimeStamp, fkV2QoS4DscpMapTunnelControlReqResult, fkV2QoS4DscpMapTunnelControlPriority, fkV2QoS4DscpMapTunnelControlColor, 
				fkV2QoS4DscpMapTunnelControlDscp }
			STATUS current
			DESCRIPTION 
				"Description."
			::= { fkV2QoS4DscpMapTunnelNotification 1 }

		
		-- 1.3.6.1.4.1.10428 9 1.102.10.3
		fkV2QoS6 OBJECT IDENTIFIER ::= { fkV2QoS 3 }

		
		-- 1.3.6.1.4.1.10428 9 1.102.10.4
		fkV2QoSGroup OBJECT-GROUP
			OBJECTS { fkV2QoS4FlowIndex, fkV2QoS4FlowName, fkV2QoS4FlowEthernetType, fkV2QoS4FlowDstMacAddr, fkV2QoS4FlowDstMacAddrMask, 
				fkV2QoS4FlowSrcMacAddr, fkV2QoS4FlowSrcMacAddrMask, fkV2QoS4Flow8021p, fkV2QoS4FlowSrcIpAddr, fkV2QoS4FlowSrcIpAddrMask, 
				fkV2QoS4FlowDstIpAddr, fkV2QoS4FlowDstIpAddrMask, fkV2QoS4FlowPktLen, fkV2QoS4FlowProtocolType, fkV2QoS4FlowTcpFlag, 
				fkV2QoS4FlowIcmpType, fkV2QoS4FlowIcmpCode, fkV2QoS4ClassIndex, fkV2QoS4ClassName, fkV2QoS4ClassFlowCnt, 
				fkV2QoS4ClassFlowIndex, fkV2QoS4PolicerIndex, fkV2QoS4PolicerName, fkV2QoS4PolicerRateLimit, fkV2QoS4PolicerColorMode, 
				fkV2QoS4PolicerColorAwareMode, fkV2QoS4PolicerColorCIR, fkV2QoS4PolicerColorCBS, fkV2QoS4PolicerColorPIR, fkV2QoS4PolicerColorPBS, 
				fkV2QoS4PolicerColorEBS, fkV2QoS4PolicerColorRedAction, fkV2QoS4PolicerColorYellowAction, fkV2QoS4PolicerColorGreenAction, fkV2QoS4PolicerCounterMode, 
				fkV2QoS4PolicyIndex, fkV2QoS4PolicyName, fkV2QoS4PolicyPriority, fkV2QoS4PolicyIngressPorts, fkV2QoS4PolicyEgressPorts, 
				fkV2QoS4PolicyVlan, fkV2QoS4PolicyMatchFlag, fkV2QoS4PolicyMatchVlan, fkV2QoS4PolicyMatchRedirectVlan, fkV2QoS4PolicyMatchRedirectPort, 
				fkV2QoS4PolicyMatchMarkMode, fkV2QoS4PolicyMatchQueue, fkV2QoS4PolicyMatchDp, fkV2QoS4PolicyMatchCoS, fkV2QoS4PolicyMatchDscp, 
				fkV2QoS4PolicyMatchIpPrecedence, fkV2QoS4PolicyMatchDstMacOrEgressPorts, fkV2QoS4PolicyMatchDstMac, fkV2QoS4PolicyMatchEgressPorts, fkV2QoS4PolicyNomatchFlag, 
				fkV2QoS4PolicyNomatchRedirectPort, fkV2QoS4PolicyNomatchCoS, fkV2QoS4PolicyNomatchDscp, fkV2QoS4PolicyNomatchIpPrecedence, fkV2QoS4FlowTcpSrcStartPort, 
				fkV2QoS4FlowTcpSrcEndPort, fkV2QoS4FlowTcpDstStartPort, fkV2QoS4PolicyFlowCnt, fkV2QoS4PolicerColorType, fkV2QoS4ClassFlowID, 
				fkV2QoS4PolicyClassCnt, fkV2QoS4FlowTcpDstEndPort, fkV2QoS4FlowUdpSrcStartPort, fkV2QoS4FlowUdpSrcEndPort, fkV2QoS4FlowUdpDstStartPort, 
				fkV2QoS4FlowUdpDstEndPort, fkV2QoS4PolicyPolicerIndex, fkV2QoS4PolicyFlowClassID, fkV2QoS4RemarkL2ColorIndex, fkV2QoS4RemarkL2QueueCoSIndex, 
				fkV2QoS4RemarkL2Queue, fkV2QoS4RemarkL2Dp, fkV2QoS4RemarkL2CoS, fkV2QoS4RemarkL2Dscp, fkV2QoS4RemarkL3ColorIndex, 
				fkV2QoS4RemarkL3DSCPIndex, fkV2QoS4RemarkL3Queue, fkV2QoS4RemarkL3Dp, fkV2QoS4RemarkL3CoS, fkV2QoS4RemarkL3Dscp, 
				fkV2QoS4PolicyFlowClassType, fkV2QoS4PolicerMeterMode, fkV2QoS4PolicyCounterRedBytes, fkV2QoS4PolicyCounterYellowBytes, fkV2QoS4PolicyCounterGreenBytes, 
				fkV2QoS4PolicyCounterValue, fkV2QoS4ClassFlowControlFlowIndex, fkV2QoS4PolicyFlowClassName, fkV2QoS4ClassFlowName, fkV2QoS4ClassPolicyIndex, 
				fkV2QoS4ClassPolicyID, fkV2QoS4ClassPolicyName, fkV2QoS4FlowPolicyName, fkV2QoS4FlowPolicyID, fkV2QoS4FlowPolicyIndex, 
				fkV2QoS4FlowClassName, fkV2QoS4FlowClassID, fkV2QoS4FlowClassIndex, fkV2QoS4REDProfileDp1MinThres, fkV2QoS4REDProfileDp1MaxThres, 
				fkV2QoS4REDProfileDp1Prob, fkV2QoS4REDProfileDp2MinThres, fkV2QoS4REDProfileDp2MaxThres, fkV2QoS4REDProfileDp2Prob, fkV2QoS4REDProfileWeight, 
				fkV2QoS4REDProfileDp0Prob, fkV2QoS4REDProfileDp0MaxThres, fkV2QoS4REDProfileDp0MinThres, fkV2QoS4REDProfileQueueId, fkV2QoS4REDProfileId, 
				fkV2QoS4PortREDInfoInterfaceIndex, fkV2QoS4PortREDInfoEnable, fkV2QoS4PortREDInfoProfileId, fkV2QoS4QueueInfoInterfaceIndex, fkV2QoS4QueueInfoId, 
				fkV2QoS4QueueInfoScheduleMode, fkV2QoS4QueueInfoDWRRGroup, fkV2QoS4QueueInfoMinBandwidth, fkV2QoS4QueueInfoMaxBandwidth, fkV2QoS4QueueInfoWeight, 
				fkV2QoS4QueueMappedCoS, fkV2QoS4FlowHdrlen, fkV2QoS4PolicyRedirBlackhole, fkV2QoS4FlowHdrError, fkV2QoS4PolicerAvrgCounterMode, 
				fkV2QoS4PolicyAvrg5SecCounterValue, fkV2QoS4PolicyAvrg1minCounterValue, fkV2QoS4PolicyAvrg10minCounterValue, fkV2QoS4PolicerMaxBandwidth, fkV2QoS4PolicerMinBandwidth, 
				fkV2QoS4FlowInnerVlan, fkV2QoS4FlowInner8021p, fkV2QoS4FlowControlRequest, fkV2QoS4FlowControlStatus, fkV2QoS4FlowControlTimer, 
				fkV2QoS4FlowControlTimeStamp, fkV2QoS4FlowControlReqResult, fkV2QoS4FlowControlIndex, fkV2QoS4FlowControlName, fkV2QoS4FlowControlEthernetType, 
				fkV2QoS4FlowControlSrcMacAddr, fkV2QoS4FlowControlSrcMacAddrMask, fkV2QoS4FlowControlDstMacAddr, fkV2QoS4FlowControlDstMacAddrMask, fkV2QoS4FlowControl8021p, 
				fkV2QoS4FlowControlSrcIpAddr, fkV2QoS4FlowControlSrcIpAddrMask, fkV2QoS4FlowControlDstIpAddr, fkV2QoS4FlowControlDstIpAddrMask, fkV2QoS4FlowControlIpPktPriorityType, 
				fkV2QoS4FlowControlIpPktPriority, fkV2QoS4FlowControlPktLen, fkV2QoS4FlowControlProtocolType, fkV2QoS4FlowControlTcpSrcStartPort, fkV2QoS4FlowControlTcpSrcEndPort, 
				fkV2QoS4FlowControlTcpDstStartPort, fkV2QoS4FlowControlTcpDstEndPort, fkV2QoS4FlowControlTcpFlag, fkV2QoS4FlowControlUdpSrcStartPort, fkV2QoS4FlowControlUdpSrcEndPort, 
				fkV2QoS4FlowControlUdpDstStartPort, fkV2QoS4FlowControlUdpDstEndPort, fkV2QoS4FlowControlIcmpType, fkV2QoS4FlowControlIcmpCode, fkV2QoS4FlowControlHdrlen, 
				fkV2QoS4FlowControlHdrError, fkV2QoS4FlowControlInnerVlan, fkV2QoS4FlowControlInner8021p, fkV2QoS4ClassControlRequest, fkV2QoS4ClassControlStatus, 
				fkV2QoS4ClassControlTimer, fkV2QoS4ClassControlTimeStamp, fkV2QoS4ClassControlReqResult, fkV2QoS4ClassControlIndex, fkV2QoS4ClassControlName, 
				fkV2QoS4ClassFlowControlRequest, fkV2QoS4ClassFlowControlStatus, fkV2QoS4ClassFlowControlTimer, fkV2QoS4ClassFlowControlTimeStamp, fkV2QoS4ClassFlowControlReqResult, 
				fkV2QoS4ClassFlowControlClassIndex, fkV2QoS4ClassFlowControlFlowID, fkV2QoS4PolicerColorRedDscp, fkV2QoS4PolicerColorYellowDscp, fkV2QoS4PolicerColorGreenDscp, 
				fkV2QoS4PolicerControlRequest, fkV2QoS4PolicerControlStatus, fkV2QoS4PolicerControlTimer, fkV2QoS4PolicerControlTimeStamp, fkV2QoS4PolicerControlReqResult, 
				fkV2QoS4PolicerControlIndex, fkV2QoS4PolicerControlName, fkV2QoS4PolicerControlMeterMode, fkV2QoS4PolicerControlRateLimit, fkV2QoS4PolicerControlColorType, 
				fkV2QoS4PolicerControlColorMode, fkV2QoS4PolicerControlColorAwareMode, fkV2QoS4PolicerControlColorCIR, fkV2QoS4PolicerControlColorCBS, fkV2QoS4PolicerControlColorPIR, 
				fkV2QoS4PolicerControlColorPBS, fkV2QoS4PolicerControlColorEBS, fkV2QoS4PolicerControlColorRedAction, fkV2QoS4PolicerControlColorYellowAction, fkV2QoS4PolicerControlColorGreenAction, 
				fkV2QoS4PolicerControlRemarkLayerMode, fkV2QoS4PolicerControlRemarkMode, fkV2QoS4PolicerControlCounterMode, fkV2QoS4PolicerControlAvrgCounterMode, fkV2QoS4PolicerControlMinBandwidth, 
				fkV2QoS4PolicerControlMaxBandwidth, fkV2QoS4PolicerControlColorRedDscp, fkV2QoS4PolicerControlColorYellowDscp, fkV2QoS4PolicerControlColorGreenDscp, fkV2QoS4PolicyControlRequest, 
				fkV2QoS4PolicyControlStatus, fkV2QoS4PolicyControlTimer, fkV2QoS4PolicyControlTimeStamp, fkV2QoS4PolicyControlReqResult, fkV2QoS4PolicyControlIndex, 
				fkV2QoS4PolicyControlName, fkV2QoS4PolicyControlPolicerIndex, fkV2QoS4PolicyControlPriority, fkV2QoS4PolicyControlIngressPorts, fkV2QoS4PolicyControlEgressPorts, 
				fkV2QoS4PolicyControlVlan, fkV2QoS4PolicyControlMatchFlag, fkV2QoS4PolicyControlMatchVlan, fkV2QoS4PolicyControlMatchRedirectVlan, fkV2QoS4PolicyControlMatchRedirectPort, 
				fkV2QoS4PolicyControlMatchMarkMode, fkV2QoS4PolicyControlMatchQueue, fkV2QoS4PolicyControlMatchDp, fkV2QoS4PolicyControlMatchCoS, fkV2QoS4PolicyControlMatchDscp, 
				fkV2QoS4PolicyControlMatchIpPrecedence, fkV2QoS4PolicyControlMatchDstMacOrEgressPorts, fkV2QoS4PolicyControlMatchDstMac, fkV2QoS4PolicyControlMatchEgressPorts, fkV2QoS4PolicyControlNomatchFlag, 
				fkV2QoS4PolicyControlNomatchRedirectPort, fkV2QoS4PolicyControlNomatchCoS, fkV2QoS4PolicyControlNomatchDscp, fkV2QoS4PolicyControlNomatchIpPrecedence, fkV2QoS4PolicyControlMatchRedirBlackhole, 
				fkV2QoS4PolicyFlowClassControlRequest, fkV2QoS4PolicyFlowClassControlStatus, fkV2QoS4PolicyFlowClassControlTimer, fkV2QoS4PolicyFlowClassControlTimeStamp, fkV2QoS4PolicyFlowClassControlReqResult, 
				fkV2QoS4PolicyFlowClassControlPolicyIndex, fkV2QoS4PolicyFlowClassControlIndex, fkV2QoS4PolicyFlowClassControlType, fkV2QoS4PolicyFlowClassControlFlowID, fkV2QoS4PolicyFlowClassControlClassID, 
				fkV2QoS4RemarkLayer2Mode, fkV2QoS4RemarkMode, fkV2QoS4RemarkControlRequest, fkV2QoS4RemarkControlStatus, fkV2QoS4RemarkControlTimer, 
				fkV2QoS4RemarkControlTimStamp, fkV2QoS4RemarkControlReqResult, fkV2QoS4RemarkControlLayer2Mode, fkV2QoS4RemarkControlMode, fkV2QoS4RemarkL3ControlRequest, 
				fkV2QoS4RemarkL3ControlStatus, fkV2QoS4RemarkL3ControlTimer, fkV2QoS4RemarkL3ControlTimeStamp, fkV2QoS4RemarkL3ControlReqResult, fkV2QoS4RemarkL3ControlColorIndex, 
				fkV2QoS4RemarkL3ControlDSCPIndex, fkV2QoS4RemarkL3ControlQueue, fkV2QoS4RemarkL3ControlDp, fkV2QoS4RemarkL3ControlCoS, fkV2QoS4RemarkL3ControlDscp, 
				fkV2QoS4RemarkL2ControlRequest, fkV2QoS4RemarkL2ControlStatus, fkV2QoS4RemarkL2ControlTimer, fkV2QoS4RemarkL2ControlTimeStamp, fkV2QoS4RemarkL2ControlReqResult, 
				fkV2QoS4RemarkL2ControlColorIndex, fkV2QoS4RemarkL2ControlQueueCoSIndex, fkV2QoS4RemarkL2ControlQueue, fkV2QoS4RemarkL2ControlDp, fkV2QoS4RemarkL2ControlCoS, 
				fkV2QoS4RemarkL2ControlDscp, fkV2QoS4REDProfileControlRequest, fkV2QoS4REDProfileControlStatus, fkV2QoS4REDProfileControlTimer, fkV2QoS4REDProfileControlTimeStamp, 
				fkV2QoS4REDProfileControlReqResult, fkV2QoS4REDProfileControlId, fkV2QoS4REDProfileControlQueueId, fkV2QoS4REDProfileControlDp0MinThres, fkV2QoS4REDProfileControlDp0MaxThres, 
				fkV2QoS4REDProfileControlDp0Prob, fkV2QoS4REDProfileControlDp1MinThres, fkV2QoS4REDProfileControlDp1MaxThres, fkV2QoS4REDProfileControlDp1Prob, fkV2QoS4REDProfileControlDp2MinThres, 
				fkV2QoS4REDProfileControlDp2MaxThres, fkV2QoS4REDProfileControlDp2Prob, fkV2QoS4REDProfileControlWeight, fkV2QoS4PortREDInfoControlRequest, fkV2QoS4PortREDInfoControlStatus, 
				fkV2QoS4PortREDInfoControlTimer, fkV2QoS4PortREDInfoControlTimeStamp, fkV2QoS4PortREDInfoControlReqResult, fkV2QoS4PortREDInfoControlInterfaceIndex, fkV2QoS4PortREDInfoControlEnable, 
				fkV2QoS4PortREDInfoControlProfileId, fkV2QoS4QueueInfoControlRequest, fkV2QoS4QueueInfoControlStatus, fkV2QoS4QueueInfoControlTimer, fkV2QoS4QueueInfoControlTimeStamp, 
				fkV2QoS4QueueInfoControlReqResult, fkV2QoS4QueueInfoControlInterfaceIndex, fkV2QoS4QueueInfoControlId, fkV2QoS4QueueInfoControlScheduleMode, fkV2QoS4QueueInfoControlDWRRGroup, 
				fkV2QoS4QueueInfoControlMinBandwidth, fkV2QoS4QueueInfoControlMaxBandwidth, fkV2QoS4QueueInfoControlWeight, fkV2QoS4QueueInfoControlMappedCoS, fkV2QoS4PolicyIngressTunnelIfIndex, 
				fkV2QoS4PolicyEgressTunnelIfIndex, fkV2QoS4PolicyControlIngressTunnelIfIndex, fkV2Qo4SPolicyControlEgressTunnelIfIndex, fkV2QoS4DscpMapIngressDscpIndex, fkV2QoS4DscpMapIngressDscp, 
				fkV2QoS4DscpMapIngressCos, fkV2QoS4DscpMapIngressColor, fkV2QoS4DscpMapIngressControlRequest, fkV2QoS4DscpMapIngressControlStatus, fkV2QoS4DscpMapIngressControlTimer, 
				fkV2QoS4DscpMapIngressControlTimeStamp, fkV2QoS4DscpMapIngressControlReqResult, fkV2QoS4DscpMapIngressControlDscpIndex, fkV2QoS4DscpMapIngressControlDscp, fkV2QoS4DscpMapIngressControlCos, 
				fkV2QoS4DscpMapIngressControlColor, fkV2QoS4DscpMapTunnelPriority, fkV2QoS4DscpMapTunnelColor, fkV2QoS4DscpMapTunnelDscp, fkV2QoS4DscpMapTunnelControlRequest, 
				fkV2QoS4DscpMapTunnelControlStatus, fkV2QoS4DscpMapTunnelControlTimer, fkV2QoS4DscpMapTunnelControlTimeStamp, fkV2QoS4DscpMapTunnelControlReqResult, fkV2QoS4DscpMapTunnelControlPriority, 
				fkV2QoS4DscpMapTunnelControlColor, fkV2QoS4DscpMapTunnelControlDscp, fkV2QoS4BaseFlowMode, fkV2QoS4BaseControlRequest, fkV2QoS4BaseControlStatus, 
				fkV2QoS4BaseControlTimer, fkV2QoS4BaseControlTimeStamp, fkV2QoS4BaseControlResult, fkV2QoS4BaseControlFlowMode, fkV2QoS4PolicyCounterElapsedTimeAfterClear, 
				fkV2QoS4PolicerMatchCounterName, fkV2QoS4PolicerMatchCounterDesc, fkV2QoS4PolicerMatchCounterValue, fkV2QoS4FlowMacFlag, fkV2QoS4FlowIpFlag, 
				fkV2QoS4FlowControlMacFlag, fkV2QoS4FlowControlIpFlag, fkV2QoS4PolicerColorRedCos, fkV2QoS4PolicerColorYellowCos, fkV2QoS4PolicerColorGreenCos, 
				fkV2QoS4PolicerControlColorRedCos, fkV2QoS4PolicerControlColorYellowCos, fkV2QoS4PolicerControlColorGreenCos, fkV2QoS4PolicerColorRedCosType, fkV2QoS4PolicerColorYellowCosType, 
				fkV2QoS4PolicerControlColorRedCosType, fkV2QoS4PolicerControlColorYellowCosType, fkV2QoS4PolicerControlColorGreenCosType, fkV2QoS4FlowMacDlf, fkV2QoS4FlowControlMacDlf, 
				fkV2QoS4PolicyStage, fkV2QoS4PolicyControlStage, fkV2QoS4PolicyIngressPortsFlag, fkV2QoS4PolicyEgressPortsFlag, fkV2QoS4PolicyControlIngressPortsFlag, 
				fkV2QoS4PolicyControlEgressPortsFlag, fkV2QoS4PolicyInnerVlanAction, fkV2QoS4PolicyOuterVlanAction, fkV2QoS4PolicyInnerVlan, fkV2QoS4PolicyOuterVlan, 
				fkV2QoS4PolicyControlInnerVlanAction, fkV2QoS4PolicyControlOuterVlanAction, fkV2QoS4PolicyControlInnerVlan, fkV2QoS4PolicyControlOuterVlan, fkV2QoS4PolicyIFDirection, 
				fkV2QoS4PolicyIFControlRequest, fkV2QoS4PolicyIFControlStatus, fkV2QoS4PolicyIFControlTimer, fkV2QoS4PolicyIFControlTimeStamp, fkV2QoS4PolicyIFControlReqResult, 
				fkV2QoS4PolicyIFControlIfindex, fkV2QoS4PolicyIFControlPolicyIndex, fkV2QoS4PolicyIFControlDirection, fkV2QoS4PolicyMatchPbrNextHopSecondary, fkV2QoS4PolicyMatchPbrNextHopVerifyReach, 
				fkV2QoS4PolicyControlMatchPbrNextHopSecondary, fkV2QoS4PolicyControlMatchPbrNextHopVerifyReach, fkV2QoS4FlowTagType, fkV2QoS4FlowControlTagType, fkV2QoS4FlowInPktTagVid, 
				fkV2QoS4FlowInPktTagCfi, fkV2QoS4FlowInPktTagCoS, fkV2QoS4FlowOutPktTagVid, fkV2QoS4FlowOutPktTagCfi, fkV2QoS4FlowOutPktTagCoS, 
				fkV2QoS4FlowFlowAlias, fkV2QoS4FlowControlPktTagVid, fkV2QoS4FlowControlPktTagCfi, fkV2QoS4FlowControlPktTagCoS, fkV2QoS4FlowControlFlowAlias, 
				fkV2QoS4PolicyMatchFlowAlias, fkV2QoS4PolicyControlMatchFlowAlias, fkV2QoS4PolicyMatchInnerVlanCosReplace, fkV2QoS4PolicyMatchInnerVlanCfiReplace, fkV2QoS4PolicyMatchOuterVlanCosReplace, 
				fkV2QoS4PolicyMatchOuterVlanCfiReplace, fkV2QoS4PolicyControlMatchInnerVlanCosReplace, fkV2QoS4PolicyControlMatchInnerVlanCfiReplace, fkV2QoS4PolicyControlMatchOuterVlanCosReplace, fkV2QoS4PolicyControlMatchOuterVlanCfiReplace, 
				fkV2QoS4PolicyFlowClassIndex, fkV2QoS4FlowIpPktPriorityType, fkV2QoS4FlowIpPktPriority, fkV2QoS4PolicerRemarkLayerMode, fkV2QoS4PolicerRemarkMode, 
				fkV2QoS4PolicerColorGreenCosType, fkV2QoS4PolicyMatchPbrNextHop, fkV2QoS4PolicyControlMatchPbrNextHop }
			STATUS current
			DESCRIPTION 
				"Description."
			::= { fkV2QoS 4 }

		
		-- 1.3.6.1.4.1.10428 9 1.102.10.5
		fkV2QoSNotificationGroup NOTIFICATION-GROUP
			NOTIFICATIONS { fkFlowCreated, fkFlowChanged, fkFlowDestroyed, fkFlowAllDestroyed, fkClassCreated, 
				fkClassDestroyed, fkClassAllDestroyed, fkClassFlowAdded, fkClassFlowDeleted, fkClassFlowAllDeleted, 
				fkPolicerCreated, fkPolicerChanged, fkPolicerDestroyed, fkPolicyCreated, fkPolicyDestroyed, 
				fkRemarkChanged, fkRemarkL3Changed, fkV2QS4REDProfileChanged, fkV2QoS4PortREDInfoChanged, fkV2QoS4QueueInfoChanged, 
				fkV2QS4REDProfileCleared, fkPolicyEmptyCreated, fkV2QoS4DscpMapIngressChanged, fkV2QoS4DscpMapTunnelChanged, fkV2QoS4BaseFlowModeChanged, 
				fkRemarkL2Changed, fkPolicyInfoChanged, fkPolicyMatchActionChanged, fkPolicyNomatchActionChanged, fkPolicyCounterCleared, 
				fkPolicyFlowAdded, fkPolicyFlowDeleted, fkPolicyAllFlowDeleted, fkPolicyAllClassDeleted, fkV2QoS4QueueInfoScheduleModeChanged, 
				fkV2QoS4QueueInfoWeightChanged, fkV2QosPolicyIFServicePolicyChanged, fkV2QosPolicyIFServicePolicyCleared, fkPolicyAllFlowClassDeleted, fkPolicyIngressTunnelSet, 
				fkPolicyIngressTunnelUnset, fkPolicyEgressTunnelSet, fkPolicyEgressTunnelUnset, fkV2QoS4QueueInfoMaxBandwidthChanged, fkPolicyMatchInnerVlanCosReplaceChanged, 
				fkPolicyMatchInnerVlanCfiReplaceChanged, fkPolicyMatchOuterVlanCosReplaceChanged, fkPolicyMatchOuterVlanCfiReplaceChanged, fkV2QoS4QueueInfoMinBandwidthChanged, fkFlowInPktTagChanged, 
				fkFlowOutPktTagChanged, fkFlowAliasChanged, fkPolicyActionMatchFlowAliasChanged }
			STATUS current
			DESCRIPTION 
				"Description."
			::= { fkV2QoS 5 }

		
	
	END

--
-- fkv2-qos-mib.mib
--
