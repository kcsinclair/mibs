--
-- fkv2-pppoe-mib.mib
-- MIB generated by MG-SOFT Visual MIB Builder Version 6.0  Build 88
-- Friday, April 05, 2013 at 15:37:45
--

	FKV2-PPPoE-MIB DEFINITIONS ::= BEGIN
 
		IMPORTS
			fkV2Mgmt			
				FROM FKOLTG1040-SMI			
			FkControlStatusType, FkControlRequestResultType			
				FROM FK-TC-MIB			
			OBJECT-GROUP, NOTIFICATION-GROUP			
				FROM SNMPv2-CONF			
			TimeTicks, Integer32, Gauge32, OBJECT-TYPE, MODULE-IDENTITY, 
			NOTIFICATION-TYPE			
				FROM SNMPv2-SMI;
	
	
		-- 1.3.6.1.4.1.10428 9 1.102.16
		fkV2PPPoE MODULE-IDENTITY 
			LAST-UPDATED "201302061009Z"		-- February 06, 2013 at 10:09 GMT
			ORGANIZATION 
				"Furukawa Industrial S.A."
			CONTACT-INFO 
				"Furukawa Industrial S.A. Produtos Eletricos
        Rua Hasdrubal Bellegard, 820 - CIC
        CEP 81460-120 - Curitiba - Parana - Brasil
        CSC 0800-41-2100
        E-mail: fisa@furukawa.com.br"
			DESCRIPTION 
				"The MIB module for Furukawa GPON OLT FK-OLT-G1040."
			::= { fkV2Mgmt 16 }

		
	
--
-- Type definitions
--
	
		Boolean ::= Integer32

	
	
--
-- Node definitions
--
	
		-- 1.3.6.1.4.1.10428 9 1.102.16.1
		fkV2PPPoEBase OBJECT IDENTIFIER ::= { fkV2PPPoE 1 }

		
		-- 1.3.6.1.4.1.10428 9 1.102.16.1.1
		fkV2PPPoEInfo OBJECT IDENTIFIER ::= { fkV2PPPoEBase 1 }

		
		-- 1.3.6.1.4.1.10428 9 1.102.16.1.1.1
		fkV2PPPoESnoopingActivity OBJECT-TYPE
			SYNTAX INTEGER
				{
				disable(0),
				enable(1)
				}
			MAX-ACCESS read-only
			STATUS current
			DESCRIPTION
				"Description."
			::= { fkV2PPPoEInfo 1 }

		
		-- 1.3.6.1.4.1.10428 9 1.102.16.1.2
		fkV2PPPoEControl OBJECT IDENTIFIER ::= { fkV2PPPoEBase 2 }

		
		-- 1.3.6.1.4.1.10428 9 1.102.16.1.2.1
		fkV2PPPoEControlRequest OBJECT-TYPE
			SYNTAX INTEGER { setPPPoESnoopingActivity(1) }
			MAX-ACCESS read-write
			STATUS current
			DESCRIPTION
				"Description."
			::= { fkV2PPPoEControl 1 }

		
		-- 1.3.6.1.4.1.10428 9 1.102.16.1.2.2
		fkV2PPPoEControlStatus OBJECT-TYPE
			SYNTAX FkControlStatusType
			MAX-ACCESS read-only
			STATUS current
			DESCRIPTION
				"Description."
			::= { fkV2PPPoEControl 2 }

		
		-- 1.3.6.1.4.1.10428 9 1.102.16.1.2.3
		fkV2PPPoEControlTimer OBJECT-TYPE
			SYNTAX Gauge32
			MAX-ACCESS read-write
			STATUS current
			DESCRIPTION
				"Description."
			::= { fkV2PPPoEControl 3 }

		
		-- 1.3.6.1.4.1.10428 9 1.102.16.1.2.4
		fkV2PPPoEControlTimeStamp OBJECT-TYPE
			SYNTAX TimeTicks
			MAX-ACCESS read-write
			STATUS current
			DESCRIPTION
				"Description."
			::= { fkV2PPPoEControl 4 }

		
		-- 1.3.6.1.4.1.10428 9 1.102.16.1.2.5
		fkV2PPPoEControlReqResult OBJECT-TYPE
			SYNTAX FkControlRequestResultType
			MAX-ACCESS read-only
			STATUS current
			DESCRIPTION
				"Description."
			::= { fkV2PPPoEControl 5 }

		
		-- 1.3.6.1.4.1.10428 9 1.102.16.1.2.6
		fkV2PPPoEControlSnoopingActivity OBJECT-TYPE
			SYNTAX INTEGER
				{
				disable(0),
				enable(1)
				}
			MAX-ACCESS read-write
			STATUS current
			DESCRIPTION
				"Description."
			::= { fkV2PPPoEControl 6 }

		
		-- 1.3.6.1.4.1.10428 9 1.102.16.1.3
		fkV2PPPoENotification OBJECT IDENTIFIER ::= { fkV2PPPoEBase 3 }

		
		-- 1.3.6.1.4.1.10428 9 1.102.16.1.3.1
		fkV2PPPoESnoopingActivityChanged NOTIFICATION-TYPE
			OBJECTS { fkV2PPPoEControlRequest, fkV2PPPoEControlTimeStamp, fkV2PPPoEControlReqResult, fkV2PPPoEControlSnoopingActivity }
			STATUS current
			DESCRIPTION 
				"Description."
			::= { fkV2PPPoENotification 1 }

		
		-- 1.3.6.1.4.1.10428 9 1.102.16.2
		fkV2PPPoEFilter OBJECT IDENTIFIER ::= { fkV2PPPoE 2 }

		
		-- 1.3.6.1.4.1.10428 9 1.102.16.2.1
		fkV2PPPoEFilterTable OBJECT-TYPE
			SYNTAX SEQUENCE OF FkV2PPPoEFilterEntry
			MAX-ACCESS not-accessible
			STATUS current
			DESCRIPTION
				"Description."
			::= { fkV2PPPoEFilter 1 }

		
		-- 1.3.6.1.4.1.10428 9 1.102.16.2.1.1
		fkV2PPPoEFilterEntry OBJECT-TYPE
			SYNTAX FkV2PPPoEFilterEntry
			MAX-ACCESS not-accessible
			STATUS current
			DESCRIPTION
				"Description."
			INDEX { fkV2PPPoEFilterId, fkV2PPPoEFilterPortIndex, fkV2PPPoEFilterVlanId }
			::= { fkV2PPPoEFilterTable 1 }

		
		FkV2PPPoEFilterEntry ::=
			SEQUENCE { 
				fkV2PPPoEFilterId
					INTEGER,
				fkV2PPPoEFilterPortIndex
					INTEGER,
				fkV2PPPoEFilterVlanId
					INTEGER,
				fkV2PPPoEFilterAction
					INTEGER
			 }

		-- 1.3.6.1.4.1.10428 9 1.102.16.2.1.1.1
		fkV2PPPoEFilterId OBJECT-TYPE
			SYNTAX INTEGER (1..16)
			MAX-ACCESS read-only
			STATUS current
			DESCRIPTION
				"Description."
			::= { fkV2PPPoEFilterEntry 1 }

		
		-- 1.3.6.1.4.1.10428 9 1.102.16.2.1.1.2
		fkV2PPPoEFilterPortIndex OBJECT-TYPE
			SYNTAX INTEGER (1..255)
			MAX-ACCESS read-only
			STATUS current
			DESCRIPTION
				"Description."
			::= { fkV2PPPoEFilterEntry 2 }

		
		-- 1.3.6.1.4.1.10428 9 1.102.16.2.1.1.3
		fkV2PPPoEFilterVlanId OBJECT-TYPE
			SYNTAX INTEGER (1..4094)
			MAX-ACCESS read-write
			STATUS current
			DESCRIPTION
				"Description."
			::= { fkV2PPPoEFilterEntry 3 }

		
		-- 1.3.6.1.4.1.10428 9 1.102.16.2.1.1.4
		fkV2PPPoEFilterAction OBJECT-TYPE
			SYNTAX INTEGER
				{
				drop(1),
				permit(2)
				}
			MAX-ACCESS read-only
			STATUS current
			DESCRIPTION
				"Description."
			::= { fkV2PPPoEFilterEntry 4 }

		
		-- 1.3.6.1.4.1.10428 9 1.102.16.2.2
		fkV2PPPoEFilterControl OBJECT IDENTIFIER ::= { fkV2PPPoEFilter 2 }

		
		-- 1.3.6.1.4.1.10428 9 1.102.16.2.2.1
		fkV2PPPoEFilterControlRequest OBJECT-TYPE
			SYNTAX INTEGER
				{
				createPPPoEFilter(1),
				destroyPPPoEFilter(2),
				modifyPPPoEFilter(3)
				}
			MAX-ACCESS read-write
			STATUS current
			DESCRIPTION
				"Description."
			::= { fkV2PPPoEFilterControl 1 }

		
		-- 1.3.6.1.4.1.10428 9 1.102.16.2.2.2
		fkV2PPPoEFilterControlStatus OBJECT-TYPE
			SYNTAX FkControlStatusType
			MAX-ACCESS read-only
			STATUS current
			DESCRIPTION
				"Description."
			::= { fkV2PPPoEFilterControl 2 }

		
		-- 1.3.6.1.4.1.10428 9 1.102.16.2.2.3
		fkV2PPPoEFilterControlTimer OBJECT-TYPE
			SYNTAX Gauge32
			MAX-ACCESS read-write
			STATUS current
			DESCRIPTION
				"Description."
			::= { fkV2PPPoEFilterControl 3 }

		
		-- 1.3.6.1.4.1.10428 9 1.102.16.2.2.4
		fkV2PPPoEFilterControlTimeStamp OBJECT-TYPE
			SYNTAX TimeTicks
			MAX-ACCESS read-write
			STATUS current
			DESCRIPTION
				"Description."
			::= { fkV2PPPoEFilterControl 4 }

		
		-- 1.3.6.1.4.1.10428 9 1.102.16.2.2.5
		fkV2PPPoEFilterControlReqResult OBJECT-TYPE
			SYNTAX FkControlRequestResultType
			MAX-ACCESS read-write
			STATUS current
			DESCRIPTION
				"Description."
			::= { fkV2PPPoEFilterControl 5 }

		
		-- 1.3.6.1.4.1.10428 9 1.102.16.2.2.6
		fkV2PPPoEFilterControlId OBJECT-TYPE
			SYNTAX INTEGER (1..16)
			MAX-ACCESS read-write
			STATUS current
			DESCRIPTION
				"Description."
			::= { fkV2PPPoEFilterControl 6 }

		
		-- 1.3.6.1.4.1.10428 9 1.102.16.2.2.7
		fkV2PPPoEFilterControlPortIndex OBJECT-TYPE
			SYNTAX INTEGER (0 | 1..255)
			MAX-ACCESS read-write
			STATUS current
			DESCRIPTION
				"Description."
			::= { fkV2PPPoEFilterControl 7 }

		
		-- 1.3.6.1.4.1.10428 9 1.102.16.2.2.8
		fkV2PPPoEFilterControlVlanId OBJECT-TYPE
			SYNTAX INTEGER (0 | 1..4094)
			MAX-ACCESS read-write
			STATUS current
			DESCRIPTION
				"Description."
			::= { fkV2PPPoEFilterControl 8 }

		
		-- 1.3.6.1.4.1.10428 9 1.102.16.2.2.9
		fkV2PPPoEFilterControlAction OBJECT-TYPE
			SYNTAX INTEGER
				{
				drop(1),
				permit(2)
				}
			MAX-ACCESS read-write
			STATUS current
			DESCRIPTION
				"Description."
			::= { fkV2PPPoEFilterControl 9 }

		
		-- 1.3.6.1.4.1.10428 9 1.102.16.2.4
		fkV2PPPoEFilterNotification OBJECT IDENTIFIER ::= { fkV2PPPoEFilter 4 }

		
		-- 1.3.6.1.4.1.10428 9 1.102.16.2.4.1
		fkV2PPPoEFilterCreatedChanged NOTIFICATION-TYPE
			OBJECTS { fkV2PPPoEFilterControlRequest, fkV2PPPoEFilterControlTimeStamp, fkV2PPPoEFilterControlReqResult, fkV2PPPoEFilterControlId, fkV2PPPoEFilterControlPortIndex, 
				fkV2PPPoEFilterControlVlanId, fkV2PPPoEFilterControlAction }
			STATUS current
			DESCRIPTION 
				"Description."
			::= { fkV2PPPoEFilterNotification 1 }

		
		-- 1.3.6.1.4.1.10428 9 1.102.16.2.4.2
		fkV2PPPoEFilterModifyChanged NOTIFICATION-TYPE
			OBJECTS { fkV2PPPoEFilterControlRequest, fkV2PPPoEFilterControlTimeStamp, fkV2PPPoEFilterControlReqResult, fkV2PPPoEFilterControlId, fkV2PPPoEFilterControlPortIndex, 
				fkV2PPPoEFilterControlVlanId, fkV2PPPoEFilterControlAction }
			STATUS current
			DESCRIPTION 
				"Description."
			::= { fkV2PPPoEFilterNotification 2 }

		
		-- 1.3.6.1.4.1.10428 9 1.102.16.2.4.3
		fkV2PPPoEFilterDestroyChanged NOTIFICATION-TYPE
			OBJECTS { fkV2PPPoEFilterControlRequest, fkV2PPPoEFilterControlTimeStamp, fkV2PPPoEFilterControlReqResult, fkV2PPPoEFilterControlId }
			STATUS current
			DESCRIPTION 
				"Description."
			::= { fkV2PPPoEFilterNotification 3 }

		
		-- 1.3.6.1.4.1.10428 9 1.102.16.3
		fkV2PPPoETag OBJECT IDENTIFIER ::= { fkV2PPPoE 3 }

		
		-- 1.3.6.1.4.1.10428 9 1.102.16.3.1
		fkV2PPPoETagOper OBJECT IDENTIFIER ::= { fkV2PPPoETag 1 }

		
		-- 1.3.6.1.4.1.10428 9 1.102.16.3.1.1
		fkV2PPPoETagOperTable OBJECT-TYPE
			SYNTAX SEQUENCE OF FkV2PPPoETagOperEntry
			MAX-ACCESS not-accessible
			STATUS current
			DESCRIPTION
				"Description."
			::= { fkV2PPPoETagOper 1 }

		
		-- 1.3.6.1.4.1.10428 9 1.102.16.3.1.1.1
		fkV2PPPoETagOperEntry OBJECT-TYPE
			SYNTAX FkV2PPPoETagOperEntry
			MAX-ACCESS not-accessible
			STATUS current
			DESCRIPTION
				"Description."
			INDEX { fkV2PPPoETagOperId, fkV2PPPoETagOperVlanId, fkV2PPPoETagOperPortIndex }
			::= { fkV2PPPoETagOperTable 1 }

		
		FkV2PPPoETagOperEntry ::=
			SEQUENCE { 
				fkV2PPPoETagOperId
					INTEGER,
				fkV2PPPoETagOperType
					OCTET STRING,
				fkV2PPPoETagOperPortIndex
					INTEGER,
				fkV2PPPoETagOperVlanId
					INTEGER,
				fkV2PPPoETagOperAction
					INTEGER,
				fkV2PPPoETagOperTagFmt
					OCTET STRING
			 }

		-- 1.3.6.1.4.1.10428 9 1.102.16.3.1.1.1.1
		fkV2PPPoETagOperId OBJECT-TYPE
			SYNTAX INTEGER (1..16)
			MAX-ACCESS read-only
			STATUS current
			DESCRIPTION
				"Description."
			::= { fkV2PPPoETagOperEntry 1 }

		
		-- 1.3.6.1.4.1.10428 9 1.102.16.3.1.1.1.2
		fkV2PPPoETagOperType OBJECT-TYPE
			SYNTAX OCTET STRING
			MAX-ACCESS read-only
			STATUS current
			DESCRIPTION
				"Description."
			::= { fkV2PPPoETagOperEntry 2 }

		
		-- 1.3.6.1.4.1.10428 9 1.102.16.3.1.1.1.3
		fkV2PPPoETagOperPortIndex OBJECT-TYPE
			SYNTAX INTEGER (1..255)
			MAX-ACCESS read-only
			STATUS current
			DESCRIPTION
				"Description."
			::= { fkV2PPPoETagOperEntry 3 }

		
		-- 1.3.6.1.4.1.10428 9 1.102.16.3.1.1.1.4
		fkV2PPPoETagOperVlanId OBJECT-TYPE
			SYNTAX INTEGER (1..4094)
			MAX-ACCESS read-only
			STATUS current
			DESCRIPTION
				"Description."
			::= { fkV2PPPoETagOperEntry 4 }

		
		-- 1.3.6.1.4.1.10428 9 1.102.16.3.1.1.1.5
		fkV2PPPoETagOperAction OBJECT-TYPE
			SYNTAX INTEGER
				{
				add(1),
				keep(2),
				remove(3),
				replace(4),
				update(5)
				}
			MAX-ACCESS read-only
			STATUS current
			DESCRIPTION
				"Description."
			::= { fkV2PPPoETagOperEntry 5 }

		
		-- 1.3.6.1.4.1.10428 9 1.102.16.3.1.1.1.6
		fkV2PPPoETagOperTagFmt OBJECT-TYPE
			SYNTAX OCTET STRING
			MAX-ACCESS read-only
			STATUS current
			DESCRIPTION
				"Description."
			::= { fkV2PPPoETagOperEntry 6 }

		
		-- 1.3.6.1.4.1.10428 9 1.102.16.3.1.2
		fkV2PPPoETagOperControl OBJECT IDENTIFIER ::= { fkV2PPPoETagOper 2 }

		
		-- 1.3.6.1.4.1.10428 9 1.102.16.3.1.2.1
		fkV2PPPoETagOperControlRequest OBJECT-TYPE
			SYNTAX INTEGER
				{
				createPPPoETagOper(1),
				modifyPPPoETagOper(2),
				destroyPPPoETagOper(3)
				}
			MAX-ACCESS read-write
			STATUS current
			DESCRIPTION
				"Description."
			::= { fkV2PPPoETagOperControl 1 }

		
		-- 1.3.6.1.4.1.10428 9 1.102.16.3.1.2.2
		fkV2PPPoETagOperControlStatus OBJECT-TYPE
			SYNTAX FkControlStatusType
			MAX-ACCESS read-only
			STATUS current
			DESCRIPTION
				"Description."
			::= { fkV2PPPoETagOperControl 2 }

		
		-- 1.3.6.1.4.1.10428 9 1.102.16.3.1.2.3
		fkV2PPPoETagOperControlTimer OBJECT-TYPE
			SYNTAX Gauge32
			MAX-ACCESS read-write
			STATUS current
			DESCRIPTION
				"Description."
			::= { fkV2PPPoETagOperControl 3 }

		
		-- 1.3.6.1.4.1.10428 9 1.102.16.3.1.2.4
		fkV2PPPoETagOperControlTimeStamp OBJECT-TYPE
			SYNTAX TimeTicks
			MAX-ACCESS read-write
			STATUS current
			DESCRIPTION
				"Description."
			::= { fkV2PPPoETagOperControl 4 }

		
		-- 1.3.6.1.4.1.10428 9 1.102.16.3.1.2.5
		fkV2PPPoETagOperControlReqResult OBJECT-TYPE
			SYNTAX FkControlRequestResultType
			MAX-ACCESS read-write
			STATUS current
			DESCRIPTION
				"Description."
			::= { fkV2PPPoETagOperControl 5 }

		
		-- 1.3.6.1.4.1.10428 9 1.102.16.3.1.2.6
		fkV2PPPoETagOperControlId OBJECT-TYPE
			SYNTAX INTEGER (1..16)
			MAX-ACCESS read-write
			STATUS current
			DESCRIPTION
				"Description."
			::= { fkV2PPPoETagOperControl 6 }

		
		-- 1.3.6.1.4.1.10428 9 1.102.16.3.1.2.7
		fkV2PPPoETagOperControlType OBJECT-TYPE
			SYNTAX OCTET STRING
			MAX-ACCESS read-write
			STATUS current
			DESCRIPTION
				"Description."
			::= { fkV2PPPoETagOperControl 7 }

		
		-- 1.3.6.1.4.1.10428 9 1.102.16.3.1.2.8
		fkV2PPPoETagOperControlPortIndex OBJECT-TYPE
			SYNTAX INTEGER (0..255)
			MAX-ACCESS read-write
			STATUS current
			DESCRIPTION
				"Description."
			::= { fkV2PPPoETagOperControl 8 }

		
		-- 1.3.6.1.4.1.10428 9 1.102.16.3.1.2.9
		fkV2PPPoETagOperControlVlanId OBJECT-TYPE
			SYNTAX INTEGER (0..4094)
			MAX-ACCESS read-write
			STATUS current
			DESCRIPTION
				"Description."
			::= { fkV2PPPoETagOperControl 9 }

		
		-- 1.3.6.1.4.1.10428 9 1.102.16.3.1.2.10
		fkV2PPPoETagOperControlAction OBJECT-TYPE
			SYNTAX INTEGER
				{
				add(1),
				keep(2),
				remove(3),
				replace(4),
				update(5)
				}
			MAX-ACCESS read-write
			STATUS current
			DESCRIPTION
				"Description."
			::= { fkV2PPPoETagOperControl 10 }

		
		-- 1.3.6.1.4.1.10428 9 1.102.16.3.1.2.11
		fkV2PPPoETagOperControlTagFmt OBJECT-TYPE
			SYNTAX OCTET STRING
			MAX-ACCESS read-write
			STATUS current
			DESCRIPTION
				"Description."
			::= { fkV2PPPoETagOperControl 11 }

		
		-- 1.3.6.1.4.1.10428 9 1.102.16.3.1.3
		fkV2PPPoETagOperNotification OBJECT IDENTIFIER ::= { fkV2PPPoETagOper 3 }

		
		-- 1.3.6.1.4.1.10428 9 1.102.16.3.1.3.1
		fkV2PPPoETagOperCreateChanged NOTIFICATION-TYPE
			OBJECTS { fkV2PPPoETagOperControlRequest, fkV2PPPoETagOperControlTimeStamp, fkV2PPPoETagOperControlReqResult, fkV2PPPoETagOperControlId, fkV2PPPoETagOperControlType, 
				fkV2PPPoETagOperControlPortIndex, fkV2PPPoETagOperControlVlanId, fkV2PPPoETagOperControlAction, fkV2PPPoETagOperControlTagFmt }
			STATUS current
			DESCRIPTION 
				"Description."
			::= { fkV2PPPoETagOperNotification 1 }

		
		-- 1.3.6.1.4.1.10428 9 1.102.16.3.1.3.2
		fkV2PPPoETagOperDestroyChanged NOTIFICATION-TYPE
			OBJECTS { fkV2PPPoETagOperControlRequest, fkV2PPPoETagOperControlTimeStamp, fkV2PPPoETagOperControlReqResult, fkV2PPPoETagOperControlId }
			STATUS current
			DESCRIPTION 
				"Description."
			::= { fkV2PPPoETagOperNotification 2 }

		
		-- 1.3.6.1.4.1.10428 9 1.102.16.3.1.3.3
		fkV2PPPoETagOperModifyChanged NOTIFICATION-TYPE
			OBJECTS { fkV2PPPoETagOperControlRequest, fkV2PPPoETagOperControlTimeStamp, fkV2PPPoETagOperControlReqResult, fkV2PPPoETagOperControlId, fkV2PPPoETagOperControlType, 
				fkV2PPPoETagOperControlPortIndex, fkV2PPPoETagOperControlVlanId, fkV2PPPoETagOperControlAction, fkV2PPPoETagOperControlTagFmt }
			STATUS current
			DESCRIPTION 
				"Description."
			::= { fkV2PPPoETagOperNotification 3 }

		
		-- 1.3.6.1.4.1.10428 9 1.102.16.3.2
		fkV2PPPoETagFormat OBJECT IDENTIFIER ::= { fkV2PPPoETag 2 }

		
		-- 1.3.6.1.4.1.10428 9 1.102.16.3.2.1
		fkV2PPPoETagFormatBase OBJECT IDENTIFIER ::= { fkV2PPPoETagFormat 1 }

		
		-- 1.3.6.1.4.1.10428 9 1.102.16.3.2.1.1
		fkV2PPPoETagFormatTable OBJECT-TYPE
			SYNTAX SEQUENCE OF FkV2PPPoETagFormatEntry
			MAX-ACCESS not-accessible
			STATUS current
			DESCRIPTION
				"Description."
			::= { fkV2PPPoETagFormatBase 1 }

		
		-- 1.3.6.1.4.1.10428 9 1.102.16.3.2.1.1.1
		fkV2PPPoETagFormatEntry OBJECT-TYPE
			SYNTAX FkV2PPPoETagFormatEntry
			MAX-ACCESS not-accessible
			STATUS current
			DESCRIPTION
				"Description."
			INDEX { fkV2PPPoETagFormatName }
			::= { fkV2PPPoETagFormatTable 1 }

		
		FkV2PPPoETagFormatEntry ::=
			SEQUENCE { 
				fkV2PPPoETagFormatName
					OCTET STRING
			 }

		-- 1.3.6.1.4.1.10428 9 1.102.16.3.2.1.1.1.1
		fkV2PPPoETagFormatName OBJECT-TYPE
			SYNTAX OCTET STRING (SIZE (1..32))
			MAX-ACCESS read-only
			STATUS current
			DESCRIPTION
				"Description."
			::= { fkV2PPPoETagFormatEntry 1 }

		
		-- 1.3.6.1.4.1.10428 9 1.102.16.3.2.1.2
		fkV2PPPoETagFormatControl OBJECT IDENTIFIER ::= { fkV2PPPoETagFormatBase 2 }

		
		-- 1.3.6.1.4.1.10428 9 1.102.16.3.2.1.2.1
		fkV2PPPoETagFormatControlRequest OBJECT-TYPE
			SYNTAX INTEGER
				{
				createTagFormat(1),
				destroyTagFormat(2)
				}
			MAX-ACCESS read-write
			STATUS current
			DESCRIPTION
				"Description."
			::= { fkV2PPPoETagFormatControl 1 }

		
		-- 1.3.6.1.4.1.10428 9 1.102.16.3.2.1.2.2
		fkV2PPPoETagFormatControlStatus OBJECT-TYPE
			SYNTAX FkControlStatusType
			MAX-ACCESS read-only
			STATUS current
			DESCRIPTION
				"Description."
			::= { fkV2PPPoETagFormatControl 2 }

		
		-- 1.3.6.1.4.1.10428 9 1.102.16.3.2.1.2.3
		fkV2PPPoETagFormatControlTimer OBJECT-TYPE
			SYNTAX Gauge32
			MAX-ACCESS read-write
			STATUS current
			DESCRIPTION
				"Description."
			::= { fkV2PPPoETagFormatControl 3 }

		
		-- 1.3.6.1.4.1.10428 9 1.102.16.3.2.1.2.4
		fkV2PPPoETagFormatControlTimeStamp OBJECT-TYPE
			SYNTAX TimeTicks
			MAX-ACCESS read-only
			STATUS current
			DESCRIPTION
				"Description."
			::= { fkV2PPPoETagFormatControl 4 }

		
		-- 1.3.6.1.4.1.10428 9 1.102.16.3.2.1.2.5
		fkV2PPPoETagFormatControlReqResult OBJECT-TYPE
			SYNTAX FkControlRequestResultType
			MAX-ACCESS read-only
			STATUS current
			DESCRIPTION
				"Description."
			::= { fkV2PPPoETagFormatControl 5 }

		
		-- 1.3.6.1.4.1.10428 9 1.102.16.3.2.1.2.6
		fkV2PPPoETagFormatControlName OBJECT-TYPE
			SYNTAX OCTET STRING (SIZE (1..32))
			MAX-ACCESS read-write
			STATUS current
			DESCRIPTION
				"Description."
			::= { fkV2PPPoETagFormatControl 6 }

		
		-- 1.3.6.1.4.1.10428 9 1.102.16.3.2.1.3
		fkV2PPPoETagFormatNotification OBJECT IDENTIFIER ::= { fkV2PPPoETagFormatBase 3 }

		
		-- 1.3.6.1.4.1.10428 9 1.102.16.3.2.1.3.1
		fkV2PPPoETagFormatCreated NOTIFICATION-TYPE
			OBJECTS { fkV2PPPoETagFormatControlRequest, fkV2PPPoETagFormatControlTimeStamp, fkV2PPPoETagFormatControlReqResult, fkV2PPPoETagFormatControlName }
			STATUS current
			DESCRIPTION 
				"Description."
			::= { fkV2PPPoETagFormatNotification 1 }

		
		-- 1.3.6.1.4.1.10428 9 1.102.16.3.2.1.3.2
		fkV2PPPoETagFormatDestroyed NOTIFICATION-TYPE
			OBJECTS { fkV2PPPoETagFormatControlRequest, fkV2PPPoETagFormatControlTimeStamp, fkV2PPPoETagFormatControlReqResult, fkV2PPPoETagFormatControlName }
			STATUS current
			DESCRIPTION 
				"Description."
			::= { fkV2PPPoETagFormatNotification 2 }

		
		-- 1.3.6.1.4.1.10428 9 1.102.16.3.2.2
		fkV2PPPoETagFormatAttribute OBJECT IDENTIFIER ::= { fkV2PPPoETagFormat 2 }

		
		-- 1.3.6.1.4.1.10428 9 1.102.16.3.2.2.1
		fkV2PPPoETagFormatAttrTable OBJECT-TYPE
			SYNTAX SEQUENCE OF FkV2PPPoETagFormatAttrEntry
			MAX-ACCESS not-accessible
			STATUS current
			DESCRIPTION
				"Description."
			::= { fkV2PPPoETagFormatAttribute 1 }

		
		-- 1.3.6.1.4.1.10428 9 1.102.16.3.2.2.1.1
		fkV2PPPoETagFormatAttrEntry OBJECT-TYPE
			SYNTAX FkV2PPPoETagFormatAttrEntry
			MAX-ACCESS not-accessible
			STATUS current
			DESCRIPTION
				"Description."
			INDEX { fkV2PPPoETagFormatName, fkV2PPPoETagFormattAttrID }
			::= { fkV2PPPoETagFormatAttrTable 1 }

		
		FkV2PPPoETagFormatAttrEntry ::=
			SEQUENCE { 
				fkV2PPPoETagFormattAttrID
					INTEGER,
				fkV2PPPoETagFormatAttrLength
					INTEGER,
				fkV2PPPoETagFormatAttrHiddenLength
					INTEGER,
				fkV2PPPoETagFormatAttrType
					INTEGER,
				fkV2PPPoETagFormatAttrVarType
					INTEGER,
				fkV2PPPoETagFormatAttrVarValue
					OCTET STRING
			 }

		-- 1.3.6.1.4.1.10428 9 1.102.16.3.2.2.1.1.1
		fkV2PPPoETagFormattAttrID OBJECT-TYPE
			SYNTAX INTEGER (1..32)
			MAX-ACCESS read-only
			STATUS current
			DESCRIPTION
				"Description."
			::= { fkV2PPPoETagFormatAttrEntry 1 }

		
		-- 1.3.6.1.4.1.10428 9 1.102.16.3.2.2.1.1.2
		fkV2PPPoETagFormatAttrLength OBJECT-TYPE
			SYNTAX INTEGER (-1..128)
			MAX-ACCESS read-write
			STATUS current
			DESCRIPTION
				"Description."
			::= { fkV2PPPoETagFormatAttrEntry 2 }

		
		-- 1.3.6.1.4.1.10428 9 1.102.16.3.2.2.1.1.3
		fkV2PPPoETagFormatAttrHiddenLength OBJECT-TYPE
			SYNTAX INTEGER (-1..128)
			MAX-ACCESS read-write
			STATUS current
			DESCRIPTION
				"Description."
			::= { fkV2PPPoETagFormatAttrEntry 3 }

		
		-- 1.3.6.1.4.1.10428 9 1.102.16.3.2.2.1.1.4
		fkV2PPPoETagFormatAttrType OBJECT-TYPE
			SYNTAX INTEGER (-1..255)
			MAX-ACCESS read-write
			STATUS current
			DESCRIPTION
				"Description."
			::= { fkV2PPPoETagFormatAttrEntry 4 }

		
		-- 1.3.6.1.4.1.10428 9 1.102.16.3.2.2.1.1.5
		fkV2PPPoETagFormatAttrVarType OBJECT-TYPE
			SYNTAX INTEGER
				{
				hex(1),
				index(2),
				ip(3),
				string(4),
				tagFmt(5)
				}
			MAX-ACCESS read-only
			STATUS current
			DESCRIPTION
				"Description."
			::= { fkV2PPPoETagFormatAttrEntry 5 }

		
		-- 1.3.6.1.4.1.10428 9 1.102.16.3.2.2.1.1.6
		fkV2PPPoETagFormatAttrVarValue OBJECT-TYPE
			SYNTAX OCTET STRING (SIZE (1..255))
			MAX-ACCESS read-write
			STATUS current
			DESCRIPTION
				"Description."
			::= { fkV2PPPoETagFormatAttrEntry 6 }

		
		-- 1.3.6.1.4.1.10428 9 1.102.16.3.2.2.2
		fkV2PPPoETagFormatAttrControl OBJECT IDENTIFIER ::= { fkV2PPPoETagFormatAttribute 2 }

		
		-- 1.3.6.1.4.1.10428 9 1.102.16.3.2.2.2.1
		fkV2PPPoETagFormatAttrControlRequest OBJECT-TYPE
			SYNTAX INTEGER
				{
				addTagFormatAttr(1),
				deleteTagFormatAttr(2),
				modifyTagFormatAttr(3)
				}
			MAX-ACCESS read-write
			STATUS current
			DESCRIPTION
				"Description."
			::= { fkV2PPPoETagFormatAttrControl 1 }

		
		-- 1.3.6.1.4.1.10428 9 1.102.16.3.2.2.2.2
		fkV2PPPoETagFormatAttrControlStatus OBJECT-TYPE
			SYNTAX FkControlStatusType
			MAX-ACCESS read-only
			STATUS current
			DESCRIPTION
				"Description."
			::= { fkV2PPPoETagFormatAttrControl 2 }

		
		-- 1.3.6.1.4.1.10428 9 1.102.16.3.2.2.2.3
		fkV2PPPoETagFormatAttrControlTimer OBJECT-TYPE
			SYNTAX Gauge32
			MAX-ACCESS read-write
			STATUS current
			DESCRIPTION
				"Description."
			::= { fkV2PPPoETagFormatAttrControl 3 }

		
		-- 1.3.6.1.4.1.10428 9 1.102.16.3.2.2.2.4
		fkV2PPPoETagFormatAttrControlTimeStamp OBJECT-TYPE
			SYNTAX TimeTicks
			MAX-ACCESS read-only
			STATUS current
			DESCRIPTION
				"Description."
			::= { fkV2PPPoETagFormatAttrControl 4 }

		
		-- 1.3.6.1.4.1.10428 9 1.102.16.3.2.2.2.5
		fkV2PPPoETagFormatAttrControlReqResult OBJECT-TYPE
			SYNTAX FkControlRequestResultType
			MAX-ACCESS read-only
			STATUS current
			DESCRIPTION
				"Description."
			::= { fkV2PPPoETagFormatAttrControl 5 }

		
		-- 1.3.6.1.4.1.10428 9 1.102.16.3.2.2.2.6
		fkV2PPPoETagFormatAttrControlName OBJECT-TYPE
			SYNTAX OCTET STRING (SIZE (1..32))
			MAX-ACCESS read-write
			STATUS current
			DESCRIPTION
				"Description."
			::= { fkV2PPPoETagFormatAttrControl 6 }

		
		-- 1.3.6.1.4.1.10428 9 1.102.16.3.2.2.2.7
		fkV2PPPoETagFormatAttrControlID OBJECT-TYPE
			SYNTAX INTEGER (1..32)
			MAX-ACCESS read-write
			STATUS current
			DESCRIPTION
				"Description."
			::= { fkV2PPPoETagFormatAttrControl 7 }

		
		-- 1.3.6.1.4.1.10428 9 1.102.16.3.2.2.2.8
		fkV2PPPoETagFormatAttrControlLength OBJECT-TYPE
			SYNTAX INTEGER (-1..128)
			MAX-ACCESS read-write
			STATUS current
			DESCRIPTION
				"Description."
			::= { fkV2PPPoETagFormatAttrControl 8 }

		
		-- 1.3.6.1.4.1.10428 9 1.102.16.3.2.2.2.9
		fkV2PPPoETagFormatAttrControlHiddenLength OBJECT-TYPE
			SYNTAX INTEGER (-1..128)
			MAX-ACCESS read-write
			STATUS current
			DESCRIPTION
				"Description."
			::= { fkV2PPPoETagFormatAttrControl 9 }

		
		-- 1.3.6.1.4.1.10428 9 1.102.16.3.2.2.2.10
		fkV2PPPoETagFormatAttrControlType OBJECT-TYPE
			SYNTAX INTEGER (-1..255)
			MAX-ACCESS read-write
			STATUS current
			DESCRIPTION
				"Description."
			::= { fkV2PPPoETagFormatAttrControl 10 }

		
		-- 1.3.6.1.4.1.10428 9 1.102.16.3.2.2.2.11
		fkV2PPPoETagFormatAttrControlVarType OBJECT-TYPE
			SYNTAX INTEGER
				{
				hex(1),
				index(2),
				ip(3),
				string(4),
				tagFmt(5)
				}
			MAX-ACCESS read-only
			STATUS current
			DESCRIPTION
				"Description."
			::= { fkV2PPPoETagFormatAttrControl 11 }

		
		-- 1.3.6.1.4.1.10428 9 1.102.16.3.2.2.2.12
		fkV2PPPoETagFormatAttrControlVarValue OBJECT-TYPE
			SYNTAX OCTET STRING (SIZE (1..255))
			MAX-ACCESS read-write
			STATUS current
			DESCRIPTION
				"Description."
			::= { fkV2PPPoETagFormatAttrControl 12 }

		
		-- 1.3.6.1.4.1.10428 9 1.102.16.3.2.2.3
		fkV2PPPoETagFormatAttrNotification OBJECT IDENTIFIER ::= { fkV2PPPoETagFormatAttribute 3 }

		
		-- 1.3.6.1.4.1.10428 9 1.102.16.3.2.2.3.1
		fkV2PPPoETagFormatAttrAdded NOTIFICATION-TYPE
			OBJECTS { fkV2PPPoETagFormatAttrControlRequest, fkV2PPPoETagFormatAttrControlTimeStamp, fkV2PPPoETagFormatAttrControlReqResult, fkV2PPPoETagFormatAttrControlName, fkV2PPPoETagFormatAttrControlID, 
				fkV2PPPoETagFormatAttrControlLength, fkV2PPPoETagFormatAttrControlHiddenLength, fkV2PPPoETagFormatAttrControlType, fkV2PPPoETagFormatAttrControlVarType, fkV2PPPoETagFormatAttrControlVarValue
				 }
			STATUS current
			DESCRIPTION 
				"Description."
			::= { fkV2PPPoETagFormatAttrNotification 1 }

		
		-- 1.3.6.1.4.1.10428 9 1.102.16.3.2.2.3.2
		fkV2PPPoETagFormatAttrDeleted NOTIFICATION-TYPE
			OBJECTS { fkV2PPPoETagFormatAttrControlRequest, fkV2PPPoETagFormatAttrControlTimeStamp, fkV2PPPoETagFormatAttrControlReqResult, fkV2PPPoETagFormatAttrControlName, fkV2PPPoETagFormatAttrControlID
				 }
			STATUS current
			DESCRIPTION 
				"Description."
			::= { fkV2PPPoETagFormatAttrNotification 2 }

		
		-- 1.3.6.1.4.1.10428 9 1.102.16.3.2.2.3.3
		fkV2PPPoETagFormatAttrModified NOTIFICATION-TYPE
			OBJECTS { fkV2PPPoETagFormatAttrControlRequest, fkV2PPPoETagFormatAttrControlTimeStamp, fkV2PPPoETagFormatAttrControlReqResult, fkV2PPPoETagFormatAttrControlName, fkV2PPPoETagFormatAttrControlID, 
				fkV2PPPoETagFormatAttrControlLength, fkV2PPPoETagFormatAttrControlHiddenLength, fkV2PPPoETagFormatAttrControlType, fkV2PPPoETagFormatAttrControlVarType, fkV2PPPoETagFormatAttrControlVarValue
				 }
			STATUS current
			DESCRIPTION 
				"Description."
			::= { fkV2PPPoETagFormatAttrNotification 3 }

		
		-- 1.3.6.1.4.1.10428 9 1.102.16.5
		fkV2PPPoEGroup OBJECT-GROUP
			OBJECTS { fkV2PPPoEControlRequest, fkV2PPPoEControlStatus, fkV2PPPoEControlTimer, fkV2PPPoEControlTimeStamp, fkV2PPPoEControlReqResult, 
				fkV2PPPoESnoopingActivity, fkV2PPPoEControlSnoopingActivity, fkV2PPPoETagFormatControlReqResult, fkV2PPPoETagFormatControlTimeStamp, fkV2PPPoETagFormatControlTimer, 
				fkV2PPPoETagFormatName, fkV2PPPoETagFormatControlRequest, fkV2PPPoETagFormatControlStatus, fkV2PPPoETagFormatControlName, fkV2PPPoETagFormatAttrControlVarType, 
				fkV2PPPoETagFormatAttrControlType, fkV2PPPoETagFormatAttrControlHiddenLength, fkV2PPPoETagFormatAttrControlLength, fkV2PPPoETagFormatAttrControlName, fkV2PPPoETagFormatAttrControlID, 
				fkV2PPPoETagFormatAttrControlReqResult, fkV2PPPoETagFormatAttrControlTimeStamp, fkV2PPPoETagFormatAttrControlTimer, fkV2PPPoETagFormatAttrControlStatus, fkV2PPPoETagFormatAttrVarValue, 
				fkV2PPPoETagFormatAttrControlRequest, fkV2PPPoETagFormatAttrVarType, fkV2PPPoETagFormatAttrType, fkV2PPPoETagFormatAttrHiddenLength, fkV2PPPoETagFormatAttrLength, 
				fkV2PPPoETagFormattAttrID, fkV2PPPoETagFormatAttrControlVarValue, fkV2PPPoETagOperControlAction, fkV2PPPoETagOperControlVlanId, fkV2PPPoETagOperControlPortIndex, 
				fkV2PPPoETagOperControlId, fkV2PPPoETagOperControlType, fkV2PPPoETagOperControlReqResult, fkV2PPPoETagOperControlTimeStamp, fkV2PPPoETagOperControlTimer, 
				fkV2PPPoETagOperControlStatus, fkV2PPPoETagOperControlRequest, fkV2PPPoETagOperAction, fkV2PPPoETagOperVlanId, fkV2PPPoETagOperPortIndex, 
				fkV2PPPoEFilterControlAction, fkV2PPPoEFilterControlVlanId, fkV2PPPoEFilterControlPortIndex, fkV2PPPoEFilterControlId, fkV2PPPoEFilterControlReqResult, 
				fkV2PPPoEFilterControlTimeStamp, fkV2PPPoEFilterControlTimer, fkV2PPPoEFilterControlStatus, fkV2PPPoEFilterControlRequest, fkV2PPPoEFilterVlanId, 
				fkV2PPPoEFilterPortIndex, fkV2PPPoEFilterId, fkV2PPPoETagOperType, fkV2PPPoETagOperId, fkV2PPPoETagOperControlTagFmt, 
				fkV2PPPoETagOperTagFmt, fkV2PPPoEFilterAction }
			STATUS current
			DESCRIPTION 
				"Description."
			::= { fkV2PPPoE 5 }

		
		-- 1.3.6.1.4.1.10428 9 1.102.16.6
		fkV2PPPoENotificationGroup NOTIFICATION-GROUP
			NOTIFICATIONS { fkV2PPPoESnoopingActivityChanged, fkV2PPPoETagFormatDestroyed, fkV2PPPoETagFormatCreated, fkV2PPPoETagFormatAttrModified, fkV2PPPoETagFormatAttrDeleted, 
				fkV2PPPoETagFormatAttrAdded, fkV2PPPoETagOperDestroyChanged, fkV2PPPoETagOperCreateChanged, fkV2PPPoETagOperModifyChanged, fkV2PPPoEFilterDestroyChanged, 
				fkV2PPPoEFilterModifyChanged, fkV2PPPoEFilterCreatedChanged }
			STATUS current
			DESCRIPTION 
				"Description."
			::= { fkV2PPPoE 6 }

		
	
	END

--
-- fkv2-pppoe-mib.mib
--
