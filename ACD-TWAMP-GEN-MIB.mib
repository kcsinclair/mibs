--
-- Accedian Enterprise Specific MIB
--
-- Copyright (c) 2004-2016, Accedian Networks, Inc.
-- All rights reserved.
--
-- The contents of this document are subject to change without notice.
--


ACD-TWAMP-GEN-MIB DEFINITIONS ::= BEGIN

IMPORTS
    MODULE-IDENTITY, OBJECT-TYPE,
    IpAddress, Integer32, Unsigned32, Counter64
        FROM SNMPv2-SMI
    DisplayString, TruthValue, DateAndTime
        FROM SNMPv2-TC
    MODULE-COMPLIANCE, OBJECT-GROUP
        FROM SNMPv2-CONF
    acdMibs
        FROM ACCEDIAN-SMI;

acdTwampGen MODULE-IDENTITY

    LAST-UPDATED "201609230100Z"
    ORGANIZATION "Accedian Networks, Inc."
    CONTACT-INFO
            "Accedian Technical Assistance Center
             Accedian Networks, Inc.
             2351 Alfred-Nobel blvd., Suite N-410
             Saint-Laurent, Quebec Canada H4S 2A9
             E-mail: support@accedian.com"
    DESCRIPTION
            "TWAMP-Generator database for this Accedian Networks device."

    REVISION "201609230100Z"        -- 23 September 2016
    DESCRIPTION
            "Add acdTwampGenHistResultID and acdTwampGenHistResultSampleIndex
             to acdTwampGenHistResultGroup."

    REVISION "201605260100Z"        -- 26 May 2016
    DESCRIPTION
            "Set access level to read-only for acdTwampGenHistResultID,
             acdTwampGenHistResultSampleIndex."

    REVISION "201402240000Z"        -- Feb. 24 2014
    DESCRIPTION
            "Initial version of MIB module ACD-TWAMP-GEN-MIB."

    ::= { acdMibs 19}

acdTwampGenNotifications   OBJECT IDENTIFIER ::= { acdTwampGen 5 }
acdTwampGenMIBObjects      OBJECT IDENTIFIER ::= { acdTwampGen 6 }
acdTwampGenConformance     OBJECT IDENTIFIER ::= { acdTwampGen 7 }

---------------------------------------------------------------------------
 -- The TWAMP-Generator Results table
 -- This table contains all TWAMP-Generator entry results.
---------------------------------------------------------------------------

acdTwampGenResultTable OBJECT-TYPE
    SYNTAX      SEQUENCE OF AcdTwampGenResultEntry
    MAX-ACCESS  not-accessible
    STATUS      current
    DESCRIPTION
        "Result table of all TWAMP-Generator entries"
    ::= { acdTwampGen 1 }

acdTwampGenResultEntry OBJECT-TYPE
    SYNTAX      AcdTwampGenResultEntry
    MAX-ACCESS  not-accessible
    STATUS      current
    DESCRIPTION
        "An entry consisting of results for a TWAMP-Generator instance."
    INDEX   { acdTwampGenResultID }
    ::=  { acdTwampGenResultTable 1 }

AcdTwampGenResultEntry ::= SEQUENCE {
    acdTwampGenResultID                         Unsigned32,
    acdTwampGenResultInstName                   DisplayString,

    acdTwampGenResultPeriodNb                   Unsigned32,
    acdTwampGenResultPeriodTime                 DateAndTime,
    acdTwampGenResultCurrTxPacketCount          Counter64,
    acdTwampGenResultCurrRxPacketCount          Counter64,

    acdTwampGenResultTwoWayDelayValid           TruthValue,
    acdTwampGenResultTwoWayDelayInstValue       Integer32,
    acdTwampGenResultTwoWayDelayCurrSamples     Unsigned32,
    acdTwampGenResultTwoWayDelayCurrMinValue    Integer32,
    acdTwampGenResultTwoWayDelayCurrMaxValue    Integer32,
    acdTwampGenResultTwoWayDelayCurrAvgValue    Integer32,
    acdTwampGenResultTwoWayDelayCurrThreshEx    Unsigned32,

    acdTwampGenResultTwoWayDvValid              TruthValue,
    acdTwampGenResultTwoWayDvInstValue          Integer32,
    acdTwampGenResultTwoWayDvCurrSamples        Unsigned32,
    acdTwampGenResultTwoWayDvCurrMinValue       Integer32,
    acdTwampGenResultTwoWayDvCurrMaxValue       Integer32,
    acdTwampGenResultTwoWayDvCurrAvgValue       Integer32,
    acdTwampGenResultTwoWayDvCurrThreshEx       Unsigned32,

    acdTwampGenResultOneWayNeDelayValid         TruthValue,
    acdTwampGenResultOneWayNeDelayInstValue     Integer32,
    acdTwampGenResultOneWayNeDelayCurrSamples   Unsigned32,
    acdTwampGenResultOneWayNeDelayCurrMinValue  Integer32,
    acdTwampGenResultOneWayNeDelayCurrMaxValue  Integer32,
    acdTwampGenResultOneWayNeDelayCurrAvgValue  Integer32,
    acdTwampGenResultOneWayNeDelayCurrThreshEx  Unsigned32,

    acdTwampGenResultOneWayNeDvValid            TruthValue,
    acdTwampGenResultOneWayNeDvInstValue        Integer32,
    acdTwampGenResultOneWayNeDvCurrSamples      Unsigned32,
    acdTwampGenResultOneWayNeDvCurrMinValue     Integer32,
    acdTwampGenResultOneWayNeDvCurrMaxValue     Integer32,
    acdTwampGenResultOneWayNeDvCurrAvgValue     Integer32,
    acdTwampGenResultOneWayNeDvCurrThreshEx     Unsigned32,

    acdTwampGenResultOneWayFeDelayValid         TruthValue,
    acdTwampGenResultOneWayFeDelayInstValue     Integer32,
    acdTwampGenResultOneWayFeDelayCurrSamples   Unsigned32,
    acdTwampGenResultOneWayFeDelayCurrMinValue  Integer32,
    acdTwampGenResultOneWayFeDelayCurrMaxValue  Integer32,
    acdTwampGenResultOneWayFeDelayCurrAvgValue  Integer32,
    acdTwampGenResultOneWayFeDelayCurrThreshEx  Unsigned32,

    acdTwampGenResultOneWayFeDvValid            TruthValue,
    acdTwampGenResultOneWayFeDvInstValue        Integer32,
    acdTwampGenResultOneWayFeDvCurrSamples      Unsigned32,
    acdTwampGenResultOneWayFeDvCurrMinValue     Integer32,
    acdTwampGenResultOneWayFeDvCurrMaxValue     Integer32,
    acdTwampGenResultOneWayFeDvCurrAvgValue     Integer32,
    acdTwampGenResultOneWayFeDvCurrThreshEx     Unsigned32,

    acdTwampGenResultPktLossCurrSamples         Unsigned32,
    acdTwampGenResultPktLossCurrLostPackets     Unsigned32,
    acdTwampGenResultPktLossCurrLossRatio       Unsigned32,
    acdTwampGenResultPktLossCurrOutOfOrder      Unsigned32,
    acdTwampGenResultPktLossCurrDuplicate       Unsigned32,
    acdTwampGenResultPktLossCurrGaps            Unsigned32,
    acdTwampGenResultPktLossCurrLargestGap      Unsigned32
}

acdTwampGenResultID  OBJECT-TYPE
    SYNTAX      Unsigned32
    MAX-ACCESS  not-accessible
    STATUS      current
    DESCRIPTION
        "Unique value for each TWAMP-Generator instance. Its value ranges from 1 to
        MAXINT (4 bytes). "
    ::= { acdTwampGenResultEntry 1 }

acdTwampGenResultInstName  OBJECT-TYPE
    SYNTAX      DisplayString (SIZE (1..32))
    MAX-ACCESS  read-only
    STATUS      current
    DESCRIPTION
        "Name of the associated TWAMP-Generator instance."
    ::= { acdTwampGenResultEntry 2 }

acdTwampGenResultPeriodNb  OBJECT-TYPE
    SYNTAX      Unsigned32
    MAX-ACCESS  read-only
    STATUS      current
    DESCRIPTION
        "The number of periods that have elapsed since the probe was enabled."
    ::= { acdTwampGenResultEntry 3 }

acdTwampGenResultPeriodTime  OBJECT-TYPE
    SYNTAX      DateAndTime
    MAX-ACCESS  read-only
    STATUS      current
    DESCRIPTION
        "The start time of the current period."
    ::= { acdTwampGenResultEntry 4 }

acdTwampGenResultCurrTxPacketCount  OBJECT-TYPE
    SYNTAX      Counter64
    MAX-ACCESS  read-only
    STATUS      current
    DESCRIPTION
        "The number of TWAMP packets that have been sent in the current period."
    ::= { acdTwampGenResultEntry 5 }

acdTwampGenResultCurrRxPacketCount  OBJECT-TYPE
    SYNTAX      Counter64
    MAX-ACCESS  read-only
    STATUS      current
    DESCRIPTION
        "The number of TWAMP packets that have been received in the current period."
    ::= { acdTwampGenResultEntry 6 }

acdTwampGenResultTwoWayDelayValid  OBJECT-TYPE
    SYNTAX      TruthValue
    MAX-ACCESS  read-only
    STATUS      current
    DESCRIPTION
        "Indicate the validity of the Two-way instantaneous delay measurements."
    ::= { acdTwampGenResultEntry 7 }

acdTwampGenResultTwoWayDelayInstValue  OBJECT-TYPE
    SYNTAX      Integer32
    MAX-ACCESS  read-only
    STATUS      current
    DESCRIPTION
        "Indicates the Two-way delay instantaneous value. The value
         is expressed in micro-seconds."
    ::= { acdTwampGenResultEntry 8 }

acdTwampGenResultTwoWayDelayCurrSamples  OBJECT-TYPE
    SYNTAX      Unsigned32
    MAX-ACCESS  read-only
    STATUS      current
    DESCRIPTION
        "Indicates the number of samples gathered to calculate
         the current period two-way delay results."
    ::= { acdTwampGenResultEntry 9 }

acdTwampGenResultTwoWayDelayCurrMinValue  OBJECT-TYPE
    SYNTAX      Integer32
    MAX-ACCESS  read-only
    STATUS      current
    DESCRIPTION
        "Indicates the current Two-way delay minimum value. The value
         is expressed in micro-seconds."
    ::= { acdTwampGenResultEntry 10 }

acdTwampGenResultTwoWayDelayCurrMaxValue  OBJECT-TYPE
    SYNTAX      Integer32
    MAX-ACCESS  read-only
    STATUS      current
    DESCRIPTION
        "Indicates the current Two-way delay maximum value. The value
         is expressed in micro-seconds."
    ::= { acdTwampGenResultEntry 11 }

acdTwampGenResultTwoWayDelayCurrAvgValue  OBJECT-TYPE
    SYNTAX      Integer32
    MAX-ACCESS  read-only
    STATUS      current
    DESCRIPTION
        "Indicates the current Two-way delay average value. The value
         is expressed in micro-seconds."
    ::= { acdTwampGenResultEntry 12 }

acdTwampGenResultTwoWayDelayCurrThreshEx  OBJECT-TYPE
    SYNTAX      Unsigned32
    MAX-ACCESS  read-only
    STATUS      current
    DESCRIPTION
        "Indicates the current number of samples exceeding the limit."
    ::= { acdTwampGenResultEntry 13 }

acdTwampGenResultTwoWayDvValid  OBJECT-TYPE
    SYNTAX      TruthValue
    MAX-ACCESS  read-only
    STATUS      current
    DESCRIPTION
        "Indicate the validity of the Two-way instantaneous delay variation measurements."
    ::= { acdTwampGenResultEntry 14 }

acdTwampGenResultTwoWayDvInstValue  OBJECT-TYPE
    SYNTAX      Integer32
    MAX-ACCESS  read-only
    STATUS      current
    DESCRIPTION
        "Indicates the Two-way delay variation instantaneous value. The value
         is expressed in micro-seconds."
    ::= { acdTwampGenResultEntry 15 }

acdTwampGenResultTwoWayDvCurrSamples  OBJECT-TYPE
    SYNTAX      Unsigned32
    MAX-ACCESS  read-only
    STATUS      current
    DESCRIPTION
        "Indicates the number of samples gathered to calculate
         the current period two-way delay variation results."
    ::= { acdTwampGenResultEntry 16 }

acdTwampGenResultTwoWayDvCurrMinValue  OBJECT-TYPE
    SYNTAX      Integer32
    MAX-ACCESS  read-only
    STATUS      current
    DESCRIPTION
        "Indicates the current Two-way delay variation minimum value. The value
         is expressed in micro-seconds."
    ::= { acdTwampGenResultEntry 17 }

acdTwampGenResultTwoWayDvCurrMaxValue  OBJECT-TYPE
    SYNTAX      Integer32
    MAX-ACCESS  read-only
    STATUS      current
    DESCRIPTION
        "Indicates the current Two-way delay variation maximum value. The value
         is expressed in micro-seconds."
    ::= { acdTwampGenResultEntry 18 }

acdTwampGenResultTwoWayDvCurrAvgValue  OBJECT-TYPE
    SYNTAX      Integer32
    MAX-ACCESS  read-only
    STATUS      current
    DESCRIPTION
        "Indicates the current Two-way delay variation average value. The value
         is expressed in micro-seconds."
    ::= { acdTwampGenResultEntry 19 }

acdTwampGenResultTwoWayDvCurrThreshEx  OBJECT-TYPE
    SYNTAX      Unsigned32
    MAX-ACCESS  read-only
    STATUS      current
    DESCRIPTION
        "Indicates the current number of samples exceeding the limit."
    ::= { acdTwampGenResultEntry 20 }

acdTwampGenResultOneWayNeDelayValid  OBJECT-TYPE
    SYNTAX      TruthValue
    MAX-ACCESS  read-only
    STATUS      current
    DESCRIPTION
        "Indicate the validity of the One-way near-end instantaneous delay measurements."
    ::= { acdTwampGenResultEntry 21 }

acdTwampGenResultOneWayNeDelayInstValue  OBJECT-TYPE
    SYNTAX      Integer32
    MAX-ACCESS  read-only
    STATUS      current
    DESCRIPTION
        "Indicates the One-way near-end delay instantaneous value. The value
         is expressed in micro-seconds."
    ::= { acdTwampGenResultEntry 22 }

acdTwampGenResultOneWayNeDelayCurrSamples  OBJECT-TYPE
    SYNTAX      Unsigned32
    MAX-ACCESS  read-only
    STATUS      current
    DESCRIPTION
        "Indicates the number of samples gathered to calculate
         the current period One-way near-end delay results."
    ::= { acdTwampGenResultEntry 23 }

acdTwampGenResultOneWayNeDelayCurrMinValue  OBJECT-TYPE
    SYNTAX      Integer32
    MAX-ACCESS  read-only
    STATUS      current
    DESCRIPTION
        "Indicates the current One-way near-end delay minimum value. The value
         is expressed in micro-seconds."
    ::= { acdTwampGenResultEntry 24 }

acdTwampGenResultOneWayNeDelayCurrMaxValue  OBJECT-TYPE
    SYNTAX      Integer32
    MAX-ACCESS  read-only
    STATUS      current
    DESCRIPTION
        "Indicates the current One-way near-end delay maximum value. The value
         is expressed in micro-seconds."
    ::= { acdTwampGenResultEntry 25 }

acdTwampGenResultOneWayNeDelayCurrAvgValue  OBJECT-TYPE
    SYNTAX      Integer32
    MAX-ACCESS  read-only
    STATUS      current
    DESCRIPTION
        "Indicates the current One-way near-end delay average value. The value
         is expressed in micro-seconds."
    ::= { acdTwampGenResultEntry 26 }

acdTwampGenResultOneWayNeDelayCurrThreshEx  OBJECT-TYPE
    SYNTAX      Unsigned32
    MAX-ACCESS  read-only
    STATUS      current
    DESCRIPTION
        "Indicates the current number of samples exceeding the limit."
    ::= { acdTwampGenResultEntry 27 }

acdTwampGenResultOneWayNeDvValid  OBJECT-TYPE
    SYNTAX      TruthValue
    MAX-ACCESS  read-only
    STATUS      current
    DESCRIPTION
        "Indicate the validity of the One-way near-end instantaneous delay variation measurements."
    ::= { acdTwampGenResultEntry 28 }

acdTwampGenResultOneWayNeDvInstValue  OBJECT-TYPE
    SYNTAX      Integer32
    MAX-ACCESS  read-only
    STATUS      current
    DESCRIPTION
        "Indicates the One-way near-end delay variation instantaneous value. The value
         is expressed in micro-seconds."
    ::= { acdTwampGenResultEntry 29 }

acdTwampGenResultOneWayNeDvCurrSamples  OBJECT-TYPE
    SYNTAX      Unsigned32
    MAX-ACCESS  read-only
    STATUS      current
    DESCRIPTION
        "Indicates the number of samples gathered to calculate
         the current period One-way near-end delay variation results."
    ::= { acdTwampGenResultEntry 30 }

acdTwampGenResultOneWayNeDvCurrMinValue  OBJECT-TYPE
    SYNTAX      Integer32
    MAX-ACCESS  read-only
    STATUS      current
    DESCRIPTION
        "Indicates the current One-way near-end delay variation minimum value. The value
         is expressed in micro-seconds."
    ::= { acdTwampGenResultEntry 31 }

acdTwampGenResultOneWayNeDvCurrMaxValue  OBJECT-TYPE
    SYNTAX      Integer32
    MAX-ACCESS  read-only
    STATUS      current
    DESCRIPTION
        "Indicates the current One-way near-end delay variation maximum value. The value
         is expressed in micro-seconds."
    ::= { acdTwampGenResultEntry 32 }

acdTwampGenResultOneWayNeDvCurrAvgValue  OBJECT-TYPE
    SYNTAX      Integer32
    MAX-ACCESS  read-only
    STATUS      current
    DESCRIPTION
        "Indicates the current One-way near-end delay variation average value. The value
         is expressed in micro-seconds."
    ::= { acdTwampGenResultEntry 33 }

acdTwampGenResultOneWayNeDvCurrThreshEx  OBJECT-TYPE
    SYNTAX      Unsigned32
    MAX-ACCESS  read-only
    STATUS      current
    DESCRIPTION
        "Indicates the current number of samples exceeding the limit."
    ::= { acdTwampGenResultEntry 34 }

acdTwampGenResultOneWayFeDelayValid  OBJECT-TYPE
    SYNTAX      TruthValue
    MAX-ACCESS  read-only
    STATUS      current
    DESCRIPTION
        "Indicate the validity of the One-way far-end instantaneous delay measurements."
    ::= { acdTwampGenResultEntry 35 }

acdTwampGenResultOneWayFeDelayInstValue  OBJECT-TYPE
    SYNTAX      Integer32
    MAX-ACCESS  read-only
    STATUS      current
    DESCRIPTION
        "Indicates the One-way far-end delay instantaneous value. The value
         is expressed in micro-seconds."
    ::= { acdTwampGenResultEntry 36 }

acdTwampGenResultOneWayFeDelayCurrSamples  OBJECT-TYPE
    SYNTAX      Unsigned32
    MAX-ACCESS  read-only
    STATUS      current
    DESCRIPTION
        "Indicates the number of samples gathered to calculate
         the current period One-way far-end delay results."
    ::= { acdTwampGenResultEntry 37 }

acdTwampGenResultOneWayFeDelayCurrMinValue  OBJECT-TYPE
    SYNTAX      Integer32
    MAX-ACCESS  read-only
    STATUS      current
    DESCRIPTION
        "Indicates the current One-way far-end delay minimum value. The value
         is expressed in micro-seconds."
    ::= { acdTwampGenResultEntry 38 }

acdTwampGenResultOneWayFeDelayCurrMaxValue  OBJECT-TYPE
    SYNTAX      Integer32
    MAX-ACCESS  read-only
    STATUS      current
    DESCRIPTION
        "Indicates the current One-way far-end delay maximum value. The value
         is expressed in micro-seconds."
    ::= { acdTwampGenResultEntry 39 }

acdTwampGenResultOneWayFeDelayCurrAvgValue  OBJECT-TYPE
    SYNTAX      Integer32
    MAX-ACCESS  read-only
    STATUS      current
    DESCRIPTION
        "Indicates the current One-way far-end delay average value. The value
         is expressed in micro-seconds."
    ::= { acdTwampGenResultEntry 40 }

acdTwampGenResultOneWayFeDelayCurrThreshEx  OBJECT-TYPE
    SYNTAX      Unsigned32
    MAX-ACCESS  read-only
    STATUS      current
    DESCRIPTION
        "Indicates the current number of samples exceeding the limit."
    ::= { acdTwampGenResultEntry 41 }

acdTwampGenResultOneWayFeDvValid  OBJECT-TYPE
    SYNTAX      TruthValue
    MAX-ACCESS  read-only
    STATUS      current
    DESCRIPTION
        "Indicate the validity of the One-way far-end instantaneous delay variation measurements."
    ::= { acdTwampGenResultEntry 42 }


acdTwampGenResultOneWayFeDvInstValue  OBJECT-TYPE
    SYNTAX      Integer32
    MAX-ACCESS  read-only
    STATUS      current
    DESCRIPTION
        "Indicates the One-way far-end delay variation instantaneous value. The value
         is expressed in micro-seconds."
    ::= { acdTwampGenResultEntry 43 }

acdTwampGenResultOneWayFeDvCurrSamples  OBJECT-TYPE
    SYNTAX      Unsigned32
    MAX-ACCESS  read-only
    STATUS      current
    DESCRIPTION
        "Indicates the number of samples gathered to calculate
         the current period One-way far-end delay variation results."
    ::= { acdTwampGenResultEntry 44 }

acdTwampGenResultOneWayFeDvCurrMinValue  OBJECT-TYPE
    SYNTAX      Integer32
    MAX-ACCESS  read-only
    STATUS      current
    DESCRIPTION
        "Indicates the current One-way far-end delay variation minimum value. The value
         is expressed in micro-seconds."
    ::= { acdTwampGenResultEntry 45 }

acdTwampGenResultOneWayFeDvCurrMaxValue  OBJECT-TYPE
    SYNTAX      Integer32
    MAX-ACCESS  read-only
    STATUS      current
    DESCRIPTION
        "Indicates the current One-way far-end delay variation maximum value. The value
         is expressed in micro-seconds."
    ::= { acdTwampGenResultEntry 46 }

acdTwampGenResultOneWayFeDvCurrAvgValue  OBJECT-TYPE
    SYNTAX      Integer32
    MAX-ACCESS  read-only
    STATUS      current
    DESCRIPTION
        "Indicates the current One-way far-end delay variation average value. The value
         is expressed in micro-seconds."
    ::= { acdTwampGenResultEntry 47 }

acdTwampGenResultOneWayFeDvCurrThreshEx  OBJECT-TYPE
    SYNTAX      Unsigned32
    MAX-ACCESS  read-only
    STATUS      current
    DESCRIPTION
        "Indicates the current number of samples exceeding the limit."
    ::= { acdTwampGenResultEntry 48 }

acdTwampGenResultPktLossCurrSamples  OBJECT-TYPE
    SYNTAX      Unsigned32
    MAX-ACCESS  read-only
    STATUS      current
    DESCRIPTION
        "The number of TWAMP packets that have been sent in the current period."
    ::= { acdTwampGenResultEntry 49 }

acdTwampGenResultPktLossCurrLostPackets  OBJECT-TYPE
    SYNTAX      Unsigned32
    MAX-ACCESS  read-only
    STATUS      current
    DESCRIPTION
        "The number of TWAMP packets that have been lost in the current period."
    ::= { acdTwampGenResultEntry 50 }

acdTwampGenResultPktLossCurrLossRatio  OBJECT-TYPE
    SYNTAX      Unsigned32
    MAX-ACCESS  read-only
    STATUS      current
    DESCRIPTION
        "Packet loss ratio expressed in hundreth of percent (100 is 1%)."
    ::= { acdTwampGenResultEntry 51 }

acdTwampGenResultPktLossCurrOutOfOrder  OBJECT-TYPE
    SYNTAX      Unsigned32
    MAX-ACCESS  read-only
    STATUS      current
    DESCRIPTION
        "The number of out-of-order TWAMP packets in the current period."
    ::= { acdTwampGenResultEntry 52 }

acdTwampGenResultPktLossCurrDuplicate  OBJECT-TYPE
    SYNTAX      Unsigned32
    MAX-ACCESS  read-only
    STATUS      current
    DESCRIPTION
        "The number of duplicate TWAMP packets in the current period."
    ::= { acdTwampGenResultEntry 53 }

acdTwampGenResultPktLossCurrGaps  OBJECT-TYPE
    SYNTAX      Unsigned32
    MAX-ACCESS  read-only
    STATUS      current
    DESCRIPTION
        "The number of gaps that were registered during the period."
    ::= { acdTwampGenResultEntry 54 }

acdTwampGenResultPktLossCurrLargestGap  OBJECT-TYPE
    SYNTAX      Unsigned32
    MAX-ACCESS  read-only
    STATUS      current
    DESCRIPTION
        "The largest number of consecutive packets that were detected as missing."
    ::= { acdTwampGenResultEntry 55 }


---------------------------------------------------------------------------
 -- The TWAMP-Generator status table
 -- This table contains all TWAMP-Generator entry statuses.
---------------------------------------------------------------------------

acdTwampGenStatusTable OBJECT-TYPE
    SYNTAX      SEQUENCE OF AcdTwampGenStatusEntry
    MAX-ACCESS  not-accessible
    STATUS      current
    DESCRIPTION
        "Status table of all TWAMP-Generator entries"
    ::= { acdTwampGen 2 }

acdTwampGenStatusEntry OBJECT-TYPE
    SYNTAX      AcdTwampGenStatusEntry
    MAX-ACCESS  not-accessible
    STATUS      current
    DESCRIPTION
        "An entry consisting of the status for a TWAMP-Generator instance."
    INDEX   { acdTwampGenStatusID }
    ::=  { acdTwampGenStatusTable 1 }

AcdTwampGenStatusEntry ::= SEQUENCE {
    acdTwampGenStatusID                              Unsigned32,
    acdTwampGenStatusInstName                        DisplayString,
    acdTwampGenStatusTwoWayDelayAlert                TruthValue,
    acdTwampGenStatusTwoWayAvgDelayAlert             TruthValue,
    acdTwampGenStatusTwoWayDvAlert                   TruthValue,
    acdTwampGenStatusTwoWayAvgDvAlert                TruthValue,
    acdTwampGenStatusOneWayNeDelayAlert              TruthValue,
    acdTwampGenStatusOneWayNeAvgDelayAlert           TruthValue,
    acdTwampGenStatusOneWayNeDvAlert                 TruthValue,
    acdTwampGenStatusOneWayNeAvgDvAlert              TruthValue,
    acdTwampGenStatusOneWayFeDelayAlert              TruthValue,
    acdTwampGenStatusOneWayFeAvgDelayAlert           TruthValue,
    acdTwampGenStatusOneWayFeDvAlert                 TruthValue,
    acdTwampGenStatusOneWayFeAvgDvAlert              TruthValue,
    acdTwampGenStatusPacketLossContinuityCheckAlert  TruthValue,
    acdTwampGenStatusPacketLossExcessivePacketLossAlert    TruthValue
}

acdTwampGenStatusID  OBJECT-TYPE
    SYNTAX      Unsigned32
    MAX-ACCESS  not-accessible
    STATUS      current
    DESCRIPTION
        "Unique value for each TWAMP-Generator instance. Its value ranges from 1 to
        MAXINT (4 bytes). "
    ::= { acdTwampGenStatusEntry 1 }

acdTwampGenStatusInstName  OBJECT-TYPE
    SYNTAX      DisplayString (SIZE (1..32))
    MAX-ACCESS  read-only
    STATUS      current
    DESCRIPTION
        "Name of the associated TWAMP-Generator instance."
    ::= { acdTwampGenStatusEntry 2 }

acdTwampGenStatusTwoWayDelayAlert  OBJECT-TYPE
    SYNTAX      TruthValue
    MAX-ACCESS  read-only
    STATUS      current
    DESCRIPTION
        "Indicates the presence of the Two-way Delay alert."
    ::= { acdTwampGenStatusEntry 3 }

acdTwampGenStatusTwoWayAvgDelayAlert  OBJECT-TYPE
    SYNTAX      TruthValue
    MAX-ACCESS  read-only
    STATUS      current
    DESCRIPTION
        "Indicates the presence of the Two-way Average Delay alert."
    ::= { acdTwampGenStatusEntry 4 }

acdTwampGenStatusTwoWayDvAlert  OBJECT-TYPE
    SYNTAX      TruthValue
    MAX-ACCESS  read-only
    STATUS      current
    DESCRIPTION
        "Indicates the presence of the Two-way Delay Variation alert."
    ::= { acdTwampGenStatusEntry 5 }

acdTwampGenStatusTwoWayAvgDvAlert  OBJECT-TYPE
    SYNTAX      TruthValue
    MAX-ACCESS  read-only
    STATUS      current
    DESCRIPTION
        "Indicates the presence of the Two-way Average Delay Variation alert."
    ::= { acdTwampGenStatusEntry 6 }

acdTwampGenStatusOneWayNeDelayAlert  OBJECT-TYPE
    SYNTAX      TruthValue
    MAX-ACCESS  read-only
    STATUS      current
    DESCRIPTION
        "Indicates the presence of the One-way near-end Delay alert."
    ::= { acdTwampGenStatusEntry 7 }

acdTwampGenStatusOneWayNeAvgDelayAlert  OBJECT-TYPE
    SYNTAX      TruthValue
    MAX-ACCESS  read-only
    STATUS      current
    DESCRIPTION
        "Indicates the presence of the One-way near-end Average Delay alert."
    ::= { acdTwampGenStatusEntry 8 }

acdTwampGenStatusOneWayNeDvAlert  OBJECT-TYPE
    SYNTAX      TruthValue
    MAX-ACCESS  read-only
    STATUS      current
    DESCRIPTION
        "Indicates the presence of the One-way near-end Delay Variation alert."
    ::= { acdTwampGenStatusEntry 9 }

acdTwampGenStatusOneWayNeAvgDvAlert  OBJECT-TYPE
    SYNTAX      TruthValue
    MAX-ACCESS  read-only
    STATUS      current
    DESCRIPTION
        "Indicates the presence of the One-way near-end Average Delay Variation alert."
    ::= { acdTwampGenStatusEntry 10 }

acdTwampGenStatusOneWayFeDelayAlert  OBJECT-TYPE
    SYNTAX      TruthValue
    MAX-ACCESS  read-only
    STATUS      current
    DESCRIPTION
        "Indicates the presence of the One-way far-end Delay alert."
    ::= { acdTwampGenStatusEntry 11 }

acdTwampGenStatusOneWayFeAvgDelayAlert  OBJECT-TYPE
    SYNTAX      TruthValue
    MAX-ACCESS  read-only
    STATUS      current
    DESCRIPTION
        "Indicates the presence of the One-way far-end Average Delay alert."
    ::= { acdTwampGenStatusEntry 12 }

acdTwampGenStatusOneWayFeDvAlert  OBJECT-TYPE
    SYNTAX      TruthValue
    MAX-ACCESS  read-only
    STATUS      current
    DESCRIPTION
        "Indicates the presence of the One-way far-end Delay Variation alert."
    ::= { acdTwampGenStatusEntry 13 }

acdTwampGenStatusOneWayFeAvgDvAlert  OBJECT-TYPE
    SYNTAX      TruthValue
    MAX-ACCESS  read-only
    STATUS      current
    DESCRIPTION
        "Indicates the presence of the One-way far-end Average Delay Variation alert."
    ::= { acdTwampGenStatusEntry 14 }

acdTwampGenStatusPacketLossContinuityCheckAlert  OBJECT-TYPE
    SYNTAX      TruthValue
    MAX-ACCESS  read-only
    STATUS      current
    DESCRIPTION
        "Indicates the presence of the packet loss continuity check alert."
    ::= { acdTwampGenStatusEntry 15 }

acdTwampGenStatusPacketLossExcessivePacketLossAlert  OBJECT-TYPE
    SYNTAX      TruthValue
    MAX-ACCESS  read-only
    STATUS      current
    DESCRIPTION
        "Indicates the presence of the excessive packet loss alert."
    ::= { acdTwampGenStatusEntry 16 }


---------------------------------------------------------------------------
 -- The TWAMP-Generator configuration table
 -- This table contains all TWAMP-Generator entry configurations.
---------------------------------------------------------------------------

acdTwampGenCfgTable OBJECT-TYPE
    SYNTAX      SEQUENCE OF AcdTwampGenCfgEntry
    MAX-ACCESS  not-accessible
    STATUS      current
    DESCRIPTION
        "Configuration table of all TWAMP-Generator entries."
    ::= { acdTwampGen 3 }

acdTwampGenCfgEntry OBJECT-TYPE
    SYNTAX      AcdTwampGenCfgEntry
    MAX-ACCESS  not-accessible
    STATUS      current
    DESCRIPTION
        "An entry consisting of all settings to manage a TWAMP-Generator instance."
    INDEX   { acdTwampGenCfgID }
    ::=  { acdTwampGenCfgTable 1 }


AcdTwampGenCfgEntry ::= SEQUENCE {
    acdTwampGenCfgID                      Unsigned32,
    acdTwampGenCfgName                    DisplayString,
    acdTwampGenCfgState                   INTEGER,
    acdTwampGenCfgInterval                Unsigned32,
    acdTwampGenCfgReferencePeriod         Unsigned32,
    acdTwampGenCfgPktSize                 Unsigned32,
    acdTwampGenCfgDestIPv4Addr            IpAddress,
    acdTwampGenCfgSourcePortNumber        Unsigned32,
    acdTwampGenCfgDestPortNumber          Unsigned32,
    acdTwampGenCfgDscp                    Unsigned32,
    acdTwampGenCfgEcn                     Unsigned32,
    acdTwampGenCfgVlan1Priority           Unsigned32,
    acdTwampGenCfgTwoWayMaxDelay          Unsigned32,
    acdTwampGenCfgTwoWayMaxDelayThrs      Unsigned32,
    acdTwampGenCfgTwoWayAvgDelayThrs      Unsigned32,
    acdTwampGenCfgTwoWayMaxDv             Unsigned32,
    acdTwampGenCfgTwoWayMaxDvThrs         Unsigned32,
    acdTwampGenCfgTwoWayAvgDvThrs         Unsigned32,
    acdTwampGenCfgOneWayNearEndMaxDelay         Unsigned32,
    acdTwampGenCfgOneWayNearEndMaxDelayThrs     Unsigned32,
    acdTwampGenCfgOneWayNearEndAvgDelayThrs     Unsigned32,
    acdTwampGenCfgOneWayNearEndMaxDv            Unsigned32,
    acdTwampGenCfgOneWayNearEndMaxDvThrs        Unsigned32,
    acdTwampGenCfgOneWayNearEndAvgDvThrs        Unsigned32,
    acdTwampGenCfgOneWayFarEndMaxDelay          Unsigned32,
    acdTwampGenCfgOneWayFarEndMaxDelayThrs      Unsigned32,
    acdTwampGenCfgOneWayFarEndAvgDelayThrs      Unsigned32,
    acdTwampGenCfgOneWayFarEndMaxDv             Unsigned32,
    acdTwampGenCfgOneWayFarEndMaxDvThrs         Unsigned32,
    acdTwampGenCfgOneWayFarEndAvgDvThrs         Unsigned32,
    acdTwampGenCfgPacketLossContinuityCheck     Unsigned32,
    acdTwampGenCfgPacketLossRate                Unsigned32
}

acdTwampGenCfgID  OBJECT-TYPE
    SYNTAX      Unsigned32
    MAX-ACCESS  not-accessible
    STATUS      current
    DESCRIPTION
        "Unique value for each TWAMP-Generator instance. This value follows the ordering
         of the status and the results table. Its value ranges from 1 to
         MAXINT (4 bytes)."
    ::= { acdTwampGenCfgEntry 1 }

acdTwampGenCfgName  OBJECT-TYPE
    SYNTAX      DisplayString (SIZE (1..32))
    MAX-ACCESS  read-write
    STATUS      current
    DESCRIPTION
        "This is a string to identify this TWAMP-Generator instance."
    ::= { acdTwampGenCfgEntry 2 }

acdTwampGenCfgState  OBJECT-TYPE
    SYNTAX      INTEGER {
                    enable(0),
                    disable(1)
                }
    MAX-ACCESS  read-write
    STATUS      current
    DESCRIPTION
        "Configuration state of this TWAMP-Generator entry."
    ::= { acdTwampGenCfgEntry 3 }

acdTwampGenCfgInterval  OBJECT-TYPE
    SYNTAX      Unsigned32
    MAX-ACCESS  read-write
    STATUS      current
    DESCRIPTION
        "Interval in milliseconds at which TWAMP-Generator packets should be sent."
    ::= { acdTwampGenCfgEntry 4 }

acdTwampGenCfgReferencePeriod  OBJECT-TYPE
    SYNTAX      Unsigned32
    MAX-ACCESS  read-write
    STATUS      current
    DESCRIPTION
        "Reference period in minutes."
    ::= { acdTwampGenCfgEntry 5 }

acdTwampGenCfgTwoWayMaxDelay  OBJECT-TYPE
    SYNTAX      Unsigned32
    MAX-ACCESS  read-write
    STATUS      current
    DESCRIPTION
        "Maximum two-way delay allowed. (in usec)"
    ::= { acdTwampGenCfgEntry 13 }

acdTwampGenCfgTwoWayMaxDv  OBJECT-TYPE
    SYNTAX      Unsigned32
    MAX-ACCESS  read-write
    STATUS      current
    DESCRIPTION
        "Maximum two-way delay variation allowed.(in usec)"
    ::= { acdTwampGenCfgEntry 16 }

acdTwampGenCfgTwoWayMaxDelayThrs  OBJECT-TYPE
    SYNTAX      Unsigned32
    MAX-ACCESS  read-write
    STATUS      current
    DESCRIPTION
        "Maximum consecutive two-way delay samples allowed greater than tw-max-delay."
    ::= { acdTwampGenCfgEntry 14 }

acdTwampGenCfgTwoWayMaxDvThrs  OBJECT-TYPE
    SYNTAX      Unsigned32
    MAX-ACCESS  read-write
    STATUS      current
    DESCRIPTION
        "Maximum consecutive two-way delay samples allowed greater than tw-max-dv."
    ::= { acdTwampGenCfgEntry 17 }

acdTwampGenCfgTwoWayAvgDelayThrs  OBJECT-TYPE
    SYNTAX      Unsigned32
    MAX-ACCESS  read-write
    STATUS      current
    DESCRIPTION
        "Maximum two-way average delay.(in usec)"
    ::= { acdTwampGenCfgEntry 15 }

acdTwampGenCfgTwoWayAvgDvThrs  OBJECT-TYPE
    SYNTAX      Unsigned32
    MAX-ACCESS  read-write
    STATUS      current
    DESCRIPTION
        "Maximum two-way average delay variation.(in usec)"
    ::= { acdTwampGenCfgEntry 18 }

acdTwampGenCfgOneWayNearEndMaxDelay  OBJECT-TYPE
    SYNTAX      Unsigned32
    MAX-ACCESS  read-write
    STATUS      current
    DESCRIPTION
        "Maximum one-way near-end delay allowed.(in usec)"
    ::= { acdTwampGenCfgEntry 19 }

acdTwampGenCfgOneWayNearEndMaxDv  OBJECT-TYPE
    SYNTAX      Unsigned32
    MAX-ACCESS  read-write
    STATUS      current
    DESCRIPTION
        "Maximum one-way near-end delay variation allowed.(in usec)"
    ::= { acdTwampGenCfgEntry 22 }

acdTwampGenCfgOneWayNearEndMaxDelayThrs  OBJECT-TYPE
    SYNTAX      Unsigned32
    MAX-ACCESS  read-write
    STATUS      current
    DESCRIPTION
        "Maximum consecutive one-way near-end delay samples allowed greater than ow-near-end-max-delay."
    ::= { acdTwampGenCfgEntry 20 }

acdTwampGenCfgOneWayNearEndMaxDvThrs  OBJECT-TYPE
    SYNTAX      Unsigned32
    MAX-ACCESS  read-write
    STATUS      current
    DESCRIPTION
        "Maximum consecutive one-way near-end delay samples allowed greater than ow-near-end-max-dv."
    ::= { acdTwampGenCfgEntry 23 }

acdTwampGenCfgOneWayNearEndAvgDelayThrs  OBJECT-TYPE
    SYNTAX      Unsigned32
    MAX-ACCESS  read-write
    STATUS      current
    DESCRIPTION
        "Maximum one-way near-end average delay.(in usec)"
    ::= { acdTwampGenCfgEntry 21 }

acdTwampGenCfgOneWayNearEndAvgDvThrs  OBJECT-TYPE
    SYNTAX      Unsigned32
    MAX-ACCESS  read-write
    STATUS      current
    DESCRIPTION
        "Maximum one-way near-end average delay variation.(in usec)"
    ::= { acdTwampGenCfgEntry 24 }

acdTwampGenCfgOneWayFarEndMaxDelay  OBJECT-TYPE
    SYNTAX      Unsigned32
    MAX-ACCESS  read-write
    STATUS      current
    DESCRIPTION
        "Maximum one-way far-end delay allowed.(in usec)"
    ::= { acdTwampGenCfgEntry 25 }

acdTwampGenCfgOneWayFarEndMaxDv  OBJECT-TYPE
    SYNTAX      Unsigned32
    MAX-ACCESS  read-write
    STATUS      current
    DESCRIPTION
        "Maximum one-way far-end delay variation allowed.(in usec)"
    ::= { acdTwampGenCfgEntry 28 }

acdTwampGenCfgOneWayFarEndMaxDelayThrs  OBJECT-TYPE
    SYNTAX      Unsigned32
    MAX-ACCESS  read-write
    STATUS      current
    DESCRIPTION
        "Maximum consecutive one-way far-end delay samples allowed greater than ow-far-end-max-delay."
    ::= { acdTwampGenCfgEntry 26 }

acdTwampGenCfgOneWayFarEndMaxDvThrs  OBJECT-TYPE
    SYNTAX      Unsigned32
    MAX-ACCESS  read-write
    STATUS      current
    DESCRIPTION
        "Maximum consecutive one-way far-end delay samples allowed greater than ow-far-end-max-dv."
    ::= { acdTwampGenCfgEntry 29 }

acdTwampGenCfgOneWayFarEndAvgDelayThrs  OBJECT-TYPE
    SYNTAX      Unsigned32
    MAX-ACCESS  read-write
    STATUS      current
    DESCRIPTION
        "Maximum one-way far-end average delay.(in usec)"
    ::= { acdTwampGenCfgEntry 27 }

acdTwampGenCfgOneWayFarEndAvgDvThrs  OBJECT-TYPE
    SYNTAX      Unsigned32
    MAX-ACCESS  read-write
    STATUS      current
    DESCRIPTION
        "Maximum one-way far-end average delay variation.(in usec)"
    ::= { acdTwampGenCfgEntry 30 }

acdTwampGenCfgDscp  OBJECT-TYPE
    SYNTAX      Unsigned32
    MAX-ACCESS  read-write
    STATUS      current
    DESCRIPTION
       "The DSCP value used to reach the peer TWAMP-Generator instance. Its value ranges
            from 0 to 64."
    ::= { acdTwampGenCfgEntry 10 }

acdTwampGenCfgEcn  OBJECT-TYPE
    SYNTAX      Unsigned32
    MAX-ACCESS  read-write
    STATUS      current
    DESCRIPTION
       "The Explicit Congestion Notification value"
    ::= { acdTwampGenCfgEntry 11 }

acdTwampGenCfgVlan1Priority OBJECT-TYPE
    SYNTAX      Unsigned32
    MAX-ACCESS  read-write
    STATUS      current
    DESCRIPTION
       "The first VLAN priority used to tag the outgoing traffic.
             Its value ranges from 0 to 7."
    ::= { acdTwampGenCfgEntry 12 }

acdTwampGenCfgDestIPv4Addr  OBJECT-TYPE
    SYNTAX      IpAddress
    MAX-ACCESS  read-write
    STATUS      current
    DESCRIPTION
        "The destination IP address used to reach the peer TWAMP-Generator instance."
    ::= { acdTwampGenCfgEntry 7 }

acdTwampGenCfgDestPortNumber  OBJECT-TYPE
    SYNTAX      Unsigned32
    MAX-ACCESS  read-write
    STATUS      current
    DESCRIPTION
        "The destination UDP port number used to reach the peer TWAMP-Generator instance."
    ::= { acdTwampGenCfgEntry 9 }

acdTwampGenCfgSourcePortNumber  OBJECT-TYPE
    SYNTAX      Unsigned32
    MAX-ACCESS  read-write
    STATUS      current
    DESCRIPTION
        "The source UDP port number on which to listen for peer TWAMP-Generator samples."
    ::= { acdTwampGenCfgEntry 8 }

acdTwampGenCfgPktSize  OBJECT-TYPE
    SYNTAX      Unsigned32
    MAX-ACCESS  read-write
    STATUS      current
    DESCRIPTION
        "Transmit packet size."
    ::= { acdTwampGenCfgEntry 6 }

acdTwampGenCfgPacketLossContinuityCheck  OBJECT-TYPE
    SYNTAX      Unsigned32
    MAX-ACCESS  read-write
    STATUS      current
    DESCRIPTION
        "Continuity check threshold."
    ::= { acdTwampGenCfgEntry 31 }

acdTwampGenCfgPacketLossRate  OBJECT-TYPE
    SYNTAX      Unsigned32
    MAX-ACCESS  read-write
    STATUS      current
    DESCRIPTION
        "Packet loss ratio threshold allowed without issuing an excessive
         packet loss alarm expressed in hundreth of percent (100 is 1%)."
    ::= { acdTwampGenCfgEntry 32 }

------------------------------------------------------------------------
 -- The TWAMP-Generator history Results table
 -- This table contains all TWAMP-Generator entry results.
---------------------------------------------------------------------------

acdTwampGenHistResultTable OBJECT-TYPE
    SYNTAX      SEQUENCE OF AcdTwampGenHistResultEntry
    MAX-ACCESS  not-accessible
    STATUS      current
    DESCRIPTION
        "Result table of all TWAMP-Generator entries"
    ::= { acdTwampGen 4 }

acdTwampGenHistResultEntry OBJECT-TYPE
    SYNTAX      AcdTwampGenHistResultEntry
    MAX-ACCESS  not-accessible
    STATUS      current
    DESCRIPTION
        "An entry consisting of results for a TWAMP-Generator instance for a specific
         periodin time."
    INDEX   { acdTwampGenHistResultID , acdTwampGenHistResultSampleIndex }
    ::=  { acdTwampGenHistResultTable 1 }

AcdTwampGenHistResultEntry ::= SEQUENCE {
    acdTwampGenHistResultID                         Unsigned32,
    acdTwampGenHistResultSampleIndex                Unsigned32,

    acdTwampGenHistResultInstName                   DisplayString,
    acdTwampGenHistResultPeriodTime                 DateAndTime,
    acdTwampGenHistResultTxPacketCount              Counter64,
    acdTwampGenHistResultRxPacketCount              Counter64,

    acdTwampGenHistResultTwoWayDelayValid           TruthValue,
    acdTwampGenHistResultTwoWayDelayInstValue       Integer32,
    acdTwampGenHistResultTwoWayDelaySamples         Unsigned32,
    acdTwampGenHistResultTwoWayDelayMinValue        Integer32,
    acdTwampGenHistResultTwoWayDelayMaxValue        Integer32,
    acdTwampGenHistResultTwoWayDelayAvgValue        Integer32,
    acdTwampGenHistResultTwoWayDelayThreshEx        Unsigned32,

    acdTwampGenHistResultTwoWayDvValid              TruthValue,
    acdTwampGenHistResultTwoWayDvInstValue          Integer32,
    acdTwampGenHistResultTwoWayDvSamples            Unsigned32,
    acdTwampGenHistResultTwoWayDvMinValue           Integer32,
    acdTwampGenHistResultTwoWayDvMaxValue           Integer32,
    acdTwampGenHistResultTwoWayDvAvgValue           Integer32,
    acdTwampGenHistResultTwoWayDvThreshEx           Unsigned32,

    acdTwampGenHistResultOneWayNeDelayValid         TruthValue,
    acdTwampGenHistResultOneWayNeDelayInstValue     Integer32,
    acdTwampGenHistResultOneWayNeDelaySamples       Unsigned32,
    acdTwampGenHistResultOneWayNeDelayMinValue      Integer32,
    acdTwampGenHistResultOneWayNeDelayMaxValue      Integer32,
    acdTwampGenHistResultOneWayNeDelayAvgValue      Integer32,
    acdTwampGenHistResultOneWayNeDelayThreshEx      Unsigned32,

    acdTwampGenHistResultOneWayNeDvValid            TruthValue,
    acdTwampGenHistResultOneWayNeDvInstValue        Integer32,
    acdTwampGenHistResultOneWayNeDvSamples          Unsigned32,
    acdTwampGenHistResultOneWayNeDvMinValue         Integer32,
    acdTwampGenHistResultOneWayNeDvMaxValue         Integer32,
    acdTwampGenHistResultOneWayNeDvAvgValue         Integer32,
    acdTwampGenHistResultOneWayNeDvThreshEx         Unsigned32,

    acdTwampGenHistResultOneWayFeDelayValid         TruthValue,
    acdTwampGenHistResultOneWayFeDelayInstValue     Integer32,
    acdTwampGenHistResultOneWayFeDelaySamples       Unsigned32,
    acdTwampGenHistResultOneWayFeDelayMinValue      Integer32,
    acdTwampGenHistResultOneWayFeDelayMaxValue      Integer32,
    acdTwampGenHistResultOneWayFeDelayAvgValue      Integer32,
    acdTwampGenHistResultOneWayFeDelayThreshEx      Unsigned32,

    acdTwampGenHistResultOneWayFeDvValid            TruthValue,
    acdTwampGenHistResultOneWayFeDvInstValue        Integer32,
    acdTwampGenHistResultOneWayFeDvSamples          Unsigned32,
    acdTwampGenHistResultOneWayFeDvMinValue         Integer32,
    acdTwampGenHistResultOneWayFeDvMaxValue         Integer32,
    acdTwampGenHistResultOneWayFeDvAvgValue         Integer32,
    acdTwampGenHistResultOneWayFeDvThreshEx         Unsigned32,

    acdTwampGenHistResultPktLossSamples             Unsigned32,
    acdTwampGenHistResultPktLossLostPackets         Unsigned32,
    acdTwampGenHistResultPktLossLossRatio           Unsigned32,
    acdTwampGenHistResultPktLossOutOfOrder          Unsigned32,
    acdTwampGenHistResultPktLossDuplicate           Unsigned32,
    acdTwampGenHistResultPktLossGaps                Unsigned32,
    acdTwampGenHistResultPktLossLargestGap          Unsigned32
}

acdTwampGenHistResultID  OBJECT-TYPE
    SYNTAX      Unsigned32
    MAX-ACCESS  read-only
    STATUS      current
    DESCRIPTION
        "Unique value for each TWAMP-Generator instance. Its value ranges from 1 to
        MAXINT (4 bytes). "
    ::= { acdTwampGenHistResultEntry 1 }

acdTwampGenHistResultSampleIndex  OBJECT-TYPE
    SYNTAX      Unsigned32
    MAX-ACCESS  read-only
    STATUS      current
    DESCRIPTION
        "An index that uniquely identifies the particular sample this entry
         represents among all samples associated with the same TWAMP-Generator instance.
         This index starts at 1 and increases by one as each new sample."
    ::= { acdTwampGenHistResultEntry 2 }

acdTwampGenHistResultInstName  OBJECT-TYPE
    SYNTAX      DisplayString (SIZE (1..32))
    MAX-ACCESS  read-only
    STATUS      current
    DESCRIPTION
        "Name of the associated TWAMP-Generator instance."
    ::= { acdTwampGenHistResultEntry 3 }

acdTwampGenHistResultPeriodTime  OBJECT-TYPE
    SYNTAX      DateAndTime
    MAX-ACCESS  read-only
    STATUS      current
    DESCRIPTION
        "This is the time of the end of this entry."
    ::= { acdTwampGenHistResultEntry 4 }

acdTwampGenHistResultTxPacketCount  OBJECT-TYPE
    SYNTAX      Counter64
    MAX-ACCESS  read-only
    STATUS      current
    DESCRIPTION
        "The number of TWAMP packets that have been sent in the period."
    ::= { acdTwampGenHistResultEntry 5 }

acdTwampGenHistResultRxPacketCount  OBJECT-TYPE
    SYNTAX      Counter64
    MAX-ACCESS  read-only
    STATUS      current
    DESCRIPTION
        "The number of TWAMP packets that have been received in the period."
    ::= { acdTwampGenHistResultEntry 6 }

acdTwampGenHistResultTwoWayDelayValid  OBJECT-TYPE
    SYNTAX      TruthValue
    MAX-ACCESS  read-only
    STATUS      current
    DESCRIPTION
        "Indicate the validity of the Two-way instantaneous delay measurements."
    ::= { acdTwampGenHistResultEntry 7 }

acdTwampGenHistResultTwoWayDelayInstValue  OBJECT-TYPE
    SYNTAX      Integer32
    MAX-ACCESS  read-only
    STATUS      current
    DESCRIPTION
        "Indicates the Two-way delay instantaneous value. The value
         is expressed in micro-seconds."
    ::= { acdTwampGenHistResultEntry 8 }

acdTwampGenHistResultTwoWayDelaySamples  OBJECT-TYPE
    SYNTAX      Unsigned32
    MAX-ACCESS  read-only
    STATUS      current
    DESCRIPTION
        "Indicates the number of samples gathered to calculate
         the period two-way delay results."
    ::= { acdTwampGenHistResultEntry 9 }

acdTwampGenHistResultTwoWayDelayMinValue  OBJECT-TYPE
    SYNTAX      Integer32
    MAX-ACCESS  read-only
    STATUS      current
    DESCRIPTION
        "Indicates the Two-way delay minimum value. The value
         is expressed in micro-seconds."
    ::= { acdTwampGenHistResultEntry 10 }

acdTwampGenHistResultTwoWayDelayMaxValue  OBJECT-TYPE
    SYNTAX      Integer32
    MAX-ACCESS  read-only
    STATUS      current
    DESCRIPTION
        "Indicates the Two-way delay maximum value. The value
         is expressed in micro-seconds."
    ::= { acdTwampGenHistResultEntry 11 }

acdTwampGenHistResultTwoWayDelayAvgValue  OBJECT-TYPE
    SYNTAX      Integer32
    MAX-ACCESS  read-only
    STATUS      current
    DESCRIPTION
        "Indicates the Two-way delay average value. The value
         is expressed in micro-seconds."
    ::= { acdTwampGenHistResultEntry 12 }

acdTwampGenHistResultTwoWayDelayThreshEx  OBJECT-TYPE
    SYNTAX      Unsigned32
    MAX-ACCESS  read-only
    STATUS      current
    DESCRIPTION
        "Indicates the number of samples exceeding the limit."
    ::= { acdTwampGenHistResultEntry 13 }

acdTwampGenHistResultTwoWayDvValid  OBJECT-TYPE
    SYNTAX      TruthValue
    MAX-ACCESS  read-only
    STATUS      current
    DESCRIPTION
        "Indicate the validity of the Two-way instantaneous delay variation measurements."
    ::= { acdTwampGenHistResultEntry 14 }

acdTwampGenHistResultTwoWayDvInstValue  OBJECT-TYPE
    SYNTAX      Integer32
    MAX-ACCESS  read-only
    STATUS      current
    DESCRIPTION
        "Indicates the Two-way delay variation instantaneous value. The value
         is expressed in micro-seconds."
    ::= { acdTwampGenHistResultEntry 15 }

acdTwampGenHistResultTwoWayDvSamples  OBJECT-TYPE
    SYNTAX      Unsigned32
    MAX-ACCESS  read-only
    STATUS      current
    DESCRIPTION
        "Indicates the number of samples gathered to calculate
         the period two-way delay variation results."
    ::= { acdTwampGenHistResultEntry 16 }

acdTwampGenHistResultTwoWayDvMinValue  OBJECT-TYPE
    SYNTAX      Integer32
    MAX-ACCESS  read-only
    STATUS      current
    DESCRIPTION
        "Indicates the Two-way delay variation minimum value. The value
         is expressed in micro-seconds."
    ::= { acdTwampGenHistResultEntry 17 }

acdTwampGenHistResultTwoWayDvMaxValue  OBJECT-TYPE
    SYNTAX      Integer32
    MAX-ACCESS  read-only
    STATUS      current
    DESCRIPTION
        "Indicates the Two-way delay variation maximum value. The value
         is expressed in micro-seconds."
    ::= { acdTwampGenHistResultEntry 18 }

acdTwampGenHistResultTwoWayDvAvgValue  OBJECT-TYPE
    SYNTAX      Integer32
    MAX-ACCESS  read-only
    STATUS      current
    DESCRIPTION
        "Indicates the Two-way delay variation average value. The value
         is expressed in micro-seconds."
    ::= { acdTwampGenHistResultEntry 19 }

acdTwampGenHistResultTwoWayDvThreshEx  OBJECT-TYPE
    SYNTAX      Unsigned32
    MAX-ACCESS  read-only
    STATUS      current
    DESCRIPTION
        "Indicates the number of samples exceeding the limit."
    ::= { acdTwampGenHistResultEntry 20 }

acdTwampGenHistResultOneWayNeDelayValid  OBJECT-TYPE
    SYNTAX      TruthValue
    MAX-ACCESS  read-only
    STATUS      current
    DESCRIPTION
        "Indicate the validity of the One-way near-end instantaneous delay measurements."
    ::= { acdTwampGenHistResultEntry 21 }

acdTwampGenHistResultOneWayNeDelayInstValue  OBJECT-TYPE
    SYNTAX      Integer32
    MAX-ACCESS  read-only
    STATUS      current
    DESCRIPTION
        "Indicates the One-way near-end delay instantaneous value. The value
         is expressed in micro-seconds."
    ::= { acdTwampGenHistResultEntry 22 }

acdTwampGenHistResultOneWayNeDelaySamples  OBJECT-TYPE
    SYNTAX      Unsigned32
    MAX-ACCESS  read-only
    STATUS      current
    DESCRIPTION
        "Indicates the number of samples gathered to calculate
         the period One-way near-end delay results."
    ::= { acdTwampGenHistResultEntry 23 }

acdTwampGenHistResultOneWayNeDelayMinValue  OBJECT-TYPE
    SYNTAX      Integer32
    MAX-ACCESS  read-only
    STATUS      current
    DESCRIPTION
        "Indicates the One-way near-end delay minimum value. The value
         is expressed in micro-seconds."
    ::= { acdTwampGenHistResultEntry 24 }

acdTwampGenHistResultOneWayNeDelayMaxValue  OBJECT-TYPE
    SYNTAX      Integer32
    MAX-ACCESS  read-only
    STATUS      current
    DESCRIPTION
        "Indicates the One-way near-end delay maximum value. The value
         is expressed in micro-seconds."
    ::= { acdTwampGenHistResultEntry 25 }

acdTwampGenHistResultOneWayNeDelayAvgValue  OBJECT-TYPE
    SYNTAX      Integer32
    MAX-ACCESS  read-only
    STATUS      current
    DESCRIPTION
        "Indicates the One-way near-end delay average value. The value
         is expressed in micro-seconds."
    ::= { acdTwampGenHistResultEntry 26 }

acdTwampGenHistResultOneWayNeDelayThreshEx  OBJECT-TYPE
    SYNTAX      Unsigned32
    MAX-ACCESS  read-only
    STATUS      current
    DESCRIPTION
        "Indicates the number of samples exceeding the limit."
    ::= { acdTwampGenHistResultEntry 27 }

acdTwampGenHistResultOneWayNeDvValid  OBJECT-TYPE
    SYNTAX      TruthValue
    MAX-ACCESS  read-only
    STATUS      current
    DESCRIPTION
        "Indicate the validity of the One-way near-end instantaneous delay variation measurements."
    ::= { acdTwampGenHistResultEntry 28 }

acdTwampGenHistResultOneWayNeDvInstValue  OBJECT-TYPE
    SYNTAX      Integer32
    MAX-ACCESS  read-only
    STATUS      current
    DESCRIPTION
        "Indicates the One-way near-end delay variation instantaneous value. The value
         is expressed in micro-seconds."
    ::= { acdTwampGenHistResultEntry 29 }

acdTwampGenHistResultOneWayNeDvSamples  OBJECT-TYPE
    SYNTAX      Unsigned32
    MAX-ACCESS  read-only
    STATUS      current
    DESCRIPTION
        "Indicates the number of samples gathered to calculate
         the period One-way near-end delay variation results."
    ::= { acdTwampGenHistResultEntry 30 }

acdTwampGenHistResultOneWayNeDvMinValue  OBJECT-TYPE
    SYNTAX      Integer32
    MAX-ACCESS  read-only
    STATUS      current
    DESCRIPTION
        "Indicates the One-way near-end delay variation minimum value. The value
         is expressed in micro-seconds."
    ::= { acdTwampGenHistResultEntry 31 }

acdTwampGenHistResultOneWayNeDvMaxValue  OBJECT-TYPE
    SYNTAX      Integer32
    MAX-ACCESS  read-only
    STATUS      current
    DESCRIPTION
        "Indicates the One-way near-end delay variation maximum value. The value
         is expressed in micro-seconds."
    ::= { acdTwampGenHistResultEntry 32 }

acdTwampGenHistResultOneWayNeDvAvgValue  OBJECT-TYPE
    SYNTAX      Integer32
    MAX-ACCESS  read-only
    STATUS      current
    DESCRIPTION
        "Indicates the One-way near-end delay variation average value. The value
         is expressed in micro-seconds."
    ::= { acdTwampGenHistResultEntry 33 }

acdTwampGenHistResultOneWayNeDvThreshEx  OBJECT-TYPE
    SYNTAX      Unsigned32
    MAX-ACCESS  read-only
    STATUS      current
    DESCRIPTION
        "Indicates the number of samples exceeding the limit."
    ::= { acdTwampGenHistResultEntry 34 }

acdTwampGenHistResultOneWayFeDelayValid  OBJECT-TYPE
    SYNTAX      TruthValue
    MAX-ACCESS  read-only
    STATUS      current
    DESCRIPTION
        "Indicate the validity of the One-way far-end instantaneous delay measurements."
    ::= { acdTwampGenHistResultEntry 35 }

acdTwampGenHistResultOneWayFeDelayInstValue  OBJECT-TYPE
    SYNTAX      Integer32
    MAX-ACCESS  read-only
    STATUS      current
    DESCRIPTION
        "Indicates the One-way far-end delay instantaneous value. The value
         is expressed in micro-seconds."
    ::= { acdTwampGenHistResultEntry 36 }

acdTwampGenHistResultOneWayFeDelaySamples  OBJECT-TYPE
    SYNTAX      Unsigned32
    MAX-ACCESS  read-only
    STATUS      current
    DESCRIPTION
        "Indicates the number of samples gathered to calculate
         the period One-way far-end delay results."
    ::= { acdTwampGenHistResultEntry 37 }

acdTwampGenHistResultOneWayFeDelayMinValue  OBJECT-TYPE
    SYNTAX      Integer32
    MAX-ACCESS  read-only
    STATUS      current
    DESCRIPTION
        "Indicates the One-way far-end delay minimum value. The value
         is expressed in micro-seconds."
    ::= { acdTwampGenHistResultEntry 38 }

acdTwampGenHistResultOneWayFeDelayMaxValue  OBJECT-TYPE
    SYNTAX      Integer32
    MAX-ACCESS  read-only
    STATUS      current
    DESCRIPTION
        "Indicates the One-way far-end delay maximum value. The value
         is expressed in micro-seconds."
    ::= { acdTwampGenHistResultEntry 39 }

acdTwampGenHistResultOneWayFeDelayAvgValue  OBJECT-TYPE
    SYNTAX      Integer32
    MAX-ACCESS  read-only
    STATUS      current
    DESCRIPTION
        "Indicates the One-way far-end delay average value. The value
         is expressed in micro-seconds."
    ::= { acdTwampGenHistResultEntry 40 }

acdTwampGenHistResultOneWayFeDelayThreshEx  OBJECT-TYPE
    SYNTAX      Unsigned32
    MAX-ACCESS  read-only
    STATUS      current
    DESCRIPTION
        "Indicates the number of samples exceeding the limit."
    ::= { acdTwampGenHistResultEntry 41 }

acdTwampGenHistResultOneWayFeDvValid  OBJECT-TYPE
    SYNTAX      TruthValue
    MAX-ACCESS  read-only
    STATUS      current
    DESCRIPTION
        "Indicate the validity of the One-way far-end instantaneous delay variation measurements."
    ::= { acdTwampGenHistResultEntry 42 }

acdTwampGenHistResultOneWayFeDvInstValue  OBJECT-TYPE
    SYNTAX      Integer32
    MAX-ACCESS  read-only
    STATUS      current
    DESCRIPTION
        "Indicates the One-way far-end delay variation instantaneous value. The value
         is expressed in micro-seconds."
    ::= { acdTwampGenHistResultEntry 43 }

acdTwampGenHistResultOneWayFeDvSamples  OBJECT-TYPE
    SYNTAX      Unsigned32
    MAX-ACCESS  read-only
    STATUS      current
    DESCRIPTION
        "Indicates the number of samples gathered to calculate
         the period One-way far-end delay variation results."
    ::= { acdTwampGenHistResultEntry 44 }

acdTwampGenHistResultOneWayFeDvMinValue  OBJECT-TYPE
    SYNTAX      Integer32
    MAX-ACCESS  read-only
    STATUS      current
    DESCRIPTION
        "Indicates the One-way far-end delay variation minimum value. The value
         is expressed in micro-seconds."
    ::= { acdTwampGenHistResultEntry 45 }

acdTwampGenHistResultOneWayFeDvMaxValue  OBJECT-TYPE
    SYNTAX      Integer32
    MAX-ACCESS  read-only
    STATUS      current
    DESCRIPTION
        "Indicates the One-way far-end delay variation maximum value. The value
         is expressed in micro-seconds."
    ::= { acdTwampGenHistResultEntry 46 }

acdTwampGenHistResultOneWayFeDvAvgValue  OBJECT-TYPE
    SYNTAX      Integer32
    MAX-ACCESS  read-only
    STATUS      current
    DESCRIPTION
        "Indicates the One-way far-end delay variation average value. The value
         is expressed in micro-seconds."
    ::= { acdTwampGenHistResultEntry 47 }

acdTwampGenHistResultOneWayFeDvThreshEx  OBJECT-TYPE
    SYNTAX      Unsigned32
    MAX-ACCESS  read-only
    STATUS      current
    DESCRIPTION
        "Indicates the number of samples exceeding the limit."
    ::= { acdTwampGenHistResultEntry 48 }

acdTwampGenHistResultPktLossSamples  OBJECT-TYPE
    SYNTAX      Unsigned32
    MAX-ACCESS  read-only
    STATUS      current
    DESCRIPTION
        "The number of TWAMP packets that have been sent."
    ::= { acdTwampGenHistResultEntry 49 }

acdTwampGenHistResultPktLossLostPackets  OBJECT-TYPE
    SYNTAX      Unsigned32
    MAX-ACCESS  read-only
    STATUS      current
    DESCRIPTION
        "The number of TWAMP packets that have been lost."
    ::= { acdTwampGenHistResultEntry 50 }

acdTwampGenHistResultPktLossLossRatio  OBJECT-TYPE
    SYNTAX      Unsigned32
    MAX-ACCESS  read-only
    STATUS      current
    DESCRIPTION
        "Packet loss ratio expressed in hundreth of percent (100 is 1%)."
    ::= { acdTwampGenHistResultEntry 51 }

acdTwampGenHistResultPktLossOutOfOrder  OBJECT-TYPE
    SYNTAX      Unsigned32
    MAX-ACCESS  read-only
    STATUS      current
    DESCRIPTION
        "The number of out-of-order TWAMP packets."
    ::= { acdTwampGenHistResultEntry 52 }

acdTwampGenHistResultPktLossDuplicate  OBJECT-TYPE
    SYNTAX      Unsigned32
    MAX-ACCESS  read-only
    STATUS      current
    DESCRIPTION
        "The number of duplicate TWAMP packets."
    ::= { acdTwampGenHistResultEntry 53 }

acdTwampGenHistResultPktLossGaps  OBJECT-TYPE
    SYNTAX      Unsigned32
    MAX-ACCESS  read-only
    STATUS      current
    DESCRIPTION
        "The number of gaps."
    ::= { acdTwampGenHistResultEntry 54 }

acdTwampGenHistResultPktLossLargestGap  OBJECT-TYPE
    SYNTAX      Unsigned32
    MAX-ACCESS  read-only
    STATUS      current
    DESCRIPTION
        "The largest number of consecutive packets that were detected as missing."
    ::= { acdTwampGenHistResultEntry 55 }


---------------------------------------------------------------------------
 -- ACD-TWAMP-GEN-MIB Module - Conformance Information
---------------------------------------------------------------------------

acdTwampGenCompliances  OBJECT IDENTIFIER ::= { acdTwampGenConformance 1 }
acdTwampGenGroups       OBJECT IDENTIFIER ::= { acdTwampGenConformance 2 }

---------------------------------------------------------------------------
 -- Units of conformance
---------------------------------------------------------------------------

acdTwampGenResultGroup OBJECT-GROUP
    OBJECTS {
        acdTwampGenResultInstName,

        acdTwampGenResultPeriodNb,
        acdTwampGenResultPeriodTime,
        acdTwampGenResultCurrTxPacketCount,
        acdTwampGenResultCurrRxPacketCount,

        acdTwampGenResultTwoWayDelayValid,
        acdTwampGenResultTwoWayDelayInstValue,
        acdTwampGenResultTwoWayDelayCurrSamples,
        acdTwampGenResultTwoWayDelayCurrMinValue,
        acdTwampGenResultTwoWayDelayCurrMaxValue,
        acdTwampGenResultTwoWayDelayCurrAvgValue,
        acdTwampGenResultTwoWayDelayCurrThreshEx,

        acdTwampGenResultTwoWayDvValid,
        acdTwampGenResultTwoWayDvInstValue,
        acdTwampGenResultTwoWayDvCurrSamples,
        acdTwampGenResultTwoWayDvCurrMinValue,
        acdTwampGenResultTwoWayDvCurrMaxValue,
        acdTwampGenResultTwoWayDvCurrAvgValue,
        acdTwampGenResultTwoWayDvCurrThreshEx,

        acdTwampGenResultOneWayNeDelayValid,
        acdTwampGenResultOneWayNeDelayInstValue,
        acdTwampGenResultOneWayNeDelayCurrSamples,
        acdTwampGenResultOneWayNeDelayCurrMinValue,
        acdTwampGenResultOneWayNeDelayCurrMaxValue,
        acdTwampGenResultOneWayNeDelayCurrAvgValue,
        acdTwampGenResultOneWayNeDelayCurrThreshEx,

        acdTwampGenResultOneWayNeDvValid,
        acdTwampGenResultOneWayNeDvInstValue,
        acdTwampGenResultOneWayNeDvCurrSamples,
        acdTwampGenResultOneWayNeDvCurrMinValue,
        acdTwampGenResultOneWayNeDvCurrMaxValue,
        acdTwampGenResultOneWayNeDvCurrAvgValue,
        acdTwampGenResultOneWayNeDvCurrThreshEx,

        acdTwampGenResultOneWayFeDelayValid,
        acdTwampGenResultOneWayFeDelayInstValue,
        acdTwampGenResultOneWayFeDelayCurrSamples,
        acdTwampGenResultOneWayFeDelayCurrMinValue,
        acdTwampGenResultOneWayFeDelayCurrMaxValue,
        acdTwampGenResultOneWayFeDelayCurrAvgValue,
        acdTwampGenResultOneWayFeDelayCurrThreshEx,

        acdTwampGenResultOneWayFeDvValid,
        acdTwampGenResultOneWayFeDvInstValue,
        acdTwampGenResultOneWayFeDvCurrSamples,
        acdTwampGenResultOneWayFeDvCurrMinValue,
        acdTwampGenResultOneWayFeDvCurrMaxValue,
        acdTwampGenResultOneWayFeDvCurrAvgValue,
        acdTwampGenResultOneWayFeDvCurrThreshEx,

        acdTwampGenResultPktLossCurrSamples,
        acdTwampGenResultPktLossCurrLostPackets,
        acdTwampGenResultPktLossCurrLossRatio,
        acdTwampGenResultPktLossCurrOutOfOrder,
        acdTwampGenResultPktLossCurrDuplicate,
        acdTwampGenResultPktLossCurrGaps,
        acdTwampGenResultPktLossCurrLargestGap
    }
    STATUS      current
    DESCRIPTION
       "Objects for the TWAMP-Generator result Group."
    ::= { acdTwampGenGroups 1 }

acdTwampGenStatusGroup OBJECT-GROUP
    OBJECTS {
        acdTwampGenStatusInstName,
        acdTwampGenStatusTwoWayDelayAlert,
        acdTwampGenStatusTwoWayAvgDelayAlert,
        acdTwampGenStatusTwoWayDvAlert,
        acdTwampGenStatusTwoWayAvgDvAlert,
        acdTwampGenStatusOneWayNeDelayAlert,
        acdTwampGenStatusOneWayNeAvgDelayAlert,
        acdTwampGenStatusOneWayNeDvAlert,
        acdTwampGenStatusOneWayNeAvgDvAlert,
        acdTwampGenStatusOneWayFeDelayAlert,
        acdTwampGenStatusOneWayFeAvgDelayAlert,
        acdTwampGenStatusOneWayFeDvAlert,
        acdTwampGenStatusOneWayFeAvgDvAlert,
        acdTwampGenStatusPacketLossContinuityCheckAlert,
        acdTwampGenStatusPacketLossExcessivePacketLossAlert
    }
    STATUS      current
    DESCRIPTION
       "Objects for the TWAMP-Generator status Group."
    ::= { acdTwampGenGroups 2 }

acdTwampGenCfgGroup OBJECT-GROUP
    OBJECTS {
        acdTwampGenCfgName,
        acdTwampGenCfgState,
        acdTwampGenCfgInterval,
        acdTwampGenCfgReferencePeriod,
        acdTwampGenCfgPktSize,
        acdTwampGenCfgDestIPv4Addr,
        acdTwampGenCfgSourcePortNumber,
        acdTwampGenCfgDestPortNumber,
        acdTwampGenCfgDscp,
        acdTwampGenCfgEcn,
        acdTwampGenCfgVlan1Priority,
        acdTwampGenCfgTwoWayMaxDelay,
        acdTwampGenCfgTwoWayMaxDelayThrs,
        acdTwampGenCfgTwoWayAvgDelayThrs,
        acdTwampGenCfgTwoWayMaxDv,
        acdTwampGenCfgTwoWayMaxDvThrs,
        acdTwampGenCfgTwoWayAvgDvThrs,
        acdTwampGenCfgOneWayNearEndMaxDelay,
        acdTwampGenCfgOneWayNearEndMaxDelayThrs,
        acdTwampGenCfgOneWayNearEndAvgDelayThrs,
        acdTwampGenCfgOneWayNearEndMaxDv,
        acdTwampGenCfgOneWayNearEndMaxDvThrs,
        acdTwampGenCfgOneWayNearEndAvgDvThrs,
        acdTwampGenCfgOneWayFarEndMaxDelay,
        acdTwampGenCfgOneWayFarEndMaxDelayThrs,
        acdTwampGenCfgOneWayFarEndAvgDelayThrs,
        acdTwampGenCfgOneWayFarEndMaxDv,
        acdTwampGenCfgOneWayFarEndMaxDvThrs,
        acdTwampGenCfgOneWayFarEndAvgDvThrs,
        acdTwampGenCfgPacketLossContinuityCheck,
        acdTwampGenCfgPacketLossRate
    }
    STATUS      current
    DESCRIPTION
       "Objects for the TWAMP-Generator configuration Group."
    ::= { acdTwampGenGroups 3 }

acdTwampGenHistResultGroup OBJECT-GROUP
    OBJECTS {
        acdTwampGenHistResultID,
        acdTwampGenHistResultSampleIndex,
        acdTwampGenHistResultInstName,

        acdTwampGenHistResultPeriodTime,
        acdTwampGenHistResultTxPacketCount,
        acdTwampGenHistResultRxPacketCount,

        acdTwampGenHistResultTwoWayDelayValid,
        acdTwampGenHistResultTwoWayDelayInstValue,
        acdTwampGenHistResultTwoWayDelaySamples,
        acdTwampGenHistResultTwoWayDelayMinValue,
        acdTwampGenHistResultTwoWayDelayMaxValue,
        acdTwampGenHistResultTwoWayDelayAvgValue,
        acdTwampGenHistResultTwoWayDelayThreshEx,

        acdTwampGenHistResultTwoWayDvValid,
        acdTwampGenHistResultTwoWayDvInstValue,
        acdTwampGenHistResultTwoWayDvSamples,
        acdTwampGenHistResultTwoWayDvMinValue,
        acdTwampGenHistResultTwoWayDvMaxValue,
        acdTwampGenHistResultTwoWayDvAvgValue,
        acdTwampGenHistResultTwoWayDvThreshEx,

        acdTwampGenHistResultOneWayNeDelayValid,
        acdTwampGenHistResultOneWayNeDelayInstValue,
        acdTwampGenHistResultOneWayNeDelaySamples,
        acdTwampGenHistResultOneWayNeDelayMinValue,
        acdTwampGenHistResultOneWayNeDelayMaxValue,
        acdTwampGenHistResultOneWayNeDelayAvgValue,
        acdTwampGenHistResultOneWayNeDelayThreshEx,

        acdTwampGenHistResultOneWayNeDvValid,
        acdTwampGenHistResultOneWayNeDvInstValue,
        acdTwampGenHistResultOneWayNeDvSamples,
        acdTwampGenHistResultOneWayNeDvMinValue,
        acdTwampGenHistResultOneWayNeDvMaxValue,
        acdTwampGenHistResultOneWayNeDvAvgValue,
        acdTwampGenHistResultOneWayNeDvThreshEx,

        acdTwampGenHistResultOneWayFeDelayValid,
        acdTwampGenHistResultOneWayFeDelayInstValue,
        acdTwampGenHistResultOneWayFeDelaySamples,
        acdTwampGenHistResultOneWayFeDelayMinValue,
        acdTwampGenHistResultOneWayFeDelayMaxValue,
        acdTwampGenHistResultOneWayFeDelayAvgValue,
        acdTwampGenHistResultOneWayFeDelayThreshEx,

        acdTwampGenHistResultOneWayFeDvValid,
        acdTwampGenHistResultOneWayFeDvInstValue,
        acdTwampGenHistResultOneWayFeDvSamples,
        acdTwampGenHistResultOneWayFeDvMinValue,
        acdTwampGenHistResultOneWayFeDvMaxValue,
        acdTwampGenHistResultOneWayFeDvAvgValue,
        acdTwampGenHistResultOneWayFeDvThreshEx,

        acdTwampGenHistResultPktLossSamples,
        acdTwampGenHistResultPktLossLostPackets,
        acdTwampGenHistResultPktLossLossRatio,
        acdTwampGenHistResultPktLossOutOfOrder,
        acdTwampGenHistResultPktLossDuplicate,
        acdTwampGenHistResultPktLossGaps,
        acdTwampGenHistResultPktLossLargestGap

    }
    STATUS      current
    DESCRIPTION
       "Objects for the TWAMP-Generator history result Group."
    ::= { acdTwampGenGroups 4 }

acdTwampGenCompliance MODULE-COMPLIANCE
    STATUS      current
    DESCRIPTION
       "The compliance statement for support of the ACD-TWAMP-GEN-MIB module."
    MODULE
        MANDATORY-GROUPS {
            acdTwampGenResultGroup,
            acdTwampGenStatusGroup,
            acdTwampGenCfgGroup,
            acdTwampGenHistResultGroup
         }

    ::= { acdTwampGenCompliances 1 }


END
