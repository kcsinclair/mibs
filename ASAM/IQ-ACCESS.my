-- orig IQ_ACCESS_MIB

IQ-ACCESS DEFINITIONS ::= BEGIN

IMPORTS

    OBJECT-TYPE
        FROM RFC-1212

    asam
        FROM SYSTEM-MIB;

asamIqAccessMIB OBJECT IDENTIFIER ::= { asam 14 }

QosType	::= 		INTEGER {   		 
				ubr (1),        
				gfr (2),        
				nrtVbr (6),        
				rtVbr (7),        
				cbr (8)          
			}

IqAccessMode ::=	INTEGER  {
				nil(1),		
				aging(2),
				weighted(3)
			}

IqAccessWeightMode ::=	INTEGER {
				nil(1),		
				administrative(2),
				lineRate(3),
				dynamic(4)
			}

IqAccessDynamicWeight ::= INTEGER {
				nil(1),		
				pcrOnly(2),     
				mcrOnly(3),     
				diffPcrMcr(4)   
			}
				
iqBusAccesTable		OBJECT-TYPE
        SYNTAX          SEQUENCE OF IqBusAccessTableEntry
        ACCESS          not-accessible
        STATUS          mandatory    
        DESCRIPTION     "This table describes the IQ Access Mechanism
			for each supported QoS class. 
			This data is part of system data and requires
			a complete ASAM Restart i.o. to modify them.
			To avoid a system restart whenever a value is changed, the 
			Manager can change the requested... fields
			without any impact on the ASAM. 
			The changed fields will become only valid after an
			explicit ASAM restart command.
			Rows cannot be created/deleted by the Manager."
::= {asamIqAccessMIB 1}

iqBusAccessTableEntry   OBJECT-TYPE
        SYNTAX          IqBusAccessTableEntry
        ACCESS          not-accessible
        STATUS          mandatory
        DESCRIPTION     "An entry in the iqBusAccessTable"
        INDEX           {qosClass}

::= {iqBusAccesTable 1}

IqBusAccessTableEntry ::=
	SEQUENCE {
		qosClass			QosType,	
		actualNgcrSubClassPriority	INTEGER,
		actualNgcrMode			IqAccessMode,
		actualNgcrWeightMode		IqAccessWeightMode,
		actualNgcrDynamicWeight		IqAccessDynamicWeight,
		actualGcrSubClassPriority	INTEGER,
		actualGcrMode			IqAccessMode,
		actualGcrWeightMode		IqAccessWeightMode,
		actualGcrDynamicWeight		IqAccessDynamicWeight,
		requestedNgcrSubClassPriority	INTEGER,
		requestedNgcrMode		IqAccessMode,
		requestedNgcrWeightMode		IqAccessWeightMode,
		requestedNgcrDynamicWeight	IqAccessDynamicWeight,
		requestedGcrSubClassPriority	INTEGER,
		requestedGcrMode		IqAccessMode,
		requestedGcrWeightMode		IqAccessWeightMode,
		requestedGcrDynamicWeight	IqAccessDynamicWeight
	}

qosClass      		OBJECT-TYPE
        SYNTAX          QosType
        ACCESS          read-only
        STATUS          mandatory
        DESCRIPTION     "the QoS class supported by the IQ Access Mechanisnm and
			for which the IQ Access mechanism is described in this 
			table"

::= {iqBusAccessTableEntry 1}

actualNgcrSubClassPriority	OBJECT-TYPE
	SYNTAX		INTEGER(-1..14)
        ACCESS          read-only 
        STATUS          mandatory 
        DESCRIPTION     "the priority class for NGCR part of this QoS
			-1 means this QoS class does not have a NGCR part
			and all other ngcr fields have irrelevant values"

::= {iqBusAccessTableEntry 2}

actualNgcrMode		OBJECT-TYPE
        SYNTAX          IqAccessMode
        ACCESS          read-only  
        STATUS          mandatory  
        DESCRIPTION     "Aging or Weigthed mode for accessing the IQ BUS
			for the NGCR part of this QoS class"

::= {iqBusAccessTableEntry 3} 
 
actualNgcrWeightMode	OBJECT-TYPE 
        SYNTAX          IqAccessWeightMode
        ACCESS          read-only   
        STATUS          mandatory   
        DESCRIPTION     "describes how the weight is calculated
			relevant only if Weighted Mode :
			- weight fixed at subscribtion time (administrative)
			- weight based on ADSL line rate (lineRate)
			- weight based on connection parameters (dynamic)"

::= {iqBusAccessTableEntry 4}
 
actualNgcrDynamicWeight OBJECT-TYPE 
        SYNTAX          IqAccessDynamicWeight
        ACCESS          read-only   
        STATUS          mandatory
        DESCRIPTION     "relevant only if mode = weighted and weightmode =
			dynamic : defines how dynamic weights are computed
			- based on PCR only
			- based on MCR only
			- based on difference between PCR and MCR"

::= {iqBusAccessTableEntry 5}

actualGcrSubClassPriority      OBJECT-TYPE
        SYNTAX          INTEGER(-1..14)
        ACCESS          read-only
        STATUS          mandatory
        DESCRIPTION     "the priority class for GCR part of this QoS
                        -1 means this QoS class does not have a GCR part
			and all other ngcr fields have irrelevant values"

::= {iqBusAccessTableEntry 6}
 
actualGcrMode         	OBJECT-TYPE
        SYNTAX          IqAccessMode
        ACCESS          read-only 
        STATUS          mandatory 
        DESCRIPTION     "Aging or Weigthed mode for accessing the IQ BUS
			for the GCR part of this QoS class"
 
::= {iqBusAccessTableEntry 7}
 
actualGcrWeightMode    	OBJECT-TYPE
        SYNTAX          IqAccessWeightMode
        ACCESS          read-only  
        STATUS          mandatory  
        DESCRIPTION     "describes how the weight is calculated
			relevant only if Weighted Mode :
                        - weight fixed at subscribtion time (administrative)
                        - weight based on ADSL line rate (lineRate)
                        - weight based on connection parameters (dynamic)"
 
::= {iqBusAccessTableEntry 8}
 
actualGcrDynamicWeight OBJECT-TYPE
        SYNTAX          IqAccessDynamicWeight
        ACCESS          read-only  
        STATUS          mandatory
        DESCRIPTION     "relevant only if mode = weighted and weightmode =
                        dynamic, defines how dynamic weights are computed
                        - based on PCR only
                        - based on MCR only
                        - based on difference between PCR and MCR"
 
::= {iqBusAccessTableEntry 9}
 
requestedNgcrSubClassPriority	OBJECT-TYPE
	SYNTAX		INTEGER(-1..14)
        ACCESS          read-write 
        STATUS          mandatory 
        DESCRIPTION     "the priority class for NGCR part of this QoS
			-1 means this QoS class does not have a NGCR part
			and all other ngcr fields have irrelevant values"

::= {iqBusAccessTableEntry 10}

requestedNgcrMode		OBJECT-TYPE
        SYNTAX          IqAccessMode
        ACCESS          read-write  
        STATUS          mandatory  
        DESCRIPTION     "Aging or Weigthed mode for accessing the IQ BUS
			for the NGCR part of this QoS class"

::= {iqBusAccessTableEntry 11} 
 
requestedNgcrWeightMode	OBJECT-TYPE 
        SYNTAX          IqAccessWeightMode
        ACCESS          read-write   
        STATUS          mandatory   
        DESCRIPTION     "describes how the weight is calculated
			relevant only if Weighted Mode :
			- weight fixed at subscribtion time (administrative)
			- weight based on ADSL line rate (lineRate)
			- weight based on connection parameters (dynamic)"

::= {iqBusAccessTableEntry 12}
 
requestedNgcrDynamicWeight OBJECT-TYPE 
        SYNTAX          IqAccessDynamicWeight
        ACCESS          read-write   
        STATUS          mandatory
        DESCRIPTION     "relevant only if mode = weighted and weightmode =
			dynamic : defines how dynamic weights are computed
			- based on PCR only
			- based on MCR only
			- based on difference between PCR and MCR"

::= {iqBusAccessTableEntry 13}
 
requestedGcrSubClassPriority      OBJECT-TYPE
        SYNTAX          INTEGER(-1..14)
        ACCESS          read-write
        STATUS          mandatory
        DESCRIPTION     "the priority class for GCR part of this QoS
                        -1 means this QoS class does not have a GCR part
			and all other ngcr fields have irrelevant values"

::= {iqBusAccessTableEntry 14}
 
requestedGcrMode         	OBJECT-TYPE
        SYNTAX          IqAccessMode
        ACCESS          read-write 
        STATUS          mandatory 
        DESCRIPTION     "Aging or Weigthed mode for accessing the IQ BUS
			for the GCR part of this QoS class"
 
::= {iqBusAccessTableEntry 15}
 
requestedGcrWeightMode    	OBJECT-TYPE
        SYNTAX          IqAccessWeightMode
        ACCESS          read-write  
        STATUS          mandatory  
        DESCRIPTION     "describes how the weight is calculated
			relevant only if Weighted Mode :
                        - weight fixed at subscribtion time (administrative)
                        - weight based on ADSL line rate (lineRate)
                        - weight based on connection parameters (dynamic)"
 
::= {iqBusAccessTableEntry 16}
 
requestedGcrDynamicWeight OBJECT-TYPE
        SYNTAX          IqAccessDynamicWeight
        ACCESS          read-write  
        STATUS          mandatory
        DESCRIPTION     "relevant only if mode = weighted and weightmode =
                        dynamic, defines how dynamic weights are computed
                        - based on PCR only
                        - based on MCR only
                        - based on difference between PCR and MCR"
 
::= {iqBusAccessTableEntry 17}

END
