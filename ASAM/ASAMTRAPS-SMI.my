-- orig asam_traps.smi

ASAMTRAPS-SMI DEFINITIONS ::= BEGIN

IMPORTS
       alcatel
         FROM SYSTEM-MIB
       asamCraftLoginStatus
         FROM ASAM-SYSTEM-MIB
       asamNumOfNTRReferenceChanges
         FROM NTR-MIB
       eqptHwNumberOfChanges,
       eqptProtNumberOfChanges,
       eqptRestartNumberOfChanges
         FROM ASAM-EQUIP-MIB
       asamPhyItfNumberChangeOccurred
         FROM ITF-MIB-EXT
       asamAlarmTrapNumberOfAlarmChanges,
       asamNumberOfIndeterminateChanges,
       asamNumberOfWarningChanges,
       asamNumberOfMinorChanges,
       asamNumberOfMajorChanges,
       asamNumberOfCriticalChanges
         FROM ALARM-MIB
       asamNumberOfSets
         FROM TRANSACTION-MIB

       licenseCounter
         FROM ASAM-SYSTEM-MIB
       ifIndex
         FROM ITF-MIB 
         ipAdEntAddr,
       snmp, egpNeighAddr, DisplayString
         FROM RFC1213-MIB
       ltTrapSessionId,
       ltTrapCmd,
       ltTrapLineId,
       ltTrapStatus,
       ltTrapLineHookStatus
         FROM MEGACO-MIB
       TRAP-TYPE
         FROM RFC-1215
       OBJECT-TYPE
         FROM RFC-1212
       dhcpTrapPreSessionForwarderType, 
       dhcpTrapPreSessionForwarderId,
       dhcpTrapPreSessionIPAddress,
       dhcpTrapPreSessionIfIndex,
       dhcpTrapPreSessionReason
         FROM DHCP-RELAY-MIB 
       eqptPortMappingGlobalChangeCounter
         FROM ASAM-EQUIP-MIB
         radAuthServerAddress
         FROM RADIUS-CLIENT-MIB
       mstBrgAddress,
       mstGenTrapType,
       mstErrTrapType,
       mstMstiBridgeRegionalRoot,
       mstMstiBridgeInstanceIndex,
       mstPortTrapIndex,
       mstForceProtocolVersion,
       mstPortMigrationType,
       mstPktErrType,
       mstPktErrVal,
       mstMstiConfigIdSel,
       mstMstiRegionName,
       mstMstiRegionVersion,
       mstMstiConfigDigest,
       mstInstanceIndex
         FROM MST-MIB
       ;

       alcatelTraps      OBJECT IDENTIFIER ::=  { alcatel 0 }

coldStart            TRAP-TYPE
    ENTERPRISE       snmp
    DESCRIPTION      "A coldStart trap signifies that the sending
                     protocol entity is reinitializing itself such 
                     that the agent's configuration or the protocol
                     entity implementation may be altered."
::= 0

warmStart            TRAP-TYPE
    ENTERPRISE       snmp
    DESCRIPTION      "A warmStart trap signifies that the sending 
                     protocol entity is reinitializing itself such 
                     that neither the agent's configuration nor the 
                     protocol entity implementation may be altered.

    ALCATEL NOTE: the ALCATEL ASAM does NOT support this trap."

::= 1

linkDown             TRAP-TYPE
    ENTERPRISE       snmp
    VARIABLES        { ifIndex }
    DESCRIPTION      "A linkDown trap signifies that the sending
                     protocol entity recognizes a failure in one of
                     the communication links represented in the
                     agent's configuration."

::= 2

linkUp               TRAP-TYPE     
    ENTERPRISE       snmp
    VARIABLES        { ifIndex }
    DESCRIPTION      "A linkUp trap signifies that the sending
                     protocol entity recognizes that one of the
                     communication links represented in the agent's
                     configuration has come up."
::= 3

authenticationFailure TRAP-TYPE
    ENTERPRISE        snmp
    DESCRIPTION       "An authenticationFailure trap signifies that
                    the sending protocol entity is the addressee
                    of a protocol message that is not properly
                    authenticated.  While implementations of the
                    SNMP must be capable of generating this trap,
                    they must also be capable of suppressing the
                    emission of such traps via an implementation-
                    specific mechanism."

::= 4

egpNeighborLoss      TRAP-TYPE
    ENTERPRISE       snmp
    VARIABLES        { egpNeighAddr }
    DESCRIPTION      "An egpNeighborLoss trap signifies that an EGP
                     neighbor for whom the sending protocol entity
                     was an EGP peer has been marked down and the
                     peer relationship no longer obtains.

    ALCATEL NOTE: the ALCATEL ASAM does NOT support this trap."

::= 5

alcatelChangeOccuredTrap OBJECT-TYPE
    SYNTAX     OBJECT IDENTIFIER
    ACCESS     not-accessible
    STATUS     mandatory
    DESCRIPTION
                  "Reference to the Alcatel enterprise specific changeOccured trap"
    ::= { alcatelTraps 7 }

changeOccured       TRAP-TYPE
    ENTERPRISE      alcatel
    VARIABLES       {
                      asamAlarmTrapNumberOfAlarmChanges,
                      asamPhyItfNumberChangeOccurred,
                      eqptHwNumberOfChanges,
                      asamNumberOfSets,
                      asamNumberOfIndeterminateChanges,
                      asamNumberOfWarningChanges,
                      asamNumberOfMinorChanges,
                      asamNumberOfMajorChanges,
                      asamNumberOfCriticalChanges,

                      eqptProtNumberOfChanges,
                      asamCraftLoginStatus,
                      eqptRestartNumberOfChanges,
                      asamNumOfNTRReferenceChanges,
                      eqptPortMappingGlobalChangeCounter
                      
                    }
    DESCRIPTION     "This trap is sent when the value of one of its
                    variables has changed."
::= 7

alcatelLineTestReportTrap OBJECT-TYPE
    SYNTAX     OBJECT IDENTIFIER
    ACCESS     not-accessible
    STATUS     mandatory
    DESCRIPTION 
                  "Reference to the Alcatel enterprise specific lineTestReport trap"
    ::= { alcatelTraps 10 }

lineTestReport      TRAP-TYPE
    ENTERPRISE      alcatel
    VARIABLES       {
                      ltTrapSessionId,
                      ltTrapCmd,
                      ltTrapLineId,
                      ltTrapStatus,
                      ltTrapLineHookStatus
       
                    }
    DESCRIPTION     "This is for notify network manager test status."
       
::= 10

alcatelInitStartedTrap OBJECT-TYPE
    SYNTAX     OBJECT IDENTIFIER
    ACCESS     not-accessible
    STATUS     mandatory
    DESCRIPTION        
                  "Reference to the Alcatel enterprise specific initStarted trap"
    ::= { alcatelTraps 11 }

initStarted         TRAP-TYPE
    ENTERPRISE      alcatel
    DESCRIPTION     "The ASAM sends an initStarted trap during its
                    initialisation phase, as soon as IP connectivity
                    is established "
::= 11

alcatelLicenseKeyChangeOccurredTrap OBJECT-TYPE 
    SYNTAX     OBJECT IDENTIFIER
    ACCESS     not-accessible
    STATUS     mandatory
    DESCRIPTION        
                  "Reference to the Alcatel enterprise specific licenseKeyChangeOccurred trap"
    ::= { alcatelTraps 12 }

licenseKeyChangeOccurred       TRAP-TYPE
    ENTERPRISE      alcatel
    VARIABLES       {
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
                      licenseCounter,
		      licenseCounter,
                      licenseCounter,
                      licenseCounter,
                      licenseCounter
                    }
    DESCRIPTION     "This trap is sent when the value of one of its
                    variables has changed.
                    Note that this trap contains different instances
                    of the same variable. The index of the variable
                    differentiates the instances as follows:
                    1  licenseCounter for ADSL2+
                    2  licenseCounter for READSL2
                    3  licenseCounter for IGMP
                    4  licenseCounter for BVB
                    5  licenseCounter for Annex-M
                    6  licenseCounter for IP Forwarding
                    7  licenseCounter for PPPoX Relay
                    8  licenseCounter for PPPoX Termination
                    9  licenseCounter for 802.1x
                    10 licenseCounter for SELT
                    13 licenseCounter for IPoA-CC and IPoA-RB
                    14 licenseCounter for UPBO-policing
                    15 licenseCounter for XDSL-PerLine-Overrule
                    16 licenseCounter for Impulse Noise Sensor
                    17 licenseCounter for ADSL1/2 PSD Shaping
                    18 licenseCounter for Annex-J
                    19 licenseCounter for SyncE
                    20 licenseCounter for 2.5 Gbps enabled LT
                    21 licenseCounter for NT load sharing + redundancy 
		    22 licenseCounter for SHDSL cross-talk cancellation	
                    23 licenseCounter for SRA on VDSL2
                    24 licenseCounter for ARQ
		    25 licenseCounter for 10 Gbps enabled LT
		    26 licenseCounter for 20 Gbps enabled LT
                    27 licenseCounter for Gxr
                    28 licenseCounter for IPv6 security
                    29 licenseCounter for Lawful Intercept "
::= 12

alcatelTopoChangedTrap OBJECT-TYPE 
    SYNTAX     OBJECT IDENTIFIER
    ACCESS     not-accessible
    STATUS     mandatory
    DESCRIPTION        
                  "Reference to the Alcatel enterprise specific topoChanged trap"
    ::= { alcatelTraps 13 }

topoChanged         TRAP-TYPE
    ENTERPRISE      alcatel
    DESCRIPTION     "When an ISAM is configured as the command or backup-
                    command node in a cluster, as long as the ISAM detected
                    the topology in the cluster is changed, the ISAM will
                    send a topoChanged trap."
::= 13

alcatelSeltStateChangedTrap OBJECT-TYPE 
    SYNTAX     OBJECT IDENTIFIER
    ACCESS     not-accessible
    STATUS     mandatory
    DESCRIPTION        
                  "Reference to the Alcatel enterprise specific seltStateChanged trap"
    ::= { alcatelTraps 14 }

seltStateChanged    TRAP-TYPE     
    ENTERPRISE       alcatel
    VARIABLES        { ifIndex }
    DESCRIPTION      "When a SELT test has finished and the test results are available in the SELT mib" 
::= 14

alcatelDhcpSessionPreemptedTrap OBJECT-TYPE 
    SYNTAX     OBJECT IDENTIFIER
    ACCESS     not-accessible
    STATUS     mandatory
    DESCRIPTION        
                  "Reference to the Alcatel enterprise specific dhcpSessionPreempted trap"
    ::= { alcatelTraps 15 }

dhcpSessionPreempted         TRAP-TYPE
    ENTERPRISE      alcatel
    VARIABLES {
                dhcpTrapPreSessionForwarderType, 
                dhcpTrapPreSessionForwarderId,
                dhcpTrapPreSessionIPAddress,
                dhcpTrapPreSessionIfIndex,
                dhcpTrapPreSessionReason
              }
    DESCRIPTION     "When a dynamic ip address is preempted for
                    ip-aware bridge or enhanced iBridge forwarding mode, 
                    ISAM should generate and send out this trap. 
                    Following is the item description.
                    1.dhcpTrapPreSessionForwarderType, Forwarder type (L2/L3)
                      (1) L2
                      (2) L3
                    2.dhcpTrapPreSessionForwarderId, Forwarder id (VRF-id/VLAN-id)
                    3.dhcpTrapPreSessionIPAddress, Preempted session IP address
                    4.dhcpTrapPreSessionIfIndex, User interface ifIndex
                    5.dhcpTrapPreSessionReason, Reason for preemption, including:
                      (1)conflict with static;
                      (2)conflict with DHCP;
                      (3)no resources available. "
::= 15

alcatelRadiusServerFailureTrap OBJECT-TYPE 
    SYNTAX     OBJECT IDENTIFIER
    ACCESS     not-accessible
    STATUS     mandatory
    DESCRIPTION        
                  "Reference to the Alcatel enterprise specific radiusServerFailure trap"
    ::= { alcatelTraps 16 }

radiusServerFailure  TRAP-TYPE
    ENTERPRISE       alcatel
    VARIABLES        { radAuthServerAddress }
    DESCRIPTION     "When a RADIUS server fails to successfully
                    respond to a request from the ISAM, this trap
                    is sent with the address of the server that failed.
                    RADIUS servers are configured with a dead interval
                    which prevents the use of the same server for that
                    interval, limiting the number of traps sent.
    ALCATEL NOTE:
       SUPPORT:     YES
       PERSIST:     NA
       INSRVMOD:    NA
       RANGE:       NA
       DEFVALUE:    NA
       UNITS:       NA"
::= 16

alcatelLoginOccuredTrap OBJECT-TYPE 
    SYNTAX     OBJECT IDENTIFIER
    ACCESS     not-accessible
    STATUS     mandatory
    DESCRIPTION        
                  "Reference to the Alcatel enterprise specific loginOccured trap"
    ::= { alcatelTraps 17 }

loginOccured TRAP-TYPE
    ENTERPRISE       alcatel
    VARIABLES        { ipAdEntAddr }
    DESCRIPTION     "When a CLI or TL1 user sucessfully logs into
                    ISAM from a remote address, this trap is sent 
                    with the address from which user logs in.
    ALCATEL NOTE:
       SUPPORT:     YES
       PERSIST:     NA
       INSRVMOD:    NA
       RANGE:       NA
       DEFVALUE:    NA
       UNITS:       NA"
::= 17

alcatelLogoutOccuredTrap OBJECT-TYPE 
    SYNTAX     OBJECT IDENTIFIER
    ACCESS     not-accessible
    STATUS     mandatory
    DESCRIPTION        
                  "Reference to the Alcatel enterprise specific logoutOccured trap"
    ::= { alcatelTraps 18 }

logoutOccured TRAP-TYPE
    ENTERPRISE       alcatel
    VARIABLES        { ipAdEntAddr }
    DESCRIPTION     "When a CLI or TL1 user sucessfully logs out 
                    or is logged out from the ISAM, this trap is 
                    sent with the address from which user logs in.
    ALCATEL NOTE:
       SUPPORT:     YES
       PERSIST:     NA
       INSRVMOD:    NA
       RANGE:       NA
       DEFVALUE:    NA
       UNITS:       NA"
::= 18

alcatelasamTrapManagerChangeOccuredTrap OBJECT-TYPE 
    SYNTAX     OBJECT IDENTIFIER
    ACCESS     not-accessible
    STATUS     mandatory
    DESCRIPTION        
                  "Reference to the Alcatel enterprise specific asamTrapManagerChangeOccured trap"
    ::= { alcatelTraps 19 }

asamTrapManagerChangeOccured TRAP-TYPE
    ENTERPRISE       alcatel
    VARIABLES        { ipAdEntAddr }
    DESCRIPTION     "Each time an entry is added or deleted from
                     the asamTrapManagerTable, this trap will be 
                     sent with the address of the manager that 
                     was added or deleted from the table.
    ALCATEL NOTE:
       SUPPORT:     YES
       PERSIST:     NA
       INSRVMOD:    NA
       RANGE:       NA
       DEFVALUE:    NA
       UNITS:       NA"
::= 19

alcatelmstGenTrap OBJECT-TYPE
    SYNTAX     OBJECT IDENTIFIER
    ACCESS     not-accessible
    STATUS     mandatory
    DESCRIPTION
                  "Reference to the Alcatel enterprise specific mstGenTrap trap"
    ::= { alcatelTraps 20 }

mstGenTrap TRAP-TYPE
    ENTERPRISE  alcatel
    VARIABLES   { mstBrgAddress, mstGenTrapType,mstInstanceIndex}
    DESCRIPTION 
        "Generated when any of the general events like protocol up or 
         protocol down, or MSTP instance up or down occurs"
    ::= 20
         
alcatelmstErrTrap OBJECT-TYPE
    SYNTAX     OBJECT IDENTIFIER
    ACCESS     not-accessible
    STATUS     mandatory
    DESCRIPTION
                  "Reference to the Alcatel enterprise specific mstErrTrap trap"
    ::= { alcatelTraps 21 }

mstErrTrap TRAP-TYPE
    ENTERPRISE  alcatel
    VARIABLES   { mstBrgAddress, mstErrTrapType }
    DESCRIPTION 
        "Generated when any of the error events like memory failure or buffer failure
         or protocol migration or new root or topology change occurs "
    ::= 21
         
alcatelmstProtocolMigrationTrap OBJECT-TYPE
    SYNTAX     OBJECT IDENTIFIER
    ACCESS     not-accessible
    STATUS     mandatory
    DESCRIPTION
                  "Reference to the Alcatel enterprise specific mstProtocolMigrationTrap trap"
    ::= { alcatelTraps 22 }

mstProtocolMigrationTrap TRAP-TYPE
    ENTERPRISE  alcatel
    VARIABLES   { mstBrgAddress, mstPortTrapIndex, 
                  mstForceProtocolVersion, mstPortMigrationType }
    DESCRIPTION 
        "Generated when port protocol migration happens in the port "
    ::= 22
         
alcatelmstInvalidBpduRxdTrap OBJECT-TYPE
    SYNTAX     OBJECT IDENTIFIER
    ACCESS     not-accessible
    STATUS     mandatory
    DESCRIPTION
                  "Reference to the Alcatel enterprise specific mstInvalidBpduRxdTrap trap"
    ::= { alcatelTraps 23 }
    
mstInvalidBpduRxdTrap TRAP-TYPE
    ENTERPRISE  alcatel
    VARIABLES   { mstBrgAddress, mstPortTrapIndex, 
                  mstPktErrType, mstPktErrVal }
    DESCRIPTION 
        "Generated when the invalid packet is received for 
         bpdu/stp/rstp/maximum age/forward delay/hello time"
    ::= 23
         
alcatelmstRegionConfigChangeTrap OBJECT-TYPE
    SYNTAX     OBJECT IDENTIFIER
    ACCESS     not-accessible
    STATUS     mandatory
    DESCRIPTION
                  "Reference to the Alcatel enterprise specific mstRegionConfigChangeTrap trap"
    ::= { alcatelTraps 24 }
    
mstRegionConfigChangeTrap TRAP-TYPE
    ENTERPRISE  alcatel
    VARIABLES   { mstBrgAddress, 
                  mstMstiConfigIdSel, mstMstiRegionName, 
                  mstMstiRegionVersion, mstMstiConfigDigest }
    DESCRIPTION 
        "Generated when the MST region's configuration     
         identifier changes."
    ::= 24

alcatelSessionStartedTrap OBJECT-TYPE 
    SYNTAX     OBJECT IDENTIFIER
    ACCESS     not-accessible
    STATUS     mandatory
    DESCRIPTION        
                  "Reference to the Alcatel enterprise specific sessionStarted trap"
    ::= { alcatelTraps 8 }

sessionStarted      TRAP-TYPE
    ENTERPRISE      alcatel

    DESCRIPTION     "When a manager starts a SET session, agent
                    generates this trap to inform all manager that
                    SET actions are allowed for the NMC that has
                    IpAddress in the variable-binding.

    NOTE: the STATUS of the sessionStarted trap is obsolete."

::= 8

alcatelSessionEndedTrap OBJECT-TYPE 
    SYNTAX     OBJECT IDENTIFIER
    ACCESS     not-accessible
    STATUS     mandatory
    DESCRIPTION        
                  "Reference to the Alcatel enterprise specific sessionEnded trap"
    ::= { alcatelTraps 9 }

sessionEnded        TRAP-TYPE
    ENTERPRISE      alcatel
    DESCRIPTION     "When a manager ends a SET session, agent
                    generates this trap to inform that Set Session
                    is free at this moment.

    NOTE: the STATUS of the sessionEnded trap is obsolete."

::= 9

END
