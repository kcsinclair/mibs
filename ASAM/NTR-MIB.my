-- orig NTR_MIB

NTR-MIB DEFINITIONS ::= BEGIN

IMPORTS 
	OBJECT-TYPE	FROM RFC-1212
	Counter, IpAddress	FROM RFC1155-SMI
        asamSystemClockSelect FROM ASAM-SYSTEM-MIB    
        EqptSlotIndex FROM ASAM-EQUIP-MIB;
   SysClkSrcPriorityScheme ::= INTEGER {
         autoselect (1),             
         local (2),                  
         networkLocal (3),           
         externalLocal (4),          
         networkExternalLocal (5),   
         externalNetworkLocal (6)    
      }

  SystemClockSource ::= INTEGER {
         activeExternal (1),  
         activeNetwork (2),   
         activeLocal (3)      
      }

   SysClkSrcQL ::= INTEGER {
         clk-QL-STU  (0), 
         clk-QL-PRS  (1), 
         clk-QL-PRC  (2), 
         clk-QL-INV3 (3), 
         clk-QL-SSU-A-TNC(4), 
                              
         clk-QL-INV5 (5), 
         clk-QL-INV6 (6), 
         clk-QL-ST2  (7), 
         clk-QL-SSU-B(8), 
         clk-QL-INV9 (9), 
         clk-QL-ST3  (10),
         clk-QL-SEC  (11),
         clk-QL-SMC  (12),
         clk-QL-ST3E (13),
         clk-QL-PROV (14),
         clk-QL-DNU-DUS  (15),
         useSystemDefault (16) 
                          
      }
   
   asamClockSelectAdminState OBJECT-TYPE
      SYNTAX INTEGER {
         loopTiming (1),
         bitsClock (2), 
         localClock (3)
      }
      ACCESS read-write
      STATUS obsolete
      DESCRIPTION
         "Specifies the desired reference clock of the system."
   ::= { asamSystemClockSelect 1 }

   asamClockSelectOperState OBJECT-TYPE
      SYNTAX INTEGER {
         loopTiming (1),
         bitsClock (2), 
         localClock (3)
      }
      ACCESS read-only
      STATUS obsolete
      DESCRIPTION
         "Reflects the reference clock chosen by the system."
      ::= { asamSystemClockSelect 2 } 

   asamClockSelectStatus OBJECT-TYPE
      SYNTAX INTEGER (1..30)  
      ACCESS read-only
      STATUS obsolete
      DESCRIPTION
         "This variable indicates the status of the system for what concerns
          its reference clock. It is a bitmap represented as a sum, therefore,
          it can represent multiple failures simultaneously.
          The asamClockSelectNoDefect should be set if and only if no other
          flag is set.
          BITS A is the BITS interface terminated by NT A.
          BITS B is the BITS interface terminated by NT B.
          The various bit positions are:
             1       asamClockSelectNoDefect;
             2       asamClockSelectionBitsALoss;
             4       asamClockSelectionBitsBLoss;
             8       asamClockSelectionLoopTimingALoss;
             16      asamClockSelectionLoopTimingBLoss."
      ::= { asamSystemClockSelect 3 }

   asamConfSysClkSrcPriorityScheme OBJECT-TYPE
      SYNTAX SysClkSrcPriorityScheme
      ACCESS read-write
      STATUS mandatory
      DESCRIPTION
         "This variable specifies the desired priority scheme to be used in the
          selection of the source for the system clock.  A value of <autoselect>
          indicates that the most suitable priority scheme must be used
          depending on whether the equipment is used.

          ALCATEL NOTE: Applicable to NTs supporting the Basic Clock Mgmt
             SUPPORT: YES   INSRVMOD: YES         RANGE: See above
             PERSIST: YES  DEFVALUE: autoselect  UNITS: -"
      ::= { asamSystemClockSelect 4 }

   asamActualSysClkSrcPriorityScheme OBJECT-TYPE
      SYNTAX SysClkSrcPriorityScheme
      ACCESS read-only
      STATUS mandatory
      DESCRIPTION
         "This variable specifies the actual priority scheme that will be used
          in the selection of the source for the system clock.

          If asamConfSysClkSrcPriorityScheme is not equal to <autoselect>,
          asamActualSysClkSrcPriorityScheme will simply be equal to
          asamConfSysClkSrcPriorityScheme, else
          asamActualSysClkSrcPriorityScheme will indicate the autoselected
          priority scheme ( which will be by default <externalNetworkLocal>
          if configured priority scheme is default <autoselect>).
          ALCATEL NOTE: Applicable to NTs supporting the Basic Clock Mgmt
             SUPPORT: YES   INSRVMOD: NA   RANGE: See above
             PERSIST: NO    DEFVALUE: NA   UNITS: -"
      ::= { asamSystemClockSelect 5 }

   asamSysClkSrcStatus OBJECT-TYPE
      SYNTAX INTEGER (1..4294967295)
      ACCESS read-only
      STATUS mandatory
      DESCRIPTION
         "This variable indicates the status of the system for what concerns the
          sources for the system clock.  It is a bitmap so that it can represent
          multiple failures simultaneously.
          Bitmap:
          Bit 0: bit 0 is set if and only if none of the other bits is set.
          Bit 1: external clock failure on NT A.
          Bit 2: external clock failure on NT B.
          Bit 3: network clock failure on NT-A.
          Bit 4: network clock failure on NT-B.
          Bit 5: local clock failure on NT-A.
          Bit 6: local clock failure on NT-B.
	  Bit 7..31: reserved for future extensions.

          ALCATEL NOTE: Applicable to NTs supporting the Basic Clock Mgmt
             SUPPORT: YES   INSRVMOD: NA   RANGE: 1..4294967295
             PERSIST: NO    DEFVALUE: NA   UNITS: -"
      ::= { asamSystemClockSelect 6 }

   asamSysClkSrcSelection OBJECT-TYPE
      SYNTAX SystemClockSource
      ACCESS read-only
      STATUS mandatory
      DESCRIPTION
         "This variable indicates the clock chosen by the system as the source
          for the system clock.

          ALCATEL NOTE: Applicable to NTs supporting the Basic Clock Mgmt
             SUPPORT: YES   INSRVMOD: NA   RANGE: See above
             PERSIST: NO    DEFVALUE: NA   UNITS: -"
      ::= { asamSystemClockSelect 7 }

   asamSysClkBITSMode OBJECT-TYPE
      SYNTAX INTEGER {
         ds1 (1),
         e1 (2),
         khz2048 (3),
         autoselect (4)
      }
      ACCESS read-write
      STATUS mandatory
      DESCRIPTION
         "Specifies the type of the BITS interface as 
          ds1 (ANSI),
          e1 (ETSI),
          khz2048 (ETSI),
          autoselect (DEFAULT VALUE).

          ALCATEL NOTE: Applicable to NTs supporting either clock mgmt
             SUPPORT: YES   INSRVMOD: NA          RANGE: 1..4     
             PERSIST: YES   DEFVALUE: autoselect  UNITS: NA"
      ::= { asamSystemClockSelect 11 }

   asamActualSysClkBITSMode OBJECT-TYPE
      SYNTAX INTEGER {
         ds1 (1),
         e1 (2),
         khz2048 (3)
      }
      ACCESS read-only
      STATUS mandatory
      DESCRIPTION
         "This variable specifies the actual external source.
          If asamSysClkBITSMode is not equal to <autoselect>,
          asamActualSysClkBITSMode will be equal to AsamSysClkBITSMode, else
          asamActualSysClkBITSMode will indicate the autoselected
          external source (which will be by default ds1 for T1/
          e1 for E1 based on the NT RIP info for board capability 
         for clock device type).
          
          ALCATEL NOTE: Applicable to NTs supporting either clock mgmt
             SUPPORT: YES   INSRVMOD: NA   RANGE: See above
             PERSIST: NO    DEFVALUE: NA   UNITS: -"
      ::= { asamSystemClockSelect 13 }

   asamSysClkSwitchingMode OBJECT-TYPE
      SYNTAX INTEGER {
         revertive (1),
         non-revertive (2)
      }
      ACCESS read-write
      STATUS mandatory
      DESCRIPTION
         "This variable specifies the switching mode. In revertive mode, the 
          system automatically switches from a selected alternate source when a 
          failed higher priority source has been restored. In non-revertive mode,
          the system only switches when the selected clock source fails.
          
          ALCATEL NOTE: Applicable to NTs supporting the Enhanced clock mgmt
             SUPPORT: YES   INSRVMOD: YES         RANGE: 1..2
             PERSIST: YES   DEFVALUE: revertive   UNITS: NA"
      ::= { asamSystemClockSelect 14 }

   asamSysClkForceReference OBJECT-TYPE
      SYNTAX INTEGER {
         none   (1),  
         local  (2)   
                      
      }
      ACCESS read-write
      STATUS mandatory
      DESCRIPTION
         "This variable specifies which clock to manually select. 
          The default is <none> and corresponds to automatic clock selection.
          The manual selection <local> corresponds to the local clock 
          which is in holdover or free run after a system reset.
          
          ALCATEL NOTE: Applicable to NTs supporting the Enhanced clock mgmt
             SUPPORT: YES   INSRVMOD: YES         RANGE: 1..2
             PERSIST: YES   DEFVALUE: none (1)    UNITS: NA"
      ::= { asamSystemClockSelect 15 }

   asamSysClkPriorityTable OBJECT-TYPE
      SYNTAX SEQUENCE OF AsamSysClkPriorityEntry
      ACCESS not-accessible
      STATUS mandatory
      DESCRIPTION     
         "This table contains the prioritised list of configured clock source
          for automatic selection. The first table entry corresponds to the
         first priority, the second entry, to the next priority clock source,
         etc.
         All entries are factory defaulted to <none>, except for the last entry 
         which is defaulted to <local>, and this last entry cannot be modified.
         ALCATEL NOTE: Applicable to NTs supporting the Enhanced clock mgmt
            TABLESIZE: 3 "
     ::=  { asamSystemClockSelect 16 }

   asamSysClkPriorityEntry OBJECT-TYPE
      SYNTAX AsamSysClkPriorityEntry
      ACCESS not-accessible
      STATUS mandatory
      DESCRIPTION
         "An entry in the AsamSysClkPriorityTable."
      INDEX { asamSysClkPriorityIndex }

     ::= { asamSysClkPriorityTable 1}

   AsamSysClkPriorityEntry ::=
      SEQUENCE {
               asamSysClkPriorityIndex          INTEGER,
               asamSysClkPriorityReference      INTEGER
               }

   asamSysClkPriorityIndex          OBJECT-TYPE
      SYNTAX INTEGER (1..3)
      ACCESS not-accessible
      STATUS mandatory
      DESCRIPTION     
        " This object is used by the asamSysClkPriorityTable to identify 
          the priority of the clock source; the first index corresponds 
          to the highest priority. The last index  corresponds to the 
          preset entry for the clock <local> and cannot be changed as
          the clock assigned the lowest priority.

      ALCATEL NOTE: Applicable to NTs supporting the Enhanced clock mgmt
             SUPPORT: YES    INSRVMOD: YES          RANGE: 1..3
             PERSIST: YES    DEFVALUE: NA           UNITS: NA"

      ::= { asamSysClkPriorityEntry 1}

   asamSysClkPriorityReference          OBJECT-TYPE
      SYNTAX INTEGER {
         none       (1), 
         local      (2), 
         bits-a     (3), 
         bits-b     (4), 
         synce-1    (5), 
         synce-2    (6), 
         ieee1588   (7)  
      }
      ACCESS read-write
      STATUS mandatory
      DESCRIPTION
        " This object is used by the asamSysClkPriorityTable to assign 
          the clock source to the corresponding priority for the automatic
          selection of the clock reference. 
          The entries <synce-1> and <synce-2> correspond to the configured SyncE
          ports in the asamSysClkSynceTable.

      ALCATEL NOTE: Applicable to NTs supporting the Enhanced clock mgmt
             SUPPORT: YES    INSRVMOD: YES          RANGE: 1..7
             PERSIST: YES    DEFVALUE: none (1)     UNITS: NA"

      ::= { asamSysClkPriorityEntry 2}

   asamSysClkStatusTable OBJECT-TYPE
      SYNTAX SEQUENCE OF AsamSysClkStatusEntry
      ACCESS not-accessible
      STATUS mandatory
      DESCRIPTION     
         "This table contains the operational status of the configured clocks.
         ALCATEL NOTE: Applicable to NTs supporting the Enhanced clock mgmt
            TABLESIZE: 3 "
     ::=  { asamSystemClockSelect 17 }

   asamSysClkStatusEntry OBJECT-TYPE
      SYNTAX AsamSysClkStatusEntry
      ACCESS not-accessible
      STATUS mandatory
      DESCRIPTION
         "An entry in the AsamSysClkStatusTable."
      INDEX { asamSysClkPriorityIndex }

     ::= { asamSysClkStatusTable 1}

   AsamSysClkStatusEntry ::=
      SEQUENCE {
               asamSysClkStatusQL          SysClkSrcQL,
               asamSysClkStatusActual      INTEGER
               }

   asamSysClkStatusQL          OBJECT-TYPE
      SYNTAX SysClkSrcQL 
      ACCESS read-only
      STATUS mandatory
      DESCRIPTION     
        " This object corresponds to the Quality Level (QL) of the
          configured clock source as identified in the Sync Status
          Message (SSM) or the assigned default value if SSM is disabled. 

      ALCATEL NOTE: Applicable to NTs supporting the Enhanced clock mgmt
             SUPPORT: YES    INSRVMOD: NA           RANGE: 0..15
             PERSIST: NO     DEFVALUE: NA           UNITS: NA"
      ::= { asamSysClkStatusEntry 1}

   asamSysClkStatusActual          OBJECT-TYPE
      SYNTAX INTEGER {
         reference  (1),       
         valid      (2),       
         failed     (3),       
                               
         doNotUse   (4),       
         unknown    (5),       
         forced     (6),       
         noSynceConfig (7),    
         noSynceSupport (8),   
                               
         onNonReadyPeerNt(9),  
                               
         synceNotAvailable(10),
                               
         noIeee1588Config(11), 
         missing(12),          
         invalid(13)           
      }
      ACCESS read-only
      STATUS mandatory
      DESCRIPTION
        " This object corresponds to the operational status of the 
          configured clock source.

      ALCATEL NOTE: Applicable to NTs supporting the Enhanced clock mgmt
             SUPPORT: YES    INSRVMOD: NA           RANGE: 1..13
             PERSIST: NO     DEFVALUE: 5            UNITS: NA"
      ::= { asamSysClkStatusEntry 2}

   asamSysClkSynceTable OBJECT-TYPE
      SYNTAX SEQUENCE OF AsamSysClkSynceEntry
      ACCESS not-accessible
      STATUS mandatory
      DESCRIPTION     
         "This table contains the configuration of the binding of the
          SyncE port from which to enable clock sync recovery.
         ALCATEL NOTE: Applicable to NTs supporting the Enhanced clock mgmt
            TABLESIZE: 2 "
     ::=  { asamSystemClockSelect 18 }

   asamSysClkSynceEntry OBJECT-TYPE
      SYNTAX AsamSysClkSynceEntry
      ACCESS not-accessible
      STATUS mandatory
      DESCRIPTION
         "An entry in the AsamSysClkSynceTable."
      INDEX { asamSysClkSynceIndex }

     ::= { asamSysClkSynceTable 1}

   AsamSysClkSynceEntry ::=
      SEQUENCE {
               asamSysClkSynceIndex          INTEGER,
               asamSysClkSynceLogicalSlot    EqptSlotIndex,
               asamSysClkSyncePortType       INTEGER,
               asamSysClkSyncePortNumber     INTEGER
               }

   asamSysClkSynceIndex          OBJECT-TYPE
      SYNTAX INTEGER (1..2)
      ACCESS not-accessible
      STATUS mandatory
      DESCRIPTION     
        " This object corresponds to the reference number of the port 
          supporting the SyncE clock. The first index corresponds to 
          synce-1 and the second index to synce-2 - to be configured in 
          asamSysClkPriorityTable and monitored in asamSysClkStatusTable.

      ALCATEL NOTE:
             SUPPORT: YES    INSRVMOD: NA           RANGE: 1..2
             PERSIST: YES    DEFVALUE: NA           UNITS: NA"
      ::= { asamSysClkSynceEntry 1}

   asamSysClkSynceLogicalSlot          OBJECT-TYPE
      SYNTAX EqptSlotIndex
      ACCESS read-write
      STATUS mandatory
      DESCRIPTION
        " This object corresponds to the logical slot ID of the equipment 
          (as defined in the Equipment MIB) which hold the SyncE port.
          The value <65535> indicates that no selection is made for this entry.

      ALCATEL NOTE: Applicable to NTs supporting the Enhanced clock mgmt
             SUPPORT: YES    INSRVMOD: YES          RANGE: see above
             PERSIST: YES    DEFVALUE: 65535        UNITS: NA"

      ::= { asamSysClkSynceEntry 2}

   asamSysClkSyncePortType          OBJECT-TYPE
      SYNTAX INTEGER {
         none (1),        
         sfp  (2),        
         xfp  (3)         
                     }
      ACCESS read-write
      STATUS mandatory
      DESCRIPTION
        " This object corresponds to the port type of the SyncE port to 
          configure. 
          The value <none:(1)> indicates that no selection is made for this 
          entry.

      ALCATEL NOTE: Applicable to NTs supporting the Enhanced clock mgmt
             SUPPORT: YES    INSRVMOD: YES          RANGE: 1..3
             PERSIST: YES    DEFVALUE: none(1)      UNITS: NA"

      ::= { asamSysClkSynceEntry 3}

   asamSysClkSyncePortNumber          OBJECT-TYPE
      SYNTAX INTEGER (0..511)
      ACCESS read-write
      STATUS mandatory
      DESCRIPTION
        " This object corresponds to the faceplate port number of the 
          SyncE port to configure. The number of the faceplate port of the 
          board combined with the port type and slot ID uniquely identify the port.
          The value <511> indicates that no selection is made for this entry.

      ALCATEL NOTE: Applicable to NTs supporting the Enhanced clock mgmt
             SUPPORT: YES    INSRVMOD: YES          RANGE: 0..511
             PERSIST: YES    DEFVALUE: 511          UNITS: NA"

      ::= { asamSysClkSynceEntry 4}

   asamSysClkSSMTable OBJECT-TYPE
      SYNTAX SEQUENCE OF AsamSysClkSSMEntry
      ACCESS not-accessible
      STATUS mandatory
      DESCRIPTION     
         "This table contains the SSM configuration for the clock sources.
         ALCATEL NOTE: Applicable to NTs supporting the Enhanced clock mgmt
            TABLESIZE: 4 "
     ::=  { asamSystemClockSelect 19 }

   asamSysClkSSMEntry OBJECT-TYPE
      SYNTAX AsamSysClkSSMEntry
      ACCESS not-accessible
      STATUS mandatory
      DESCRIPTION
         "An entry in the AsamSysClkSSMTable."
      INDEX { asamSysClkSSMIndex }

     ::= { asamSysClkSSMTable 1}

   AsamSysClkSSMEntry ::=
      SEQUENCE {
               asamSysClkSSMIndex         INTEGER,
               asamSysClkSSMConfig        INTEGER,
               asamSysClkDefaultQL        SysClkSrcQL,
               asamSysClkTargetQL         SysClkSrcQL
               }

   asamSysClkSSMIndex          OBJECT-TYPE
      SYNTAX INTEGER {
         bits-a     (1), 
         bits-b     (2), 
         synce-1    (3), 
         synce-2    (4), 
         ieee1588   (5)  
      }
      ACCESS not-accessible
      STATUS mandatory
      DESCRIPTION     
        " This object corresponds to the index in the SSM table for each
          supported clock source.

      ALCATEL NOTE: Applicable to NTs supporting the Enhanced clock mgmt
             SUPPORT: YES    INSRVMOD: NO           RANGE: 1..5
             PERSIST: YES    DEFVALUE: DEP          UNITS: NA"

      ::= { asamSysClkSSMEntry 1}

   asamSysClkSSMConfig          OBJECT-TYPE
      SYNTAX INTEGER {
         enable  (1),
         disable (2)
      }
      ACCESS read-write
      STATUS mandatory
      DESCRIPTION
        " This object corresponds to the configuration of the reception 
          of the Sync Status Message (SSM) for the selected source. 
          NOTE: The value selected is not changed when the SyncE 
          sources synce-1 or synce-2 are changed in the asamSysClkSynceTable.
          The value cannot be changed for the BITS and IEEE1588 clock sources
          (bits-a, bits-b and ieee1588).

      ALCATEL NOTE: Applicable to NTs supporting the Enhanced clock mgmt
             SUPPORT: YES    INSRVMOD: YES          RANGE: 1..2
             PERSIST: YES    DEFVALUE: disable      UNITS: NA"

      ::= { asamSysClkSSMEntry 2}

   asamSysClkDefaultQL             OBJECT-TYPE
      SYNTAX SysClkSrcQL
      ACCESS read-write
      STATUS mandatory
      DESCRIPTION
        " This object corresponds to the configuration of the default 
          value that the system assigns to the clock source when SSM is 
          disabled for SyncE, BITS or IEEE1588. 
          The system initially sets the default QL value based on 
          the configuration of asamSysClkBITSMode.
          For BITS/SyncE/IEEE1588 clock:
           SDH Option     BITS Mode    SSM default       QL
               I             E1             2         QL-PRC
               I           2048KHZ          2         QL-PRC
               II            DS1            0         QL-STU
          For local clock:
           SDH Option     BITS Mode    SSM default       QL
               I             E1            11         QL-SEC
               I           2048KHZ         11         QL-SEC
               II            DS1           10         QL-ST3
          The default QL value can not be configured for the Local clock.
          Changing this value may result in clock reselection. 

          The range is 0..15 because the value useSystemDefault is
          only used internally.

      ALCATEL NOTE: Applicable to NTs supporting the Enhanced clock mgmt
             SUPPORT: YES    INSRVMOD: YES          RANGE: 0..15
             PERSIST: YES    DEFVALUE: see descr    UNITS: NA"

      ::= { asamSysClkSSMEntry 3}

   asamSysClkTargetQL              OBJECT-TYPE
      SYNTAX SysClkSrcQL
      ACCESS read-write
      STATUS mandatory
      DESCRIPTION
        " This object corresponds to the configuration of the target 
          threshold that the system compares to the QL of the clock source 
          (from QL of SSM frames) when SSM is enabled. 
          If the SSM-QL if of better or equal quality compared to the target
          value, the port is eligible to be selected as the clock 
          input port.  This selection mechanism however involves many more 
          criteria.  When the SSM-QL quality becomes worse than the 
          target value, switchover to another port happens, if possible.          
          Changing this value may result in clock reselection. 

          The range is 0..15 because the value useSystemDefault is
          only used internally.

      ALCATEL NOTE: Applicable to NTs supporting the Enhanced clock mgmt
             SUPPORT: YES    INSRVMOD: YES          RANGE: 0..15
             PERSIST: YES    DEFVALUE: DNU (15)     UNITS: NA"

      ::= { asamSysClkSSMEntry 4}

   asamSysClkOutputQLThreshold OBJECT-TYPE
      SYNTAX SysClkSrcQL 
      ACCESS read-write
      STATUS mandatory
      DESCRIPTION
         "This variable corresponds to the configuration of the ISAM NTR 
          output threshold. If the system QL - the QL of the current 
          reference clock - becomes worse than this configured value, 
          the T4 output (only BITS supported) is shut down.

          The range is 0..15 because the value useSystemDefault is
          only used internally.
         
          ALCATEL NOTE: Applicable to NTs supporting the Enhanced clock mgmt
             SUPPORT: YES   INSRVMOD: YES         RANGE: 0..15
             PERSIST: YES   DEFVALUE: DNU (15)    UNITS: NA"
      ::= { asamSystemClockSelect 20 }

    asamSysClkNTRSwitchWaitTime OBJECT-TYPE
      SYNTAX INTEGER (0..720) 
      ACCESS read-write
      STATUS mandatory
      DESCRIPTION 
         "This variable corresponds to the configuration of the value of the                                  
          wait-to-restore timer in seconds.  When the QL of the clock becomes 
          sufficient to make the clock eligible (nominated) for clock selection
          after the QL was insufficient, the timer is started.  
          In order for the clock to become a reference clock, it has to stay 
          eligible for as long as the timer runs.
          It is used to prevent continuous switchovers in case of unstable clock  
          sources.  Value 0 means the switch wait timer mechanism is disabled.
          
          ALCATEL NOTE: Applicable to NTs supporting the Enhanced clock mgmt
             SUPPORT: YES   INSRVMOD: YES         RANGE: 0..720
             PERSIST: YES   DEFVALUE: 10          UNITS: NA"
      ::= { asamSystemClockSelect 21 }

   asamNumOfNTRReferenceChanges OBJECT-TYPE
      SYNTAX Counter
      ACCESS read-only
      STATUS mandatory
      DESCRIPTION
         "This variable specifies the number of times a NTR switchover
          occurred since start up.
          
          ALCATEL NOTE: Applicable to NTs supporting the Enhanced clock mgmt
             SUPPORT: YES   INSRVMOD: NA   RANGE: See above
             PERSIST: NO    DEFVALUE: 0    UNITS: -"
      ::= { asamSystemClockSelect 22 }

  NtrPtpPacketMode ::= INTEGER
  {
         multicast (1),   
         unicast (2),
         unicast-multicast (3)
  }

  ntrPtpPacketMode OBJECT-TYPE
      SYNTAX NtrPtpPacketMode
      ACCESS read-write
      STATUS mandatory
      DESCRIPTION
             "This parameter determines the PTP Packet Processing Mode.
              It is intended to be managed by the System Operator.
              ALCATEL NOTE: Applicable to NTs supporting the Enhanced clock mgnt
             SUPPORT: YES   INSRVMOD: YES         RANGE: 2..3
             PERSIST: YES   DEFVALUE: 3           UNITS: NA"
             
      DEFVAL { 3 }
      ::= { asamSystemClockSelect 23 }

  ntrTransmissionProtocolTable OBJECT-TYPE
      SYNTAX SEQUENCE OF NtrTransmissionProtocolEntry
      ACCESS not-accessible
      STATUS mandatory
      DESCRIPTION
         "This table contains the transmission protocol configuration for the
         IEEE1588 clock sources.
         ALCATEL NOTE: Applicable to NTs supporting the Enhanced clock mgnt
           TABLESIZE: 2 "
      ::= { asamSystemClockSelect 24 }

  ntrTransmissionProtocolEntry OBJECT-TYPE
      SYNTAX NtrTransmissionProtocolEntry
      ACCESS not-accessible
      STATUS mandatory
      DESCRIPTION
         "An entry in the ntrTransmissionProtocolTable."
      INDEX { ntrTransmissionProtocolIndex }

      ::= { ntrTransmissionProtocolTable 1 }

  NtrTransmissionProtocolEntry ::=
      SEQUENCE {
               ntrTransmissionProtocolIndex    INTEGER,
               ntrTransmissionProtocolAddress  IpAddress,
               ntrTransmissionProtocolMask     IpAddress,
               ntrTransmissionProtocolGateway  IpAddress
      }

   ntrTransmissionProtocolIndex OBJECT-TYPE
      SYNTAX INTEGER {
          ieee1588-a (1), 
          ieee1588-b (2)  
      }
      ACCESS not-accessible
      STATUS mandatory
      DESCRIPTION
        " This object corresponds to the index in the transmission 
          protocol table for both the IEEE 1588 sources 
      
          ALCATEL NOTE: Applicable to NTs supporting the Enhanced clock mgnt
             SUPPORT: YES     INSRVMOD: NO          RANGE: 1..2  
             PERSIST: YES     DEFVALUE: DEP         UNITS: NA "
      ::= { ntrTransmissionProtocolEntry 1 }

    ntrTransmissionProtocolAddress OBJECT-TYPE
        SYNTAX IpAddress
        ACCESS read-write
        STATUS mandatory
        DESCRIPTION
               "This parameter determines the IP Address of the clock extraction
                function.
                It is intended to be managed by the System Operator.  A value of 0 
                Indicates a non-valid value.
          
                ALCATEL NOTE: Applicable to NTs supporting the Enhanced clock mgnt
                 SUPPORT: YES     INSRVMOD: YES         RANGE: NA  
                 PERSIST: YES     DEFVALUE: 0           UNITS: NA "
        DEFVAL { '00000000'H }
      ::= { ntrTransmissionProtocolEntry 2 }

    ntrTransmissionProtocolMask OBJECT-TYPE
        SYNTAX IpAddress
        ACCESS read-write
        STATUS mandatory
        DESCRIPTION
               "This parameter determines the subnet mask for the clock extraction
                function.
                It is intended to be managed by the System Operator.  A value of 0
                indicates a non-valid value. 

ALCATEL NOTE: Applicable to NTs supporting the Enhanced clock mgnt
                 SUPPORT: YES     INSRVMOD: YES         RANGE: NA  
                 PERSIST: YES     DEFVALUE: 0           UNITS: NA "
        DEFVAL { '00000000'H }
        ::= { ntrTransmissionProtocolEntry 3 }

    ntrTransmissionProtocolGateway OBJECT-TYPE
        SYNTAX IpAddress
        ACCESS read-write
        STATUS mandatory
        DESCRIPTION
               "This parameter determines the default gateway clock extraction
                function.
                It is intended to be managed by the System Operator.  A value of 0  
                indicates a non-valid value. 
                ALCATEL NOTE: Applicable to NTs supporting the Enhanced clock mgnt
                   SUPPORT: YES     INSRVMOD: YES         RANGE: NA  
                   PERSIST: YES     DEFVALUE: 0           UNITS: NA "
        DEFVAL { '00000000'H }
        ::= { ntrTransmissionProtocolEntry 4 }

  ntrAcceptableMasterTable OBJECT-TYPE
      SYNTAX SEQUENCE OF NtrAcceptableMasterEntry
      ACCESS not-accessible
      STATUS mandatory
      DESCRIPTION
           "This object is a table that identifies the clock masters that are
            acceptable.  At least one acceptable master must be provisioned for 
            operation of the feature.
            It is intended to be managed by the System Operator.
            ALCATEL NOTE: Applicable to NTs supporting the Enhanced clock mgnt
              TABLESIZE: 3  "
      ::= { asamSystemClockSelect 25 }

  ntrAcceptableMasterEntry OBJECT-TYPE
      SYNTAX NtrAcceptableMasterEntry
      ACCESS not-accessible
      STATUS mandatory
      DESCRIPTION
           "Rows of this table identify the clock masters that are acceptable"
      INDEX { ntrAcceptableMasterIndex }
      ::= { ntrAcceptableMasterTable 1 }

  NtrAcceptableMasterEntry ::=
      SEQUENCE {
             ntrAcceptableMasterIndex           INTEGER,
             ntrAcceptableMasterAddress		IpAddress,
             ntrAcceptableMasterPriority1	INTEGER,
             ntrAcceptableMasterPriority2	INTEGER
  }

  ntrAcceptableMasterIndex OBJECT-TYPE
      SYNTAX INTEGER (1..3)
      ACCESS not-accessible
      STATUS mandatory
      DESCRIPTION
       "Identifies the instance of an acceptable clock master
          ALCATEL NOTE: Applicable to NTs supporting the Enhanced clock mgnt
             SUPPORT: YES     INSRVMOD: NO          RANGE: 1..3  
             PERSIST: YES     DEFVALUE: DEP         UNITS: NA "
      ::= { ntrAcceptableMasterEntry 1 }

  ntrAcceptableMasterAddress OBJECT-TYPE
      SYNTAX IpAddress
      ACCESS read-write
      STATUS mandatory
      DESCRIPTION
             "The IP address of the Acceptable Master.  A value if 0 indicates a
              non-valid value. 
              
              ALCATEL NOTE: Applicable to NTs supporting the Enhanced clock mgnt
                SUPPORT: YES   INSRVMOD: YES         RANGE: NA
                PERSIST: YES   DEFVALUE: 0           UNITS: NA "
      DEFVAL { '00000000'H }
      ::= { ntrAcceptableMasterEntry 2 }

  ntrAcceptableMasterPriority1 OBJECT-TYPE
      SYNTAX INTEGER (0..255)
      ACCESS read-write
      STATUS mandatory
      DESCRIPTION
             "The Priority of the Acceptable Master.
        Low values of priority1 will be selected as current master in preference
        to higher values.

        A designation that the IEEE 1588 clock belongs to an ordered set of
        clocks from which a master is selected.

        ALCATEL NOTE: Applicable to NTs supporting the Enhanced clock mgnt
         SUPPORT: YES   INSRVMOD: YES         RANGE: 0..255
         PERSIST: YES   DEFVALUE: 128         UNITS: NA "
      DEFVAL { 128 }
      ::= { ntrAcceptableMasterEntry 3 }

  ntrAcceptableMasterPriority2 OBJECT-TYPE
      SYNTAX INTEGER (0..255)
      ACCESS read-write
      STATUS mandatory
      DESCRIPTION
             "A designation that provides finer grained ordering among otherwise
              equivalent IEEE 1588 clocks.

      ALCATEL NOTE: Applicable to NTs supporting the Enhanced clock mgnt
       SUPPORT: YES   INSRVMOD: YES         RANGE: 0..255
       PERSIST: YES   DEFVALUE: 128         UNITS: NA "
      DEFVAL { 128 }
      ::= { ntrAcceptableMasterEntry 4 }

 ntrPtpDomain OBJECT-TYPE
      SYNTAX INTEGER (0..255)
      ACCESS read-write
      STATUS mandatory
      DESCRIPTION
             "The PTP domain. Value (decimal) definition:
        0	Default domain
        1	Alternate domain 1
        2	Alternate domain 2
        3	Alternate domain 3
        4-127	User-defined domains
        128-255	Reserved

        Definition from the standard:

        A logical grouping of PTP clocks that synchronize to each other using the 
        PTP protocol but that are not necessarily synchronized to PTP clocks in
        another PTP subdomain.  NOTE: It should be emphasized that this grouping is
        logical. Clocks sharing a PTP communication path may or may not be in the 
        same PTP subdomain, and clocks in the same PTP subdomain may or may not 
        share a PTP communication path.
        It is intended to be managed by the System Operator.
             ALCATEL NOTE: Applicable to NTs supporting the Enhanced clock mgnt
               SUPPORT: YES   INSRVMOD: YES      RANGE: 0..255
               PERSIST: YES   DEFVALUE: 0        UNITS: NA "
      DEFVAL { 0 }
      ::= { asamSystemClockSelect 26 }	

  NtrPtpMode ::= INTEGER
                  {
      portFaulty(1), 
   
      portDisabled(2), 

      portListening(3), 

      portPreMaster(4), 

      portMaster(5), 

      portPassive(6), 

      portUncalibrated(7), 
      portSlave(8) 

      }

  ntrPtpMode OBJECT-TYPE
      SYNTAX NtrPtpMode
      ACCESS read-only
      STATUS mandatory
      DESCRIPTION
             "This parameter represents the operational mode of the NE's PTP 
              functionality.
        It is intended to be only read by the System Operator.

ALCATEL NOTE: Applicable to NTs supporting the Enhanced clock mgnt
               SUPPORT: YES   INSRVMOD: YES      RANGE: 1..8
               PERSIST: NO    DEFVALUE: 0        UNITS: NA "
       
      ::= { asamSystemClockSelect 27 }

END
