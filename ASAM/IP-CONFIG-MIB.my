IP-CONFIG-MIB DEFINITIONS ::= BEGIN

IMPORTS
        IpAddress, Counter, Gauge, TimeTicks
            FROM RFC1155-SMI
        PhysAddress, DisplayString
            FROM RFC1213-MIB
        IANAifType
            FROM IANAifType-MIB
        InterfaceIndex
            FROM ITF-MIB
        asam
            FROM SYSTEM-MIB
        OBJECT-TYPE
            FROM RFC-1212;

ipConfigMIB OBJECT IDENTIFIER ::= { asam 10 }
ipConfigObjects OBJECT IDENTIFIER ::= { ipConfigMIB 1 }

ipCAddrTable OBJECT-TYPE
    SYNTAX  SEQUENCE OF IpCAddrEntry
    ACCESS  not-accessible
    STATUS  mandatory
    DESCRIPTION
        "The table of addressing information relevant to this entity's
        IP addresses.
        ALCATEL NOTE:
            TABLESIZE: 10
            DESCR: NA"
    ::= { ipConfigObjects 1 }

ipCAddrEntry OBJECT-TYPE
    SYNTAX  IpCAddrEntry
    ACCESS  not-accessible
    STATUS  mandatory
    DESCRIPTION
        "The addressing information for one of this entity's IP addresses.
        Row creation : An entry is created by a manager when the creation
            of a MIB instance for at least ipCAdEntIfIndex and ipCAdEntNetMask
            was successfull.
        Row deletion : An entry is deleted when a manager writes 0 in
            ipCAdEntReasmMaxSize.
        Index usage : the index is the IP address.
        Note that entries will be presented to the SNMP manager in full
        lexicographical order :  sorted on IP address."
    INDEX   { ipCAdEntAddr }
    ::= { ipCAddrTable 1 }

IpCAddrEntry ::=
    SEQUENCE {
        ipCAdEntAddr             IpAddress,
        ipCAdEntIfIndex          INTEGER,
        ipCAdEntNetMask          IpAddress,
        ipCAdEntBcastAddr        INTEGER,
        ipCAdEntReasmMaxSize     INTEGER (0..65535)
    }

ipCAdEntAddr OBJECT-TYPE
    SYNTAX  IpAddress
    ACCESS  read-write
    STATUS  mandatory
    DESCRIPTION
        "The IP address to which this entry's addressing information pertains.
        ALCATEL NOTE:
            ACCESS:      RO            USAGE:       NA
            PERSIST:     YES           INSRVMOD:    NO
            RANGE:       NA            DEFVALUE:    NA
            UNITS:       NA            SPARSE:      NA
            DESCR:       NA"
    ::= { ipCAddrEntry 1 }

ipCAdEntIfIndex OBJECT-TYPE
    SYNTAX  INTEGER
    ACCESS  read-write
    STATUS  mandatory
    DESCRIPTION
        "The index value which uniquely identifies the interface to which
        this entry is applicable.  The interface identified by a particular
        value of this index is the same interface as identified by the
        same value of ifIndex.
        ALCATEL NOTE:
            ACCESS:      NA            USAGE:       MAND
            PERSIST:     YES           INSRVMOD:    ??
            RANGE:       1..2147483647 DEFVALUE:    NA
            UNITS:       NA            SPARSE:      NA
            DESCR:       NA"
    ::= { ipCAddrEntry 2 }

ipCAdEntNetMask OBJECT-TYPE
    SYNTAX  IpAddress
    ACCESS  read-write
    STATUS  mandatory
    DESCRIPTION
        "The subnet mask associated with the IP address of this entry.
        The value of the mask is an IP address with all the network bits
        set to 1 and all the hosts bits set to 0.
        ALCATEL NOTE:
            ACCESS:      NA            USAGE:       MAND
            PERSIST:     YES           INSRVMOD:    ??
            RANGE:       NA            DEFVALUE:    NA
            UNITS:       NA            SPARSE:      NA
            DESCR:       NA"
    ::= { ipCAddrEntry 3 }

ipCAdEntBcastAddr OBJECT-TYPE
    SYNTAX  INTEGER
    ACCESS  read-write
    STATUS  mandatory
    DESCRIPTION
        "The value of the least-significant bit in the IP broadcast address
        used for sending datagrams on the (logical) interface associated
        with the IP address of this entry.
        For example, when the Internet standard all-ones broadcast address is
        used, the value will be 1.  This value applies to both the subnet and
        network broadcasts addresses used by the entity on this (logical)
        interface.
        ALCATEL NOTE:
            ACCESS:      NA            USAGE:       OPT
            PERSIST:     YES           INSRVMOD:    ??
            RANGE:       1             DEFVALUE:    NA
            UNITS:       NA            SPARSE:      NA
            DESCR:       NA"
    DEFVAL {1}
    ::= { ipCAddrEntry 4 }

ipCAdEntReasmMaxSize OBJECT-TYPE
    SYNTAX  INTEGER (0..65535)
    ACCESS  read-write
    STATUS  mandatory
    DESCRIPTION
        "The size of the largest IP datagram which this entity can re-assemble
        from incoming IP fragmented datagrams received on this interface.
        Value 0 means maximum possible length.
        Writing 0 into an existing instance of this object deletes the row.
        ALCATEL NOTE:
            ACCESS:      NA            USAGE:       OPT
            PERSIST:     YES           INSRVMOD:    YES
            RANGE:       NA            DEFVALUE:    NA
            UNITS:       NA            SPARSE:      NA
            DESCR:       NA"
    DEFVAL {0}
    ::= { ipCAddrEntry 5 }

ConfigifType ::= INTEGER {
                         none(1),
                         bootp(2)
                         }

ifCTable OBJECT-TYPE
    SYNTAX  SEQUENCE OF IfCEntry
    ACCESS  not-accessible
    STATUS  mandatory
    DESCRIPTION
        "A list of management interface entries.
        The number of entries is given by the value of ifNumber.
        ALCATEL NOTE:
            TABLESIZE: 16
            DESCR: NA"
    ::= { ipConfigObjects  2 }

ifCEntry OBJECT-TYPE
    SYNTAX  IfCEntry
    ACCESS  not-accessible
    STATUS  mandatory
    DESCRIPTION
        "An entry containing management information applicable to a particular
        interface.
        Row creation : Entries are created by the system at initialization.
        Row deletion : A manager cannot delete entries.
        Index usage : the index is the ifIndex.
        Note that entries will be presented to the SNMP manager in full
        lexicographical order :  sorted on ifIndex."
    INDEX   { ifCIndex }
    ::= { ifCTable  1 }

IfCEntry ::=
    SEQUENCE {
        ifCIndex              InterfaceIndex,
        ifCDescr              DisplayString,
        ifCType               IANAifType,
        ifCMtu                INTEGER (-2147483648..2147483647),
        ifCSpeed              Gauge,
        ifCPhysAddress        PhysAddress,
        ifCAdminStatus        INTEGER,
        ifCOperStatus         INTEGER,
        ifCLastChange         TimeTicks,
        ifCInOctets           Counter,
        ifCInUcastPkts        Counter,
        ifCInNUcastPkts       Counter,
        ifCInDiscards         Counter,
        ifCInErrors           Counter,
        ifCInUnknownProtos    Counter,
        ifCOutOctets          Counter,
        ifCOutUcastPkts       Counter,
        ifCOutNUcastPkts      Counter,
        ifCOutDiscards        Counter,
        ifCOutErrors          Counter,
        ifCOutQLen            Gauge,
        ifCSpecific           OBJECT IDENTIFIER,
        ifConfig              ConfigifType
    }

ifCIndex OBJECT-TYPE
    SYNTAX  InterfaceIndex
    ACCESS  read-only
    STATUS  mandatory
    DESCRIPTION
        "A unique value, greater than zero, for each interface.
        It is recommended that values are assigned contiguously starting from 1.
        The value for each interface sub-layer must remain constant at least
        from one re-initialization of the entity's network management system to
        the next re-initialization.
        ALCATEL NOTE:
            ACCESS:      NA            USAGE:       NA
            PERSIST:     YES           INSRVMOD:    NA
            RANGE:       1..2147483647 DEFVALUE:    NA
            UNITS:       NA            SPARSE:      NA
            DESCR:       NA"
    ::= { ifCEntry  1 }

ifCDescr OBJECT-TYPE
    SYNTAX  DisplayString
    ACCESS  read-only
    STATUS  mandatory
    DESCRIPTION
        "A textual string containing information about the interface.
        This string should include the name of the manufacturer,
        the product name and the version of the interface hardware/software.
        ALCATEL NOTE:
            ACCESS:      NA            USAGE:       NA
            PERSIST:     NA            INSRVMOD:    NA
            RANGE:       NA            DEFVALUE:    DEP
            UNITS:       NA            SPARSE:      NA
            DESCR:       ...."
    ::= { ifCEntry  2 }

ifCType OBJECT-TYPE
    SYNTAX  IANAifType
    ACCESS  read-only
    STATUS  mandatory
    DESCRIPTION
        "The type of interface.  Additional values for ifCType are assigned by
        the Internet Assigned Numbers Authority (IANA), through updating
        the syntax of the IANAifType textual convention.
        ALCATEL NOTE:
            ACCESS:      NA            USAGE:       NA
            PERSIST:     NA            INSRVMOD:    NA
            RANGE:       NA            DEFVALUE:    DEP (see DESCR)
            UNITS:       NA            SPARSE:      NA
            DESCR:       Eth i/f: ...."
    ::= { ifCEntry  3 }

ifCMtu OBJECT-TYPE
    SYNTAX  INTEGER (-2147483648..2147483647)
    ACCESS  read-write
    STATUS  mandatory
    DESCRIPTION
        "The size of the largest packet which can be sent/received on
        the interface, specified in octets. For interfaces that are used for
        transmitting network datagrams, this is the size of the largest network
        datagram that can be sent on the interface.
        The ALCATEL ASAM only supports the value '1500' for
               the Ethernet interface.
        ALCATEL NOTE:
            ACCESS:      NA            USAGE:       ??
            PERSIST:     YES           INSRVMOD:    YES
            RANGE:       0..??         DEFVALUE:    DEP (see DESCR)
            UNITS:       NA            SPARSE:      NA
            DESCR:       Eth i/f: 1500...."
    ::= { ifCEntry  4 }

ifCSpeed OBJECT-TYPE
    SYNTAX  Gauge
    ACCESS  read-only
    STATUS  mandatory
    DESCRIPTION
        "An estimate of the interface's current bandwidth in bits per second.
        For interfaces which do not vary in bandwidth or for those where no
        accurate estimation can be made, this object should contain the
        nominal bandwidth.  If the bandwidth of the interface is greater than
        the maximum value reportable by this object then this object should
        report its maximum value (4,294,967,295) and ifHighSpeed must be used
        to report the interace's speed.  For a sub-layer which has no concept
        of bandwidth, this object should be zero.
        ALCATEL NOTE:
            ACCESS:      NA            USAGE:       NA
            PERSIST:     NA            INSRVMOD:    NA
            RANGE:       0..??         DEFVALUE:    DEP (see DESCR)
            UNITS:       NA            SPARSE:      NA
            DESCR:       SLIP i/f: 9600, ETH i/f: 10000000"
    ::= { ifCEntry  5 }

ifCPhysAddress OBJECT-TYPE
    SYNTAX  PhysAddress
    ACCESS  read-write
    STATUS  mandatory
    DESCRIPTION
        "The interface's address at its protocol sub-layer.
        The interface's media-specific MIB must define the bit and byte ordering
        and format of the value contained by this object.
        For interfaces which do not have such an address (e.g., a serial line),
        this object should contain an octet string of zero length.
        ALCATEL NOTE:
            ACCESS:      RO            USAGE:       NA
            PERSIST:     YES           INSRVMOD:    ??
            RANGE:       0..??         DEFVALUE:    DEP (see DESCR)
            UNITS:       NA            SPARSE:      NA
            DESCR:       SLIP i/f: '', ETH i/f: MAC address"
    ::= { ifCEntry  6 }

ifCAdminStatus OBJECT-TYPE
    SYNTAX  INTEGER {
                 up(1),
                 down(2),
                 testing(3)
               }
    ACCESS  read-write
    STATUS  mandatory
    DESCRIPTION
        "The desired state of the interface.  The testing(3) state indicates
        that no operational packets can be passed.  When a managed system
        initializes, all interfaces start with ifCAdminStatus in the
        down(2) state.  As a result of either explicit management action or
        per configuration information retained by the managed system,
        ifCAdminStatus is then changed to either the up(1) or testing(3) states
        (or remains in the down(2) state).
        ALCATEL NOTE:
            ACCESS:      NA            USAGE:       NA
            PERSIST:     YES           INSRVMOD:    YES
            RANGE:       1|2           DEFVALUE:    DEP (see DESCR)
            UNITS:       NA            SPARSE:      NA
            DESCR:       SLIP i/f: up, ETH i/f: up"
    ::= { ifCEntry  7 }

ifCOperStatus OBJECT-TYPE
    SYNTAX  INTEGER {
                 up(1),
                 down(2),
                 testing(3),
                 unknown(4),
                 dormant(5)
               }
    ACCESS  read-only
    STATUS  mandatory
    DESCRIPTION
        "The current operational state of the interface.  The testing(3) state
        indicates that no operational packets can be passed.
        If ifCAdminStatus is down(2) then ifCOperStatus should be down(2).
        If ifCAdminStatus is changed to up(1) then ifCOperStatus should change
        to up(1) if the interface is ready to transmit and receive network
        traffic; it should change to dormant(5) if the interface is waiting for
        external actions (such as a serial line waiting for an incoming
        connection); it should remain in the down(2) state if and only if there
        is a fault that prevents if from going to the up(1) state.
        ALCATEL NOTE:
            ACCESS:      NA            USAGE:       NA
            PERSIST:     YES           INSRVMOD:    YES
            RANGE:       1|2           DEFVALUE:    DEP
            UNITS:       NA            SPARSE:      NA
            DESCR:       ...."
    ::= { ifCEntry  8 }

ifCLastChange OBJECT-TYPE
    SYNTAX  TimeTicks
    ACCESS  read-only
    STATUS  mandatory
    DESCRIPTION
        "The value of sysUpTime at the time the interface entered its current
        operational state.  If the current state was entered prior to the last
        re-initialization of the local network management subsystem, then this
        object contains a zero value.
        ALCATEL NOTE:
            ACCESS:      NA            USAGE:       NA
            PERSIST:     NO            INSRVMOD:    NA
            RANGE:       NA            DEFVALUE:    0
            UNITS:       NA            SPARSE:      NA
            DESCR:       NA"
    ::= { ifCEntry  9 }

ifCInOctets OBJECT-TYPE
    SYNTAX  Counter
    ACCESS  read-only
    STATUS  mandatory
    DESCRIPTION
        "The total number of octets received on the interface,
        including framing characters.
        ALCATEL NOTE:
            ACCESS:      NA            USAGE:       NA
            PERSIST:     NO            INSRVMOD:    NA
            RANGE:       NA            DEFVALUE:    0
            UNITS:       octets        SPARSE:      NA
            DESCR:       NA"
    ::= { ifCEntry  10 }

ifCInUcastPkts OBJECT-TYPE
    SYNTAX  Counter
    ACCESS  read-only
    STATUS  mandatory
    DESCRIPTION
           "The number of packets, delivered by this sub-layer to
               a higher (sub-)layer, which were not addressed to a
               multicast or broadcast address at this sub-layer."
    ::= { ifCEntry  11 }

ifCInNUcastPkts OBJECT-TYPE
    SYNTAX  Counter
    ACCESS  read-only
    STATUS  deprecated
    DESCRIPTION
           "The number of packets, delivered by this sub-layer to
               a higher (sub-)layer, which were addressed to a
               multicast or broadcast address at this sub-layer.
               This object is deprecated in favour of
               ifCInMulticastPkts and ifCInBroadcastPkts."
    ::= { ifCEntry  12 }

ifCInDiscards OBJECT-TYPE
    SYNTAX  Counter
    ACCESS  read-only
    STATUS  mandatory
    DESCRIPTION
           "The number of inbound packets which were chosen to be
               discarded even though no errors had been detected to
               prevent their being deliverable to a higher-layer
               protocol.  One possible reason for discarding such a
               packet could be to free up buffer space."
    ::= { ifCEntry  13 }

ifCInErrors OBJECT-TYPE
    SYNTAX  Counter
    ACCESS  read-only
    STATUS  mandatory
    DESCRIPTION
           "For packet-oriented interfaces, the number of inbound
               packets that contained errors preventing them from
               being deliverable to a higher-layer protocol.  For
               character-oriented or fixed-length interfaces, the
               number of inbound transmission units that contained
               errors preventing them from being deliverable to a
               higher-layer protocol."
    ::= { ifCEntry  14 }

ifCInUnknownProtos OBJECT-TYPE
    SYNTAX  Counter
    ACCESS  read-only
    STATUS  mandatory
    DESCRIPTION
           "For packet-oriented interfaces, the number of packets
               received via the interface which were discarded
               because of an unknown or unsupported protocol.  For
               character-oriented or fixed-length interfaces which
               support protocol multiplexing the number of
               transmission units received via the interface which
               were discarded because of an unknown or unsupported
               protocol.  For any interface which does not support
               protocol multiplexing, this counter will always be 0."
    ::= { ifCEntry  15 }

ifCOutOctets OBJECT-TYPE
    SYNTAX  Counter
    ACCESS  read-only
    STATUS  mandatory
    DESCRIPTION
           "The total number of octets transmitted out of the
               interface, including framing characters."
    ::= { ifCEntry  16 }

ifCOutUcastPkts OBJECT-TYPE
    SYNTAX  Counter
    ACCESS  read-only
    STATUS  mandatory
    DESCRIPTION
           "The total number of packets that higher-level
               protocols requested be transmitted, and which were not
               addressed to a multicast or broadcast address at this
               sub-layer, including those that were discarded or not
               sent."
    ::= { ifCEntry  17 }

ifCOutNUcastPkts OBJECT-TYPE
    SYNTAX  Counter
    ACCESS  read-only
    STATUS  deprecated
    DESCRIPTION
           "The total number of packets that higher-level
               protocols requested be transmitted, and which were
               addressed to a multicast or broadcast address at this
               sub-layer, including those that were discarded or not
               sent.

               This object is deprecated in favour of
               ifCOutMulticastPkts and ifCOutBroadcastPkts."
    ::= { ifCEntry  18 }

ifCOutDiscards OBJECT-TYPE
    SYNTAX  Counter
    ACCESS  read-only
    STATUS  mandatory
    DESCRIPTION
           "The number of outbound packets which were chosen to
               be discarded even though no errors had been detected
               to prevent their being transmitted.  One possible
               reason for discarding such a packet could be to free
               up buffer space.
               The ALCATEL ASAM does NOT support this object."
    ::= { ifCEntry  19 }

ifCOutErrors OBJECT-TYPE
    SYNTAX  Counter
    ACCESS  read-only
    STATUS  mandatory
    DESCRIPTION
           "For packet-oriented interfaces, the number of
               outbound packets that could not be transmitted because
               of errors.  For character-oriented or fixed-length
               interfaces, the number of outbound transmission units
               that could not be transmitted because of errors."
    ::= { ifCEntry  20 }

ifCOutQLen OBJECT-TYPE
    SYNTAX  Gauge
    ACCESS  read-only
    STATUS  deprecated
    DESCRIPTION
           "The length of the output packet queue (in packets)."
    ::= { ifCEntry  21 }

ifCSpecific OBJECT-TYPE
    SYNTAX  OBJECT IDENTIFIER
    ACCESS  read-only
    STATUS  deprecated
    DESCRIPTION
           "A reference to MIB definitions specific to the
               particular media being used to realize the interface.
               It is recommended that this value point to an instance
               of a MIB object in the media-specific MIB, i.e., that
               this object have the semantics associated with the
               InstancePointer textual convention defined in RFC
               1443.  In fact, it is recommended that the media-
               specific MIB specify what value ifSpecific should/can
               take for values of ifCType.  If no MIB definitions
               specific to the particular media are available, the
               value should be set to the OBJECT IDENTIFIER { 0 0 }."
    ::= { ifCEntry  22 }

ifConfig OBJECT-TYPE
    SYNTAX  ConfigifType
    ACCESS  read-write
    STATUS  mandatory
    DESCRIPTION
           " Specifies how an interface retrieves his configuration data.
             If <none> is specified, persistant data is used to configure
             the interface.
             When <bootp> is specified, the interface will receives his 
             configuration during exchange of a BOOTP request-reply, and
             snmp configuration."
    ::= { ifCEntry  23 }

END
