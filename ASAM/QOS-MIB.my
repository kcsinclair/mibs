-- orig QOS_MIB

QOS-MIB DEFINITIONS ::= BEGIN

IMPORTS
	Gauge   	FROM RFC1155-SMI
        Counter  	FROM RFC1155-SMI
        TimeTicks	FROM RFC1155-SMI
       	OBJECT-TYPE     FROM RFC-1212
       	asam 		FROM SYSTEM-MIB
       	RowStatus, TruthValue       FROM SNMPv2-TC
        
       	InterfaceIndex  FROM ITF-MIB

        InetAddressType 	FROM INET-ADDRESS-MIB
        InetAddress     	FROM INET-ADDRESS-MIB
        InetAddressPrefixLength  FROM INET-ADDRESS-MIB
        InetPortNumber           FROM INET-ADDRESS-MIB

	ExtendVlanSystemPriority FROM PLIM-ETHERNET-MIB
       	DisplayString        FROM RFC1213-MIB
	eqptSlotId           FROM ASAM-EQUIP-MIB
       	AsamProfileIndex     FROM ASAM-TC-MIB
        AsamProfilePointer   FROM ASAM-TC-MIB
       	AsamProfileName      FROM ASAM-TC-MIB
        AsamProfileRefCount  FROM ASAM-TC-MIB
        AsamProfileRefCount32  FROM ASAM-TC-MIB
        MacAddress	     FROM SNMPv2-TC ;

DscpValue ::= INTEGER (0..63)
DscpOrAny ::= INTEGER (-1|0 .. 63)
Uint32 ::= Gauge (0..4294967295) 

qosMIB       OBJECT IDENTIFIER ::= { asam 47 } 

qosSystemGroup OBJECT IDENTIFIER ::= {qosMIB 1}

qosSessionProfileGetNextFree OBJECT-TYPE
	SYNTAX INTEGER
	ACCESS read-only
	STATUS mandatory
	DESCRIPTION
	"This object contains an appropriate value to
	be used for qosSessionProfileEntry when creating
	entries in the qosSessionProfileTable. The value
	0 indicates that no unassigned entries are
	available"
::= { qosSystemGroup 1 }
qosMarkerProfileGetNextFree OBJECT-TYPE
	SYNTAX INTEGER
	ACCESS read-only
	STATUS mandatory
	DESCRIPTION
	"This object contains an appropriate value to
	be used for qosMarkerProfileEntry when creating
	entries in the qosMarkerProfileTable. The value
	0 indicates that no unassigned entries are
	available"
::= { qosSystemGroup 2 }
qosPolicerProfileGetNextFree OBJECT-TYPE
	SYNTAX INTEGER
	ACCESS read-only
	STATUS mandatory
	DESCRIPTION
	"This object contains an appropriate value to
	be used for qosPolicerProfileEntry when creating
	entries in the qosPolicerProfileTable. The value
	0 indicates that no unassigned entries are
	available"
::= { qosSystemGroup 3 }

qosQueueProfileGetNextFree OBJECT-TYPE
	SYNTAX INTEGER
	ACCESS read-only
	STATUS mandatory
	DESCRIPTION
	"This object contains an appropriate value to
	be used for qosQueueProfileEntry when creating
	entries in the qosQueueProfileTable. The value
	0 indicates that no unassigned entries are
	available"
::= { qosSystemGroup 4 }

qosSchedulerProfileGetNextFree OBJECT-TYPE
	SYNTAX INTEGER
	ACCESS read-only
	STATUS mandatory
	DESCRIPTION
	"This object contains an appropriate value to
	be used for qosSchedulerProfileEntry when creating
	entries in the qosSchedulerProfileTable. The value
	0 indicates that no unassigned entries are
	available"
::= { qosSystemGroup 5 }

qosCacProfileGetNextFree OBJECT-TYPE
	SYNTAX INTEGER
	ACCESS read-only
	STATUS mandatory
	DESCRIPTION
	"This object contains an appropriate value to
	be used for qosCacProfileEntry when creating
	entries in the qosCacProfileTable. The value
	0 indicates that no unassigned entries are
	available"
::= { qosSystemGroup 6 }

qosPolicyTableGetNextFree OBJECT-TYPE
    SYNTAX  INTEGER
    ACCESS  read-only
    STATUS  mandatory
    DESCRIPTION
           "This object contains an appropriate value to
            be used for qosPolicyEntry when creating
            entries in the qosPolicyTable. The value
            0 indicates that no unassigned entries are
            available"
    ::= {  qosSystemGroup 7 }

qosL2FilterTableGetNextFree OBJECT-TYPE
    SYNTAX  INTEGER
    ACCESS  read-only
    STATUS  mandatory
    DESCRIPTION
           "This object contains an appropriate value to
            be used for qosL2FilterEntry when creating
            entries in the qosL2FilterTable. The value
            0 indicates that no unassigned entries are
            available"
    ::= {  qosSystemGroup 8 }

qosL3FilterTableGetNextFree OBJECT-TYPE
    SYNTAX  INTEGER
    ACCESS  read-only
    STATUS  mandatory
    DESCRIPTION
           "This object contains an appropriate value to
            be used for qosL3FilterEntry when creating
            entries in the qosL3FilterTable. The value
            0 indicates that no unassigned entries are
            available"
    ::= {  qosSystemGroup 9 }

qosPolicyActionTableGetNextFree OBJECT-TYPE
    SYNTAX  INTEGER
    ACCESS  read-only
    STATUS  mandatory
    DESCRIPTION
           "This object contains an appropriate value to
            be used for qosPolicyActionEntry when creating
            entries in the qosPolicyActionTable. The value
            0 indicates that no unassigned entries are
            available"
::= {  qosSystemGroup 10 }

qosShaperProfileTableGetNextFree OBJECT-TYPE
    SYNTAX  INTEGER
    ACCESS  read-only
    STATUS  mandatory
    DESCRIPTION
           "This object contains an appropriate value to
            be used for qosShaperProfileEntry when creating
            entries in the qosShaperProfileTable. The value
            0 indicates that no unassigned entries are
            available
      ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 11 }

qosBandwidthProfileTableGetNextFree OBJECT-TYPE
    SYNTAX  INTEGER
    ACCESS  read-only
    STATUS  mandatory
    DESCRIPTION
           "This object contains an appropriate value to
            be used for qosBandwidthProfileEntry when creating
            entries in the qosBandwidthProfileTable. The value
            0 indicates that no unassigned entries are
            available
      ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 12 }

qosSchedulerNodeProfileTableGetNextFree OBJECT-TYPE
    SYNTAX  INTEGER
    ACCESS  read-only
    STATUS  mandatory
    DESCRIPTION
           "This object contains an appropriate value to
            be used for qosSchedulerNodeProfileEntry when creating
            entries in the qosSchedulerNodeProfileTable. The value
            0 indicates that no unassigned entries are
            available
      ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 13 }

qosIngressQosProfileTableGetNextFree OBJECT-TYPE
    SYNTAX  INTEGER
    ACCESS  read-only
    STATUS  mandatory
    DESCRIPTION
           "This object contains an appropriate value to
            be used for qosIngressQosProfileEntry when creating
            entries in the qosIngressQosProfileTable. The value
            0 indicates that no unassigned entries are
            available
      ALCATEL NOTE:
                 ACCESS:     NA       USAGE:      NA
                 PERSIST:    NO       INSRVMOD:   NO
                 RANGE:      NA       DEFVALUE:   NA
                 UNITS:      NA       SPARSE:     NA
                 DESCR:      NA "
    ::= {  qosSystemGroup 14 }

qosMacroProfiles OBJECT IDENTIFIER ::= {qosMIB 2}

qosSessionProfileTable OBJECT-TYPE
	SYNTAX	SEQUENCE OF QosSessionProfileEntry
	ACCESS	not-accessible
	STATUS	mandatory
	DESCRIPTION
	"This object contains a table for creating and storing
	QoS Session Profiles. Session profiles contain information
	on the bandwidth, traffic class and marking applicable on
	the session. Most objects in this table are references to
	other profiles stored in other MIB tables"
::= { qosMacroProfiles 1 }
qosSessionProfileEntry OBJECT-TYPE
	SYNTAX 	QosSessionProfileEntry
	ACCESS	not-accessible
	STATUS mandatory
	DESCRIPTION
	"Each entry contains the data of one QoS session
	profile.Session profiles are also called macro profiles,
	because they also call on other profiles, not only plain
	objects."
	INDEX	{qosSessionProfileIndex }
	::= {qosSessionProfileTable 1}

QosLfDefinitionType ::= INTEGER (0..19)

PolicyList ::= OCTET STRING ( SIZE (32))

Counter64bit ::= OCTET STRING (SIZE (8))

QosColourType ::= INTEGER (0..2)

QosSessionProfileEntry ::=
     SEQUENCE { qosSessionProfileIndex 			AsamProfileIndex,
		qosSessionProfileName 			AsamProfileName,
		qosSessionProfileVersion		INTEGER,
		qosSessionProfileRefCount		AsamProfileRefCount32,
		qosSessionProfileLogFlowType		QosLfDefinitionType,
		qosSessionProfileUpPolProfileId 	AsamProfilePointer,
		qosSessionProfileDnPolProfileId 	AsamProfilePointer,
		qosSessionProfileUpMarkerProfileId	AsamProfilePointer,

		qosSessionProfileRowStatus 		RowStatus,
		qosSessionProfilePolicyListUp		PolicyList,
		qosSessionProfilePolicyListDn		PolicyList
	
				}

qosSessionProfileIndex OBJECT-TYPE
	SYNTAX	AsamProfileIndex
	ACCESS	not-accessible
	STATUS mandatory
	DESCRIPTION
	"This object is the index to the qosSessionProfileTable."
::= { qosSessionProfileEntry 1}
qosSessionProfileName OBJECT-TYPE
	SYNTAX	AsamProfileName
	ACCESS	read-write
	STATUS mandatory
	DESCRIPTION
	"A text string containing the operator-assigned name of
	this profile"
::= { qosSessionProfileEntry 2}
qosSessionProfileVersion OBJECT-TYPE
	SYNTAX	INTEGER
	ACCESS	read-write
	STATUS mandatory
	DESCRIPTION
	"Integer containing the version number of this profile."
::= { qosSessionProfileEntry 3}

qosSessionProfileRefCount OBJECT-TYPE
	SYNTAX	AsamProfileRefCount32
	ACCESS read-only
	STATUS	mandatory
	DESCRIPTION
	" Indicates the number of entities using this profile. If the
	reference count is greater than 0, then this profile is 'in use',
	and may NOT be deleted. If the value is 0, then this profile is
	'not in use', and can be deleted."
::= { qosSessionProfileEntry 4}
qosSessionProfileLogFlowType OBJECT-TYPE
	SYNTAX	QosLfDefinitionType
	ACCESS	read-write
	STATUS mandatory
	DESCRIPTION
	"Integer, which defines a logical flow. A logical flow is a
	traffic stream upon which a policy or a contract is made,
	such as all frames on an interface with a particular code point
	or all frames in a PPP session, etc..
	0 - Generic		- Applicable to any defined logical flow
	1 - PVC 		- All frames on a PVC.
	2 - 802.1X session	- All frames on a PVC except
				(port based)	  PPP frames.
	3 - PVC.VLAN		- Represents all frames on a .1D port
				  with the same VLAN ID.
	4 - PVC.VLAN.P (ns)	- Represents all frames on a .1D port
				  with the same VLAN ID and .1P bits.
				(not supported in R2.0)
	5 - PPP			- 	Represents all
					frames in a terminated PPP
					session/interface.		
	6 - IP            	- Represents all frames
				  in a terminated IP session/interface.
	7 - IPoE VLAN CC        - Represents all IPoE frames in a
				  VLAN CC interface.
	8 - PPPoE VLAN CC       -  Represents all PPPoE frames in
                                   a VLAN CC interface.
	9 - IPoA CC             -  Represents all IPoA frames in a IPoA CC 
				   interface.
	10 - PPPoA CC   	-  Represents all PPPoA frames in
				   a PPPoA CC interface.
	11 - IPoE I-Bridge      -  Represents all IPoE frames in I-Bridge 
				   interface.
	12 - PPPoE I-Bridge     -  Represents all PPPoE frames inI-Bridge 
				   interface.
	13 - PPPoA Relay        -  Represents all PPPoA frames in PPPoA relay 
	                           interface.
	14 - PPPoE Relay with MAC concentration   
	                        -  Represents all PPPoE 
	                           frames in PPPeE relay with MAC concentration
				   interface.
	15 - IPoE IP Aware Bridge   -	Represents all IPoE
				   frames in IP Aware Bridge interface.
	16 - IPoA IP Aware Bridge   -	Represents all IPoA
				   frames in IP Aware Bridge interface.
	17 - PPPoE termination   - Represents all PPPoE
                                   frames in PPPoE termination interface.
	18 - PPPoA termination   - Represents all PPPoA
                                   frames in PPPoA termination interface.
        19 -  IPoA Forwarder       - Represents all IPoA
                                   frames in all IPoA forwarders including IPoA E-IBridge, IPoA CC and IPoA Termination."
 
::= { qosSessionProfileEntry 5}
qosSessionProfileUpPolProfileId OBJECT-TYPE
	SYNTAX	AsamProfilePointer
	ACCESS	read-write
	STATUS mandatory
	DESCRIPTION
	"This object contains the ID of the applicable policer
	profile on this session upstream.
	The default (null entry) is no policing upstream."
::= { qosSessionProfileEntry 6}
qosSessionProfileDnPolProfileId OBJECT-TYPE
	SYNTAX	AsamProfilePointer
	ACCESS	read-write
	STATUS mandatory
	DESCRIPTION
	"This object contains the ID of the applicable policer
	profile on this session downstream. The
	default is no policing downstream"
::= { qosSessionProfileEntry 7}

qosSessionProfileUpMarkerProfileId OBJECT-TYPE
	SYNTAX	AsamProfilePointer
	ACCESS	read-write
	STATUS mandatory
	DESCRIPTION
	"This object contains the ID of the applicable marker
	profile on a session upstream. If not
	specified, then default markings will be applied."
::= { qosSessionProfileEntry 8}

qosSessionProfileRowStatus OBJECT-TYPE
	SYNTAX	RowStatus
	ACCESS	read-write
	STATUS mandatory
	DESCRIPTION
	"This object is used to create a new row or modify or
	delete an existing row in this table. The usage is as per
	standard semantics of 'RowStatus' defined in SNMPv2-TC, with
	following limitations:
	The entry associated with a Profile that is being used may
	not be deleted."
::= { qosSessionProfileEntry 10}

qosSessionProfilePolicyListUp OBJECT-TYPE 
	SYNTAX	PolicyList
	ACCESS	read-write
	STATUS  mandatory
	DESCRIPTION
"A set of Policies that will be applied to the upstream direction of a subscriber interface. The amount of upstream policies that can be linked to one Session Profile is defined in Board Capability Manager."
::= { qosSessionProfileEntry 11}

qosSessionProfilePolicyListDn OBJECT-TYPE 
	SYNTAX	PolicyList
	ACCESS	read-write
	STATUS  mandatory
	DESCRIPTION
"A set of Policies that will be applied to the downstream direction of a subscriber interface. The amount of downstream policies that can be linked to one Session Profile is defined in Board Capability Manager."
::= { qosSessionProfileEntry 12}

qosSessionProfileMappingTable OBJECT-TYPE
	SYNTAX	SEQUENCE OF QosSessionProfileMappingEntry
	ACCESS	not-accessible
	STATUS	mandatory
	DESCRIPTION
			"This object contains a table for qosSessionProfile
name to index mapping"
::= { qosMacroProfiles 2 }

qosSessionProfileMappingEntry OBJECT-TYPE
	SYNTAX 	QosSessionProfileMappingEntry
	ACCESS	not-accessible
	STATUS mandatory
	DESCRIPTION
	" An entry (conceptual row) representing the qossession Profile Name to
	Index mapping. The system automatically creates an entry in this Table 
	for each corresponding entry (qosSession-profile) created
	in the qosSessionProfileTable.
	Similarly, when an qosSessionprofile is deleted, the
	corresponding entry in this
	table is also automatically deleted by the system."
	INDEX	{qosSessionProfileMappingName }
	::= {qosSessionProfileMappingTable  1}

QosSessionProfileMappingEntry ::=
	SEQUENCE { qosSessionProfileMappingName AsamProfileName,
		   qosSessionProfileMappingIndex AsamProfileIndex
			}

qosSessionProfileMappingName OBJECT-TYPE
	SYNTAX	AsamProfileName
	ACCESS	not-accessible
	STATUS  mandatory
	DESCRIPTION
		"A text string containing the name of
		this profile"
::= { qosSessionProfileMappingEntry 1}

qosSessionProfileMappingIndex OBJECT-TYPE
	SYNTAX	AsamProfileIndex
	ACCESS	read-write
	STATUS mandatory
	DESCRIPTION
		"This object is the Profile index."
::= { qosSessionProfileMappingEntry 2}

qosProfiles OBJECT IDENTIFIER ::= {qosMIB 3}

qosMarkerProfileTable OBJECT-TYPE
	SYNTAX 	SEQUENCE OF QosMarkerProfileEntry
	ACCESS	not-accessible
	STATUS	mandatory
	DESCRIPTION
	" This object contains a table for creating and storing
	marker profiles. A marker profile contains marking
	information for frames within the session to which this
	marker profile is attached"
::= {qosProfiles 1 }
qosMarkerProfileEntry OBJECT-TYPE
	SYNTAX QosMarkerProfileEntry
	ACCESS not-accessible
	STATUS mandatory	
	DESCRIPTION
	"This table contains QoS Marker Profile settings"
	INDEX {qosMarkerProfileIndex}
::= {qosMarkerProfileTable 1}
QosMarkerProfileEntry ::=
     SEQUENCE { qosMarkerProfileIndex	        AsamProfileIndex,
		qosMarkerProfileName		AsamProfileName,
		qosMarkerProfileType		INTEGER,
		qosMarkerProfileRefCount	AsamProfileRefCount32,
		qosMarkerProfileDot1P	        ExtendVlanSystemPriority,
		qosMarkerProfileRowStatus	RowStatus,
                qosMarkerProfileDscp		DscpValue,
	        qosMarkerProfileDscpContractTable	  OCTET STRING,
		qosMarkerProfileDscpToDot1PalignmentFlag   INTEGER
	
		}
qosMarkerProfileIndex 	OBJECT-TYPE
	SYNTAX AsamProfileIndex
	ACCESS not-accessible
	STATUS mandatory
	DESCRIPTION
	 "This object is the index to the qosMarkerProfileTable."
::= { qosMarkerProfileEntry 1}
qosMarkerProfileName 	OBJECT-TYPE
	SYNTAX	AsamProfileName
	ACCESS read-write
	STATUS mandatory
	DESCRIPTION
	 "Octet string storing the operator-given name of the profile"
::= {qosMarkerProfileEntry 2}
qosMarkerProfileType 	OBJECT-TYPE
	SYNTAX INTEGER { singleDot1P (1),

                         singleDscp (4),
                         dscpContract (5),
                         dot1PandDscp (6),
                         dot1PandDscpContract (7),
                         dscpToDot1PAlignment (8)
}
	ACCESS read-write
	STATUS mandatory
	DESCRIPTION
	 "The type field specifies the type of marking applied.
          the type 'singleDot1P'means a single Dot1P marking action.
          QosMarkerProfileDot1P field should be used.
          The type 'DscpContract' means a DSCP contract table will
          be applied, qosMarkerProfileDscpContractTable field
          should be used and qosMarkerProfileDscpToDot1PalignmentFlag
          field should be checked.
          The type 'Dot1PandDscp' means a default P-bits and DSCP
          marking action, so qosMarkerProfileDot1P and qosMarkerProfileDscp
          fields should be used and qosMarkerProfileDscpToDot1PalignmentFlag
          field should be checked.
          The type 'singleDscp' means a default DSCP marking action, so
          qosMarkerProfileDscp field should be used and
          qosMarkerProfileDscpToDot1PalignmentFlag field should be checked.
          The type 'dot1PandDscpContract'means a default P-bits and DSCP
          contract table marking action, so qosMarkerProfileDot1P field
          and qosMarkerProfileDscpContractTable field should be used and
          qosMarkerProfileDscpToDot1PalignmentFlag field should be checked.
          The type 'DscpToDot1Palignment' means DSCP to Dot1P alignment should
          be applied, and no other fields need to be checked anymore. "
::= { qosMarkerProfileEntry 3}

qosMarkerProfileRefCount OBJECT-TYPE
	SYNTAX	AsamProfileRefCount32
	ACCESS read-only
	STATUS	mandatory
	DESCRIPTION
		" Indicates the number of entities using this profile. If the
reference count is greater than 0, then this profile is 'in use',
and may NOT be deleted. If the value is 0, then this profile is
'not in use', and can be deleted."
::= { qosMarkerProfileEntry 4}

qosMarkerProfileDot1P 	OBJECT-TYPE
	SYNTAX ExtendVlanSystemPriority
	ACCESS read-write
	STATUS mandatory
	DESCRIPTION
	 "This object stores the default .1P-value (3 bits) to be
	 applied on all frames in a given direction on the session
	 to which this marker profile was attached"
::= { qosMarkerProfileEntry 5}

qosMarkerProfileRowStatus OBJECT-TYPE
	SYNTAX	RowStatus
	ACCESS	read-write
	STATUS mandatory
	DESCRIPTION
		"This object is used to create a new row or modify or
delete an existing row in this table. The usage is as per
standard semantics of 'RowStatus' defined in SNMPv2-TC, with
following limitations:
o The entry associated with a Profile that is being used may
not be deleted."
::= { qosMarkerProfileEntry 6}

qosMarkerProfileDscp 	OBJECT-TYPE
	SYNTAX DscpValue
	ACCESS read-write
	STATUS mandatory
	DESCRIPTION
	"This object stores the default DSCP value (the six most
         significant bits of the 1-byte IP TOS field) to be applied on all
         frames in a given direction on the subscriber interface to which
         this marker profile was attached"
::= { qosMarkerProfileEntry  7}

qosMarkerProfileDscpContractTable OBJECT-TYPE
	SYNTAX	OCTET STRING
	ACCESS	read-write
	STATUS  mandatory
	DESCRIPTION
        " The following mapping applies: DSCP codepoint 0 corresponds
        to bit 0-7, codepoint 1 to bit 8-15,...The mapping goes from
        6 bit to 8 bit for implementation convenience.
        As a consequence, the most significant two bits of the new DSCP
        value is not used. Graphical representation of where to find the
        regenerated DSCP value in the string of a received DSCP codepoint
        Bit511-504 bit503-496 bit495-488 . . . bit31-bit24 bit23-16
        bit15-8 bit7-0  CP63      CP62      CP61     . . .     CP3    
        CP2     CP1     CP0 "
::= { qosMarkerProfileEntry  8}

qosMarkerProfileDscpToDot1PalignmentFlag	OBJECT-TYPE
	SYNTAX INTEGER
			{
				enabled (1),
				disabled (2)
			}
	ACCESS read-write
	STATUS mandatory
	DESCRIPTION
	    " Setting the object to enabled enables the DSCP to P-bits
alignment on the subscriber interface"
	DEFVAL { disabled }
::= { qosMarkerProfileEntry  9}

qosPolicerProfileTable OBJECT-TYPE
	SYNTAX	SEQUENCE OF QosPolicerProfileEntry
	ACCESS	not-accessible
	STATUS	mandatory
	DESCRIPTION
	"This object contains a table for creating and storing
	policer profiles. A policer profile contains rate enforcement
	information for frames within the session to which
	this policer profile is attached. "
::= { qosProfiles 2 }
qosPolicerProfileEntry OBJECT-TYPE
	SYNTAX 	QosPolicerProfileEntry
	ACCESS	not-accessible
	STATUS	mandatory
	DESCRIPTION
		"Rows of this table contain QoS Policer Profiles"
	INDEX {qosPolicerProfileIndex }
::= {qosPolicerProfileTable 1}
QosPolicerProfileEntry ::=
     SEQUENCE { qosPolicerProfileIndex		AsamProfileIndex,
		qosPolicerProfileName		AsamProfileName,
		qosPolicerProfileRefCount	AsamProfileRefCount32,
		qosPolicerProfileType 		INTEGER,
		qosPolicerProfileCIR		INTEGER,
		qosPolicerProfileCBS		INTEGER,
		qosPolicerProfileRowStatus RowStatus,
        qosPolicerProfileEIR		INTEGER,
		qosPolicerProfileEBS		INTEGER,
		qosPolicerProfileCF			INTEGER,
		qosPolicerProfileCM			INTEGER,
		qosPolicerProfileGreenAction	INTEGER,
		qosPolicerProfileGreenDot1P	INTEGER,
		qosPolicerProfileGreenDSCP	INTEGER,
		qosPolicerProfileYellowAction	INTEGER,
		qosPolicerProfileYellowDot1P	INTEGER,
		qosPolicerProfileYellowDSCP	INTEGER,
		qosPolicerProfileRedAction	INTEGER,
		qosPolicerProfileRedDot1P	INTEGER,
		qosPolicerProfileRedDSCP	INTEGER
				}
qosPolicerProfileIndex OBJECT-TYPE
	SYNTAX AsamProfileIndex
	ACCESS not-accessible
	STATUS mandatory
	DESCRIPTION
	 "This object is the index to the qosPolicerProfileTable."
::= { qosPolicerProfileEntry 1}
qosPolicerProfileName 	OBJECT-TYPE
	SYNTAX	AsamProfileName
	ACCESS read-write
	STATUS mandatory
	DESCRIPTION
	 "Octet string storing the operator-given name of the profile"
::= {qosPolicerProfileEntry 2}
qosPolicerProfileRefCount OBJECT-TYPE
	SYNTAX	AsamProfileRefCount32
	ACCESS read-only
	STATUS	mandatory
	DESCRIPTION
		" Indicates the number of entities using this profile. If the
reference count is greater than 0, then this profile is 'in use',
and may NOT be deleted. If the value is 0, then this profile is
'not in use', and can be deleted."
::= { qosPolicerProfileEntry 3}
qosPolicerProfileType OBJECT-TYPE
	SYNTAX INTEGER { singleTokenBucket (1), trTCM (2)}
	ACCESS read-write
	STATUS mandatory
	DESCRIPTION
	 "The policer profile type encodes a standardized policing
	algorithm with an integer value. Based on this type the
	hardware will know how to configure the policers, and which
	of the following fields are required.	
	1 - Single Token Bucket Policer
	2 - trTCM Policer "
::= { qosPolicerProfileEntry 4}
qosPolicerProfileCIR OBJECT-TYPE
	SYNTAX INTEGER
	ACCESS read-write
	STATUS mandatory
	DESCRIPTION
	 "This object stores the Committed Information Rate (CIR)
	of a policer in Kilobits per second. Cannot be negative."
::= { qosPolicerProfileEntry 5}
qosPolicerProfileCBS OBJECT-TYPE
	SYNTAX INTEGER
	ACCESS read-write
	STATUS mandatory
	DESCRIPTION
	 "This object stores the Committed Burst Size (CBS)
	of a policer in bytes. Cannot be negative.
	Some hardware might not be able to support this
	granularity level. If so, values are rounded in hardware always
	upwards.Range is: 64 to 256K in terms of bytes. "
::= { qosPolicerProfileEntry 6}
qosPolicerProfileRowStatus OBJECT-TYPE
	SYNTAX	RowStatus
	ACCESS	read-write
	STATUS mandatory
	DESCRIPTION
"This object is used to create a new row or modify or
delete an existing row in this table. The usage is as per
standard semantics of 'RowStatus' defined in SNMPv2-TC, with
following limitations:
o The entry associated with a Profile that is being used may
not be deleted."

::= { qosPolicerProfileEntry 7}
qosPolicerProfileEIR OBJECT-TYPE
	SYNTAX INTEGER
	ACCESS read-write
	STATUS mandatory
	DESCRIPTION
	 "This object stores the Excess Information Rate (EIR)
	of a policer in Kilobits per second. Cannot be negative.
        ALCATEL NOTE:
                 ACCESS:     NA       USAGE:      NA
                 PERSIST:    YES       INSRVMOD:   NO
                 RANGE:      NA      DEFVALUE:   NA
                 UNITS:      NA       SPARSE:     NA
                            DESCR:      NA "
DEFVAL { 0 }
::= { qosPolicerProfileEntry 8}

qosPolicerProfileEBS OBJECT-TYPE
	SYNTAX INTEGER
	ACCESS read-write
	STATUS mandatory
	DESCRIPTION
	 "This object stores the Excess Burst Size (EBS)
	of a policer in bytes. Cannot be negative.
	Some hardware might not be able to support this
	granularity level. If so, values are rounded in hardware always
	upwards.Range is: 64 to 256K in terms of bytes.
        ALCATEL NOTE:
                 ACCESS:     NA       USAGE:      NA
                 PERSIST:    YES       INSRVMOD:   NO
                 RANGE:      NA      DEFVALUE:   NA
                 UNITS:      NA       SPARSE:     NA
                                     DESCR:      NA"
        DEFVAL { 64 }
::= { qosPolicerProfileEntry 9}

qosPolicerProfileCF OBJECT-TYPE
	SYNTAX INTEGER { disable (1), enable (2)}
	ACCESS read-write
	STATUS mandatory
	DESCRIPTION
	 "This object stores the Coupling Flag (CF).
	The Coupling Flag CF is set to either 1 or 2. The choice 
	of the value of CF has the effect of controlling the volume 
	of the Service Frames that are declared Yellow. When CF is 
	set to 1, the long term average bit rate of Service Frames 
	that are declared Yellow. When CF is set to 1, the long 
	term average bit rate of Service Frames that are declared 
	Yellow is bounded by EIR. When CF is set to 2, the long 
	term average bit rate of Service Frames that are declared 
	Yellow is bounded by CIR + EIR depending on volume of the 
	offered Service Frames that are declared Green. In both 
	cases the burst size of the Service Frames that are declared 
	Yellow is bounded by EBS.
        ALCATEL NOTE:
                 ACCESS:     NA       USAGE:      NA
                 PERSIST:    YES       INSRVMOD:   NO
                 RANGE:      NA      DEFVALUE:   1
                 UNITS:      NA       SPARSE:     NA
                                     DESCR:      NA"
	DEFVAL {1}
::= { qosPolicerProfileEntry 10}

qosPolicerProfileCM OBJECT-TYPE
	SYNTAX INTEGER { color-blind (1), color-aware (2)}
	ACCESS read-write
	STATUS mandatory
	DESCRIPTION
	 "This object stores the color mode.
	The color mode parameter indicates whether 
	the color-aware or color-blind property is 
	employed by the policer profile. It takes a 
	value of color-blind or color-aware only.
        ALCATEL NOTE:
                 ACCESS:     NA       USAGE:      NA
                 PERSIST:    YES       INSRVMOD:   NO
                 RANGE:      NA      DEFVALUE:   1
                 UNITS:      NA      SPARSE:  NA
                                     DESCR:      NA"
	DEFVAL {1}
::= { qosPolicerProfileEntry 11}

qosPolicerProfileGreenAction OBJECT-TYPE
	SYNTAX INTEGER { pass (1), discard (2)}
	ACCESS read-write
	STATUS mandatory
	DESCRIPTION
	 "This object stores the action for green packet.
	1 - pass
	2 - discard
	ALCATEL NOTE:
                 ACCESS:     NA       USAGE:      NA
                 PERSIST:    YES       INSRVMOD:   NO
                 RANGE:      NA      DEFVALUE:   1
                 UNITS:      NA      SPARSE:     NA
                                     DESCR:      NA"
	DEFVAL {1}
::= { qosPolicerProfileEntry 12}

qosPolicerProfileGreenDot1P OBJECT-TYPE
	SYNTAX INTEGER 
	ACCESS read-write
	STATUS mandatory
	DESCRIPTION
	 "This object stores the dot1p value for green packet.
	ALCATEL NOTE:
                 ACCESS:     NA       USAGE:      NA
                 PERSIST:    YES       INSRVMOD:   NO
                 RANGE:      NA      DEFVALUE:   1
                 UNITS:      NA       SPARSE:     NA
                                     DESCR:      NA"
::= { qosPolicerProfileEntry 13}

qosPolicerProfileGreenDSCP OBJECT-TYPE
	SYNTAX INTEGER 
	ACCESS read-write
	STATUS mandatory
	DESCRIPTION
	 "This object stores the dscp value for green packet.
	ALCATEL NOTE:
                 ACCESS:     NA       USAGE:      NA
                 PERSIST:    YES       INSRVMOD:   NO
                 RANGE:      NA      DEFVALUE:   1
                 UNITS:      NA       SPARSE:     NA
                                     DESCR:      NA"
::= { qosPolicerProfileEntry 14}

qosPolicerProfileYellowAction OBJECT-TYPE
	SYNTAX INTEGER { pass (1), discard (2)}
	ACCESS read-write
	STATUS mandatory
	DESCRIPTION
	 "This object stores the action for yellow packet.
	1 - pass
	2 - discard
        ALCATEL NOTE:
                 ACCESS:     NA       USAGE:      NA
                 PERSIST:    YES       INSRVMOD:   NO
                 RANGE:      NA      DEFVALUE:   1
                 UNITS:      NA      SPARSE:     NA
                                     DESCR:      NA"
	DEFVAL {1}
::= { qosPolicerProfileEntry 15}

qosPolicerProfileYellowDot1P OBJECT-TYPE
	SYNTAX INTEGER 
	ACCESS read-write
	STATUS mandatory
	DESCRIPTION
	 "This object stores the dot1p value for yellow packet.
	ALCATEL NOTE:
                 ACCESS:     NA       USAGE:      NA
                 PERSIST:    YES       INSRVMOD:   NO
                 RANGE:      NA      DEFVALUE:   1
                 UNITS:      NA       SPARSE:     NA
                                     DESCR:      NA"
::= { qosPolicerProfileEntry 16}

qosPolicerProfileYellowDSCP OBJECT-TYPE
	SYNTAX INTEGER 
	ACCESS read-write
	STATUS mandatory
	DESCRIPTION
	 "This object stores the dscp value for yellow packet.
	ALCATEL NOTE:
                 ACCESS:     NA       USAGE:      NA
                 PERSIST:    YES       INSRVMOD:   NO
                 RANGE:      NA      DEFVALUE:   1
                 UNITS:      NA       SPARSE:     NA
                                     DESCR:      NA"
::= { qosPolicerProfileEntry 17}

qosPolicerProfileRedAction OBJECT-TYPE
   SYNTAX INTEGER { pass (1), discard (2)}
   ACCESS read-write
   STATUS mandatory
   DESCRIPTION
    "This object stores the action for red packet.
   In R4.2 only pass and discard are supported
   1 - pass
   2 - discard
   ALCATEL NOTE:
                 ACCESS:     NA       USAGE:      NA
                 PERSIST:    YES       INSRVMOD:   NO
                 RANGE:      NA      DEFVALUE:   1
                 UNITS:      NA      SPARSE:     NA
                                     DESCR:      NA"
   DEFVAL {1}
::= { qosPolicerProfileEntry 18}

qosPolicerProfileRedDot1P OBJECT-TYPE
	SYNTAX INTEGER 
	ACCESS read-write
	STATUS mandatory
	DESCRIPTION
	 "This object stores the dot1p value for red packet.
	ALCATEL NOTE:
                 ACCESS:     NA       USAGE:      NA
                 PERSIST:    YES       INSRVMOD:   NO
                 RANGE:      NA      DEFVALUE:   1
                 UNITS:      NA       SPARSE:     NA
                                     DESCR:      NA"
::= { qosPolicerProfileEntry 19}

qosPolicerProfileRedDSCP OBJECT-TYPE
	SYNTAX INTEGER 
	ACCESS read-write
	STATUS mandatory
	DESCRIPTION
	 "This object stores the dscp value for red packet.
	ALCATEL NOTE:
                 ACCESS:     NA       USAGE:      NA
                 PERSIST:    YES       INSRVMOD:   NO
                 RANGE:      NA      DEFVALUE:   1
                 UNITS:      NA       SPARSE:     NA
                                     DESCR:      NA"
::= { qosPolicerProfileEntry 20}

qosQueueProfileTable OBJECT-TYPE
	SYNTAX	SEQUENCE OF QosQueueProfileEntry
	ACCESS	not-accessible
	STATUS	mandatory
	DESCRIPTION
	"This object contains a table for creating and storing
	queue (Buffer Acceptance Control)profiles.
	A queue profile contains queue buffer admission control
	information for frames arriving to the buffer."
::= {qosProfiles 3 }
qosQueueProfileEntry OBJECT-TYPE
	SYNTAX	QosQueueProfileEntry
	ACCESS	not-accessible
	STATUS	mandatory
	DESCRIPTION
	"This table contains as rows QoS Queue profiles."
	INDEX {qosQueueProfileIndex }
::= { qosQueueProfileTable 1}
QosQueueProfileEntry ::=
     SEQUENCE { qosQueueProfileIndex 		AsamProfileIndex,
		qosQueueProfileName		AsamProfileName,
		qosQueueProfileVersion 	INTEGER,
		qosQueueProfileRefCount	AsamProfileRefCount32,
		qosQueueProfileBacType		INTEGER,
		qosQueueProfileMinThGreen	INTEGER,
		qosQueueProfileMaxThGreen	INTEGER,
		qosQueueProfileMaxPrGreen	INTEGER,
		qosQueueProfileRowStatus 	RowStatus,
		qosQueueProfileMinThYellow 		INTEGER,
		qosQueueProfileMaxThYellow	INTEGER,
		qosQueueProfileMaxPrYellow	INTEGER,
		qosQueueProfileUnit			INTEGER,
		qosQueueProfileMinThRed		INTEGER,
		qosQueueProfileMaxThRed		INTEGER,
		qosQueueProfileMaxPrRed		INTEGER
				}
qosQueueProfileIndex OBJECT-TYPE
	SYNTAX	AsamProfileIndex
	ACCESS	not-accessible
	STATUS mandatory
	DESCRIPTION
	"This object is the key to the queue profile table."
::= { qosQueueProfileEntry 1}
qosQueueProfileName OBJECT-TYPE
	SYNTAX	AsamProfileName
	ACCESS	read-write
	STATUS mandatory
	DESCRIPTION
	"This object stores as an octet string the name of the BAC
	profile given by the operator"
::= { qosQueueProfileEntry 2}
qosQueueProfileVersion OBJECT-TYPE
	SYNTAX	INTEGER
	ACCESS	read-write
	STATUS mandatory
	DESCRIPTION
	"Integer containing the version number of this profile."
::= { qosQueueProfileEntry 3}

qosQueueProfileRefCount OBJECT-TYPE
	SYNTAX	AsamProfileRefCount32
	ACCESS read-only
	STATUS	mandatory
	DESCRIPTION
" Indicates the number of entities using this profile. If the
reference count is not 0, then this profile is 'in use',
and can NOT be deleted. If the value is 0, then this profile is
'not in use', and can be deleted."
::= { qosQueueProfileEntry 4}

qosQueueProfileBacType OBJECT-TYPE
	SYNTAX INTEGER { taildrop (1), red (2),twoColourTaildrop(3),twoColourRed(4), gpon(5),threeColourTaildrop(6),threeColourRed(7)}
	ACCESS read-write
	STATUS mandatory
	DESCRIPTION
	 "The queue profile type encodes a widely known buffer
	acceptance control (BAC) algorithm with an integer value.
	Based on this type the hardware will know how
	to configure the policers, and which
	of the following fields are required.
	The following values are defined:
			1 - Taildrop
			2 - RED (Random Early Detection)
			3 -twoColourTaildrop
			4 -twoColourRed
			5 - gpon
			6 - threeColourTaildrop
			7 - threeColourRed

	Based on this values some fields of this row become
	active or don't care.
	Taildrop (1)only the qosQueueProfileMaxThGreen object is active.
	RED (2)	qosQueueProfileMaxThGreen,
	qosQueueProfileMinThGreen
	qosQueueProfileMaxPrGreen fields are active.
	twoColourTaildrop (3)  qosQueueProfileMaxThGreen and qosQueueProfileMaxThYellow are active.
	twoColourRed(4)  qosQueueProfileMaxThGreen,qosQueueProfileMinThGreen, qosQueueProfileMaxPrGreen, qosQueueProfileMaxThYellow,	qosQueueProfileMinThYellow,
	qosQueueProfileMaxPrYellow fields are active.
        threeColourTaildrop (6)  qosQueueProfileMaxThGreen, qosQueueProfileMaxThYellow and qosQueueProfileMaxThRed are active.
	threeColourRed (7)  qosQueueProfileMaxThGreen, qosQueueProfileMinThGreen, qosQueueProfileMaxPrGreen, qosQueueProfileMaxThYellow, qosQueueProfileMinThYellow, qosQueueProfileMaxPrYellow, qosQueueProfileMaxThRed, qosQueueProfileMinThRed and qosQueueProfileMaxPrRed fields are active.
                  ALCATEL NOTE:
                 ACCESS:     NA       USAGE:      NA
                 PERSIST:    YES       INSRVMOD:   NO
                 RANGE:      NA      DEFVALUE:   NA
                 UNITS:      NA       SPARSE:     NA
                 DESCR:      NA "
::= { qosQueueProfileEntry 5}
qosQueueProfileMinThGreen OBJECT-TYPE
	SYNTAX	INTEGER
	ACCESS	read-write
	STATUS mandatory
	DESCRIPTION
	 "This object stores the minimum threshold value in packets of
	green frames in a RED BAC mechanism, above
	which random discard of green frames is executed. 	
	 The Dot1P value represented by green is defined in 
	qosLimDot1PMappingTable. The value unit is set via qosQueueProfileUnit.
     ALCATEL NOTE:
                 ACCESS:     NA       USAGE:      NA
                 PERSIST:    YES       INSRVMOD:   NO
                 RANGE:      NA       DEFVALUE:   0
                 UNITS:      NA       SPARSE:     NA
                 DESCR:      NA "
::= { qosQueueProfileEntry 6}
qosQueueProfileMaxThGreen OBJECT-TYPE
	SYNTAX	INTEGER
	ACCESS	read-write
	STATUS mandatory
	DESCRIPTION
	 "This object stores the maximum threshold value in packets of
	green frames in a RED mechanism, above
	which deterministic discard of green frames is executed.
	This object is also used as maximum threshold of a simple
	Taildrop queue (in packets) for all frames entering a queue
	 The Dot1P value represented by green is defined in 
	qosLimDot1PMappingTable. The value unit is set via qosQueueProfileUnit.
	
     ALCATEL NOTE:
                 ACCESS:     NA       USAGE:      NA
                 PERSIST:    YES       INSRVMOD:   NO
                 RANGE:      NA       DEFVALUE:   0
                 UNITS:      NA       SPARSE:     NA
                 DESCR:      NA "
::= { qosQueueProfileEntry 7}
qosQueueProfileMaxPrGreen OBJECT-TYPE
	SYNTAX	INTEGER
	ACCESS	read-write
	STATUS mandatory
	DESCRIPTION
	 "This object stores the maximum discard probability
	of green frames in a RED BAC mechanism.
	The probability is defined as a real number between [0..1].
	The MIB represents it as an integer between 0 and 100, and
	The normalization to [0 .. 1]is done by the system.
     ALCATEL NOTE:
                 ACCESS:     NA       USAGE:      NA
                 PERSIST:    YES       INSRVMOD:   NO
                 RANGE:      0..100       DEFVALUE:   0
                 UNITS:     %       SPARSE:     NA
                 DESCR:      NA. "
::= { qosQueueProfileEntry 8}
qosQueueProfileRowStatus OBJECT-TYPE
	SYNTAX	RowStatus
	ACCESS	read-write
	STATUS mandatory
	DESCRIPTION
"This object is used to create a new row or modify or
delete an existing row in this table. The usage is as per
standard semantics of 'RowStatus' defined in SNMPv2-TC, with
following limitations:
o The entry associated with a Profile that is being used may
not be deleted.
     ALCATEL NOTE:
                 ACCESS:     NA       USAGE:      NA
                 PERSIST:    YES       INSRVMOD:   NO
                 RANGE:      1,4,6       DEFVALUE:   0
                 UNITS:      NA       SPARSE:     NA
                 DESCR:      NA. "
::= {qosQueueProfileEntry 9}
qosQueueProfileMinThYellow OBJECT-TYPE
	SYNTAX	INTEGER
	ACCESS	read-write
	STATUS mandatory
	DESCRIPTION
	 "This object stores the minimum threshold value of
	yellow frames in a RED BAC mechanism, above
	which random discard of yellow frames is executed. The Dot1P value represented by yellow is defined in qosLimDot1PMappingTable. The value unit is set via qosQueueProfileUnit. 
      ALCATEL NOTE:
                 ACCESS:     NA       USAGE:      NA
                 PERSIST:    YES       INSRVMOD:   NO
                 RANGE:      NA        DEFVALUE:   NA
                 UNITS:      NA       SPARSE:     NA
                 DESCR:     This parameter is optional when the queue profile is color-unware type: Red or taildrop. The value  always is 0 whatever the manager input or not. When the queue profile type is color-aware, this parameter is mandantory. "
::= { qosQueueProfileEntry 10}

qosQueueProfileMaxThYellow OBJECT-TYPE
	SYNTAX	INTEGER
	ACCESS	read-write
	STATUS mandatory
	DESCRIPTION
	 "This object stores the maximum threshold value in packets of
	yellow frames in a RED mechanism, above
	which deterministic discard of yellow frames is executed.
	This object is also used as maximum threshold of a simple
	Taildrop queue (in packets) for yellow frames entering a queue. The Dot1P value represented by yellow is defined in qosLimDot1PMappingTable. The value unit is set via qosQueueProfileUnit.
      ALCATEL NOTE:
                 ACCESS:     NA       USAGE:      NA
                 PERSIST:    YES       INSRVMOD:   NO
                 RANGE:      NA       DEFVALUE:   0
                 UNITS:      NA       SPARSE:     NA
                 DESCR:      This parameter is optional when the queue profile is color-unware type: Red or taildrop. The value  always is 0 whatever the manager input or not. When the queue profile type is color-aware, this parameter is mandantory."
::= { qosQueueProfileEntry 11}

qosQueueProfileMaxPrYellow OBJECT-TYPE
	SYNTAX	INTEGER
	ACCESS	read-write
	STATUS mandatory
	DESCRIPTION
	 "This object stores the maximum discard probability
	of yellow frames in a RED BAC mechanism.
	The probability is defined as a real number between [0..1].
	The MIB represents it as an integer between 0 and 100, and
	The normalization to [0 .. 1]is done by the system. The Dot1P value represented by yellow is defined in qosLimDot1PMappingTable.
      ALCATEL NOTE:
                 ACCESS:     NA       USAGE:      NA
                 PERSIST:    YES       INSRVMOD:   NO
                 RANGE:      NA       DEFVALUE:   0
                 UNITS:      NA       SPARSE:     NA
                 DESCR:      This parameter is optional when the queue profile is color-unware type: Red or taildrop. The value  always is 0 whatever the manager input or not. When the queue profile type is color-aware, this parameter is mandantory."
::= { qosQueueProfileEntry 12}

qosQueueProfileUnit OBJECT-TYPE
	SYNTAX	INTEGER(0..1)
	ACCESS	read-write
	STATUS mandatory
	DESCRIPTION
	 "This object identify the unit of the maximum discard threshold and minimum discard threshold. It can be packet (0) or byte(1).
      ALCATEL NOTE:
                 ACCESS:     NA       USAGE:      NA
                 PERSIST:    YES       INSRVMOD:   NO
                 RANGE:      NA       DEFVALUE:   NA
                 UNITS:      NA       SPARSE:     NA
                 DESCR:      NA "
	DEFVAL {0}
::= { qosQueueProfileEntry 13}

qosQueueProfileMinThRed OBJECT-TYPE
	SYNTAX	INTEGER
	ACCESS	read-write
	STATUS mandatory
	DESCRIPTION
	 "This object stores the minimum threshold value of
	red frames in a RED BAC mechanism, above
	which random discard of red frames is executed. The Dot1P value represented by red is defined in qosLimDot1PMappingTable. The value unit is set via qosQueueProfileUnit. 
      ALCATEL NOTE:
                 ACCESS:     NA       USAGE:      NA
                 PERSIST:    YES       INSRVMOD:   NO
                 RANGE:      NA        DEFVALUE:   0
                 UNITS:      NA       SPARSE:     NA
                 DESCR:     This parameter is optional when the queue profile is color-unware type: Red or taildrop. The value  always is 0 whatever the manager input or not. When the queue profile type is color-aware, this parameter is mandantory. "
::= { qosQueueProfileEntry 14}

qosQueueProfileMaxThRed OBJECT-TYPE
	SYNTAX	INTEGER
	ACCESS	read-write
	STATUS mandatory
	DESCRIPTION
	 "This object stores the maximum threshold value in packets of
	red frames in a RED mechanism, above
	which deterministic discard of red frames is executed.
	This object is also used as maximum threshold of a simple
	Taildrop queue (in packets) for red frames entering a queue. The Dot1P value represented by red is defined in qosLimDot1PMappingTable. The value unit is set via qosQueueProfileUnit.
      ALCATEL NOTE:
                 ACCESS:     NA       USAGE:      NA
                 PERSIST:    YES       INSRVMOD:   NO
                 RANGE:      NA       DEFVALUE:   0
                 UNITS:      NA       SPARSE:     NA
                 DESCR:      This parameter is optional when the queue profile is color-unware type: Red or taildrop. The value  always is 0 whatever the manager input or not. When the queue profile type is color-aware, this parameter is mandantory."
::= { qosQueueProfileEntry 15}

qosQueueProfileMaxPrRed OBJECT-TYPE
	SYNTAX	INTEGER
	ACCESS	read-write
	STATUS mandatory
	DESCRIPTION
	 "This object stores the maximum discard probability
	of red frames in a RED BAC mechanism.
	The probability is defined as a real number between [0..1].
	The MIB represents it as an integer between 0 and 100, and
	The normalization to [0 .. 1]is done by the system. The Dot1P value represented by red is defined in qosLimDot1PMappingTable.
      ALCATEL NOTE:
                 ACCESS:     NA       USAGE:      NA
                 PERSIST:    YES       INSRVMOD:   NO
                 RANGE:      NA       DEFVALUE:   0
                 UNITS:      NA       SPARSE:     NA
                 DESCR:      This parameter is optional when the queue profile is color-unware type: Red or taildrop. The value  always is 0 whatever the manager input or not. When the queue profile type is color-aware, this parameter is mandantory."
::= { qosQueueProfileEntry 16}

qosSchedulerProfileTable OBJECT-TYPE
	SYNTAX	SEQUENCE OF QosSchedulerProfileEntry
	ACCESS	not-accessible
	STATUS	mandatory
	DESCRIPTION
	"This object contains a table for creating and storing DSL
link scheduler profiles. A scheduler profile contains settings
for the WFQ scheduler of the DSL scheduler.
Presently only the weight of Queue1 can be set, while the
weight for Queue0 is auto-adjusted."
::= { qosProfiles 4 }
qosSchedulerProfileEntry OBJECT-TYPE
	SYNTAX QosSchedulerProfileEntry
	ACCESS	not-accessible
	STATUS mandatory
	DESCRIPTION
	"This table contains as row QoS Scheduler Profiles"
	INDEX {qosSchedulerProfileIndex}
::= {qosSchedulerProfileTable 1}
QosSchedulerProfileEntry 	::=
     SEQUENCE { qosSchedulerProfileIndex		AsamProfileIndex ,
		qosSchedulerProfileName			AsamProfileName,
		qosSchedulerProfileVersion 		INTEGER,
		qosSchedulerProfileRefCount		AsamProfileRefCount32,
		qosSchedulerProfileWfqQ1Weight		INTEGER,
		qosSchedulerProfileRowStatus 		RowStatus	
				}
qosSchedulerProfileIndex OBJECT-TYPE
	SYNTAX	AsamProfileIndex
	ACCESS	not-accessible
	STATUS mandatory
	DESCRIPTION
	"This object is the key in the Scheduler Profile table"
::= { qosSchedulerProfileEntry 1}
qosSchedulerProfileName OBJECT-TYPE
	SYNTAX	AsamProfileName
	ACCESS	read-write
	STATUS mandatory
	DESCRIPTION
	"This object stores as an octet string the name of the
Scheduler profile given by the operator."
::= {qosSchedulerProfileEntry 2}
qosSchedulerProfileVersion OBJECT-TYPE
	SYNTAX	INTEGER
	ACCESS	read-write
	STATUS mandatory
	DESCRIPTION
	"Integer containing the version number of this profile."
::= { qosSchedulerProfileEntry 3}
qosSchedulerProfileRefCount OBJECT-TYPE
	SYNTAX	AsamProfileRefCount32
	ACCESS read-only
	STATUS	mandatory
	DESCRIPTION
	" Indicates the number of entities using this profile. If the
reference count is greater than 0, then this profile is 'in use',
and may NOT be deleted. If the value is 0, then this profile is
'not in use', and can be deleted."
::= { qosSchedulerProfileEntry 4}

qosSchedulerProfileWfqQ1Weight OBJECT-TYPE
	SYNTAX	INTEGER
	ACCESS	read-write
	STATUS mandatory
	DESCRIPTION
	 "This object stores the weight of the DSL link WFQ scheduler for 
	Queue 1. It stores it as an Integer with values
	between 0 and 100. The weight of Queue0 is auto-adjusted
	such that the sum of the two is always 100"
::= {qosSchedulerProfileEntry 5}
qosSchedulerProfileRowStatus OBJECT-TYPE
	SYNTAX	RowStatus
	ACCESS	read-write
	STATUS mandatory
	DESCRIPTION
	"This object is used to create a new row or modify or
delete an existing row in this table. The usage is as per
standard semantics of 'RowStatus' defined in SNMPv2-TC, with
following limitations:
o The entry associated with a Profile that is being used may
not be deleted."
::= {qosSchedulerProfileEntry 6}

qosCacProfileTable OBJECT-TYPE
	SYNTAX	SEQUENCE OF QosCacProfileEntry
	ACCESS	not-accessible
	STATUS	mandatory
	DESCRIPTION
	"This object contains a table for creating and storing
	CAC (Connection Admission Control)profiles.
	A CAC profile contains rate parameters for:
the maximum allowed bandwidth for voice
the maximum allowed bandwidth for multicast video
the minimum reserved bandwidth for data traffic
The scope of a CAC profile is a DSL interface, downstream. "
::= { qosProfiles 5 }
qosCacProfileEntry OBJECT-TYPE
	SYNTAX QosCacProfileEntry
	ACCESS not-accessible
	STATUS mandatory
	DESCRIPTION
	"This table contains as rows QoS CAC Profiles."
	INDEX {qosCacProfileIndex }
::= {qosCacProfileTable 1}
QosCacProfileEntry ::=
	SEQUENCE { qosCacProfileIndex 		AsamProfileIndex ,
		qosCacProfileName		AsamProfileName,
		qosCacProfileVersion 		INTEGER,
		qosCacProfileRefCount		AsamProfileRefCount32,
		qosCacProfileResVoiceBw		INTEGER,
		qosCacProfileMaxMcastBw		INTEGER,
		qosCacProfileResDataBw		INTEGER,
		qosCacProfileRowStatus 		RowStatus,
		qosCacProfileType 		             INTEGER
	
				}
qosCacProfileIndex OBJECT-TYPE
	SYNTAX	AsamProfileIndex
	ACCESS	not-accessible
	STATUS mandatory
	DESCRIPTION
		"This object is the index in the CAC Profile table"
::= { qosCacProfileEntry 1}
qosCacProfileName OBJECT-TYPE
	SYNTAX	AsamProfileName
	ACCESS	read-write
	STATUS mandatory
	DESCRIPTION
		"This object stores as an octet string the name of the CAC
		 (Connection Admission Control) profile."
::= {qosCacProfileEntry 2}
qosCacProfileVersion OBJECT-TYPE
	SYNTAX	INTEGER
	ACCESS	read-write
	STATUS mandatory
	DESCRIPTION
		"Integer containing the version number of this profile."
::= { qosCacProfileEntry 3}
qosCacProfileRefCount OBJECT-TYPE
	SYNTAX	AsamProfileRefCount32
	ACCESS read-only
	STATUS	mandatory
	DESCRIPTION
	" Indicates the number of entities using this profile. If the
reference count is greater than 0, then this profile is 'in use',
and may NOT be deleted. If the value is 0, then this profile is
'not in use', and can be deleted."
::= { qosCacProfileEntry 4}

qosCacProfileResVoiceBw OBJECT-TYPE
	SYNTAX	INTEGER
	ACCESS	read-write
	STATUS mandatory
	DESCRIPTION
	 "This object stores the reserved bandwidth for the Voice service
	or services as an INTEGER in Kilobits/sec. Voice has the highest
	priority in the system. The reservation is such that in the
	absence of Voice traffic, data traffic can re-use this bandwidth.
	The scope of the reservation is one DSL link.
	There is no awareness of the number of voice sessions. This
	Object stores the bandwidth necessary to support all the voice
	Sessions that are contractually agreed for on one DSL link"
::= {qosCacProfileEntry 5}
qosCacProfileMaxMcastBw OBJECT-TYPE
	SYNTAX	INTEGER
	ACCESS	read-write
	STATUS mandatory
	DESCRIPTION
	"This object stores the maximum allowed bandwidth
	for the Multicast Video service as an INTEGER in
	Kilobits/sec. Upon a new IGMP join the CAC entity
	will check the available bandwidth on the DSL
	link against the bandwidth of the requested multicast
	video stream. The currently used multicast bandwidth is stored
	in the DSL record table qosDslRecordUsedMcastBw object.
	The actual check is executed against the smaller value
	of the qosCacProfileMaxMcastBw and
	qosDslRecordAvailableMcastBw, where
	qosDslRecordAvailableMcastBw is automatically calculated
	as the guaranteed frame bandwidth of the DSL link minus
	the provisioned bandwidths for Voice and Data services.
	Multicast CAC is executed only for known multicast streams.
	Known multicast streams are configured in the IGMP MIB."
::= { qosCacProfileEntry 6}
qosCacProfileResDataBw OBJECT-TYPE
	SYNTAX	INTEGER
	ACCESS	read-write
	STATUS mandatory
	DESCRIPTION
	"This object stores the reserved bandwidth for all
	data services on a DSL link in Kilobits/sec
	(always positive or null). It is useful in case
	the intention is to guarantee a minimum bandwidth
	for data services in case there is no hard-bound
	limitation intended for multicast services.
	This way a specified minimum is always reserved
	for data traffic."
::= { qosCacProfileEntry 7}
qosCacProfileRowStatus OBJECT-TYPE
	SYNTAX	RowStatus
	ACCESS	read-write
	STATUS mandatory
	DESCRIPTION
	"This object is used to create a new row or modify or
delete an existing row in this table. The usage is as per
standard semantics of 'RowStatus' defined in SNMPv2-TC, with
following limitations:
o The entry associated with a Profile that is being used may
not be deleted."
::= {qosCacProfileEntry 8}

qosCacProfileType OBJECT-TYPE
	SYNTAX	INTEGER (1..2)
	ACCESS	read-write
	STATUS mandatory
	DESCRIPTION
	"This object is used to indicate whether the profile applies to DSL lines or to PON interfaces. By default the profile applies to DSL lines for backward compatibility. Value 1 = DSL and value 2 = PON interface. If the value = 2 (PON), only the qosCacProfileMaxMcastBw  is used from this table and other parameters such as Voice BW and data BW will be ignored. This profile will be applied to UNI and PON levels. The default is 1, DSL."
	DEFVAL {1}

::= {qosCacProfileEntry 9}

qosMarkerProfileMappingTable OBJECT-TYPE
	SYNTAX	SEQUENCE OF QosMarkerProfileMappingEntry
	ACCESS	not-accessible
	STATUS	mandatory
	DESCRIPTION
	"This object contains a table for qosMarkerProfile name
to index mapping"
::= { qosProfiles 6 }

qosMarkerProfileMappingEntry OBJECT-TYPE
	SYNTAX 	QosMarkerProfileMappingEntry
	ACCESS	not-accessible
	STATUS mandatory
	DESCRIPTION
	" An entry (conceptual row) representing the qos Marker
Profile Name to Index mapping. The system automatically creates an
entry in this Table for each corresponding entry (qosMarker-profile)
created in the qosMarkerProfileTable.  Similarly, when an
qosMarkerprofile is deleted, the corresponding entry in this table is also
automatically deleted by thesystem."
	INDEX	{qosMarkerProfileMappingName }
	::= {qosMarkerProfileMappingTable  1}

QosMarkerProfileMappingEntry ::=
	SEQUENCE { qosMarkerProfileMappingName 	AsamProfileName,
		   qosMarkerProfileMappingIndex AsamProfileIndex
		 }

qosMarkerProfileMappingName OBJECT-TYPE
	SYNTAX	AsamProfileName
	ACCESS	not-accessible
	STATUS  mandatory
	DESCRIPTION
		"A text string containing the name of
		this profile"
::= { qosMarkerProfileMappingEntry 1}

qosMarkerProfileMappingIndex OBJECT-TYPE
	SYNTAX	AsamProfileIndex
	ACCESS	read-write
	STATUS mandatory
	DESCRIPTION
		"This object is the Profile index."
::= { qosMarkerProfileMappingEntry 2}

qosPolicerProfileMappingTable OBJECT-TYPE
	SYNTAX	SEQUENCE OF QosPolicerProfileMappingEntry
	ACCESS	not-accessible
	STATUS	mandatory
	DESCRIPTION
	"This object contains a table for qosPolicerProfile
name to index mapping"
::= { qosProfiles 7 }

qosPolicerProfileMappingEntry OBJECT-TYPE
	SYNTAX 	QosPolicerProfileMappingEntry
	ACCESS	not-accessible
	STATUS mandatory
	DESCRIPTION
	" An entry (conceptual row) representing the qos
Policer Profile Name to Index mapping. The system automatically creates an
entry in this Table for each corresponding entry (qosPolicer-profile) 
created in the qosPolicerProfileTable.  Similarly, when an
qosPolicerprofile is deleted, the corresponding entry in this table is also
automatically deleted by the system."
	INDEX	{qosPolicerProfileMappingName }
	::= {qosPolicerProfileMappingTable  1}

QosPolicerProfileMappingEntry ::=
	SEQUENCE { qosPolicerProfileMappingName AsamProfileName,
		   qosPolicerProfileMappingIndex AsamProfileIndex
			}

qosPolicerProfileMappingName OBJECT-TYPE
	SYNTAX	AsamProfileName
	ACCESS	not-accessible
	STATUS  mandatory
	DESCRIPTION
		"A text string containing the name of
		this profile"
::= { qosPolicerProfileMappingEntry 1}

qosPolicerProfileMappingIndex OBJECT-TYPE
	SYNTAX	AsamProfileIndex
	ACCESS	read-write
	STATUS mandatory
	DESCRIPTION
		"This object is the Profile index."
::= { qosPolicerProfileMappingEntry 2}

qosQueueProfileMappingTable OBJECT-TYPE
	SYNTAX	SEQUENCE OF QosQueueProfileMappingEntry
	ACCESS	not-accessible
	STATUS	mandatory
	DESCRIPTION
	"This object contains a table for qosQueueProfile name
to index mapping"
        ::= { qosProfiles 8 }

qosQueueProfileMappingEntry OBJECT-TYPE
	SYNTAX 	QosQueueProfileMappingEntry
	ACCESS	not-accessible
	STATUS mandatory
	DESCRIPTION
	" An entry (conceptual row) representing the qos Queue
Profile Name to Index mapping. The system automatically creates an
entry in this Table for each corresponding entry (qosQueue-profile)
created in the qosQueueProfileTable.  Similarly, when an
qosQueueprofile is deleted, the corresponding entry in this table is also
automatically deleted by the system."
	INDEX	{qosQueueProfileMappingName}
	::= {qosQueueProfileMappingTable  1}

QosQueueProfileMappingEntry ::=
	SEQUENCE { qosQueueProfileMappingName 	AsamProfileName,
		   qosQueueProfileMappingIndex 	AsamProfileIndex
		 }

qosQueueProfileMappingName OBJECT-TYPE
	SYNTAX	AsamProfileName
	ACCESS	not-accessible
	STATUS  mandatory
	DESCRIPTION
		"A text string containing the name of
		this profile"
        ::= { qosQueueProfileMappingEntry 1}

qosQueueProfileMappingIndex OBJECT-TYPE
        SYNTAX	AsamProfileIndex
	ACCESS	read-write
	STATUS mandatory
	DESCRIPTION
		"This object is the Profile index."
        ::= { qosQueueProfileMappingEntry 2}

qosSchedulerProfileMappingTable OBJECT-TYPE
	SYNTAX	SEQUENCE OF QosSchedulerProfileMappingEntry
	ACCESS	not-accessible
	STATUS	mandatory
	DESCRIPTION
	"This object contains a table for qosSchedulerProfile
name to index mapping"
::= { qosProfiles 9 }

qosSchedulerProfileMappingEntry OBJECT-TYPE
	SYNTAX 	QosSchedulerProfileMappingEntry
	ACCESS	not-accessible
	STATUS mandatory
	DESCRIPTION
	" An entry (conceptual row) representing the qos
Scheduler Profile Name to Index mapping. The system automatically creates an
entry in this Table for each corresponding entry (qosScheduler-profile) created
in the qosSchedulerProfileTable. Similarly, when an qosSchedulerprofile is 
deleted, them corresponding entry in this table is also automatically deleted
 by the system."
	INDEX	{qosSchedulerProfileMappingName }
	::= {qosSchedulerProfileMappingTable  1}

QosSchedulerProfileMappingEntry ::=
	SEQUENCE { qosSchedulerProfileMappingName AsamProfileName,
		   qosSchedulerProfileMappingIndex AsamProfileIndex
			}

qosSchedulerProfileMappingName OBJECT-TYPE
	SYNTAX	AsamProfileName
	ACCESS	not-accessible
	STATUS  mandatory
	DESCRIPTION
		"A text string containing the name of
		this profile"
::= { qosSchedulerProfileMappingEntry 1}

qosSchedulerProfileMappingIndex OBJECT-TYPE
	SYNTAX	AsamProfileIndex
	ACCESS	read-write
	STATUS mandatory
	DESCRIPTION
		"This object is the Profile index."
::= { qosSchedulerProfileMappingEntry 2}

qosCacProfileMappingTable OBJECT-TYPE
	SYNTAX	SEQUENCE OF QosCacProfileMappingEntry
	ACCESS	not-accessible
	STATUS	mandatory
	DESCRIPTION
	"This object contains a table for qosCacProfile name to
index mapping"
::= { qosProfiles 10 }

qosCacProfileMappingEntry OBJECT-TYPE
	SYNTAX 	QosCacProfileMappingEntry
	ACCESS	not-accessible
	STATUS mandatory
	DESCRIPTION
	" An entry (conceptual row) representing the qos Cac
Profile Name to Index mapping. The system automatically creates an
entry in this Table for each corresponding entry (qosCac-profile) created
in the qosCacProfileTable. Similarly, when an qosCacprofile is deleted, the
corresponding entry in this table is also automatically deleted by the 
system."
	INDEX	{qosCacProfileMappingName }
	::= {qosCacProfileMappingTable  1}

QosCacProfileMappingEntry ::=
	SEQUENCE { qosCacProfileMappingName 	AsamProfileName,
		   qosCacProfileMappingIndex 	AsamProfileIndex
			}

qosCacProfileMappingName OBJECT-TYPE
	SYNTAX	AsamProfileName
	ACCESS	not-accessible
	STATUS  mandatory
	DESCRIPTION
		"A text string containing the name of
		this profile"
::= { qosCacProfileMappingEntry 1}

qosCacProfileMappingIndex OBJECT-TYPE
	SYNTAX	AsamProfileIndex
	ACCESS	read-write
	STATUS mandatory
	DESCRIPTION
		"This object is the Profile index."
::= { qosCacProfileMappingEntry 2}

qosPolicyTableMappingTable OBJECT-TYPE
	SYNTAX	SEQUENCE OF QosPolicyTableMappingEntry
	ACCESS	not-accessible
	STATUS	mandatory
	DESCRIPTION
	"This object contains a table for qosPolicyTable name
to index mapping"
::= { qosProfiles 11 }

qosPolicyTableMappingEntry OBJECT-TYPE
	SYNTAX 	QosPolicyTableMappingEntry
	ACCESS	not-accessible
	STATUS mandatory
	DESCRIPTION
	" An entry (conceptual row) representing the qos Policy Table Name to
Index mapping. The system automatically creates an entry in this Table for each
corresponding entry (qosPolicyEntry) created in the qosPolicyTable.  Similarly,
when an qosPolicyEntry is deleted, the corresponding entry in this table is
also automatically deleted by the system."
	INDEX	{qosPolicyTableMappingName }
	::= {qosPolicyTableMappingTable  1}

QosPolicyTableMappingEntry ::=
SEQUENCE { qosPolicyTableMappingName 			AsamProfileName,
           qosPolicyTableMappingIndex 			AsamProfileIndex
		}

qosPolicyTableMappingName OBJECT-TYPE
	SYNTAX	AsamProfileName
	ACCESS	not-accessible
	STATUS  mandatory
	DESCRIPTION
	"A text string containing the name of
	this profile"
::= { qosPolicyTableMappingEntry 1}

qosPolicyTableMappingIndex OBJECT-TYPE
	SYNTAX	AsamProfileIndex
	ACCESS	read-only
	STATUS mandatory
	DESCRIPTION
	"This object is the Profile index."
::= { qosPolicyTableMappingEntry 2}

qosL2FilterTableMappingTable OBJECT-TYPE
	SYNTAX	SEQUENCE OF QosL2FilterTableMappingEntry
	ACCESS	not-accessible
	STATUS	mandatory
	DESCRIPTION
	"This object contains a table for qosL2FilterTable name
to index mapping"
::= { qosProfiles 12 }

qosL2FilterTableMappingEntry OBJECT-TYPE
	SYNTAX 	QosL2FilterTableMappingEntry
	ACCESS	not-accessible
	STATUS mandatory
	DESCRIPTION
	" An entry (conceptual row) representing the qos L2
Filter Table Name to Index mapping. The system automatically creates an entry
in this Table for each corresponding entry (qosL2FilterEntry) created in the
qosL2FilterTable.  Similarly, when an qosL2FilterEntry is deleted, the
corresponding entry in this table is also automatically deleted by the system."
	INDEX	{qosL2FilterTableMappingName }
	::= {qosL2FilterTableMappingTable  1}

QosL2FilterTableMappingEntry ::=
SEQUENCE { qosL2FilterTableMappingName 		AsamProfileName,
           qosL2FilterTableMappingIndex 	AsamProfileIndex
			}

qosL2FilterTableMappingName OBJECT-TYPE
	SYNTAX	AsamProfileName
	ACCESS	not-accessible
	STATUS  mandatory
	DESCRIPTION
		"A text string containing the name of
		this profile"
::= { qosL2FilterTableMappingEntry 1}

qosL2FilterTableMappingIndex OBJECT-TYPE
	SYNTAX	AsamProfileIndex
	ACCESS	read-only
	STATUS mandatory
	DESCRIPTION
		"This object is the Profile index."
::= { qosL2FilterTableMappingEntry 2}

qosL3FilterTableMappingTable OBJECT-TYPE
	SYNTAX	SEQUENCE OF QosL3FilterTableMappingEntry
	ACCESS	not-accessible
	STATUS	mandatory
	DESCRIPTION
	"This object contains a table for qosL3FilterTable name
to index mapping"
::= { qosProfiles 13 }

qosL3FilterTableMappingEntry OBJECT-TYPE
	SYNTAX 	QosL3FilterTableMappingEntry
	ACCESS	not-accessible
	STATUS mandatory
	DESCRIPTION
	" An entry (conceptual row) representing the qos L3
Filter Table Name to Index mapping. The system automatically creates an entry
in this Table for each corresponding entry (qosL3FilterEntry) created in the
qosL3FilterTable.  Similarly, when an qosL3FilterEntry is deleted, the
corresponding entry in this table is also automatically deleted by the system."
	INDEX	{qosL3FilterTableMappingName }
	::= {qosL3FilterTableMappingTable  1}

QosL3FilterTableMappingEntry ::=
SEQUENCE { qosL3FilterTableMappingName 			AsamProfileName,
           qosL3FilterTableMappingIndex 		AsamProfileIndex
			}

qosL3FilterTableMappingName OBJECT-TYPE
	SYNTAX	AsamProfileName
	ACCESS	not-accessible
	STATUS  mandatory
	DESCRIPTION
		"A text string containing the name of
		this profile"
::= { qosL3FilterTableMappingEntry 1}

qosL3FilterTableMappingIndex OBJECT-TYPE
	SYNTAX	AsamProfileIndex
	ACCESS	read-only
	STATUS mandatory
	DESCRIPTION
		"This object is the Profile index."
::= { qosL3FilterTableMappingEntry 2}

qosPolicyActionTableMappingTable OBJECT-TYPE
	SYNTAX	SEQUENCE OF QosPolicyActionTableMappingEntry
	ACCESS	not-accessible
	STATUS	mandatory
	DESCRIPTION
			"This object contains a table for qosPolicyActionTable
name to index mapping"
::= { qosProfiles 14 }

qosPolicyActionTableMappingEntry OBJECT-TYPE
	SYNTAX 	QosPolicyActionTableMappingEntry
	ACCESS	not-accessible
	STATUS mandatory
	DESCRIPTION
	" An entry (conceptual row) representing the qos Policy
Action Table Name to Index mapping. The system automatically creates an entry
in this Table for each corresponding entry (qosPolicyActionEntry) created in
the qosPolicyActionTable.  Similarly, when an qosPolicyActionEntry is deleted,
the corresponding entry in this table is also automatically deleted by the
system."
	INDEX	{qosPolicyActionTableMappingName }
	::= {qosPolicyActionTableMappingTable  1}

QosPolicyActionTableMappingEntry ::=
	SEQUENCE { qosPolicyActionTableMappingName 		AsamProfileName,
		   qosPolicyActionTableMappingIndex 		AsamProfileIndex
			}

qosPolicyActionTableMappingName OBJECT-TYPE
	SYNTAX	AsamProfileName
	ACCESS	not-accessible
	STATUS  mandatory
	DESCRIPTION
	"A text string containing the name of
	this profile"
::= { qosPolicyActionTableMappingEntry 1}

qosPolicyActionTableMappingIndex OBJECT-TYPE
	SYNTAX	AsamProfileIndex
	ACCESS	read-only
	STATUS mandatory
	DESCRIPTION
	"This object is the Profile index."
::= { qosPolicyActionTableMappingEntry 2}

qosPolicyTable OBJECT-TYPE
	SYNTAX	SEQUENCE OF QosPolicyEntry
	ACCESS	not-accessible
	STATUS	mandatory
	DESCRIPTION
	"This object contains a table for creating and storing
	QoS Policy Rules. A QoS Policy rule contains:
-	L2 or L3 filter pointer for sub-flow classifier
-	Policy Action pointer for QoS policy actions
These two pointer can be L2/L3 filter Index and Policy Action Index. "
::= { qosProfiles 15  }

qosPolicyEntry OBJECT-TYPE
	SYNTAX QosPolicyEntry
	ACCESS not-accessible
	STATUS mandatory
	DESCRIPTION
		"This table contains as rows QoS Policy rules."
	INDEX {qosPolicyIndex }
::= {qosPolicyTable 1}

QosPolicyEntry ::=
     SEQUENCE { qosPolicyIndex 		AsamProfileIndex ,
		qosPolicyName		AsamProfileName,
		qosPolicyVersion 	INTEGER,
		qosPolicyRefCount	AsamProfileRefCount32,
                qosPolicyFilterType	INTEGER,
		qosPolicyFilterId	AsamProfilePointer,
		qosPolicyActions	AsamProfilePointer,
		qosPolicyPrecedence	INTEGER,
		qosPolicyRowStatus 	RowStatus	
				}

qosPolicyIndex OBJECT-TYPE
	SYNTAX	AsamProfileIndex
	ACCESS	not-accessible
	STATUS  mandatory
	DESCRIPTION
		"This object is the index in the QoS Policy table"
::= { qosPolicyEntry 1}

qosPolicyName OBJECT-TYPE
	SYNTAX	AsamProfileName
	ACCESS	read-write
	STATUS  mandatory
	DESCRIPTION
"This object stores as an octet string the name of the Policy rule."
::= {qosPolicyEntry 2}

qosPolicyVersion OBJECT-TYPE
	SYNTAX	INTEGER
	ACCESS	read-write
	STATUS  mandatory
	DESCRIPTION
		"Integer containing the version number of this profile."
::= { qosPolicyEntry 3}

qosPolicyRefCount OBJECT-TYPE
	SYNTAX	AsamProfileRefCount32
	ACCESS read-only
	STATUS	mandatory
	DESCRIPTION
		" Indicates the number of entities using this profile. If the
          reference count is greater than 0, then this profile is 'in use',
          and may NOT be deleted. If the value is 0, then this profile is
          'not in use', and can be deleted."
::= { qosPolicyEntry 4}

qosPolicyFilterType OBJECT-TYPE
	SYNTAX	INTEGER {
				l2filter (1),
				l3filter (2)
			}

	ACCESS	read-write
	STATUS  mandatory
	DESCRIPTION
"This object stores the filter type of this policy rule. Value 1 means
qosPolicyFilterId refer to a L2 filter, value 2 means qosPolicyFilterId refer
to a L3 filter."
::= {qosPolicyEntry 5}

qosPolicyFilterId OBJECT-TYPE
	SYNTAX	AsamProfilePointer
	ACCESS	read-write
	STATUS  mandatory
	DESCRIPTION
	    "This object stores the object identifier of a filter id. The value
can refer to one of L2FilterIndex or L3FilterIndex. SW will deal with such
conversion between the operator input and the internal OBJECT IDENTIFIER. "
::= {qosPolicyEntry 6}

qosPolicyActions OBJECT-TYPE
	SYNTAX	AsamProfilePointer
	ACCESS	read-write
	STATUS  mandatory
	DESCRIPTION
	"This object stores the QoS Policy Action id as an INTEGER(0,65535).
The value can be one of qosPolicyActionIndex. Value 0 means no Policy Action Id
configured."
::= { qosPolicyEntry 7}

qosPolicyPrecedence OBJECT-TYPE
	SYNTAX	INTEGER (0..255)
	ACCESS	read-write
	STATUS  mandatory
	DESCRIPTION
		"This object stores precedence value of this policy rule. Value
255 is highest priority. The policy with higher priority configured in specific
interface and direction will be firstly executed. Policy rules on the same
interface and direction with same precedence value will be executed according
to operator's configuration order."
	DEFVAL		{10}
::= { qosPolicyEntry 8}

qosPolicyRowStatus OBJECT-TYPE
	SYNTAX	RowStatus
	ACCESS	read-write
	STATUS  mandatory
	DESCRIPTION
	"This object is used to create a new row or modify or
         delete an existing row in this table. The usage is as per
         standard semantics of 'RowStatus' defined in SNMPv2-TC, with
         following limitations:
         The entry associated with a Profile that is being used may
         not be deleted."
::= {qosPolicyEntry 9}

qosL2FilterTable OBJECT-TYPE
	SYNTAX	SEQUENCE OF QosL2FilterEntry
	ACCESS	not-accessible
	STATUS	mandatory
	DESCRIPTION
	"This object contains a table for creating and storing
	QoS L2 Filters.
	A QoS L2 Filter contains:
-	MAC destination address
-	MAC destination address prefix
-	MAC source address
-	MAC source address prefix
-	Ethtype, Ethernet type
-	Dot1P, 802.1p priority value, range from 0 to 7.
-	CFI
-	VLAN ID value. "
::= { qosProfiles 16  }

qosL2FilterEntry OBJECT-TYPE
	SYNTAX QosL2FilterEntry
	ACCESS not-accessible
	STATUS mandatory
	DESCRIPTION
	"This table contains as rows QoS L2 filters."
	INDEX {qosL2FilterIndex }
::= {qosL2FilterTable 1}

QosL2FilterEntry ::=
     SEQUENCE { qosL2FilterIndex 		AsamProfileIndex ,
		qosL2FilterName			AsamProfileName,
		qosL2FilterRowStatus 		RowStatus,
		qosL2FilterRefCount		AsamProfileRefCount32,
		qosL2FilterMacDa		MacAddress,
		qosL2FilterMacDaPrefix		Gauge,
		qosL2FilterMacSa		MacAddress,
		qosL2FilterMacSaPrefix		Gauge,
		qosL2FilterEthtype		INTEGER,
		qosL2FilterDot1P		INTEGER,
		qosL2FilterCFI			INTEGER,
		qosL2FilterVlanId		INTEGER
				}

qosL2FilterIndex OBJECT-TYPE
	SYNTAX	AsamProfileIndex
	ACCESS	not-accessible
	STATUS  mandatory
	DESCRIPTION
		"This object is the index in the QoS L2 Filter table"
::= { qosL2FilterEntry 1}

qosL2FilterName OBJECT-TYPE
	SYNTAX	AsamProfileName
	ACCESS	read-write
	STATUS  mandatory
	DESCRIPTION
"This object stores as an octet string the name of the L2 Filter."
::= {qosL2FilterEntry 2}

qosL2FilterRowStatus OBJECT-TYPE
	SYNTAX	RowStatus
	ACCESS	read-write
	STATUS  mandatory
	DESCRIPTION
		"This object is used to create a new row or modify or
         delete an existing row in this table. The usage is as per
         standard semantics of 'RowStatus' defined in SNMPv2-TC, with
         following limitations:
              The entry associated with a Profile that is being used may
              not be deleted."
::= {qosL2FilterEntry 3}

qosL2FilterRefCount OBJECT-TYPE
	SYNTAX	AsamProfileRefCount32
	ACCESS read-only
	STATUS	mandatory
	DESCRIPTION
		" Indicates the number of entities using this profile. If the
          reference count is greater than 0, then this profile is 'in use',
          and may NOT be deleted. If the value is 0, then this profile is
          'not in use', and can be deleted."
::= { qosL2FilterEntry 4}

qosL2FilterMacDa OBJECT-TYPE
	SYNTAX	MacAddress
	ACCESS	read-write
	STATUS  mandatory
	DESCRIPTION
	    "This object stores the destination MAC address. It is a 6 octet
string as defined in Bridge-MIB."
::= {qosL2FilterEntry 5}

qosL2FilterMacDaPrefix OBJECT-TYPE
	SYNTAX	Gauge
	ACCESS	read-write
	STATUS  mandatory
	DESCRIPTION
	"This object stores the destination MAC address prefix length as an
INTEGER(0..48). A length of 0 indicates a match of any MAC address; a length of
48 indicates a match of a single MAC address, and a length between 0 and 48
indicates the use of a qosL2FilterMacDa prefix, similar with the use of IP CIDR
prefix."
DEFVAL {0}
::= { qosL2FilterEntry 6}

qosL2FilterMacSa OBJECT-TYPE
	SYNTAX	MacAddress
	ACCESS	read-write
	STATUS  mandatory
	DESCRIPTION
	    "This object stores the source MAC address. It is a 6 octet string
as defined in Bridge-MIB."
::= {qosL2FilterEntry 7}

qosL2FilterMacSaPrefix OBJECT-TYPE
	SYNTAX	Gauge
	ACCESS	read-write
	STATUS  mandatory
	DESCRIPTION
	"This object stores the source MAC address prefix length as an
INTEGER(0..48). A length of 0 indicates a match of any MAC address; a length of
48 indicates a match of a single MAC address, and a length between 0 and 48
indicates the use of a qosL2FilterMacSa prefix, similar with the use of IP CIDR
prefix."
	DEFVAL {0}
::= { qosL2FilterEntry 8}

qosL2FilterEthtype OBJECT-TYPE
	SYNTAX	INTEGER (-1|0..65535)
	ACCESS	read-write
	STATUS  mandatory
	DESCRIPTION
		"This object stores Ethernet type value of this filter for both
Ethernet II-encoded frames and 802.3 encoded frames. A value of -1 indicates
that a specific Ether type has not been defined and thus all Ethtype values are
considered a match."
	DEFVAL {-1}
::= { qosL2FilterEntry 9}

qosL2FilterDot1P OBJECT-TYPE
	SYNTAX	INTEGER (-1|0..7)
	ACCESS	read-write
	STATUS  mandatory
	DESCRIPTION
		"This object stores 802.1p priority bits value of this filter.
A value of -1 indicates that a specific Dot1P has not been defined and thus all
Dot1P values are considered a match."
	DEFVAL {-1}
::= { qosL2FilterEntry 10}

qosL2FilterCFI OBJECT-TYPE
	SYNTAX	INTEGER (-1|0..1)
	ACCESS	read-write
	STATUS  mandatory
	DESCRIPTION
		"This object stores Canonical Format Indicator(CFI) bit of this
filter. A value of -1 indicates that a specific CFI has not been defined and
thus all CFI values are considered a match."
	DEFVAL {-1}
::= { qosL2FilterEntry 11}

qosL2FilterVlanId OBJECT-TYPE
	SYNTAX	INTEGER (-1..4095)
	ACCESS	read-write
	STATUS  mandatory
	DESCRIPTION
		"This object stores VLAN ID value of this filter. A value of -1
indicates that a specific VLAN ID has not been defined and thus all VLAN ID
values are considered a match."
	DEFVAL {-1}
::= { qosL2FilterEntry 12}

qosL3FilterTable OBJECT-TYPE
	SYNTAX	SEQUENCE OF QosL3FilterEntry
	ACCESS	not-accessible
	STATUS	mandatory
	DESCRIPTION
	"This object contains a table for creating and storing
	QoS L3 Filters.
	A QoS L3 Filter contains:
-	IP destination address
-	IP destination address prefix
-	IP source address
-	IP source address prefix
-	DSCP
-	Flow ID
-	Protocol
-	The minimum value that the layer-4 destination port number
-	The maximum value that the layer-4 destination port number
-	The minimum value that the layer-4 source port number
-	The maximum value that the layer-4 source port number "
::= { qosProfiles 17 }

qosL3FilterEntry OBJECT-TYPE
	SYNTAX QosL3FilterEntry
	ACCESS not-accessible
	STATUS mandatory
	DESCRIPTION
		"This table contains as rows QoS L3 filters."
	INDEX {qosL3FilterIndex }
::= {qosL3FilterTable 1}

QosL3FilterEntry ::=
     SEQUENCE { qosL3FilterIndex 		AsamProfileIndex ,
		qosL3FilterName			AsamProfileName,
		qosL3FilterRowStatus 		RowStatus,
		qosL3FilterRefCount		AsamProfileRefCount32,
		qosL3FilterAddrType		InetAddressType,
		qosL3FilterIpDa			InetAddress,
		qosL3FilterIpDaPrefix		InetAddressPrefixLength,
		qosL3FilterIpSa			InetAddress,
		qosL3FilterIpSaPrefix		InetAddressPrefixLength,
		qosL3FilterDSCP			DscpOrAny,
		qosL3FilterFlowId		INTEGER,
		qosL3FilterProtocol		INTEGER,
		qosL3FilterDestPortMin		InetPortNumber,
		qosL3FilterDestPortMax		InetPortNumber,
		qosL3FilterSrcPortMin		InetPortNumber,
		qosL3FilterSrcPortMax		InetPortNumber
				}

qosL3FilterIndex OBJECT-TYPE
	SYNTAX	AsamProfileIndex
	ACCESS	not-accessible
	STATUS  mandatory
	DESCRIPTION
		"This object is the index in the QoS L3 Filter table"
::= { qosL3FilterEntry 1}

qosL3FilterName OBJECT-TYPE
	SYNTAX	AsamProfileName
	ACCESS	read-write
	STATUS  mandatory
	DESCRIPTION
"This object stores as an octet string the name of the L3 Filter."
::= {qosL3FilterEntry 2}

qosL3FilterRowStatus OBJECT-TYPE
	SYNTAX	RowStatus
	ACCESS	read-write
	STATUS  mandatory
	DESCRIPTION
		"This object is used to create a new row or modify or
         delete an existing row in this table. The usage is as per
         standard semantics of 'RowStatus' defined in SNMPv2-TC, with
         following limitations:
         The entry associated with a Profile that is being used may
         not be deleted."
::= {qosL3FilterEntry 3}

qosL3FilterRefCount OBJECT-TYPE
	SYNTAX	AsamProfileRefCount32
	ACCESS read-only
	STATUS	mandatory
	DESCRIPTION
	" Indicates the number of entities using this profile. If the
          reference count is greater than 0, then this profile is 'in use',
          and may NOT be deleted. If the value is 0, then this profile is
          'not in use', and can be deleted."
::= { qosL3FilterEntry 4}

qosL3FilterAddrType OBJECT-TYPE
	SYNTAX	InetAddressType
	ACCESS	read-only
	STATUS  mandatory
	DESCRIPTION
	" The type of IP address used by this classifier entry.  While
       other types of addresses are defined in the InetAddressType textual
       convention, and DNS names, a classifier can only look at
       packets on the wire. Therefore, this object is limited to IPv4(1)
       and IPv6 addresses. In ISAM R2.3, Ipv6 related address type is not
       supported.So we should just support the value Ipv4(1)."
	DEFVAL {1}
::= {qosL3FilterEntry 5}

qosL3FilterIpDa OBJECT-TYPE
	SYNTAX	InetAddress
	ACCESS	read-write
	STATUS  mandatory
	DESCRIPTION
	" The IP address to match against the packet's destination IP      
address. This may not be a DNS name, but may be an IPv4 or IPv6       prefix. 
QosL3FilterIpDaPrefix indicates the number of bits that are relevant. In ISAM
R2.3, Ipv6 address is not supported."
::= { qosL3FilterEntry 6}

qosL3FilterIpDaPrefix OBJECT-TYPE
	SYNTAX	InetAddressPrefixLength
	ACCESS	read-write
	STATUS  mandatory
	DESCRIPTION
" The length of the CIDR Prefix carried in qosL3FilterIpDa. In IPv4 addresses,
a length of 0 indicates a match of any address; a length of 32 indicates a
match of a single host address, and a length between 0 and 32 indicates the use
of a CIDR Prefix. IPv6 is similar, except that prefix lengths range from
0..128. In ISAM R2.3, Ipv6 address is not supported."
	DEFVAL		{0}
::= {qosL3FilterEntry 7}

qosL3FilterIpSa OBJECT-TYPE
	SYNTAX	InetAddress
	ACCESS	read-write
	STATUS  mandatory
	DESCRIPTION
	" The IP address to match against the packet's source IP       address.
This may not be a DNS name, but may be an IPv4 or IPv6       prefix. 
QosL3FilterIpSaPrefix indicates the number of bits that are relevant. In ISAM
R2.3, Ipv6 address is not supported."
::= { qosL3FilterEntry 8}

qosL3FilterIpSaPrefix OBJECT-TYPE
	SYNTAX	InetAddressPrefixLength
	ACCESS	read-write
	STATUS  mandatory
	DESCRIPTION
" The length of the CIDR Prefix carried in qosL3FilterIpSa. In IPv4 addresses,
a length of 0 indicates a match of any address; a length of 32 indicates a
match of a single host address, and a length between 0 and 32 indicates the use
of a CIDR Prefix. IPv6 is similar, except that prefix lengths range from
0..128. In ISAM R2.3, Ipv6 address is not supported."
	DEFVAL		{0}
::= {qosL3FilterEntry 9}

qosL3FilterDSCP OBJECT-TYPE
	SYNTAX	DscpOrAny
	ACCESS	read-write
	STATUS  mandatory
	DESCRIPTION
" The value that the DSCP in the packet must have to match this entry. A value
of -1 indicates that a specific DSCP value has not been defined and thus all
DSCP values are considered a match."
	DEFVAL {-1}
::= { qosL3FilterEntry 10}

qosL3FilterFlowId OBJECT-TYPE
	SYNTAX	INTEGER (0..1048575)
	ACCESS	read-only
	STATUS  mandatory
	DESCRIPTION
		" The flow identifier in an IPv6 header. In ISAM R2.3, Ipv6 is
not supported by NP. So this field will be ignored by NP u-Code."
	DEFVAL {0}
::= { qosL3FilterEntry 11}

qosL3FilterProtocol OBJECT-TYPE
	SYNTAX	INTEGER (0..255)
	ACCESS	read-write
	STATUS  mandatory
	DESCRIPTION
" The IP protocol to match against the IPv4 protocol number or the IPv6 Next-
Header number in the packet. A value of 255 means match all.  Note the protocol
number of 255 is reserved by IANA, and Next-Header number of 0 is used in IPv6.
In ISAM R2.3, Ipv6 is not supported."
	DEFVAL {255}
::= { qosL3FilterEntry 12}

qosL3FilterDestPortMin OBJECT-TYPE
	SYNTAX	InetPortNumber
	ACCESS	read-write
	STATUS  mandatory
	DESCRIPTION
" The minimum value that the layer-4 destination port number in the
packet must have in order to match this classifier entry."
	DEFVAL {0}
::= { qosL3FilterEntry 13}

qosL3FilterDestPortMax OBJECT-TYPE
	SYNTAX	InetPortNumber
	ACCESS	read-write
	STATUS  mandatory
	DESCRIPTION
" The maximum value that the layer-4 destination port number in  the
packet must have in order to match this classifier entry. This value must
be equal to or greater than the value specified  for this entry in
qosL3FilterDestPortMin. If both qosL3FilterDestPortMin and
qosL3FilterDestPortMax is default, then destination port field will be
ignored."
	DEFVAL {65535}
::= { qosL3FilterEntry 14}

qosL3FilterSrcPortMin OBJECT-TYPE
	SYNTAX	InetPortNumber
	ACCESS	read-write
	STATUS  mandatory
	DESCRIPTION
" The minimum value that the layer-4 source port number in the packet
must have in order to match this classifier entry."
	DEFVAL {0}
::= { qosL3FilterEntry 15}

qosL3FilterSrcPortMax OBJECT-TYPE
	SYNTAX	InetPortNumber
	ACCESS	read-write
	STATUS  mandatory
	DESCRIPTION
" The maximum value that the layer-4 source port number in the packet
must have in order to match this classifier entry. This value must be
equal to or greater than the value specified for  this entry in
qosL3FilterSrcPortMin. If both qosL3FilterSrcPortMin and qosL3FilterSrcPortMax
is default, then source port field will be ignored."
	DEFVAL {65535}
::= { qosL3FilterEntry 16}

qosPolicyActionTable OBJECT-TYPE
	SYNTAX	SEQUENCE OF QosPolicyActionEntry
	ACCESS	not-accessible
	STATUS	mandatory
	DESCRIPTION
			"This object contains a table for creating and storing
			 QoS Policy Actions.
			 A QoS Policy Action contains:
-	Default discard/pass
-	Set a DSCP value
-	Set a Dot1P value
-	Policing with a policer
-	Policer sharing attribute "
::= { qosProfiles 18 }

qosPolicyActionEntry OBJECT-TYPE
	SYNTAX QosPolicyActionEntry
	ACCESS not-accessible
	STATUS mandatory
	DESCRIPTION
		"This table contains as rows QoS Policy Actions."
	INDEX {qosPolicyActionIndex }
::= {qosPolicyActionTable 1}

QosPolicyActionEntry ::=
	SEQUENCE { qosPolicyActionIndex 	AsamProfileIndex ,
		qosPolicyActionName		AsamProfileName,
		qosPolicyActionRowStatus 	RowStatus,	
		qosPolicyActionRefCount		AsamProfileRefCount32,
		qosPolicyActionDisposition	INTEGER,
		qosPolicyActionSetDSCP		DscpOrAny,
		qosPolicyActionSetDot1P		INTEGER,
		qosPolicyActionPolicerId 	AsamProfilePointer,
		qosPolicyActionSharing		INTEGER

				}

qosPolicyActionIndex OBJECT-TYPE
	SYNTAX	AsamProfileIndex
	ACCESS	not-accessible
	STATUS  mandatory
	DESCRIPTION
		"This object is the index in the QoS Policy Action table"
::= { qosPolicyActionEntry 1}

qosPolicyActionName OBJECT-TYPE
	SYNTAX	AsamProfileName
	ACCESS	read-write
	STATUS  mandatory
	DESCRIPTION
"This object stores as an octet string the name of the Policy Action."
::= {qosPolicyActionEntry 2}

qosPolicyActionRowStatus OBJECT-TYPE
	SYNTAX	RowStatus
	ACCESS	read-write
	STATUS  mandatory
	DESCRIPTION
	"This object is used to create a new row or modify or
         delete an existing row in this table. The usage is as per
         standard semantics of 'RowStatus' defined in SNMPv2-TC, with
         following limitations:
         The entry associated with a Profile that is being used may
         not be deleted."
::= {qosPolicyActionEntry 3}

qosPolicyActionRefCount OBJECT-TYPE
	SYNTAX	AsamProfileRefCount32
	ACCESS read-only
	STATUS	mandatory
	DESCRIPTION
	" Indicates the number of entities using this profile. If the
          reference count is greater than 0, then this profile is 'in use',
          and may NOT be deleted. If the value is 0, then this profile is
          'not in use', and can be deleted."
::= { qosPolicyActionEntry 4}

qosPolicyActionDisposition OBJECT-TYPE
	SYNTAX	INTEGER {
				discard (1),
				pass (2)
 }
	ACCESS	read-write
	STATUS  mandatory
	DESCRIPTION
	    "This object stores the forwarding action. Forwarding action can be
discard or pass. The default forwarding action is pass. When the forwarding
action is discard, the other policy actions in this entry will not be checked,
the frame will be discarded immediately."
	DEFVAL {pass}
::= {qosPolicyActionEntry 5}

qosPolicyActionSetDSCP OBJECT-TYPE
	SYNTAX	DscpOrAny
	ACCESS	read-write
	STATUS  mandatory
	DESCRIPTION
	"This object stores the DSCP value as an INTEGER(-1|0..63). policy with
this policy action will set this DSCP value to matched frames. Default value is
-1, means not to change DSCP value in the frame."
	DEFVAL 	{-1}
::= { qosPolicyActionEntry 6}

qosPolicyActionSetDot1P OBJECT-TYPE
	SYNTAX	INTEGER ( -1|0..7 )
	ACCESS	read-write
	STATUS  mandatory
	DESCRIPTION
	" This object stores the Dot1P value as an INTEGER(-1|0..7).
policy with this policy action will set this Dot1P value to matched frames.
Default value is -1, means not to change Dot1P value in the frame."
	DEFVAL		{-1}
::= { qosPolicyActionEntry 7}

qosPolicyActionPolicerId OBJECT-TYPE
	SYNTAX	AsamProfilePointer
	ACCESS	read-write
	STATUS  mandatory
	DESCRIPTION
	" This object stores the qosPolicerIndex value as an INTEGER.
policy with this policy action will policing matched frames according to a
Policer Profile. Default value is 0, means no policer."
	DEFVAL		{0}
::= { qosPolicyActionEntry 8}

qosPolicyActionSharing OBJECT-TYPE
	SYNTAX	INTEGER {
				enabled (1),
				disabled (2)
 }
	ACCESS	read-write
	STATUS  mandatory
	DESCRIPTION
		" This object stores the Policer sharing attributes as an
INTEGER. Enabled means the policies with same policer profile in a session
profile will create only one policer instance. disabled means the policies with
same policer profile in a session profile will create their own policer
instance separately. Default value is disabled."
	DEFVAL		{2}
::= { qosPolicyActionEntry 9}

qosShaperProfileTable OBJECT-TYPE
	SYNTAX	SEQUENCE OF QosShaperProfileEntry
	ACCESS	not-accessible
	STATUS	mandatory
	DESCRIPTION
	"This object contains a table for creating and storing
	shaper profiles. A shaper profile contains rate enforcement
	information for frames  which this shaper profile is applied. "
::= { qosProfiles 19 }
qosShaperProfileEntry OBJECT-TYPE
	SYNTAX 	QosShaperProfileEntry
	ACCESS	not-accessible
	STATUS	mandatory
	DESCRIPTION
		"Rows of this table contain QoS Shaper Profiles"
	INDEX {qosShaperProfileIndex }
::= {qosShaperProfileTable 1}
QosShaperProfileEntry ::=
     SEQUENCE { 
qosShaperProfileIndex		AsamProfileIndex,
		qosShaperProfileName		AsamProfileName,
         qosShaperProfileRowStatus      RowStatus	,
		qosShaperProfileRefCount	AsamProfileRefCount32,
		qosShaperProfileType 		 INTEGER,
		qosShaperProfileCIR		INTEGER,
		qosShaperProfileCBS		INTEGER,
    qosShaperProfileEIR		INTEGER

				}

qosShaperProfileIndex OBJECT-TYPE
	SYNTAX AsamProfileIndex
	ACCESS not-accessible
	STATUS mandatory
	DESCRIPTION
	 "This object is the index to the qosShaperProfileTable.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileEntry 1}

qosShaperProfileName 	OBJECT-TYPE
	SYNTAX	AsamProfileName
	ACCESS read-write
	STATUS mandatory
	DESCRIPTION
	 "Octet string storing the operator-given name of the profile.
      ALCATEL NOTE:
                 ACCESS:     NA       USAGE:      NA
                 PERSIST:    YES       INSRVMOD:   NO
                 RANGE:      NA       DEFVALUE:   NA
                 UNITS:      NA       SPARSE:     NA
                 DESCR:      NA "
::= {qosShaperProfileEntry 2}

qosShaperProfileRowStatus OBJECT-TYPE
	SYNTAX	RowStatus
	ACCESS	read-write
	STATUS mandatory
	DESCRIPTION
"This object is used to create a new row or modify or
delete an existing row in this table. The usage is as per
standard semantics of 'RowStatus' defined in SNMPv2-TC.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileEntry 3}

qosShaperProfileRefCount OBJECT-TYPE
	SYNTAX	AsamProfileRefCount32
	ACCESS read-only
	STATUS	mandatory
	DESCRIPTION
		" Indicates the number of entities using this profile. If the
reference count is greater than 0, then this profile is 'in use',
and may NOT be deleted. If the value is 0, then this profile is
'not in use', and can be deleted.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileEntry 4}

qosShaperProfileType OBJECT-TYPE
   SYNTAX INTEGER { singleTokenBucket (1), singleTokenBucketGpon (2), singleTokenTwoRate (3)}
   ACCESS read-write
   STATUS mandatory
   DESCRIPTION
    "The shaper profile type encodes a standardized shaping
   algorithm with an integer value. Based on this type the
   hardware will know how to configure the shapers, and which
   of the following fields are required.
      ALCATEL NOTE:
                 ACCESS:     NA       USAGE:      NA
                 PERSIST:    YES       INSRVMOD:   NO
                 RANGE:      NA       DEFVALUE:   singletokenbucket
                 UNITS:      NA       SPARSE:     NA
                 DESCR:      NA "
      DEFVAL { singleTokenBucket }

::= { qosShaperProfileEntry 5}

qosShaperProfileCIR OBJECT-TYPE
	SYNTAX INTEGER(0..2147483647)
	ACCESS read-write
	STATUS mandatory
	DESCRIPTION
	 "This object stores the Committed Information Rate (CIR)
	of a shaper in Kilobits per second. Cannot be negative.
        If the qosShaperProfileType is set to singleTokenBucket or
	singleTokenBucket, CIR can be used for shaper profile otherwise
	this object not be supported.            
      ALCATEL NOTE:
                 ACCESS:     NA       USAGE:      NA
                 PERSIST:    YES       INSRVMOD:   NO
                 RANGE:      NA       DEFVALUE:   0
                 UNITS:      NA       SPARSE:     NA
                 DESCR:      NA "
::= { qosShaperProfileEntry 6}

qosShaperProfileCBS OBJECT-TYPE
	SYNTAX INTEGER(0..2147483647)
	ACCESS read-write
	STATUS mandatory
	DESCRIPTION
	 "This object stores the Committed Burst Size (CBS)
	of a shaper in bytes. Cannot be negative.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileEntry 7}

qosShaperProfileEIR OBJECT-TYPE
	SYNTAX INTEGER(0..2147483647)
	ACCESS read-write
	STATUS mandatory
	DESCRIPTION
	 "This object stores the Excess Information Rate (CIR)
	of a shaper in Kilobits per second. Cannot be negative.
            The range of EIR will be 0..2400000 for GLT.
            The range of EIR will be 0..10000000 for FGXT.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileEntry 8}

qosShaperProfileMappingTable OBJECT-TYPE
	SYNTAX	SEQUENCE OF QosShaperProfileMappingEntry
	ACCESS	not-accessible
	STATUS	mandatory
	DESCRIPTION
	"This object contains a table for qosShaperProfile
name to index mapping"
::= { qosProfiles 20 }

qosShaperProfileMappingEntry OBJECT-TYPE
	SYNTAX 	QosShaperProfileMappingEntry
	ACCESS	not-accessible
	STATUS mandatory
	DESCRIPTION
	" An entry (conceptual row) representing the qos
Shaper Profile Name to Index mapping. The system automatically creates an
entry in this Table for each corresponding entry (qosShaper profile)created in the qosShaperProfileTable.  Similarly, when an qosShaper profile is deleted, the corresponding entry in this table is also automatically deleted by the system."
	INDEX	{qosShaperProfileMappingName }
	::= {qosShaperProfileMappingTable  1}

QosShaperProfileMappingEntry ::=
	SEQUENCE { 
qosShaperProfileMappingName     AsamProfileName,
		qosShaperProfileMappingIndex      AsamProfileIndex
			}

qosShaperProfileMappingName OBJECT-TYPE
	SYNTAX	AsamProfileName
	ACCESS	not-accessible
	STATUS  mandatory
	DESCRIPTION
		"A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { qosShaperProfileMappingEntry 1}

qosShaperProfileMappingIndex OBJECT-TYPE
	SYNTAX	AsamProfileIndex
	ACCESS	read-only
	STATUS mandatory
	DESCRIPTION
		"This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { qosShaperProfileMappingEntry 2}

qosSchedulerNodeProfileTable OBJECT-TYPE
	SYNTAX	SEQUENCE OF QosSchedulerNodeProfileEntry
	ACCESS	not-accessible
	STATUS	mandatory
	DESCRIPTION
	" It is pretty much the same as QoSSchedulerProfileTable but with new parameters added. QoSSchedulerProfileTable will not be supported on GLTs."
::= { qosProfiles 21 }

qosSchedulerNodeProfileEntry OBJECT-TYPE
	SYNTAX QosSchedulerNodeProfileEntry
	ACCESS	not-accessible
	STATUS mandatory
	DESCRIPTION
	"This table contains as row QoS Scheduler Profiles"
	INDEX {qosSchedulerNodeProfileIndex}
::= {qosSchedulerNodeProfileTable 1}

QosSchedulerNodeProfileEntry 	::=
     SEQUENCE { qosSchedulerNodeProfileIndex		AsamProfileIndex ,
		qosSchedulerNodeProfileName			AsamProfileName,
		qosSchedulerNodeProfileVersion 		INTEGER,
		qosSchedulerNodeProfileRefCount		AsamProfileRefCount32,
		qosSchedulerNodeProfileRowStatus 		RowStatus,
		qosSchedulerNodeProfileWeight		INTEGER,
		qosSchedulerNodeProfilePriority		INTEGER,
		qosSchedulerNodeProfileShaperProfile		AsamProfilePointer,
                qosSchedulerNodeProfileMulticastInclShaping     TruthValue

				}

qosSchedulerNodeProfileIndex OBJECT-TYPE
	SYNTAX	AsamProfileIndex
	ACCESS	not-accessible
	STATUS mandatory
	DESCRIPTION
	"This object is the key in the Scheduler Node Profile table. Values of 1..32 will be supported."
::= { qosSchedulerNodeProfileEntry 1}

qosSchedulerNodeProfileName OBJECT-TYPE
	SYNTAX	AsamProfileName
	ACCESS	read-write
	STATUS mandatory
	DESCRIPTION
	"This object stores as an octet string the name of the
Scheduler Node Profile given by the operator."
::= {qosSchedulerNodeProfileEntry 2}

qosSchedulerNodeProfileVersion OBJECT-TYPE
	SYNTAX	INTEGER
	ACCESS	read-write
	STATUS mandatory
	DESCRIPTION
	"Integer containing the version number of this profile."
::= { qosSchedulerNodeProfileEntry 3}

qosSchedulerNodeProfileRefCount OBJECT-TYPE
	SYNTAX	AsamProfileRefCount32
	ACCESS read-only
	STATUS	mandatory
	DESCRIPTION
	" Indicates the number of entities using this profile. If the
reference count is greater than 0, then this profile is 'in use',
and may NOT be deleted. If the value is 0, then this profile is
'not in use', and can be deleted."
::= { qosSchedulerNodeProfileEntry 4}

qosSchedulerNodeProfileRowStatus OBJECT-TYPE
	SYNTAX	RowStatus
	ACCESS	read-write
	STATUS mandatory
	DESCRIPTION
	"This object is used to create a new row or modify or
delete an existing row in this table. The usage is as per
standard semantics of 'RowStatus' defined in SNMPv2-TC, with
following limitations:
o The entry associated with a Profile that is being used may
not be deleted."
::= {qosSchedulerNodeProfileEntry 5}

qosSchedulerNodeProfileWeight OBJECT-TYPE
	SYNTAX	INTEGER
	ACCESS	read-write
	STATUS mandatory
	DESCRIPTION
	 "This object stores the relative weight of the scheduler. It stores it as an Integer with values 	between 0 and 127. "
	DEFVAL		{1}

::= {qosSchedulerNodeProfileEntry 6}

qosSchedulerNodeProfilePriority OBJECT-TYPE
	SYNTAX	INTEGER
	ACCESS	read-write
	STATUS mandatory
	DESCRIPTION
	 "This object stores the relative priority of the scheduler when multiple schedulers have the same weight.  It stores it as an Integer with values between 1 and 8 "
	DEFVAL		{1}

::= {qosSchedulerNodeProfileEntry 7}

qosSchedulerNodeProfileShaperProfile OBJECT-TYPE
	SYNTAX	AsamProfilePointer
	ACCESS	read-write
	STATUS mandatory
	DESCRIPTION
	 "This object stores the id  of the associated shaper profile "
        DEFVAL   {0}

::= {qosSchedulerNodeProfileEntry 8}

qosSchedulerNodeProfileMulticastInclShaping OBJECT-TYPE
        SYNTAX  TruthValue
        ACCESS  read-write
        STATUS mandatory
        DESCRIPTION
  "This object indicates whether the UNI level shaper should rate-limit 
the aggregate of unicast + multicast traffic. The default is false (rate-limit unicast only).
ALCATEL NOTE:
                 ACCESS:     NA       USAGE:      NA
                 PERSIST:    YES      INSRVMOD:   NO
                 RANGE:      NA       DEFVALUE:   FALSE
                 UNITS:      NA       SPARSE:     NA
                 DESCR:      NA "
        DEFVAL { false }

  ::= {qosSchedulerNodeProfileEntry 9}

qosSchedulerNodeProfileMappingTable OBJECT-TYPE
	SYNTAX	SEQUENCE OF QosSchedulerNodeProfileMappingEntry
	ACCESS	not-accessible
	STATUS	mandatory
	DESCRIPTION
	"This object contains a table for qosSchedulerNodeProfile
name to index mapping. "
::= { qosProfiles 22 }

qosSchedulerNodeProfileMappingEntry OBJECT-TYPE
	SYNTAX 	QosSchedulerNodeProfileMappingEntry
	ACCESS	not-accessible
	STATUS mandatory
	DESCRIPTION
	" An entry (conceptual row) representing the qos
Scheduler Node Profile Name to Index mapping. The system automatically creates an
entry in this Table for each corresponding entry (qosScheduler-Nodeprofile) created
in the qosSchedulerNodeProfileTable. Similarly, when an qosSchedulerNodeprofile is 
deleted, them corresponding entry in this table is also automatically deleted
 by the system."
	INDEX	{qosSchedulerNodeProfileMappingName }
	::= {qosSchedulerNodeProfileMappingTable  1}

QosSchedulerNodeProfileMappingEntry ::=
	SEQUENCE { qosSchedulerNodeProfileMappingName AsamProfileName,
		   qosSchedulerNodeProfileMappingIndex AsamProfileIndex
			}

qosSchedulerNodeProfileMappingName OBJECT-TYPE
	SYNTAX	AsamProfileName
	ACCESS	not-accessible
	STATUS  mandatory
	DESCRIPTION
		"A text string containing the name of
		this profile"
::= { qosSchedulerNodeProfileMappingEntry 1}

qosSchedulerNodeProfileMappingIndex OBJECT-TYPE
	SYNTAX	AsamProfileIndex
	ACCESS	read-write
	STATUS mandatory
	DESCRIPTION
		"This object is the Profile index."
::= { qosSchedulerNodeProfileMappingEntry 2}

qosBandwidthProfileMappingTable OBJECT-TYPE
	SYNTAX	SEQUENCE OF QosBandwidthProfileMappingEntry
	ACCESS	not-accessible
	STATUS	mandatory
	DESCRIPTION
	"This object contains a table for qosBandwidthProfile
name to index mapping"
::= { qosProfiles 23 }

qosBandwidthProfileMappingEntry OBJECT-TYPE
	SYNTAX 	QosBandwidthProfileMappingEntry
	ACCESS	not-accessible
	STATUS mandatory
	DESCRIPTION
	" An entry (conceptual row) representing the qos
Bandwidth Profile Name to Index mapping. The system automatically creates an
entry in this Table for each corresponding entry (qosBandwidth profile)created in the qosShaperProfileTable.  Similarly, when an qosBandwidth profile is deleted, the corresponding entry in this table is also automatically deleted by the system."
	INDEX	{qosBandwidthProfileMappingName }
	::= {qosBandwidthProfileMappingTable  1}

QosBandwidthProfileMappingEntry ::=
	SEQUENCE { 
qosBandwidthProfileMappingName     AsamProfileName,
		qosBandwidthProfileMappingIndex      AsamProfileIndex
			}

qosBandwidthProfileMappingName OBJECT-TYPE
	SYNTAX	AsamProfileName
	ACCESS	not-accessible
	STATUS  mandatory
	DESCRIPTION
		"A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileMappingEntry 1}

qosBandwidthProfileMappingIndex OBJECT-TYPE
	SYNTAX	AsamProfileIndex
	ACCESS	read-only
	STATUS mandatory
	DESCRIPTION
		"This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileMappingEntry 2}

qosBandwidthProfileTable OBJECT-TYPE
	SYNTAX	SEQUENCE OF QosBandwidthProfileEntry
	ACCESS	not-accessible
	STATUS	mandatory
	DESCRIPTION
	"This object contains a table for creating and storing
	Bandwidth profiles. A Bandwidth profile contains upstream rate enforcement
	information for frames  to which this profile is applied. "
::= { qosProfiles 24 }
qosBandwidthProfileEntry OBJECT-TYPE
	SYNTAX 	QosBandwidthProfileEntry
	ACCESS	not-accessible
	STATUS	mandatory
	DESCRIPTION
		"Rows of this table contain QoS Bandwidth Profiles"
	INDEX {qosBandwidthProfileIndex }
::= {qosBandwidthProfileTable 1}
QosBandwidthProfileEntry ::=
     SEQUENCE { 
qosBandwidthProfileIndex		AsamProfileIndex,
		qosBandwidthProfileName		AsamProfileName,
        qosBandwidthProfileRowStatus      RowStatus	,
		qosBandwidthProfileRefCount	AsamProfileRefCount32,
		qosBandwidthProfileCIR		INTEGER,
		qosBandwidthProfileAIR		INTEGER,
		qosBandwidthProfileEIR		INTEGER,
		qosBandwidthProfileDelayTolerance		INTEGER

				}

qosBandwidthProfileIndex OBJECT-TYPE
	SYNTAX AsamProfileIndex
	ACCESS not-accessible
	STATUS mandatory
	DESCRIPTION
	 "This object is the index to the qosBandwidthProfileTable.
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 1}

qosBandwidthProfileName 	OBJECT-TYPE
	SYNTAX	AsamProfileName
	ACCESS read-write
	STATUS mandatory
	DESCRIPTION
	 "Octet string storing the operator-given name of the profile.
      ALCATEL NOTE:
                 ACCESS:     NA       USAGE:      NA
                 PERSIST:    YES       INSRVMOD:   NO
                 RANGE:      NA       DEFVALUE:   NA
                 UNITS:      NA       SPARSE:     NA
                 DESCR:      NA "
::= {qosBandwidthProfileEntry 2}

qosBandwidthProfileRowStatus OBJECT-TYPE
	SYNTAX	RowStatus
	ACCESS	read-write
	STATUS mandatory
	DESCRIPTION
"This object is used to create a new row or modify or
delete an existing row in this table. The usage is as per
standard semantics of 'RowStatus' defined in SNMPv2-TC.
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 3}

qosBandwidthProfileRefCount OBJECT-TYPE
	SYNTAX	AsamProfileRefCount32
	ACCESS read-only
	STATUS	mandatory
	DESCRIPTION
		" Indicates the number of entities using this profile. If the
reference count is greater than 0, then this profile is 'in use',
and may NOT be deleted. If the value is 0, then this profile is
'not in use', and can be deleted.
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 4}

qosBandwidthProfileCIR OBJECT-TYPE
	SYNTAX INTEGER(0..2147483647)
	ACCESS read-write
	STATUS mandatory
	DESCRIPTION
	 "This object stores the Committed Information Rate (CIR).
	Cannot be negative.  The range of CIR will be
   0..2400000 for GLT. The range of CIR will be 0..10000000 for FGXT-A
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 5}

qosBandwidthProfileAIR OBJECT-TYPE
	SYNTAX INTEGER(0..2147483647)
	ACCESS read-write
	STATUS mandatory
	DESCRIPTION
	 "This object stores the Assured Information Rate (AIR)
    Cannot be negative. The range of AIR will be 0..2400000 for GLT and
    0..10000000 for FGXT-A
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 6}

qosBandwidthProfileEIR OBJECT-TYPE
	SYNTAX INTEGER(0..2147483647)
	ACCESS read-write
	STATUS mandatory
	DESCRIPTION
	 "This object stores the Excess Information Rate (AIR)
	  Cannot be negative. The range of EIR will be 0..2400000 for GLT and
     0..10000000 for FGXT-A
      ALCATEL NOTE:
                 ACCESS:     NA       USAGE:      NA
                 PERSIST:    YES       INSRVMOD:   NO
                 RANGE:      NA       DEFVALUE:   NA
                 UNITS:      NA       SPARSE:     NA
                 DESCR:      NA "
::= { qosBandwidthProfileEntry 7}

qosBandwidthProfileDelayTolerance OBJECT-TYPE
	SYNTAX INTEGER(1..240)
	ACCESS read-write
	STATUS mandatory
	DESCRIPTION
	 "This object stores the DelayTolerance
	of a shaper in units of 125 microseconds. Cannot be negative. This object is used only if type is singleTokenBucketGpon in the upstream direction.
      ALCATEL NOTE:
                 ACCESS:     NA       USAGE:      NA
                 PERSIST:    YES       INSRVMOD:   NO
                 RANGE:      NA       DEFVALUE:   NA
                 UNITS:      NA       SPARSE:     NA
                 DESCR:      NA "
	DEFVAL		{80}

::= { qosBandwidthProfileEntry 8}

qosLimDot1PtcMapping OBJECT IDENTIFIER ::= {qosMIB 4}
qosLimDot1PtcMappingTable OBJECT-TYPE
	SYNTAX	SEQUENCE OF QosLimDot1PTcMappingEntry
	ACCESS	not-accessible
	STATUS	mandatory
	DESCRIPTION
	"This object contains a table that defines the
	 mapping between the .1P field of the VLAN tag to
	a certain traffic class. The row index of the table is
 	the ingress .1P value (0..7) while the value is the
	 (the traffic class) (0..7)."
::= { qosLimDot1PtcMapping 1}
qosLimDot1PTcMappingEntry OBJECT-TYPE
	SYNTAX QosLimDot1PTcMappingEntry
	ACCESS not-accessible
	STATUS	mandatory
	DESCRIPTION
	"This table contains the 802.1P traffic class to queue mapping
	information. There are 8 rows, each containing one output
	traffic class number (0..7), one discard priority colour (0..1) 
	and one	policer colour (0..2) in the context of the outgoing 
	interface on LIMs"
	INDEX {qosLimDot1P }
	::= {qosLimDot1PtcMappingTable 1}
QosLimDot1PTcMappingEntry ::=
	SEQUENCE {	qosLimDot1P		 INTEGER,
			qosLimTc		 INTEGER,
			qosLimDPColour           QosColourType,
			qosLimPolicerColour      QosColourType
		  }
qosLimDot1P OBJECT-TYPE
	SYNTAX	INTEGER
	ACCESS	not-accessible
	STATUS mandatory
	DESCRIPTION
	 "This field is used to index the Dot1P traffic class
	mapping table. The lengths of the table is 8 (fixed)"
::= { qosLimDot1PTcMappingEntry 1 }

qosLimTc OBJECT-TYPE
	SYNTAX	INTEGER (0..7)
	ACCESS	read-write
	STATUS mandatory
	DESCRIPTION
	 "This object encodes the traffic class (0..7) into which
	frames coming in with the .1P value equal to the
	index of the row in this table will be cast.
	E.g., if row 6 contains value 3, that means that frames
	with .1P value equal to 6 will be cast in output traffic class 3 "
::= { qosLimDot1PTcMappingEntry 2 }

qosLimDPColour OBJECT-TYPE
	SYNTAX	QosColourType
	ACCESS	read-write
	STATUS mandatory
	DESCRIPTION
	 "This object encodes the frame discard priority in queue. The colour corresponds to the colour defined in QueueProfileTable. ISAM supports green(0) and yellow(1) now. 
      ALCATEL NOTE:
                 ACCESS:     NA       USAGE:      NA
                 PERSIST:    YES       INSRVMOD:   NO
                 RANGE:      NA       DEFVALUE:   NA
                 UNITS:     green(0) , yellow(1)       SPARSE:     NA
                 DESCR:      NA "
	DEFVAL		{0}
::= { qosLimDot1PTcMappingEntry 3 }

qosLimPolicerColour OBJECT-TYPE
	SYNTAX	QosColourType
	ACCESS	read-write
	STATUS mandatory
	DESCRIPTION
	 "This object encodes the frame colour for TrTCM. The colour corresponds to the colour defined in PolicerProfileTable. ISAM supports green(0), yellow(1) and red(2) now. 
      ALCATEL NOTE:
                 ACCESS:     NA       USAGE:      NA
                 PERSIST:    YES       INSRVMOD:   NO
                 RANGE:      NA       DEFVALUE:   0
                 UNITS:     green(0) , yellow(1) ,red(2)  SPARSE:     NA
                 DESCR:      NA "
	DEFVAL		{0}
::= { qosLimDot1PTcMappingEntry 4 }

qosLimTcToQueueMappingTable OBJECT-TYPE
	SYNTAX	SEQUENCE OF QosLimTcToQueueMappingEntry
	ACCESS	not-accessible
	STATUS	mandatory
	DESCRIPTION
	"This object contains a table that defines the
	 mapping between the traffic class and the queue of a UNI. Three rows 
              in the table will be automatically created with default values and can only be edited but the operator. Row 1 is used for the case when the LIM has 4 queues per UNI and 4 TCs, Row 2 is used for the case when the LIM has 4 queues per UNI but 8 TCs, Row 3 is used for the case when the LIM has 8 queues per UNI but 8 TCs."
::= { qosLimDot1PtcMapping 2}
qosLimTcToQueueMappingEntry OBJECT-TYPE
	SYNTAX QosLimTcToQueueMappingEntry
	ACCESS not-accessible
	STATUS	mandatory
	DESCRIPTION
	"This table contains the 802.1P traffic class to queue mapping
	information. There are 8 rows, each containing one output
	buffer number (0..7) in the context of the outgoing interface "
	INDEX {qosLimTcToQueueMappingIndex}
	::= {qosLimTcToQueueMappingTable 1}
QosLimTcToQueueMappingEntry ::=
	SEQUENCE {	qosLimTcToQueueMappingIndex			INTEGER,			
			qosLimTcToQueueMappingQueue                           INTEGER,
			qosLimTcToQueueMappingName			AsamProfileName
				}
qosLimTcToQueueMappingIndex OBJECT-TYPE
	SYNTAX	INTEGER 
	ACCESS	not-accessible
	STATUS mandatory
	DESCRIPTION
	 "This field is used to identify the row of the table. Row 1 is used for the case when the LIM has 4 queues per UNI and 4 TCs, Row 2 is used for the case when the LIM has 4 queues per UNI but 8 TCs, Row 3 is used for the case when the LIM has 8 queues per UNI but 8 TCs."
::= { qosLimTcToQueueMappingEntry 1 }

qosLimTcToQueueMappingQueue OBJECT-TYPE
	SYNTAX	INTEGER 
	ACCESS	read-only
	STATUS mandatory
	DESCRIPTION
	 "The following mapping applies:
       The queue corresponding to TC 0 is indicated in bits 0-3, the queue corresponding to TC 1 in indicated in bit 4-7. The mapping uses 4 bits for implementation convenience. The MSB should be set to 0 if the queue is used (i.e valid queues are indicated with 0000 to 0111). If a particular TC is not used, then the corresponding bits have to be 1111. Graphical representation is given below :
      Bit31-28 bit27-24 bit23-20 bit19-16 bit15-bit12 bit11-8 bit7-4 bit3-0 
         TC7      TC6      TC5      TC4      TC3         TC2    TC1    TC0
             ALCATEL NOTE:
                 ACCESS:     RO       USAGE:      NA
                 PERSIST:    YES      INSRVMOD:   NO
                 RANGE:      NA       DEFVALUE:   NA
                 UNITS:      NA       SPARSE:     NA
                 		DESCR:      NA."
::= { qosLimTcToQueueMappingEntry 2 }

qosLimTcToQueueMappingName OBJECT-TYPE
	SYNTAX	AsamProfileName 
	ACCESS	not-accessible
	STATUS mandatory
	DESCRIPTION
	 "This field is used to identify the row of the table. Row 1 is used for the case when the LIM has 4 queues per UNI and 4 TCs and has the name 4queue4tc, Row 2 is used for the case when the LIM has 4 queues per UNI but 8 TCs and has the name 4queue8tc, Row 3 is used for the case when the LIM has 8 queues per UNI but 8 TCs and has the name 8queue8tc "
::= { qosLimTcToQueueMappingEntry 3 }

qosIngressQoSProfileTable OBJECT-TYPE
	SYNTAX	SEQUENCE OF QosIngressQoSProfileEntry
	ACCESS	not-accessible
	STATUS	mandatory
	DESCRIPTION
	" This table stores the pbit to Queue mappings 
 that can be used by a VLAN PORT in the upstream and dowstream directions.
(same profile for both directions). A row with index = 1 is created by default which 
maps pbits 0..7 to TC 0..7 one to one (pbit 0 to TC 0, pbit 1 to TC 1 etc etc). Rows with index = 2 to 32 can be created and deleted and modified by the operator."
::= { qosLimDot1PtcMapping 3}
qosIngressQoSProfileEntry OBJECT-TYPE
	SYNTAX QosIngressQoSProfileEntry
	ACCESS not-accessible
	STATUS	mandatory
	DESCRIPTION
	"This table contains the 802.1P pbits to traffic class mappings"
	INDEX {qosIngressQoSProfileIndex }
	::= {qosIngressQoSProfileTable 1}
QosIngressQoSProfileEntry ::=
	SEQUENCE {	qosIngressQoSProfileIndex			AsamProfileIndex,
qosIngressQoSProfileName                    AsamProfileName,
				qosIngressQoSProfileTc                          INTEGER,
				qosIngressQoSProfileRowStatus             RowStatus,
				qosIngressQoSProfileRefCount	        AsamProfileRefCount32
				}
qosIngressQoSProfileIndex OBJECT-TYPE
	SYNTAX	AsamProfileIndex 
	ACCESS	not-accessible
	STATUS mandatory
	DESCRIPTION
	 "This field is used to identify the row of the table. Rows with  qosIngressQoSProfileIndex = 1 is automatically created by the system and cannot be edited. It  has one to one mapping of pbits (0..7) to TCs (0..7). Rows with qosIngressQoSProfileIndex = 2..32 can be created, deleted and modified by the operator."
::= { qosIngressQoSProfileEntry 1 }

qosIngressQoSProfileName OBJECT-TYPE
	SYNTAX	AsamProfileName
	ACCESS	read-write
	STATUS mandatory
	DESCRIPTION
	 "This field is used to identify the row of the table with a name"
::= { qosIngressQoSProfileEntry 2 }

qosIngressQoSProfileTc OBJECT-TYPE
	SYNTAX	INTEGER 
	ACCESS	read-write
	STATUS mandatory
	DESCRIPTION
	 "The following mapping applies:
          The TC corresponding to pbits 0 is indicated in bits 0-3, the TC corresponding 
          to pbit 1 in indicated in bit 4-7, !-The mapping uses 4 bits for implementation
	  convenience. The MSB should be set to 0 if the TC is used (i.e valid TCs are 
	  indicated with 0000 to 0111). If a particular TC is not used, then the corresponding 
	  bits have to be 1111. Graphical representation is given below :
      Bit31-28 bit27-24 bit23-20 bit19-16 bit15-bit12 bit11-8 bit7-4 bit3-0 
      pbit-7   pbit-6   pbit-5    pbit-4    pbit-3    pbit-2  pbit-1    pbit-0
             ALCATEL NOTE:
                 ACCESS:     RO       USAGE:      NA
                 PERSIST:    YES      INSRVMOD:   NO
                 RANGE:      NA       DEFVALUE:   NA
                 UNITS:      NA       SPARSE:     NA
                 		DESCR:      NA."
::= { qosIngressQoSProfileEntry 3 }

qosIngressQoSProfileRowStatus OBJECT-TYPE
	SYNTAX	RowStatus
	ACCESS	read-write
	STATUS mandatory
	DESCRIPTION
	 "This object is the Row Status of the row in the table."
::= { qosIngressQoSProfileEntry 4 }

qosIngressQoSProfileRefCount OBJECT-TYPE
	SYNTAX	AsamProfileRefCount32 
	ACCESS	read-only
	STATUS mandatory
	DESCRIPTION
	 "This field is used to specify the reference count of how many times this profile has been applied. If 0 the profile is not in use and can be deleted."
::= { qosIngressQoSProfileEntry 5 }

qosIngressQosProfileMappingTable OBJECT-TYPE
	SYNTAX	SEQUENCE OF QosIngressQosProfileMappingEntry
	ACCESS	not-accessible
	STATUS	mandatory
	DESCRIPTION
	"This object contains a table for qosIngressQosProfile
name to index mapping"
::= { qosLimDot1PtcMapping 4 }

qosIngressQosProfileMappingEntry OBJECT-TYPE
	SYNTAX 	QosIngressQosProfileMappingEntry
	ACCESS	not-accessible
	STATUS mandatory
	DESCRIPTION
	" An entry (conceptual row) representing the qos
IngressQos Profile Name to Index mapping. The system automatically creates an
entry in this Table for each corresponding entry (qosIngressQos profile)created in the system.  Similarly, when an qosIngressQos profile is deleted, the corresponding entry in this table is also automatically deleted by the system."
	INDEX	{qosIngressQosProfileMappingName }
	::= {qosIngressQosProfileMappingTable  1}

QosIngressQosProfileMappingEntry ::=
	SEQUENCE { 
qosIngressQosProfileMappingName     AsamProfileName,
		qosIngressQosProfileMappingIndex      AsamProfileIndex
			}

qosIngressQosProfileMappingName OBJECT-TYPE
	SYNTAX	AsamProfileName
	ACCESS	not-accessible
	STATUS  mandatory
	DESCRIPTION
		"A text string containing the name of this profile.
      ALCATEL NOTE:
                 ACCESS:     NA       USAGE:      NA
                 PERSIST:    YES       INSRVMOD:   NO
                 RANGE:      NA       DEFVALUE:   NA
                 UNITS:      NA       SPARSE:     NA
                 DESCR:      NA "
::= { qosIngressQosProfileMappingEntry 1}

qosIngressQosProfileMappingIndex OBJECT-TYPE
	SYNTAX	AsamProfileIndex
	ACCESS	read-only
	STATUS mandatory
	DESCRIPTION
		"This object is the Profile index. 
     ALCATEL NOTE:
                 ACCESS:     NA       USAGE:      NA
                 PERSIST:    YES       INSRVMOD:   NO
                 RANGE:      NA       DEFVALUE:   NA
                 UNITS:      NA       SPARSE:     NA
                 DESCR:      NA "
::= { qosIngressQosProfileMappingEntry 2}

qosLimQueueConfigurations OBJECT IDENTIFIER ::= {qosMIB 5}

qosLimQueueConfigTable OBJECT-TYPE
	SYNTAX	SEQUENCE OF QosLimQueueConfigEntry
	ACCESS	not-accessible
	STATUS	mandatory
	DESCRIPTION
	"This object contains a table which associates
	configurable queues on the LIM with queue profiles"
::= { qosLimQueueConfigurations 1 }
qosLimQueueConfigEntry OBJECT-TYPE
	SYNTAX 	QosLimQueueConfigEntry
	ACCESS 	not-accessible
	STATUS	mandatory
	DESCRIPTION
		"This table contains the LIM Queue configurations."
	INDEX {qosLimDslLinkIndex, qosLimDslQueueIndex}
::= {qosLimQueueConfigTable 1 }
QosLimQueueConfigEntry ::=
	SEQUENCE {	
                        qosLimDslLinkIndex	InterfaceIndex,
			qosLimDslQueueIndex	INTEGER,
			qosQueueProfileId	AsamProfilePointer,
			qosLimQueueShaperProfileId  AsamProfilePointer,
			qosLimQueueWeight  INTEGER,
			qosLimQueuePriority  INTEGER

				}

qosLimDslLinkIndex OBJECT-TYPE
	SYNTAX	InterfaceIndex
	ACCESS	not-accessible
	STATUS mandatory
	DESCRIPTION
	 "This field is used to index the physical interface
	 of a DSL link or UNI or LLID."
::= { qosLimQueueConfigEntry 1 }

qosLimDslQueueIndex OBJECT-TYPE
	SYNTAX	INTEGER (0..7)
	ACCESS	not-accessible
	STATUS mandatory
	DESCRIPTION
	 "This object is used to index the queue within the
	 scope of one DSL link on the EBLT LIM."
::= { qosLimQueueConfigEntry 2 }

qosQueueProfileId OBJECT-TYPE
	SYNTAX	AsamProfilePointer
	ACCESS	read-write
	STATUS mandatory
	DESCRIPTION
	 "This object contains a reference to an existing Queue
		 configuration profile. "
::= { qosLimQueueConfigEntry 3 }

qosLimQueueShaperProfileId OBJECT-TYPE
	SYNTAX	AsamProfilePointer
	ACCESS	read-write
	STATUS mandatory
	DESCRIPTION
	 "This object contains a reference to an existing shaper profile. 
      ALCATEL NOTE:
                 ACCESS:     NA       USAGE:      NA
                 PERSIST:    YES       INSRVMOD:   NO
                 RANGE:      NA       DEFVALUE:   NA
                 UNITS:      NA       SPARSE:     NA
                 DESCR:      NA "
DEFVAL { 0 }
::= { qosLimQueueConfigEntry 4 }

qosLimQueueWeight OBJECT-TYPE
	SYNTAX	INTEGER
	ACCESS	read-write
	STATUS mandatory
	DESCRIPTION
	 "This object contains a weight of the queue in the range 0..127. 
      ALCATEL NOTE:
                 ACCESS:     NA       USAGE:      NA
                 PERSIST:    YES       INSRVMOD:   NO
                 RANGE:      NA       DEFVALUE:   NA
                 UNITS:      NA       SPARSE:     NA
                 DESCR:      NA "
DEFVAL { 10 }
::= { qosLimQueueConfigEntry 5 }

qosLimQueuePriority OBJECT-TYPE
	SYNTAX	INTEGER
	ACCESS	read-write
	STATUS mandatory
	DESCRIPTION
	 "This object contains the priority of the queue in the range 1..8. It is used when the weights are the same for two queues. 8 means highest priority and 1 means lowest priority.
      ALCATEL NOTE:
                 ACCESS:     NA       USAGE:      NA
                 PERSIST:    YES       INSRVMOD:   NO
                 RANGE:      NA       DEFVALUE:   NA
                 UNITS:      NA       SPARSE:     NA
                 DESCR:      NA "
DEFVAL { 1 }
::= { qosLimQueueConfigEntry 6}

qosLimUpstreamQueueConfigTable OBJECT-TYPE
	SYNTAX	SEQUENCE OF QosLimUpstreamQueueConfigEntry
	ACCESS	not-accessible
	STATUS	mandatory
	DESCRIPTION
	"This object contains a table which associates
	configurable upstream queues on the LIM with queue profiles"
::= { qosLimQueueConfigurations 2 }
qosLimUpstreamQueueConfigEntry OBJECT-TYPE
	SYNTAX 	QosLimUpstreamQueueConfigEntry
	ACCESS 	not-accessible
	STATUS	mandatory
	DESCRIPTION
		"This table contains the upstream LIM Queue configurations."
	INDEX {qosLimUpstreamLinkIndex, qosLimUpstreamQueueIndex}
::= {qosLimUpstreamQueueConfigTable 1 }
QosLimUpstreamQueueConfigEntry ::=
	SEQUENCE {	qosLimUpstreamLinkIndex	InterfaceIndex,
			qosLimUpstreamQueueIndex	INTEGER,
			qosLimUpstreamQueueBandwidthProfileId  AsamProfilePointer,
			qosLimUpstreamQueueWeight  INTEGER,
			qosLimUpstreamQueuePriority  INTEGER,
			qosLimUpstreamQueueBandwidthSharing INTEGER

				}

qosLimUpstreamLinkIndex OBJECT-TYPE
	SYNTAX	InterfaceIndex
	ACCESS	not-accessible
	STATUS mandatory
	DESCRIPTION
	 "This field is used to index the physical interface
	 of a DSL link or ONT UNI or LLID."
::= { qosLimUpstreamQueueConfigEntry 1 }

qosLimUpstreamQueueIndex OBJECT-TYPE
	SYNTAX	INTEGER (0..7|255)
	ACCESS	not-accessible
	STATUS mandatory
	DESCRIPTION
	 "This object is used to index the queue within the
	 scope of one DSL link or ONT UNI.
The value 255 indicates the configuration is on the interface not on the queue."
::= { qosLimUpstreamQueueConfigEntry 2 }

qosLimUpstreamQueueBandwidthProfileId OBJECT-TYPE
	SYNTAX	AsamProfilePointer
	ACCESS	read-write
	STATUS mandatory
	DESCRIPTION
	 "This object contains a reference to an existing shaper profile. 
      ALCATEL NOTE:
                 ACCESS:     NA       USAGE:      NA
                 PERSIST:    YES       INSRVMOD:   NO
                 RANGE:      NA       DEFVALUE:   NA
                 UNITS:      NA       SPARSE:     NA
                 DESCR:      NA "
DEFVAL { 0 }
::= { qosLimUpstreamQueueConfigEntry 3 }

qosLimUpstreamQueueWeight OBJECT-TYPE
	SYNTAX	INTEGER
	ACCESS	read-write
	STATUS mandatory
	DESCRIPTION
	 "This object contains a weight of the queue in the range 0..127. 
      ALCATEL NOTE:
                 ACCESS:     NA       USAGE:      NA
                 PERSIST:    YES       INSRVMOD:   NO
                 RANGE:      NA       DEFVALUE:   NA
                 UNITS:      NA       SPARSE:     NA
                 DESCR:      NA "
DEFVAL { 10 }
::= { qosLimUpstreamQueueConfigEntry 4 }

qosLimUpstreamQueuePriority OBJECT-TYPE
	SYNTAX	INTEGER
	ACCESS	read-write
	STATUS mandatory
	DESCRIPTION
	 "This object contains the priority of the queue in the range 1..8. It is used when the weights are the same for two queues. 1 means highest priority and 8 means lowest priority.
      ALCATEL NOTE:
                 ACCESS:     NA       USAGE:      NA
                 PERSIST:    YES       INSRVMOD:   NO
                 RANGE:      NA       DEFVALUE:   NA
                 UNITS:      NA       SPARSE:     NA
                 DESCR:      NA "
DEFVAL { 1 }
::= { qosLimUpstreamQueueConfigEntry 5}

qosLimUpstreamQueueBandwidthSharing OBJECT-TYPE
	SYNTAX	INTEGER (1..3)
	ACCESS	read-write
	STATUS mandatory
	DESCRIPTION
	 "This object specifies whether shaper sharing is enabled or disabled. 1 = disabled, 2 = BW  or TCONT sharing enabled on a single UNI only, 3 = BW or TCONT sharing enabled on across UNIs of an ONT
      ALCATEL NOTE:
                 ACCESS:     NA       USAGE:      NA
                 PERSIST:    YES       INSRVMOD:   NO
                 RANGE:      1..3       DEFVALUE:  1
                 UNITS:      NA       SPARSE:     NA
                 DESCR:      NA "
DEFVAL { 1 }
::= { qosLimUpstreamQueueConfigEntry 6}

qosDslRecord OBJECT IDENTIFIER ::= {qosMIB 6}

qosDslRecordTable OBJECT-TYPE
	SYNTAX	SEQUENCE OF QosDslRecordEntry
	ACCESS	not-accessible
	STATUS	mandatory
	DESCRIPTION
	"This object contains a table which is used to store
QoS settings that are applicable on a DSL link or ONT UNI or ONT or PON or LLID.  "
::= { qosDslRecord 1 }
qosDslRecordEntry OBJECT-TYPE
	SYNTAX	QosDslRecordEntry
	ACCESS	not-accessible
	STATUS	mandatory
	DESCRIPTION
		"This table contains the per-DSL link QoS settings"
	INDEX {qosDslRecordInterfaceIndex}
::= {qosDslRecordTable 1}
QosDslRecordEntry ::=
	SEQUENCE {	qosDslRecordInterfaceIndex	InterfaceIndex,
			qosDslRecordSchedProfile	AsamProfilePointer,
			qosDslRecordCacProfile	AsamProfilePointer,
			qosDslRecordAvailableMcastBw	 INTEGER,
			qosDslRecordUsedMcastBw	INTEGER,
			qosDslRecordDslFrBw		INTEGER,
			qosDslRecordSchedNodeProfile	AsamProfilePointer,
			qosDslRecordDsNumQueue	INTEGER,
			qosDslRecordOntUsNumQueue	INTEGER,
			qosDslRecordAvailableUsUnicastBw	 INTEGER,
			qosDslRecordAvailableDsUnicastBw	 INTEGER,
			qosOntUpstreamQueueSharing				 TruthValue,
			qosOntDownstreamQueueSharing				 TruthValue,
			qosOntUniQueueStatsEnable			TruthValue

				}

qosDslRecordInterfaceIndex OBJECT-TYPE
	SYNTAX	InterfaceIndex
	ACCESS	not-accessible
	STATUS mandatory
	DESCRIPTION
	 "This field is used to index the physical interface
	of a DSL link or in the ONT UNI, ONT or PON or LLID."
::= { qosDslRecordEntry 1 }

qosDslRecordSchedProfile OBJECT-TYPE
	SYNTAX	AsamProfilePointer
	ACCESS	read-write
	STATUS mandatory
	DESCRIPTION
	 "This object stores the scheduler profile ID attached to the
	DSL link indexed by qosDslRecordInterfaceIndex This profile is not curently supported, SchedulerNodeProfile is to be used instead."
::= { qosDslRecordEntry 2 }

qosDslRecordCacProfile OBJECT-TYPE
	SYNTAX	AsamProfilePointer
	ACCESS	read-write
	STATUS mandatory
	DESCRIPTION
	 "This object stores the CAC profile ID attached to the
	DSL link or ONT UNI or PON indexed by qosDslRecordInterfaceIndex"
::= { qosDslRecordEntry 3 }

qosDslRecordAvailableMcastBw OBJECT-TYPE
	SYNTAX	INTEGER
	ACCESS	read-only
	STATUS mandatory
	DESCRIPTION
	"This object contains the maximum available bandwidth for
	 video multicast on an interface (Kilobits/sec). It is calculated
	 as: qosDslRecordDslFrBw - qosCacProfileResVoiceBw -
									
	qosCacProfileResDataBw
	where:
	'qosDslRecordDslFrBw' 	is the approximate net frame bandwidth
	calculated based on the minimum guaranteed raw bit rate or actual line 	rate read from interface management,
	'qosCacProfileResVoiceBw' 	is the reserved bandwidth for voice
	specified in the CAC profile attached to this DSL link, and
	'qosCacProfileResDataBw' is the reserved bandwidth for data
	specified in the same CAC profile mentioned earlier.
	For multicast admission control the minimum of this object and
	the qosCacProfileMaxMcastBw - read from the CAC profile
	attached to this DSL link - will be used."
::= { qosDslRecordEntry 4 }

qosDslRecordUsedMcastBw OBJECT-TYPE
	SYNTAX	INTEGER
	ACCESS	read-only
	STATUS mandatory
	DESCRIPTION
	 "This object contains the amount of bandwidth currently in use
	on an interface by known multicast streams (Kilobits/sec). "
::= { qosDslRecordEntry 5 }

qosDslRecordDslFrBw OBJECT-TYPE
	SYNTAX	INTEGER
	ACCESS	read-only
	STATUS mandatory
	DESCRIPTION
	 "This object contains the amount of frame net bandwidth
	available on a DSL link for transmitting Ethernet frames. It
	is calculated as the guaranteed raw sync rate of the DSL link,
	multiplied by a global ATM-overhead factor, (0.85 by default).
	You can change this value under the QoS Global Settings
	table."
::= { qosDslRecordEntry 6 }

qosDslRecordSchedNodeProfile OBJECT-TYPE
	SYNTAX	AsamProfilePointer
	ACCESS	read-write
	STATUS mandatory
	DESCRIPTION
	 "This object stores the scheduler Node profile ID attached to the
	DSL Line or ONT UNI or ONT indexed by InterfaceIndex of the DSL Line/UNI/ ONT"
::= { qosDslRecordEntry 7 }

qosDslRecordDsNumQueue OBJECT-TYPE
	SYNTAX	INTEGER
	ACCESS	read-write
	STATUS mandatory
	DESCRIPTION
	 "This object stores the number of downstream queues per UNI. This is settable for all UNIs on a given PON by specifying the InterfaceIndex of the PON in this table. The allowed values are 4 and 8. When there are services already configured on the ONT UNIs of a PON, this value cannot be changed by the operator."
	DEFVAL		{4}

::= { qosDslRecordEntry 8 }

qosDslRecordOntUsNumQueue OBJECT-TYPE
	SYNTAX	INTEGER
	ACCESS	read-write
	STATUS mandatory
	DESCRIPTION
	 "This object stores the number of upstream queues per UNI on an ONT. This is configured on an ONT basis with the IfIndex of the ONT as index. "
	DEFVAL		{8}

::= { qosDslRecordEntry 9 }

qosDslRecordAvailableUsUnicastBw OBJECT-TYPE
	SYNTAX	INTEGER
	ACCESS	read-only
	STATUS mandatory
	DESCRIPTION
	"This object contains the available upstream bandwidth for
	Unicast services on a PON interface on GLTs in kbps."
::= { qosDslRecordEntry 10}

qosDslRecordAvailableDsUnicastBw OBJECT-TYPE
	SYNTAX	INTEGER
	ACCESS	read-only
	STATUS mandatory
	DESCRIPTION
	"This object contains the available downstream bandwidth for
	Unicast services on a PON interface on GLTs in kbps"
::= { qosDslRecordEntry 11}

qosOntUpstreamQueueSharing OBJECT-TYPE
	SYNTAX	TruthValue
	ACCESS	read-write
	STATUS mandatory
	DESCRIPTION
	 "This object specifies whether upstream queue sharing is enabled or disabled per ONT. Enabled if True. The value of this object cannot be changed after UNIs are created on the ONT.
      ALCATEL NOTE:
                 ACCESS:     NA       USAGE:      NA
                 PERSIST:    YES       INSRVMOD:   NO
                 RANGE:      yes,no       DEFVALUE:   no
                 UNITS:      NA       SPARSE:     NA
                 DESCR:      NA "
DEFVAL { false }
::= { qosDslRecordEntry 12}

qosOntDownstreamQueueSharing OBJECT-TYPE
	SYNTAX	TruthValue
	ACCESS	read-write
	STATUS mandatory
	DESCRIPTION
	 "This object specifies whether downstream queue sharing is enabled or disabled per ONT. Enabled if True. The value of this object cannot be changed after UNIs are created on the ONT.
      ALCATEL NOTE:
                 ACCESS:     NA       USAGE:      NA
                 PERSIST:    YES       INSRVMOD:   NO
                 RANGE:      yes,no       DEFVALUE:   no
                 UNITS:      NA       SPARSE:     NA
                 DESCR:      NA "
DEFVAL { false }
::= { qosDslRecordEntry 13}

qosOntUniQueueStatsEnable OBJECT-TYPE
	SYNTAX	TruthValue
	ACCESS	read-write
	STATUS mandatory
	DESCRIPTION
	 "This object enables queue stats collection for a ONT UNI. Can be enabled only on 32 UNIs per GLT.
      ALCATEL NOTE:
                 ACCESS:     NA       USAGE:      NA
                 PERSIST:    YES       INSRVMOD:   NO
                 RANGE:      yes,no       DEFVALUE:   no
                 UNITS:      NA       SPARSE:     NA
                 DESCR:      NA "
DEFVAL { false }
::= { qosDslRecordEntry 14}

qosStatisticsAndData OBJECT IDENTIFIER ::= { qosMIB 7}

qosStatsP15mTable OBJECT-TYPE
	SYNTAX	SEQUENCE OF QosStatsP15mEntry
	ACCESS not-accessible
	STATUS	mandatory
	DESCRIPTION
	"This table contains the previous 15 minute QoS statistics on a
	per L3 LIM basis"
::= {qosStatisticsAndData 1 }

qosStatsP15mEntry OBJECT-TYPE
SYNTAX QosStatsP15mEntry
ACCESS not-accessible
STATUS mandatory
DESCRIPTION "An entry in the qosStatsP15mTable"
INDEX { eqptSlotId, qosStatsP15mIntervalNumber }
::= {qosStatsP15mTable 1 }

QosStatsP15mEntry ::= SEQUENCE
	{
		qosStatsP15mIntervalNumber	 		INTEGER,
		qosStatsP15mUpAggrBufOvflw 			Counter,
		qosStatsP15mUpObcAggrBufOvflw			Counter,
		qosStatsP15mDnObcAggrBufOvflw			Counter,
		qosStatsP15mDnUcAggrBufOvflw			Counter,
		qosStatsP15mDnMcAggrBufOvflw			Counter,
		qosStatsP15mObcInjectedBufOvflw			Counter,
		qosStatsP15mMeasuredTime			TimeTicks,
		qosStatsP15mPartialAggrBufOvflw			Counter64bit

	}
qosStatsP15mIntervalNumber 	OBJECT-TYPE
	SYNTAX	INTEGER (1..32)
	ACCESS not-accessible
	STATUS mandatory
	DESCRIPTION
	"A number between 1 and 32, which identifies the interval for which the
set of statistics is available. The interval identified by 1 is the
most recently completed 15 minute interval, and the interval identified
by N is the interval immediately preceding the one identified by N-1."
::= {qosStatsP15mEntry 1 }
qosStatsP15mUpAggrBufOvflw 	OBJECT-TYPE
	SYNTAX	Counter
	ACCESS read-only
	STATUS mandatory
	DESCRIPTION
	 "This object is used to count the number of buffer overflows
	on an L3 LIM module in the upstream direction on a 15 minute
	interval basis. The upstream direction on the LIM is non-blocking,
	hence this value should always read zero under normal working
	conditions. The reassembly buffers are also included in this
	counter. "
::= {qosStatsP15mEntry 2 }

qosStatsP15mUpObcAggrBufOvflw 	OBJECT-TYPE
	SYNTAX	Counter
	ACCESS read-only
	STATUS mandatory
	DESCRIPTION
	 "This object is used to count the number of buffer overflows
	on an L3 LIM module for the OBC-directed traffic upstream
	on a 15 minute	 interval basis. In some special conditions
	such as system startup or re-start packet loss may occur here
	but under normal circumstances this counter should read zero.
	There are 4 queues towards the OBC (upstream). This counter
	counts the buffer overflows for all 4 queues together."
::= {qosStatsP15mEntry 3 }
qosStatsP15mDnObcAggrBufOvflw 	OBJECT-TYPE
	SYNTAX	Counter
	ACCESS read-only
	STATUS mandatory
	DESCRIPTION
	 "This object is used to count the number of buffer overflows
	on an L3 LIM module for the OBC-directed traffic downstream
	on a 15 minute	 interval basis.
	Under normal circumstances this counter should always read zero.
	There are 4 queues towards the OBC (downstream). This counter
	counts the buffer overflows for all 4 queues together."
::= {qosStatsP15mEntry 4 }
qosStatsP15mDnUcAggrBufOvflw 	OBJECT-TYPE
	SYNTAX	Counter
	ACCESS read-only
	STATUS mandatory
	DESCRIPTION
	 "Previous 15 minute downstream buffer pool overflow
	On an L3 LIM module the buffer space is divided into groups
	per usage: downstream pool, upstream pool, and
	OBC-injected traffic pool. This object stores a counter for the
	event of total buffer overflow of the downstream unicast pool.
	This even should not occur. Queue fill-up and tail drop is a
	normal condition for data traffic (individual queues) but not for
	voice and video on demand services (individual queues).
	If the total downstream pool is filled, that means
	that non-QoS aware packet loss will occur. This event can happen
	if the memory was statistically over-allocated or there is an
	internal system error, which should be reported."
::= {qosStatsP15mEntry 5 }

qosStatsP15mDnMcAggrBufOvflw 	OBJECT-TYPE
	SYNTAX	Counter
	ACCESS read-only
	STATUS mandatory
	DESCRIPTION
	 "Previous 15 minute downstream multicast total buffer pool overflow
	On an L3 LIM module the buffer space is divided into groups
	per usage: downstream pool, upstream pool, multicast pool and
	OBC-injected traffic pool. This object stores a counter for the
	event of total buffer overflow of the downstream multicast pool.
	This even should be a rather rare event. On the long term,buffer
	overflow in the multicast pool may occur a few times a day less
	than a few tens under heavy multicast usage).This object is not implemented."
::= {qosStatsP15mEntry 6 }
qosStatsP15mObcInjectedBufOvflw OBJECT-TYPE
	SYNTAX	Counter
	ACCESS read-only
	STATUS mandatory
	DESCRIPTION
	 "Previous 15 minute for OBC-injected buffer overflow event on LIM
	This event happens if the processor cannot cope with the extensive
	load of the system and cannot reassemble a frame in due time.
	This event should not occur under normal working conditions.
	This counter is used for both upstream and downstream
	OBC-injected frames on an L3 LIM. This object is not implemented. "
::= {qosStatsP15mEntry 7 }
qosStatsP15mMeasuredTime 	OBJECT-TYPE
	SYNTAX	TimeTicks
	ACCESS read-only
	STATUS mandatory
	DESCRIPTION
	 "The amount of time, measured in seconds, that statistics
	for this entry have been counted."
::= {qosStatsP15mEntry 8 }
qosStatsP15mPartialAggrBufOvflw 	OBJECT-TYPE 
	SYNTAX	Counter64bit
	ACCESS read-only
	STATUS mandatory
	DESCRIPTION
	    "Previous 15 minute dropped lower traffic class packets due to global buffer occupancy threshold overflow. Currently the lower traffic class means BE+CL traffic. When global available buffer used up, the dropped BE+CL packets will be counted in other aggregation buffer overflow counters together with other traffic classes."
::= {qosStatsP15mEntry 9 }

qosStatsC15mTable OBJECT-TYPE
	SYNTAX	SEQUENCE OF QosStatsC15mEntry
	ACCESS not-accessible
	STATUS	mandatory
	DESCRIPTION
	"This table contains the current 15 minute QoS statistics
	 on a per L3 LIM basis"
::= {qosStatisticsAndData 2 }
qosStatsC15mEntry OBJECT-TYPE
	SYNTAX QosStatsC15mEntry
	ACCESS not-accessible
	STATUS mandatory
	DESCRIPTION "An entry in the qosStatsC15mTable"
	INDEX { eqptSlotId }
::= {qosStatsC15mTable 1 }
QosStatsC15mEntry ::= SEQUENCE
	{
		qosStatsC15mUpAggrBufOvflw 			Counter,
		qosStatsC15mUpObcAggrBufOvflw			Counter,
		qosStatsC15mDnObcAggrBufOvflw			Counter,
		qosStatsC15mDnUcAggrBufOvflw			Counter,
		qosStatsC15mDnMcAggrBufOvflw			Counter,
		qosStatsC15mObcInjectedBufOvflw			Counter,
		qosStatsC15mElapseTime				TimeTicks,
		qosStatsC15mMeasuredTime			TimeTicks,
		qosStatsC15mPartialAggrBufOvflw			Counter64bit

	}
qosStatsC15mUpAggrBufOvflw 	OBJECT-TYPE
	SYNTAX	Counter
	ACCESS read-only
	STATUS mandatory
	DESCRIPTION
	 "This object is used to count the number of buffer overflows
	on an L3 LIM module in the upstream direction on a 15 minute
	interval basis in the current measurement epoch.
	The upstream direction on the LIM is non-blocking,
	hence this value should read always zero under normal working
 	conditions. The reassembly buffers are included in this
	counter. "
::= {qosStatsC15mEntry 1 }

qosStatsC15mUpObcAggrBufOvflw 	OBJECT-TYPE
	SYNTAX	Counter
	ACCESS read-only
	STATUS mandatory
	DESCRIPTION
	 "This object is used to count the number of buffer overflows
	on an L3 LIM module for the OBC-directed traffic upstream
	on a 15 minute	 interval basis in the current measurement epoch.
	In some special conditions
	such as system startup or re-start packet loss may occur here
	but under normal circumstances this counter should read zero.
	There are 4 queues towards the OBC (upstream). This counter
	counts the buffer overflows for all 4 queues together. "
::= {qosStatsC15mEntry 2 }

qosStatsC15mDnObcAggrBufOvflw 	OBJECT-TYPE
	SYNTAX	Counter
	ACCESS read-only
	STATUS mandatory
	DESCRIPTION
	 "This object is used to count the number of buffer overflows
	on an L3 LIM module for the OBC-directed traffic downstream
	on a 15 minute	 interval basis in the current measurement epoch.
	Under normal circumstances this counter should always readm zero.
	There are 4 queues towards the OBC (downstream). This counter
	counts the buffer overflows for all 4 queues together."
::= {qosStatsC15mEntry 3 }
qosStatsC15mDnUcAggrBufOvflw 	OBJECT-TYPE
	SYNTAX	Counter
	ACCESS read-only
	STATUS mandatory
	DESCRIPTION
	 "Current 15 minute downstream buffer pool overflow
	On an L3 LIM module the buffer space is divided into groups
	per usage: downstream pool, upstream pool, and
	OBC-injected traffic pool. This object stores a counter for the
	event of total buffer overflow of the downstream unicast pool.
	This even should not occur. Queue fill-up and tail drop is a
	normal condition for data traffic (individual queues) but not for
	voice and video on demand services (individual queues).
	If the total downstream pool is filled, that means
	that QoS un-aware packet loss will occur. This event can happen
	if the memory was statistically over-allocated via configuration
	or there is an	 internal system error, which should be reported.
	If the downstream buffer pool was statistically
	over-allocated, an warning message will be raised in
	the Error Management."
::= {qosStatsC15mEntry 4 }
qosStatsC15mDnMcAggrBufOvflw 	OBJECT-TYPE
	SYNTAX	Counter
	ACCESS read-only
	STATUS mandatory
	DESCRIPTION
	 "Current 15 minute downstream multicast total buffer pool overflow
	On a LIM module the buffer space is divided into groups
	per usage: downstream pool, upstream pool, multicast pool and
	OBC-injected traffic pool. This object stores a counter for the
	event of total buffer overflow of the downstream multicast pool.
	This even should be a rather rare event. On the long term, buffer
	overflow in the multicast pool may occur a few times a day (less
	than a few tens under heavy multicast usage). This object is not implemented."
::= {qosStatsC15mEntry 5 }

qosStatsC15mObcInjectedBufOvflw OBJECT-TYPE
	SYNTAX	Counter
	ACCESS read-only
	STATUS mandatory
	DESCRIPTION
	 "Current 15 minute for OBC-injected buffer overflow event on LIM
	There is a reserved buffer pool for OBC-injected traffic which
	Under very heavy load conditions may eventually get full, and the
	LIM OBC will be unable to communicate with the external world for
	a very short time interval. If this counter reaches large numbers,
	(above ten) then there is an error condition and should be
	reported. This object is not implemented."
::= {qosStatsC15mEntry 6 }
qosStatsC15mElapseTime 	OBJECT-TYPE
	SYNTAX	TimeTicks
	ACCESS read-only
	STATUS mandatory
	DESCRIPTION
	 "The elapsed time interval since the last measurement epoch
	started."
::= {qosStatsC15mEntry 7 }
qosStatsC15mMeasuredTime 	OBJECT-TYPE
	SYNTAX	TimeTicks
	ACCESS read-only
	STATUS mandatory
	DESCRIPTION
	 "The amount of time, measured in seconds, that statistics
	for this entry have been counted."
::= {qosStatsC15mEntry 8 }
qosStatsC15mPartialAggrBufOvflw 	OBJECT-TYPE 
	SYNTAX	Counter64bit
	ACCESS read-only
	STATUS mandatory
	DESCRIPTION
	    "Current 15 minute dropped lower traffic class packets due to global buffer occupancy threshold overflow. Currently the lower traffic class means BE+CL traffic. When global available buffer used up, the dropped BE+CL packets will be counted in other aggregation buffer overflow counters together with other traffic classes."
::= {qosStatsC15mEntry 9 }

qosStatsP1dTable OBJECT-TYPE
	SYNTAX	SEQUENCE OF QosStatsP1dEntry
	ACCESS not-accessible
	STATUS	mandatory
	DESCRIPTION
	"This table contains the previous one day QoS statistics on a
	 per L3 LIM basis"
::= {qosStatisticsAndData 3 }
qosStatsP1dEntry OBJECT-TYPE
	SYNTAX	 QosStatsP1dEntry
	ACCESS	not-accessible
	STATUS 	mandatory
	DESCRIPTION
	"This table contains past one day QoS statistics"
	INDEX {eqptSlotId, qosStatsP1dIntervalNumber}
::=	{qosStatsP1dTable 1}
QosStatsP1dEntry ::= SEQUENCE
	{
		qosStatsP1dIntervalNumber			INTEGER,
		qosStatsP1dUpAggrBufOvflw 			Counter,
		qosStatsP1dUpObcAggrBufOvflw			Counter,
		qosStatsP1dDnObcAggrBufOvflw			Counter,
		qosStatsP1dDnUcAggrBufOvflw			Counter,
		qosStatsP1dDnMcAggrBufOvflw			Counter,
		qosStatsP1dObcInjectedBufOvflw			Counter,
		qosStatsP1dMeasuredTime				TimeTicks,
		qosStatsP1dPartialAggrBufOvflw			Counter64bit
	}
qosStatsP1dIntervalNumber 	OBJECT-TYPE
	SYNTAX	INTEGER (1)
	ACCESS not-accessible
	STATUS mandatory
	DESCRIPTION
	"Presently always 1, because day statistics are only stored for
	 one day. This may change in the future."
::= {qosStatsP1dEntry 1}
qosStatsP1dUpAggrBufOvflw 	OBJECT-TYPE
	SYNTAX	Counter
	ACCESS read-only
	STATUS mandatory
	DESCRIPTION
	 "Previous One Day Upstream Aggregate Buffer Overflow
	This object is used to count the number of buffer overflows
	on an L3 LIM module in the upstream direction on a one day
	interval basis. The upstream direction on the LIM is non-blocking,
	hence this value should read always zero under normal working
	conditions. The reassembly buffers are also included in this
	counter. "
::= {qosStatsP1dEntry 2}

qosStatsP1dUpObcAggrBufOvflw 	OBJECT-TYPE
	SYNTAX	Counter
	ACCESS read-only
	STATUS mandatory
	DESCRIPTION
	 "Previous One Day Upstream OBC Aggregate Buffer Overflow
	This object is used to count the number of buffer overflows
 	on an L3 LIM module for the OBC-directed traffic upstream
	on a one day interval basis. In some special conditions
	such as system startup or re-start packet loss may occur here
	but under normal circumstances this counter should read zero.
	There are 4 queues towards the OBC (upstream). This counter
	counts the buffer overflows for all 4 queues together."
::= {qosStatsP1dEntry 3}

qosStatsP1dDnObcAggrBufOvflw 	OBJECT-TYPE
	SYNTAX	Counter
	ACCESS read-only
	STATUS mandatory
	DESCRIPTION
	 "Previous One Day Downstream OBC Aggregate Buffer Overflow
	This object is used to count the number of buffer overflows
	on a L3 LIM module for the OBC-directed traffic downstream
	on a one day interval basis.
	Under normal circumstances this counter should always read zero.
	There are 4 queues towards the OBC (downstream). This counter
	counts the buffer overflows for all 4 queues together."
::= {qosStatsP1dEntry 4}
qosStatsP1dDnUcAggrBufOvflw 	OBJECT-TYPE
	SYNTAX	Counter
	ACCESS read-only
	STATUS mandatory
	DESCRIPTION
	 "Previous One Day Downstream buffer pool overflow
	On an L3 LIM module the buffer space is divided into groups
	per usage: downstream pool, upstream pool, and
	OBC-injected traffic pool. This object stores a counter for the
	event of total buffer overflow of the downstream unicast pool.
	This even should not occur. Queue fill-up and tail drop is a
	normal condition for data traffic (individual queues) but not for
	voice and video on demand services (individual queues).
	If the total downstream pool is filled, that means
	that non-QoS aware packet loss will occur. This event can happen
	if the memory was statistically over-allocated or there is an
	internal system error, which should be reported.
	If the downstream buffer pool was statistically over-allocated,
	a warning message will be raised in the Error management after
	each queue configuration."
::= {qosStatsP1dEntry 5}
qosStatsP1dDnMcAggrBufOvflw 	OBJECT-TYPE
	SYNTAX	Counter
	ACCESS read-only
	STATUS mandatory
	DESCRIPTION
	 "Previous One Day Downstream Multicast total buffer pool overflow
	On an L3 LIM module the buffer space is divided into groups
	per usage: downstream pool, upstream pool, multicast pool and
	OBC-injected traffic pool. This object stores a counter for the
	event of total buffer overflow of the downstream multicast pool.
	This even should be a rather rare event. On the long term,buffer
	overflow in the multicast pool may occur a few times a day (less
	than a few tens under heavy multicast usage). This object is not implemented."
::= {qosStatsP1dEntry 6}
qosStatsP1dObcInjectedBufOvflw OBJECT-TYPE
	SYNTAX	Counter
	ACCESS read-only
	STATUS mandatory
	DESCRIPTION
	 "Previous One Day OBC-injected buffer-pool overflow
	In some heavy load conditions this event may occur as the
	OBC-injected frames fill up completely the buffer space mreserved
	for this purpose. In heavy load conditions, this even may occur
	with a low probability. If this counter reads in the order of
	hundreds or above, then there is clearly an error. This object is not implemented. "
::= {qosStatsP1dEntry 7}
qosStatsP1dMeasuredTime 	OBJECT-TYPE
	SYNTAX	TimeTicks
	ACCESS read-only
	STATUS mandatory
	DESCRIPTION
	 "The actual time elapsed during which the measurement was made"
::= {qosStatsP1dEntry 8}

qosStatsP1dPartialAggrBufOvflw 	OBJECT-TYPE 
	SYNTAX	Counter64bit
	ACCESS read-only
	STATUS mandatory
	DESCRIPTION
	    "Previous One Day dropped lower traffic class packets due to global buffer occupancy threshold overflow. Currently the lower traffic class means BE+CL traffic. When global available buffer used up, the dropped BE+CL packets will be counted in other aggregation buffer overflow counters together with other traffic classes."
::= {qosStatsP1dEntry 9}

qosStatsC1dTable OBJECT-TYPE
	SYNTAX	SEQUENCE OF QosStatsC1dEntry
	ACCESS not-accessible
	STATUS	mandatory
	DESCRIPTION
	"This table contains the current one day QoS statistics
	 on a per LIM basis"
::= {qosStatisticsAndData 4 }
qosStatsC1dEntry OBJECT-TYPE
	SYNTAX QosStatsC1dEntry
	ACCESS not-accessible
	STATUS mandatory
	DESCRIPTION "An entry in the qosStatsC1dTable"
	INDEX { eqptSlotId }
::= {qosStatsC1dTable 1 }

QosStatsC1dEntry ::= SEQUENCE
	{
		qosStatsC1dUpAggrBufOvflw 			Counter,
		qosStatsC1dUpObcAggrBufOvflw			Counter,
		qosStatsC1dDnObcAggrBufOvflw			Counter,
		qosStatsC1dDnUcAggrBufOvflw			Counter,
		qosStatsC1dDnMcAggrBufOvflw			Counter,
		qosStatsC1dObcInjectedBufOvflw			Counter,
		qosStatsC1dElapseTime				TimeTicks,
		qosStatsC1dMeasuredTime				TimeTicks,
		qosStatsC1dPartialAggrBufOvflw			Counter64bit
	}

qosStatsC1dUpAggrBufOvflw 	OBJECT-TYPE
	SYNTAX	Counter
	ACCESS read-only
	STATUS mandatory
	DESCRIPTION
	 "This object is used to count the number of buffer overflows
	on L3 LIM modules in the upstream direction on a one day
	interval basis in the current measurement epoch.
	The upstream direction on the LIM is non-blocking,
	hence this value should read always zero under normal working
	conditions. The reassembly buffers overflows are also
	included in this counter."
::= {qosStatsC1dEntry 1 }

qosStatsC1dUpObcAggrBufOvflw 	OBJECT-TYPE
	SYNTAX	Counter
	ACCESS read-only
	STATUS mandatory
	DESCRIPTION
	 "This object is used to count the number of buffer overflows
	on L3 LIM modules for the OBC-directed traffic upstream
	on a one day interval basis in the current measurement epoch.
	In some special conditions
	such as system startup or re-start packet loss may occur here
	but under normal circumstances this counter should read zero.
	There are 4 queues towards the OBC (upstream). This counter
	counts the buffer overflows for all 4 queues together. "
::= {qosStatsC1dEntry 2 }
qosStatsC1dDnObcAggrBufOvflw 	OBJECT-TYPE
	SYNTAX	Counter
	ACCESS read-only
	STATUS mandatory
	DESCRIPTION
	 "This object is used to count the number of buffer overflows
	on an L3 LIM module for the OBC-directed traffic downstream
	on a one day interval basis in the current measurement epoch.
	Under normal circumstances this counter should always read zero.
	There are 4 queues towards the OBC (downstream). This counter
	counts the buffer overflows for all 4 queues together."
::= {qosStatsC1dEntry 3 }
qosStatsC1dDnUcAggrBufOvflw 	OBJECT-TYPE
	SYNTAX	Counter
	ACCESS read-only
	STATUS mandatory
	DESCRIPTION
	 "Current One Day Downstream buffer pool overflow.
	On an L3 LIM module the buffer space is divided into groups
	per usage: downstream pool, upstream pool, and
	OBC-injected traffic pool. This object stores a counter for the
	event of total buffer overflow of the downstream unicast pool.
	This even should not occur. Queue fill-up and tail drop is a
	normal condition for data traffic (individual queues) but not for
	voice and video on demand services (individual queues).
	If the total downstream pool is filled, that means
	that QoS un-aware packet loss will occur. This event can happen
	if the memory was statistically over-allocated or there is an
	internal system error, which should be reported.
	If the downstream buffer pool was statistically over-allocated,
	a warning message will be raised in the Error management after
	each queue configuration."
::= {qosStatsC1dEntry 4 }
qosStatsC1dDnMcAggrBufOvflw 	OBJECT-TYPE
	SYNTAX	Counter
	ACCESS read-only
	STATUS mandatory
	DESCRIPTION
	 "Current one day downstream multicast total buffer pool overflow
	On a LIM module the buffer space is divided into groups
	per usage: downstream pool, upstream pool, multicast pool and
	OBC-injected traffic pool. This object stores a counter for the
	event of total buffer overflow of the downstream multicast pool.
	This even should be a rather rare event. On the long term,buffer
	overflow in the multicast pool may occur a few times a day (less
	than a few tens under heavy multicast usage). This object is not implemented."
::= {qosStatsC1dEntry 5}

qosStatsC1dObcInjectedBufOvflw OBJECT-TYPE
	SYNTAX	Counter
	ACCESS read-only
	STATUS mandatory
	DESCRIPTION
	 "Current One Day OBC-injected buffer overflow event on EBLT LIMs.
	There is a reserved buffer pool for OBC-injected traffic which
	Under very heavy load conditions may eventually get full, and the
	LIM OBC will be unable to communicate with the external world for
	a very short time interval. If this counter reaches large numbers,
	(above ten) then there is an error condition and should be
	reported. This object is not implemented."
::= {qosStatsC1dEntry 6 }
qosStatsC1dElapseTime 	OBJECT-TYPE
	SYNTAX	TimeTicks
	ACCESS read-only
	STATUS mandatory
	DESCRIPTION
	 "The elapsed time interval since the last measurement epoch
	started."
::= {qosStatsC1dEntry 7 }
qosStatsC1dMeasuredTime 	OBJECT-TYPE
	SYNTAX	TimeTicks
	ACCESS read-only
	STATUS mandatory
	DESCRIPTION
	 "The measured time interval since the last measurement epoch
	started."
::= {qosStatsC1dEntry 8 }
qosStatsC1dPartialAggrBufOvflw OBJECT-TYPE 
	SYNTAX	Counter64bit
	ACCESS read-only
	STATUS mandatory
	DESCRIPTION
	    "Current One Day dropped lower traffic class packets due to global buffer occupancy threshold overflow. Currently the lower traffic class means BE+CL traffic. When global available buffer used up, the dropped BE+CL packets will be counted in other aggregation buffer overflow counters together with other traffic classes."
::= {qosStatsC1dEntry 9 }

qosStatsTotalTable OBJECT-TYPE
	SYNTAX	SEQUENCE OF QosStatsTotalEntry
	ACCESS not-accessible
	STATUS	mandatory
	DESCRIPTION
	"This table contains the current one day QoS statistics
	 per L3 LIM"
::= {qosStatisticsAndData 5 }
qosStatsTotalEntry OBJECT-TYPE
	SYNTAX QosStatsTotalEntry
	ACCESS not-accessible
	STATUS mandatory
	DESCRIPTION "An entry in the qosStatsTotalTable"
	INDEX { eqptSlotId }
::= {qosStatsTotalTable 1 }

QosStatsTotalEntry ::= SEQUENCE
	{
		qosStatsTotalUpAggrBufOvflw 			Counter,
		qosStatsTotalUpObcAggrBufOvflw			Counter,
		qosStatsTotalDnObcAggrBufOvflw			Counter,
		qosStatsTotalDnUcAggrBufOvflw			Counter,
		qosStatsTotalDnMcAggrBufOvflw			Counter,
		qosStatsTotalObcInjectedBufOvflw		Counter,
		qosStatsTotalElapseTime				TimeTicks,
		qosStatsTotalMeasuredTime			TimeTicks,
		qosStatsValid15mIntervals			INTEGER,
		qosStatsValid1dIntervals			INTEGER,
		qosTotalPolicersInUse				INTEGER,
		qosPolicersInUseVlan				INTEGER,
		qosPolicersInUseDot1X				INTEGER,
		qosPolicersInUsePPP				INTEGER,
        qosPolicersInUseIp			        INTEGER,
		qosPolicersInUseSubFlow				INTEGER,
		qosStatsTotalFanOutPassBytes			Counter64bit,
		qosStatsTotalFanOutPassFrames			Counter64bit,
		qosStatsTotalPartialAggrBufOvflw		Counter64bit
	}
qosStatsTotalUpAggrBufOvflw 	OBJECT-TYPE
	SYNTAX	Counter
	ACCESS read-only
	STATUS mandatory
	DESCRIPTION
	 "This object is used to count the number of buffer overflows
	per L3 LIM module in the upstream direction
	since the statistics were last reset.
	The upstream direction on the LIM is non-blocking,
	hence this value should read always zero under normal working
	conditions. The reassembly buffer overflows are also
	included in this counter."
::= {qosStatsTotalEntry 1}

qosStatsTotalUpObcAggrBufOvflw 	OBJECT-TYPE
	SYNTAX	Counter
	ACCESS read-only
	STATUS mandatory
	DESCRIPTION
	 "This object is used to count the number of buffer overflows
	on a LIM module for the OBC-directed traffic upstream
	since the statistic was last reset.
	In some special conditions
	such as system startup or re-start packet loss may occur here
	but under normal circumstances this counter should read zero.
	There are 4 queues towards the OBC (upstream). This counter
	counts the buffer overflows for all 4 queues together."
::= {qosStatsTotalEntry 2}
qosStatsTotalDnObcAggrBufOvflw 	OBJECT-TYPE
	SYNTAX	Counter
	ACCESS read-only
	STATUS mandatory
	DESCRIPTION
	 "This object is used to count the number of buffer overflows
	on a LIM module for the OBC-directed traffic downstream
	since the statistic was last reset.
	Under normal circumstances this counter should always read zero.
	There are 4 queues towards the OBC (downstream). This counter
	counts the buffer overflows for all 4 queues together."
::= {qosStatsTotalEntry 3}
qosStatsTotalDnUcAggrBufOvflw 	OBJECT-TYPE
	SYNTAX	Counter
	ACCESS read-only
	STATUS mandatory
	DESCRIPTION
	 "Total Downstream buffer pool overflow.
	On an L3 LIM module the buffer space is divided into groups
	per usage: downstream pool, upstream pool, and
	OBC-injected traffic pool. This object stores a counter for the
	event of total buffer overflow of the downstream unicast pool.
	This even should not occur. Queue fill-up and tail drop is a
	normal condition for data traffic (individual queues) but not for
	voice and video on demand services (individual queues).
	If the total downstream pool is filled, that means
	that QoS un-aware packet loss will occur. This event can happen
	if the memory was statistically over-allocated or there is an
	internal system error, which should be reported.
	If the downstream buffer pool was statistically over-allocated,
	a warning message will be raised in the Error management after
	each queue configuration."
::= {qosStatsTotalEntry 4}
qosStatsTotalDnMcAggrBufOvflw 	OBJECT-TYPE
	SYNTAX	Counter
	ACCESS read-only
	STATUS mandatory
	DESCRIPTION
	 "Total Downstream Multicast Aggregate buffer pool overflow
	On L3 LIM modules the buffer space is divided into groups
	per usage: downstream pool, upstream pool, multicast pool and
	OBC-injected traffic pool. This object stores a counter for the
	event of total buffer overflow of the downstream multicast pool.
	This even should be a rather rare event. On the long term, buffer
	overflow in the multicast pool may occur a few times a day (less
	than a few tens under heavy multicast usage). This object is not implemented."
::= {qosStatsTotalEntry 5}
qosStatsTotalObcInjectedBufOvflw OBJECT-TYPE
	SYNTAX	Counter
	ACCESS read-only
	STATUS mandatory
	DESCRIPTION
	 "Total OBC-injected buffer overflow event on EBLT LIMs
	There is a reserved buffer pool for OBC-injected traffic which
	Under very heavy load conditions may eventually get full, and the
	LIM OBC will be unable to communicate with the external world for
	a very short time interval. This object is not implemented."
::= {qosStatsTotalEntry 6}
qosStatsTotalElapseTime 	OBJECT-TYPE
	SYNTAX	TimeTicks
	ACCESS read-only
	STATUS mandatory
	DESCRIPTION
	 "The elapsed time interval since the last measurement epoch
	started."
::= {qosStatsTotalEntry 7}
qosStatsTotalMeasuredTime 	OBJECT-TYPE
	SYNTAX	TimeTicks
	ACCESS read-only
	STATUS mandatory
	DESCRIPTION
	 "The measured time interval since the last measurement epoch
	started."
::= {qosStatsTotalEntry 8}
qosStatsValid15mIntervals OBJECT-TYPE
	SYNTAX INTEGER (0..96)
	ACCESS read-only
	STATUS mandatory
	DESCRIPTION
	"This object stores the number of statistics of 15 minutes
	collected so far. At most 96 such entries are stored."
::= { qosStatsTotalEntry 9}
qosStatsValid1dIntervals OBJECT-TYPE
	SYNTAX INTEGER (0..1)
	ACCESS read-only
	STATUS mandatory
	DESCRIPTION
	" This object stores the number of statistics of one day
	collected so far. At most one entry is stored from the past."
::= { qosStatsTotalEntry 10}
qosTotalPolicersInUse OBJECT-TYPE
	SYNTAX INTEGER
	ACCESS read-only
	STATUS mandatory
	DESCRIPTION
	 "This object shows the total number of policers in use per LIM.
The interface level policers are managed in hardware in pairs, so even if a
Session is using both up and downstream policers, it is counted as two policer.
But sub-flow is for single direction so a sub-flow policer is counted as one
actual policer.
 "
::= {qosStatsTotalEntry 11}
qosPolicersInUseVlan OBJECT-TYPE
	SYNTAX INTEGER
	ACCESS read-only
	STATUS mandatory
	DESCRIPTION
	 "This object shows the number of policers in use by static
	sessions (PVC, PVC.VLAN) per L3 LIM. "
::= {qosStatsTotalEntry 12}
qosPolicersInUseDot1X OBJECT-TYPE
	SYNTAX INTEGER
	ACCESS read-only
	STATUS mandatory
	DESCRIPTION
	 "This object shows the number of policers in use by Dot1X
	sessions per L3 LIM. "
::= {qosStatsTotalEntry 13}
qosPolicersInUsePPP OBJECT-TYPE
	SYNTAX INTEGER
	ACCESS read-only
	STATUS mandatory
	DESCRIPTION
	 "This object shows the number of policers in use by PPP
	sessions per L3 LIM."
::= {qosStatsTotalEntry 14}

qosPolicersInUseIp OBJECT-TYPE
	SYNTAX INTEGER
	ACCESS read-only
	STATUS mandatory
	DESCRIPTION
	"This object shows the number of policers in use by Ip
	sessions/interfaces per L3 LIM."
::= {qosStatsTotalEntry 15}

qosPolicersInUseSubFlow OBJECT-TYPE
	SYNTAX INTEGER
	ACCESS read-only
	STATUS mandatory
	DESCRIPTION
	    "This object shows the number of policers in use by sub-flow
 per L3 LIM."
::= {qosStatsTotalEntry 16}

qosStatsTotalFanOutPassBytes 	OBJECT-TYPE 
	SYNTAX	Counter64bit
	ACCESS read-only
	STATUS mandatory
	DESCRIPTION
"This object is used to count the number of LIM physical bus fan out passed bytes per LIM module at subscriber side since the statistics were last reset. Here the physical bus can refer to Utopia II, POS-II or even GE port of Ethernet LT. In fact it is the sum of passed bytes of all queues at subscriber side."
::= {qosStatsTotalEntry 17}

qosStatsTotalFanOutPassFrames 	OBJECT-TYPE 
	SYNTAX	Counter64bit
	ACCESS read-only
	STATUS mandatory
	DESCRIPTION
"This object is used to count the number of LIM physical bus fan out passed frames per LIM module at subscriber side since the statistics were last reset. Here the physical bus can refer to Utopia II, POS-II or even GE port of Ethernet LT. In fact it is the sum of passed frames of all queues at subscriber side."
::= {qosStatsTotalEntry 18}

qosStatsTotalPartialAggrBufOvflw 	OBJECT-TYPE 
	SYNTAX	Counter64bit
	ACCESS read-only
	STATUS mandatory
	DESCRIPTION
	    "This object is used to count the number of buffer overflows
		 on a LIM module for the dropped lower traffic class packets due to global buffer occupancy threshold overflow since the statistic was last reset. Currently the lower traffic class means BE+CL traffic. When global available buffer used up, the dropped BE+CL packets will be counted in other aggregation buffer overflow counters together with other traffic classes. "
::= {qosStatsTotalEntry 19}

qosGlobalSettings OBJECT IDENTIFIER ::= { qosStatisticsAndData 6 }
qosGlobalCacSettings OBJECT IDENTIFIER ::= { qosGlobalSettings 1 }
qosAtmOverheadFactor OBJECT-TYPE
	SYNTAX INTEGER (1..100)
	ACCESS read-write
	STATUS mandatory
	DESCRIPTION
	 "QoS ATM Overhead Factor
	This object stores an appropriate value to estimate the bandwidth
	Overhead introduced by the ATM layer. It takes values between 1
	100, which is then normalized to (0.01, 1)
	Eth_BW = ATM_BW * qosAtmOverheadFactor/100
	The default value is 85 (leaving 15% overhead for ATM/AAL5/LLC 
	Encapsulation. As the precise overhead depends also on the Ethernet 
	frame size,
	this object can be used to tune the overhead factor is the
	factory default is considered too optimistic or too conservative."
::= {qosGlobalCacSettings 1 }

qosEthEfmOverheadFactor OBJECT-TYPE
	SYNTAX INTEGER (1..100)
	ACCESS read-write
	STATUS mandatory
	DESCRIPTION
	    "QoS Eth Efm Overhead Factor
		 This object stores an appropriate value to estimate the bandwidth
		 Overhead introduced by the Efm layer. It takes values between 1
		 100, which is then normalized to (0.01, 1)
				Eth_BW = EFM_BW * qosEthEfmOverheadFactor/100
		The default value is 97 (leaving 3% overhead for EFM
		Encapsulation. 
		As the precise overhead depends also on the Ethernet frame size,
		this object can be used to tune the overhead factor is the factory
		default is considered too optimistic or too conservative."
	DEFVAL		{97}
::= {qosGlobalCacSettings 2 }

qosCacModeSelection OBJECT-TYPE
	SYNTAX INTEGER (1..3)
	ACCESS read-write
	STATUS mandatory
	DESCRIPTION
	    "QoS CAC mode selection
This object stores an global CAC mode selection switch. It takes values between 1 to 3. 1 means no CAC in system. 2 means do CAC based on minimum synchronized rate. 3 means do CAC based on actual line rate."
	DEFVAL		{2}
::= {qosGlobalCacSettings 3}

qosGlobalDslPolicerSettings OBJECT IDENTIFIER ::= { qosGlobalSettings 2 }
qosDslControlPktRate OBJECT-TYPE
	SYNTAX INTEGER (1..64)
	ACCESS read-write
	STATUS mandatory
	DESCRIPTION
	"This object can be used to police the user incoming packets on all
	pvc's ( for all protocols) of a dsl line. It takes values between
	1 and 64 pps."
       	DEFVAL {15} 
::= {qosGlobalDslPolicerSettings 1 }

qosDslControlPktBurst OBJECT-TYPE
	SYNTAX INTEGER (1..128)
	ACCESS read-write
	STATUS mandatory
	DESCRIPTION
	"This object can be used to police the user incoming packets on all
	pvc's ( for all protocols) of a dsl line. It takes values between
	1 and 128 packets."
       	DEFVAL {10}
::= {qosGlobalDslPolicerSettings 2 }

qosLimQueueStatsP15mTable OBJECT-TYPE
	SYNTAX	SEQUENCE OF QosLimQueueStatsP15mEntry
	ACCESS  not-accessible
	STATUS	mandatory
	DESCRIPTION
	"This table contains the previous 15 minute QoS statistics on a 
	per EBLT LIM basis"
::= {qosStatisticsAndData 7 }

qosLimQueueStatsP15mEntry OBJECT-TYPE
    SYNTAX      QosLimQueueStatsP15mEntry
    ACCESS      not-accessible
    STATUS      mandatory
    DESCRIPTION "An entry in the qosLimQueueStatsP15mTable"
    INDEX      {qosLimQueueStatsP15mLineLinkIndex, qosLimQueueStatsP15mLineQueueIndex, qosLimQueueStatsP15mIntervalNumber }
    ::=  {qosLimQueueStatsP15mTable 1 }

QosLimQueueStatsP15mEntry ::= SEQUENCE
   {
      qosLimQueueStatsP15mLineLinkIndex               InterfaceIndex,
      qosLimQueueStatsP15mLineQueueIndex           INTEGER,
      qosLimQueueStatsP15mIntervalNumber           INTEGER,
      qosLimQueueStatsP15mLineQueueLoad               INTEGER,
      qosLimQueueStatsP15mPassBytes                Counter64bit,
      qosLimQueueStatsP15mPassFrames               Counter64bit,
      qosLimQueueStatsP15mDiscBytes                Counter64bit,
      qosLimQueueStatsP15mDiscFrames               Counter64bit,
      qosLimQueueStatsP15mMeasuredTime             TimeTicks
   }

qosLimQueueStatsP15mLineLinkIndex 	OBJECT-TYPE 
	SYNTAX	InterfaceIndex
	ACCESS read-only
	STATUS mandatory
	DESCRIPTION
	    " This object is used to index the physical line such as DSL line on the LIM."
::= {qosLimQueueStatsP15mEntry 1 }

qosLimQueueStatsP15mLineQueueIndex 	OBJECT-TYPE 
	SYNTAX	INTEGER (0..8)
	ACCESS read-only
	STATUS mandatory
	DESCRIPTION
	    " This object is used to index the queue within the 
		 scope of one physical link on the LIM. Index 8 means total physical line. Queue index 0 to 3 correspond to current queue 0 to queue 3. Currently queue index 4 to 7 are always null as only four queue per line supported."
::= {qosLimQueueStatsP15mEntry 2 }

qosLimQueueStatsP15mIntervalNumber 	OBJECT-TYPE 
	SYNTAX	INTEGER (1)
	ACCESS not-accessible
	STATUS mandatory
	DESCRIPTION
	"A number, which identifies the interval for which the 
    set of statistics is available. The interval identified by 1 is the 
    most recently completed 15 minute interval, and the interval identified 
    by N is the interval immediately preceding the one identified by N-1. currently only 1 interval supported."
::= {qosLimQueueStatsP15mEntry 3 }

qosLimQueueStatsP15mLineQueueLoad 	OBJECT-TYPE 
	SYNTAX	INTEGER
	ACCESS read-only
	STATUS mandatory
	DESCRIPTION
	    "This object is used to show the queue load percentage. It means the average load percentage in this 15 minutes. If queue index is 8, the load is for physical line. Its range is from 0 to 100. System should check its value in the range of 0 to 100. If calculation result is above 100, system should round it to 100."
::= {qosLimQueueStatsP15mEntry 4 }

qosLimQueueStatsP15mPassBytes 	OBJECT-TYPE 
	SYNTAX	Counter64bit
	ACCESS read-only
	STATUS mandatory
	DESCRIPTION
	    "Previous 15 minute passed bytes in this queue. If queue index is 8, it means the sum of each queue of this physical line."
::= {qosLimQueueStatsP15mEntry 5 }

qosLimQueueStatsP15mPassFrames 	OBJECT-TYPE 
	SYNTAX	Counter64bit
	ACCESS read-only
	STATUS mandatory
	DESCRIPTION
	    " Previous 15 minute passed frames in this queue. If queue index is 8, it means the sum of each queue of this physical line."
::= {qosLimQueueStatsP15mEntry 6 }

qosLimQueueStatsP15mDiscBytes OBJECT-TYPE 
	SYNTAX	Counter64bit
	ACCESS read-only
	STATUS mandatory
	DESCRIPTION
	    " Previous 15 minutes discarded bytes in this queue. If queue index is 8, it means the sum of each queue of this physical line."
::= {qosLimQueueStatsP15mEntry 7  }

qosLimQueueStatsP15mDiscFrames OBJECT-TYPE 
	SYNTAX	Counter64bit
	ACCESS read-only
	STATUS mandatory
	DESCRIPTION
	    " Previous 15 minutes discarded frames in this queue. If queue index is 8, it means the sum of each queue of this physical line."
::= {qosLimQueueStatsP15mEntry 8  }
 
qosLimQueueStatsP15mMeasuredTime 	OBJECT-TYPE 
	SYNTAX	TimeTicks
	ACCESS read-only
	STATUS mandatory
	DESCRIPTION
	    "The amount of time, measured in seconds, that statistics 
		 for this entry have been counted."
::= {qosLimQueueStatsP15mEntry 9  }

qosLimQueueStatsC15mTable OBJECT-TYPE
	SYNTAX	SEQUENCE OF QosLimQueueStatsC15mEntry
	ACCESS not-accessible
	STATUS	mandatory
	DESCRIPTION
	"This table contains the current 15 minute QoS statistics on a 
	per EBLT LIM basis"
::= {qosStatisticsAndData 8 }

qosLimQueueStatsC15mEntry OBJECT-TYPE
    SYNTAX      QosLimQueueStatsC15mEntry
    ACCESS      not-accessible
    STATUS      mandatory
    DESCRIPTION "An entry in the qosLimQueueStatsC15mTable"
    INDEX      { qosLimQueueStatsC15mLineLinkIndex, qosLimQueueStatsC15mLineQueueIndex}
    ::=  {qosLimQueueStatsC15mTable 1 }

QosLimQueueStatsC15mEntry ::= SEQUENCE
	{
		qosLimQueueStatsC15mLineLinkIndex		 			InterfaceIndex,
		qosLimQueueStatsC15mLineQueueIndex				INTEGER,
		qosLimQueueStatsC15mLineQueueLoad					INTEGER,
		qosLimQueueStatsC15mPassBytes						Counter64bit,
		qosLimQueueStatsC15mPassFrames					Counter64bit,
		qosLimQueueStatsC15mDiscBytes						Counter64bit,
		qosLimQueueStatsC15mDiscFrames					Counter64bit,
		qosLimQueueStatsC15mElapseTime					TimeTicks,
		qosLimQueueStatsC15mMeasuredTime					TimeTicks
	}

qosLimQueueStatsC15mLineLinkIndex 	OBJECT-TYPE 
	SYNTAX	InterfaceIndex
	ACCESS read-only
	STATUS mandatory
	DESCRIPTION
	    " This object is used to index the physical line such as DSL line on the LIM."
::= {qosLimQueueStatsC15mEntry 1 }

qosLimQueueStatsC15mLineQueueIndex 	OBJECT-TYPE 
	SYNTAX	INTEGER (0..8)
	ACCESS read-only
	STATUS mandatory
	DESCRIPTION
	    " This object is used to index the queue within the 
		 scope of one physical link on the LIM. Index 8 means total physical line. Queue index 0 to 3 correspond to current queue 0 to queue 3. Currently queue index 4 to 7 are always null as only four queue per line supported."
::= {qosLimQueueStatsC15mEntry 2 }

qosLimQueueStatsC15mLineQueueLoad 	OBJECT-TYPE 
	SYNTAX	INTEGER
	ACCESS read-only
	STATUS mandatory
	DESCRIPTION
	    "This object is used to show the queue load percentage. It means the average load percentage in  measured time of this 15 minutes. If queue index is 8, the load is for physical line. Its range is from 0 to around 100. System should check its value in the range of 0 to 100. If calculation result is above 100, system should round it to 100."
::= {qosLimQueueStatsC15mEntry 3 }

qosLimQueueStatsC15mPassBytes 	OBJECT-TYPE 
	SYNTAX	Counter64bit
	ACCESS read-only
	STATUS mandatory
	DESCRIPTION
	    "Current 15 minute passed bytes in this queue. If queue index is 8, it means the sum of each queue of this physical line."
::= {qosLimQueueStatsC15mEntry 4 }

qosLimQueueStatsC15mPassFrames 	OBJECT-TYPE 
	SYNTAX	Counter64bit
	ACCESS read-only
	STATUS mandatory
	DESCRIPTION
	    " Current 15 minute passed frames in this queue. If queue index is 8, it means the sum of each queue of this physical line."
::= {qosLimQueueStatsC15mEntry 5 }

qosLimQueueStatsC15mDiscBytes OBJECT-TYPE 
	SYNTAX	Counter64bit
	ACCESS read-only
	STATUS mandatory
	DESCRIPTION
	    " Current 15 minutes discarded bytes in this queue. If queue index is 8, it means the sum of each queue of this physical line."
::= {qosLimQueueStatsC15mEntry 6  }

qosLimQueueStatsC15mDiscFrames OBJECT-TYPE 
	SYNTAX	Counter64bit
	ACCESS read-only
	STATUS mandatory
	DESCRIPTION
	    " Current 15 minutes discarded frames in this queue. If queue index is 8, it means the sum of each queue of this physical line."
::= {qosLimQueueStatsC15mEntry 7  }

qosLimQueueStatsC15mElapseTime 	OBJECT-TYPE 
	SYNTAX	TimeTicks
	ACCESS read-only
	STATUS mandatory
	DESCRIPTION
	    "The elapsed time interval since the last measurement epoch started."
::= {qosLimQueueStatsC15mEntry 8  }

qosLimQueueStatsC15mMeasuredTime 	OBJECT-TYPE 
	SYNTAX	TimeTicks
	ACCESS read-only
	STATUS mandatory
	DESCRIPTION
	    "The amount of time, measured in seconds, that statistics 
		 for this entry have been counted."
::= {qosLimQueueStatsC15mEntry 9  }

qosFanOutLoadStatsP15mTable OBJECT-TYPE
	SYNTAX	SEQUENCE OF QosFanOutLoadStatsP15mEntry
	ACCESS not-accessible
	STATUS	mandatory
	DESCRIPTION
	"This table contains the previous 15 minute QoS statistics on a 
	per EBLT LIM basis"
::= {qosStatisticsAndData 9 }

qosFanOutLoadStatsP15mEntry OBJECT-TYPE
    SYNTAX      QosFanOutLoadStatsP15mEntry
    ACCESS      not-accessible
    STATUS      mandatory
    DESCRIPTION "An entry in the qosFanOutLoadStatsP15mTable"
    INDEX      { eqptSlotId, qosFanOutLoadStatsP15mTrafficClass, qosFanOutLoadStatsP15mIntervalNumber }
    ::=  {qosFanOutLoadStatsP15mTable 1 }

QosFanOutLoadStatsP15mEntry ::= SEQUENCE
	{
		qosFanOutLoadStatsP15mTrafficClass	 			INTEGER,
		qosFanOutLoadStatsP15mIntervalNumber	 			INTEGER,
		qosFanOutLoadStatsP15mLoad						INTEGER,
		qosFanOutLoadStatsP15mPassBytes					Counter64bit,
		qosFanOutLoadStatsP15mPassFrames					Counter64bit,
		qosFanOutLoadStatsP15mMeasuredTime				TimeTicks
	}

qosFanOutLoadStatsP15mTrafficClass 	OBJECT-TYPE 
	SYNTAX	INTEGER (0..8)
	ACCESS read-only
	STATUS mandatory
	DESCRIPTION
	    " This object is used to index the traffic class on the LIM. Index 8 means total traffic. Index 0 to 7 refer to the traffic class with different priority, the same sequence with queue index definition."
::= {qosFanOutLoadStatsP15mEntry 1 }

qosFanOutLoadStatsP15mIntervalNumber 	OBJECT-TYPE 
	SYNTAX	INTEGER (1..96)
	ACCESS not-accessible
	STATUS mandatory
	DESCRIPTION
	"A number between 1 and 96, which identifies the interval for which the set of statistics is available. The interval identified by 1 is the most recently completed 15 minute interval, and the interval identified by N is the interval immediately preceding the one identified by N-1."
::= {qosFanOutLoadStatsP15mEntry 2 }

qosFanOutLoadStatsP15mLoad 	OBJECT-TYPE 
	SYNTAX	INTEGER
	ACCESS read-only
	STATUS mandatory
	DESCRIPTION
	    "This object is used to show the traffic class load percentage. It calculates total throughput of internal bus of LIM by the passed bits in this 15 minutes, compared with internal bus capability of LIM. It means the average load percentage in this 15 minutes. If traffic class index is 8, the load is for total traffic of LIM. System should check its value in the range of 0 to 100. If calculation result is above 100, system should round it to 100."
::= {qosFanOutLoadStatsP15mEntry 3 }

qosFanOutLoadStatsP15mPassBytes 	OBJECT-TYPE 
	SYNTAX	Counter64bit
	ACCESS read-only
	STATUS mandatory
	DESCRIPTION
	    "Previous 15 minute passed bytes in this traffic class. If traffic class is 8, it means the sum of each traffic class of this LIM."
::= {qosFanOutLoadStatsP15mEntry 4 }

qosFanOutLoadStatsP15mPassFrames 	OBJECT-TYPE 
	SYNTAX	Counter64bit
	ACCESS read-only
	STATUS mandatory
	DESCRIPTION
	    " Previous 15 minute passed frames in this traffic class. If traffic class is 8, it means the sum of each traffic class of this LIM."
::= {qosFanOutLoadStatsP15mEntry 5 }

qosFanOutLoadStatsP15mMeasuredTime 	OBJECT-TYPE 
	SYNTAX	TimeTicks
	ACCESS read-only
	STATUS mandatory
	DESCRIPTION
	    "The amount of time, measured in seconds, that statistics 
		 for this entry have been counted."
::= {qosFanOutLoadStatsP15mEntry 6  }

qosFanOutLoadStatsC15mTable OBJECT-TYPE
	SYNTAX	SEQUENCE OF QosFanOutLoadStatsC15mEntry
	ACCESS not-accessible
	STATUS	mandatory
	DESCRIPTION
	"This table contains the current 15 minute QoS statistics on a 
	per EBLT LIM basis"
::= {qosStatisticsAndData 10 }

qosFanOutLoadStatsC15mEntry OBJECT-TYPE
    SYNTAX      QosFanOutLoadStatsC15mEntry
    ACCESS      not-accessible
    STATUS      mandatory
    DESCRIPTION "An entry in the qosFanOutLoadStatsC15mTable"
    INDEX      { eqptSlotId, qosFanOutLoadStatsC15mTrafficClass}
    ::=  {qosFanOutLoadStatsC15mTable 1 }

QosFanOutLoadStatsC15mEntry ::= SEQUENCE
	{
		qosFanOutLoadStatsC15mTrafficClass	 			INTEGER,
		qosFanOutLoadStatsC15mLoad						INTEGER,
		qosFanOutLoadStatsC15mPassBytes					Counter64bit,
		qosFanOutLoadStatsC15mPassFrames					Counter64bit,
		qosFanOutLoadStatsC15mElapseTime					TimeTicks,
		qosFanOutLoadStatsC15mMeasuredTime				TimeTicks
	}

qosFanOutLoadStatsC15mTrafficClass 	OBJECT-TYPE 
	SYNTAX	INTEGER (0..8)
	ACCESS read-only
	STATUS mandatory
	DESCRIPTION
	    " This object is used to index the traffic class on the LIM. Index 8 means total traffic. Index 0 to 7 refer to the traffic class with different priority, the same sequence with queue index definition."
::= {qosFanOutLoadStatsC15mEntry 1 }

qosFanOutLoadStatsC15mLoad 	OBJECT-TYPE 
	SYNTAX	INTEGER
	ACCESS read-only
	STATUS mandatory
	DESCRIPTION
	    "This object is used to show the traffic class load percentage. It calculates total throughput of internal bus of LIM by the passed bits in this 15 minutes, compared with internal bus capability of LIM. It means the average load percentage in the measured time. If traffic class index is 8, the load is for total traffic of LIM. System should check its value in the range of 0 to 100. If calculation result is above 100, system should round it to 100."
::= {qosFanOutLoadStatsC15mEntry 2 }

qosFanOutLoadStatsC15mPassBytes 	OBJECT-TYPE 
	SYNTAX	Counter64bit
	ACCESS read-only
	STATUS mandatory
	DESCRIPTION
	    "Current 15 minute passed bytes in this traffic class. If traffic class is 8, it means the sum of each traffic class of this LIM."
::= {qosFanOutLoadStatsC15mEntry 3 }

qosFanOutLoadStatsC15mPassFrames 	OBJECT-TYPE 
	SYNTAX	Counter64bit
	ACCESS read-only
	STATUS mandatory
	DESCRIPTION
	    " Current 15 minute passed frames in this traffic class. If traffic class is 8, it means the sum of each traffic class of this LIM."
::= {qosFanOutLoadStatsC15mEntry 4 }

qosFanOutLoadStatsC15mElapseTime 	OBJECT-TYPE 
	SYNTAX	TimeTicks
	ACCESS read-only
	STATUS mandatory
	DESCRIPTION
	    "The elapsed time interval since the last measurement epoch started."
::= {qosFanOutLoadStatsC15mEntry 5  }

qosFanOutLoadStatsC15mMeasuredTime 	OBJECT-TYPE 
	SYNTAX	TimeTicks
	ACCESS read-only
	STATUS mandatory
	DESCRIPTION
	    "The amount of time, measured in seconds, that statistics 
		 for this entry have been counted."
::= {qosFanOutLoadStatsC15mEntry 6  }

qosFanOutLoadStatsP1dTable OBJECT-TYPE
	SYNTAX	SEQUENCE OF QosFanOutLoadStatsP1dEntry
	ACCESS not-accessible
	STATUS	mandatory
	DESCRIPTION
	"This table contains the previous 1 day QoS statistics on a 
	per EBLT LIM basis"
::= {qosStatisticsAndData 11 }

qosFanOutLoadStatsP1dEntry OBJECT-TYPE
    SYNTAX      QosFanOutLoadStatsP1dEntry
    ACCESS      not-accessible
    STATUS      mandatory
    DESCRIPTION "An entry in the qosFanOutLoadStatsP1dTable"
    INDEX      { eqptSlotId, qosFanOutLoadStatsP1dIntervalNumber }
    ::=  {qosFanOutLoadStatsP1dTable 1 }

QosFanOutLoadStatsP1dEntry ::= SEQUENCE
	{
		qosFanOutLoadStatsP1dIntervalNumber	 			INTEGER,
		qosFanOutLoadStatsP1dPassBytes					Counter64bit,
		qosFanOutLoadStatsP1dPassFrames					Counter64bit,
		qosFanOutLoadStatsP1dMeasuredTime					TimeTicks
	}

qosFanOutLoadStatsP1dIntervalNumber 	OBJECT-TYPE 
	SYNTAX	INTEGER (1)
	ACCESS not-accessible
	STATUS mandatory
	DESCRIPTION
	"A number, which identifies the interval for which the set of statistics is available. The interval identified by 1 is the most recently completed 1 day interval, and the interval identified by N is the interval immediately preceding the one identified by N-1. Currently we support only 1 entry."
::= {qosFanOutLoadStatsP1dEntry 1 }

qosFanOutLoadStatsP1dPassBytes 	OBJECT-TYPE 
	SYNTAX	Counter64bit
	ACCESS read-only
	STATUS mandatory
	DESCRIPTION
	    "Previous 1 day passed bytes in this traffic class. "
::= {qosFanOutLoadStatsP1dEntry 2 }

qosFanOutLoadStatsP1dPassFrames 	OBJECT-TYPE 
	SYNTAX	Counter64bit
	ACCESS read-only
	STATUS mandatory
	DESCRIPTION
	    " Previous 1 day passed frames in this traffic class. "
::= {qosFanOutLoadStatsP1dEntry 3 }

qosFanOutLoadStatsP1dMeasuredTime 	OBJECT-TYPE 
	SYNTAX	TimeTicks
	ACCESS read-only
	STATUS mandatory
	DESCRIPTION
	    "The amount of time, measured in seconds, that statistics 
		 for this entry have been counted."
::= {qosFanOutLoadStatsP1dEntry 4  }

qosFanOutLoadStatsC1dTable OBJECT-TYPE
	SYNTAX	SEQUENCE OF QosFanOutLoadStatsC1dEntry
	ACCESS not-accessible
	STATUS	mandatory
	DESCRIPTION
	"This table contains the current 1 day QoS statistics on a 
	per EBLT LIM basis"
::= {qosStatisticsAndData 12 }

qosFanOutLoadStatsC1dEntry OBJECT-TYPE
    SYNTAX      QosFanOutLoadStatsC1dEntry
    ACCESS      not-accessible
    STATUS      mandatory
    DESCRIPTION "An entry in the qosFanOutLoadStatsC1dTable"
    INDEX      { eqptSlotId }
    ::=  {qosFanOutLoadStatsC1dTable 1 }

QosFanOutLoadStatsC1dEntry ::= SEQUENCE
	{
		qosFanOutLoadStatsC1dPassBytes					Counter64bit,
		qosFanOutLoadStatsC1dPassFrames					Counter64bit,
		qosFanOutLoadStatsC1dElapseTime					TimeTicks,
		qosFanOutLoadStatsC1dMeasuredTime					TimeTicks
	}

qosFanOutLoadStatsC1dPassBytes 	OBJECT-TYPE 
	SYNTAX	Counter64bit
	ACCESS read-only
	STATUS mandatory
	DESCRIPTION
	    "Current 1 day passed bytes in this traffic class. "
::= {qosFanOutLoadStatsC1dEntry 1 }

qosFanOutLoadStatsC1dPassFrames 	OBJECT-TYPE 
	SYNTAX	Counter64bit
	ACCESS read-only
	STATUS mandatory
	DESCRIPTION
	    " Current 1 day passed frames in this traffic class. "
::= {qosFanOutLoadStatsC1dEntry 2 }

qosFanOutLoadStatsC1dElapseTime 	OBJECT-TYPE 
	SYNTAX	TimeTicks
	ACCESS read-only
	STATUS mandatory
	DESCRIPTION
	    "The elapsed time interval since the last measurement epoch started."
::= {qosFanOutLoadStatsC1dEntry 3  }

qosFanOutLoadStatsC1dMeasuredTime 	OBJECT-TYPE 
	SYNTAX	TimeTicks
	ACCESS read-only
	STATUS mandatory
	DESCRIPTION
	    "The amount of time, measured in seconds, that statistics 
		 for this entry have been counted."
::= {qosFanOutLoadStatsC1dEntry 5  }

qosStatsSettingTable OBJECT-TYPE
	SYNTAX	SEQUENCE OF QosStatsSettingEntry
	ACCESS not-accessible
	STATUS	mandatory
	DESCRIPTION
	"This table contains the configurable parameters of QoS queue statistics function."
::= {qosStatisticsAndData 13 }

qosStatsSettingEntry OBJECT-TYPE
    SYNTAX      QosStatsSettingEntry
    ACCESS      not-accessible
    STATUS      mandatory
    DESCRIPTION "An entry in the qosStatsSettingTable"
    INDEX      { eqptSlotId }
    ::=  {qosStatsSettingTable 1 }

QosStatsSettingEntry ::= SEQUENCE
	{
		qosLimBufferOccupancyThreshold		 				INTEGER,
		qosStatsSettingQueueStatsEnable						INTEGER,
		qosStatsSettingFanOutLoadTcaEnable					INTEGER,
		qosStatsSettingFanOutLoadTcaThreshold				INTEGER,
		qosStatsSettingAggrBufOvflwTcaEnable					INTEGER,
		qosStatsSettingUpAggrBufOvflwTcaThreshold			INTEGER,
		qosStatsSettingUpObcAggrBufOvflwTcaThreshold			INTEGER,
		qosStatsSettingDnObcAggrBufOvflwTcaThreshold			INTEGER,
		qosStatsSettingDnUcAggrBufOvflwTcaThreshold			INTEGER,
		qosStatsSettingPartialAggrBufOvflwTcaThreshold		Counter64bit
	}

qosLimBufferOccupancyThreshold 	OBJECT-TYPE 
	SYNTAX	INTEGER ( 0..100 )
	ACCESS read-write
	STATUS mandatory
	DESCRIPTION
	"The threshold is defined as percentage. Means the ratio of occupied data buffer entries to the LIM global data buffer size. The incoming packets to BE and CL queues will be dropped when this threshold arrives while the incoming packets to voice and video queues can be queued. Default 0 means system don't judge the threshold cross over. the range of this object is from 0 to 100. System shold convert the percentage to the number of occupied data buffer entries according to system global data buffer size. "
		DEFVAL { 0 }
::= {qosStatsSettingEntry 1 }

qosStatsSettingQueueStatsEnable 	OBJECT-TYPE 
	SYNTAX	INTEGER 
			{
				enabled (1),
				disabled (2)
			}
	ACCESS read-write
	STATUS mandatory
	DESCRIPTION
	"setting the object to enable or disable queue statistics of the LIM. It only means the increment of HW queues counters is enabled or disabled. The upper layer interfaces of queue statistics are still open to operator. For example, operator still can access the P15m queue drop counter of a specific queue even if this object is disabled.  "
		DEFVAL { disabled }
::= {qosStatsSettingEntry 2 }

qosStatsSettingFanOutLoadTcaEnable 	OBJECT-TYPE 
	SYNTAX	INTEGER 
			{
				enabled (1),
				disabled (2)
			}
	ACCESS read-write
	STATUS mandatory
	DESCRIPTION
	"setting the object to enable or disable the threshold crossover alarm of fan-out load of the LIM. Only if this object is enabled, system will send TCA when fan-out load is supper than nonzero fan-out load threshold."
		DEFVAL { disabled }
::= {qosStatsSettingEntry 3 }

qosStatsSettingFanOutLoadTcaThreshold 	OBJECT-TYPE 
	SYNTAX	INTEGER ( 0..100 )
	ACCESS read-write
	STATUS mandatory
	DESCRIPTION
	"The threshold of LT fan out load, defined as percentage, means the ratio of  the 15 minutes PM counter of LIM fan out passed bytes to the LIM internal net bus capability. Fan out load means the LIM internal bus fan out throughput in downstream direction. The calculation is the sum of all PM counters of queue passed bytes of the LIM, divided by LIM net bus capability and time interval. Default 0 means system don't judge the threshold cross over. The value range of this object is 0 to 100."
		DEFVAL { 0 }
::= {qosStatsSettingEntry 4 }

qosStatsSettingAggrBufOvflwTcaEnable 	OBJECT-TYPE 
	SYNTAX	INTEGER 
			{
				enabled (1),
				disabled (2)
			}
	ACCESS read-write
	STATUS mandatory
	DESCRIPTION
	"setting the object to enable or disable the threshold crossover alarm of aggregation buffer overflow in the LIM. Only if this object is enabled, system will send TCA when each type of aggregation buffer overflow is supper than their nonzero threshold."
		DEFVAL { disabled }
::= {qosStatsSettingEntry 5 }

qosStatsSettingUpAggrBufOvflwTcaThreshold 	OBJECT-TYPE 
	SYNTAX	INTEGER 
	ACCESS read-write
	STATUS mandatory
	DESCRIPTION
	"The threshold of upstream aggregation buffer overflow TCA. The unit is frame. This referred PM counter UpAggrBufOvflw is incremented when any of the 4 upstream aggregate buffers overflow, or when there is no free packet handler for a reassembly area. Also incremented when the free list is up for upstream packets (if possible) on an LIM module on a 15 minute interval basis. Default 0 means system don't judge the threshold cross over."
		DEFVAL { 0 }
::= {qosStatsSettingEntry 6 }

qosStatsSettingUpObcAggrBufOvflwTcaThreshold 	OBJECT-TYPE 
	SYNTAX	INTEGER 
	ACCESS read-write
	STATUS mandatory
	DESCRIPTION
	" The threshold of OBC-directed upstream aggregation buffer overflow TCA. The unit is frame. This referred PM counter UpObcAggrBufOvflw is incremented when any of the OBC directed queues for upstream packets overflow on an LIM module on a 15 minute interval basis. These are packet counters; byte counters not needed. Default 0 means system don't judge the threshold cross over."
		DEFVAL { 0 }
::= {qosStatsSettingEntry 7 }

qosStatsSettingDnObcAggrBufOvflwTcaThreshold 	OBJECT-TYPE 
	SYNTAX	INTEGER 
	ACCESS read-write
	STATUS mandatory
	DESCRIPTION
	" The threshold of downstream OBC-directed aggregation buffer overflow TCA. The unit is frame. This referred PM counter DnObcAggrBufOvflw is incremented when any of the OBC directed queues for downstream packets overflow on an LIM module on a 15 minute interval basis. These are packet counters; byte counters not needed. Default 0 means system don't judge the threshold cross over."
		DEFVAL { 0 }
::= {qosStatsSettingEntry 8 }

qosStatsSettingDnUcAggrBufOvflwTcaThreshold 	OBJECT-TYPE 
	SYNTAX	INTEGER 
	ACCESS read-write
	STATUS mandatory
	DESCRIPTION
	"The threshold of downstream data aggregation buffer overflow TCA. The unit is frame. This referred PM counter  DnUcAggrBufOvflw is incremented when the total free list is up for a downstream packets on an LIM module on a 15 minute interval basis. Default 0 means system don't judge the threshold cross over."
		DEFVAL { 0 }
::= {qosStatsSettingEntry 9 }

qosStatsSettingPartialAggrBufOvflwTcaThreshold 	OBJECT-TYPE 
	SYNTAX	Counter64bit 
	ACCESS read-write
	STATUS mandatory
	DESCRIPTION
	"The threshold of dropped lower class packets of global buffer occupancy threshold overflow TCA. The unit is frame. This referred PM counter  PartialAggrBufOvflw is incremented when the used buffer number is above global buffer occupancy threshold and the packet is belongs to lower classes traffic on an LIM module on a 15 minute interval basis. Default 0 means system don't judge the threshold cross over. Currently lower traffic class means BE+CL  traffic."
::= {qosStatsSettingEntry 10 }

qosQueueStatsTcaTable OBJECT-TYPE
	SYNTAX	SEQUENCE OF QosQueueStatsTcaEntry
	ACCESS not-accessible
	STATUS	mandatory
	DESCRIPTION
	"This table contains per queue the configurable TCA parameters of QoS queue statistics function."
::= {qosStatisticsAndData 14 }

qosQueueStatsTcaEntry OBJECT-TYPE
    SYNTAX      QosQueueStatsTcaEntry
    ACCESS      not-accessible
    STATUS      mandatory
    DESCRIPTION "An entry in the qosQueueStatsTcaTable"
    INDEX      { qosQueueStatsTcaLineLinkIndex, qosQueueStatsTcaLineQueueIndex }
    ::=  {qosQueueStatsTcaTable 1 }

QosQueueStatsTcaEntry ::= SEQUENCE
	{
		qosQueueStatsTcaLineLinkIndex			 				InterfaceIndex,
		qosQueueStatsTcaLineQueueIndex						INTEGER,
		qosQueueStatsTcaEnable									INTEGER,
		qosQueueStatsQueueLoadTcaThreshold					INTEGER,
		qosQueueStatsDiscFramesTcaThreshold					INTEGER
	}

qosQueueStatsTcaLineLinkIndex 	OBJECT-TYPE 
	SYNTAX	InterfaceIndex 
	ACCESS not-accessible
	STATUS mandatory
	DESCRIPTION
	" This object is used to index the physical lines of this LIM. "
::= {qosQueueStatsTcaEntry 1 }

qosQueueStatsTcaLineQueueIndex 	OBJECT-TYPE 
	SYNTAX	INTEGER ( 0..7 )
	ACCESS not-accessible
	STATUS mandatory
	DESCRIPTION
	" This object is used to index the queue within the scope of one physical link on the LIM. Currently Index 0 to 3 correspond to physical queue 0 to 3, and index 4 to 7 is meaningless since only four queues per line supported"
::= {qosQueueStatsTcaEntry 2 }

qosQueueStatsTcaEnable 	OBJECT-TYPE 
	SYNTAX	INTEGER 
			{
				enabled (1),
				disabled (2)
			}
	ACCESS read-write
	STATUS mandatory
	DESCRIPTION
	"setting the object to enable or disable each queue statistic TCA of this queue. It contains the TCA of passed/discarded bytes/frames of this queue. Only if this object is enabled, system will send related TCA when some of queue counter of this queue are supper than their nonzero threshold."
		DEFVAL { disabled }
::= {qosQueueStatsTcaEntry 3 }

qosQueueStatsQueueLoadTcaThreshold 	OBJECT-TYPE 
	SYNTAX	INTEGER ( 0..100 )
	ACCESS read-write
	STATUS mandatory
	DESCRIPTION
	" The threshold of queue traffic load, defined as percentage. Means the ratio of the statistical traffic rate of this queue to the actual line rate. The referred PM counter is LimQueueStatsPassBytes. Default 0 means system don't judge the threshold cross over. The value range of this object is from 0 to 100. "
		DEFVAL { 0 }
::= {qosQueueStatsTcaEntry 4 }

qosQueueStatsDiscFramesTcaThreshold 	OBJECT-TYPE 
	SYNTAX	INTEGER 
	ACCESS read-write
	STATUS mandatory
	DESCRIPTION
	" The threshold of discarded frames of this queue. The referred PM counter is LimQueueStatsDiscFrames. Default 0 means system don't judge the threshold cross over. "
		DEFVAL { 0 }
::= {qosQueueStatsTcaEntry 5 }

qosLimQueueStatsPerfInfoTable OBJECT-TYPE
	SYNTAX	SEQUENCE OF QosLimQueueStatsPerfInfoEntry
	ACCESS not-accessible
	STATUS	mandatory
	DESCRIPTION
	"Table of number of previous statistics intervals for the traffic on a LIM queue or line."
::= {qosStatisticsAndData 15 }

qosLimQueueStatsPerfInfoEntry OBJECT-TYPE
    SYNTAX      QosLimQueueStatsPerfInfoEntry
    ACCESS      not-accessible
    STATUS      mandatory
    DESCRIPTION "An entry in the qosLimQueueStatsPerfInfoTable"
    INDEX      { qosLimQueueStatsPerfInfoLineLinkIndex, qosLimQueueStatsPerfInfoLineQueueIndex }
    ::=  {qosLimQueueStatsPerfInfoTable 1 }

QosLimQueueStatsPerfInfoEntry ::= SEQUENCE
	{
		qosLimQueueStatsPerfInfoLineLinkIndex				InterfaceIndex,
		qosLimQueueStatsPerfInfoLineQueueIndex				INTEGER,
		qosLimQueueStatsPerfInfo15MValidIntervals				INTEGER
	}

qosLimQueueStatsPerfInfoLineLinkIndex 	OBJECT-TYPE 
	SYNTAX	InterfaceIndex 
	ACCESS not-accessible
	STATUS mandatory
	DESCRIPTION
	" This object is used to index the physical lines of this LIM. "
::= {qosLimQueueStatsPerfInfoEntry 1 }

qosLimQueueStatsPerfInfoLineQueueIndex 	OBJECT-TYPE 
	SYNTAX	INTEGER ( 0..8 )
	ACCESS not-accessible
	STATUS mandatory
	DESCRIPTION
	" This object is used to index the queue within the scope of one physical link on the LIM. Index 8 means total line. Currently Index 0 to 3 correspond to physical queue 0 to 3, and index 4 to 7 is meaningless since only four queues per line supported"
::= {qosLimQueueStatsPerfInfoEntry 2 }

qosLimQueueStatsPerfInfo15MValidIntervals 	OBJECT-TYPE 
	SYNTAX	INTEGER (0..1)
	ACCESS read-only
	STATUS mandatory
	DESCRIPTION
	" Number of previous 15 minutes intervals."
::= {qosLimQueueStatsPerfInfoEntry 3 }

qosFanOutLoadStats15MPerfInfoTable OBJECT-TYPE
	SYNTAX	SEQUENCE OF QosFanOutLoadStats15MPerfInfoEntry
	ACCESS not-accessible
	STATUS	mandatory
	DESCRIPTION
	"Table of number of previous statistics intervals for the fan out traffic on a LIM."
::= {qosStatisticsAndData 16 }

qosFanOutLoadStats15MPerfInfoEntry OBJECT-TYPE
    SYNTAX      QosFanOutLoadStats15MPerfInfoEntry
    ACCESS      not-accessible
    STATUS      mandatory
    DESCRIPTION "An entry in the qosFanOutLoadStats15MPerfInfoTable"
    INDEX      { eqptSlotId, qosFanOutLoadStats15MPerfInfoTrafficClass } 
    ::=  {qosFanOutLoadStats15MPerfInfoTable 1 }

QosFanOutLoadStats15MPerfInfoEntry ::= SEQUENCE
	{
		qosFanOutLoadStats15MPerfInfoTrafficClass				INTEGER,
		qosFanOutLoadStats15MPerfInfo15MValidIntervals		INTEGER
	}

qosFanOutLoadStats15MPerfInfoTrafficClass 	OBJECT-TYPE 
	SYNTAX	INTEGER ( 0..8 )
	ACCESS not-accessible
	STATUS mandatory
	DESCRIPTION
	" This object is used to index the traffic class on the LIM. Index 8 means total traffic. Index 0 to 7 refer to the traffic class with different priority, the same sequence with queue index definition."
::= {qosFanOutLoadStats15MPerfInfoEntry 1 }

qosFanOutLoadStats15MPerfInfo15MValidIntervals 	OBJECT-TYPE 
	SYNTAX	INTEGER (0..96)
	ACCESS read-only
	STATUS mandatory
	DESCRIPTION
	" Number of previous 15 minutes intervals."
::= {qosFanOutLoadStats15MPerfInfoEntry 2 }

qosFanOutLoadStats1DPerfInfoTable OBJECT-TYPE
	SYNTAX	SEQUENCE OF QosFanOutLoadStats1DPerfInfoEntry
	ACCESS not-accessible
	STATUS	mandatory
	DESCRIPTION
	"Table of number of previous statistics intervals for the fan out traffic on a LIM."
::= {qosStatisticsAndData 17 }

qosFanOutLoadStats1DPerfInfoEntry OBJECT-TYPE
    SYNTAX      QosFanOutLoadStats1DPerfInfoEntry
    ACCESS      not-accessible
    STATUS      mandatory
    DESCRIPTION "An entry in the qosFanOutLoadStats1DPerfInfoTable"
    INDEX      { eqptSlotId } 
    ::=  {qosFanOutLoadStats1DPerfInfoTable 1 }

QosFanOutLoadStats1DPerfInfoEntry ::= SEQUENCE
	{
		qosFanOutLoadStats1DPerfInfo1DValidIntervals		INTEGER
	}

qosFanOutLoadStats1DPerfInfo1DValidIntervals 	OBJECT-TYPE 
	SYNTAX	INTEGER (0..1)
	ACCESS read-only
	STATUS mandatory
	DESCRIPTION
	" Number of previous 15 minutes intervals."
::= {qosFanOutLoadStats1DPerfInfoEntry 1 }

qosLimObcBackplaneQueueStatsC15mTable OBJECT-TYPE
	SYNTAX	SEQUENCE OF QosLimObcBackplaneQueueStatsC15mEntry
	ACCESS not-accessible
	STATUS	mandatory
	DESCRIPTION
	"This table contains the current QoS statistics on a 
	per GLT LIM basis of packets discarded towards OBC and backplane"
::= {qosStatisticsAndData 18 }

qosLimObcBackplaneQueueStatsC15mEntry OBJECT-TYPE
    SYNTAX      QosLimObcBackplaneQueueStatsC15mEntry
    ACCESS      not-accessible
    STATUS      mandatory
    DESCRIPTION "An entry in the qosLimObcBackplaneQueueStatsC15mTable"
    INDEX      { eqptSlotId }
    ::=  {qosLimObcBackplaneQueueStatsC15mTable 1 }

QosLimObcBackplaneQueueStatsC15mEntry ::= SEQUENCE
	{
		qosLimObcBackplaneQueueStatsC15mObcLowDiscPkts		Counter,
		qosLimObcBackplaneQueueStatsC15mObcLowDiscBytes		Counter,
		qosLimObcBackplaneQueueStatsC15mObcHighDiscPkts	Counter,
		qosLimObcBackplaneQueueStatsC15mObcHighDiscBytes	Counter,
		qosLimObcBackplaneQueueStatsC15mBplLowDiscPkts		Counter,
		qosLimObcBackplaneQueueStatsC15mBplLowDiscBytes	Counter,
		qosLimObcBackplaneQueueStatsC15mBplHighDiscPkts		Counter,
		qosLimObcBackplaneQueueStatsC15mBplHighDiscBytes		Counter
	}

qosLimObcBackplaneQueueStatsC15mObcLowDiscPkts OBJECT-TYPE 
	SYNTAX	Counter
	ACCESS read-only
	STATUS mandatory
	DESCRIPTION
	    " Current discarded packet count towards OBC due to low water mark crossing."
::= { qosLimObcBackplaneQueueStatsC15mEntry 1  }

qosLimObcBackplaneQueueStatsC15mObcLowDiscBytes OBJECT-TYPE 
	SYNTAX	Counter
	ACCESS read-only
	STATUS mandatory
	DESCRIPTION
	    " Current discarded byte count towards OBC due to low water mark crossing."
::= { qosLimObcBackplaneQueueStatsC15mEntry 2  }

qosLimObcBackplaneQueueStatsC15mObcHighDiscPkts OBJECT-TYPE 
	SYNTAX	Counter
	ACCESS read-only
	STATUS mandatory
	DESCRIPTION
	    " Current discarded packet count towards OBC due to high water mark crossing."
::= { qosLimObcBackplaneQueueStatsC15mEntry 3  }

qosLimObcBackplaneQueueStatsC15mObcHighDiscBytes OBJECT-TYPE 
	SYNTAX	Counter
	ACCESS read-only
	STATUS mandatory
	DESCRIPTION
	    " Current discarded byte count towards OBC due to high water mark crossing."
::= { qosLimObcBackplaneQueueStatsC15mEntry 4  }

qosLimObcBackplaneQueueStatsC15mBplLowDiscPkts OBJECT-TYPE 
	SYNTAX	Counter
	ACCESS read-only
	STATUS mandatory
	DESCRIPTION
	    " Current discarded packet count towards backplane due to low water mark crossing."
::= { qosLimObcBackplaneQueueStatsC15mEntry 5  }

qosLimObcBackplaneQueueStatsC15mBplLowDiscBytes OBJECT-TYPE 
	SYNTAX	Counter
	ACCESS read-only
	STATUS mandatory
	DESCRIPTION
	    " Current discarded bytes count towards backplane due to low water mark crossing."
::= { qosLimObcBackplaneQueueStatsC15mEntry 6  }

qosLimObcBackplaneQueueStatsC15mBplHighDiscPkts OBJECT-TYPE 
	SYNTAX	Counter
	ACCESS read-only
	STATUS mandatory
	DESCRIPTION
	    " Current discarded packet count towards backplane due to high water mark crossing."
::= { qosLimObcBackplaneQueueStatsC15mEntry 7  }

qosLimObcBackplaneQueueStatsC15mBplHighDiscBytes OBJECT-TYPE 
	SYNTAX	Counter
	ACCESS read-only
	STATUS mandatory
	DESCRIPTION
	    " Current discarded bytes count towards backplane due to high water mark crossing."
::= { qosLimObcBackplaneQueueStatsC15mEntry 8  }

qosLimObcBackplaneQueueStatsP15mTable OBJECT-TYPE
	SYNTAX	SEQUENCE OF QosLimObcBackplaneQueueStatsP15mEntry
	ACCESS not-accessible
	STATUS	mandatory
	DESCRIPTION
	"This table contains the prev 15 min QoS statistics on a 
	per GLT LIM basis of packets discarded towards OBC and backplane. Only one 15 min interval is supported."
::= {qosStatisticsAndData 19 }

qosLimObcBackplaneQueueStatsP15mEntry OBJECT-TYPE
    SYNTAX      QosLimObcBackplaneQueueStatsP15mEntry
    ACCESS      not-accessible
    STATUS      mandatory
    DESCRIPTION "An entry in the qosLimObcBackplaneQueueStatsP15mTable"
    INDEX      { eqptSlotId, qosLimObcBackplaneQueueStatsP15mCounterIndex}
    ::=  {qosLimObcBackplaneQueueStatsP15mTable 1 }

QosLimObcBackplaneQueueStatsP15mEntry ::= SEQUENCE
	{
		qosLimObcBackplaneQueueStatsP15mCounterIndex                INTEGER,
		qosLimObcBackplaneQueueStatsP15mObcLowDiscPkts		Counter,
		qosLimObcBackplaneQueueStatsP15mObcLowDiscBytes		Counter,
		qosLimObcBackplaneQueueStatsP15mObcHighDiscPkts	        Counter,
		qosLimObcBackplaneQueueStatsP15mObcHighDiscBytes	        Counter,
		qosLimObcBackplaneQueueStatsP15mBplLowDiscPkts		        Counter,
		qosLimObcBackplaneQueueStatsP15mBplLowDiscBytes		Counter,
		qosLimObcBackplaneQueueStatsP15mBplHighDiscPkts		Counter,
		qosLimObcBackplaneQueueStatsP15mBplHighDiscBytes		Counter
	}

qosLimObcBackplaneQueueStatsP15mCounterIndex OBJECT-TYPE 
	SYNTAX	INTEGER (1)
	ACCESS not-accessible
	STATUS mandatory
	DESCRIPTION
	    " Number of previous interval. Currently only value of 1 is supported."
::= { qosLimObcBackplaneQueueStatsP15mEntry 1  }

qosLimObcBackplaneQueueStatsP15mObcLowDiscPkts OBJECT-TYPE 
	SYNTAX	Counter
	ACCESS read-only
	STATUS mandatory
	DESCRIPTION
	    " Current discarded packet count towards OBC due to low water mark crossing."
::= { qosLimObcBackplaneQueueStatsP15mEntry 2  }

qosLimObcBackplaneQueueStatsP15mObcLowDiscBytes OBJECT-TYPE 
	SYNTAX	Counter
	ACCESS read-only
	STATUS mandatory
	DESCRIPTION
	    " Current discarded bytes count towards OBC due to low water mark crossing."
::= { qosLimObcBackplaneQueueStatsP15mEntry 3 }

qosLimObcBackplaneQueueStatsP15mObcHighDiscPkts OBJECT-TYPE 
	SYNTAX	Counter
	ACCESS read-only
	STATUS mandatory
	DESCRIPTION
	    " Current discarded packet count towards OBC due to high water mark crossing."
::= { qosLimObcBackplaneQueueStatsP15mEntry 4 }

qosLimObcBackplaneQueueStatsP15mObcHighDiscBytes OBJECT-TYPE 
	SYNTAX	Counter
	ACCESS read-only
	STATUS mandatory
	DESCRIPTION
	    " Current discarded byte count towards OBC due to high water mark crossing."
::= { qosLimObcBackplaneQueueStatsP15mEntry 5 }

qosLimObcBackplaneQueueStatsP15mBplLowDiscPkts OBJECT-TYPE 
	SYNTAX	Counter
	ACCESS read-only
	STATUS mandatory
	DESCRIPTION
	    " Current discarded packet count towards backplane due to low water mark crossing."
::= { qosLimObcBackplaneQueueStatsP15mEntry 6 }

qosLimObcBackplaneQueueStatsP15mBplLowDiscBytes OBJECT-TYPE 
	SYNTAX	Counter
	ACCESS read-only
	STATUS mandatory
	DESCRIPTION
	    " Current discarded bytes count towards backplane due to low water mark crossing."
::= { qosLimObcBackplaneQueueStatsP15mEntry 7 }

qosLimObcBackplaneQueueStatsP15mBplHighDiscPkts OBJECT-TYPE 
	SYNTAX	Counter
	ACCESS read-only
	STATUS mandatory
	DESCRIPTION
	    " Current discarded packet count towards backplane due to high water mark crossing."
::= { qosLimObcBackplaneQueueStatsP15mEntry 8 }

qosLimObcBackplaneQueueStatsP15mBplHighDiscBytes OBJECT-TYPE 
	SYNTAX	Counter
	ACCESS read-only
	STATUS mandatory
	DESCRIPTION
	    " Current discarded bytes count towards backplane due to high water mark crossing."
::= { qosLimObcBackplaneQueueStatsP15mEntry 9 }

qosDscpDot1PAlignment OBJECT IDENTIFIER ::= {qosMIB 8}

qosDscpToDot1PAlignmentTable OBJECT-TYPE
        SYNTAX  SEQUENCE OF QosDscpToDot1PAlignmentEntry
        ACCESS	not-accessible
	STATUS	mandatory
	DESCRIPTION
	"This object contains a table that defines the mapping from DSCP
         value to the .1P field of the VLAN tag. The row index of the table
         is the ingress DSCP value (0..63) while the value is the .1P(0..7)."
::= { qosDscpDot1PAlignment 1}

qosDscpToDot1PAlignmentEntry OBJECT-TYPE
	SYNTAX QosDscpToDot1PAlignmentEntry
	ACCESS not-accessible
	STATUS	mandatory
	DESCRIPTION
	"This table contains the DSCP value to 802.1P traffic class mapping
         information. There are 64 rows, each containing one .1P value (0..7)"
	INDEX {qosDscpToDot1PAlignmentDscp }
	::= {qosDscpToDot1PAlignmentTable  1}

QosDscpToDot1PAlignmentEntry ::=
	SEQUENCE {	qosDscpToDot1PAlignmentDscp      INTEGER,	
			qosDscpToDot1PAlignmentDot1P     INTEGER
		 }

qosDscpToDot1PAlignmentDscp OBJECT-TYPE
	SYNTAX	INTEGER(0..63)
	ACCESS	not-accessible
	STATUS mandatory
	DESCRIPTION
	    "This field is used to index the DSCP to Dot1P alignment table.
             The lengths of the table is 64 (fixed)"
::= {  qosDscpToDot1PAlignmentEntry 1 }

qosDscpToDot1PAlignmentDot1P OBJECT-TYPE
	SYNTAX	INTEGER(0..7)
	ACCESS	read-write
	STATUS mandatory
	DESCRIPTION
	"This object encodes the Dot1P (0..7) into which
	frames coming in with the DSCP value equal to the
	index of the row in this table.
	E.g., if row 63 contains value 7, that means that frames
	with DSCP value equal to 63 will be encoded to .1P value 7"
::= {  qosDscpToDot1PAlignmentEntry 2 }

qosDscpToDot1PAlignmentL3Traffic OBJECT-TYPE
	SYNTAX INTEGER	{
				true (1),
				false (2)
			}
	ACCESS read-write
	STATUS mandatory
	DESCRIPTION
        "setting this object to true will do the DSCP to P-bits
         alignment for all the L3 forwarding traffic"
        DEFVAL {false}
::= {	qosDscpDot1PAlignment 2}

    qosPccRules OBJECT IDENTIFIER ::= { qosMIB 9 }

    pccRuleTable OBJECT-TYPE
        SYNTAX          SEQUENCE OF PccRuleEntry
        ACCESS          not-accessible
        STATUS          mandatory
        DESCRIPTION
             "The table is partitioned per userLineId and sub-partitioned
              per userFwdPortId. 
              Each table row is indexed by pccRuleIndex.
              Each such table row contains the parameters of a PCC Rule obtained
              via e.g. the DIAMETER Gxr Interface.
        ALCATEL NOTE:
             TABLESIZE: depends on the number of User Lines,
                  multiplied by the average number of PCC Rules per User Line.
                  The latter is about 0.15 PCC Rules, derived from:
                  average 1.5 set-top box per household, and
                  average 10% of the streaming traffic is unicast video (VoD). "
        ::= { qosPccRules 1 }

    pccRuleEntry OBJECT-TYPE
        SYNTAX          PccRuleEntry
        ACCESS          not-accessible
        STATUS          mandatory
        DESCRIPTION
             "Rows are created automatically when a PCC rule is accepted and
              installed by the DSLAM after being downloaded by a Policy and
              Charging Rule Function (PCRF server). "
        INDEX { userLineId, userFwdPortId, pccRuleIndex }
        ::= { pccRuleTable 1 }

    PccRuleEntry ::= SEQUENCE {
        userLineId           InterfaceIndex,
        userFwdPortId        InterfaceIndex,
        pccRuleIndex                INTEGER,
        pccRuleName            OCTET STRING,
        pccRuleMaxDownRate          INTEGER,
        pccRulePreEmptPriority       Uint32,
        pccRulePreEmpVulnerability  INTEGER
        }

    userLineId OBJECT-TYPE
        SYNTAX          InterfaceIndex
        ACCESS          read-only
        STATUS          mandatory
        DESCRIPTION
             "The userLineId identifies a ADSL-port index, a VDSL-port index, 
              or a native Ethernet-port index.
              In case the PCC Rule is installed via the DIAMETER Gxr Interface, the
              userLine Id must match with a rcSessionUserLineId in the DIAMETER
              MIB.
        ALCATEL NOTE:
             ACCESS:    NA
             USAGE:     NA
             PERSIST:   NA
             INSRVMOD:  NA
             RANGE:     NA
             DEFVALUE:  NA
             UNITS:     NA
             SPARSE:    NO "
        ::= { pccRuleEntry 1 }

    userFwdPortId OBJECT-TYPE
        SYNTAX          InterfaceIndex
        ACCESS          read-only
        STATUS          mandatory
        DESCRIPTION
             "The userFwdPortId identify a VLAN port or a PPPoE client port, so
              in general the access port to the forwarding service.
              The value is the ifIndex that matches with the circuit id in the
              Gxr's Bearer-Identifier AVP.
        ALCATEL NOTE:
             ACCESS:    NA
             USAGE:     NA
             PERSIST:   NA
             INSRVMOD:  NA
             RANGE:     NA
             DEFVALUE:  NA
             UNITS:     NA
             SPARSE:    NO "
        ::= { pccRuleEntry 2 }

    pccRuleIndex OBJECT-TYPE
        SYNTAX          INTEGER
        ACCESS          read-only
        STATUS          mandatory
        DESCRIPTION
             "An index to distinguish between different PCC rules.
        ALCATEL NOTE:
             ACCESS:    NA
             USAGE:     NA
             PERSIST:   NA
             INSRVMOD:  NA
             RANGE:     NA
             DEFVALUE:  NA
             UNITS:     NA
             SPARSE:    NO "
        ::= { pccRuleEntry 3 }

    pccRuleName OBJECT-TYPE
        SYNTAX          OCTET STRING (SIZE(0..32))
        ACCESS          read-only
        STATUS          mandatory
        DESCRIPTION
             "The name of the PCC rule.  
              The name is unique with an RC session, i.e. per User Line.
        ALCATEL NOTE:
             ACCESS:    NA
             USAGE:     NA
             PERSIST:   NA
             INSRVMOD:  NA
             RANGE:     NA
             DEFVALUE:  NA
             UNITS:     NA
             SPARSE:    NO "
        ::= { pccRuleEntry 4 }

    pccRuleMaxDownRate OBJECT-TYPE
        SYNTAX          INTEGER
        ACCESS          read-only
        STATUS          mandatory
        DESCRIPTION
             "The pccRuleMaxDownRate defines the maximum bit rate to be reserved
              for the downlink direction. 
        ALCATEL NOTE:
             ACCESS:    NA
             USAGE:     NA
             PERSIST:   NA
             INSRVMOD:  NA
             RANGE:     NA
             DEFVALUE:  NA
             UNITS:     Kilobits/sec
             SPARSE:    NO "
        ::= { pccRuleEntry 5 }

    pccRulePreEmptPriority OBJECT-TYPE
        SYNTAX          Uint32
        ACCESS          read-only
        STATUS          mandatory
        DESCRIPTION
             "The value of pccRulePreEmptPriority is used to decide which PCC rules
              to terminate in the event of a bandwidth drop of the User Line, 
              whilst the line remains operational.
              The highest level of priority is specified by the value 1.
        ALCATEL NOTE:
             ACCESS:    NA
             USAGE:     NA
             PERSIST:   NA
             INSRVMOD:  NA
             RANGE:     1..15
             DEFVALUE:  NA
             UNITS:     NA
             SPARSE:    NO "
        ::= { pccRuleEntry 6 }

    pccRulePreEmpVulnerability OBJECT-TYPE
        SYNTAX          INTEGER {
                                enabled(1),
                                disabled(2)
                                }
        ACCESS          read-only
        STATUS          mandatory
        DESCRIPTION
             "When pccRulePreEmpVulnerability is enabled, it is allowed to
              consider this rule for termination in the event of a bandwidth drop
              of the User Line, whilst the line remains operational.
        ALCATEL NOTE:
             ACCESS:    NA
             USAGE:     NA
             PERSIST:   NA
             INSRVMOD:  NA
             RANGE:     NA
             DEFVALUE:  NA
             UNITS:     NA
             SPARSE:    NO "
        ::= { pccRuleEntry 7 }

    pccRuleEthIpFactor OBJECT-TYPE
        SYNTAX          Uint32
        ACCESS          read-write
        STATUS          mandatory
        DESCRIPTION
             "The rates in PCC rules are IP-rates, while ISAM RAC calculations
              are done with Eth-rates.
              The value pccRuleEthIpFactor gives in percentages the conversion
              factor IP-to-Ethernet. So the frame net bandwidth available on a
              DSL link for transmitting Ethernet frames equals the IP-rate
              multiplied by pccRuleEthIpFactor/100. 
              Ethernet overhead is about 20 bytes per IP packet. Then for 
              a stream of 1Kbyte IP packets, the Ehernet overhead is 2 percent,
              and so the pccRuleEthIpFactor is 102 percent.
              This is taken as default value.
        ALCATEL NOTE:
             ACCESS:    NA
             USAGE:     NA
             PERSIST:   YES
             INSRVMOD:  YES
             RANGE:     NA
             DEFVALUE:  102
             UNITS:     percentage
             SPARSE:    NO "
        ::= { qosPccRules 2 }

END
