-- orig TRAP_MIB

TRAP-MIB DEFINITIONS ::= BEGIN

IMPORTS

    OBJECT-TYPE
        FROM RFC-1212

    Gauge, IpAddress, Counter
        FROM RFC1155-SMI

    NetworkTimeInSeconds
        FROM ASAM-TC-MIB

    RowStatus
        FROM SNMPv2-TC

    AsamAlarmSeverityType
        FROM ALARM-MIB

    asam
        FROM SYSTEM-MIB; 
    
AsamTrapPriority    ::=  INTEGER { 
                    urgent          (1),
                    high        (2),
                    medium      (3), 
                    low     (4)
                    } 

AsamTrapMode        ::= INTEGER {
                    enabled         (1), 
                    disabled        (2)
                    }

AsamTrapMask        ::= OCTET STRING (SIZE(4))

AsamTrapReset       ::= INTEGER {
                    resetCompleted      (1),
                    reset           (2)
                    }

AsamTrapOverflow    ::= INTEGER {
                    notoverflowed   (1),
                    overflowed      (2)
                    }

asamTrapMIB         OBJECT IDENTIFIER ::= { asam 2 }

asamTrapDefinitionTable         OBJECT-TYPE
    SYNTAX          SEQUENCE OF AsamTrapDefinitionEntry
    ACCESS          not-accessible
    STATUS          mandatory
    DESCRIPTION     "This table allows to define the reporting mode and
                    priority for each supported trap."
::= {asamTrapMIB 3}

asamTrapDefinitionEntry         OBJECT-TYPE
    SYNTAX          AsamTrapDefinitionEntry
    ACCESS          not-accessible
    STATUS          mandatory
    DESCRIPTION     "Entry for Trap definitions"
    INDEX           {asamTrapId}
::= {asamTrapDefinitionTable 1}

AsamTrapDefinitionEntry ::=         SEQUENCE {
                    asamTrapId              INTEGER(0..65535),
                    asamTrapPriority        AsamTrapPriority,
                    asamTrapRepMode         AsamTrapMode
                    }

asamTrapId                      OBJECT-TYPE
    SYNTAX          INTEGER(0..65535)
    ACCESS          read-only
    STATUS          mandatory
    DESCRIPTION     "Index of the table and trap identifier. For standard
                    traps, this id is used as generic trap type. For
                    enterprise traps, this id is used as the specific
                    trap type in the TRAP PDU."
::= {asamTrapDefinitionEntry 1}

asamTrapPriority                    OBJECT-TYPE
    SYNTAX          AsamTrapPriority
    ACCESS          read-write
    STATUS          mandatory
    DESCRIPTION     "This object allows to configure the priority
                    of a trap. This value can be set to urgent,
                    high, medium or low. "
::= {asamTrapDefinitionEntry 2}

asamTrapRepMode                     OBJECT-TYPE
    SYNTAX          AsamTrapMode
    ACCESS          read-write
    STATUS          obsolete
    DESCRIPTION     "This object is to manage the reporting mode 
                    of a trap. This value can be set to Enabled
                    or Disabled."
::= {asamTrapDefinitionEntry 3}

asamTrapManagersTable        OBJECT-TYPE
    SYNTAX          SEQUENCE OF AsamTrapManagerEntry
    ACCESS          not-accessible
    STATUS          mandatory
    DESCRIPTION     "An SNMP manager should create an entry in this table
                    when it requests to receive traps."
::= {asamTrapMIB 11}

asamTrapManagerEntry    OBJECT-TYPE
    SYNTAX          AsamTrapManagerEntry
    ACCESS          not-accessible
    STATUS          mandatory
    DESCRIPTION     "Entry for Trap destinations"
    INDEX           {asamTrapManagerAddress, asamTrapManagerPort }
::= {asamTrapManagersTable 1}

AsamTrapManagerEntry ::=    SEQUENCE
                    {
                    asamTrapManagerAddress             IpAddress, 
                    asamTrapManagerPort                INTEGER,
                    asamTrapManagerPriority            AsamTrapPriority,
                    asamTrapManagerTrapMask            AsamTrapMask,
                    asamTrapManagerMaxPerWindow        INTEGER,
                    asamTrapManagerWindowTime          INTEGER,
                    asamTrapManagerMaxBufSize          INTEGER,
                    asamTrapManagerSecondsInBetween    INTEGER,
                    asamTrapManagerResetBuffer         AsamTrapReset,
                    asamTrapManagerResetTime           NetworkTimeInSeconds,
                    asamTrapManagerBufferOverflow      AsamTrapOverflow,
                    asamTrapManagerAlarmSeverity       AsamAlarmSeverityType,
                    asamTrapManagerRowStatus           RowStatus,
                    asamTrapManagerTrapExtMask         AsamTrapMask
                    }

asamTrapManagerAddress      OBJECT-TYPE
    SYNTAX          IpAddress
    ACCESS          read-write
    STATUS          mandatory
    DESCRIPTION     "IP address of the SNMP manager to send traps to." 
::= {asamTrapManagerEntry 1}

asamTrapManagerPort         OBJECT-TYPE
    SYNTAX          INTEGER  (0..65536)
    ACCESS          read-write
    STATUS          mandatory
    DESCRIPTION     "The destination UDP port number for sending traps"
::= {asamTrapManagerEntry 2}

asamTrapManagerPriority     OBJECT-TYPE
    SYNTAX          AsamTrapPriority 
    ACCESS          read-write
    STATUS          mandatory
    DESCRIPTION     "The Lowest priority of a trap that should
                    be sent to the SNMP manager."
    DEFVAL          { medium }
::= {asamTrapManagerEntry 3}

asamTrapManagerTrapMask            OBJECT-TYPE
    SYNTAX          AsamTrapMask
    ACCESS          read-write
    STATUS          mandatory
    DESCRIPTION     "This is a bitmask.  Each bit represents a trap or
                    a variable in the changeOccured trap.
                    If a bit is set, the corresponding trap or
                    variable within a trap is enabled.
                    Following list gives the assigned bits for the traps:
                    bit 0 : coldStart
                    bit 2 : linkDown
                    bit 3 : linkUp
                    bit 4 : authenticationFailure
                    bit 7 : changeOccured
                    bit 10: lineTestReport
                    bit 11: initStarted
                    bit 12: licenseKeyChangeOccurred
                    bit 13: topoChanged
                    bit 14: seltStateChanged
                    bit 15: dhcpSessionPreempted
                    Following list gives the assigned bits for the changeOccured
                    variables:
                    bit 16: asamAlarmTrapNumberOfAlarmChanges
                    bit 17: asamPhyItfNumberChangeOccurred
                    bit 18: eqptHwNumberOfChanges
                    bit 19: asamNumberOfSets
                    bit 20: asamNumberOfIndeterminateChanges
                    bit 21: asamNumberOfWarningChanges
                    bit 22: asamNumberOfMinorChanges
                    bit 23: asamNumberOfMajorChanges
                    bit 24: asamNumberOfCriticalChanges
                    bit 25: eqptProtNumberOfChanges
                    bit 26: asamCraftLoginStatus
                    bit 27: eqptRestartNumberOfChanges
                    bit 28: asamNumOfNTRReferenceChanges
                    bit 29: eqptPortMappingGlobalChangeCounter"                     
     DEFVAL         { '1FFF8481'H } 
::= {asamTrapManagerEntry 4}

asamTrapManagerMaxPerWindow         OBJECT-TYPE
    SYNTAX          INTEGER(1..20)
    ACCESS          read-write
    STATUS          mandatory
    DESCRIPTION     "This object defines the number of traps that can 
                    be sent in a limited time base. This limited 
                    time-base is defined as Window Time."
    DEFVAL          { 2 }
::= {asamTrapManagerEntry 5}

asamTrapManagerWindowTime           OBJECT-TYPE
    SYNTAX          INTEGER(0..3600)
    ACCESS          read-write
    STATUS          mandatory
    DESCRIPTION     "This object defines the time-base for
                    asamTrapManagerMaxPerWindow."
    DEFVAL          { 60 }
::= {asamTrapManagerEntry 6}

asamTrapManagerMaxBufSize           OBJECT-TYPE
    SYNTAX          INTEGER(1..20)
    ACCESS          read-write
    STATUS          mandatory
    DESCRIPTION     "This object defines the number of traps that can be
                     queued while waiting to be sent."
    DEFVAL          { 10 }
::= {asamTrapManagerEntry 7}

asamTrapManagerSecondsInBetween     OBJECT-TYPE
    SYNTAX          INTEGER(0..3600)
    ACCESS          read-write
    STATUS          mandatory
    DESCRIPTION     "This object defines the number of seconds to
                    be waited between 2 traps. Traffic shaping
                    is done according to this object value."
    DEFVAL          { 30 }
::= {asamTrapManagerEntry 8}

asamTrapManagerResetBuffer          OBJECT-TYPE
    SYNTAX          AsamTrapReset
    ACCESS          read-write
    STATUS          mandatory
    DESCRIPTION     "This object is a button-like object. The
                    parameters for filtering and shaping only become
                    active after a trap has been sent.
                    To activate new values immediately,
                    buffers should be reset. This object is defined
                    to reset buffers. When it is set to reset,
                    the buffer is cleared and new shaping parameters
                    are taken into account. The object value is set to
                    resetCompleted at the end of the reset process.
                    The ASAM does not take any action, when the
                    object value is set to resetCompleted by the SNMP
                    manager."
::= {asamTrapManagerEntry 9}

asamTrapManagerResetTime      OBJECT-TYPE
    SYNTAX          NetworkTimeInSeconds
    ACCESS          read-only
    STATUS          mandatory
    DESCRIPTION     "Time when the buffer has been reset."
::= {asamTrapManagerEntry 10}

asamTrapManagerBufferOverflow       OBJECT-TYPE
    SYNTAX          AsamTrapOverflow
    ACCESS          read-only
    STATUS          mandatory
    DESCRIPTION     "This object indicates the status of the trap buffer.
                    If buffer overflow occurred, it is set to overflowed.
                    The object value is set to notoverflowed, after resetting
                    the buffer."
    DEFVAL          { notoverflowed }
::= {asamTrapManagerEntry 11}

asamTrapManagerAlarmSeverity        OBJECT-TYPE
   SYNTAX          AsamAlarmSeverityType
   ACCESS          read-write
   STATUS          mandatory
   DESCRIPTION     "This object represents the lowest severity level that an 
                   alarm must have in order to be reported."
   DEFVAL          { major }
::= {asamTrapManagerEntry 12}

asamTrapManagerRowStatus  OBJECT-TYPE
    SYNTAX          RowStatus
    ACCESS          read-write
    STATUS          mandatory
    DESCRIPTION     "Object to create and delete a row."
::= {asamTrapManagerEntry 13}

asamTrapManagerTrapExtMask            OBJECT-TYPE
    SYNTAX          AsamTrapMask
    ACCESS          read-write
    STATUS          mandatory
    DESCRIPTION     "This is a bitmask.  Each bit represents a trap.
                    If a bit is set, the corresponding trap is enabled.
                    Following list gives the assigned bits for the traps:
                    bit 0 : radiusServerFailure
                    bit 1 : loginOccured
                    bit 2 : logoutOccured
                    bit 3 : asamTrapManagerChangeOccured
                    bit 4 : mstGenTrap
                    bit 5 : mstErrTrap
                    bit 6 : mstProtocolMigrationTrap
                    bit 7 : mstInvalidBpduRxdTrap
                    bit 8 : mstRegionConfigChangeTrap"
     DEFVAL         { '00000000'H } 
::= {asamTrapManagerEntry 14}

asamTrapManagersLogTable        OBJECT-TYPE
    SYNTAX          SEQUENCE OF AsamTrapManagerLogEntry
    ACCESS          not-accessible
    STATUS          mandatory
    DESCRIPTION     "A read only table that keeps per SNMP Manager of the asamTrapManagersTable
                    the last send traps."
::= {asamTrapMIB 12}

asamTrapManagerLogEntry    OBJECT-TYPE
    SYNTAX          AsamTrapManagerLogEntry
    ACCESS          not-accessible
    STATUS          mandatory
    DESCRIPTION     "Entry for Trap Managers Log Table"
    INDEX           {asamTrapManagerLogAddress, asamTrapManagerLogPort, asamTrapManagerLogSeqId }
::= {asamTrapManagersLogTable 1}

AsamTrapManagerLogEntry ::=    SEQUENCE
                    {
                    asamTrapManagerLogAddress             IpAddress, 
                    asamTrapManagerLogPort                INTEGER,
                    asamTrapManagerLogSeqId               Counter,
                    asamTrapManagerLogTrapId              INTEGER,
                    asamTrapManagerLogIfIndex             INTEGER,
                    asamTrapManagerLogIpAddress           IpAddress
                    }

asamTrapManagerLogAddress      OBJECT-TYPE
    SYNTAX          IpAddress
    ACCESS          read-only
    STATUS          mandatory
    DESCRIPTION     "IP address of the SNMP manager" 
::= {asamTrapManagerLogEntry 1}

asamTrapManagerLogPort         OBJECT-TYPE
    SYNTAX          INTEGER  (0..65536)
    ACCESS          read-only
    STATUS          mandatory
    DESCRIPTION     "The destination UDP port number of the SNMP manager"
::= {asamTrapManagerLogEntry 2}

asamTrapManagerLogSeqId       OBJECT-TYPE
    SYNTAX          Counter
    ACCESS          read-only
    STATUS          mandatory
    DESCRIPTION     "The sequence number of the Trap"
::= {asamTrapManagerLogEntry 3}

asamTrapManagerLogTrapId    OBJECT-TYPE
    SYNTAX          INTEGER  (0..255)
    ACCESS          read-only
    STATUS          mandatory
    DESCRIPTION     "The Trap Id."
::= {asamTrapManagerLogEntry 4}

asamTrapManagerLogIfIndex      OBJECT-TYPE
    SYNTAX          INTEGER
    ACCESS          read-only
    STATUS          mandatory
    DESCRIPTION     "The content of the Trap in case of LinkDown, LinkUp and SeltStateChanged trap"
::= {asamTrapManagerLogEntry 5}

asamTrapManagerLogIpAddress      OBJECT-TYPE
    SYNTAX          IpAddress
    ACCESS          read-only
    STATUS          mandatory
    DESCRIPTION     "IpAddress should be part of the content of the Trap in case of loginOccured, logoutOccured and asamTrapManagerChangeOccured trap"
::= {asamTrapManagerLogEntry 6}

asamTrapDestinationNextAvailable    OBJECT-TYPE
    SYNTAX          INTEGER (0..10)
    ACCESS          read-only
    STATUS          obsolete
    DESCRIPTION     "This object gives the next available index
                    in the asamTrapDestinationTable. If it 
                    returns 0, it means no free index left."
::= {asamTrapMIB 1}

asamTrapDestinationTable        OBJECT-TYPE
    SYNTAX          SEQUENCE OF AsamTrapDestinationEntry
    ACCESS          not-accessible
    STATUS          obsolete
    DESCRIPTION     "NMC should create an entry in this table when it  
                    requests to receive traps. The index to create a 
                    row should be equal to the object value of 
                    asamTrapDestinationNextAvailable. And Row
                    Status field of the entry should be set to 
                    CreateAndGo. If other objects in the entry 
                    are set to valid values, RowStatus is set to 
                    Active by the agent and entry becomes Active.
                    To delete an entry from this table, RowStatus 
                    should be set to Destroy value by the SNMP 
                    manager. "
::= {asamTrapMIB 2}

asamTrapDestinationEntry    OBJECT-TYPE
    SYNTAX          AsamTrapDestinationEntry
    ACCESS          not-accessible
    STATUS          obsolete
    DESCRIPTION     "Entry for Trap destinations"
    INDEX           {asamTrapDestinationIndex}
::= {asamTrapDestinationTable 1}

AsamTrapDestinationEntry ::=    SEQUENCE
                    {asamTrapDestinationIndex       INTEGER,
                    asamTrapDestinationAddress      IpAddress, 
                    asamTrapDestinationPort         INTEGER,
                    asamTrapDestinationPriority     AsamTrapPriority,
                    asamTrapDestinationEntryStatus  RowStatus}

asamTrapDestinationIndex            OBJECT-TYPE
    SYNTAX          INTEGER (1..10)
    ACCESS          read-write
    STATUS          obsolete
    DESCRIPTION     "Index of the Trap destination entry"
::= {asamTrapDestinationEntry 1}

asamTrapDestinationAddress      OBJECT-TYPE
    SYNTAX          IpAddress
    ACCESS          read-write
    STATUS          obsolete
    DESCRIPTION     "Network address of the Network Management
                    Center to send traps." 
::= {asamTrapDestinationEntry 2}

asamTrapDestinationPort         OBJECT-TYPE
    SYNTAX          INTEGER  (1..65536)
    ACCESS          read-write
    STATUS          obsolete
    DESCRIPTION     "The destination port number for sending traps"
    DEFVAL          { 162 }
::=     {asamTrapDestinationEntry 3}

asamTrapDestinationPriority     OBJECT-TYPE
    SYNTAX          AsamTrapPriority 
    ACCESS          read-write
    STATUS          obsolete
    DESCRIPTION     "The Lowest priority of a trap that should
                    be sent to the Network Management Center."
    DEFVAL          { medium }
::=     {asamTrapDestinationEntry 4}

asamTrapDestinationEntryStatus  OBJECT-TYPE
    SYNTAX          RowStatus
    ACCESS          read-write
    STATUS          obsolete
    DESCRIPTION     "Validity of this entry. If it is set to CreateAndGo 
                    by the SNMP Manager, other objects of the entry are 
                    checked. If they are valid, then the agent sets RowStatus 
                    to Active. If set to Destroy, the entry is deleted."
::= {asamTrapDestinationEntry 5}

asamTrapMaxPerWindow                OBJECT-TYPE
    SYNTAX          INTEGER(0..4294967295)
    ACCESS          read-write
    STATUS          obsolete
    DESCRIPTION     "This object defines the number of traps that can 
                    be sent in a limited time base. This limited 
                    time-base is defined as Window Time."
    DEFVAL          { 2 }
::= {asamTrapMIB 4}

asamTrapWindowTime              OBJECT-TYPE
    SYNTAX          INTEGER(0..4294967295)
    ACCESS          read-write
    STATUS          obsolete
    DESCRIPTION     "This object defines the number of seconds that 
                    the number traps is limited by the value of 
                    Trap Max Per Window object."
    DEFVAL          { 60 }
::= {asamTrapMIB 5}

asamTrapMaxBufSize              OBJECT-TYPE
    SYNTAX          INTEGER(0..4294967295)
    ACCESS          read-write
    STATUS          obsolete
    DESCRIPTION     "This object defines the number buffers to 
                    keep traps to be sent."
    DEFVAL          { 10 }
::= {asamTrapMIB 6}

asamTrapSecondsInBetween            OBJECT-TYPE
    SYNTAX          INTEGER(0..4294967295)
    ACCESS          read-write
    STATUS          obsolete
    DESCRIPTION     "This object defines the number seconds to 
                    be waited between 2 traps. Traffic shaping
                    is done according to this object value."
    DEFVAL          { 30 }  
::= {asamTrapMIB 7}

asamTrapResetBuffer             OBJECT-TYPE
    SYNTAX          AsamTrapReset
    ACCESS          read-write
    STATUS          obsolete
    DESCRIPTION     "This object is a button-like object. The 
                    parameter for filtering and shaping are not 
                    active immediately. To activate new values, 
                    buffers should be reset. This object is defined 
                    to reset buffers. When it is set to Reset Value,
                    the buffer is reset. At the end of reset process,
                    object value is set to resetCompleted. If 
                    object value is set to resetCompleted by the SNMP
                    manager, no action is taken by the agent."
::= {asamTrapMIB 8}

asamTrapResetBufferTime             OBJECT-TYPE
    SYNTAX          NetworkTimeInSeconds
    ACCESS          read-only
    STATUS          obsolete
    DESCRIPTION     "Time when the buffer has been reset."
::= {asamTrapMIB 9}

asamTrapBufferOverflow          OBJECT-TYPE
    SYNTAX          AsamTrapOverflow
    ACCESS          read-only
    STATUS          obsolete
    DESCRIPTION     "This object gives the information whether the trap buffer
                    Has overflowed or not. If buffer overflows it is set to
                    overflowed value. After resetting the buffer, the object value
                    is set to notoverflowed."
::= {asamTrapMIB 10}

END
