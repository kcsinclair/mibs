-- orig Plim_mib

PLIM-ETHERNET-MIB DEFINITIONS ::= BEGIN

IMPORTS
		Gauge, Counter
			FROM RFC1155-SMI
		OBJECT-TYPE
			FROM RFC-1212
		RowStatus
			FROM SNMPv2-TC
		ifIndex
        		FROM ITF-MIB
		MacAddress, dot1dBasePort
			FROM BRIDGE-MIB
		PortList, dot1qFdbId, dot1qVlanIndex, VlanId, VlanIndex, SnmpAdminString,
 		dot1vProtocolTemplateFrameType, dot1vProtocolTemplateProtocolValue, 
		dot1vProtocolPortGroupId
			FROM Q-BRIDGE-MIB
		asam
			FROM SYSTEM-MIB
		NetworkTimeInSeconds
			FROM	 ASAM-TC-MIB
                eqptSlotId 
                        FROM  ASAM-EQUIP-MIB
  AsamProfileRefCount  FROM ASAM-TC-MIB
		AtmVpIdentifier, AtmVcIdentifier
			FROM ATM-TC-MIB;
	      
PriorityBitList ::= OCTET STRING (SIZE(1))
        
VlanList ::= OCTET STRING
	
ExtendInterworkingEvent ::= OCTET STRING

plimEthernet		OBJECT IDENTIFIER ::= { asam 31 }

plimSystemObject	OBJECT IDENTIFIER ::= { plimEthernet 1 }

	numPortsInPortList	OBJECT-TYPE
		SYNTAX	INTEGER
		ACCESS	read-only
		STATUS	mandatory
		DESCRIPTION
			"The object dot1dBaseNumPorts specifies the number of ports
			controlled by the bridging entity. This at the same time 
			determines the size of objects such as the object
			dot1qVlanStaticEgressPorts, more in general the objects of 
			the SYNTAX 'Portlist'. For those entities supporting many 
			Ports this would result in an object of a too big size. 
			The alternative is to split this object in a set of bitlists.
			The object numPortsInPortList identifies the number of 
			Ports in objects of the type 'PortList'.
             ALCATEL NOTE:
                 ACCESS:     NA       USAGE:      NA
                 PERSIST:    NO       INSRVMOD:   NO
                 RANGE:      NA       
                 DEFVALUE:   DEP [depends on the value of dot1dBaseNumPorts]
                 UNITS:      NA       SPARSE:     NA
                 DESCR:      NA"
		::= { plimSystemObject 2 }

	extendVlanMgntMode OBJECT-TYPE
		SYNTAX	INTEGER
				{
				inband(1),
				outband(2)
				}
		ACCESS	read-only
		STATUS	mandatory
		DESCRIPTION
			"The selection of the management mode of the PLIM.
			In case inband is selected, the extendVlanMgntVlanId shall
			contain a valid	Mgnt VLAN id.
			In case outband is selected, the in-band management path
			is disabled
			The default (initial) value shall be in-band
             ALCATEL NOTE:
                 ACCESS:     NA       USAGE:      NA
                 PERSIST:    NO       INSRVMOD:   NO
                 RANGE:      1,2      DEFVALUE:   1[inband]
                 UNITS:      NA       SPARSE:     NA
                 DESCR:      NA"
		::= { plimSystemObject 4 }

	extendVlanMgntVlanId OBJECT-TYPE
		SYNTAX	INTEGER (0|1..4093)

		ACCESS	read-write
		STATUS	mandatory
		DESCRIPTION
			"The VLAN-ID referring to the management VLAN.
			The instance of this object only exists when extendVlanMgntMode
			is set to in-band.
                        This object is meaningful when the NE comprises a SHUB.
                        When the NE comprises an IHUB, the value of this object is zero, 
         indicating 'not applicable'.
             ALCATEL NOTE:
                 ACCESS:     NA       USAGE:      NA
                 PERSIST:    NO       INSRVMOD:   YES
                 RANGE:      DEP| 
                             1-4093 in case of SHUB, 0 in case of IHUB
                 DEFVALUE:   DEP| 
                             4093 in case of SHUB, 0 in case of IHUB
                 UNITS:      NA       SPARSE:     NA
                 DESCR:      NA"
		::= { plimSystemObject 5 }

	systemBroadcastControl OBJECT-TYPE
		SYNTAX	INTEGER 
				{
				on (1),
				off (2)
				}
		ACCESS	read-write
		STATUS	mandatory
		DESCRIPTION
			"The object is used to control the downstream broadcast behaviour
			of the system. When it is 'off', all the downstream broadcast
			packets will be discarded for each VLAN domain.
			Note: except for broadcast packets of protocols for which a protocol
			specific behaviour is defined.
             ALCATEL NOTE:
                 ACCESS:     NA       USAGE:      NA
                 PERSIST:    YES      INSRVMOD:   YES
                 RANGE:      1,2      DEFVALUE:   1[on]
                 UNITS:      NA       SPARSE:     NA
                 DESCR:      NA"
		::= { plimSystemObject 6 }

   extendVlanTraceAndDebugVlanId OBJECT-TYPE 
      SYNTAX    INTEGER (0|1..4093)
      ACCESS read-write 
      STATUS mandatory 
      DESCRIPTION 
         "The VLAN-ID referring to the Trace and Debug VLAN for NT-ONT communication. 
          The default value shall be 0 which means no trace and debug VLAN. The 
          valid range shall be from (0..4093).
             ALCATEL NOTE:
                 ACCESS:     NA       USAGE:      NA
                 PERSIST:    YES      INSRVMOD:   YES
                 RANGE:      0..4093  DEFVALUE:   0[none]
                 UNITS:      NA       SPARSE:     NA
                 DESCR:      NA"

       DEFVAL { 0 } 
          ::= { plimSystemObject 11 }

        extendVlanBcmStackingVlanId OBJECT-TYPE
            SYNTAX    INTEGER (0|1..4093)
            ACCESS    read-write    
            STATUS    mandatory
            DESCRIPTION   
"The VLAN-ID refers to the VLAN used for communicating between stacked Broadcom switching devices on the NTs. Multiple Broadcom switching devices are stacked or chained to act as one larger device. The stacking VLAN is required to communicate amongst the devices.
In case the value of the object is modified, the system will accept unless this VLAN is already configured for another purpose. When the configuration is accepted, the VLAN ID is reserved and is no longer available for other configurations.
Take care: a modification to this object will only take effect after a system reset has taken place.

This object is introduced in ISAM R3.7.10.
The object is only meaningful in case of an NE with IHUB, where Broadcom switches of one NT or NT-A and NT-B are stacked.
When the NE comprises an SHUB, the value of this object is zero, indicating not applicable.

             ALCATEL NOTE:
                 ACCESS:     NA       USAGE:      NA
                     PERSIST:    YES      INSRVMOD:   YES 
                     RANGE:      DEP|
                            1-4093 in case of IHUB, 0 in case of SHUB
                     DEFVALUE:   DEP|     
                            4092 in case of IHUB, 0 in case of SHUB
                     UNITS:      NA       SPARSE:     NA
                     DESCR:      NA"
        ::= { plimSystemObject 12 }
 
        extendVlanCurBcmStackingVlanId OBJECT-TYPE
            SYNTAX    INTEGER (0|1..4093)
            ACCESS    read-only
            STATUS    mandatory
            DESCRIPTION
"The VLAN-ID refers to the VLAN used for communicating between stacked Broadcom switching devices on the NTs.
This object has the same meaning as the extendVlanBcmStackingVlanId, except that it reflects the VLAN which is currently applied.

This object is introduced in ISAM R3.7.10.
The object is only meaningful in case of an NE with IHUB, where Broadcom switches of one NT or NT-A and NT-B are stacked.
When the NE comprises an SHUB, the value of this object is zero, indicating 'not applicable'.

             ALCATEL NOTE:
                 ACCESS:     NA       USAGE:      NA
                     PERSIST:    YES      INSRVMOD:   NA
                     RANGE:      DEP|
                                 1-4093 in case of IHUB, 0 in case of SHUB
                     DEFVALUE:   DEP|
                                 4092 in case of IHUB, 0 in case of SHUB
                     UNITS:      NA       SPARSE:     NA
                     DESCR:      NA"
        ::= { plimSystemObject 16 }

        extendVlanBcmNetworkVlanId OBJECT-TYPE
            SYNTAX    INTEGER (0|1..4093)
            ACCESS    read-write    
            STATUS    mandatory
            DESCRIPTION   
                "The VLAN-ID refers to the VLAN used for internal usage, i.e.
                 handling of packets from network ports at the Broadcom switching
                 device.
                 In case the value of the object is modified, the system will
                 accept unless this VLAN is already configured for another purpose.
                 When the configuration is accepted, the VLAN ID is reserved and is
                 no longer available for other configurations.
                 Take care: a modification to this object will only take effect
                 after a system reset has taken place.

                 This object is introduced in ISAM R4.1
                 The object is only meaningful in case of an NE with IHUB, even if 
                 no ports are used in network mode.
                 When the NE comprises an SHUB, the value of this object is zero,  
                 indicating not applicable.
                 
                 ALCATEL NOTE:   
                     ACCESS:     NA       USAGE:      NA
                     PERSIST:    YES      INSRVMOD:   YES 
                     RANGE:      DEP|
                            1-4093 in case of IHUB, 0 in case of SHUB
                     DEFVALUE:   DEP|     
                            4089 in case of IHUB, 0 in case of SHUB
                     UNITS:      NA       SPARSE:     NA
                     DESCR:      NA"
        ::= { plimSystemObject 17 }
 
        extendVlanCurBcmNetworkVlanId OBJECT-TYPE
            SYNTAX    INTEGER (0|1..4093)
            ACCESS    read-only
            STATUS    mandatory
            DESCRIPTION
                "The VLAN-ID refers to the VLAN used for internal handling of
                 packets from network ports at the Broadcom switching device.
                 This object has the same meaning as the
                 extendVlanBcmNetworkVlanId, 
                 except that it reflects the VLAN which is currently applied.
                 The initial value for this object equals the value of object 
                 extendVlanBcmNetworkVlanId.

                 This object is introduced in ISAM R4.1
                 The object is only meaningful in case of an NE with IHUB,even 
                 if no ports are used in network mode.
                 When the NE comprises an SHUB, the value of this object is zero, 
                 indicating not applicable.

                 ALCATEL NOTE:   
                     ACCESS:     NA       USAGE:      NA
                     PERSIST:    YES      INSRVMOD:   NA
                     RANGE:      DEP|
                                 1-4093 in case of IHUB, 0 in case of SHUB
                     DEFVALUE:   NA
                     UNITS:      NA       SPARSE:     NA
                     DESCR:      NA"
        ::= { plimSystemObject 18 }

        extendPeripheralMgntVlanId OBJECT-TYPE
                SYNTAX        INTEGER (0|1..4093)
                ACCESS        read-write
                STATUS        mandatory
                DESCRIPTION   
                 "The VLAN-ID referring to the Pheripheral management VLAN.
                 ISAM supports dedicated interfaces for the remote management of 
                 co-located 3rd party equipment through Ethernet connections. 
                 In case of FD-REM a 10/100 Base-T electronical interface is 
                 provided on the REM control board NRCD-x. 3rd party equipment can 
                 be connected to this Ethernet port. 
                 This object is the VLAN used for the corresponding management 
                 traffic. The value 0 of this object is indicating not configured. 
           
                           ALCATEL NOTE:
                   ACCESS:    NA      USAGE:      NA
                   PERSIST:   YES     INSRVMOD:   YES
                   RANGE:     0|1-4093| 
                       DEFVALUE:   0           
                       UNITS:      NA       
                   SPARSE:     NA
                   DESCR:      NA"
        ::= { plimSystemObject 19 }

plimExtendVlan	OBJECT IDENTIFIER ::= {plimEthernet 2}

	ExtendVlanSystemMode ::=	INTEGER
				{
				crossconnect(1),
				residentialBridge(2),
				qosAware (3),
            layer2terminated (4),
            mirroring (7)
				}

	ExtendVlanSystemPriority ::=	INTEGER
				{
				bestEffort (0),
				background (1),
				spare (2),
				excellentEffort (3),
				controlledLoad (4),
				videoLessThan100msLatencyAndJitter (5),
				videoLessThan10msLatencyAndJitter (6),
				networkControl (7)
				}
	ExtendPortVlanUntagged ::= INTEGER
				{
				untagged (1),
				singletagged (2),
				prioritytagged (3)
				}

	extendVlanCurrentVlanList OBJECT-TYPE
		SYNTAX	VlanList
		ACCESS	read-only
		STATUS	mandatory
		DESCRIPTION
			"The current configured VLAN list in the PLIM. This is
			the set of VLANs for which an entry is available in
			the dot1qVlanStaticTable. A 1 indicates an entry for
			this VLAN exists in the dot1qVlanStaticTable, a 0
			indicates no corresponding entry exists.
			Note: in NBE, the object is only used for Local User VLANs.
			Note: it includes also those VLANs that are reserved for other
			purposes and for which there is no corresponding entry in
			dot1qVlanStaticTable. E.g. the VLAN reserved for inband management 
			in the iSAM.
             ALCATEL NOTE:
                 ACCESS:     NA       USAGE:      NA
                 PERSIST:    YES      INSRVMOD:   NO
                 RANGE:      NA       DEFVALUE:   NA
                 UNITS:      NA       SPARSE:     NA
                 DESCR:      NA"
		::= { plimExtendVlan 3}

	extendVlanStaticTable OBJECT-TYPE
		SYNTAX	SEQUENCE OF ExtendVlanStaticEntry
		ACCESS	not-accessible
		STATUS	mandatory
		DESCRIPTION
			"A table containing configuration information for
			each VLAN configured into the device by (local or
			network) management.
			Note: in NBE, the table is only used for Local User VLANs.
             ALCATEL NOTE:
                 TABLESIZE:  DEP [depends on the value of dot1qVlanCurrentTable]
                 DESCR:      NA"
		::= { plimExtendVlan 4 }

	extendVlanStaticEntry OBJECT-TYPE
		SYNTAX	ExtendVlanStaticEntry
		ACCESS	not-accessible
		STATUS	mandatory
		DESCRIPTION
			"An entry in the extendVlanStaticTable used to augment
 			the table dot1qVlanStaticTable with information common to all Vlans."
		INDEX	{ dot1qVlanIndex }
		::= { extendVlanStaticTable 1 }

	ExtendVlanStaticEntry ::=
		SEQUENCE	{ 

				extendVlanStaticSystemMode
					ExtendVlanSystemMode,

                                extendVlanStaticName
                                        SnmpAdminString,
                                extendVlanStaticRowStatus
                                        RowStatus,
				extendVlanStaticPriority
					ExtendVlanSystemPriority,
				extendVlanStaticBroadcastControl
					INTEGER,
				extendVlanStaticVersionNbr
					INTEGER,
				extendVlanRemoveAllPorts
					INTEGER,
				extendDot1vProtocolVlanGroupId
					OCTET STRING, 
				extendAddPppoeRelayTag
					INTEGER,
				extendNetworkIfIndex
					INTEGER,
				extendAddDhcpOption82
					INTEGER,
				extendCircuitIdControl
					INTEGER,
				extendRemoteIdControl
					INTEGER,
                                extendDslLineRateInsertionForDhcp
                                        INTEGER,	
                                extendDslLineRateInsertionForPppoe
                                        INTEGER,	
				extendCircuitIdControlPppoe
					INTEGER,
				extendRemoteIdControlPppoe
					INTEGER,
                                extendVlanSecureForwardingControl
					INTEGER,
                                extendVlanMacAgingTime
					INTEGER,
                                extendVlanStaticVirtualMac
                 	                INTEGER,
                                extendVlanStaticVMacSrcAddrDownstBlock
                 	                INTEGER,
                                extendVlanStaticL2CPTransparencyControl 
				        INTEGER,
				extendInterfaceIdControlDhcpv6
					INTEGER,
				extendRemoteIdControlDhcpv6
					INTEGER,
				extendTrustedPortControlDhcpv6
					INTEGER,
                                extendVlanStaticNoVmacInOpt61 
                INTEGER,
				extendEnterpriseNumberDhcpv6
					INTEGER,
				extendSecureFilterIcmpv6
		                        INTEGER,
             extendVlanStaticIPv4McastControl
                INTEGER,
             extendVlanStaticIPv6McastControl
                INTEGER,
             extendVlanStaticMacMcastControl
                INTEGER,
             extendVlanStaticIngressQosTcProfile
                INTEGER,
             extendVlanStaticProtocolControlFlags
                OCTET STRING,
             extendVlanStaticPortsNum
                INTEGER,
             extendVlanUnknownUnicastControl
               INTEGER,
             extendVlanIpAntispoofingEnable
               INTEGER
				}

	extendVlanStaticSystemMode OBJECT-TYPE
		SYNTAX	ExtendVlanSystemMode
		ACCESS	read-write
		STATUS	mandatory
		DESCRIPTION
			"The Ethernet-ATM interworking function of this VLAN can work 
         in either cross-connect mode, residential bridging mode, QOS aware 
             or 'layer2Terminated' mode.
             ALCATEL NOTE:
                 ACCESS:     RO       USAGE:      MAND
                 PERSIST:    YES      INSRVMOD:   NO
                 RANGE:   1,2,3,4,7   DEFVALUE:   NA
                 UNITS:      NA       SPARSE:     NA
                 DESCR:      NA"

		::= { extendVlanStaticEntry 3 }

   extendVlanStaticName OBJECT-TYPE
      SYNTAX   SnmpAdminString 
      ACCESS   read-write
      STATUS   mandatory
      DESCRIPTION
         "An administratively assigned string, which may be used
         to identify the VLAN."
      ::= { extendVlanStaticEntry 6 }

      extendVlanStaticRowStatus OBJECT-TYPE
      SYNTAX   RowStatus
      ACCESS  read-write
      STATUS   mandatory
      DESCRIPTION
         "This object indicates the status of this entry."
      ::= { extendVlanStaticEntry 7 }

	extendVlanStaticPriority	OBJECT-TYPE
		SYNTAX	ExtendVlanSystemPriority
		ACCESS	read-write
		STATUS	mandatory
		DESCRIPTION
      "For the untagged frames received over the ATM PVC port identified by
			the VLAN ID and to be sent upstream over the Ethernet 
			interface, this object specifies the Ethernet priority tag to 
			be set only in these untagged frames as default p-bit in 
             case priorityMappingSwitch is set to (1) vlan-id.
             ALCATEL NOTE:
                 ACCESS:     NA       USAGE:      OPT
                 PERSIST:    YES      INSRVMOD:   YES
                 RANGE:      0..7     DEFVALUE:   0[bestEffort]
                 UNITS:      NA       SPARSE:     NA
                 DESCR:      NA"
		::= { extendVlanStaticEntry 8 }

	extendVlanStaticBroadcastControl OBJECT-TYPE
		SYNTAX	INTEGER 
				{
				on (1),
				off (2)
				}
		ACCESS	read-write
		STATUS	mandatory
		DESCRIPTION
			"The object is used to control the downstream broadcast behaviour
			of the VLAN. When it is 'off', all the downstream broadcast
			packets of this VLAN domain will be discarded.
			Note: except for broadcast packets of protocols for which a protocol
			specific behaviour is defined.
             ALCATEL NOTE:
                 ACCESS:     NA       USAGE:      OPT
                 PERSIST:    YES      INSRVMOD:   YES
                 RANGE:      1,2      DEFVALUE:   2[off]
                 UNITS:      NA       SPARSE:     NA
                 DESCR:      NA"
		::= { extendVlanStaticEntry 9 }

	extendVlanStaticVersionNbr OBJECT-TYPE
		SYNTAX          INTEGER
		ACCESS          read-write
		STATUS          mandatory
		DESCRIPTION     
         "The manager can associate a version number to the VLAN data. 
         It is set to 1 when the VLAN is created and can be incremented 
         by the manager when the VLAN data is modified.
             ALCATEL NOTE:
                 ACCESS:     NA       USAGE:      OPT
                 PERSIST:    YES      INSRVMOD:   YES
                 RANGE:      NA       DEFVALUE:   1
                 UNITS:      NA       SPARSE:     NA
                 DESCR:      NA"
		::= {extendVlanStaticEntry 10}

	extendVlanRemoveAllPorts OBJECT-TYPE
		SYNTAX	INTEGER
				{
				clearAllPorts (0)
				}
		ACCESS	write-only
		STATUS	mandatory
		DESCRIPTION
			"Writing the value clearAllPorts to this object causes the system 
			to remove all port-VLAN associations for this port.
             ALCATEL NOTE:
                 ACCESS:     NA       USAGE:      NA
                 PERSIST:    NO       INSRVMOD:   NA
                 RANGE:      NA       DEFVALUE:   NA
                 UNITS:      NA       SPARSE:     NA
                 DESCR:      NA"
		::= { extendVlanStaticEntry 11 }

	extendDot1vProtocolVlanGroupId OBJECT-TYPE
		SYNTAX	OCTET STRING 
		ACCESS	read-write
		STATUS	mandatory
		DESCRIPTION
			"This filter is applicable on a RB ,CC or Qos aware VLAN.
			If the octet string contains all zeros, no filter is configured 
			(default value) In all other cases, only traffic belonging to a 
			dot1v protocol group of which the corresponding bit is set shall 
			be passed. All other traffic shall be deleted. The mapping of the
			protocol groups is as follows :
                Bit 0:  PPPoE 
                Bit 1:  IPoE		 
                Bit 2:  IPv6oE
                Bit 3 - 7: not used and set to 0
             ALCATEL NOTE:
                 ACCESS:     NA       USAGE:      OPT
                 PERSIST:    YES      INSRVMOD:   YES
                 RANGE:      0...7
                 DEFVALUE:   0        UNITS:      NA
                 SPARSE:     NA       DESCR:      NA"
		DEFVAL { "0" }
		::= { extendVlanStaticEntry 12 }

	extendAddPppoeRelayTag OBJECT-TYPE
		SYNTAX	INTEGER
				{
       			true(1),
      			false(2),
				  configurable (3)
      			}
		ACCESS	read-write
		STATUS	mandatory
		DESCRIPTION
         "Setting the object to true enables adding a proprietary relay tag
			to be added to the PPPoE relayed traffic. 
             true(1) means the current fixed format PPPoE tag will be added.
			false(2) means no PPPoE tag will be added.
			configurable(3) means the PPPoE tag will be added with the format
             controlled by CircuitIdControlPppoe and RemoteIdControlPppoe to PPPoE
			relayed traffic (PPPoE discovery only).
             ALCATEL NOTE:
                 ACCESS:     NA       USAGE:      OPT
                 PERSIST:    YES      INSRVMOD:   YES
                 RANGE:      1,2,3    DEFVALUE:   2[false]
                 UNITS:      NA       SPARSE:     NA
                 DESCR:      NA"
		DEFVAL { false }
		::= { extendVlanStaticEntry 13 }

	extendNetworkIfIndex OBJECT-TYPE
		SYNTAX  INTEGER 
		ACCESS  read-only
		STATUS  mandatory
		DESCRIPTION
			"This object returns the IfIndex of the IpoE interface at network side
 			of a layer 2 terminated VLAN. This object has no meaning for all other
 			VLAN types and will be set to 0
             ALCATEL NOTE:
                 ACCESS:     NA       USAGE:      NA
                 PERSIST:    YES      INSRVMOD:   NO
                 RANGE:      NA       DEFVALUE:   0
                 UNITS:      NA       SPARSE:     NA
                 DESCR:      NA"
		::= { extendVlanStaticEntry 14 }

	extendAddDhcpOption82 OBJECT-TYPE
		SYNTAX	INTEGER
				{
       			true(1),
      			false(2)
      			}
		ACCESS	read-write
		STATUS	mandatory
		DESCRIPTION
         "Setting the object to true enables adding option 82 to the DHCP
			packets. This option is only valid for RB VLAN
             ALCATEL NOTE:
                 ACCESS:     NA       USAGE:      OPT
                 PERSIST:    YES      INSRVMOD:   YES
                 RANGE:      1,2      DEFVALUE:   2[false]
                 UNITS:      NA       SPARSE:     NA
                 DESCR:      NA"
		DEFVAL { false }
		::= { extendVlanStaticEntry 15 }

        extendCircuitIdControl OBJECT-TYPE
                SYNTAX INTEGER
                       {
                        notAdd(1),
                        addCustomerId (2),
                        addPhysicalLineId (3),
                        addCcsaFormat (4)
                        }
                ACCESS read-write
                STATUS mandatory
                DESCRIPTION
                        "This object controls what content will be included in the 
                        CirciutId sub option of option 82.The following values are 
                        defined currently:
                        notAdd(1)             CircuitId sub option is not include 
                                              in the option 82.
                        addCustomerId(2)       The CustomerId will be included in 
                                              CircuitId sub option.
                        addPhysicalLineId(3)   A auto-generated PhysicalLineId will 
                                              be included in CircuitId sub option.
                        addCcsaFormat(4)       A auto-generated circuit ID as per 
                                              CCSA format will be included in 
                                              CircuitId sub option.
                        ALCATEL NOTE:
                            ACCESS:     NA       USAGE:      OPT
                            PERSIST:    YES      INSRVMOD:   YES
                            RANGE:      1,2,3,4  DEFVALUE:   1[notAdd]
                            UNITS:      NA       SPARSE:     NA
                            DESCR:      NA"
                DEFVAL { notAdd }
                ::= { extendVlanStaticEntry 16 }

        extendRemoteIdControl OBJECT-TYPE
                SYNTAX INTEGER
                       {
                        notAdd(1),
                        addCustomerId(2) ,
                        addPhysicalLineId(3)
                        }
                ACCESS read-write
                STATUS mandatory
                DESCRIPTION
                        "This object controls what content will be included in the 
                        RemoteId sub option of option 82.The following values are 
                        defined currently:
                        notAdd(1)               RemoteId sub option is not include 
                                                in the option 82.
                        addCustomerId(2)        The CustomerId will be included in 
                                                RemoteId sub option.
                        addPhysicalLineId(3)    An auto-generated PhysicalLineId
                                                be included in RemoteId sub option.
                        ALCATEL NOTE:
                            ACCESS:     NA       USAGE:      OPT
                            PERSIST:    YES      INSRVMOD:   YES
                            RANGE:      1,2      DEFVALUE:   1[notAdd]
                            UNITS:      NA       SPARSE:     NA
                            DESCR:      NA"
                DEFVAL { notAdd }
                ::= { extendVlanStaticEntry 17 }

        extendDslLineRateInsertionForDhcp OBJECT-TYPE
           	   SYNTAX	INTEGER
        		   {
               		 notAdd(1),
              		 addActualLineRate(2)
                }
        	       ACCESS	read-write
          	   STATUS	mandatory
           	   DESCRIPTION
                        "Setting the object to addActualLineRate enables insertion 
                        of DSL linerate  as suboption of Option82 for Layer2 DHCP 
                        Relay. The following values are defined currently:
                        notAdd(1)              The insertion of DSL line rate will 
                                               be disabled as suboption in the 
                                               option 82.
                        addActualLineRate (2)  The insertion of DSL line rate will 
                                               be enabled as suboption in the    
                                               option 82.
                        ALCATEL NOTE:
                            ACCESS:     NA       USAGE:      OPT
                            PERSIST:    YES      INSRVMOD:   YES
                            RANGE:      1,2      DEFVALUE:   1[notAdd]
                            UNITS:      NA       SPARSE:     NA
                            DESCR:      NA"
        	       DEFVAL { notAdd }
        	       ::= { extendVlanStaticEntry 19 }

        extendDslLineRateInsertionForPppoe OBJECT-TYPE
        	      SYNTAX	INTEGER
        		  {
               		 notAdd (1),
              		 addActualLineRate (2)
              		}
        	      ACCESS	read-write
        	      STATUS	mandatory
        	      DESCRIPTION
                	"Setting the object to addActualLineRate enables insertion of DSL
                 linerate as suboption of the vendor specific tag for PPPoE relay. 
                 The following values are defined currently:
                 notAdd(1)           The insertion of DSL line rate will be 
                                     disabled as suboption in vendor specific tag 
                                     for PPPoE.
                 addActualLineRate (2)  The insertion of DSL line rate will be 
                                        enabled as suboption in vendor specific tag 
                                        for PPPoE. 
                 ALCATEL NOTE:
                     ACCESS:     NA       USAGE:      OPT
                     PERSIST:    YES      INSRVMOD:   YES
                     RANGE:      1,2      DEFVALUE:   1[notAdd]
                     UNITS:      NA       SPARSE:     NA
                     DESCR:      NA"
          	DEFVAL { notAdd }
        	    ::= { extendVlanStaticEntry 20 }
        
        extendCircuitIdControlPppoe OBJECT-TYPE
                SYNTAX INTEGER
                       {
                       notAdd(1),
                        addCustomerId (2),
                        addPhysicalLineId (3),
                        addCcsaFormat (4)
                        }
                ACCESS read-write
                STATUS mandatory
                DESCRIPTION
                        "This object controls what content will be included in the 
                        CirciutId sub option for PPPoE relay. The following values 
                        are defined currently:
                        notAdd(1)             CircuitId sub option is not include 
                                              in the option 82.
                        addCustomerId(2)       PPPoE relay will add the customerid 
                                              configured on PVC/DSL line to the 
                                              CircuitId sub-option.
                        addPhysicalLineId(3)   PPPoE relay will add the 
                                               AgentCircuitId string with the 
                                               string generated according to the 
                                               configured 
                                               port numbering method/offset, 
                                               transport classifier and syntax.
                        addCcsaFormat(4)       A auto-generated circuit ID as per 
                                               CCSA format will be included in 
                                               CircuitId sub option.
                        ALCATEL NOTE:
                            ACCESS:     NA       USAGE:      OPT
                            PERSIST:    YES      INSRVMOD:   YES
                            RANGE:      1,2,3,4  DEFVALUE:   1[notAdd]
                            UNITS:      NA       SPARSE:     NA
                            DESCR:      NA"
        
        	        DEFVAL { notAdd }
                ::= { extendVlanStaticEntry 21 }
        
        extendRemoteIdControlPppoe OBJECT-TYPE
                SYNTAX INTEGER
                       {
                        notAdd(1),
                        addCustomerId(2),
                        addPhysicalLineId(3)
                       }
                ACCESS read-write
                STATUS mandatory
                DESCRIPTION
                        "This object controls what content will be included in the 
                        RemoteId sub option for PPPoE relay.The following values 
                        are defined currently:
                        notAdd(1)               RemoteId sub-option is not included 
                              in the PPPoE Relay Tag.
                        addCustomerId(2)        PPPoE relay will add the customerid 
                                                configured on PVC/DSL line to the 
                                                RemoteId sub-option.
                        addPhysicalLineId(3)    PPPoE relay will add an auto-
                                 generated PhysicalLineId in RemoteId sub option.
                        ALCATEL NOTE:
                            ACCESS:     NA       USAGE:      OPT
                            PERSIST:    YES      INSRVMOD:   YES
                            RANGE:      1,2      DEFVALUE:   1[notAdd]
                            UNITS:      NA       SPARSE:     NA
                            DESCR:      NA"
                DEFVAL { notAdd }
                ::= { extendVlanStaticEntry 22 }

        extendVlanSecureForwardingControl OBJECT-TYPE
				SYNTAX	INTEGER 
						{
						disable(1),
						enable (2)
						}
				ACCESS	read-write
				STATUS	mandatory
				DESCRIPTION
                                       " This object is used to enable IP anti-spoofing, DHCP session snooping and ARP relay. 
                        ALCATEL NOTE:
                            ACCESS:     NA       USAGE:      OPT
                            PERSIST:    YES      INSRVMOD:   YES
                            RANGE:      1,2      DEFVALUE:   1[disable]
                            UNITS:      NA       SPARSE:     NA
                            DESCR:      NA"
                DEFVAL { disable }
                ::= { extendVlanStaticEntry 31 }

        extendVlanMacAgingTime OBJECT-TYPE
				SYNTAX	INTEGER
				ACCESS	read-write
				STATUS	mandatory
				DESCRIPTION
"This object is used to configure per VLAN Mac aging time 
in seconds. The default value -1 indicates to inherit the value from the system level.
                        ALCATEL NOTE:
                            ACCESS:     NA       USAGE:      OPT
                            PERSIST:    YES      INSRVMOD:   YES
             RANGE:       -1, 10..1000000       DEFVALUE:   -1
                            UNITS:      seconds  SPARSE:     NA
                            DESCR:      NA"
                DEFVAL { -1 }
                ::= { extendVlanStaticEntry 32 }

          extendVlanStaticVirtualMac OBJECT-TYPE
                SYNTAX  INTEGER
                        {
                        true(1),
                        false(2)
                        }
                ACCESS  read-write
                STATUS  mandatory
                DESCRIPTION
                        "Setting the object to true enables virtual MAC address
        							  translation on a residential bridge or C-VLAN cross-connect or 
         							  SC-VLAN cross-connect mode VLAN.
ALCATEL NOTE:
ACCESS:     NA       USAGE:      OPT
 	PERSIST:    YES      INSRVMOD:   YES
  	RANGE:      1,2      DEFVALUE:   2[false]
 	UNITS:      NA       SPARSE:     NA
 	DESCR:      NA"
                DEFVAL { false }
                ::= { extendVlanStaticEntry 35 }

          extendVlanStaticVMacSrcAddrDownstBlock OBJECT-TYPE
                SYNTAX  INTEGER
                        {
                        true(1),
                        false(2)
                        }
                ACCESS  read-write
                STATUS  mandatory
                DESCRIPTION
                        "Setting the object to true enables the filter in LT . The 
filter will discard any Ethernet packets received from the 
          NT within the VLAN and where the MAC source address matches 
          the signature of the local virtual MAC address format.
ALCATEL NOTE:
ACCESS:     NA       USAGE:      OPT
PERSIST:    YES      INSRVMOD:   YES
   	RANGE:      1,2      DEFVALUE:   2[false]
 	UNITS:      NA       SPARSE:     NA
   	DESCR:      NA"
                DEFVAL { false }	
                ::= { extendVlanStaticEntry 36 }

        extendVlanStaticL2CPTransparencyControl  OBJECT-TYPE
              SYNTAX  INTEGER
                      {
                       enable(1),
                       disable(2)
                       }
              ACCESS  read-write
              STATUS  mandatory
              DESCRIPTION
         "Setting the object to enable means to transparently forward L2CP frames in this VLAN except PAUSE frames. Setting to disable will discard L2CP frames in this VLAN.
              ALCATEL NOTE:
                      ACCESS:     NA       USAGE:      OPT
                      PERSIST:    YES      INSRVMOD:   YES
                      RANGE:      1,2      DEFVALUE:   2[disable]
                      UNITS:      NA       SPARSE:     NA
                      DESCR:      NA"
              DEFVAL { disable }   
                ::= { extendVlanStaticEntry 37 }

   extendInterfaceIdControlDhcpv6 OBJECT-TYPE
      SYNTAX INTEGER
          {
          notAdd(1),
          addCustomerId (2),
          addPhysicalLineId (3),
          addCcsaFormat (4)
          }
      ACCESS read-write
      STATUS mandatory
      DESCRIPTION
         "This object controls what content will be included in the 
         DHCPv6 InterfaceId option (option-18). The following values 
         are currently defined:
         notAdd(1)                InterfaceId option will not be inserted 
                                  in DHCPv6 messages.
         addCustomerId(2)         The CustomerId will be inserted in
                                  InterfaceId option.  
         addPhysicalLineId(3)     A auto-generated PhysicalLineId will be
                                  included in InterfaceId option.
         addCcsaFormat(4)         A auto-generated circuit ID as per CCSA
                                  format will be included in InterfaceId
                                  option.
         ALCATEL NOTE:
             ACCESS:      NA       USAGE:      OPT
             PERSIST:     YES      INSRVMOD:   YES
             RANGE:       1,2,3,4  DEFVALUE:   1 [notAdd]
             UNITS:       NA       SPARSE:     NA
             DESCR:       NA"
      DEFVAL { notAdd }
      ::= { extendVlanStaticEntry 38 }

   extendRemoteIdControlDhcpv6 OBJECT-TYPE
      SYNTAX INTEGER
          {
          notAdd(1),
          addCustomerId(2) ,
          addPhysicalLineId(3)
          }
      ACCESS read-write
      STATUS mandatory
      DESCRIPTION
         "This object controls what content will be included in the
         DHCPv6 RemoteId option (option-37).The following values are
         currently defined:
         notAdd(1)               RemoteId option will not be included 
                                 in the DHCPv6 messages.
         addCustomerId(2)        The CustomerId will be included in 
                                 RemoteId option.
         addPhysicalLineId(3)    An auto-generated PhysicalLineId will 
                                 be included in RemoteId option.
         ALCATEL NOTE:
             ACCESS:     NA       USAGE:      OPT
             PERSIST:    YES      INSRVMOD:   YES
             RANGE:      1,2,3    DEFVALUE:   1[notAdd]
             UNITS:      NA       SPARSE:     NA
             DESCR:      NA"
      DEFVAL { notAdd }
      ::= { extendVlanStaticEntry 39 }

   extendTrustedPortControlDhcpv6 OBJECT-TYPE
	  SYNTAX	INTEGER 
          {
	      trusted (1),
	      untrusted (2)
	      }
	  ACCESS	read-write
	  STATUS	mandatory
	  DESCRIPTION
         "This object is used to configure a port as a DHCPv6 
         trusted port or untrusted port. The DHCPv6 Relay Agent 
         allows Relay-Forward messages received from a 
         client-facing trusted port to pass but discards 
         any Relay-Forward messages received from a 
         client-facing untrusted port. 
         ALCATEL NOTE:
             ACCESS:     NA       USAGE:      OPT
             PERSIST:    YES      INSRVMOD:   YES
             RANGE:      1,2      DEFVALUE:   1[untrusted]
             UNITS:      NA       SPARSE:     NA
             DESCR:      NA"
      DEFVAL { untrusted }
      ::= { extendVlanStaticEntry 40 }

extendVlanStaticNoVmacInOpt61 OBJECT-TYPE
      SYNTAX  INTEGER
         {
         true(1),
         false(2)
         }
      ACCESS  read-write
      STATUS  mandatory
      DESCRIPTION
         "Setting the object to true lets DHCP Option 61 keep the
          genuine user MAC@ even when vMAC is enabled.
          This object will be effective only to the entries 
          on which extendVlanStaticVirtualMac take effect, and 
          will work only when extendVlanStaticVirtualMac is enabled.
       ALCATEL NOTE:
            ACCESS:     NA       USAGE:      OPT
            PERSIST:    YES      INSRVMOD:   YES
            RANGE:      1,2      DEFVALUE:   2[false]
            UNITS:      NA       SPARSE:     NA
            DESCR:      NA"
      DEFVAL { false }
      ::= { extendVlanStaticEntry 41 }

   extendEnterpriseNumberDhcpv6 OBJECT-TYPE
	  SYNTAX	INTEGER (0..4294967295) 
	  ACCESS	read-write
	  STATUS	mandatory
	  DESCRIPTION
         " This parameter is used to specify the vendor's 
         registered Enterprise Number as registered with IANA. 
         ALCATEL NOTE:
             ACCESS:     NA       USAGE:      OPT
             PERSIST:    YES      INSRVMOD:   YES
             RANGE:      NA      DEFVALUE:   3561
             UNITS:      NA       SPARSE:     NA
             DESCR:      NA"
      DEFVAL { 3561 }
      ::= { extendVlanStaticEntry 55 }

   extendSecureFilterIcmpv6 OBJECT-TYPE
	  SYNTAX	INTEGER 
         {
         enable(1),
         disable(2)
         }
	  ACCESS	read-write
	  STATUS	mandatory
	  DESCRIPTION
         " This object is used to enable ICMPv6 secure filtering. 
         ALCATEL NOTE:
             ACCESS:     NA       USAGE:      OPT
             PERSIST:    YES      INSRVMOD:   YES
            RANGE:      1,2      DEFVALUE:   1[disable]
             UNITS:      NA       SPARSE:     NA
             DESCR:      NA"
      DEFVAL { disable }
      ::= { extendVlanStaticEntry 56 }

extendVlanStaticIPv4McastControl OBJECT-TYPE
      SYNTAX  INTEGER
         {
         enable(1),
         disable(2)
         }
      ACCESS  read-write
      STATUS  mandatory
      DESCRIPTION
         "Setting the object to enable means to transparently forward IPV4 multicast frames in this VLAN (multicast addresses not in the multicast tree) in both upstream and downstream directions. Setting the object to disable means to discard IPV4 multicast frames in this VLAN (multicast addresses not in the multicast tree). This setting affects only iBridge VLANs. 
          ALCATEL NOTE:
              ACCESS:     NA       USAGE:      OPT
              PERSIST:    YES      INSRVMOD:   YES
              RANGE:      1,2      DEFVALUE:   2[disable]
              UNITS:      NA       SPARSE:     NA
              DESCR:      NA"
      DEFVAL { disable }   
      ::= { extendVlanStaticEntry 49 }

extendVlanStaticIPv6McastControl OBJECT-TYPE
      SYNTAX  INTEGER
         {
         enable(1),
         disable(2)
         }
      ACCESS  read-write
      STATUS  mandatory
      DESCRIPTION
         "Setting the object to enable means to transparently forward IPV6 multicast frames in this VLAN in both upstream and downstream directions. Setting the object to disable means to discard IPV6 multicast frames in this VLAN. This setting affects only iBridge VLANs. 
          ALCATEL NOTE:
              ACCESS:     NA       USAGE:      OPT
              PERSIST:    YES      INSRVMOD:   YES
              RANGE:      1,2      DEFVALUE:   2[disable]
              UNITS:      NA       SPARSE:     NA
              DESCR:      NA"
      DEFVAL { disable }   
      ::= { extendVlanStaticEntry 50 }

extendVlanStaticMacMcastControl OBJECT-TYPE
      SYNTAX  INTEGER
         {
         enable(1),
         disable(2)
         }
      ACCESS  read-write
      STATUS  mandatory
      DESCRIPTION
         "Setting the object to enable means to transparently forward MAC multicast frames in this VLAN in both upstream and downstream directions (multicast frames that are neither IPV4, IPV6, nor L2CP but Ethernet multicast frames such as CFM). Setting the object to disable means to discard MAC multicast frames in this VLAN. This setting affects only iBridge VLANs. 
          ALCATEL NOTE:
              ACCESS:     NA       USAGE:      OPT
              PERSIST:    YES      INSRVMOD:   YES
              RANGE:      1,2      DEFVALUE:   2[disable]
              UNITS:      NA       SPARSE:     NA
              DESCR:      NA"
      DEFVAL { disable }   
      ::= { extendVlanStaticEntry 51 }

extendVlanStaticIngressQosTcProfile OBJECT-TYPE
      SYNTAX  INTEGER
      ACCESS  read-write
      STATUS  mandatory
      DESCRIPTION
         "It defines a pointer to the Ingress Qos Profile that maps pbits to TCs on a per forwarder basis. The Ingress QoS Profile exists in the QoS MIB.
          ALCATEL NOTE:
              ACCESS:     NA       USAGE:      OPT
              PERSIST:    YES      INSRVMOD:   YES
              RANGE:      1..32    DEFVALUE:   1
              UNITS:      NA       SPARSE:     NA
              DESCR:      NA"
      DEFVAL { 1 }   
      ::= { extendVlanStaticEntry 52 }

extendVlanStaticProtocolControlFlags OBJECT-TYPE
      SYNTAX  OCTET STRING (SIZE (2))
      ACCESS  read-write
      STATUS  mandatory
      DESCRIPTION
         "Protocol control bitmap that indicates whether a particular protocol has to be transparent in both upstream and downstream directions or not (if flooding of multicast or broadcast is disabled via the above flags). Rightnow RIP and NTP are supported. By default RIPV4 is enabled for forwarding. The bit map is 
<unused> <unused> <unused> <unused> <unused> <unused> <unused> <unused> <unused> <unused> <unused> <unused> <unused> <unused> <NTP> <RIP-V4> with RIP-V4 being the LSB of the octets.
          ALCATEL NOTE:
              ACCESS:     NA       USAGE:      OPT
              PERSIST:    YES      INSRVMOD:   YES
              RANGE:      0000 - FFFF      DEFVALUE:   0001
              UNITS:      NA       SPARSE:     NA
              DESCR:      NA"
      ::= { extendVlanStaticEntry 53 }

extendVlanStaticPortsNum OBJECT-TYPE
      SYNTAX  INTEGER
      ACCESS  read-only
      STATUS  mandatory
      DESCRIPTION
         "The number of ports that are attached on one specific Vlan.
          ALCATEL NOTE:
              ACCESS:     RO      USAGE:      NA
              PERSIST:    NO      INSRVMOD:  NO
              RANGE:     NA       DEFVALUE: NA  
              UNITS:      NA       SPARSE:     NA
              DESCR:      NA"                   
        ::= {extendVlanStaticEntry 54}

extendVlanUnknownUnicastControl OBJECT-TYPE
                       SYNTAX  INTEGER
                        {
                          enable (1),
                          disable(2)
                        }
                       ACCESS  read-write
                       STATUS  mandatory
                       DESCRIPTION
                          "Decide whether to flood unknown unicast to ONT or not
                       ALCATEL NOTE:
                           ACCESS:     NA      USAGE:      NA
                           PERSIST:    NO      INSRVMOD:  NO
                           RANGE:     1..2       DEFVALUE: 2(disable)  
                           UNITS:      NA       SPARSE:     NA
                           DESCR:      NA"                   
                       ::= {extendVlanStaticEntry 58}

   extendVlanIpAntispoofingEnable OBJECT-TYPE
       SYNTAX   INTEGER 
        {
        disable(1),
        enable (2)
        }
       ACCESS   read-write
       STATUS   mandatory
       DESCRIPTION
" This object is used to control if IP anti-spoofing is enable when extendVlanSecureForwardingControl is enable.
         ALCATEL NOTE:
             ACCESS:     NA       USAGE:      OPT
             PERSIST:    YES      INSRVMOD:   YES
             RANGE:      1,2      DEFVALUE:   2[enable]
             UNITS:      NA       SPARSE:     NA
             DESCR:      NA"
      DEFVAL { enable }
      ::= { extendVlanStaticEntry 59 }

	extendVlanPortTable OBJECT-TYPE
		SYNTAX	SEQUENCE OF ExtendVlanPortEntry
		ACCESS	not-accessible
		STATUS	mandatory
		DESCRIPTION
			"A table containing port configuration information as an 
			extension to the table dot1qPortVlanTable.
             ALCATEL NOTE:
                 TABLESIZE:  DEP [depends on the value of dot1dBaseNumPorts]
                 DESCR:      NA"
		::= { plimExtendVlan 5 }

	extendVlanPortEntry OBJECT-TYPE
		SYNTAX	ExtendVlanPortEntry
		ACCESS	not-accessible
		STATUS	mandatory
		DESCRIPTION
			"The extended information for a port."
		INDEX	{ dot1dBasePort }
		::= { extendVlanPortTable 1 }

	ExtendVlanPortEntry ::=
		SEQUENCE	{

				extendVlanPortDefaultPriority
					ExtendVlanSystemPriority,
				extendVlanPortMaxNumMacAddresses
					Gauge,
				extendVlanPortAcceptableFrameTypes
					INTEGER,

				extendVlanPortSelfLearnAdminStatus
					INTEGER,

				extendVlanPortIfIndex
					INTEGER,
				extendVlanPortQosProfile
					INTEGER,
				extendVlanPortPriorityRegenerationProfile
					INTEGER,

            extendVlanPortMirroringMode
               INTEGER,
            extendVlanPortMirroringVlanId
               INTEGER,
                                extendVlanPortCommittedMaxNumMacAddresses
                                        Gauge

				}

	extendVlanPortDefaultPriority OBJECT-TYPE
		SYNTAX	ExtendVlanSystemPriority
		ACCESS	read-write
		STATUS	mandatory
		DESCRIPTION
		"For the frames, received over the bridge port (e.g.ATM 
                 PVC,EFM,..)identified by the dot1dBasePort and to be sent upstream 
                 over the Ethernet interface, this object specifies the Ethernet 
                 priority tag to be set in these frames in case a (port dependent) 
                 default value is to be used.
                 This object is only applicable to UNTAGGED traffic.
             ALCATEL NOTE:
                 ACCESS:     NA       USAGE:      OPT
                 PERSIST:    YES      INSRVMOD:   YES
                 RANGE:      0..7     DEFVALUE:   0[bestEffort]
                 UNITS:      NA       SPARSE:     NA
                 DESCR:      NA"
		::= { extendVlanPortEntry 2 }

	extendVlanPortMaxNumMacAddresses OBJECT-TYPE
		SYNTAX	Gauge
		ACCESS	read-write
		STATUS	mandatory
		DESCRIPTION
         "The uncommitted maximum number of unicast MAC addresses on the
         port, i.e. the maximum for the sum of the dynamic learned and the
         static configured unicast MAC addresses.
	        ALCATEL NOTE:
                 ACCESS:     NA       USAGE:      OPT
                 PERSIST:    YES      INSRVMOD:   YES
                 RANGE:      DEP [For BCM LIM only value between 1 and 16 
                             with step 1 and value between 20 and 64 with 
                             step 4 can be set; for Infineon LT, any value 
                             from 1 to 63 can be set;for Intel LIM any  
                             value from 1 to 64 can be set; For NGLT range 
                             is from 1..128]
                  DEFVALUE:   1        UNITS:      NA       
                  SPARSE:     NA       DESCR:      NA"
		::= { extendVlanPortEntry 3 }

	extendVlanPortAcceptableFrameTypes OBJECT-TYPE
		SYNTAX	INTEGER {

				admitOnlyVlanTagged (2),
				admitOnlyVlanUntagged (3),

				admitVlanTaggedAndUntaggedMixture (5)
	            	}
		ACCESS	read-write
		STATUS	mandatory
		DESCRIPTION
			"When admitAll(1), untagged frames or Priority-Tagged 
			frames received on this port will be accepted and assigned 
         to the default VLAN for this port. VLAN-tagged and double VLAN 
         tagged frames (if supported) are accepted too.
			When this is admitOnlyVlanTagged(2) the device will discard 
             untagged frames or Priority-Tagged frames
			received on this port. VLAN-tagged are accepted.
			When this is admitOnlyVlanUntagged(3), the untagged frames or 
			Priority-Tagged frames received on this port will be accepted 
			and assigned to the default VLAN for this port. VLAN-tagged frames 
			are discarded.
			When this is admitOnlyDoubleVlanTagged(4),only frame with double VLAN 
                        tag can be accepted, other frame types will be discarded.
                        When this is admitOnlyVlanUntagged(5), both the untagged 
                        frames/Priority-Tagged frames received on this port will be 
                        accepted Double VLAN-tagged frames will be discarded.
--			This control does not affect VLAN independent BPDU
--			frames, such as GVRP and STP.  It does affect VLAN
--			dependent BPDU frames, such as GMRP.
             ALCATEL NOTE:
                 ACCESS:     NA       USAGE:      OPT
                 PERSIST:    YES      INSRVMOD:   YES
                 RANGE:      2,3,5    DEFVALUE:   3[admitOnlyVlanUntagged]
                 UNITS:      NA       SPARSE:     NA
                 DESCR:      NA"
	        DEFVAL      { admitOnlyVlanUntagged  }
	        ::= { extendVlanPortEntry 4 }

	extendVlanPortSelfLearnAdminStatus OBJECT-TYPE
		SYNTAX  INTEGER {
				up(1),
				down(2)
				}
		ACCESS  read-write
		STATUS  mandatory
		DESCRIPTION
			"This object specifies the desired administrative state of the
			self learning process of MAC addresses. The up state indicates
			that MAC addresses shall be learned, the down state indicates
			that MAC addresses shall not be learned on that port.
             ALCATEL NOTE:
                 ACCESS:     NA       USAGE:      OPT
                 PERSIST:    YES      INSRVMOD:   YES
                 RANGE:      1,2      DEFVALUE:   1[up]
                 UNITS:      NA       SPARSE:     NA
                 DESCR:      NA"
		::= { extendVlanPortEntry 6 }

	extendVlanPortIfIndex OBJECT-TYPE
		SYNTAX  INTEGER 
		ACCESS  read-only
		STATUS  mandatory
		DESCRIPTION
			"This object returns the IfIndex of a dot1dBasePort
             ALCATEL NOTE:
                 ACCESS:     NA       USAGE:      NA
                 PERSIST:    NO       INSRVMOD:   NO
                 RANGE:      NA       DEFVALUE:   NA
                 UNITS:      NA       SPARSE:     NA
                 DESCR:      NA"
		::= { extendVlanPortEntry 8 }

	extendVlanPortQosProfile OBJECT-TYPE
		SYNTAX  INTEGER
		ACCESS  read-write
		STATUS  mandatory
		DESCRIPTION
			"The QOS profile assigned to a port by QOS management. 
			A value of 0 means no QOS profile is allocated
             ALCATEL NOTE:
                 ACCESS:     NA       USAGE:      OPT
                 PERSIST:    YES      INSRVMOD:   YES
                 RANGE:      NA       DEFVALUE:   0
                 UNITS:      NA       SPARSE:     NA
                 DESCR:      NA"
		DEFVAL { 0 }
		::= { extendVlanPortEntry 9 }

	extendVlanPortPriorityRegenerationProfile OBJECT-TYPE
		SYNTAX  INTEGER
		ACCESS  read-write
		STATUS  mandatory
		DESCRIPTION
			"The Priority regeneration profile assigned to a port. The default
         value is 0, meaning no priority bit regeneration profile is
         applied on the port. DSL interfaces can use profiles 1..10.
         GPON interfaces can use profiles 1..32.
             ALCATEL NOTE:
                 ACCESS:     NA       USAGE:      OPT
                 PERSIST:    YES      INSRVMOD:   YES
                 RANGE:      NA       DEFVALUE:   0 
                 UNITS:      NA       SPARSE:     NA
                 DESCR:      NA"
		DEFVAL { 0 }
		::= { extendVlanPortEntry 10 }

   extendVlanPortMirroringMode OBJECT-TYPE 
      SYNTAX INTEGER 
      { 
         disabled (1), 
         insertNewEthernetHeader (2),
         insertVlanTagOnly (3),
         overwriteOuterVlanTag (4)
      } 
      ACCESS read-write 
      STATUS mandatory 
      DESCRIPTION 
      "Indicates the flow mirroring mode of the bridgeport. It is disabled by default. Flow mirroring can be enabled in 3 modes: In mode 2, a completely new Ethernet Header is added to the mirrored packets. The VLAN-ID and Dest MAC address are configured in the objects given below this object. In mode 3, only a new VLAN tag is inserted, which is configured in extendVlanPortMirroringVlanId. In mode 4, a the outer VLAN tag is overwitten with the mirror VLAN tag.  Only values 1 and 4 are supported on GLTs.
             ALCATEL NOTE:
                 ACCESS:     NA       USAGE:      OPT
                 PERSIST:    YES      INSRVMOD:   YES
                 RANGE:      1..4       DEFVALUE:   1
                 UNITS:      NA       SPARSE:     NA
                 DESCR:      NA "
      DEFVAL { disabled } 
      ::= { extendVlanPortEntry 13 }

   extendVlanPortMirroringVlanId OBJECT-TYPE 
      SYNTAX INTEGER (0..4093) 
      ACCESS read-write 
      STATUS mandatory 
      DESCRIPTION 
      "Indicates the VLAN ID to be inserted into  mirrored packets if bridgeport mirroring is enabled on this bridgeport. 
             ALCATEL NOTE:
                 ACCESS:     NA       USAGE:      OPT
                 PERSIST:    YES      INSRVMOD:   YES
                 RANGE:      0..4093  DEFVALUE:   0
                 UNITS:      NA       SPARSE:     NA
                 DESCR:      NA " 
      DEFVAL { 0 } 
      ::= { extendVlanPortEntry 14 }

        extendVlanPortCommittedMaxNumMacAddresses OBJECT-TYPE
                SYNTAX   Gauge
                ACCESS   read-write
                STATUS   mandatory
                DESCRIPTION
                       "The committed maximum number of unicast MAC addresses on the 
                        port, i.e. the committed maximum for the sum of the dynamic 
                        learned and the static configured unicast MAC addresses. This 
                        value should be equal to or less than the value of 
                        extendVlanPortMaxNumMacAddresses.Default value is 65535, which 
                        means it has the same value as extendVlanPortMaxNumMacAddresses.
                ALCATEL NOTE:
                        ACCESS:     NA       USAGE:      OPT
                        PERSIST:    YES      INSRVMOD:   YES
                        RANGE:      0..128,65535.[For BCM LT, only value between 1 
                                    and 16 with step 1 and value between 20 and 64 
                                    with step 4, or the default value 65535 can be 
                                    set.]    
                        DEFVALUE:   65535    UNITS:      NA       
                        SPARSE:     NA       DESCR:      NA"
                   ::= { extendVlanPortEntry 38 }

	extendMaxSupportedBrVlans OBJECT-TYPE
		SYNTAX	Gauge
		ACCESS	read-only
		STATUS	mandatory
		DESCRIPTION
			"This object identifies the maximum number of VLans that can
			be in the mode residentialBridge.
             ALCATEL NOTE:
                 ACCESS:     NA       USAGE:      NA
                 PERSIST:    NO       INSRVMOD:   NO
                 RANGE:      NA       DEFVALUE:   768
                 UNITS:      NA       SPARSE:     NA
                 DESCR:      NA"
		::= { plimExtendVlan 7}

	extendVlanCurrentVlanBridgeList OBJECT-TYPE
		SYNTAX	VlanList
		ACCESS	read-only
		STATUS	mandatory
		DESCRIPTION
			"The VLAN list currently configured with the mode residential 
			Bridge. This is the set of Vlans configured in the 
			extendVlanStaticTable for which the object 
			extendVlanStaticSystemMode has the value residentialBridge. 
			A 1 indicates an entry for this VLAN exists and is 
			configured with the residential bridge mode, a 0 indicates 
			no corresponding entry exists or it is configured in the 
			crossconnect or layer2Terminated mode. 
             ALCATEL NOTE:
                 ACCESS:     NA       USAGE:      NA
                 PERSIST:    NO       INSRVMOD:   NO
                 RANGE:      NA       DEFVALUE:   all '0'
                 UNITS:      NA       SPARSE:     NA
                 DESCR:      NA"
		::= { plimExtendVlan 8}

	extendPortVlanAssociationTable OBJECT-TYPE
		SYNTAX	SEQUENCE OF ExtendPortVlanAssociationEntry
		ACCESS	not-accessible
		STATUS	mandatory
		DESCRIPTION
			"A virtual Bridge has multiple ports and supports various VLANs. 
			It is possible to associate ports to VLANs. Each VLAN supports its 
			forwarding function between the ports associated to it. It is 
			possible to associate a single port to multiple VLANs. This table 
			is used to configure these port - VLAN associations.
             ALCATEL NOTE:
                 TABLESIZE:  DEP [max nbr of static associations/board * nbr of boards]
                 DESCR:      The max nbr of static associations/board is 576."
		::= { plimExtendVlan 12 }

	extendPortVlanAssociationEntry OBJECT-TYPE
		SYNTAX	ExtendPortVlanAssociationEntry 
		ACCESS	not-accessible
		STATUS	mandatory
		DESCRIPTION
			"A port - VLan association."
		INDEX	{ dot1dBasePort, extendPortVlanVlanIndex }
		::= { extendPortVlanAssociationTable 1 }

	ExtendPortVlanAssociationEntry ::=
		SEQUENCE	{
				extendPortVlanVlanIndex 
					VlanIndex,
				extendPortVlanRowStatus
					RowStatus,
				extendPortVlanQosProfile
					INTEGER,
				extendPortVlanUntagged
					ExtendPortVlanUntagged, 
                                extendPortVlanPbitList
					PriorityBitList,
                                extendPortVlanThisVlanScope
                                        INTEGER,
                                extendPortVlanNetworkVlan
                                        VlanIndex,
                                extendPortVlanIfIndex 
                                        INTEGER,
                                extendPortVlanQosPolicy
                                       INTEGER,
                                extendPortVlanRegeneratedPbit
                                       ExtendVlanSystemPriority,
                                extendPortVlanPriorityRegenerationProfile
                                       INTEGER,
                                extendPortVlanIngressQosTcProfile
                                       INTEGER,
                                extendPortVlanMaxNbrOfPolicy
                                       INTEGER,
                                extendPortVlanMaxNbrOfIpAddresses
                                       INTEGER,
                               extendPortVlanMaxNumMacAddresses
                                       INTEGER

				}

	extendPortVlanVlanIndex OBJECT-TYPE
		SYNTAX	VlanIndex
		ACCESS	read-write
		STATUS	mandatory
		DESCRIPTION
			"This object indicates the VLAN associated to a port.
             ALCATEL NOTE:
                 ACCESS:     NA       USAGE:      NA
                 PERSIST:    YES      INSRVMOD:   NO
                 RANGE:      NA       DEFVALUE:   NA
                 UNITS:      NA       SPARSE:     NA
                 DESCR:      NA"
		::= { extendPortVlanAssociationEntry 1 }

	extendPortVlanRowStatus OBJECT-TYPE
		SYNTAX	RowStatus
		ACCESS	read-write
		STATUS	mandatory
		DESCRIPTION
			"This object indicates the status of this entry.
             ALCATEL NOTE:
                 ACCESS:     NA       USAGE:      MAND
                 PERSIST:    YES      INSRVMOD:   YES
                 RANGE:      1,4,6    DEFVALUE:   NA
                 UNITS:      NA       SPARSE:     NA
                 DESCR:      NA"
		::= { extendPortVlanAssociationEntry 2 }

	extendPortVlanQosProfile OBJECT-TYPE
		SYNTAX  INTEGER
		ACCESS  read-write
		STATUS  mandatory
		DESCRIPTION
			"The QOS profile assigned to a port-VLAN association by QOS
			management. A value of 0 	means no QOS profile is allocated
             ALCATEL NOTE:
                 ACCESS:     NA       USAGE:      OPT
                 PERSIST:    NO       INSRVMOD:   YES
                 RANGE:      NA       DEFVALUE:   0
                 UNITS:      NA       SPARSE:     NA
                 DESCR:      NA"
		DEFVAL { 0 }
 
		::= { extendPortVlanAssociationEntry 3 }
	
	extendPortVlanUntagged OBJECT-TYPE
		SYNTAX  ExtendPortVlanUntagged
		ACCESS  read-write
		STATUS  mandatory
		DESCRIPTION
			"If 1, untagging shall be enabled,if 2, singletagging
             shall be enabled,if 3, priority tagging should be enabled 
             for the VLAN on the port (transmit direction)
             ALCATEL NOTE:
                 ACCESS:     NA       USAGE:      OPT
                 PERSIST:    YES      INSRVMOD:   YES
                 RANGE:      1,2,3    DEFVALUE:   1[untagged]
                 UNITS:      NA       SPARSE:     NA
                 DESCR:      NA"
		DEFVAL { untagged }
		::= { extendPortVlanAssociationEntry 4 }
	
        extendPortVlanPbitList OBJECT-TYPE
        	SYNTAX	PriorityBitList
        	ACCESS	read-write
        	STATUS	mandatory
        	DESCRIPTION
        		"Priority bitmap. In the case of a QoS aware VLAN,
        		a 1 set at a bit position corresponding to a certain
        		priority indicates that this priority is associated
        		with the Vlan Port.
        		For Vlan Ports of VLANs other than QoS aware, this bitmap
        		has no meaning and should be 0.
             ALCATEL NOTE:
                 ACCESS:     NA       USAGE:      OPT
                 PERSIST:    YES      INSRVMOD:   YES
                 RANGE:      NA       DEFVALUE:   0
                 UNITS:      NA       SPARSE:     NA
                 DESCR:      NA"
		DEFVAL { "0" }
		::= { extendPortVlanAssociationEntry 6 }

	extendPortVlanThisVlanScope OBJECT-TYPE
		SYNTAX	INTEGER
				{
                 network (1),
                 local (2)
				}
		ACCESS  read-write
		STATUS  mandatory
		DESCRIPTION
			"Indicating whether the VLAN is scoped as local within a bridge port 
             or as network wide.If 1(network), it means the VLAN-port forwarding 
             interface is attached to a L2 forwarder and the network VLAN has the 
             same VLAN id;if 2(local), it means the VLAN is terminated in the 
             bridge port.
             ALCATEL NOTE:
                 ACCESS:     NA       USAGE:      OPT
                 PERSIST:    YES      INSRVMOD:   YES
                 RANGE:      1,2      DEFVALUE:   1[network]
                 UNITS:      NA       SPARSE:     NA
                 DESCR:      NA"
		DEFVAL { network }
		::= { extendPortVlanAssociationEntry 7 }

	extendPortVlanNetworkVlan OBJECT-TYPE
		SYNTAX	VlanIndex
		ACCESS	read-write
		STATUS	mandatory
		DESCRIPTION
			"Only need to be configured in case of VLAN translation, otherwise it 
             will have the default value none. If configured, it should be 
             configured as a valid network VLAN ID, which means to attach the 
             VLAN-port forwarding interface to a L2 forwarder. It is allowed that 
             the object has the same VLAN ID as the subscriber VLAN --
             extendPortVlanVlanIndex
             ALCATEL NOTE:
                 ACCESS:     NA       USAGE:      NA
                 PERSIST:    YES      INSRVMOD:   NO
                 RANGE:      NA       DEFVALUE:   16777217
                 UNITS:      NA       SPARSE:     NA
                 DESCR:      Default network VLAN of a VLAN-port is 0x01000001 
                             which is interpreted as (0,4097) and means none"
         DEFVAL { 16777217 }
		::= { extendPortVlanAssociationEntry 8 }

	 extendPortVlanIfIndex OBJECT-TYPE
		SYNTAX	INTEGER
		ACCESS	read-only
		STATUS	mandatory
		DESCRIPTION
			"IfIndex of the VLAN-port forwarding interface.
             ALCATEL NOTE:
                 ACCESS:     NA       USAGE:      NA
                 PERSIST:    YES      INSRVMOD:   NO
                 RANGE:      NA       DEFVALUE:   NA
                 UNITS:      NA       SPARSE:     NA
                 DESCR:      NA"
		::= { extendPortVlanAssociationEntry 9 }

	extendPortVlanQosPolicy OBJECT-TYPE
		SYNTAX	INTEGER
				{
                 regeneratedPbit (1),
                 regenerationProfile (2)
				}
		ACCESS  read-write
		STATUS  mandatory
		DESCRIPTION
			"Indicating Qos policy on VLAN-port forwarding interface.There are two 
             options.If 1(regeneratedPbit), it means all untagged and tagged frames 
             received on the VLAN-port forwarding interface be tagged with a fixed 
             priority identified by extendPortVlanRegeneratedPbit;if 
             2(regenerationProfile), it means all tagged frames received on the 
             VLAN-port should be replaced according to Pbit regeneration profile 
             identified by object extendPortVlanPrioritytRegenerationProfile.
             Default value of Qos policy is regenerationProfile.
             ALCATEL NOTE:
                 ACCESS:     NA       USAGE:      OPT
                 PERSIST:    YES      INSRVMOD:   YES
                 RANGE:      1,2      DEFVALUE:   2[regenerationProfile]
                 UNITS:      NA       SPARSE:     NA
                 DESCR:      NA"
		DEFVAL { regenerationProfile }
		::= { extendPortVlanAssociationEntry 10 }

	extendPortVlanRegeneratedPbit OBJECT-TYPE
		SYNTAX  ExtendVlanSystemPriority
		ACCESS  read-write
		STATUS  mandatory
		DESCRIPTION
			"All traffic received on the VLAN-port should be tagged with the fixed 
             priority identified by this object.
             ALCATEL NOTE:
                 ACCESS:     NA       USAGE:      OPT
                 PERSIST:    YES      INSRVMOD:   YES
                 RANGE:      0..7     DEFVALUE:   0
                 UNITS:      NA       SPARSE:     NA
                 DESCR:      NA"
		DEFVAL { 0 }
		::= { extendPortVlanAssociationEntry 11 }

	extendPortVlanPriorityRegenerationProfile OBJECT-TYPE
		SYNTAX  INTEGER
		ACCESS  read-write
		STATUS  mandatory
		DESCRIPTION
			"The Priority regeneration profile assigned to a VLAN-port forwarding 
             interface. 
       The default value is 0, meaning no priority bit regeneration profile
       is applied on the VLAN-port forwarding interface.. 
       DSL interfaces can use profiles 1..10.
       GPON interfaces can use profiles 1..32.

             ALCATEL NOTE:
                 ACCESS:     NA       USAGE:      OPT
                 PERSIST:    YES      INSRVMOD:   YES
                 RANGE:      NA       DEFVALUE:   0 
                 UNITS:      NA       SPARSE:     NA
                 DESCR:      NA"
		DEFVAL { 0 }
		::= { extendPortVlanAssociationEntry 12 }

extendPortVlanIngressQosTcProfile OBJECT-TYPE
      SYNTAX  INTEGER
      ACCESS  read-write
      STATUS  mandatory
      DESCRIPTION
         "It defines a pointer to the Qos Profile that maps pbits to TCs on a VLAN port basis. The QoS Profile exists in the QoS MIB.
          ALCATEL NOTE:
              ACCESS:     NA       USAGE:      OPT
              PERSIST:    YES      INSRVMOD:   YES
              RANGE:               DEFVALUE:   33
              UNITS:      NA       SPARSE:     NA
              DESCR:      NA"
      DEFVAL { 33 }   
      ::= { extendPortVlanAssociationEntry 13 }

extendPortVlanMaxNbrOfPolicy OBJECT-TYPE
      SYNTAX  INTEGER
      ACCESS  read-write
      STATUS  mandatory
      DESCRIPTION
         "It defines the max number of Qos Policy numbers (ACL and CCL) on a VLAN port basis .
          ALCATEL NOTE:
              ACCESS:     NA       USAGE:      OPT
              PERSIST:    YES      INSRVMOD:   YES
              RANGE:      0..8      DEFVALUE:   0
              UNITS:      NA       SPARSE:     NA
              DESCR:      NA"
      DEFVAL { 0 }   
      ::= { extendPortVlanAssociationEntry 14 }

extendPortVlanMaxNbrOfIpAddresses OBJECT-TYPE
      SYNTAX  INTEGER
      ACCESS  read-write
      STATUS  mandatory
      DESCRIPTION
         "It defines the max number of IP address number used in IP antispoofing and/or ARP relay on a VLAN port basis .
          ALCATEL NOTE:
              ACCESS:     NA       USAGE:      OPT
              PERSIST:    YES      INSRVMOD:   YES
              RANGE:               DEFVALUE:   65535
              UNITS:      NA       SPARSE:     NA
              DESCR:      NA"
      DEFVAL { 65535 }   
      ::= { extendPortVlanAssociationEntry 15 }

extendPortVlanMaxNumMacAddresses OBJECT-TYPE
      SYNTAX  INTEGER
      ACCESS  read-write
      STATUS  mandatory
      DESCRIPTION
         "It defines the max number of Mac Address on a VLAN port basis .
          ALCATEL NOTE:
              ACCESS:     NA       USAGE:      OPT
              PERSIST:    YES      INSRVMOD:   YES
              RANGE:      0..65535      DEFVALUE:   65535(not to check max mac on VP)
              UNITS:      NA       SPARSE:     NA
              DESCR:      NA"
      DEFVAL { 65535 }   
      ::= { extendPortVlanAssociationEntry 16 }

	extendVlanNameTable OBJECT-TYPE
		SYNTAX	SEQUENCE OF ExtendVlanNameEntry
		ACCESS	not-accessible
		STATUS	mandatory
		DESCRIPTION
			"A table to translate a VLAN name into a VLANId
             ALCATEL NOTE:
             TABLESIZE:  DEP [depends on the value of dot1qVlanCurrentTable]
             DESCR:      NA"
		::= { plimExtendVlan 15 }

	extendVlanNameEntry OBJECT-TYPE
		SYNTAX	ExtendVlanNameEntry 
		ACCESS	not-accessible
		STATUS	mandatory
		DESCRIPTION
			"One VLAN name - VLAN index relationship."
		INDEX	{ extendVlanNameStaticName, extendVlanNameVlanIndex }
		::= { extendVlanNameTable 1 }

	ExtendVlanNameEntry ::=
		SEQUENCE	{
				extendVlanNameStaticName
               SnmpAdminString (SIZE (0..80)),
				extendVlanNameVlanIndex 
					VlanIndex
				}

	extendVlanNameStaticName OBJECT-TYPE
      SYNTAX   SnmpAdminString 
		ACCESS	read-only
		STATUS	mandatory
		DESCRIPTION
			"An administratively assigned string, which may be used
			to identify the VLAN.
             ALCATEL NOTE:
                 ACCESS:     NA       USAGE:      NA
                 PERSIST:    NO       INSRVMOD:   NO
                 RANGE:      NA       DEFVALUE:   NA
                 UNITS:      NA       SPARSE:     NA
                 DESCR:      NA"
		::= { extendVlanNameEntry 1 }

	extendVlanNameVlanIndex OBJECT-TYPE
		SYNTAX	VlanIndex
		ACCESS	read-only
		STATUS	mandatory
		DESCRIPTION
			"The index of the row in dot1qVlanCurrentTable for the
			VLAN constrained by this entry.
             ALCATEL NOTE:
                 ACCESS:     NA       USAGE:      NA
                 PERSIST:    NO       INSRVMOD:   NO
                 RANGE:      NA       DEFVALUE:   NA
                 UNITS:      NA       SPARSE:     NA
                 DESCR:      NA"
		::= { extendVlanNameEntry 2 }

	extendVlanCurrentVlanQosAwareList OBJECT-TYPE
		SYNTAX	VlanList
		ACCESS	read-only
		STATUS	mandatory
		DESCRIPTION
			"The list of QoS-aware C-VLANs currently configured. 
			This is the set of C-Vlans configured in the 
			extendVlanStaticTable for which the object 
			extendVlanStaticSystemMode has the value QoS aware. 
			A 1 indicates an entry for this VLAN exists and is 
			configured with the QoS aware mode, a 0 indicates 
			no corresponding entry exists or it is configured in the 
			other mode. 
             ALCATEL NOTE:
                 ACCESS:     NA       USAGE:      NA
                 PERSIST:    NO       INSRVMOD:   NO
                 RANGE:      NA       DEFVALUE:   all '0'    
                 UNITS:      NA       SPARSE:     NA
                 DESCR:      NA"
		::= { plimExtendVlan 16}

	extendVlanCurrentVlanlayer2TermList OBJECT-TYPE
		SYNTAX	VlanList
		ACCESS	read-only
		STATUS	mandatory
		DESCRIPTION
			"The VLAN list currently configured with the layer 2 termination. 
			This is the set of Vlans configured in the 
			extendVlanStaticTable for which the object 
			extendVlanStaticSystemMode has the value layer2Terminated. 
			A 1 indicates an entry for this VLAN exists and is 
			configured with the layer2Terminated mode, a 0 indicates 
			no corresponding entry exists or it is configured in the 
			residential bridge or crossconnect mode.
             ALCATEL NOTE:
                 ACCESS:     NA       USAGE:      NA
                 PERSIST:    NO       INSRVMOD:   NO
                 RANGE:      NA       DEFVALUE:   all '0'
                 UNITS:      NA       SPARSE:     NA
                 DESCR:      NA"
		::= { plimExtendVlan 22 }
		
		extendMaxSupportedLayer2TermVlans OBJECT-TYPE
		SYNTAX	Gauge
		ACCESS	read-only
		STATUS	mandatory
		DESCRIPTION
			"This object identifies the maximum number of VLans that can
			be in the mode layer2Terminated.
             ALCATEL NOTE:
                 ACCESS:     NA       USAGE:      NA
                 PERSIST:    NO       INSRVMOD:   NO
                 RANGE:      NA       DEFVALUE:   5372
                 UNITS:      NA       SPARSE:     NA
                 DESCR:      NA"
		::= { plimExtendVlan 23}

        extendUniPortTable OBJECT-TYPE
                SYNTAX        SEQUENCE OF ExtendUniPortEntry
                ACCESS        not-accessible
                STATUS        mandatory
                DESCRIPTION
                    "A table that contains all the UNIs that are configured to support bridging functionality. The IfIndex is that of the UNI.
             ALCATEL NOTE:
                        TABLESIZE:  DEP [depends on the value of dot1dBaseNumPorts] 
                        DESCR:      NA"
                ::= { plimExtendVlan 25 }

        extendUniPortEntry OBJECT-TYPE
                SYNTAX        ExtendUniPortEntry 
                ACCESS        not-accessible
                STATUS        mandatory
                DESCRIPTION
                        "An entry in the UniPortTable representing one UNI."
                INDEX        { ifIndex }
                ::= { extendUniPortTable 1 }

        ExtendUniPortEntry ::=
                SEQUENCE        {
                    extendUniPortDot1dBasePort
                        INTEGER,
                    extendUniPortRowStatus
                        RowStatus,
                    extendUniPortIfIndex
                        INTEGER

                }

        extendUniPortDot1dBasePort OBJECT-TYPE
                SYNTAX        INTEGER (1..2147483647)
                ACCESS        read-only
                STATUS        mandatory
                DESCRIPTION
               "The port identifier assigned by the system to this UNI.
                    A port identifier identifies uniquely a port of the VLAN-Bridge
                    within the system.
                 ALCATEL NOTE:
                        ACCESS:     RO       USAGE:      NA
                        PERSIST:    YES      INSRVMOD:   NO
                        RANGE:      NA       DEFVALUE:   NA
                        UNITS:      NA       SPARSE:     NA
                        DESCR:      NA"
                ::= { extendUniPortEntry 1 }

        extendUniPortRowStatus OBJECT-TYPE
                SYNTAX        RowStatus
                ACCESS        read-write
                STATUS        mandatory
                DESCRIPTION
"This object indicates the status of this entry.
                 ALCATEL NOTE:
                        ACCESS:     NA       USAGE:      MAND
                        PERSIST:    NO       INSRVMOD:   NO
                        RANGE:      1,4,6    DEFVALUE:   NA
                        UNITS:      NA       SPARSE:     NA
                        DESCR:      NA"
                ::= { extendUniPortEntry 2 }

         extendUniPortIfIndex OBJECT-TYPE
                SYNTAX        INTEGER
                ACCESS        read-only
                STATUS        mandatory
                DESCRIPTION
                    "IfIndex of the dot1dBasePort
                 ALCATEL NOTE:
                        ACCESS:     RO       USAGE:      NA
                        PERSIST:    YES      INSRVMOD:   NO
                        RANGE:      NA       DEFVALUE:   NA
                        UNITS:      NA       SPARSE:     NA
                        DESCR:      NA"
                ::= { extendUniPortEntry 3 }

	extendL2ForwarderContainerTable  OBJECT-TYPE
		SYNTAX	SEQUENCE OF ExtendL2ForwarderContainerEntry
		ACCESS	not-accessible
		STATUS	mandatory
		DESCRIPTION
			" This table is a search table for L2 forwarder interfaces, per FdbId. It contains the same entries as the extendPortVlanAssociationTable, but without attributes and ordered according to the FdbId. .
             ALCATEL NOTE:
                 TABLESIZE:  DEP [depends on the tablesize of
                             extendPortVlanAssociationTable]
                 DESCR:     The L2 forwarder interface is subscriber VLAN.port in this table"

		::= { plimExtendVlan 27 }

	extendL2ForwarderContainerEntry  OBJECT-TYPE
		SYNTAX	ExtendL2ForwarderContainerEntry
		ACCESS	not-accessible
		STATUS	mandatory
		DESCRIPTION
			"A L2 forwarder interface and a L2 forwarder association."
		INDEX	{ dot1qVlanIndex, extendL2ForwarderContainerInterfaceIndex  }
		::= { extendL2ForwarderContainerTable 1 }

	ExtendL2ForwarderContainerEntry ::=
		SEQUENCE	{
			extendL2ForwarderContainerInterfaceIndex
				INTEGER
			}

	extendL2ForwarderContainerInterfaceIndex OBJECT-TYPE
		SYNTAX	INTEGER
		ACCESS	read-only
		STATUS	mandatory
		DESCRIPTION
			"The ifIndex of a L2 forwarder interface.
             ALCATEL NOTE:
                 ACCESS:     NA       USAGE:      NA
                 PERSIST:    NO       INSRVMOD:   NO
                 RANGE:      NA       DEFVALUE:   NA
                 UNITS:      NA       SPARSE:     NA
                 DESCR:      identify a subscriber vlan.port"
		::= { extendL2ForwarderContainerEntry 1 }

plimExtendStatic	OBJECT IDENTIFIER ::= {plimEthernet 3}

	extendStaticUnicastTable OBJECT-TYPE
		SYNTAX	SEQUENCE OF ExtendStaticUnicastEntry
		ACCESS	not-accessible
		STATUS	mandatory
		DESCRIPTION
			"This table is a proprietary variant on the table 
			dot1qStaticUnicast Table defined in the Q-BRIDGE-MIB.
			It is a table containing filtering information for Unicast
			MAC addresses for each Filtering Database, configured
			into the device by (local or network) management
			specifying the set of ports to which frames received
			from specific ports and containing specific unicast
			destination addresses are allowed to be forwarded. A
			value of zero in this table as the port number from
			which frames with a specific destination address are
			received, is used to specify all ports for which there
			is no specific entry in this table for that particular
			destination address.  Entries are valid for unicast
			addresses only.
			Note: in NBE, only the Local User VLAN can be used as
			index of this table. 
             ALCATEL NOTE:
                 TABLESIZE:  DEP [nbr of unicast addresses/board * nbr of 
                                 boards] "
		::= { plimExtendStatic 1 }

	extendStaticUnicastEntry OBJECT-TYPE
		SYNTAX	ExtendStaticUnicastEntry 
		ACCESS	not-accessible
		STATUS	mandatory
		DESCRIPTION
			"An entry in the table extendStaticUnicastTable. One entry 
			exists in this table for each Unicast MAC address statically 
			configured within a Vlan.
			Filtering information configured into the device by
			(local or network) management specifying the port to 
			which frames received from the Ethernet port and
			containing a specific unicast destination address is
			forwarded."
		INDEX	{ dot1qFdbId, extendStaticUnicastAddress}
		::= { extendStaticUnicastTable 1 }

	ExtendStaticUnicastEntry ::=
		SEQUENCE	{ 
				extendStaticUnicastAddress
					MacAddress,
				extendStaticUnicastAllowedToGoTo
					INTEGER,
				extendStaticUnicastStatus
					INTEGER
				}

	extendStaticUnicastAddress OBJECT-TYPE
		SYNTAX	MacAddress
		ACCESS	not-accessible
		STATUS	mandatory
		DESCRIPTION
			"The destination MAC address in a frame to which this
			entry's filtering information applies. This object must
			take the value of a unicast address.
             ALCATEL NOTE:
                 ACCESS:     NA       USAGE:      NA
                 PERSIST:    YES      INSRVMOD:   NO
                 RANGE:      NA       DEFVALUE:   NA
                 UNITS:      NA       SPARSE:     NA
                 DESCR:      NA"
		::= { extendStaticUnicastEntry 1 }

	extendStaticUnicastAllowedToGoTo	OBJECT-TYPE
		SYNTAX	INTEGER (0..2147483647)
		ACCESS	read-write
		STATUS	mandatory
		DESCRIPTION
			"This object identifies the port number of the ATM PVC port on 
			which a frame received over the Ethernet interface will be sent. 
			It also specifies the port a specific unicast address 
			may be dynamically learnt on. 

			This approach reflects the inability of the system to flood 
			frames to various ports. It therefore is equivalent to the 
			object dot1qStaticUnicastAllowedToGoTo but with the 
			difference it is 1 port in stead of a list.
             ALCATEL NOTE:
                 ACCESS:     NA       USAGE:      MAND
                 PERSIST:    YES      INSRVMOD:   NO
                 RANGE:      NA       DEFVALUE:   NA
                 UNITS:      NA       SPARSE:     NA
                 DESCR:      NA"
		::= { extendStaticUnicastEntry 2}

	extendStaticUnicastStatus OBJECT-TYPE
		SYNTAX	INTEGER {
					other(1),
					invalid(2),
					permanent(3),
					deleteOnReset(4),
					deleteOnTimeout(5)
					}
		ACCESS	read-write
		STATUS	mandatory
		DESCRIPTION
			"This object indicates the status of this entry.
			other(1) - this entry is currently in use but
				the conditions under which it will remain
				so differ from the following values.
			invalid(2) - writing this value to the object
				removes the corresponding entry.
			permanent(3) - this entry is currently in use
				and will remain so after the next reset of
				the bridge.
			deleteOnReset(4) - this entry is currently in
				use and will remain so until the next
				reset of the bridge.
			deleteOnTimeout(5) - this entry is currently in
				use and will remain so until it is aged out.
             ALCATEL NOTE:
                 ACCESS:     NA       USAGE:      MAND
                 PERSIST:    NO       INSRVMOD:   YES
                 RANGE:      NA       DEFVALUE:   permanent
                 UNITS:      NA       SPARSE:     NA
                 DESCR:      NA"
		DEFVAL	{ permanent }
		::= { extendStaticUnicastEntry 3 }

	extendDupMacAlarmTable OBJECT-TYPE
		SYNTAX	SEQUENCE OF ExtendDupMacAlarmEntry 
		ACCESS	not-accessible
		STATUS	mandatory
		DESCRIPTION
	                "A table containing the information for every dupplicate MAC 
                    alarm generated by the system. The entry exists as long as the 
                    alarm is on.the entry is removed when the alarm is off.
                    ALCATEL NOTE:
                    TABLESIZE:  DEP [depends on (max unicast MAC number per LIM)*(num LIM of system)]
                    DESCR:      NA"
		::= { plimExtendStatic 4 }

	extendDupMacAlarmEntry OBJECT-TYPE
		SYNTAX	ExtendDupMacAlarmEntry 
		ACCESS	not-accessible
		STATUS	mandatory
		DESCRIPTION
			"An entry in the table extendDupMacAlarmTable. One entry represents 
			an alarm that is on."
		INDEX   { extendDupMacPortAlarm,
				 extendDupMacFdbId,
				 extendDupMacMacAddress }
		::= { extendDupMacAlarmTable 1 }

	ExtendDupMacAlarmEntry ::=
		SEQUENCE {
			extendDupMacPortAlarm
				INTEGER (1..2147483647),
			extendDupMacFdbId
				Gauge,
			extendDupMacMacAddress
				MacAddress,
			extendDupMacPortAssigned
                            INTEGER (1..2147483647) ,
			extendDupMacSubscriberVlanAlarm
			    VlanIndex,
			extendDupMacSubscriberVlanAssigned
			    VlanIndex
				}

	extendDupMacPortAlarm	OBJECT-TYPE
		SYNTAX	INTEGER (1..2147483647)
		ACCESS	read-only
		STATUS	mandatory
		DESCRIPTION
			"The port identifier of the port on which the self learning of a 
			MAC-address is rejected.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 1 }

	extendDupMacFdbId	OBJECT-TYPE
		SYNTAX	Gauge
		ACCESS	read-only
		STATUS	mandatory
		DESCRIPTION
			"The Filtering Database within which the self learning of a 
			MAC-address is rejected.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 2 }

	extendDupMacMacAddress	OBJECT-TYPE
		SYNTAX	MacAddress
		ACCESS	read-only
		STATUS	mandatory
		DESCRIPTION
			"The MAC address that could not be learned on the port identified 
			with extendDupMacPortAlarm within the FDB identified by the object 
			extendDupMacFdbId.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 3 }

	extendDupMacPortAssigned	OBJECT-TYPE
		SYNTAX	INTEGER (1..2147483647)
		ACCESS	read-only
		STATUS	mandatory
		DESCRIPTION
			"The port identifier of the port on which the MAC address identified
			by the object extendDupMacMacAddress is already learned or 
			statically configured within the FDB identified by the object
			extendDupMacFdbId. Because MAC addresses shall be unique per FDB 
			this gives also the reason why the MAc address could not be learned 
			on the port identified by the object extendDupMacPortAlarm.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 4 }

	extendDupMacSubscriberVlanAlarm 	OBJECT-TYPE
		SYNTAX	VlanIndex
		ACCESS	read-only
		STATUS	mandatory
		DESCRIPTION
			" The subscriber vlan which, together with the extendDupMacPortAlarm, identifies the vlan port on which the self learning of a MAC-address is rejected due to MAC-address duplicating with a learned or a static MAC-address in the same forwarder.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 5 }

  	extendDupMacSubscriberVlanAssigned	OBJECT-TYPE
		SYNTAX	VlanIndex
		ACCESS	read-only
		STATUS	mandatory
		DESCRIPTION
			" The subscriber vlan which, together with the extendDupMacPortAssigned,identifies the vlan port on which the MAC address identified by the object extendDupMacMacAddress is  already learned or statically configured within the FDB identified by the object extendDupMacFdbId.
             ALCATEL NOTE:
                 ACCESS:     NA       USAGE:      NA
                 PERSIST:    NO       INSRVMOD:   NO
                 RANGE:      NA       DEFVALUE:   NA
                 UNITS:      NA       SPARSE:     NA
                 DESCR:      NA"
		::= { extendDupMacAlarmEntry 6 }

	extendUserPortStaticUnicastTable OBJECT-TYPE
		SYNTAX	SEQUENCE OF ExtendUserPortStaticUnicastEntry
		ACCESS	not-accessible
		STATUS	mandatory
		DESCRIPTION
			"This table is a proprietary variant on the table
			dot1qStaticUnicast Table defined in the Q-BRIDGE-MIB.
			It is a table containing filtering information for Unicast
			MAC addresses for each subscriber forwarder interfaces, 					configured into the device by (local or network) management.
			 ALCATEL NOTE:
                 TABLESIZE:  DEP [nbr of unicast addresses/board * nbr of
                                 boards]
                 DESCR:      Subscriber forwarder interface refers to subscriber VLAN.Port in this table."

		::= { plimExtendStatic 7 }

	extendUserPortStaticUnicastEntry OBJECT-TYPE
		SYNTAX	ExtendUserPortStaticUnicastEntry
		ACCESS	not-accessible
		STATUS	mandatory
		DESCRIPTION
			" An entry in extenUserPortStaticUnicastTable identifies one
             Unicast MAC address statically configured on a subscriber
             forwarder interface."
		INDEX	{ ifIndex, extendUserPortStaticUnicastAddress }
		::= { extendUserPortStaticUnicastTable 1 }

	ExtendUserPortStaticUnicastEntry ::=
		SEQUENCE	{
				extendUserPortStaticUnicastAddress
					MacAddress,
				extendUserPortStaticUnicastStatus
					INTEGER,
				extendUserPortStaticUnicastFdbId
					Gauge
				}

	extendUserPortStaticUnicastAddress OBJECT-TYPE
		SYNTAX	MacAddress
		ACCESS	not-accessible
		STATUS	mandatory
		DESCRIPTION
			"The source MAC address in a frame from a subscriber forwarder
            interface. This object must take the value of a unicast address.
             ALCATEL NOTE:
                 ACCESS:     NA       USAGE:      NA
                 PERSIST:    YES      INSRVMOD:   NO
                 RANGE:      NA       DEFVALUE:   NA
                 UNITS:      NA       SPARSE:     NA
                 DESCR:      the forwarder interface refers to a vlan.port"
		::= { extendUserPortStaticUnicastEntry 1 }

	extendUserPortStaticUnicastStatus OBJECT-TYPE
		SYNTAX	INTEGER {
					other(1),
					invalid(2),
					permanent(3),
					deleteOnReset(4),
					deleteOnTimeout(5)
					}
		ACCESS	read-write
		STATUS	mandatory
		DESCRIPTION
			"This object indicates the status of this entry.
			other(1) - this entry is currently in use but
				the conditions under which it will remain
				so differ from the following values.
			invalid(2) - writing this value to the object
				removes the corresponding entry.
			permanent(3) - this entry is currently in use
				and will remain so after the next reset of
				the bridge.
			deleteOnReset(4) - this entry is currently in
				use and will remain so until the next
				reset of the bridge.
			deleteOnTimeout(5) - this entry is currently in
				use and will remain so until it is aged out.
             ALCATEL NOTE:
                 ACCESS:     NA       USAGE:      NA
                 PERSIST:    NO       INSRVMOD:   YES
                 RANGE: invalid(2),permanent(3)   DEFVALUE:   permanent
                 UNITS:      NA       SPARSE:     NA
                 DESCR:      NA"
		DEFVAL	{ permanent }
		::= { extendUserPortStaticUnicastEntry 2 }

	extendUserPortStaticUnicastFdbId	OBJECT-TYPE
		SYNTAX	Gauge
		ACCESS	read-only
		STATUS	mandatory
		DESCRIPTION
			"Identifies a L2 forwarder to which the forwarder interface attaches .

             ALCATEL NOTE:
                 ACCESS:     NA       USAGE:      NA
                 PERSIST:    NO       INSRVMOD:   NO
                 RANGE:      NA       DEFVALUE:   NA
                 UNITS:      NA       SPARSE:     NA
                 DESCR:      forwarder interface refers to a vlan.port"
		::= { extendUserPortStaticUnicastEntry 3 }

plimPriorityMapping	OBJECT IDENTIFIER ::= {plimEthernet 4}

	priorityMappingSwitch OBJECT-TYPE
		SYNTAX	INTEGER {
					vlanId(1),
					atmServiceCategory(2),
					portDefault(3)
						}
		ACCESS	read-write
		STATUS	mandatory
		DESCRIPTION
			"Object indicating the Ethernet priority tag of the upstream frames
			is mapping from the VLAN Id, or ATM Service Category or port default
			priority.
             ALCATEL NOTE:
                 ACCESS:     NA       USAGE:      NA
                 PERSIST:    YES      INSRVMOD:   YES
                 RANGE:      1,2,3    DEFVALUE:   3[portDefault]
                 UNITS:      NA       SPARSE:     NA
                 DESCR:      NA"
		::= { plimPriorityMapping 3 }

	plimL2PriorityRegenerationProfileTable OBJECT-TYPE
		SYNTAX	SEQUENCE OF PlimL2PriorityRegenerationProfileEntry
		ACCESS	not-accessible
		STATUS	mandatory
		DESCRIPTION
			"Priotity bit regeneration profile table (a profile includes both 
			upstream and downstream p bit translation). The first 10 profiles
			are fixed and are not allowed to be modified. First 10 profiles
   can be used on either DSL or GPON interfaces. Last 22 profiles can
   only be used on GPON interfaces.
             ALCATEL NOTE:
                 TABLESIZE:  32
                 DESCR:      "
		::= { plimPriorityMapping 4 }

	plimL2PriorityRegenerationProfileEntry	OBJECT-TYPE
		SYNTAX	PlimL2PriorityRegenerationProfileEntry
		ACCESS	not-accessible
		STATUS	mandatory
		DESCRIPTION
			"One upstream + downstream priority regeneration profile"
		INDEX	{ plimL2PriorityRegenerationProfileId }
		::= { plimL2PriorityRegenerationProfileTable 1 }

	PlimL2PriorityRegenerationProfileEntry	::=
   SEQUENCE	{
      plimL2PriorityRegenerationProfileId   INTEGER,	
      plimL2PriorityRegenerationProfileName SnmpAdminString (SIZE (0..32)),
      plimL2PriorityRegenerationTableUp     INTEGER, 
      plimL2PriorityRegenerationTableDown   INTEGER,
      plimL2PriorityRegenerationRowstatus   RowStatus,  	
      plimL2PriorityRegenerationRefCount    AsamProfileRefCount    
				}

	plimL2PriorityRegenerationProfileId	 OBJECT-TYPE
		SYNTAX	INTEGER
		ACCESS	read-write
		STATUS	mandatory
		DESCRIPTION
			"This is the index of the regeneration profile
             ALCATEL NOTE:
                 ACCESS:     RW       USAGE:      NA
                 PERSIST:    YES      INSRVMOD:   NO
                 RANGE:      NA       DEFVALUE:   NA
                 UNITS:      NA       SPARSE:     NA
                 DESCR:      NA"
		::= { plimL2PriorityRegenerationProfileEntry 1 }

	plimL2PriorityRegenerationProfileName	 OBJECT-TYPE
		SYNTAX	SnmpAdminString 
		ACCESS	read-write
		STATUS	mandatory
		DESCRIPTION
			"This is the name of the regeneration profile
             ALCATEL NOTE:
                 ACCESS:     RW       USAGE:      NA
                 PERSIST:    YES      INSRVMOD:   NO
                 RANGE:      NA       DEFVALUE:   NA
                 UNITS:      NA       SPARSE:     NA
                 DESCR:      NA"
		::= { plimL2PriorityRegenerationProfileEntry 2 }

	plimL2PriorityRegenerationTableUp OBJECT-TYPE
		SYNTAX  INTEGER (0..4294967295)
		ACCESS  read-write
		STATUS  mandatory
		DESCRIPTION
			"The following mapping applies in upstream direction :
       p-bit codepoint 0 corresponds to bit 0-3, codepoint 1 to bit 4-7,
			The mapping goes from 3 bit to 4 bit for implementation convenience.
			As a consequence, The most significant bit of the new p-bit value is
			not used
			Graphical representation of where to find the regenerated priority in 
			the integer of a received .1p priority codepoint :
			Bit31-28 bit27-24 bit23-20 bit19-16 bit15-bit12 bit11-8 bit7-4 bit3-0 
			   CP7      CP6      CP5      CP4      CP3       CP2     CP1     CP0
             ALCATEL NOTE:
                 ACCESS:     RW       USAGE:      NA
                 PERSIST:    YES      INSRVMOD:   NO
                 RANGE:      NA       DEFVALUE:   NA
                 UNITS:      NA       SPARSE:     NA
                 DESCR:      NA"
		::= { plimL2PriorityRegenerationProfileEntry 3 }
	
	plimL2PriorityRegenerationTableDown OBJECT-TYPE
		SYNTAX  INTEGER (0..4294967295)
		ACCESS  read-write
		STATUS  mandatory
		DESCRIPTION
			"The following mapping applies in downstream direction :
			p-bit codepoint 0 corresponds to bit 0-3, codepoint 1 to bit 4-7
			The mapping goes from 3 bit to 4 bit for implementation convenience.
			As a consequence, The most significant bit of the new p-bit value is
			not used
             ALCATEL NOTE:
                 ACCESS:     RW       USAGE:      NA
                 PERSIST:    YES      INSRVMOD:   NO
                 RANGE:      NA       DEFVALUE:   NA
                 UNITS:      NA       SPARSE:     NA
                 DESCR:      NA"
		::= { plimL2PriorityRegenerationProfileEntry 4 }

	 plimL2PriorityRegenerationRowstatus	OBJECT-TYPE
 	   	SYNTAX      	RowStatus
  		ACCESS  		read-write
  	  	STATUS      	mandatory
   		DESCRIPTION
   		"This object indicates the status of this entry.
         ALCATEL NOTE:
             ACCESS:     RW       USAGE:      NA
             PERSIST:    YES      INSRVMOD:   NO
             RANGE:      1,4,6    DEFVALUE:   NA
             UNITS:      NA       SPARSE:     NA
             DESCR:      NA"
  	  	::= { plimL2PriorityRegenerationProfileEntry 5  }

  plimL2PriorityRegenerationRefCount   OBJECT-TYPE
   SYNTAX         AsamProfileRefCount
   ACCESS         read-only
   STATUS         mandatory
   DESCRIPTION
   "This object indicates the number of entries using this
   profile. If the count is not zero, the profile is in use and
   cannot be deleted. If the count is zero, the profile is not
   in use and can be deleted
   ALCATEL NOTE:
        ACCESS:     RO       USAGE:      NA
        PERSIST:    NO       INSRVMOD:   NO
        RANGE:      NA       DEFVALUE:   0
        UNITS:      NA       SPARSE:     NA
        DESCR:      NA"
   ::= { plimL2PriorityRegenerationProfileEntry 6  }

  plimPriorityRegenerationProfileGetNextFree OBJECT-TYPE
	  SYNTAX INTEGER
	  ACCESS read-only
	  STATUS mandatory
	  DESCRIPTION
   "This object contains an appropriate value to be used
   for PlimL2PriorityRegenerationProfileEntry when creating
   entries in the plimL2PriorityRegenerationProfileTable.
   The value 0 indicates that no unassigned entries are available"
  ::= { plimPriorityMapping 5 }

extendForwardingInfo	OBJECT IDENTIFIER ::= {plimEthernet 5}

	extendUserPortFdbTable OBJECT-TYPE
		SYNTAX	SEQUENCE OF ExtendUserPortFdbEntry
		ACCESS	not-accessible
		STATUS	mandatory
		DESCRIPTION
			"A table that contains unicast MAC address, static and dynamic,
			per user forwarder interface, which could be translated to a vMAC 				address to network.
			And it also allows to remove  MAC addresses, which were obtained
			through the self learning mechanism, from the forwarding database
			on a specified port.
			Note that this table can not be used to delete a static MAc address.             			ALCATEL NOTE:
                 TABLESIZE:  DEP [nbr of unicast addresses/board * nbr of
                                 boards]"
		::= { extendForwardingInfo 10 }

	extendUserPortFdbEntry OBJECT-TYPE
		SYNTAX	ExtendUserPortFdbEntry
		ACCESS	not-accessible
		STATUS	mandatory
		DESCRIPTION
			"An entry of extendUserPortFdbTable, learned or configured on a user forwarder port."
		INDEX	{ ifIndex, extendUserPortFdbUserAddress }
		::= { extendUserPortFdbTable 1 }

	 ExtendUserPortFdbEntry ::=
      SEQUENCE {
         extendUserPortFdbUserAddress
            MacAddress,
         extendUserPortFdbId
            Gauge,
         extendUserPortFdbStatus
            INTEGER,
         extendUserPortFdbvMacAddress
            MacAddress,
         extendUserPortFdbRowStatus
            RowStatus
      }

	  extendUserPortFdbUserAddress OBJECT-TYPE
		SYNTAX	MacAddress
		ACCESS	read-only
		STATUS	mandatory
		DESCRIPTION
			"The source MAC address contained in the frame coming from a user forwarder interface.
             ALCATEL NOTE:
                 ACCESS:     NA       USAGE:      NA
                 PERSIST:    NO       INSRVMOD:   NA
                 RANGE:      NA       DEFVALUE:   NA
                 UNITS:      NA       SPARSE:     NA
                 DESCR:      the user forwarder interface identifies a vlan.port"
		::= { extendUserPortFdbEntry 1 }

   	extendUserPortFdbId OBJECT-TYPE
		SYNTAX	Gauge
		ACCESS	read-only
		STATUS	mandatory
		DESCRIPTION
			"Identifies a L2 forwarder which the user forwarder interface attaches to.
	             ALCATEL NOTE:
                 ACCESS:     NA       USAGE:      NA
                 PERSIST:    NO       INSRVMOD:   NO
                 RANGE:      NA       DEFVALUE:   NA
                 UNITS:      NA       SPARSE:     NA
                 DESCR:      NA"
		::= { extendUserPortFdbEntry 2 }

    extendUserPortFdbStatus OBJECT-TYPE
      SYNTAX	INTEGER {
         other(1),
         invalid(2),
         learned(3),
         self(4),
         mgmt(5)
      }
      ACCESS	read-only
      STATUS	mandatory
      DESCRIPTION
         "The status of this entry.  The meanings of the values are:
         other(1) - none of the following.  This may include	the case where
            some other MIB object is being used to determine if and how
            frames addressed to the value of the corresponding instance of
            extendUserPortFdbUserAddress are being forwarded.
         invalid(2) - this entry is no longer valid (e.g., it was learned
            but has aged out), but has not yet been flushed from the
            table.
         learned(3) - the value of the corresponding instance of
            extendUserPortFdbUserAddress was learned and is being used.
         self(4) - the value of the corresponding instance of
            extendUserPortFdbUserAddress represents one of the device's
            addresses.
         mgmt(5) - the value of the corresponding instance of
            extendUserPortFdbUserAddress is configured manually.
         ALCATEL NOTE:
         ACCESS:     NA       USAGE:      NA
         PERSIST:    NA       INSRVMOD:   NA
         RANGE:      3,5    DEFVALUE:   NA
         UNITS:      NA       SPARSE:     NA
         DESCR:      NA"
      ::= { extendUserPortFdbEntry 3 }

	extendUserPortFdbvMacAddress OBJECT-TYPE
		SYNTAX  MacAddress
		ACCESS  read-only
		STATUS  mandatory
		DESCRIPTION
		"A unicast virtual MAC address to which the extendUserPortFdbUserAddress was translated and the device has forwarding and/or filtering information.
		             ALCATEL NOTE:
		                 ACCESS:     NA       USAGE:      NA
		                 PERSIST:    NO       INSRVMOD:   NO
		                 RANGE:      NA       DEFVALUE:   NA
		                 UNITS:      NA       SPARSE:     NA
		                 DESCR:      NA"
	::= { extendUserPortFdbEntry 4 }

      extendUserPortFdbRowStatus OBJECT-TYPE
		SYNTAX	RowStatus
		ACCESS	read-write
		STATUS	mandatory
		DESCRIPTION
			"The row status of the entry.
             ALCATEL NOTE:
                 ACCESS:     NA       USAGE:      NA
                 PERSIST:    NO       INSRVMOD:   YES
                 RANGE: active(1),destroy(6)  DEFVALUE:   active(1)
                 UNITS:      NA       SPARSE:     NA
                 DESCR:      NA"
        DEFVAL	{ active }
		::= { extendUserPortFdbEntry 5 }

   extendBoardForwarderFdbTable OBJECT-TYPE
      SYNTAX	SEQUENCE OF ExtendBoardForwarderFdbEntry
		ACCESS	not-accessible
		STATUS	mandatory
		DESCRIPTION
			"A table that contains information about unicast
         MAC address per LIM for which the device has forwarding and/or filtering
			information.  This information is used by the
			transparent bridging function in determining how to
			propagate a received frame.
			Both dynamic and static MAC addresses are covered in this table.

             ALCATEL NOTE:
                 TABLESIZE:  DEP [depends on the tablesize of
		extendUserPortFdbTable]
DESCR:      NA"

         ::= { extendForwardingInfo 12 } 

   extendBoardForwarderFdbEntry OBJECT-TYPE
      SYNTAX	ExtendBoardForwarderFdbEntry 
		ACCESS	not-accessible
		STATUS	mandatory
		DESCRIPTION
			"Information about a specific MAC address for
			which the device has some forwarding and/or filtering
			information."
      INDEX  { eqptSlotId, dot1qFdbId, extendBoardForwarderFdbNetAddress }
         ::= { extendBoardForwarderFdbTable 1 }	

   ExtendBoardForwarderFdbEntry ::=
      SEQUENCE {
         extendBoardForwarderFdbNetAddress
            MacAddress,
         extendBoardForwarderFdbIntf
            INTEGER,   
         extendBoardForwarderFdbStatus
            INTEGER,
         extendBoardForwarderFdbUserAddress
            MacAddress
         }

   extendBoardForwarderFdbNetAddress OBJECT-TYPE
		SYNTAX	MacAddress
		ACCESS	read-only
		STATUS	mandatory
		DESCRIPTION
			"The MAC address at network side. When vMAC is enabled, it identifies a vMAC address.

             ALCATEL NOTE:
                 ACCESS:     NA       USAGE:      NA
                 PERSIST:    NO       INSRVMOD:   YES
                 RANGE:      NA       DEFVALUE:   NA
                 UNITS:      NA       SPARSE:     NA
                 DESCR:      NA"
          ::= { extendBoardForwarderFdbEntry 1 }   

   extendBoardForwarderFdbIntf OBJECT-TYPE
		SYNTAX	INTEGER
		ACCESS	read-only
		STATUS	mandatory
		DESCRIPTION
			"The ifIndex of a forwarder interface where the MAC@ will be forwarded to.
             ALCATEL NOTE:
                 ACCESS:     NA       USAGE:      NA
                 PERSIST:    NO       INSRVMOD:   YES
                 RANGE:      NA       DEFVALUE:   NA
                 UNITS:      NA       SPARSE:     NA
                 DESCR:      the forwarder interface identifies a vlan.port"
         ::= { extendBoardForwarderFdbEntry 2 }

    extendBoardForwarderFdbStatus OBJECT-TYPE
      SYNTAX	INTEGER {
         other(1),
         invalid(2),
         learned(3),
         self(4),
         mgmt(5)
      }
      ACCESS	read-only
      STATUS	mandatory
      DESCRIPTION
         "The status of this entry.  The meanings of the values are:
         other(1) - none of the following.  This may include	the case where
            some other MIB object is being used to determine if and how
            frames addressed to the value of the corresponding instance of
            extendBoardForwarderFdbNetAddress are being forwarded.
         invalid(2) - this entry is no longer valid (e.g. it was learned
            but has since aged out), but has not yet been flushed from the
            table.
         learned(3) - the value of the corresponding instance of
            extendBoardForwarderFdbNetAddress was learned and is being used.
         self(4) - the value of the corresponding instance of
            extendBoardForwarderFdbNetAddress represents one of the device's
            addresses.
         mgmt(5) - the value of the corresponding instance of
            extendBoardForwarderFdbNetAddress is manually configured.
         ALCATEL NOTE:
         ACCESS:     NA       USAGE:      NA
         PERSIST:    NA       INSRVMOD:   NA
         RANGE:      3,5       DEFVALUE:   NA
         UNITS:      NA       SPARSE:     NA
         DESCR:      NA"
      ::= { extendBoardForwarderFdbEntry 3 }

   extendBoardForwarderFdbUserAddress OBJECT-TYPE
		SYNTAX  MacAddress
		ACCESS  read-only
		STATUS  mandatory
		DESCRIPTION
         "the user MAC address, which the extendBoardForwarderFdbNetAddress 
         is translated from when vMAC is enabled. 
		             ALCATEL NOTE:
		                 ACCESS:     NA       USAGE:      NA
		                 PERSIST:    NO       INSRVMOD:   NO
		                 RANGE:      NA       DEFVALUE:   NA
		                 UNITS:      NA       SPARSE:     NA
		                 DESCR:      NA"
	::= { extendBoardForwarderFdbEntry 4 }

extendMonitor	OBJECT IDENTIFIER ::= {plimEthernet 6}

	extendMonitorPortTable OBJECT-TYPE
		SYNTAX	SEQUENCE OF ExtendMonitorPortEntry
		ACCESS	not-accessible
		STATUS	mandatory
		DESCRIPTION
			"A table containing the monitoring information
			of the port table. An entry will exist for each ATM port.
             ALCATEL NOTE:
                 TABLESIZE:  DEP [depends on the value of dot1qBaseNumPorts]
                 DESCR:      "
		::= { extendMonitor 2}

	extendMonitorPortEntry OBJECT-TYPE
		SYNTAX	ExtendMonitorPortEntry
		ACCESS	not-accessible
		STATUS	mandatory
		DESCRIPTION
			"An entry in the table extendMonitorPortTable. One entry
			specifies the events of a specified Port."
		INDEX	{ dot1dBasePort }
		::= { extendMonitorPortTable 1 }

	ExtendMonitorPortEntry ::=
		SEQUENCE	{
				extendMonitorPortEvents
					ExtendInterworkingEvent,
				extendMonitorPortTime
					NetworkTimeInSeconds
				}

	extendMonitorPortEvents	OBJECT-TYPE
		SYNTAX	ExtendInterworkingEvent
		ACCESS	read-only
		STATUS	mandatory
		DESCRIPTION
			"The events bitmap indicating the last occurred events.
             ALCATEL NOTE:
                 ACCESS:     NA       USAGE:      NA
                 PERSIST:    NO       INSRVMOD:   NO
                 RANGE:      NA       DEFVALUE:   0
                 UNITS:      NA       SPARSE:     NA
                 DESCR:      NA"
		::= { extendMonitorPortEntry 1}

	extendMonitorPortTime	OBJECT-TYPE
		SYNTAX	NetworkTimeInSeconds
		ACCESS	read-only
		STATUS	mandatory
		DESCRIPTION
			"The time in seconds when the events occur.
             ALCATEL NOTE:
                 ACCESS:     NA       USAGE:      NA
                 PERSIST:    NO       INSRVMOD:   NO
                 RANGE:      NA       DEFVALUE:   0
                 UNITS:      seconds  SPARSE:     NA
                 DESCR:      NA"
		::= { extendMonitorPortEntry 2}

vlanStack	OBJECT IDENTIFIER ::= {plimEthernet 7}

	vlanStackEtherType		OBJECT-TYPE
		SYNTAX	INTEGER
		ACCESS	read-write
		STATUS	mandatory
		DESCRIPTION
			"The Ethernet type value for the stacked VLAN tag.
             ALCATEL NOTE:
                 ACCESS:     NA       USAGE:      NA
                 PERSIST:    YES      INSRVMOD:   YES
                 RANGE:      NA       DEFVALUE:   NA
                 UNITS:      NA       SPARSE:     NA
                 DESCR:      NA"
		::= { vlanStack 1}

	vlanStackCurrentVlanList OBJECT-TYPE
		SYNTAX	VlanList
		ACCESS	read-only
		STATUS	mandatory
		DESCRIPTION
			"The current configured S-VLAN list in the system. This is
			the set of S-VLANs for which an entry is available in
			the extendVlanStaticTable. A 1 indicates an entry for
			this S-VLAN exists in the dot1qVlanStaticTable, a 0
			indicates no corresponding entry exists.
             ALCATEL NOTE:
                 ACCESS:     NA       USAGE:      NA
                 PERSIST:    NO       INSRVMOD:   NO
                 RANGE:      NA       DEFVALUE:   NA
                 UNITS:      NA       SPARSE:     NA
                 DESCR:      NA"
		::= { vlanStack 5}

	vlanStackCurrentVlanMultiplexList OBJECT-TYPE
		SYNTAX	VlanList
		ACCESS	read-only
		STATUS	mandatory
		DESCRIPTION
			"The S-VLAN termination list currently in the system. This is 
			the set of  S-VLANs configured in the extendVlanStaticTable 
			for which the object extendVlanStaticSystemMode has the value of 
			layer2Terminated. 
			A 1 indicates an entry for this S-VLAN-ID exists and is 
			configured with the layer2Terminated mode, a 0 indicates 
			no corresponding entry exists or it is configured in the 
			other mode.
             ALCATEL NOTE:
                 ACCESS:     NA       USAGE:      NA
                 PERSIST:    NO       INSRVMOD:   NO
                 RANGE:      NA       DEFVALUE:   NA
                 UNITS:      NA       SPARSE:     NA
                 DESCR:      NA"
		::= { vlanStack 6}

	vlanStackCurrentVlanQosAwareList OBJECT-TYPE
		SYNTAX	VlanList
		ACCESS	read-only
		STATUS	mandatory
		DESCRIPTION
			"The QoSaware S-VLAN list currently in the sytem. This is
			the set of S-VLANs configured in the extendVlanStaticTable 
			for which the object extendVlanStaticSystemMode has the value of 
			QoS aware. 
			A 1 indicates an entry for this S-VLAN-ID exists and is 
			configured with the QoS aware mode, a 0 indicates 
			no corresponding entry exists or it is configured in the 
			other mode.
             ALCATEL NOTE:
                 ACCESS:     NA       USAGE:      NA
                 PERSIST:    NO       INSRVMOD:   NO
                 RANGE:      NA       DEFVALUE:   NA
                 UNITS:      NA       SPARSE:     NA
                 DESCR:      NA"
		::= { vlanStack 7}

	vlanStackCurrentVlanQoSAwareTable OBJECT-TYPE
		SYNTAX	SEQUENCE OF VlanStackCurrentVlanQoSAwareEntry
		ACCESS	not-accessible
		STATUS	mandatory
		DESCRIPTION
			"A table containing the stacked QoS-aware C-VLANs. One entry
			contains a bitlist of all QoS-aware C-VLANs stacked on the
			S-VLAN identified by vlanStackCurrentQoSAwareVlanId. 
			A 1 indicates that the corresponding entry in the
			extendVlanStaticTable has the extendVlanStaticSystemMode =
			qosAware. A 0 indicates that the Vlan doesn't exist or has 
			another mode.
             ALCATEL NOTE:
                 TABLESIZE:  4092
                 DESCR:      NA"
		::= { vlanStack 14 }

	vlanStackCurrentVlanQoSAwareEntry OBJECT-TYPE
		SYNTAX	VlanStackCurrentVlanQoSAwareEntry
		ACCESS	not-accessible
		STATUS	mandatory
		DESCRIPTION
			"An entry in the table vlanStackCurrentVlanQoSAwareTable."
		INDEX	{ dot1qVlanIndex }
		::= { vlanStackCurrentVlanQoSAwareTable 1 }

	VlanStackCurrentVlanQoSAwareEntry ::=
		SEQUENCE	{
				vlanStackCurrentVlanQoSAwareVlanList
					VlanList
				}

	vlanStackCurrentVlanQoSAwareVlanList OBJECT-TYPE
		SYNTAX	VlanList
		ACCESS	read-only
		STATUS	mandatory
		DESCRIPTION
			"The bitlist of QoS-aware C-VLANs.
             ALCATEL NOTE:
                 ACCESS:     NA       USAGE:      NA
                 PERSIST:    NO       INSRVMOD:   NO
                 RANGE:      NA       DEFVALUE:   NA
                 UNITS:      NA       SPARSE:     NA
                 DESCR:      NA"
		::= { vlanStackCurrentVlanQoSAwareEntry 1}

	vlanStackCurrentVlanTable OBJECT-TYPE
		SYNTAX	SEQUENCE OF VlanStackCurrentVlanEntry
		ACCESS	not-accessible
		STATUS	mandatory
		DESCRIPTION
			"A table containing the stacked C-VLANs. One entry
			contains a bitlist of all C-VLANs stacked on the
			S-VLAN identified by dot1qVlanIndex. 
			A 1 indicates that there is a corresponding entry in the
			extendVlanStaticTable. A 0 indicates that it does 
			not exist.
             ALCATEL NOTE:
                 TABLESIZE:  4092
                 DESCR:      NA"
		::= { vlanStack 15 }

	vlanStackCurrentVlanEntry OBJECT-TYPE
		SYNTAX	VlanStackCurrentVlanEntry
		ACCESS	not-accessible
		STATUS	mandatory
		DESCRIPTION
			"An entry in the table vlanStackCurrentVlanTable."
		INDEX	{ dot1qVlanIndex }
		::= { vlanStackCurrentVlanTable 1 }

	VlanStackCurrentVlanEntry ::=
		SEQUENCE	{
				vlanStackCurrentVlanVlanList
					VlanList
				}

	vlanStackCurrentVlanVlanList OBJECT-TYPE
		SYNTAX	VlanList
		ACCESS	read-only
		STATUS	mandatory
		DESCRIPTION
			"The bitlist of C-VLANs.
             ALCATEL NOTE:
                 ACCESS:     NA       USAGE:      NA
                 PERSIST:    NO       INSRVMOD:   NO
                 RANGE:      NA       DEFVALUE:   NA
                 UNITS:      NA       SPARSE:     NA
                 DESCR:      NA"
		::= { vlanStackCurrentVlanEntry 1}

	extendDot1vProtocol	OBJECT IDENTIFIER ::= { plimEthernet 8 }

	extendDot1vProtocolGroupTable OBJECT-TYPE
		SYNTAX	SEQUENCE OF ExtendDot1vProtocolGroupEntry 
		ACCESS	not-accessible
		STATUS	mandatory
		DESCRIPTION
			"A proprietary dot1vProtocolGroupTable extension containing the
			friendly names for the protocol groups
             ALCATEL NOTE:
                 TABLESIZE:  10
                 DESCR:      NA"
		::= {  extendDot1vProtocol 1 }

	extendDot1vProtocolGroupEntry  OBJECT-TYPE
		SYNTAX	ExtendDot1vProtocolGroupEntry
		ACCESS	not-accessible
		STATUS	mandatory
		DESCRIPTION
			"An entry in the table extendDot1vProtocolGroupTable."
		INDEX	{ dot1vProtocolTemplateFrameType, 
				dot1vProtocolTemplateProtocolValue }
		::= { extendDot1vProtocolGroupTable 1 }

	ExtendDot1vProtocolGroupEntry  ::=
		SEQUENCE	{ 
				extendDot1vProtocolGroupName
					SnmpAdminString (SIZE (0..32))
				}
	
	extendDot1vProtocolGroupName	OBJECT-TYPE
		SYNTAX	SnmpAdminString 
		ACCESS	read-write
		STATUS	mandatory
		DESCRIPTION
			"The friendly name of a protocol group
             ALCATEL NOTE:
                 ACCESS:     NA       USAGE:      NA
                 PERSIST:    YES      INSRVMOD:   YES
                 RANGE:      NA       DEFVALUE:   NULL
                 UNITS:      NA       SPARSE:     NA
                 DESCR:      NA"
		::= { extendDot1vProtocolGroupEntry 1 }

	extendDot1vProtocolPortTable OBJECT-TYPE
		SYNTAX	SEQUENCE OF ExtendDot1vProtocolPortEntry 
		ACCESS	not-accessible
		STATUS	mandatory
		DESCRIPTION
			"A proprietary dot1vProtocolPortTable extension to set the defaut
			priority of a protocol based VLAN
             ALCATEL NOTE:
                 TABLESIZE:  DEP [depends on the size of extendDot1vprotocolGropuTable* dot1dBaseNumPorts]
                 DESCR:      NA"
		::= {  extendDot1vProtocol 2 }

	extendDot1vProtocolPortEntry  OBJECT-TYPE
		SYNTAX	ExtendDot1vProtocolPortEntry
		ACCESS	not-accessible
		STATUS	mandatory
		DESCRIPTION
			"An entry in the table extendDot1vprotocolPortTable."
		INDEX	{ dot1dBasePort, dot1vProtocolPortGroupId }
		::= { extendDot1vProtocolPortTable 1 }

	ExtendDot1vProtocolPortEntry  ::=
		SEQUENCE	{ 
				extendDot1vProtocolPortGroupPriority
					ExtendVlanSystemPriority,
                 extendDot1vProtocolPortGroupVid
                     VlanIndex
				}
	
	extendDot1vProtocolPortGroupPriority	OBJECT-TYPE
		SYNTAX	ExtendVlanSystemPriority
		ACCESS	read-write
		STATUS	mandatory
		DESCRIPTION
			"The default priority of a protocol based VLAN
             ALCATEL NOTE:
                 ACCESS:     NA       USAGE:      NA
                 PERSIST:    YES      INSRVMOD:   YES
                 RANGE:      0..7      DEFVALUE:   NA
                 UNITS:      NA       SPARSE:     NA
                 DESCR:      NA"
		::= { extendDot1vProtocolPortEntry 1 }

	extendDot1vProtocolPortGroupVid	OBJECT-TYPE
		SYNTAX	VlanIndex
		ACCESS	read-write
		STATUS	mandatory
		DESCRIPTION
			"The VID associated with a group of protocols for each port.
             ALCATEL NOTE:
                 ACCESS:     NA       USAGE:      NA
                 PERSIST:    YES      INSRVMOD:   NO
                 RANGE:      NA       DEFVALUE:   NULL
                 UNITS:      NA       SPARSE:     NA
                 DESCR:      NA"
		::= { extendDot1vProtocolPortEntry 2 }

	extendStatistics	OBJECT IDENTIFIER ::= { plimEthernet 9 }

	extendPortVlanPerfInfoTable	 OBJECT-TYPE
		SYNTAX	SEQUENCE OF ExtendPortVlanPerfInfoEntry
		ACCESS	not-accessible
		STATUS	mandatory
		DESCRIPTION
			"Table of number of previous statistics intervals related to one Vlan
 			on a bridge port.
             ALCATEL NOTE:
                 TABLESIZE:  DEP [depends on the value of 
                                 extendPortVlanAssociationTable]
                 DESCR:      NA"
		::= { extendStatistics 1 }

	extendPortVlanPerfInfoEntry OBJECT-TYPE
		SYNTAX	ExtendPortVlanPerfInfoEntry
		ACCESS	not-accessible
		STATUS	mandatory
		DESCRIPTION
			"Table entry for available statistics intervals for one Vlan on a 
			bridge port."
		INDEX   { dot1dBasePort, extendPortVlanPerfInfoVlanIndex }
		::= { extendPortVlanPerfInfoTable 1 }

	ExtendPortVlanPerfInfoEntry ::=
		SEQUENCE {
				extendPortVlanPerfInfoVlanIndex
					VlanIndex,
				extendPortVlanPerfInfo15MinValidIntervals
					INTEGER,
				extendPortVlanPerfInfo1DayValidIntervals
					INTEGER
				}

	extendPortVlanPerfInfoVlanIndex OBJECT-TYPE
		SYNTAX	VlanIndex
		ACCESS  	not-accessible
		STATUS	mandatory
		DESCRIPTION
			"VLAN ID.
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanPerfInfoEntry 1 }

	extendPortVlanPerfInfo15MinValidIntervals OBJECT-TYPE
		SYNTAX	INTEGER
		ACCESS  	read-only
		STATUS	mandatory
		DESCRIPTION
			"Number of previous 15 minutes intervals
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPerfInfoEntry 2 }

	extendPortVlanPerfInfo1DayValidIntervals OBJECT-TYPE
		SYNTAX	INTEGER
		ACCESS  	read-only
		STATUS	mandatory
		DESCRIPTION
			"Number of previous 1 day intervals
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPerfInfoEntry 3 }

	extendPortVlanCurrent15MinIntervalTable	 OBJECT-TYPE
		SYNTAX	SEQUENCE OF ExtendPortVlanCurrent15MinIntervalEntry
		ACCESS	not-accessible
		STATUS	mandatory
		DESCRIPTION
			"15 Minutes current statistics for a VLAN/port	
             ALCATEL NOTE:
                 TABLESIZE:  DEP [depends on the value of 
                                 extendPortVlanAssociationTable]
                 DESCR:      NA"
		::= { extendStatistics 2 }

	extendPortVlanCurrent15MinIntervalEntry OBJECT-TYPE
		SYNTAX	ExtendPortVlanCurrent15MinIntervalEntry
		ACCESS	not-accessible
		STATUS	mandatory
		DESCRIPTION
			"Table entry for the current 15 minutes statistics counters for a 
			VLAN/port."
		INDEX   { dot1dBasePort, extendPortVlanCurrent15MinIntervalVlanIndex }
		::= { extendPortVlanCurrent15MinIntervalTable	 1 }

	 ExtendPortVlanCurrent15MinIntervalEntry ::=
		SEQUENCE {
				extendPortVlanCurrent15MinIntervalVlanIndex
					VlanIndex,
				extendPortVlanCurrent15MinTimeElapsed
					INTEGER, 
				extendPortVlanCurrent15MinTimeMeasured
					INTEGER,
				extendPortVlanCurrent15MinUpFwdFrameCounter
					 OCTET STRING (SIZE (8)),
				extendPortVlanCurrent15MinUpFwdByteCounter
					 OCTET STRING (SIZE (8)),
				extendPortVlanCurrent15MinDnFwdFrameCounter
					 OCTET STRING (SIZE (8)),
				extendPortVlanCurrent15MinDnFwdByteCounter
					 OCTET STRING (SIZE (8)),
				extendPortVlanCurrent15MinUpDiscFrameCounter
					 OCTET STRING (SIZE (8)),
				extendPortVlanCurrent15MinUpDiscByteCounter
					 OCTET STRING (SIZE (8)),
				extendPortVlanCurrent15MinDnDiscFrameCounter
					 OCTET STRING (SIZE (8)),
				extendPortVlanCurrent15MinDnDiscByteCounter
					 OCTET STRING (SIZE (8))
			}

	extendPortVlanCurrent15MinIntervalVlanIndex OBJECT-TYPE
		SYNTAX	VlanIndex
		ACCESS  	not-accessible
		STATUS	mandatory
		DESCRIPTION
			"VLAN ID. on which the counters apply
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanCurrent15MinIntervalEntry 1 }
	
	extendPortVlanCurrent15MinTimeElapsed OBJECT-TYPE
		SYNTAX	INTEGER
		ACCESS  	read-only
		STATUS	mandatory
		DESCRIPTION
			"Elapsed time in interval (seconds)
            ALCATEL NOTE:
                ACCESS:     NA       USAGE:      NA
                PERSIST:    NO       INSRVMOD:   NO
                RANGE:      NA       DEFVALUE:   NA
                UNITS:      seconds  SPARSE:     NA
                DESCR:      NA"
		::= { extendPortVlanCurrent15MinIntervalEntry 2 }

	extendPortVlanCurrent15MinTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
		::= { extendPortVlanCurrent15MinIntervalEntry 3 }

	 extendPortVlanCurrent15MinUpFwdFrameCounter OBJECT-TYPE
		SYNTAX	OCTET STRING (SIZE (8))

		ACCESS  	read-only
		STATUS	mandatory
		DESCRIPTION
			"All forwarded frames in upstream direction per VLAN on a bridge port 
			in current 15 min interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 4 }

	extendPortVlanCurrent15MinUpFwdByteCounter OBJECT-TYPE
		SYNTAX	OCTET STRING (SIZE (8))
		ACCESS  	read-only
		STATUS	mandatory
		DESCRIPTION
			"All forwarded bytes in upstream direction per VLAN on a bridge port
 			in current 15 min interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 5 }

	extendPortVlanCurrent15MinDnFwdFrameCounter OBJECT-TYPE
		SYNTAX	OCTET STRING (SIZE (8))
		ACCESS  	read-only
		STATUS	mandatory
		DESCRIPTION
			"All forwarded frames in downstream direction per VLAN on a bridge
			port in current 15 min interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 6 }

	extendPortVlanCurrent15MinDnFwdByteCounter OBJECT-TYPE
		SYNTAX	OCTET STRING (SIZE (8))
		ACCESS  	read-only
		STATUS	mandatory
		DESCRIPTION
			"All forwarded  bytes in downstream direction per VLAN on a bridge 
			port in current 15 min interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 7 }

	extendPortVlanCurrent15MinUpDiscFrameCounter OBJECT-TYPE
		SYNTAX	OCTET STRING (SIZE (8))
		ACCESS  	read-only
		STATUS	mandatory
		DESCRIPTION
			"All discarded frames in upstream direction per VLAN on a bridge 
			port in current 15 min interval.Counted : discards by buffer 
			acceptance or policing
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 8 }

	extendPortVlanCurrent15MinUpDiscByteCounter OBJECT-TYPE
		SYNTAX	OCTET STRING (SIZE (8))
		ACCESS  	read-only
		STATUS	mandatory
		DESCRIPTION
			"All discarded bytes in upstream direction per VLAN on a bridge 
			port in current 15 min interval.Counted : discards by buffer 
			acceptance or policing
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 9 }

	extendPortVlanCurrent15MinDnDiscFrameCounter OBJECT-TYPE
		SYNTAX	OCTET STRING (SIZE (8))
		ACCESS  	read-only
		STATUS	mandatory
		DESCRIPTION
			"All discarded frames in downstream direction per VLAN on a bridge 
			port in current 15 min interval. Counted : discards by buffer 
			acceptance or policing
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 10 }

	extendPortVlanCurrent15MinDnDiscByteCounter OBJECT-TYPE
		SYNTAX	OCTET STRING (SIZE (8))
		ACCESS  	read-only
		STATUS	mandatory
		DESCRIPTION
			"All discarded bytes in downstream direction per VLAN on a bridge 
			port in current 15 min interval. Counted : discards by buffer 
			acceptance or policing
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent15MinIntervalEntry 11 }

	extendPortVlanCurrent1DayIntervalTable	 OBJECT-TYPE
		SYNTAX	SEQUENCE OF ExtendPortVlanCurrent1DayIntervalEntry
		ACCESS	not-accessible
		STATUS	mandatory
		DESCRIPTION
			"1 Day current statistics for a VLAN/port
             ALCATEL NOTE:
                 TABLESIZE:  DEP [depending on the value of 
                                 extendPortVlanAssociationTable]
                 DESCR:      NA"
		::= { extendStatistics 3 }

	extendPortVlanCurrent1DayIntervalEntry OBJECT-TYPE
		SYNTAX	ExtendPortVlanCurrent1DayIntervalEntry
		ACCESS	not-accessible
		STATUS	mandatory
		DESCRIPTION
			"Table entry for the current 1 day statistics counters per VLAN/port."
		INDEX   { dot1dBasePort, extendPortVlanCurrent1DayIntervalVlanIndex }
		::= { extendPortVlanCurrent1DayIntervalTable	 1 }

	 ExtendPortVlanCurrent1DayIntervalEntry ::=
		SEQUENCE {
				extendPortVlanCurrent1DayIntervalVlanIndex
					VlanIndex,
				extendPortVlanCurrent1DayTimeElapsed
					INTEGER, 
				extendPortVlanCurrent1DayTimeMeasured
					INTEGER,
				extendPortVlanCurrent1DayUpFwdFrameCounter
					OCTET STRING (SIZE (8)),
				extendPortVlanCurrent1DayUpFwdByteCounter
					OCTET STRING (SIZE (8)),
				extendPortVlanCurrent1DayDnFwdFrameCounter
					OCTET STRING (SIZE (8)),
				extendPortVlanCurrent1DayDnFwdByteCounter
					OCTET STRING (SIZE (8)),
				extendPortVlanCurrent1DayUpDiscFrameCounter
					OCTET STRING (SIZE (8)),
				extendPortVlanCurrent1DayUpDiscByteCounter
					OCTET STRING (SIZE (8)),
				extendPortVlanCurrent1DayDnDiscFrameCounter
					OCTET STRING (SIZE (8)),
				extendPortVlanCurrent1DayDnDiscByteCounter
					OCTET STRING (SIZE (8))
							}

	extendPortVlanCurrent1DayIntervalVlanIndex  OBJECT-TYPE
		SYNTAX	VlanIndex
		ACCESS  	not-accessible
		STATUS	mandatory
		DESCRIPTION
			"VLAN ID. of the VLAN on which the counters apply
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanCurrent1DayIntervalEntry 1 }
	
	extendPortVlanCurrent1DayTimeElapsed OBJECT-TYPE
		SYNTAX	INTEGER
		ACCESS  	read-only
		STATUS	mandatory
		DESCRIPTION
			"Elapsed time in interval (seconds)
             ALCATEL NOTE:
                 ACCESS:     NA       USAGE:      NA
                 PERSIST:    NO       INSRVMOD:   NO
                 RANGE:      NA       DEFVALUE:   NA
                 UNITS:      seconds  SPARSE:     NA
                                 DESCR:      NA"
		::= { extendPortVlanCurrent1DayIntervalEntry 2 }

	extendPortVlanCurrent1DayTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
		::= { extendPortVlanCurrent1DayIntervalEntry 3 }

	 extendPortVlanCurrent1DayUpFwdFrameCounter OBJECT-TYPE
		SYNTAX	OCTET STRING (SIZE (8))

		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 4 }

	extendPortVlanCurrent1DayUpFwdByteCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 5 }

	extendPortVlanCurrent1DayDnFwdFrameCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 6 }

	extendPortVlanCurrent1DayDnFwdByteCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 7 }

	extendPortVlanCurrent1DayUpDiscFrameCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 8 }

	extendPortVlanCurrent1DayUpDiscByteCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 9 }

	extendPortVlanCurrent1DayDnDiscFrameCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 10 }

	extendPortVlanCurrent1DayDnDiscByteCounter OBJECT-TYPE
		SYNTAX	OCTET STRING (SIZE (8))
		ACCESS  	read-only
		STATUS	mandatory
		DESCRIPTION
			"Definition as for corresponding 15 minutes counters but per day
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanCurrent1DayIntervalEntry 11 }

	extendPortVlanPrevious15MinIntervalTable	 OBJECT-TYPE
		SYNTAX	SEQUENCE OF ExtendPortVlanPrevious15MinIntervalEntry
		ACCESS	not-accessible
		STATUS	mandatory
		DESCRIPTION
			"15 Minutes previous statistics counters for VLAN/port
             ALCATEL NOTE:
                 TABLESIZE:  DEP [depending on the value of 
                                 extendPortVlanAssociationTable]
                 DESCR:      NA"
		::= { extendStatistics 4 }

	extendPortVlanPrevious15MinIntervalEntry OBJECT-TYPE
		SYNTAX	ExtendPortVlanPrevious15MinIntervalEntry
		ACCESS	not-accessible
		STATUS	mandatory
		DESCRIPTION
			"Table entry for the previous 15 minutes statistics counters per 
			VLAN/port."
      INDEX   { dot1dBasePort,
            extendPortVlanPrevious15MinIntervalVlanIndex,
				extendPortVlanPrevious15MinIntervalNumber }
		::= { extendPortVlanPrevious15MinIntervalTable	 1 }

	 ExtendPortVlanPrevious15MinIntervalEntry ::=
		SEQUENCE {
				extendPortVlanPrevious15MinIntervalVlanIndex
					VlanIndex,
				extendPortVlanPrevious15MinIntervalNumber
					INTEGER,
				extendPortVlanPrevious15MinTimeMeasured
					INTEGER,
				extendPortVlanPrevious15MinUpFwdFrameCounter
					OCTET STRING (SIZE (8)),
				extendPortVlanPrevious15MinUpFwdByteCounter
					OCTET STRING (SIZE (8)),
				extendPortVlanPrevious15MinDnFwdFrameCounter
					OCTET STRING (SIZE (8)),
				extendPortVlanPrevious15MinDnFwdByteCounter
					OCTET STRING (SIZE (8)),
				extendPortVlanPrevious15MinUpDiscFrameCounter
					OCTET STRING (SIZE (8)),
				extendPortVlanPrevious15MinUpDiscByteCounter
					OCTET STRING (SIZE (8)),
				extendPortVlanPrevious15MinDnDiscFrameCounter
					OCTET STRING (SIZE (8)),
				extendPortVlanPrevious15MinDnDiscByteCounter
					OCTET STRING (SIZE (8))
			}

	extendPortVlanPrevious15MinIntervalVlanIndex OBJECT-TYPE 
		SYNTAX	VlanIndex
		ACCESS  	not-accessible
		STATUS	mandatory
		DESCRIPTION
			"VLAN ID. on which the counters apply
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanPrevious15MinIntervalEntry 1 }
	
	extendPortVlanPrevious15MinIntervalNumber OBJECT-TYPE
		SYNTAX	INTEGER
		ACCESS  	not-accessible
		STATUS	mandatory
		DESCRIPTION
			"Previous interval reference
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanPrevious15MinIntervalEntry 2 }

	extendPortVlanPrevious15MinTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
		::= { extendPortVlanPrevious15MinIntervalEntry 3 }

	 extendPortVlanPrevious15MinUpFwdFrameCounter OBJECT-TYPE
		SYNTAX	OCTET STRING (SIZE (8))

		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 4 }

	extendPortVlanPrevious15MinUpFwdByteCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 5 }

	extendPortVlanPrevious15MinDnFwdFrameCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 6 }

	extendPortVlanPrevious15MinDnFwdByteCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 7 }

	extendPortVlanPrevious15MinUpDiscFrameCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 8 }

	extendPortVlanPrevious15MinUpDiscByteCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 9 }

	extendPortVlanPrevious15MinDnDiscFrameCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 10 }

	extendPortVlanPrevious15MinDnDiscByteCounter OBJECT-TYPE
		SYNTAX	OCTET STRING (SIZE (8))
		ACCESS  	read-only
		STATUS	mandatory
		DESCRIPTION
			"Definition as for current 15 minutes counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious15MinIntervalEntry 11 }

	extendPortVlanPrevious1DayIntervalTable	 OBJECT-TYPE
		SYNTAX	SEQUENCE OF ExtendPortVlanPrevious1DayIntervalEntry
		ACCESS	not-accessible
		STATUS	mandatory
		DESCRIPTION
			"1 Day previous statistics for VLAN/port
             ALCATEL NOTE:
                 TABLESIZE:  DEP [depending on the value of 
                                 extendPortVlanAssociationTable]
                 DESCR:      NA"
		::= { extendStatistics 5 }

	extendPortVlanPrevious1DayIntervalEntry OBJECT-TYPE
		SYNTAX	ExtendPortVlanPrevious1DayIntervalEntry
		ACCESS	not-accessible
		STATUS	mandatory
		DESCRIPTION
			"Table entry for the previous 1 day statistics counters."
		INDEX	{ dot1dBasePort, extendPortVlanPrevious1DayIntervalVlanIndex, 
				extendPortVlanPrevious1DayIntervalNumber
				}
		::= { extendPortVlanPrevious1DayIntervalTable	 1 }

	 ExtendPortVlanPrevious1DayIntervalEntry ::=
		SEQUENCE {
				extendPortVlanPrevious1DayIntervalVlanIndex
					VlanIndex,
				extendPortVlanPrevious1DayIntervalNumber
					INTEGER,
				extendPortVlanPrevious1DayTimeMeasured
					INTEGER,
				extendPortVlanPrevious1DayUpFwdFrameCounter
					OCTET STRING (SIZE (8)),
				extendPortVlanPrevious1DayUpFwdByteCounter
					OCTET STRING (SIZE (8)),
				extendPortVlanPrevious1DayDnFwdFrameCounter
					OCTET STRING (SIZE (8)),
				extendPortVlanPrevious1DayDnFwdByteCounter
					OCTET STRING (SIZE (8)),
				extendPortVlanPrevious1DayUpDiscFrameCounter
					OCTET STRING (SIZE (8)),
				extendPortVlanPrevious1DayUpDiscByteCounter
					OCTET STRING (SIZE (8)),
				extendPortVlanPrevious1DayDnDiscFrameCounter
					OCTET STRING (SIZE (8)),
				extendPortVlanPrevious1DayDnDiscByteCounter
					OCTET STRING (SIZE (8))
				
			}

	extendPortVlanPrevious1DayIntervalVlanIndex  OBJECT-TYPE
		SYNTAX	VlanIndex
		ACCESS  	not-accessible
		STATUS	mandatory
		DESCRIPTION
			"VLAN ID. on which the counters apply
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanPrevious1DayIntervalEntry 1 }
	
	extendPortVlanPrevious1DayIntervalNumber OBJECT-TYPE
		SYNTAX	INTEGER
		ACCESS  	not-accessible
		STATUS	mandatory
		DESCRIPTION
			"Previous interval reference
             ALCATEL NOTE:
                 ACCESS:     NA       USAGE:      NA
                 PERSIST:    NO       INSRVMOD:   NO
                 RANGE:      NA       DEFVALUE:   NA
                 UNITS:      NA       SPARSE:     NA
                 DESCR:      NA"
		::= { extendPortVlanPrevious1DayIntervalEntry 2 }

	extendPortVlanPrevious1DayTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
		::= { extendPortVlanPrevious1DayIntervalEntry 3 }

	 extendPortVlanPrevious1DayUpFwdFrameCounter OBJECT-TYPE
		SYNTAX	OCTET STRING (SIZE (8))

		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 4 }

	extendPortVlanPrevious1DayUpFwdByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 5 }

	extendPortVlanPrevious1DayDnFwdFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 6 }

	extendPortVlanPrevious1DayDnFwdByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 7 }

	extendPortVlanPrevious1DayUpDiscFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 8 }

	extendPortVlanPrevious1DayUpDiscByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 9 }

	extendPortVlanPrevious1DayDnDiscFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 10 }

	extendPortVlanPrevious1DayDnDiscByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortVlanPrevious1DayIntervalEntry 11 }

	extendPortTotalPerfInfoTable	 OBJECT-TYPE
		SYNTAX	SEQUENCE OF ExtendPortTotalPerfInfoEntry
		ACCESS	not-accessible
		STATUS	mandatory
		DESCRIPTION
			"Table of number of previous statistics intervals for the traffic on a
 			bridgeport (PortTotal = all traffic on a port, including PPPoE relayed
 			and PPPoE terminated traffic) per bridge port
             ALCATEL NOTE:
                 TABLESIZE:  DEP [depending on the value of 
                             dot1dBaseNumPorts.]
                 DESCR:      NA"
		::= { extendStatistics 6 }

	extendPortTotalPerfInfoEntry OBJECT-TYPE
		SYNTAX	ExtendPortTotalPerfInfoEntry
		ACCESS	not-accessible
		STATUS	mandatory
		DESCRIPTION
			"Table entry of extendportTotalPerfInfoTable"
		INDEX   { dot1dBasePort }
		::= { extendPortTotalPerfInfoTable 1 }

	ExtendPortTotalPerfInfoEntry ::=
		SEQUENCE	{
				extendPortTotalPerfInfo15MinValidIntervals
					INTEGER,
				extendPortTotalPerfInfo1DayValidIntervals
					INTEGER
				}

	extendPortTotalPerfInfo15MinValidIntervals OBJECT-TYPE
		SYNTAX	INTEGER
		ACCESS  	read-only
		STATUS	mandatory
		DESCRIPTION
			"Number of previous 15 minutes intervals
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPerfInfoEntry 1 }

	extendPortTotalPerfInfo1DayValidIntervals OBJECT-TYPE
		SYNTAX	INTEGER
		ACCESS  	read-only
		STATUS	mandatory
		DESCRIPTION
			"Number of previous 1 day intervals
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPerfInfoEntry 2 }

	extendPortTotalCurrent15MinIntervalTable	 OBJECT-TYPE
		SYNTAX	SEQUENCE OF ExtendPortTotalCurrent15MinIntervalEntry
		ACCESS	not-accessible
		STATUS	mandatory
		DESCRIPTION
			"15 Minutes current statistics for PortTotal (= all traffic on a port, 
			Including PPPoE relayed and PPPoE terminated traffic) 
             ALCATEL NOTE:
                 TABLESIZE:  DEP [depending on the value of 
                             dot1dBaseNumPorts.]
                 DESCR:      NA"
		::= { extendStatistics 7 }

	extendPortTotalCurrent15MinIntervalEntry OBJECT-TYPE
		SYNTAX	ExtendPortTotalCurrent15MinIntervalEntry
		ACCESS	not-accessible
		STATUS	mandatory
		DESCRIPTION
			"Table entry for the current 15 minutes statistics counters."
		INDEX   { dot1dBasePort }
		::= { extendPortTotalCurrent15MinIntervalTable 1 }

	 ExtendPortTotalCurrent15MinIntervalEntry ::=
		SEQUENCE {
				extendPortTotalCurrent15MinTimeElapsed
					INTEGER, 
				extendPortTotalCurrent15MinTimeMeasured
					INTEGER,
				extendPortTotalCurrent15MinUpFwdFrameCounter
					OCTET STRING (SIZE (8)),
				extendPortTotalCurrent15MinUpFwdByteCounter
					OCTET STRING (SIZE (8)),
				extendPortTotalCurrent15MinDnFwdFrameCounter
					OCTET STRING (SIZE (8)),
				extendPortTotalCurrent15MinDnFwdByteCounter
					OCTET STRING (SIZE (8)),
				extendPortTotalCurrent15MinUpDiscFrameCounter
					OCTET STRING (SIZE (8)),
				extendPortTotalCurrent15MinUpDiscByteCounter
					OCTET STRING (SIZE (8)),
				extendPortTotalCurrent15MinDnDiscFrameCounter
					OCTET STRING (SIZE (8)),
				extendPortTotalCurrent15MinDnDiscByteCounter
					OCTET STRING (SIZE (8))
			}

	extendPortTotalCurrent15MinTimeElapsed OBJECT-TYPE
		SYNTAX	INTEGER
		ACCESS  	read-only
		STATUS	mandatory
		DESCRIPTION
			"Elapsed time in interval (seconds)
             ALCATEL NOTE:
                 ACCESS:     NA       USAGE:      NA
                 PERSIST:    NO       INSRVMOD:   NO
                 RANGE:      NA       DEFVALUE:   0
                 UNITS:      seconds  SPARSE:     NA
                 DESCR:      NA"
		::= { extendPortTotalCurrent15MinIntervalEntry 1 }

	extendPortTotalCurrent15MinTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   0
                 UNITS:      seconds  SPARSE:     NA
                 DESCR:      NA"
		::= { extendPortTotalCurrent15MinIntervalEntry 2 }

	 extendPortTotalCurrent15MinUpFwdFrameCounter OBJECT-TYPE
		SYNTAX	OCTET STRING (SIZE (8))

		ACCESS  	read-only
		STATUS	mandatory
		DESCRIPTION
			"Total forwarded frames per port in upstream direction (current 
			15 min. interval)
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 3 }

	extendPortTotalCurrent15MinUpFwdByteCounter OBJECT-TYPE
		SYNTAX	OCTET STRING (SIZE (8))
		ACCESS  	read-only
		STATUS	mandatory
		DESCRIPTION
			"Total forwarded bytes per port in upstream direction (current 
			15 min. interval)
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 4 }

	extendPortTotalCurrent15MinDnFwdFrameCounter OBJECT-TYPE
		SYNTAX	OCTET STRING (SIZE (8))
		ACCESS  	read-only
		STATUS	mandatory
		DESCRIPTION
			"Total forwarded frames per port in downstream direction (current 
			15 min. interval)
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 5 }

	extendPortTotalCurrent15MinDnFwdByteCounter OBJECT-TYPE
		SYNTAX	OCTET STRING (SIZE (8))
		ACCESS  	read-only
		STATUS	mandatory
		DESCRIPTION
			"Total forwarded bytes per port in downstream direction (current 
			15 min. interval)
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 6 }

	extendPortTotalCurrent15MinUpDiscFrameCounter OBJECT-TYPE
		SYNTAX	OCTET STRING (SIZE (8))
		ACCESS  	read-only
		STATUS	mandatory
		DESCRIPTION
			"Total discarded frames per port in upstream direction (current 
			15 min interval). Counted : discards by buffer acceptance or 
			policing.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 7 }

	extendPortTotalCurrent15MinUpDiscByteCounter OBJECT-TYPE
		SYNTAX	OCTET STRING (SIZE (8))
		ACCESS  	read-only
		STATUS	mandatory
		DESCRIPTION
			"Total discarded bytes per port in upstream direction (current 
			15 min. interval). Counted : discards by buffer acceptance or 
			policing.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 8 }

	extendPortTotalCurrent15MinDnDiscFrameCounter OBJECT-TYPE
		SYNTAX	OCTET STRING (SIZE (8))
		ACCESS  	read-only
		STATUS	mandatory
		DESCRIPTION
			"Total discarded frames per port in downstream direction (current 
			15 min. interval). Counted : discards by buffer acceptance or 
			policing.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 9 }

	extendPortTotalCurrent15MinDnDiscByteCounter OBJECT-TYPE
		SYNTAX	OCTET STRING (SIZE (8))
		ACCESS  	read-only
		STATUS	mandatory
		DESCRIPTION
			"Total discarded bytes per port in downstream direction (current 
			15 min. interval). Counted : discards by buffer acceptance or 
			policing.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent15MinIntervalEntry 10 }

	extendPortTotalCurrent1DayIntervalTable	 OBJECT-TYPE
		SYNTAX	SEQUENCE OF ExtendPortTotalCurrent1DayIntervalEntry
		ACCESS	not-accessible
		STATUS	mandatory
		DESCRIPTION
			"1 Day current statistics for PortTotal (= all traffic on a port, 
	I		including PPPoE relayed and PPPoE terminated traffic) 
             ALCATEL NOTE:
                 TABLESIZE:  DEP [depending on the value of 
                             dot1dBaseNumPorts.]
                 DESCR:      NA"
		::= { extendStatistics 8 }

	extendPortTotalCurrent1DayIntervalEntry OBJECT-TYPE
		SYNTAX	ExtendPortTotalCurrent1DayIntervalEntry
		ACCESS	not-accessible
		STATUS	mandatory
		DESCRIPTION
			"Table entry for the current 1 day statistics counters for PortTotal."
		INDEX   { dot1dBasePort }
		::= { extendPortTotalCurrent1DayIntervalTable	 1 }

	 ExtendPortTotalCurrent1DayIntervalEntry ::=
		SEQUENCE {
				extendPortTotalCurrent1DayTimeElapsed
					INTEGER, 
				extendPortTotalCurrent1DayTimeMeasured
					INTEGER,
				extendPortTotalCurrent1DayUpFwdFrameCounter
					OCTET STRING (SIZE (8)),
				extendPortTotalCurrent1DayUpFwdByteCounter
					OCTET STRING (SIZE (8)),
				extendPortTotalCurrent1DayDnFwdFrameCounter
					OCTET STRING (SIZE (8)),
				extendPortTotalCurrent1DayDnFwdByteCounter
					OCTET STRING (SIZE (8)),
				extendPortTotalCurrent1DayUpDiscFrameCounter
					OCTET STRING (SIZE (8)),
				extendPortTotalCurrent1DayUpDiscByteCounter
					OCTET STRING (SIZE (8)),
				extendPortTotalCurrent1DayDnDiscFrameCounter
					OCTET STRING (SIZE (8)),
				extendPortTotalCurrent1DayDnDiscByteCounter
					OCTET STRING (SIZE (8))
			}

	extendPortTotalCurrent1DayTimeElapsed OBJECT-TYPE
		SYNTAX	INTEGER
		ACCESS  	read-only
		STATUS	mandatory
		DESCRIPTION
			"Elapsed time in interval (seconds)
             ALCATEL NOTE:
                 ACCESS:     NA       USAGE:      NA
                 PERSIST:    NO       INSRVMOD:   NO
                 RANGE:      NA       DEFVALUE:   0
                 UNITS:      seconds  SPARSE:     NA
                 DESCR:      NA"
		::= { extendPortTotalCurrent1DayIntervalEntry 1 }

	extendPortTotalCurrent1DayTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   0
                 UNITS:      seconds  SPARSE:     NA
                 DESCR:      NA"
		::= { extendPortTotalCurrent1DayIntervalEntry 2 }

	 extendPortTotalCurrent1DayUpFwdFrameCounter OBJECT-TYPE
		SYNTAX	OCTET STRING (SIZE (8))

		ACCESS  	read-only
		STATUS	mandatory
		DESCRIPTION
			"Definition as for current corresponding 15 min. counters but per 
			day.
             ALCATEL NOTE:
                 ACCESS:     NA       USAGE:      NA
                 PERSIST:    NO       INSRVMOD:   YES
                 RANGE:      NA       DEFVALUE:   NA
                 UNITS:      NA       SPARSE:     NA
                 DESCR:      NA"
		::= { extendPortTotalCurrent1DayIntervalEntry 3 }

	extendPortTotalCurrent1DayUpFwdByteCounter OBJECT-TYPE
		SYNTAX	OCTET STRING (SIZE (8))
		ACCESS  	read-only
		STATUS	mandatory
		DESCRIPTION
			"Definition as for current corresponding 15 min. counters but per 
			day.
              ALCATEL NOTE:
                  ACCESS:     NA       USAGE:      NA
                  PERSIST:    NO       INSRVMOD:   NO
                  RANGE:      NA       DEFVALUE:   0
                  UNITS:      NA       SPARSE:     NA
                  DESCR:      NA"
		::= { extendPortTotalCurrent1DayIntervalEntry 4 }

	extendPortTotalCurrent1DayDnFwdFrameCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 5 }

	extendPortTotalCurrent1DayDnFwdByteCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 6 }

	extendPortTotalCurrent1DayUpDiscFrameCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 7 }

	extendPortTotalCurrent1DayUpDiscByteCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 8 }

	extendPortTotalCurrent1DayDnDiscFrameCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 9 }

	extendPortTotalCurrent1DayDnDiscByteCounter OBJECT-TYPE
		SYNTAX	OCTET STRING (SIZE (8))
		ACCESS  	read-only
		STATUS	mandatory
		DESCRIPTION
			"Definition as for current corresponding 15 min. counters but per 
			day.
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalCurrent1DayIntervalEntry 10 }

	extendPortTotalPrevious15MinIntervalTable	 OBJECT-TYPE
		SYNTAX	SEQUENCE OF ExtendPortTotalPrevious15MinIntervalEntry
		ACCESS	not-accessible
		STATUS	mandatory
		DESCRIPTION
			"15 Minutes previous statistics for PortTotal(= all traffic on a port,
 			Including PPPoE relayed and PPPoE terminated traffic) 
             ALCATEL NOTE:
                 TABLESIZE:  DEP [depending on the value of 
                             dot1dBaseNumPorts.]
                 DESCR:      NA"
		::= { extendStatistics 9 }

	extendPortTotalPrevious15MinIntervalEntry OBJECT-TYPE
		SYNTAX	ExtendPortTotalPrevious15MinIntervalEntry
		ACCESS	not-accessible
		STATUS	mandatory
		DESCRIPTION
			"Table entry for the previous 15 minutes statistics counters."
		INDEX   { dot1dBasePort,	extendPortTotalPrevious15MinIntervalNumber }
		::= { extendPortTotalPrevious15MinIntervalTable	 1 }

	 ExtendPortTotalPrevious15MinIntervalEntry ::=
		SEQUENCE {
				extendPortTotalPrevious15MinIntervalNumber
					INTEGER,
				extendPortTotalPrevious15MinTimeMeasured
					INTEGER,
				extendPortTotalPrevious15MinUpFwdFrameCounter
					OCTET STRING (SIZE (8)),
				extendPortTotalPrevious15MinUpFwdByteCounter
					OCTET STRING (SIZE (8)),
				extendPortTotalPrevious15MinDnFwdFrameCounter
					OCTET STRING (SIZE (8)),
				extendPortTotalPrevious15MinDnFwdByteCounter
					OCTET STRING (SIZE (8)),
				extendPortTotalPrevious15MinUpDiscFrameCounter
					OCTET STRING (SIZE (8)),
				extendPortTotalPrevious15MinUpDiscByteCounter
					OCTET STRING (SIZE (8)),
				extendPortTotalPrevious15MinDnDiscFrameCounter
					OCTET STRING (SIZE (8)),
				extendPortTotalPrevious15MinDnDiscByteCounter
					OCTET STRING (SIZE (8))
			}

	extendPortTotalPrevious15MinIntervalNumber OBJECT-TYPE
		SYNTAX	INTEGER
		ACCESS  	not-accessible
		STATUS	mandatory
		DESCRIPTION
			"Previous interval reference
             ALCATEL NOTE:
                 ACCESS:     NA       USAGE:      NA
                 PERSIST:    NO       INSRVMOD:   NO
                 RANGE:      NA       DEFVALUE:   NA
                 UNITS:      NA       SPARSE:     NA
                 DESCR:      NA"
		::= { extendPortTotalPrevious15MinIntervalEntry 1 }

	extendPortTotalPrevious15MinTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   NA
                 UNITS:      seconds  SPARSE:     NA
                 DESCR:      NA"
		::= { extendPortTotalPrevious15MinIntervalEntry 2 }

	 extendPortTotalPrevious15MinUpFwdFrameCounter OBJECT-TYPE
		SYNTAX	OCTET STRING (SIZE (8))

		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   NA
                 UNITS:      seconds  SPARSE:     NA
                 DESCR:      NA"
		::= { extendPortTotalPrevious15MinIntervalEntry 3 }

	extendPortTotalPrevious15MinUpFwdByteCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 4 }

	extendPortTotalPrevious15MinDnFwdFrameCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 5 }

	extendPortTotalPrevious15MinDnFwdByteCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 6 }

	extendPortTotalPrevious15MinUpDiscFrameCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 7 }

	extendPortTotalPrevious15MinUpDiscByteCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 8 }

	extendPortTotalPrevious15MinDnDiscFrameCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 9 }

	extendPortTotalPrevious15MinDnDiscByteCounter OBJECT-TYPE
		SYNTAX	OCTET STRING (SIZE (8))
		ACCESS  	read-only
		STATUS	mandatory
		DESCRIPTION
			"Definition as for current 15 min. counters but for a previous 
			interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious15MinIntervalEntry 10 }

	extendPortTotalPrevious1DayIntervalTable	 OBJECT-TYPE
		SYNTAX	SEQUENCE OF ExtendPortTotalPrevious1DayIntervalEntry
		ACCESS	not-accessible
		STATUS	mandatory
		DESCRIPTION
			"1 Day previous statistics for PortTotal (= all traffic on a port,
			Including PPPoE relayed and PPPoE terminated traffic)
             ALCATEL NOTE:
                 TABLESIZE:  DEP [depending on the value of 
                             dot1dBaseNumPorts.]
                 DESCR:      NA"
		::= { extendStatistics 10 }

	extendPortTotalPrevious1DayIntervalEntry OBJECT-TYPE
		SYNTAX	ExtendPortTotalPrevious1DayIntervalEntry
		ACCESS	not-accessible
		STATUS	mandatory
		DESCRIPTION
			"Table entry for the previous 1 day statistics counters."
		INDEX   { dot1dBasePort, extendPortTotalPrevious1DayIntervalNumber }
		::= { extendPortTotalPrevious1DayIntervalTable	 1 }

	 ExtendPortTotalPrevious1DayIntervalEntry ::=
		SEQUENCE {
				extendPortTotalPrevious1DayIntervalNumber
					INTEGER,
				extendPortTotalPrevious1DayTimeMeasured
					INTEGER,
				extendPortTotalPrevious1DayUpFwdFrameCounter
					OCTET STRING (SIZE (8)),
				extendPortTotalPrevious1DayUpFwdByteCounter
					OCTET STRING (SIZE (8)),
				extendPortTotalPrevious1DayDnFwdFrameCounter
					OCTET STRING (SIZE (8)),
				extendPortTotalPrevious1DayDnFwdByteCounter
					OCTET STRING (SIZE (8)),
				extendPortTotalPrevious1DayUpDiscFrameCounter
					OCTET STRING (SIZE (8)),
				extendPortTotalPrevious1DayUpDiscByteCounter
					OCTET STRING (SIZE (8)),
				extendPortTotalPrevious1DayDnDiscFrameCounter
					OCTET STRING (SIZE (8)),
				extendPortTotalPrevious1DayDnDiscByteCounter
					OCTET STRING (SIZE (8))
			}

	extendPortTotalPrevious1DayIntervalNumber OBJECT-TYPE
		SYNTAX	INTEGER
		ACCESS  	not-accessible
		STATUS	mandatory
		DESCRIPTION
			"Previous interval reference
             ALCATEL NOTE:
                 ACCESS:     NA       USAGE:      NA
                 PERSIST:    NO       INSRVMOD:   NO
                 RANGE:      NA       DEFVALUE:   NA
                 UNITS:      NA       SPARSE:     NA
                 DESCR:      NA"
		::= { extendPortTotalPrevious1DayIntervalEntry 1 }
	
	extendPortTotalPrevious1DayTimeMeasured OBJECT-TYPE
		SYNTAX	INTEGER
		ACCESS  	read-only
		STATUS	mandatory
		DESCRIPTION
			"Measured time in interval (seconds)
             ALCATEL NOTE:
                 ACCESS:     NA       USAGE:      NA
                 PERSIST:    NO       INSRVMOD:   NO
                 RANGE:      NA       DEFVALUE:   0
                 UNITS:      seconds  SPARSE:     NA
                 DESCR:      NA"
		::= { extendPortTotalPrevious1DayIntervalEntry 2 }

	 extendPortTotalPrevious1DayUpFwdFrameCounter OBJECT-TYPE
		SYNTAX	OCTET STRING (SIZE (8))

		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 3 }

	extendPortTotalPrevious1DayUpFwdByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   YES
                 RANGE:      NA       DEFVALUE:   NA
                 UNITS:      NA       SPARSE:     NA
                 DESCR:      NA"
		::= { extendPortTotalPrevious1DayIntervalEntry 4 }

	extendPortTotalPrevious1DayDnFwdFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 5 }

	extendPortTotalPrevious1DayDnFwdByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 6 }

	extendPortTotalPrevious1DayUpDiscFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"

		::= { extendPortTotalPrevious1DayIntervalEntry 7 }

	extendPortTotalPrevious1DayUpDiscByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 8 }

	extendPortTotalPrevious1DayDnDiscFrameCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 9 }

	extendPortTotalPrevious1DayDnDiscByteCounter OBJECT-TYPE
		SYNTAX	OCTET STRING (SIZE (8))
		ACCESS  	read-only
		STATUS	mandatory
		DESCRIPTION
			"Definition as for current 1 day counters but for a previous interval
             ALCATEL NOTE:
                 ACCESS:     NA       USAGE:      NA
                 PERSIST:    NO       INSRVMOD:   NO
                 RANGE:      NA       DEFVALUE:   0
                 UNITS:      NA       SPARSE:     NA
                 DESCR:      NA"
		::= { extendPortTotalPrevious1DayIntervalEntry 10 }

extendPortVlanTroubleShootingSummaryTable    OBJECT-TYPE
      SYNTAX   SEQUENCE OF ExtendPortVlanTroubleShootingSummaryEntry    
      ACCESS   not-accessible
      STATUS   mandatory
      DESCRIPTION
         "Troubleshooting vlanport summary counters table. An entry exists for each static vlanport on boards that support vlanport troubleshooting. 
             ALCATEL NOTE:
                 TABLESIZE:  DEP [depending on the size of 
                             extendPortVlanAssociationTable.]
                 DESCR:      NA"
      ::= { extendStatistics 13 }

   extendPortVlanTroubleShootingSummaryEntry OBJECT-TYPE
      SYNTAX   ExtendPortVlanTroubleShootingSummaryEntry
      ACCESS   not-accessible
      STATUS   mandatory
      DESCRIPTION
         "Table entry for the troubleshooting summary counters. 
The ifIndex equals the extendPortVlanIfIndex. All counters show the value since the last counter reset."
      INDEX   { ifIndex }
      ::= { extendPortVlanTroubleShootingSummaryTable    1 }

    ExtendPortVlanTroubleShootingSummaryEntry ::=
      SEQUENCE {
            extendPortVlanUpFwdFrameCounter
               Counter,
            extendPortVlanUpDiscFrameCounter
               Counter,
            extendPortVlanDnFwdFrameCounter
               Counter,
            extendPortVlanDnDiscFrameCounter
               Counter,
	    extendPortVlanUpBcastFwdFrameCounter
               Counter,
            extendPortVlanUpUcastFwdFrameCounter
               Counter,
            extendPortVlanDnBcastFwdFrameCounter
               Counter,
            extendPortVlanDnUcastFwdFrameCounter
               Counter
                }

extendPortVlanUpFwdFrameCounter OBJECT-TYPE
      SYNTAX   Counter
      ACCESS     read-only
      STATUS   mandatory
      DESCRIPTION
         "The number of frames received from the user side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 1 }

extendPortVlanUpDiscFrameCounter OBJECT-TYPE
      SYNTAX   Counter
      ACCESS     read-only
      STATUS   mandatory
      DESCRIPTION
         "The number of frames received from the user side that are discarded for any reason related to the vlanport checks, including policing.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 2 }

extendPortVlanDnFwdFrameCounter OBJECT-TYPE
      SYNTAX   Counter
      ACCESS     read-only
      STATUS   mandatory
      DESCRIPTION
         "The number of frames received from the network side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 3 }

extendPortVlanDnDiscFrameCounter OBJECT-TYPE
      SYNTAX   Counter
      ACCESS     read-only
      STATUS   mandatory
      DESCRIPTION
         "The number of frames received from the network side that are discarded.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 4 }
extendPortVlanUpBcastFwdFrameCounter OBJECT-TYPE
      SYNTAX   Counter
      ACCESS     read-only
      STATUS   mandatory
      DESCRIPTION
         "The number of broadcast frames received from the user side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 5 }

 extendPortVlanUpUcastFwdFrameCounter OBJECT-TYPE
      SYNTAX   Counter
      ACCESS   read-only
      STATUS   mandatory
      DESCRIPTION
         "The number of unicast frames received from the user side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 6 }

extendPortVlanDnBcastFwdFrameCounter OBJECT-TYPE
      SYNTAX   Counter
      ACCESS     read-only
      STATUS   mandatory
      DESCRIPTION
         "The number of broadcast frames received from the network side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 7 }

extendPortVlanDnUcastFwdFrameCounter OBJECT-TYPE
      SYNTAX   Counter
      ACCESS     read-only
      STATUS   mandatory
      DESCRIPTION
         "The number of unicast frames received from the network side that are successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingSummaryEntry 8 }

extendPortVlanTroubleShootingExtensiveTable    OBJECT-TYPE
      SYNTAX   SEQUENCE OF ExtendPortVlanTroubleShootingExtensiveEntry    
      ACCESS   not-accessible
      STATUS   mandatory
      DESCRIPTION
         "Troubleshooting vlanport extensive counters table.
An entry exists for each static vlanport on each line in the TroubleShootingObservationTable which table defined in troubleshooting MIB.
             ALCATEL NOTE:
                 TABLESIZE:  DEP [(the value of 
                             Max static vlanport per line) *(the max lim number of the system).]
                 DESCR:      NA"
      ::= { extendStatistics 14 }

   extendPortVlanTroubleShootingExtensiveEntry OBJECT-TYPE
      SYNTAX   ExtendPortVlanTroubleShootingExtensiveEntry
      ACCESS   not-accessible
      STATUS   mandatory
      DESCRIPTION
         "Table entry for the troubleshooting detail counters.
The ifIndex equals the extendPortVlanIfIndex. All counters show the value since the last counter reset."
      INDEX   { ifIndex }
      ::= { extendPortVlanTroubleShootingExtensiveTable    1 }

    ExtendPortVlanTroubleShootingExtensiveEntry ::=
      SEQUENCE {
            extendPortVlanUpInvDaSaDiscFrameCounter
               Counter,
            extendPortVlanUpMacPortLimitExcDiscFrameCounter
               Counter,
            extendPortVlanUpMacFdbLimitExcDiscFrameCounter
               Counter,
            extendPortVlanUpInvProtDiscFrameCounter
               Counter,
            extendPortVlanUpIPSpoofingDiscFrameCounter
               Counter,
            extendPortVlanUpAclDiscFrameCounter
               Counter,
            extendPortVlanUpPolicerDiscFrameCounter
               Counter,
            extendPortVlanUpQueueDiscFrameCounter
               Counter,            
            extendPortVlanDnMultiFwdFrameCounter
               Counter,
            extendPortVlanDnNonMultiFwdFrameCounter
               Counter,
            extendPortVlanDnMultiDiscFrameCounter
               Counter,
            extendPortVlanDnNonMultiDiscFrameCounter
               Counter,
            extendPortVlanDnAclDiscFrameCounter
               Counter,
            extendPortVlanDnPolicerDiscFrameCounter
               Counter,
            extendPortVlanDnQueueDiscFrameCounter
               Counter,
            extendPortVlanUpIPv6SpoofingDiscFrameCounter
               Counter
                }

extendPortVlanUpInvDaSaDiscFrameCounter OBJECT-TYPE
      SYNTAX   Counter
      ACCESS     read-only
      STATUS   mandatory
      DESCRIPTION
         "The number of frames received from the user side which have an invalid destination or source MAC address. It applies to L2 and L3 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 1 }

extendPortVlanUpMacPortLimitExcDiscFrameCounter OBJECT-TYPE
      SYNTAX   Counter
      ACCESS     read-only
      STATUS   mandatory
      DESCRIPTION
         " The number of frames received from the user side that are discarded because the maximum number of MAC addresses per port is exceeded or because MAC learning is disabled on the port. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 2 }

extendPortVlanUpMacFdbLimitExcDiscFrameCounter OBJECT-TYPE
      SYNTAX   Counter
      ACCESS     read-only
      STATUS   mandatory
      DESCRIPTION
         "The number of frames received from the user side that are discarded because the max mac number of FDB is reached. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 3 }

extendPortVlanUpInvProtDiscFrameCounter OBJECT-TYPE
      SYNTAX   Counter
      ACCESS     read-only
      STATUS   mandatory
      DESCRIPTION
         "The number of frames received from the user side with an invalid protocol. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 4 }

extendPortVlanUpIPSpoofingDiscFrameCounter OBJECT-TYPE
      SYNTAX   Counter
      ACCESS     read-only
      STATUS   mandatory
      DESCRIPTION
         "The number of frames received from the user side with an IPv4 address not matching the assigned IP address. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 5 }

extendPortVlanUpAclDiscFrameCounter OBJECT-TYPE
      SYNTAX   Counter
      ACCESS     read-only
      STATUS   mandatory
      DESCRIPTION
         "The number of frames received from the user side that are discarded by an Acess Control List. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 6 }

extendPortVlanUpPolicerDiscFrameCounter OBJECT-TYPE
      SYNTAX   Counter
      ACCESS     read-only
      STATUS   mandatory
      DESCRIPTION
         " The number of frames received from the user side that are discarded due to policing. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 7 }

extendPortVlanUpQueueDiscFrameCounter OBJECT-TYPE
      SYNTAX   Counter
      ACCESS     read-only
      STATUS   mandatory
      DESCRIPTION
         " The number of frames received from the user side that are discarded due to the uplink queues overflow. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 8 }

extendPortVlanDnMultiFwdFrameCounter OBJECT-TYPE
      SYNTAX   Counter
      ACCESS     read-only
      STATUS   mandatory
      DESCRIPTION
         " The number of multicast frames received from the network side and successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 9 }

extendPortVlanDnNonMultiFwdFrameCounter OBJECT-TYPE
      SYNTAX   Counter
      ACCESS     read-only
      STATUS   mandatory
      DESCRIPTION
         " The number of unicast and broadcast frames received from the network side and successfully forwarded by the L2-forwarding engine.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 10 }

extendPortVlanDnMultiDiscFrameCounter OBJECT-TYPE
      SYNTAX   Counter
      ACCESS     read-only
      STATUS   mandatory
      DESCRIPTION
         "The discarded number of multicast frames received from the network side.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 11 }

extendPortVlanDnNonMultiDiscFrameCounter OBJECT-TYPE
      SYNTAX   Counter
      ACCESS     read-only
      STATUS   mandatory
      DESCRIPTION
         "The number of unicast and broadcast frames received from the network side.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 12 }

extendPortVlanDnAclDiscFrameCounter OBJECT-TYPE
      SYNTAX   Counter
      ACCESS     read-only
      STATUS   mandatory
      DESCRIPTION
         " The number of frames received from the network side that are discarded by an Access Control List. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 13 }

extendPortVlanDnPolicerDiscFrameCounter OBJECT-TYPE
      SYNTAX   Counter
      ACCESS     read-only
      STATUS   mandatory
      DESCRIPTION
         " The number of frames received from the network side that is discarded due to policing. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 14 }

extendPortVlanDnQueueDiscFrameCounter OBJECT-TYPE
      SYNTAX   Counter
      ACCESS     read-only
      STATUS   mandatory
      DESCRIPTION
         "The number of frames received from the network side, forwarded to the Vlan Port and then discarded because of queue overflow. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 15 }

extendPortVlanUpIPv6SpoofingDiscFrameCounter OBJECT-TYPE
      SYNTAX   Counter
      ACCESS   read-only
      STATUS   mandatory
      DESCRIPTION
         "The number of frames received from the user side with an IPv6 address not matching the assigned IP address. It applies to L2 forwarding.
             ALCATEL NOTE:
                 ACCESS:     NA       USAGE:      NA
                 PERSIST:    NO       INSRVMOD:   NO
                 RANGE:      NA       DEFVALUE:   NA
                 UNITS:      frames   SPARSE:     NA
                 DESCR:      NA"
      ::= { extendPortVlanTroubleShootingExtensiveEntry 16 }

    extendPortVlanDot1pTrafficCounterTable    OBJECT-TYPE
      SYNTAX   SEQUENCE OF ExtendPortVlanDot1pTrafficCounterEntry    
      ACCESS   not-accessible
      STATUS   mandatory
      DESCRIPTION
         "Vlanport p-bit traffic counters table.
An entry exists for each traffic flow identified by a p-bit value or range on one vlanport.
             
                 TABLESIZE:  DEP [(the value of 
                             Max p-bit traffic counter pair per line) * (the max line number of FD L3 lim) * (the max lim number of the system).]
                 DESCR:      NA"
      ::= { extendStatistics 15 }

   extendPortVlanDot1pTrafficCounterEntry OBJECT-TYPE
      SYNTAX   ExtendPortVlanDot1pTrafficCounterEntry
      ACCESS   not-accessible
      STATUS   mandatory
      DESCRIPTION
         "Table entry for the p-bit traffic counters.
The ifIndex equals the extendPortVlanIfIndex. All counters show the value since the last system reset."
      INDEX   { ifIndex,extendPortVlanDot1pMinValue, extendPortVlanDot1pMaxValue  }
      ::= { extendPortVlanDot1pTrafficCounterTable    1 }

    ExtendPortVlanDot1pTrafficCounterEntry ::=
      SEQUENCE {
            extendPortVlanDot1pMinValue
INTEGER,
            extendPortVlanDot1pMaxValue
INTEGER,
            extendPortVlanDot1pTrafficUpFwdByteCounter
               OCTET STRING (SIZE (8)),
            extendPortVlanDot1pTrafficDnFwdByteCounter
               OCTET STRING (SIZE (8)),
            extendPortVlanDot1pTrafficCounterRowStatus
               RowStatus
                }

   extendPortVlanDot1pMinValue OBJECT-TYPE
      SYNTAX   INTEGER(0..7)
      ACCESS     not-accessible
      STATUS   mandatory
      DESCRIPTION
         "The minimum value in specified p-bit range.
             ALCATEL NOTE:
                 ACCESS:     NA       USAGE:      NA
                 PERSIST:    YES       INSRVMOD:   NO
                 RANGE:      0..7     DEFVALUE:   NA
                 UNITS:      NA  SPARSE:     NA
                 DESCR:      NA"
      ::= { extendPortVlanDot1pTrafficCounterEntry 1 }

extendPortVlanDot1pMaxValue OBJECT-TYPE
      SYNTAX   INTEGER(0..7)
      ACCESS     not-accessible
      STATUS   mandatory
      DESCRIPTION
         "The maximum value in specified p-bit range.
             ALCATEL NOTE:
                 ACCESS:     NA       USAGE:      NA
                 PERSIST:    YES       INSRVMOD:   NO
                 RANGE:      0..7     DEFVALUE:   NA
                 UNITS:      NA  SPARSE:     NA
                 DESCR:      NA"
      ::= { extendPortVlanDot1pTrafficCounterEntry 2 }

extendPortVlanDot1pTrafficUpFwdByteCounter OBJECT-TYPE
      SYNTAX   OCTET STRING (SIZE (8))
      ACCESS     read-only
      STATUS   mandatory
      DESCRIPTION
         "All forwarded  bytes in upstream direction per VLAN on a bridge 
         port with traffic flow indentification in specified p-bit range.
             ALCATEL NOTE:
                 ACCESS:     NA       USAGE:      NA
                 PERSIST:    NO      INSRVMOD:   NO
                 RANGE:      NA       DEFVALUE:   NA
                 UNITS:      bytes    SPARSE:     NA
                 DESCR:      NA"
      ::= { extendPortVlanDot1pTrafficCounterEntry 3 }

extendPortVlanDot1pTrafficDnFwdByteCounter OBJECT-TYPE
      SYNTAX   OCTET STRING  (SIZE (8))
      ACCESS     read-only
      STATUS   mandatory
      DESCRIPTION
         "All forwarded  bytes in downstream direction per VLAN on a bridge 
         port with traffic flow indentification in specified p-bit range.
             ALCATEL NOTE:
                 ACCESS:     NA       USAGE:      NA
                 PERSIST:    NO       INSRVMOD:   NO
                 RANGE:      NA       DEFVALUE:   NA
                 UNITS:      bytes    SPARSE:     NA
                 DESCR:      NA"
      ::= { extendPortVlanDot1pTrafficCounterEntry 4 }

extendPortVlanDot1pTrafficCounterRowStatus OBJECT-TYPE
    SYNTAX      RowStatus
    ACCESS  	   read-write
    STATUS      mandatory
    DESCRIPTION
        "This object indicates the status of this entry.
        ALCATEL NOTE:
            ACCESS:     RO       USAGE:      NA
            PERSIST:    YES      INSRVMOD:   NO
            RANGE:      1,4,6        DEFVALUE:  NA 
            UNITS:      NA       SPARSE:     NA
            DESCR:      NA " 
    ::= { extendPortVlanDot1pTrafficCounterEntry 5 }

systemVMacAddressFormat        OBJECT IDENTIFIER ::= { plimEthernet 11 }

extendVMacValueofDSLAMId OBJECT-TYPE
SYNTAX  INTEGER
ACCESS  read-write
STATUS  mandatory
DESCRIPTION
      "The object specifies the value of the DSLAM Id. This value 
      must be unique DSLAM Id within an EMAN connected to the same IP edges. 
      When the value is 0, it implies that the object has not been 
      set yet and vMAC could not be enabled on any VLAN. The value
      0 cannot be configured; it is a factory default value only.
      For CFM, this field must be configured to ensure the uniqueness 
      of the MP MAC address across the network with multiple DSLAMs.
ALCATEL NOTE:
ACCESS:     RW       USAGE:      OPT
PERSIST:    YES      INSRVMOD:   YES
            RANGE:      0..8191  DEFVALUE:   0
UNITS:      NA       SPARSE:     NA
DESCR:      NA"
             DEFVAL { 0 }
::= { systemVMacAddressFormat 6 }

END
