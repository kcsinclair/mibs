-- orig ASAM_SYSTEM_MIB

SYSTEM-MIB DEFINITIONS ::= BEGIN

   IMPORTS asam FROM SYSTEM-MIB
           Counter, Gauge  FROM RFC1155-SMI  
           OBJECT-TYPE   FROM RFC-1212 
           EqptSlotIndex FROM ASAM-EQUIP-MIB
	   	
           MacAddress     FROM BRIDGE-MIB
           NetworkTimeInSeconds, NetworkTimeInMiliSeconds FROM ASAM-TC-MIB

   ;

   asamSystemMIB            OBJECT IDENTIFIER ::= { asam 9 }

   asamSysBootpInfo         OBJECT IDENTIFIER ::= { asamSystemMIB 2 }

   asamSystemMigration      OBJECT IDENTIFIER ::= { asamSystemMIB 11 }

   asamSystemClockSelect    OBJECT IDENTIFIER ::= { asamSystemMIB 12 }

   asamSystemLicenseMgmt    OBJECT IDENTIFIER ::= { asamSystemMIB 17 }

   asamSysMacAdresses       OBJECT IDENTIFIER ::= { asamSystemMIB 22 }

   asamCraftLogin           OBJECT IDENTIFIER ::= { asamSystemMIB 25 }

   asamAccessLoopIdSyntax   OBJECT IDENTIFIER ::= { asamSystemMIB 26 }

   environmentMonitorRelay  OBJECT IDENTIFIER ::= { asamSystemMIB 27 }

   swVersion                OBJECT IDENTIFIER ::= { asamSystemMIB 28 }

   systemMonitor            OBJECT IDENTIFIER ::= { asamSystemMIB 29 }

   asamSystemIpAtmVcVpi OBJECT-TYPE
      SYNTAX INTEGER (0..4095)
      ACCESS read-write
      STATUS mandatory
      DESCRIPTION
         "To issue a BOOTP request over an ATM connection on the network
          interface, a PVC must be defined.
          This is the VPI value for that PVC.

          ALCATEL NOTE:
             SUPPORT: NO   INSRVMOD: YES  RANGE: 0..4095
             PERSIST: YES  DEFVALUE: 0    UNITS: -"
      ::= { asamSysBootpInfo 1 }

   asamSystemIpAtmVcVci OBJECT-TYPE
      SYNTAX INTEGER (0..65535)
      ACCESS read-write
      STATUS mandatory
      DESCRIPTION
         "To issue a BOOTP request over an ATM connection on the network
          interface, a PVC must be defined.
          This is the VCI value for that PVC.

          ALCATEL NOTE:
             SUPPORT: NO    INSRVMOD: YES   RANGE: 0..65535
             PERSIST: YES   DEFVALUE: 32    UNITS: -"
      ::= { asamSysBootpInfo 2 }

   asamSystemID OBJECT-TYPE
      SYNTAX OCTET STRING(SIZE(0..64))
      ACCESS read-write
      STATUS mandatory
      DESCRIPTION
         "The asamSystemID object represents the SID (System ID) of the NE
          and is used to identify the NE.
 
          The System ID may only include printable ASCII characters from '!'
          (33 Decimal, 21 Hex) to '~' (126 Decimal, 7E Hex) inclusive and must
          be unique for each NE in a managed network. 

          ALCATEL NOTE:
             SUPPORT: YES   INSRVMOD: YES   RANGE: See above
             PERSIST: YES   DEFVALUE:       UNITS: -"
      ::= { asamSystemMIB 3 }

   asamSysStatusBitMap OBJECT-TYPE
      SYNTAX INTEGER (1..4294967295)
      ACCESS read-only
      STATUS mandatory
      DESCRIPTION
         "Status bitmap:
          Bit 0: bit 0 is set if and only if none of the other bits is set.
          Bit 1: bit 1 set indicates that persistent data has been lost
                 including data necessary to establish OAM connectivity.
          Bit 2: bit 2 set indicates that persistent data has been lost but
                 not including data necessary to establish OAM connectivity.
          Bit 3: bit 3 set indicates that a power-on reset has occured.  Notice
                 that this also means that all reset-safe data has been lost.
          Bit 4: bit 4 set indicates that a reset other than a power-on reset
                 has occured.
          Bit 5: not used anymore.
          Bit 6: this bit indicates that alarm 'SHub configuration loss' (EQUIP
                 alarm nbr 28) was raised. The purpose of using this bit is to 
                 clear this alarm by using asamSysStatusClearBitMap. 
          Bit 7: this bit indicates that one or several 'xVPS configuration
                 loss' alarms (PlugInUnit2 alarm nbr 11) were raised. 
                 The purpose of using this bit is to clear the alarms by using   
                 asamSysStatusClearBitMap.
          Bit 8: this bit indicates that alarm 'Invalid xVPS Pair Redundancy Data'
                 (LSM Redundancy 131 nbr 2) was raised. The purpose of using this
                 bit is to clear this alarm by using asamSysStatusClearBitMap.
          
          Bit 9 .. 31 : reserved for future extensions.

          ALCATEL NOTE:
             SUPPORT: YES   INSRVMOD: NA   RANGE: 1..4294967295
             PERSIST: YES   DEFVALUE: NA   UNITS: -"
      ::= { asamSystemMIB 4 }

   asamSysStatusClearBitMap OBJECT-TYPE
      SYNTAX INTEGER (1..4294967295)
      ACCESS write-only
      STATUS mandatory
      DESCRIPTION
         "Clear status bitmap:
          In order to be able to clear the status bitmap, e.g. to clear the loss
          of persistent data alarm, this bitmap has to be used by writing a 1 to
          the corresponding bit position.  Bit 0 in the status bitmap cannot be
          cleared in this way.  Therefore, the system will refuse a Set request
          that attempts to set bit 0 in the asamSysStatusClearBitMap.

          ALCATEL NOTE:
             SUPPORT: YES   INSRVMOD: YES   RANGE: 1..4294967295
             PERSIST: NO    DEFVALUE: NA    UNITS: -"
      ::= { asamSystemMIB 5 }

   asamSysStatusSetBitMap OBJECT-TYPE
      SYNTAX INTEGER (1..4294967295)
      ACCESS write-only
      STATUS obsolete
      DESCRIPTION
         "Set status bitmap:
          In order to be able to set the status bitmap, this bitmap has to be
          used by writing a 1 to the corresponding bit position."
      ::= { asamSystemMIB 6 }

   asamAWSnumberOfSets OBJECT-TYPE
      SYNTAX INTEGER
      ACCESS read-write
      STATUS obsolete
      DESCRIPTION
         "Reserved for AWS for synchronisation purposes."
      ::= { asamSystemMIB 7 }

   asamDiskStatusBitMap OBJECT-TYPE
      SYNTAX INTEGER (1..4294967295)
      ACCESS read-write
      STATUS obsolete
      DESCRIPTION
         "Disk status bitmap:
          Bit 0: by setting bit 0, all persistent data is synced (forced) to
                 disk.
          Bit 1: by setting bit 1, the ASAM disk is locked, otherwise the ASAM
                 disk is not locked.  Disk locked means it is impossible to
                 change persistent data  -->  any change by a manager is
                 ignored.
          Bit 2..31 : reserved for future use."
      ::= { asamSystemMIB 8 }

   asamShutdownBitMap OBJECT-TYPE
      SYNTAX INTEGER (0..4294967295)
      ACCESS read-write
      STATUS mandatory
      DESCRIPTION
         "Shutdown bitmap:
          Bit 0: by setting bit 0, the ASAM is prepared for shutdown;
                 it is recommended to do this before extracting the active NT
                 in a simplex system; the bit will be cleared again by
                 extracting and reinserting the NT board.
          Bit 1..31 : reserved for future use.

          ALCATEL NOTE:
             SUPPORT: YES   INSRVMOD: YES   RANGE: 0..4294967295
             PERSIST: NO    DEFVALUE: NA    UNITS: -"
      ::= { asamSystemMIB 9 }

   asamNetworkPosition OBJECT-TYPE
      SYNTAX INTEGER (1..2)
      ACCESS read-write
      STATUS obsolete
      DESCRIPTION
         "Indicates whether the ASAM is a hub-ASAM (1) or a subtending ASAM.
          The default is hub-ASAM."
      ::= { asamSystemMIB 10 }

   asamMigrationStatus OBJECT-TYPE
      SYNTAX INTEGER {
         idle (1),
         migrating (2), 
         rollBackPossible (3),
         forceRollBack (4),
         removeRollBackDatabase (5)
      }
      ACCESS read-write
      STATUS obsolete
      DESCRIPTION
         "The asamMigrationStatus object represent the ASAM's status for what
          concerns its migration capabilities.
          Whereas two of the six values, viz. 'forceRollBack' and
          'removeRollBackDatabase' may be specified in a management protocol
          set operation, three values wil be returned in response to a
          management protocol retrieval operation: 'idle', 'migrating' and
          'rollBackPossible'.  That is, when queried, this object can
          represent only three migration related states of the ASAM: the
          ASAM has no specific migration state, i.e. it is simply operational
          (the object has value 'idle'); the ASAM is busy migrating (the
          object has value 'migrating'); or, the ASAM has recently migrated
          but is still able to rol back to the previous configuration (the
          object has value 'rollBackPossible'.  Whenever a management station
          wishes the ASAM to roll back to its previous configuration it has
          to set this object to value 'forceRollBack'. Setting the object to
          value 'removeRollBackDatabase' informs the ASAM it has not
          support the rollback feature anymore. As a result the ASAM will
          perform clean up operations (e.g. free the roll back database).
             
          Remark: this object is subject to improvement in future releases
          (e.g.  coupling of data and software upgrade/rollback)."
      ::= { asamSystemMigration 1 }

   asamMibVersion OBJECT-TYPE
      SYNTAX OCTET STRING(SIZE(0..28))
      ACCESS read-only
      STATUS mandatory
      DESCRIPTION
         "This variable identifies the version of the management interface
          of the ASAM, i.e. it uniquely identifies the complete set of MIBs
          that together constitute the management interface.  The version
          is a string of the form dccdddddcccc_Vx.x.x.y.z, with d representing
          a decimal digit, c representing an uppercase character, and x, y, z
          representing a decimal number between 0 and 99.

          ALCATEL NOTE:
             SUPPORT: YES   INSRVMOD: NA   RANGE: See above
             PERSIST: NO    DEFVALUE: NA   UNITS: -"
      ::= { asamSystemMIB 13 }

   asamEthernetShapingRate OBJECT-TYPE 
      SYNTAX INTEGER (128..2000) 
      ACCESS read-write 
      STATUS mandatory 
      DESCRIPTION
         "Ethernet frame shaping rate in kbit/s.

          This object is only meaningful for a system with an Ethernet based
          management interface, which is always the case for the ISAM.
          In such a case, the system will shape the outgoing Ethernet frames
          on its management interface to the configured rate.

          ALCATEL NOTE:
             SUPPORT: YES   INSRVMOD: YES   RANGE: 128..2000
             PERSIST: YES   DEFVALUE: 128   UNITS: kbit/s"
      ::= { asamSystemMIB 14 }

   asamSystemInitProgress OBJECT-TYPE
      SYNTAX INTEGER (0..100)
      ACCESS read-only
      STATUS mandatory
      DESCRIPTION
         "Progress of the system initialization indicated as a percentage.

          When the system starts its initialization, it will at first not be
          reachable for SNMP managers.  However, as soon as the initialization
          has progressed far enough, the system will allow Get requests from
          managers on this object.  From then on, managers can poll the value
          of this variable to monitor the progress of the initialization.  Get
          requests on other objects and all Set requests will still be refused
          by the system.  When the progress has reached 100% (initialization
          complete), the system will allow all SNMP access.

          ALCATEL NOTE:
             SUPPORT: YES   INSRVMOD: NA   RANGE: 0..100
             PERSIST: NO    DEFVALUE: NA   UNITS: percent"
      ::= { asamSystemMIB 15 }

   asamPnPEnable OBJECT-TYPE
      SYNTAX INTEGER {
         enabled (1),
         disabled (2) 
      }
      ACCESS  read-write
      STATUS  mandatory
      DESCRIPTION
         "This variable allows the manager to enable/disable the Plug-and-Play
          functionality.  When enabled, the ASAM will, upon installation, start
          up autonomously without intervention of a local craftsman. Otherwise,
          a Craft Terminal is required to provide the necessary configuration
          to the ASAM so that it can start up and set up communication with the
          manager. 

          ALCATEL NOTE:
             SUPPORT: NO    INSRVMOD: YES           RANGE: 1..2
             PERSIST: YES   DEFVALUE: enabled (1)   UNITS: -"
      ::= { asamSystemMIB 16 }

   asamLicenseNumberOfChanges OBJECT-TYPE
      SYNTAX          Counter
      ACCESS          read-only
      STATUS          mandatory
      DESCRIPTION     
         "Wrap around counter for the number of changes of the licenseCounter
          object. The counter is incremented each time the licenseCounter is
          incremented for one of the features. Not persistent data.

          ALCATEL NOTE:
             SUPPORT: YES    INSRVMOD: NA           RANGE: see above
             PERSIST: NO     DEFVALUE: NA           UNITS: -"

     ::=  { asamSystemLicenseMgmt 1 }

   asamSystemLicenseMgmtTable OBJECT-TYPE
      SYNTAX SEQUENCE OF AsamSystemLicenseMgmtEntry
      ACCESS not-accessible
      STATUS mandatory
      DESCRIPTION     
         "The license key management table."
     ::=  { asamSystemLicenseMgmt 2 }

   asamSystemLicenseMgmtEntry OBJECT-TYPE
      SYNTAX AsamSystemLicenseMgmtEntry
      ACCESS not-accessible
      STATUS mandatory
      DESCRIPTION
         "An entry in the asamSystemLicenseMgmtTable."
      INDEX {licenseFeatureIndex}
     ::= {asamSystemLicenseMgmtTable 1}

   AsamSystemLicenseMgmtEntry ::=
      SEQUENCE {
               licenseFeatureIndex INTEGER,
               licenseCounter      INTEGER
               }

   licenseFeatureIndex OBJECT-TYPE
      SYNTAX INTEGER (1..255)
      ACCESS not-accessible
      STATUS mandatory
      DESCRIPTION     
        " This object is used by the asamSystemLicenseMgmtTable to identify a
          row of this table. Each row corresponds to a system feature that is
          monitored to support license management at the manager.
          Following integer values are defined:
            1.   ADSL2+ 
            2.   READSL2
            3.   IGMP 
            4.   BVB
            5.   Annex-M
            6.   IP-Forwarding
            7.   PPPoX Relay 
            8.   PPPoX Termination
            9.   802.1x
            10.  SELT
            11.  reserved
            12.  reserved
            13.  IPOA-CC and IPOA-RB
            14.  UPBO Policing
            15.  XDSL-PerLine-Overrule
            16.  Impulse Noise Sensor
            17.  ADSL1/2 PSD Shaping
            18.  Annex-J
            19.  SyncE Clock source
            20.  2.5 Gbps enabled LT
            21.  NT load sharing + redundancy
            22.  SHDSL cross-talk cancellation
            23.  SRA on VDSL2
            24.  ARQ
	    25.  10 Gbps enabled LT
	    26.  20 Gbps enabled LT
            27.  Gxr
            28.  IPv6 security
            29.  Lawful Intercept

      ALCATEL NOTE:
             SUPPORT: YES    INSRVMOD: NA           RANGE: 1..29
             PERSIST: NO    DEFVALUE: NA           UNITS: -"

      ::= {asamSystemLicenseMgmtEntry 1}
 
   licenseCounter OBJECT-TYPE
      SYNTAX INTEGER
      ACCESS read-only
      STATUS mandatory
      DESCRIPTION     
         "The counter associated with the monitoring of the feature that 
          corresponds to the licenseFeatureIndex value.

          1.  For ADSL2+, the counter indicates the number of XDSL lines for which
          an ADSL2+ operational mode (POTS and/or ISDN) is enabled in its 
          configuration and supported by the LT board and for which 
          the XDSL board is equipped.

          2.  For READSL2, the counter indicates the number of XDSL lines for which 
          a READSL2 operational mode (US mode 1 and/or US mode2) is enabled in
          its configuration and supported by the LT board and for which the 
          XDSL board is equipped.. 

          3. For IGMP, the counter indicates the number of DSL subscriber lines
          for which an IGMP control channel has been configured. 

          4. For BVB, the counter indicates whether BVB is enabled (value 1) or
          Disabled (value 0) in the ASAM and in ISAM this item is reserved. 

          5. For xDSL Annex-M, the counter indicates the number of DSL subscriber
          line which is configured for Annex-M.

          6. For IP-Forwarding, the counter indicates the number of DSL subscriber lines
          configured for Layer-3, such as IP forwarding, RFC1483R/Br with virtual routers,
          Layer-3 QoS features, IP anti-spoofing, IP filters.

          7. For PPPoX Relay, the counter indicates the number of DSL subscriber lines
          for which PPP CrossConnect has been configured.

          8. For PPPoX Termination, the counter indicates the number of DSL subscriber lines
          for which PPPoE termination or PPPoA termination has been configured.

          9. For 802.1x, the counter indicates the number of DSL subscriber lines for
          which 802.1x has been configured as 'enabled'

          10. For SELT, the counter indicates the number of DSL subscriber lines
          configured for G.selt usage and enables the collection of line test
          data.

          11. (reserved)
          12. (reserved)

          13. For IPoA-CC and IPoA-RB, the counter indicates the number of DSL
          subscriber lines which are configured for IPoA cross connect or  IPoA
          with ehanced i-bridge mode.

          14. For UPBO Policing, the counter indicates the number of XDSL lines for
          which a VDSL2 opmode has been selected, for which UPBO Policing pbo
          mode has been enabled in its configuration and supported by the 
          LT board  and for which the XDSL board is equipped.
          The counter is decremented when one
          of these conditions is not met anymore.

          15. For XDSL-Perline-Overrule, the counter indicates the number of XDSL 
          lines for which the per-line overrule data has been used in its 
          configuration and for which the XDSL board is equipped.
          The counter is decremented when one of these conditions is not 
          met anymore.

          16. For Impulse Noise Sensor, the counter indicates the number of XDSL 
          lines for which the Impulse Noise Sensor is enabled (insEnable 
          set to 1 in the Line Conf Table) and for which the XDSL board is 
          equipped. The counter is decremented if the XDSL line is unconfigured
          ( once the INS feature has been enabled, it cannot be disabled anymore
          unless the line is unconfigured ).

          17. For ADSL1/2 PSD Shaping, the counter indicates the number of XDSL 
          lines for which ADSL1 or ADSL2 opMode is enabled with DBPO shaping 
          in its configuration. The counter is incremented when a XDSL line 
          has its operating mode enabled for ADSL1 or ADSL2 and a DPBO profile 
          is assigned to that line (DPBO board profile or a line profile) and 
          the respective board is equipped and planned and supports ADSL1/2 PSD 
          Shaping. 
          The counter is decremented when the DPBO profile (DPBO board or line 
          profile) of a xDSL line is unassigned or a xDSL line has its 
          operating mode disabled for ADSL1 or ADSL2.

          18. For xDSL Annex-J, the counter indicates the number of DSL subscriber
          line which is configured for Annex-J.

          19. For syncE clock source, the counter indicates the number of 
          Synchronous Ethernet ports are configured as a clock source.

          20. For 2.5 Gbps enabled LT, the counter indicates the number of LTs
          that have an uplink that is running at 2.5 Gbps speed.

          21. When NT load sharing + redundancy is supported, the counter indicates
          1, else the counter indicates 0. 

          22. For SHDSL CTC, the counter indicates actual the number of SHDSL subscriber
          lines for which cross-talk cancellation (CTC) is enabled and for which the 
          SHDSL board is equipped.
          In current, this key isn't used, and the counter always keep as zero.

          23. For SRA on VDSL2, the counter indicates the number of XDSL lines 
          for which a VDSL2 opmode has been selected, for which SRA mode has been 
          enabled in its configuration and supported by the LT board and for 
          which the XDSL board is equipped.
          The counter is decremented when one of these conditions is not met 
          anymore. 

          24. For ARQ, the counter indicates the number of XDSL lines for which
          ARQ is enabled in the configuration, supported by the LT board and 
	  for which the XDSL board is equipped.

	  25. For 10 Gbps enabled LT, the counter indicates the number of LTs
          that have an uplink that is running at 10 Gbps speed.

          26. For 20 Gbps enabled LT, the counter indicates the number of LTs
          that have an uplink that is running at 20 Gbps speed.

          27. For Gxr, the counter indicates the number of lines that are
          enabled for resource control via Diameter Gxr interface.
 
          28. For IPv6 security, the counter indicates the number of access lines 
          (DSL, Ethernet or ONT UNI) where one or more IPv6 security features are activated.

          28. For IPv6 security, the counter indicates the number of access lines 
          (DSL, Ethernet or ONT UNI) where one or more IPv6 security features are activated.
  
          29. For Higig NT, the counter indicates whether lawful intercept is
          enabled (value 1) or Disabled (value 0).

          ALCATEL NOTE:
             SUPPORT: YES    INSRVMOD: NA           RANGE: see above
             PERSIST: NO     DEFVALUE: NA           UNITS: -"

     ::= {asamSystemLicenseMgmtEntry 2}

   systemMaxLtLinkSpeed   OBJECT-TYPE
      SYNTAX INTEGER 
      { 
        onegbps(1), 
        twodot5gbps (2),
	tengbps(10),
	twentygbps(20) 
        }
      ACCESS read-write
      STATUS mandatory
      DESCRIPTION 
      "An enum indicating high capacity is enabled. Applicable for high capacity NT's.
       ALCATEL NOTE:
           SUPPORT: YES    INSRVMOD: NO           RANGE: 1,2,10 or 20
           PERSIST: YES    DEFVALUE: onegbps      UNITS: NA"

      ::= { asamSystemLicenseMgmt 3 }

   systemMac OBJECT-TYPE
      SYNTAX OCTET STRING(SIZE(6))
      ACCESS read-write
      STATUS mandatory
      DESCRIPTION
         "Specifies MAC address of the LANX interface(100baseT)  of the NT
          This field should/must only be modified when the shelf does not
          support the SMAS functionality.

          ALCATEL NOTE:
             SUPPORT: YES   INSRVMOD: NA    RANGE: See above
             PERSIST: YES   DEFVALUE: NA    UNITS: -"

      ::= { asamSysMacAdresses 1 }

   lanxBaseMac OBJECT-TYPE
      SYNTAX OCTET STRING(SIZE(6))
      ACCESS read-write
      STATUS mandatory
      DESCRIPTION
          "Identifies the LANX MAC start adress. This field should/must only be
           modified when the shelf does not support the SMAS functionality.

             SUPPORT: YES   INSRVMOD: NA    RANGE: See above
             PERSIST: YES   DEFVALUE: NA    UNITS: -"
      ::= { asamSysMacAdresses 2 }  

   lanxRangeMac OBJECT-TYPE     
      SYNTAX INTEGER (0..65535)
      ACCESS read-write     
      STATUS mandatory     
      DESCRIPTION 
         "Specifies the range of MAC adresses on LANX. The LANX MAC address
          range is currently equal to 24(number of LANX interfaces). This field
          should/must only be modified when the shelf does not support the SMAS
          functionality.

             SUPPORT: YES   INSRVMOD: NA    RANGE: 0..65535
             PERSIST: YES   DEFVALUE: 24    UNITS: -"  
      ::= { asamSysMacAdresses 3 }

   outbandManMac OBJECT-TYPE
      SYNTAX OCTET STRING(SIZE(6))
      ACCESS read-write
      STATUS mandatory
      DESCRIPTION
          "Specifies Outband Management MACAddress. This field
          should/must only be modified when the shelf does not support the SMAS
          functionality.

             SUPPORT: YES   INSRVMOD: NA    RANGE: See above
             PERSIST: YES   DEFVALUE: NA    UNITS: -"
      ::= { asamSysMacAdresses 4 }

   asamSuperuserAuthByRadius OBJECT-TYPE
      SYNTAX INTEGER {
        enabled (1),
        disabled (2)
      }
      ACCESS read-write
      STATUS mandatory
      DESCRIPTION
         "The TL1/CLI user ID SUPERUSER/isadmin is optionally authenticated by
         RADIUS based on this object. When disabled, SUPERUSER/isadmin is always
         authenticated by the local user database. When enabled, SUPERUSER/
         isadminauthentication is initially attempted with RADIUS, but the 
         authentication will fall back to the local TL1/CLI user database, if 
         all RADIUS servers are disabled, or the RADIUS servers are not 
         responding successfully to the authentication request.

            ALCATEL NOTE:
              SUPPORT: YES
              PERSIST: YES
              INSRVMOD: NA
              RANGE: 1..2
              DEFVALUE: 2
              UNITS: NA"
              DEFVAL { disabled }
      ::= { asamSystemMIB 20 }

   asamCraftLoginStatus  OBJECT-TYPE
      SYNTAX INTEGER 
      ACCESS read-only
      STATUS mandatory
      DESCRIPTION
          "Specifies whether user has been logged in or not
          1-user logged in
          0-no user logged in.
      
             SUPPORT: YES   INSRVMOD: NA    RANGE: See above
             PERSIST: YES   DEFVALUE: NA    UNITS: -"
      ::= { asamCraftLogin 1 }

   asamPortNumberingMethodSystem OBJECT-TYPE
      SYNTAX INTEGER {
         logicalSlotId  (1),
         positionBasedSlotId (2),
         typeBasedSlotId (3),
         legacyPositionBasedSlotId (4)
      }
      ACCESS read-write
      STATUS mandatory
      DESCRIPTION
         "This object defines the Line ID format at the system level.
         logicalSlotId (1) is a numbering method defined for equipment
         identification in the MIB. 
         positionBasedSlotId (2) numbers all boards from left to rightor 
         from bottom to top starting from 1.
         typeBasedSlotId (3) numbers -per slot-type- as indicated on 
         the shelf, in case there is no indication on the shelf it numbers 
         -per slot-type- from left to right or from bottom to top starting 
         with 1.
         legacyPositionBasedSlotId (4) is identical to position-based 
         numbering except for aram-b/d where the numbering corresponds with 
         the logicalSlotId based numbering plus 1.

        ALCATEL NOTE:
              SUPPORT: YES
              PERSIST: YES
              INSRVMOD: NA
              RANGE: see above
              DEFVALUE: 1
              UNITS: NA"
      ::= { asamAccessLoopIdSyntax 1 }

   asamAccessLoopAtmBasedDslSyntax OBJECT-TYPE
      SYNTAX OCTET STRING(SIZE(0..64))
      ACCESS read-write
      STATUS mandatory
      DESCRIPTION
         "This variable defines the syntax for generating a loop id 
          for ATM based DSL lines terminated by DSL LT.
          It is a string to define a specified format at system level. 
          ALCATEL NOTE:
             SUPPORT: YES   INSRVMOD: YES  RANGE: See above
             PERSIST: YES    DEFVALUE:      UNITS: -"
      ::= { asamAccessLoopIdSyntax 3 }

   asamAccessLoopEthBasedDslSyntax OBJECT-TYPE
      SYNTAX OCTET STRING(SIZE(0..64))
      ACCESS read-write
      STATUS mandatory
      DESCRIPTION
         "This variable defines the syntax for generating a loop id 
          for Ethernet based DSL lines terminated by DSL LT and
	        for Ethernet lines terminated by Ethernet LT.
          It is a string to define  a specified format at system level.
          ALCATEL NOTE:
             SUPPORT: YES   INSRVMOD: YES  RANGE: See above
             PERSIST: YES    DEFVALUE:      UNITS: -"
      ::= { asamAccessLoopIdSyntax 4 }

   asamAccessLoopEthBasedPonSyntax OBJECT-TYPE
      SYNTAX OCTET STRING(SIZE(0..64))
      ACCESS read-write
      STATUS mandatory
      DESCRIPTION
         "This variable defines the syntax for generating a loop id 
          for Ethernet based DSL line terminated by ONTs, and 
	        for Ethernet lines terminated by ONTs.
	        ONTs are connected via a GPON transmission technology to the system.
          It is a string to define  a specified format at the system level.
          ALCATEL NOTE:
             SUPPORT: YES   INSRVMOD: YES  RANGE: See above
             PERSIST: YES    DEFVALUE:      UNITS: -"
      ::= { asamAccessLoopIdSyntax 5 }

   asamAccessLoopEthBasedEPonSyntax OBJECT-TYPE
      SYNTAX OCTET STRING(SIZE(0..64))
      ACCESS read-write
      STATUS mandatory
      DESCRIPTION
         "This variable defines the syntax for generating a loop id 
          for Ethernet based DSL line terminated by ONTs, and 
	        for Ethernet lines terminated by ONTs.
	        ONTs are connected via a EPON transmission technology to the system.
          It is a string to define  a specified format at the system level.
          ALCATEL NOTE:
             SUPPORT: YES   INSRVMOD: YES  RANGE: See above
             PERSIST: YES    DEFVALUE:      UNITS: -"
      ::= { asamAccessLoopIdSyntax 6 }

   environmentMonitorRelayMode OBJECT-TYPE
      SYNTAX INTEGER {
         enabled (1),
         disabled (2) 
       }
      ACCESS   read-write
      STATUS   mandatory
      DESCRIPTION
        " This variable allows the manager to enable/disable the environment 
          monitoring relay functionality. When enabled, the environment data 
          will be relayed between monitoring box and supervision server. 
          Otherwise, it will stop the relay.
        ALCATEL NOTE:
             SUPPORT: NO    INSRVMOD: YES           RANGE: 1..2
             PERSIST: YES   DEFVALUE: disable (2)   UNITS: -"
      ::= {environmentMonitorRelay 1}

   swEtsiVersion OBJECT-TYPE

      SYNTAX   OCTET STRING(SIZE(0..50))
      ACCESS   read-only
      STATUS   mandatory
      DESCRIPTION
        " This object holds the Software version for ETSI market. 
          (e.g. R4.1). It will be empty if not supported for ETSI market.
        ALCATEL NOTE:
            ACCESS:      NA           USAGE:       NA
            PERSIST:     NA           INSRVMOD:    NA
            RANGE:       NA           DEFVALUE:    NA
            UNITS:       NA           SPARSE:      NA
            DESCR:       NA"
    ::= {swVersion 1}

  swAnsiVersion OBJECT-TYPE

     SYNTAX   OCTET STRING(SIZE(0..50))
     ACCESS   read-only
     STATUS   mandatory
     DESCRIPTION
        " This object holds the Software version for ANSI market. 
          (such as FGN4.1.0). It will be empty if not supported for ANSI market.        ALCATEL NOTE:
            ACCESS:      NA           USAGE:       NA
            PERSIST:     NA           INSRVMOD:    NA
            RANGE:       NA           DEFVALUE:    NA
            UNITS:       NA           SPARSE:      NA
            DESCR:       NA"
     ::= {swVersion 2}

  cpuLoadTable OBJECT-TYPE
      SYNTAX SEQUENCE OF CpuLoadEntry
      ACCESS not-accessible
      STATUS mandatory
      DESCRIPTION     
         "The CPU load monitor table.
         ALCATEL NOTE:
            TABLESIZE:     max nmbr of slots "
      ::=  { systemMonitor 1 }

   cpuLoadEntry OBJECT-TYPE
      SYNTAX CpuLoadEntry
      ACCESS not-accessible
      STATUS mandatory
      DESCRIPTION
            "An entry in the cpuLoadTable. The index of the entry is slotId.
            An entry represents the CPU load of the board in the slot.
            The CPU load includes detail value and average value respectively.
            The slot can be NT slot or LT slot.
            Row creation : An entry is created by the system when a board 
            is planning
            Row deletion : An entry is deleted by the system when a board 
            is unplanning.
            Index usage : the index is the slot id.
            Note that entries will be presented to the SNMP manager in full
            lexicographical order."
      INDEX { slotId }
      ::= { cpuLoadTable 1}

   CpuLoadEntry ::=
      SEQUENCE {
               slotId           INTEGER (1..65535),
               startMonitorTime NetworkTimeInSeconds,
               cpuLoadDetail    OCTET STRING(SIZE(180)),
               cpuLoadAverage   Gauge,
               operateStatus    INTEGER
               }

   slotId OBJECT-TYPE
      SYNTAX INTEGER (1..65535)
      ACCESS read-only
      STATUS mandatory
      DESCRIPTION     
          " the slotId has the same value as eqptSlotId of ASAM-EQUIP-MIB.   
        ALCATEL NOTE:
            ACCESS:      NA            USAGE:       NA
            PERSIST:     NO            INSRVMOD:    NA
            RANGE:       NA            DEFVALUE:    0
            UNITS:       NA            SPARSE:      NO
            DESCR:       NA"
     ::= { cpuLoadEntry 1}
   
   startMonitorTime OBJECT-TYPE
      SYNTAX NetworkTimeInSeconds
      ACCESS read-only
      STATUS mandatory
      DESCRIPTION     
          "The start timestamp of CPU load monitor is the network 
          time in seconds.
          It indicates the start time of last 3 minutes or less monitoring.
          The startMonitorTime is the time at which the last CPU load
          detail & average was computed - reset every second after 
          3 minutes from monitor start time.
          The startMonitorTime is the monitor task start time if the interval 
          time between start and stop is less than 3 minutes. The 
          startMonitorTime is (stop monitor task time - 3 minutes) if the 
          interval time between start and stop is larger than 3 minutes.  
        ALCATEL NOTE:
            ACCESS:      NA            USAGE:       NA
            PERSIST:     NO            INSRVMOD:    NA
            RANGE:       NA            DEFVALUE:    0
            UNITS:       NA            SPARSE:      NO
            DESCR:       NA"
     ::= { cpuLoadEntry 2}

   cpuLoadDetail OBJECT-TYPE
      SYNTAX OCTET STRING(SIZE(180))
      ACCESS read-only
      STATUS mandatory
      DESCRIPTION     
            " The cpuLoadDetail object represents the CPU load percent value
            (x100%) in detail for 180 measurement points.
            The length of this object is always 180 octets. One octet represents
            one CPU load value of one measurement. One measurement generates one
            sample value. The measure time of a sample is a second. The maximum
            measure time is 180 seconds. So the maximum number of samples is 180.
            The interval time between start and stop (or show) operation may be
            less 180 seconds. So the sample number may be less than 180. The left
            octet will be padded with H'FF if the sample number is less than 180
            and keeps the octet length always 180.
            The type of cpuLoadDetail variable is OCTET STRING. Each octet can
            be intepreted as a double-digit (binary ecoded value) integer.
            The cpuLoadDetail indicates 180 double-digit (binary value) integers.
            Each integer indicates the CPU load percent value of a measurement.
            The order of measurement value is:
            In case of the measurement time is >= 180 seconds, only the last 180
            samples are keeped; the 1st octet is the 1st measurement value of the
            last 180 sample; the 2nd octet is the 2nd measurement value of the
            last 180 sample; the 180th octet is the 180th measurement value of
            the last 180 sample. A wrap around buffer will be used to store the
            measurement values.
            In case of the measurement time is < 180 seconds, the samples are
            less than 180, the 1st octet is the measurement value of 1st sample;
            the 2nd octet is the measurement value of 2nd sample; the left
            octet will be padded with H'FF; so the 180th octet is H'FF.

        ALCATEL NOTE:
            ACCESS:      NA            USAGE:       NA
            PERSIST:     NO            INSRVMOD:    NA
            RANGE:       NA            DEFVALUE:    'FFh'
            UNITS:       NA            SPARSE:      NO
            DESCR:       NA"
     ::= { cpuLoadEntry 3}

  cpuLoadAverage OBJECT-TYPE
      SYNTAX Gauge
      ACCESS read-only
      STATUS mandatory
      DESCRIPTION
         " The average value of CPU load. It is percent value (x100%).
         It is the average of detail CPU load value.
         One sample is generated for each second during CPU load measurement
         time. The maximum measurement time is 180 seconds.
         The maximum sample number is 180.
         cpuLoadAverage is average of all 180 sample values if the monitoring
         time is equal or longer than 180 seconds. It should be the average
         of sample values measured in the time between start monitor and
         stop monitor if the interval time between start and stop is less
         than 180 seconds.
        ALCATEL NOTE:
            ACCESS:      NA            USAGE:       NA
            PERSIST:     NO            INSRVMOD:    NA
            RANGE:       0..100        DEFVALUE:    0
            UNITS:       percentage    SPARSE:      NO
            DESCR:       NA"
     ::= { cpuLoadEntry 4}

   operateStatus OBJECT-TYPE
      SYNTAX INTEGER{
                     start(1),
                     stop(2),
                     proceeding(3),
                     idle(4),                     
                     not-operational(5)
                    }
      ACCESS read-write
      STATUS mandatory
      DESCRIPTION
         "The operate status for start/stop CPU load monitoring operation.
          The maximum measurement time is 180 seconds. 
          One sample is generated for a second.
          The maximum sample number is 180. Only the latest 180 sample values
          are kept. The previous value beyond 180 is overwritten.
          The operator should start monitor firstly, then show the CPU load 
          and stop monitor.
          The <start(1)> and <stop(2)> are for operation (action). The 
          <proceeding(3)>, <idle(4)>, and <not-operational(5)> 
          indicate the states of the monitor.
          -------------------                         ---------------
          | not-operational | --- board planning ---> |    idle     |
          -------------------                         ---------------
          -------------------                         ---------------
          |     idle        | --- start monitor  ---> |  proceeding |
          -------------------                         ---------------
          -------------------                         ---------------
          | proceeding      | --- stop monitor   ---> |    idle     |
          -------------------                         ---------------
          -------------------                           ------------------
          | idle,proceeding | --- board unplanning ---> |not-operational |
          -------------------                           ------------------
        ALCATEL NOTE:
            ACCESS:      NA            USAGE:       NA
            PERSIST:     NO            INSRVMOD:    YES
            RANGE:       NA            DEFVALUE:    finished
            UNITS:       NA            SPARSE:      NO
            DESCR:       NA"
     ::= { cpuLoadEntry 5}

  memUsageTable OBJECT-TYPE
      SYNTAX SEQUENCE OF MemUsageEntry
      ACCESS not-accessible
      STATUS mandatory
      DESCRIPTION
         "The memory usage monitor table."
      ::=  { systemMonitor 2 }

   memUsageEntry OBJECT-TYPE
      SYNTAX MemUsageEntry
      ACCESS not-accessible
      STATUS mandatory
      DESCRIPTION
         "An entry in the memUsageTable. The index of the entry is slotId. 
          An entry represents the memory usage of the board in the slot.
          The memory usage includes total size and used size respectively. 
          The solt can be NT slot or LT slot."
      INDEX { slotId }
      ::= { memUsageTable 1}

   MemUsageEntry ::=
      SEQUENCE {
               totalMemSize     Gauge,
               memAbsoluteUsage Gauge               
               }

   totalMemSize OBJECT-TYPE
      SYNTAX Gauge
      ACCESS read-only
      STATUS mandatory
      DESCRIPTION
         "The total memory size on board. It just indicates the size of 
          total semi and dynamical memory.
          ALCATEL NOTE:
             SUPPORT: YES    INSRVMOD: NO           RANGE: NA
             PERSIST: NO     DEFVALUE: NA           UNITS: Mbyte"
      ::= { memUsageEntry 1}

   memAbsoluteUsage OBJECT-TYPE
      SYNTAX Gauge
      ACCESS read-only
      STATUS mandatory
      DESCRIPTION
         "The used memory size in absolute value. It indicates total used 
          size of semi and dynamical memory.
          ALCATEL NOTE:
             SUPPORT: YES    INSRVMOD: NO           RANGE: NA
             PERSIST: NO     DEFVALUE: NA           UNITS: Mbyte"
      ::= { memUsageEntry 2}

   asamSystemAccessOperatorID OBJECT-TYPE
      SYNTAX INTEGER (0..65535)
      ACCESS read-write
      STATUS mandatory
      DESCRIPTION
         "The Access Operator ID is a unique identifier representing an operator.
          This identifier is randomly generated by ALU, then assigned to an
          operator.

          The identifier is configured at the operator's premises.

          A value of ZERO signifies that an access operator ID has not been 
          configured.  Decimal values 1 to 15 are reserved for future use.

          ALCATEL NOTE:
            ACCESS: NA
            USAGE: NA
            PERSIST: YES
            INSRVMOD: YES
            RANGE: 0..65535
            DEFVALUE: 0
            UNITS: NA
            SPARSE: NA
            DESCR: NA"
      ::= { asamSystemMIB 33 }

   asamSystemActivatedCDE OBJECT-TYPE
      SYNTAX INTEGER (1..4294967295)
      ACCESS read-only
      STATUS mandatory
      DESCRIPTION
         "The Activated CDE is a bitmap listing the CDE features that are active.

          CDE features are activated during system startup only, and are
          based on the configured Access Operator ID.

          ALCATEL NOTE:
            ACCESS: NA
            USAGE: NA
            PERSIST: NA
            INSRVMOD: NA
            RANGE: NA
            DEFVALUE: NA
            UNITS: NA
            SPARSE: NA
            DESCR: NA"
      ::= { asamSystemMIB 34 }

   asamSystemPortAddressingMode OBJECT-TYPE
      SYNTAX INTEGER {
         sequential (1),
         slotBased (2) 
                     }
      ACCESS  read-write
      STATUS  mandatory
      DESCRIPTION
         "This object allows the manager to configure the faceplate port 
          addressing mode used by operators in CLI and TL1. 
          With the mode set to <sequential>, the operator must specify the port
          as a sequential number that span the various cards in the system.
          With the mode set to <slotBased>, the operator must specify the
          ports as a combination of card type, rack/slot, port type 
          and faceplate port number.
          In the current release this object is still read only, in future
          releases the default <sequential> mode for legacy ports and systems
          can be changed to <slotBased>.
          New systems with non-legacy ports (overlapping port numbers, XFPs),
          this object is set to <slotBased> and cannot be changed.
          The default for this object is <sequential> on legacy systems and
          <slotBased> on new systems.
          ALCATEL NOTE:
             SUPPORT: YES   INSRVMOD: YES           RANGE: 1..2
             PERSIST: YES   DEFVALUE: see above     UNITS: -"
      ::= { asamSystemMIB 35 }

    peripheralMgntMacFilterTable OBJECT-TYPE
      SYNTAX SEQUENCE OF PeripheralMgntMacFilterEntry
      ACCESS not-accessible
      STATUS mandatory
      DESCRIPTION
         "The peripheral management mac filter table.

          For enhanced security in remote cabinets, it is possible to restrict
          allowed destination MAC addresses in upstream Ethernet traffic on the
          peripheral port to a white-list of 20 allowed MAC address ranges. 
          
          Each entry of this list consists of an Original manufacturer Unique 
          Identifier (OUI) value, covering the 3 Most Significant Bytes (MSB)
          of the public MAC address.
          
          A begin and end value of a single consecutive range of MAC addresses
          for the above OUI covers at maximum the full 3 Least Significant
          Bytes (LSB) of the public MAC address.

            ALCATEL NOTE:
                 TABLESIZE:  20
                 DESCR:      NA"

      ::=  { asamSystemMIB 36 }

   peripheralMgntMacFilterEntry OBJECT-TYPE
      SYNTAX PeripheralMgntMacFilterEntry
      ACCESS not-accessible
      STATUS mandatory
      DESCRIPTION
         "A filter entry in the management mac filter table.

          Unused filter entries have a start and end MAC address of
          00.00.00.00.00.00, which is the default.

          A special filter entry 7F.FF.FF.00.00.00 - 7F.FF.FF.FF.FF.FF is
          provided to always match with any destination mac address. Adding
          this entry therefore disables the MAC filter.

          Both MAC addresses in a single filter entry always have the same OUI. "
      INDEX { peripheralMgntMacFilterIndex }
      ::= { peripheralMgntMacFilterTable 1}

   PeripheralMgntMacFilterEntry ::=
      SEQUENCE {
               peripheralMgntMacFilterIndex          INTEGER (1..20),
               peripheralMgntMacFilterMacRangeFirst  MacAddress,
               peripheralMgntMacFilterMacRangeLast   MacAddress
               }

   peripheralMgntMacFilterIndex OBJECT-TYPE
      SYNTAX INTEGER (1..20)
      ACCESS not-accessible
      STATUS mandatory
      DESCRIPTION     
         "The index for the peripheralMgntMacFilter table. A maximum of 20 mac
          filters is supported.

      ALCATEL NOTE:
             SUPPORT: YES    INSRVMOD: YES    RANGE: 1..20
             PERSIST: YES    DEFVALUE: NA     UNITS: NA"

      ::= { peripheralMgntMacFilterEntry 1}

   peripheralMgntMacFilterMacRangeFirst OBJECT-TYPE
      SYNTAX MacAddress
      ACCESS read-write
      STATUS mandatory
      DESCRIPTION
         "Specifies the first MAC address of the allowed range.
          Default value 00.00.00.00.00.00

          ALCATEL NOTE:
             SUPPORT: YES   INSRVMOD: NA      RANGE: See above
             PERSIST: YES   DEFVALUE: 0       UNITS: -"

      ::= { peripheralMgntMacFilterEntry 2 }

   peripheralMgntMacFilterMacRangeLast OBJECT-TYPE
      SYNTAX MacAddress      
      ACCESS read-write
      STATUS mandatory
      DESCRIPTION
         "Specifies the last MAC address of the allowed range.
          At least the OUI part should match the OUI of the
          peripheralMgntMacFilterMacRangeFirst MAC address.
          Default value 00.00.00.00.00.00

          ALCATEL NOTE:
             SUPPORT: YES   INSRVMOD: NA      RANGE: See above
             PERSIST: YES   DEFVALUE: 0       UNITS: -"

      ::= { peripheralMgntMacFilterEntry 3 }

asamLiSeparate OBJECT-TYPE
     SYNTAX     INTEGER
                {
                  disabled (0),
                  enabled (1)
                }
     ACCESS     read-write
     STATUS     mandatory
     DESCRIPTION "
            Parameter used to create a separate LI management plane; i.e to
            restrict creation/modification of operators that can access lawful
            intercept data.

           'disabled':
              CLI user with security privileges can:
                -set li-user,li-admin user privileges
                -create a LI view
                -attach a LI view to a usergroup
                -modify a LI view
              SNMP user with view on USM,VACM MIB's can:
                -create a LI view
                        -attach a LI view to a usergroup
                -modify a LI view

           'enabled':
              CLI user with security and li-admin user privilege can:
                -set li-user,li-admin user privileges
                -create a LI view
                -attach a LI view to a usergroup
                -modify a LI view
              SNMP user with view on USM,VACM and IHUB LI ADMIN MIB's can:
                    -create a LI view
                        -attach a LI view to a usergroup
                -modify a LI view

           Notes:
            LI view= view with access on IHUB LI MIB and/or IHUB LI ADMIN MIB
            Before setting this value to enabled make sure that:
            - a CLI user exist with li-admin privilege.
            - a SNMP user exist with access to IHUB LI ADMIN MIB

           ALCATEL NOTE: Applicable to higig NTs
             SUPPORT: YES   INSRVMOD: NA          RANGE: NA
             PERSIST: YES   DEFVALUE: disabled    UNITS: NA
 "
     DEFVAL { disabled }
     ::=  { asamSystemMIB 37 }

END
