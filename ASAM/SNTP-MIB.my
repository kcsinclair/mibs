-- orig SNTP_MIB

SNTP-MIB DEFINITIONS ::= BEGIN

IMPORTS

    IpAddress
        FROM RFC1155-SMI

    OBJECT-TYPE
	FROM RFC-1212
    
    Gauge
         FROM RFC1155-SMI

    NetworkTimeInSeconds, NetworkTimeInMiliSeconds
        FROM ASAM-TC-MIB

    asam
        FROM SYSTEM-MIB;

SNTPOperatingMode		::= INTEGER {
				unicast		(1), 
				anycast 	(2),
				multicast	(3)}

SNTPEnableDisable		::= INTEGER {
				enable		(1),
				disable		(2)}

Uint32 ::= Gauge (0 .. 4294967295)

asamSNTPMIB			OBJECT IDENTIFIER ::=	{ asam 13 }

asamSNTPServerIpAddress OBJECT-TYPE
    SYNTAX   IpAddress
    ACCESS   read-write
    STATUS   mandatory
    DESCRIPTION
        "IpAddress of the SNTP Server.
        ALCATEL NOTE:
            ACCESS:      NA           USAGE:       NA
            PERSIST:     YES          INSRVMOD:    YES
            RANGE:       NA           DEFVALUE:    0.0.0.0
            UNITS:       NA           SPARSE:      NA
            DESCR:       NA"
::= {asamSNTPMIB 1}

asamSNTPServerPort OBJECT-TYPE
    SYNTAX   INTEGER (0..65535)
    ACCESS   read-write
    STATUS   mandatory
    DESCRIPTION
        "Port number of the SNTP Server.
        ALCATEL NOTE:
            ACCESS:      NA           USAGE:       NA
            PERSIST:     YES          INSRVMOD:    YES
            RANGE:       NA           DEFVALUE:    123
            UNITS:       NA           SPARSE:      NA
            DESCR:       NA"
::= {asamSNTPMIB 2}

asamSNTPPollingRate OBJECT-TYPE
    SYNTAX   INTEGER (60..864000)
    ACCESS   read-write
    STATUS   mandatory
    DESCRIPTION
        "The polling period.
        ALCATEL NOTE:
            ACCESS:      NA           USAGE:       NA
            PERSIST:     YES          INSRVMOD:    YES
            RANGE:       NA           DEFVALUE:    3600
            UNITS:       seconds      SPARSE:      NA
            DESCR:       NA"
::=	{asamSNTPMIB 3}

asamSNTPEnableDisable OBJECT-TYPE
    SYNTAX   SNTPEnableDisable
    ACCESS   read-write
    STATUS   mandatory
    DESCRIPTION
        "This object manages the functionality of the SNTP cliemt.
        If it is set to enable, the SNTP client becomes active.
        If it is set to disable, the Network Time is not polled.
        ALCATEL NOTE:
            ACCESS:      NA           USAGE:       NA
            PERSIST:     YES          INSRVMOD:    YES
            RANGE:       NA           DEFVALUE:    disable
            UNITS:       NA           SPARSE:      NA
            DESCR:       NA"
::= {asamSNTPMIB 4}

asamSNTPTimeSeconds OBJECT-TYPE
    SYNTAX   Uint32
    ACCESS   read-write
    STATUS   mandatory
    DESCRIPTION
    	"This object gives the network time in seconds. This object is read-write.
         The Network time can be set by the operator by means of this object.
        ALCATEL NOTE:
            ACCESS:      NA           USAGE:       NA
            PERSIST:     NO           INSRVMOD:    YES
            RANGE:       NA           DEFVALUE:    0
            UNITS:       seconds      SPARSE:      NA
            DESCR:       NA"
::= {asamSNTPMIB 5}

asamSNTPTimeFractionOfSeconds OBJECT-TYPE
    SYNTAX   INTEGER (1..4294967295)
    ACCESS   read-write
    STATUS   mandatory
    DESCRIPTION
        "This object gives the milliseconds elapsed in a second.
        This object is read-write. The Network time can be set
        by the Operator by means of this object.
        ALCATEL NOTE:
            ACCESS:      NA           USAGE:       NA
            PERSIST:     NO           INSRVMOD:    YES
            RANGE:       NA           DEFVALUE:    0
            UNITS:       milliseconds SPARSE:      NA
            DESCR:       NA"
::= {asamSNTPMIB 6}

asamSNTPOperatingMode OBJECT-TYPE
    SYNTAX   SNTPOperatingMode
    ACCESS   read-only
    STATUS   mandatory
    DESCRIPTION
        "This object gives the operating mode for the SNTP client.
        ALCATEL NOTE:
            ACCESS:      NA           USAGE:       NA
            PERSIST:     NO           INSRVMOD:    YES
            RANGE:       NA           DEFVALUE:    unicast
            UNITS:       NA           SPARSE:      NA
            DESCR:       NA"
::= {asamSNTPMIB 7}

END
