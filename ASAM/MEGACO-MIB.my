-- orig IVPS_MGCH_MIB

MEGACO-MIB DEFINITIONS ::= BEGIN

   IMPORTS
      OBJECT-TYPE
      FROM RFC-1212

      IpAddress, Counter, Gauge
      FROM RFC1155-SMI

      DisplayString, RowStatus, TestAndIncr
      FROM SNMPv2-TC

      asam, alcatel
      FROM SYSTEM-MIB;

   megacoMib OBJECT IDENTIFIER ::= {asam 55}

   mediaGatewayConfig OBJECT IDENTIFIER      ::= {megacoMib 1}
   accessEquipmentConfig OBJECT IDENTIFIER   ::= {megacoMib 2}
   accessTerminationConfig OBJECT IDENTIFIER ::= {megacoMib 3}
   ivpsConfig OBJECT IDENTIFIER              ::= {megacoMib 4}
   signallingGatewayInterfaceConfig OBJECT IDENTIFIER      ::= {megacoMib 5}   
   ltLineTest OBJECT IDENTIFIER              ::= {megacoMib 6}
   
   MediaGatewayId ::= INTEGER (1..2147483647)

   AccessEquipmentId ::= INTEGER (1..255)
   
   AccessBoardId ::= INTEGER (1..65535)
   
   TerminationUserPortId ::= INTEGER (1..2147483647)
   
   AccessTerminationId ::= INTEGER (0..2147483647)

   SignallingGatewayInterfaceId ::= INTEGER (1..2147483647)   
   
   MedGwyEventListType ::= OCTET STRING (SIZE (8))
   
   mediaGatewayTable OBJECT-TYPE
      SYNTAX SEQUENCE OF MediaGatewayEntry
      ACCESS not-accessible
      STATUS mandatory
      DESCRIPTION "List of gateways configured for this IVPS."
   ::= {mediaGatewayConfig 1}

   mediaGatewayEntry OBJECT-TYPE
      SYNTAX MediaGatewayEntry
      ACCESS not-accessible
      STATUS mandatory
      DESCRIPTION "Entry holding configuration information for a gateway."
      INDEX {mediaGatewayId}
   ::= {mediaGatewayTable 1}
   
   MediaGatewayEntry ::= SEQUENCE
   {
      mediaGatewayId MediaGatewayId, 
      mediaGatewayRowStatus RowStatus, 
      mediaGatewayName DisplayString, 
      mediaGatewayOperStatus INTEGER, 
      mediaGatewayAdminStatus INTEGER, 
      mediaGatewayIPAddress IpAddress, 
      mediaGatewayUDPPort INTEGER, 
      mediaGatewaySubnetMask IpAddress, 
      mediaGatewayNextHop IpAddress, 
      mediaGatewayVLAN INTEGER, 
      medGwyCtrlrCallServerId INTEGER, 
      medGwyCtrlrPrimaryIPAddress IpAddress, 
      medGwyCtrlrPrimaryUDPPort INTEGER, 
      medGwyCtrlrSecondaryIPAddress IpAddress, 
      medGwyCtrlrSecondaryUDPPort INTEGER, 
      medGwyCtrlrActiveAddress INTEGER, 
      mediaGatewaySGI INTEGER, 
      medGwyCtrlrCallServerType INTEGER, 
      mediaGatewayLockType INTEGER, 
      mediaGatewayLockDelay INTEGER, 
      mediaGatewaySignDscp INTEGER, 
      mediaGatewaySignDot1P INTEGER, 
      mediaGatewayVoiceDscp INTEGER, 
      mediaGatewayVoiceDot1P INTEGER, 
      mediaGatewayMidType INTEGER, 
      mediaGatewayDomainName DisplayString, 
      mediaGatewaySVCReasonFormat INTEGER, 
      mediaGatewayProfileName DisplayString 
   }
   
   mediaGatewayId OBJECT-TYPE
      SYNTAX MediaGatewayId
      ACCESS not-accessible
      STATUS mandatory
      DESCRIPTION "The unique media gateway Id which identifies this
                   media gateway."
   ::= {mediaGatewayEntry 1}
   
   mediaGatewayRowStatus OBJECT-TYPE
      SYNTAX RowStatus
      ACCESS read-write
      STATUS mandatory
      DESCRIPTION "Allows to control the creation and deletion
                   of rows in this table."
   ::= {mediaGatewayEntry 2}
   
   mediaGatewayName OBJECT-TYPE
      SYNTAX DisplayString
      ACCESS read-write
      STATUS mandatory
      DESCRIPTION "Name for this media gateway.The max number of the string is 64. This parameter will be used for MG mid when mediaGatewayMidType select device-name. Only '*','/','_','$','@','ALPHA','DIGIT', '-', '.' are valid for device-name. 
                      ALCATEL NOTE:
                      SUPPORT:        YES
                      PERSIST:        YES
                      INSRVMOD:       NA
                      RANGE:  NA
                      DEFVALUE:  'AG'
                      UNITS:  NA"
      DEFVAL {"AG"}
   ::= {mediaGatewayEntry 3}
   
   mediaGatewayOperStatus OBJECT-TYPE
      SYNTAX INTEGER
      {
         up (1), 
         down (2), 
         shuttingdown (3) 
      }
      ACCESS read-only
      STATUS mandatory
      DESCRIPTION "The current operational state of the gateway."
   ::= {mediaGatewayEntry 4}
   
   mediaGatewayAdminStatus OBJECT-TYPE
      SYNTAX INTEGER
      {
         locked (1),
         unlocked (2)
      }
      ACCESS read-write
      STATUS mandatory
      DESCRIPTION "The current administrative state of the gateway."
      DEFVAL {locked}
   ::= {mediaGatewayEntry 5}
   
   mediaGatewayIPAddress OBJECT-TYPE
      SYNTAX IpAddress
      ACCESS read-write
      STATUS mandatory
      DESCRIPTION "IP address for this media gateway."
   ::= {mediaGatewayEntry 6}
   
   mediaGatewayUDPPort OBJECT-TYPE
      SYNTAX INTEGER (1025..65534)
      ACCESS read-write
      STATUS mandatory
      DESCRIPTION "UDP port for this media gateway."
      DEFVAL {2944}
   ::= {mediaGatewayEntry 7}
   
   mediaGatewaySubnetMask OBJECT-TYPE
      SYNTAX IpAddress
      ACCESS read-write
      STATUS mandatory
      DESCRIPTION "Subnet mask for this media gateway."
      DEFVAL {'00000000'H}
   ::= {mediaGatewayEntry 8}
   
   mediaGatewayNextHop OBJECT-TYPE
      SYNTAX IpAddress
      ACCESS read-write
      STATUS mandatory
      DESCRIPTION "IP address for the next routing hop in this
                   media gateway."
      DEFVAL {'00000000'H}
   ::= {mediaGatewayEntry 9}
   
   mediaGatewayVLAN OBJECT-TYPE
      SYNTAX INTEGER (2..4093)
      ACCESS read-write
      STATUS mandatory
      DESCRIPTION "VLAN for this media gateway."
   ::= {mediaGatewayEntry 10}
   
   medGwyCtrlrCallServerId OBJECT-TYPE
      SYNTAX INTEGER (0..2147483647)
      ACCESS read-write
      STATUS mandatory
      DESCRIPTION "Identifier of the peer call server."
      DEFVAL {0}
   ::= {mediaGatewayEntry 11}
   
   medGwyCtrlrPrimaryIPAddress OBJECT-TYPE
      SYNTAX IpAddress
      ACCESS read-write
      STATUS mandatory
      DESCRIPTION "Primary IP address of the media gateway controller."
   ::= {mediaGatewayEntry 12}
   
   medGwyCtrlrPrimaryUDPPort OBJECT-TYPE
      SYNTAX INTEGER (0..65535)
      ACCESS read-write
      STATUS mandatory
      DESCRIPTION "Primary UDP port of the media gateway controller."
      DEFVAL {2944}
   ::= {mediaGatewayEntry 13}
   
   medGwyCtrlrSecondaryIPAddress OBJECT-TYPE
      SYNTAX IpAddress
      ACCESS read-write
      STATUS mandatory
      DESCRIPTION "Secondary IP address of the media gateway controller."
      DEFVAL {'00000000'H}
   ::= {mediaGatewayEntry 14}
   
   medGwyCtrlrSecondaryUDPPort OBJECT-TYPE
      SYNTAX INTEGER (0..65535)
      ACCESS read-write
      STATUS mandatory
      DESCRIPTION "Secondary UDP port of the media gateway controller."
      DEFVAL {2944}
   ::= {mediaGatewayEntry 15}
   
   medGwyCtrlrActiveAddress OBJECT-TYPE
      SYNTAX INTEGER
      {
         primary (1),
         secondary (2),
         none(3),
         other(4)
      }
      ACCESS read-only
      STATUS mandatory
      DESCRIPTION "Indicates which is the curretly active address
                   for the associated media gateway controller."
      DEFVAL {primary}
   ::= {mediaGatewayEntry 16}

   mediaGatewaySGI OBJECT-TYPE
      SYNTAX INTEGER (0..2147483647)
      ACCESS read-only
      STATUS mandatory
      DESCRIPTION "The unique signalling gateway Id which identifies this
                   media gateway, 0 indicates there is no sgi is configured"
   ::= {mediaGatewayEntry 17}
   
   medGwyCtrlrCallServerType OBJECT-TYPE
      SYNTAX INTEGER {
                       general(1),
                       lucent-fs5000 (2),
                       alcatel-a5020 (3),
                       alcatel-e10 (4),
                       zte-zxss(5), 
                       hw-soft3000(6),
                       siemens(7),
                       nortel(8),
                       ericsson(9),
                       meta-softswitch(10),
                       other-vendor1(11),
                       other-vendor2(12)
                     }
      ACCESS read-write
      STATUS mandatory
        DESCRIPTION " The vendor type  of MGC server. It is accessed by CLI/T&D command and NOT displayed on GUI.  
                    ALCATEL NOTE:
                      SUPPORT:        YES
                      PERSIST:        YES
                      INSRVMOD:       NO
                      RANGE:  1 | 2 | 3 |4 |5 |6 |7 |8 |9 |10
                      DEFVALUE:       general(1)
                      UNITS:  NA                               "
      DEFVAL { general }
    ::= { mediaGatewayEntry 18 }

   mediaGatewayLockType	OBJECT-TYPE
	SYNTAX	INTEGER
	{
	  force(1),  
	  graceful(2)  
	}
	ACCESS	write-only
	STATUS	mandatory
	DESCRIPTION	"The Type of the lock command.
	Should be set ONLY if the AdminStatus is locked.	
	ALCATEL NOTE 
	ACCESS: WO
	USAGE: MAN 
	PERSIST: NO 
	INSRVMOD: NO 
	RANGE: force or graceful 
	DEFVALUE: NO 
	UNITS: NA 
	SPARSE: NO 
	DESCR: NA "
	DEFVAL {force}
    ::= {mediaGatewayEntry 19}

   mediaGatewayLockDelay	OBJECT-TYPE
	SYNTAX	INTEGER (0..3600000)
	ACCESS	write-only
	STATUS	mandatory
	DESCRIPTION	"The Timer of the lock command , the unit is milliseconds.
		ALCATEL NOTE 
		ACCESS: WO 
		USAGE: MAN 
		PERSIST: NO 
		INSRVMOD: NO 
		RANGE: From 0 to 3600000 
		DEFVALUE: 0 
		UNITS: MILLISECOND 
		SPARSE: NO 
		DESCR: NA "
	DEFVAL {0}
    ::= {mediaGatewayEntry 20}

   mediaGatewaySignDscp OBJECT-TYPE
      SYNTAX INTEGER (0..63)
      ACCESS read-write
      STATUS mandatory
      DESCRIPTION "Signaling DSCP for this media gateway."
      DEFVAL {0}
   ::= {mediaGatewayEntry 21}

   mediaGatewaySignDot1P OBJECT-TYPE
      SYNTAX INTEGER (0..7)
      ACCESS read-write
      STATUS mandatory
      DESCRIPTION "Signaling P-bit for this media gateway."
      DEFVAL {0}	
   ::= {mediaGatewayEntry 22}

   mediaGatewayVoiceDscp OBJECT-TYPE
      SYNTAX INTEGER (0..63)
      ACCESS read-write
      STATUS mandatory
      DESCRIPTION "Voice DSCP for this media gateway."
      DEFVAL {0}
   ::= {mediaGatewayEntry 23}

   mediaGatewayVoiceDot1P OBJECT-TYPE
      SYNTAX INTEGER (0..7)
      ACCESS read-write
      STATUS mandatory
      DESCRIPTION "Voice P-bit for this media gateway."
      DEFVAL {0}
   ::= {mediaGatewayEntry 24}

   mediaGatewayMidType OBJECT-TYPE
      SYNTAX INTEGER {
                       ipv4 (1),
                       ipv4-port (2),
                       domain-name (3),
                       domain-name-port (4),
                       device-name (5)
                     }
      ACCESS read-write
      STATUS mandatory
      DESCRIPTION " The mid type  of MG. If ipv4 is selected, the mediaGatewayIPAddress will be used for the MG mid; If ipv4-port is selected, the mediaGatewayIPAddress+mediaGatewayUDPPort will be used for the MG mid; If domain-name is selected, the mediaGatewayDomainName will be used to support MG mid; If domain-name-port is selected, the mediaGatewayDomainName+mediaGatewayUDPPort will be used to support MG mid; if device-name is selected, the mediaGatewayName will be used for MG mid.
                    ALCATEL NOTE:
                      SUPPORT:        YES
                      PERSIST:        YES
                      INSRVMOD:       NO
                      RANGE:  1 | 2 | 3 | 4 |5
                      DEFVALUE:       ipv4-port(2)
                      UNITS:  NA "
      DEFVAL { ipv4-port }
    ::= { mediaGatewayEntry 25 }
    
   mediaGatewayDomainName OBJECT-TYPE
      SYNTAX DisplayString
      ACCESS read-write
      STATUS mandatory
      DESCRIPTION "Domain Name of this media gateway. Only 'ALPHA','DIGIT', '-', '.', '@' are valid for domainName. The max number of the string is 255. If address-type select domain-name, this parameter will be used for MG mid. 
                      ALCATEL NOTE:
                      SUPPORT:        YES
                      PERSIST:        YES
                      INSRVMOD:       NO
                      RANGE:  SIZE(1..255) 
                      DEFVALUE: 'isamv.alcatel-lucent.com' 
                      UNITS:  NA"
      DEFVAL {"isamv.alcatel-lucent.com"}
   ::= {mediaGatewayEntry 26}

   mediaGatewaySVCReasonFormat OBJECT-TYPE
      SYNTAX INTEGER {
      with-quotation (1),
      without-quotation (2)
      }
      ACCESS read-write
      STATUS mandatory
      DESCRIPTION " The format of reason, which used in H248 service change.
                     ALCATEL NOTE:
                     SUPPORT: YES
                     PERSIST: YES
                     INSRVMOD: NO
                     RANGE: 1 | 2
                     DEFVALUE: with-quotation (1)
                     UNITS: NA"
      DEFVAL { with-quotation }
   ::= { mediaGatewayEntry 27 }
    
   mediaGatewayProfileName OBJECT-TYPE
      SYNTAX DisplayString
      ACCESS read-write
      STATUS mandatory
      DESCRIPTION "Profile Name of this media gateway. Which used in H248 message service change. The max number of the string is 64.
                     ALCATEL NOTE:
                     SUPPORT: YES
                     PERSIST: YES
                     INSRVMOD: NO
                     RANGE: SIZE(1..64)
                     DEFVALUE: 'AGW'
                     UNITS: NA"
      DEFVAL {"AGW"}
   ::= { mediaGatewayEntry 28 }   

   mediaGatewayNextId OBJECT-TYPE
      SYNTAX TestAndIncr
      ACCESS read-only
      STATUS mandatory
      DESCRIPTION "Next free identifier for a new mediaGatewayEntry."
   ::= {mediaGatewayConfig 2}

   medGwyMegacoExtTable OBJECT-TYPE 
	SYNTAX SEQUENCE OF MedGwyMegacoExtEntry 
	ACCESS not-accessible 
	STATUS mandatory 
	DESCRIPTION "The megaco service extension of mediaGatewayTable.
		ALCATEL NOTE 
		ACCESS: NA 
		USAGE: MAN 
		PERSIST: YES 
		INSRVMOD: NO 
		RANGE: NA 
		DEFVALUE: NA 
		UNITS: NA 
		SPARSE: NO 
		DESCR: NA ." 
    ::= {mediaGatewayConfig 3} 

   medGwyMegacoExtEntry OBJECT-TYPE 
	SYNTAX MedGwyMegacoExtEntry 
	ACCESS not-accessible 
	STATUS mandatory 
	DESCRIPTION "An entry containing megaco service configuration information of a media gateway interface. 
		ALCATEL NOTE 
		ACCESS: NA 
		USAGE: MAN 
		PERSIST: YES 
		INSRVMOD: NO 
		RANGE: NA 
		DEFVALUE: NA 
		UNITS: NA 
		SPARSE: NO 
		DESCR: NA " 
	INDEX {mediaGatewayId} 
    ::= {medGwyMegacoExtTable 1} 

   MedGwyMegacoExtEntry ::= SEQUENCE 
   { 
	medGwyTermFormatType INTEGER, 
	medGwyPstnTermFormatStr DisplayString, 
	medGwyIsdnTermFormatStr DisplayString, 
	medGwyIsdnSuffix1Str DisplayString,   
	medGwyIsdnSuffix2Str DisplayString,   
	medGwyTMAX INTEGER, 
	medGwyMaxNetworkDelay INTEGER, 
	medGwyMaxTransRetransmission INTEGER, 
	medGwyReduceBatteryDelay INTEGER, 
	medGwyReleaseDelay INTEGER, 
	medGwyGracefulWaitingReleaseDelay INTEGER,  
	medGwyActiveHeartbeatMode INTEGER, 
	medGwyActiveHeartbeatInterval INTEGER, 
	medGwyPassiveHeartbeatMode INTEGER, 
	medGwyPassiveHeartbeatInterval INTEGER, 
	medGwyRetransmissionMode INTEGER, 
	medGwyRetransmissionInterval INTEGER, 
	medGwyMaxWaitingDelay    INTEGER,  
	medGwyProvisionalResponse  INTEGER, 
	medGwyEventRequestID INTEGER, 
	medGwyEventList MedGwyEventListType, 
	medGwyRfc2833PayloadType  INTEGER, 
	medGwyRfc2833Processing INTEGER, 
	medGwyDialingStartTimer  INTEGER, 
	medGwyDialingLongTimer INTEGER, 
	medGwyDialingShortTimer  INTEGER, 
	medGwyMinDataJitterBuffer INTEGER, 
	medGwyInitDataJitterBuffer  INTEGER, 
	medGwyMaxDataJitterBuffer INTEGER, 
	medGwyEphemeralTermPrefix  DisplayString, 
	medGwyEphemeralTermMin Gauge, 
	medGwyEphemeralTermMax Gauge, 
	medGwyReleaseType  INTEGER  

   } 

   medGwyTermFormatType OBJECT-TYPE 
	SYNTAX INTEGER 
	{ 
	  hierarchy (1), 
	  flat (2) 
	} 
	ACCESS read-write 
	STATUS mandatory 
	DESCRIPTION "The termination ID format type of the MGI.
		ALCATEL NOTE 
	ACCESS: RW 
	USAGE: MAN 
	PERSIST: YES 
	INSRVMOD: NO 
	RANGE: NA 
	DEFVALUE: Get from Database
	UNITS: NA 
	SPARSE: NO 
	DESCR: NA " 
   ::= {medGwyMegacoExtEntry 1} 

   medGwyPstnTermFormatStr OBJECT-TYPE 
	SYNTAX DisplayString 
	ACCESS read-write 
	STATUS mandatory 
	DESCRIPTION "The termination ID format pattern of PSTN user, 
		When the medGwyTermFormatType = hierarchy, it is a string like
		'AL/Dslam_Id/rackXXXXX/shelfXXXXX/slotXXXXX/portXXXXX/channel', 'X' is a number and 
		the number of 'X' is from 0 to 5, it means termination ID starts from 'XXXXX'. 
		'/'(delimiter) can be replaced by other strings or no delimiter. Dslam_Id and rack are optional.
		when the medGwyTermFormatType = flat, it is a string like 'prefix<tidXXXXX>'.
		in this format,termination 0 can be configured, and the number of 'X' is from 0 to 5.
		The max length of the string is 72.
		About the prefix, it does not care about the Capital or Lowercase.  
		The max length of the prefix is 10. 
		ALCATEL NOTE 
		ACCESS: RW 
		USAGE: MAN 
		PERSIST: YES 
		INSRVMOD: NO 
		RANGE: NA 
		DEFVALUE: Get from CDE File or Database
		UNITS: NA 
		SPARSE: NO 
		DESCR: NA " 
   ::= {medGwyMegacoExtEntry 2} 

   medGwyIsdnTermFormatStr OBJECT-TYPE 
	SYNTAX DisplayString 
	ACCESS read-write 
	STATUS mandatory 
	DESCRIPTION "The termination ID format pattern of ISDN user, 
		When the medGwyTermFormatType = hierarchy, it is a string like
		'BA/Dslam_Id/rackXXXXX/shelfXXXXX/slotXXXXX/portXXXXX/channel', 'X' is a number and 
		the number of 'X' is from 0 to 5, it means termination ID starts from 'XXXXX'. 
		'/'(delimiter) can be replaced by other strings or no delimiter. Dslam_Id and rack are optional.
		when the medGwyTermFormatType = flat, it is a string like 'prefix<tidXXXXX>'.
		in this format,termination 0 can be configured, and the number of 'X' is from 0 to 5.
		The max length of the string is 72. 
		About the prefix, it does not care about the Capital or Lowercase.  
		The max length of the prefix is 10. 
		ALCATEL NOTE 
		ACCESS: NA 
		USAGE: MAN 
		PERSIST: YES 
		INSRVMOD: NO 
		RANGE: NA 
		DEFVALUE: Get from CDE File or DataBase
		UNITS: NA 
		SPARSE: NO 
		DESCR: NA " 
   ::= {medGwyMegacoExtEntry 3} 

   medGwyIsdnSuffix1Str	OBJECT-TYPE
	SYNTAX	DisplayString
	ACCESS	read-write
	STATUS	mandatory
	DESCRIPTION "The suffix1 of the ISDN User Termination Format,
		It represents the channel of the ISDN User. 
		The max length of the ISDN Suffix1 is about 8.
		ALCATEL NOTE 
		ACCESS: RW 
		USAGE: MAN 
		PERSIST: YES 
		INSRVMOD: NO 
		RANGE: NA 
		DEFVALUE: Get from CDE File 
		UNITS: NA 
		SPARSE: NO 
		DESCR: NA ."
   ::= {medGwyMegacoExtEntry 4}

   medGwyIsdnSuffix2Str	OBJECT-TYPE
	SYNTAX	DisplayString
	ACCESS	read-write
	STATUS	mandatory
	DESCRIPTION "The suffix2 of the ISDN User Termination Format,
	It represents the channel of the ISDN User.
	The max length of the ISDN Suffix2 is about 8.	
	ALCATEL NOTE 
	ACCESS: RW 
	USAGE: MAN 
	PERSIST: YES 
	INSRVMOD: NO 
	RANGE: NA 
	DEFVALUE: Get from CDE File 
	UNITS: NA 
	SPARSE: NO 
	DESCR: NA  "
   ::= {medGwyMegacoExtEntry 5}

   medGwyTMAX OBJECT-TYPE 
	SYNTAX INTEGER (1000..30000)
	ACCESS read-write 
	STATUS mandatory 
	DESCRIPTION "The max time of MGC handling the transaction. The unit is millisecond.
	ALCATEL NOTE 
	ACCESS: RW 
	USAGE: MAN 
	PERSIST: YES 
	INSRVMOD: NO 
	RANGE: From 1000 to 30000
	DEFVALUE: 16000 
	UNITS: MILLISECOND 
	SPARSE: NO 
	DESCR: NA " 
	DEFVAL {16000} 
   ::= {medGwyMegacoExtEntry 6} 

   medGwyMaxNetworkDelay OBJECT-TYPE 
	SYNTAX INTEGER (100..1000)
	ACCESS read-write 
	STATUS mandatory 
	DESCRIPTION "The max network delay time. The unit is millisecond.
		ALCATEL NOTE 
		ACCESS: RW 
		USAGE: MAN 
		PERSIST: YES 
		INSRVMOD: NO 
		RANGE: From 100 to 1000 
		DEFVALUE: 500 
		UNITS: MILLISECOND 
		SPARSE: NO 
		DESCR: NA " 
	DEFVAL {500} 
   ::= {medGwyMegacoExtEntry 7} 

   medGwyMaxTransRetransmission OBJECT-TYPE 
	SYNTAX INTEGER (7..11)
	ACCESS read-write 
	STATUS mandatory 
	DESCRIPTION "The max retransimit times of the transaction. The unit is times.
		ALCATEL NOTE 
		ACCESS: RW 
		USAGE: MAN 
		PERSIST: YES 
		INSRVMOD: NO 
		RANGE: From 7 To 11 
		DEFVALUE: 7 
		UNITS: TIMES 
		SPARSE: NO 
		DESCR: NA " 
	DEFVAL {7} 
   ::= {medGwyMegacoExtEntry 8} 

   medGwyReduceBatteryDelay OBJECT-TYPE 
	SYNTAX INTEGER (0..120000)
	ACCESS read-write 
	STATUS mandatory 
	DESCRIPTION "The delay before MGI coming into reduced battery state. The unit is millisecond.
		ALCATEL NOTE 
		ACCESS: RW 
		USAGE: MAN 
		PERSIST: YES 
		INSRVMOD: YES 
		RANGE: From 0 To 120000 
		DEFVALUE: 70000 
		UNITS: MILLISECOND 
		SPARSE: NO 
		DESCR: NA ." 
	DEFVAL {70000} 
   ::= {medGwyMegacoExtEntry 9} 

   medGwyReleaseDelay OBJECT-TYPE 
	SYNTAX INTEGER (0..900000)
	ACCESS read-write 
	STATUS mandatory 
	DESCRIPTION "The delay before MGI releasing all sessions 
		after the connection with MGC lost temporally. The unit is millisecond. 
		ALCATEL NOTE 
		ACCESS: RW 
		USAGE: MAN 
		PERSIST: YES 
		INSRVMOD: YES 
		RANGE: From 0 To 900000 
		DEFVALUE: 600000 
		UNITS: MILLISECOND 
		SPARSE: NO 
		DESCR: NA " 
	DEFVAL {600000} 
::= {medGwyMegacoExtEntry 10} 
 
   medGwyGracefulWaitingReleaseDelay  OBJECT-TYPE
	SYNTAX	INTEGER (0..3600000)
	ACCESS read-write
	STATUS	mandatory
	DESCRIPTION  "The delay after the graceful lock delay timer expired.
		The unit is millisecond. 
		ALCATEL NOTE 
		ACCESS: RW 
		USAGE: MAN 
		PERSIST: YES 
		INSRVMOD: YES 
		RANGE: From 0 To 3600000 
		DEFVALUE: 0 
		UNITS: MILLISECOND 
		SPARSE: NO 
		DESCR: NA "
	DEFVAL	{0}
   ::= {medGwyMegacoExtEntry 11}

   medGwyActiveHeartbeatMode OBJECT-TYPE 
	SYNTAX INTEGER 
	{ 
	  fix (1), 
	  dynamic (2) 
	} 
	ACCESS read-write 
	STATUS mandatory 
	DESCRIPTION "The active heartbeat mode of the MGI.
		ALCATEL NOTE 
		ACCESS: RW 
		USAGE: MAN 
		PERSIST: YES 
		INSRVMOD: YES 
		RANGE: NA 
		DEFVALUE: fix 
		UNITS: NA 
		SPARSE: NO 
		DESCR: NA " 
	DEFVAL {fix} 
   ::= {medGwyMegacoExtEntry 12} 

   medGwyActiveHeartbeatInterval OBJECT-TYPE 
	SYNTAX INTEGER (0..65535)
	ACCESS read-write 
	STATUS mandatory 
	DESCRIPTION "The active heartbeat interval of the MGI, 
		this object is only valid when the medGwActiveHeartbeatMode = fix(1).
		The unit is 10 millisecond.
		ALCATEL NOTE 
		ACCESS: RW 
		USAGE: MAN 
		PERSIST: YES 
		INSRVMOD: YES 
		RANGE: From 0 To 65535 
		DEFVALUE: 0 
		UNITS: 10 MILLISECOND 
		SPARSE: NO 
		DESCR: NA " 
	DEFVAL {0} 
   ::= {medGwyMegacoExtEntry 13} 

   medGwyPassiveHeartbeatMode OBJECT-TYPE 
	SYNTAX INTEGER 
	{ 
	  fix (1), 
	  dynamic (2) 
	} 
	ACCESS read-write 
	STATUS mandatory 
	DESCRIPTION "The passive heartbeat mode of the MGI.
		ALCATEL NOTE 
		ACCESS: RW 
		USAGE: MAN 
		PERSIST: YES 
		INSRVMOD: YES 
		RANGE: NA 
		DEFVALUE: fix 
		UNITS: NA 
		SPARSE: NO 
		DESCR: NA " 
	DEFVAL {dynamic} 
   ::= {medGwyMegacoExtEntry 14} 

   medGwyPassiveHeartbeatInterval OBJECT-TYPE 
	SYNTAX INTEGER (0..65535)
	ACCESS read-write 
	STATUS mandatory 
	DESCRIPTION "The passive heartbeat interval of the MGI, 
		this object is only valid when the medGwPassiveHeartbeatMode = fix(1).
		The unit is 10 millisecond. 
		ALCATEL NOTE 
		ACCESS: RW 
		USAGE: MAN 
		PERSIST: YES 
		INSRVMOD: YES 
		RANGE: From 0 To 65535 
		DEFVALUE: 0 
		UNITS: 10 MILLISECOND 
		SPARSE: NO 
		DESCR: NA " 
	DEFVAL {0} 
   ::= {medGwyMegacoExtEntry 15}

   medGwyRetransmissionMode	OBJECT-TYPE
   	SYNTAX	INTEGER
   	{
	  fix (1), 
	  dynamic (2) 
   	}
	ACCESS read-write 
	STATUS mandatory 
	DESCRIPTION "The Retransmission mode of the MGI.
		ALCATEL NOTE 
		ACCESS: RW 
		USAGE: MAN 
		PERSIST: YES 
		INSRVMOD: NO 
		RANGE: NA 
		DEFVALUE: fix 
		UNITS: NA 
		SPARSE: NO 
		DESCR: NA " 
	DEFVAL {fix} 
   ::= {medGwyMegacoExtEntry 16}

   medGwyRetransmissionInterval OBJECT-TYPE 
	SYNTAX INTEGER (100..4000)
	ACCESS read-write 
	STATUS mandatory 
	DESCRIPTION "The Retransmission interval of the MGI, 
		this object is only valid when the medGwyRetransmissionMode = fix(1).
		The unit is millisecond. 
		ALCATEL NOTE 
		ACCESS: RW 
		USAGE: MAN 
		PERSIST: YES 
		INSRVMOD: NO 
		RANGE: From 100 To 4000 
		DEFVALUE: 4000 
		UNITS: MILLISECOND 
		SPARSE: NO 
		DESCR: NA " 
	DEFVAL {4000} 
   ::= {medGwyMegacoExtEntry 17}
   
   medGwyMaxWaitingDelay OBJECT-TYPE 
	SYNTAX INTEGER (0..120)
	ACCESS read-write 
	STATUS mandatory 
	DESCRIPTION "The maximum time that Media Gateway has to wait after a
	             restart before contacting to the Call Server, 
		     The unit is millisecond. 
		ALCATEL NOTE 
		ACCESS: RW 
		USAGE: MAN 
		PERSIST: YES 
		INSRVMOD: NO 
		RANGE: From 0 To 120 
		DEFVALUE: 5 
		UNITS: MILLISECOND 
		SPARSE: NO 
		DESCR: NA " 
	DEFVAL {5} 
   ::= {medGwyMegacoExtEntry 18}
   
   medGwyProvisionalResponse OBJECT-TYPE 
	SYNTAX INTEGER (0..10000)
	ACCESS read-write 
	STATUS mandatory 
	DESCRIPTION "The time need to send a transaction pending since the
        	reception of the transcation.
		The unit is millisecond. 
		ALCATEL NOTE 
		ACCESS: RW 
		USAGE: MAN 
		PERSIST: YES 
		INSRVMOD: NO 
		RANGE: From 0 To 10000 
		DEFVALUE: 1000 
		UNITS: MILLISECOND 
		SPARSE: NO 
		DESCR: NA " 
	DEFVAL {1000} 
   ::= {medGwyMegacoExtEntry 19}
   
   medGwyEventRequestID   OBJECT-TYPE 
	SYNTAX INTEGER (0..65535)
	ACCESS read-write 
	STATUS mandatory 
	DESCRIPTION "The event request identification, it is configured to cater for different MGCs, such as the case that an event is not requested from MGC.
		when this parameter is set, MG will send the event with the configured event request ID. 
		ALCATEL NOTE 
		ACCESS: RW 
		USAGE: MAN 
		PERSIST: YES 
		INSRVMOD: YES
		RANGE: From 0 To 65535 
		DEFVALUE: 0
		UNITS: NA
		SPARSE: NO 
		DESCR: NA "
	DEFVAL {0} 
   ::= {medGwyMegacoExtEntry 20}
	
   medGwyEventList   OBJECT-TYPE 
	SYNTAX MedGwyEventListType
	ACCESS read-write 
	STATUS mandatory 
	DESCRIPTION "This is a bitmap. Each bit represents an event which is supported by MG.
			If a bit is set, the corresponding event is supported. More than one mode can be set simultaneously.
			The respective event types correspond to the following integer values in the bitmap, 
			other bit positions are reserved for future use:
			
			Octet 1 :
				1: indicate stimal/stedsig event
				2: indicate al/of event
				4: indicate al/on event
				8: indicate al/of {strict=state} event
				16: indicate al/on {strict=state} event
				32: indicate ocp/mg_overload event
				64: reserved for future
				128: reserved for future
    Octet 2-7:  Reserved for future use
	 
		ALCATEL NOTE 
		ACCESS: RW
		USAGE: MAN 
		PERSIST: YES 
		INSRVMOD: YES
		RANGE: NA 
		DEFVALUE: NA
		UNITS: NA 
		SPARSE: NO 
		DESCR: NA "
	DEFVAL {'0000000000000000'H } 
   ::= {medGwyMegacoExtEntry 21} 
   
      medGwyRfc2833PayloadType   OBJECT-TYPE 
	SYNTAX INTEGER (96..127)
	ACCESS read-write 
	STATUS mandatory 
	DESCRIPTION " Payload type of RFC2833
	 
		ALCATEL NOTE 
		ACCESS: RW
		USAGE: MAN 
		PERSIST: YES 
		INSRVMOD: YES
		RANGE: From 96 To 127
		DEFVALUE: 96
		UNITS: NA 
		SPARSE: NO 
		DESCR: NA "

	DEFVAL {96} 
   ::= {medGwyMegacoExtEntry 22} 

   medGwyRfc2833Processing   OBJECT-TYPE 
	SYNTAX INTEGER
   	{
	  audio (1), 
	  rfc2833 (2), 
	  both (3) 
   	}
	ACCESS read-write 
	STATUS mandatory 
	DESCRIPTION " Processing procedure for the DTMF event tones
	 
		ALCATEL NOTE 
		ACCESS: RW
		USAGE: MAN 
		PERSIST: YES 
		INSRVMOD: YES
		RANGE: NA
		DEFVALUE: audio
		UNITS: NA 
		SPARSE: NO 
		DESCR: NA "

	DEFVAL { audio } 
   ::= {medGwyMegacoExtEntry 23} 

   medGwyDialingStartTimer   OBJECT-TYPE 
	SYNTAX INTEGER (1..60)
	ACCESS read-write 
	STATUS mandatory 
	DESCRIPTION " The start timer of dialing
				Default maximum waiting time for dialing the first digit.
				The unit is second.
	 
		ALCATEL NOTE 
		ACCESS: RW
		USAGE: MAN 
		PERSIST: YES 
		INSRVMOD: NO
		RANGE: From 1 To 60
		DEFVALUE: 10
		UNITS: SECOND 
		SPARSE: NO 
		DESCR: NA "

	DEFVAL {10} 
   ::= {medGwyMegacoExtEntry 24} 

   medGwyDialingLongTimer   OBJECT-TYPE 
	SYNTAX INTEGER (1..60)
	ACCESS read-write 
	STATUS mandatory 
	DESCRIPTION " The long timer of dialing.
				Default maximum waiting time for dialing when no matching found in the digitmap.
				The unit is second.
	 
		ALCATEL NOTE 
		ACCESS: RW
		USAGE: MAN 
		PERSIST: YES 
		INSRVMOD: NO
		RANGE: From 1 To 60
		DEFVALUE: 20
		UNITS: SECOND 
		SPARSE: NO 
		DESCR: NA "

	DEFVAL {20} 
   ::= {medGwyMegacoExtEntry 25} 

   medGwyDialingShortTimer   OBJECT-TYPE 
	SYNTAX INTEGER (1..60)
	ACCESS read-write 
	STATUS mandatory 
	DESCRIPTION " The short timer of dialing
				Default maximum waiting time for dialing when matching found in the digitmap.
				The unit is second.
	 
		ALCATEL NOTE 
		ACCESS: RW
		USAGE: MAN 
		PERSIST: YES 
		INSRVMOD: NO
		RANGE: From 1 To 60
		DEFVALUE: 5
		UNITS: SECOND 
		SPARSE: NO 
		DESCR: NA "

	DEFVAL {5} 
   ::= {medGwyMegacoExtEntry 26} 

   medGwyMinDataJitterBuffer   OBJECT-TYPE 
	SYNTAX INTEGER (0..200)
	ACCESS read-write 
	STATUS mandatory 
	DESCRIPTION " Minimum jitter buffer for data calls working in RTP mode.
				The unit is millisecond.
	 
		ALCATEL NOTE 
		ACCESS: RW
		USAGE: MAN 
		PERSIST: YES 
		INSRVMOD: YES
		RANGE: From 0 To 200
		DEFVALUE: 50
		UNITS: MILLISECOND 
		SPARSE: NO 
		DESCR: NA "

	DEFVAL {50} 
   ::= {medGwyMegacoExtEntry 27} 

   medGwyInitDataJitterBuffer   OBJECT-TYPE 
	SYNTAX INTEGER (0..200)
	ACCESS read-write 
	STATUS mandatory 
	DESCRIPTION " Initial jitter buffer for data calls working in RTP mode.
				The unit is millisecond.
	 
		ALCATEL NOTE 
		ACCESS: RW
		USAGE: MAN 
		PERSIST: YES 
		INSRVMOD: YES
		RANGE: From 0 To 200
		DEFVALUE: 50
		UNITS: MILLISECOND 
		SPARSE: NO 
		DESCR: NA "

	DEFVAL {50} 
   ::= {medGwyMegacoExtEntry 28} 

   medGwyMaxDataJitterBuffer   OBJECT-TYPE 
	SYNTAX INTEGER (0..200)
	ACCESS read-write 
	STATUS mandatory 
	DESCRIPTION " Maximum jitter buffer for data calls working in RTP mode.
				The unit is millisecond.
	 
		ALCATEL NOTE 
		ACCESS: RW
		USAGE: MAN 
		PERSIST: YES 
		INSRVMOD: YES
		RANGE: From 0 To 200
		DEFVALUE: 50
		UNITS: MILLISECOND 
		SPARSE: NO 
		DESCR: NA "

	DEFVAL {50} 
   ::= {medGwyMegacoExtEntry 29} 

   medGwyEphemeralTermPrefix   OBJECT-TYPE 
	SYNTAX DisplayString
	ACCESS read-write 
	STATUS mandatory 
	DESCRIPTION " Define the prefix to compose the ephemeral termination id.
                   The max number of the string is 10.
                   This parameter can not be same with medGwyPstnTermFormatStr and medGwyIsdnTermFormatStr.
	 
		ALCATEL NOTE 
		ACCESS: RW
		USAGE: MAN 
		PERSIST: YES 
		INSRVMOD: NO
		RANGE: From 0 To 10
		DEFVALUE: NA
		UNITS: NA 
		SPARSE: NO 
		DESCR: NA "

	DEFVAL {"E"} 
   ::= {medGwyMegacoExtEntry 30} 

   medGwyEphemeralTermMin   OBJECT-TYPE 
	SYNTAX Gauge
	ACCESS read-write 
	STATUS mandatory 
	DESCRIPTION " Minimum value of ephemeral termination for PSTN and ISDN-BA.
	 
		ALCATEL NOTE 
		ACCESS: RW
		USAGE: MAN 
		PERSIST: YES 
		INSRVMOD: NO
		RANGE: From 0 To 4294967295
		DEFVALUE: 65536
		UNITS: NA 
		SPARSE: NO 
		DESCR: NA "

	DEFVAL {65536} 
   ::= {medGwyMegacoExtEntry 31} 

   medGwyEphemeralTermMax   OBJECT-TYPE 
	SYNTAX Gauge
	ACCESS read-write 
	STATUS mandatory 
	DESCRIPTION " Maximum value of ephemeral termination for PSTN and ISDN-BA.
	 
		ALCATEL NOTE 
		ACCESS: RW
		USAGE: MAN 
		PERSIST: YES 
		INSRVMOD: NO
		RANGE: From 0 To 4294967295
		DEFVALUE: 72366
		UNITS: NA 
		SPARSE: NO 
		DESCR: NA "

	DEFVAL {72366} 
   ::= {medGwyMegacoExtEntry 32}

   medGwyReleaseType		OBJECT-TYPE
	SYNTAX	INTEGER
	{
	  normal(1),  
	  never(2)      
	}
	ACCESS	read-write
	STATUS	mandatory
	DESCRIPTION	"The Type of release the active call.
	When the value is never it means it will preserve active call , when the value is normal,
            it means the active call will be released immediately or after delay time according to the define of medGwyReleaseDelay.
	ALCATEL NOTE 
	ACCESS: WO
	USAGE: MAN 
	PERSIST: YES 
	INSRVMOD: NO 
	RANGE: normal or never
	DEFVALUE: normal 
	UNITS: NA 
	SPARSE: NO 
	DESCR: NA "
	DEFVAL {normal}
    ::= {medGwyMegacoExtEntry  33}

   accessEquipmentTable OBJECT-TYPE
      SYNTAX SEQUENCE OF AccessEquipmentEntry
      ACCESS not-accessible
      STATUS mandatory
      DESCRIPTION "List of ISAM-V NEs having an access board associated to this IVPS."
   ::= {accessEquipmentConfig 1}
   
   accessEquipmentEntry OBJECT-TYPE
      SYNTAX AccessEquipmentEntry
      ACCESS not-accessible
      STATUS mandatory
      DESCRIPTION "Entry holding configuration information for an ISAM-V NE."
      INDEX {accessEquipmentId}
   ::= {accessEquipmentTable 1}
   
   AccessEquipmentEntry ::= SEQUENCE
   {
      accessEquipmentId AccessEquipmentId, 
      accessEquipmentRowStatus RowStatus, 
      accessEquipmentAsamId DisplayString, 
      accessEquipmentVoiceIPAddress IpAddress, 
      accessEquipmentVoiceNextHop IpAddress 
   }
   
   accessEquipmentId OBJECT-TYPE
      SYNTAX AccessEquipmentId
      ACCESS not-accessible
      STATUS mandatory
      DESCRIPTION "Unique internal identifier for this ISAM-V NE."
   ::= {accessEquipmentEntry 1}
   
   accessEquipmentRowStatus OBJECT-TYPE
      SYNTAX RowStatus
      ACCESS read-write
      STATUS mandatory
      DESCRIPTION "Allows to control the creation and deletion
                   of rows in this table."
   ::= {accessEquipmentEntry 2}
   
   accessEquipmentAsamId OBJECT-TYPE
      SYNTAX DisplayString
      ACCESS read-write
      STATUS mandatory
      DESCRIPTION "Identifier of an ISAM-V NE. The max number of the string is 64. 
                   The string accept all printable characters. 
                   It is mandatory parameter of Equipment table entry. 
                      ALCATEL NOTE:
                      SUPPORT:        YES
                      PERSIST:        YES
                      INSRVMOD:       NA
                      RANGE:  NA
                      DEFVALUE:  NA
                      UNITS:  NA"
      DEFVAL {""}
   ::= {accessEquipmentEntry 3}
   
   accessEquipmentVoiceIPAddress OBJECT-TYPE
      SYNTAX IpAddress
      ACCESS read-write
      STATUS mandatory
      DESCRIPTION "IP address of the voice services for this ISAM-V NE."
   ::= {accessEquipmentEntry 4}
   
   accessEquipmentVoiceNextHop OBJECT-TYPE
      SYNTAX IpAddress
      ACCESS read-write
      STATUS mandatory
      DESCRIPTION "IP address of the next hop for this ISAM-V NE, in case
      accessEquipmentVoiceIPAddress is not in the same subnet as XLES subnet"
      DEFVAL {'00000000'H}
   ::= {accessEquipmentEntry 5}

   accessEquipmentNextId OBJECT-TYPE
      SYNTAX TestAndIncr
      ACCESS read-only
      STATUS mandatory
      DESCRIPTION "Next free identifier for a new accessEquipmentEntry."
   ::= {accessEquipmentConfig 2}
   
   accessBoardTable OBJECT-TYPE
      SYNTAX SEQUENCE OF AccessBoardEntry
      ACCESS not-accessible
      STATUS mandatory
      DESCRIPTION "List of POLT boards associated to this IVPS."
   ::= {accessEquipmentConfig 3}
   
   accessBoardEntry OBJECT-TYPE
      SYNTAX AccessBoardEntry
      ACCESS not-accessible
      STATUS mandatory
      DESCRIPTION "Entry holding configuration information for an
                   associated POLT board."
      INDEX {accessBoardHldrEquipmentId, accessBoardId}
   ::= {accessBoardTable 1}
   
   AccessBoardEntry ::= SEQUENCE
   {
      accessBoardHldrEquipmentId AccessEquipmentId, 
      accessBoardId AccessBoardId, 
      accessBoardRowStatus RowStatus, 
      accessBoardCommStatus INTEGER, 
      accessBoardLanxport   INTEGER,   
      accessBoardPlannedType  DisplayString,  
      accessBoardActualType  DisplayString  
   }
   
   accessBoardHldrEquipmentId OBJECT-TYPE
      SYNTAX AccessEquipmentId
      ACCESS not-accessible
      STATUS mandatory
      DESCRIPTION "Internal identifier of the ISAM-V NE holding this POLT board."
   ::= {accessBoardEntry 1}
   
   accessBoardId OBJECT-TYPE
      SYNTAX AccessBoardId
      ACCESS not-accessible
      STATUS mandatory
      DESCRIPTION "Slot identifier composed of the rack number (4 bits),
                   subrack number (4 bits) and slot number (8 bits).the slotId(low byte) start from 1, and the 
                   slotId 1 corresponds to LT1."
   ::= {accessBoardEntry 2}
   
   accessBoardRowStatus OBJECT-TYPE
      SYNTAX RowStatus
      ACCESS read-write
      STATUS mandatory
      DESCRIPTION "Allows to control the creation and deletion
                   of rows in this table."
   ::= {accessBoardEntry 3}
   
   accessBoardCommStatus OBJECT-TYPE
      SYNTAX INTEGER
      {
         up (1),
         down (2),
         unknown (3)
      }
      ACCESS read-only
      STATUS mandatory
      DESCRIPTION "Represents the state of the communications with the POLT."
   ::= {accessBoardEntry 4}

   accessBoardLanxport	OBJECT-TYPE
	SYNTAX	INTEGER (1..24)
	ACCESS   read-write
	STATUS	mandatory
	DESCRIPTION  "The logical slot of the board.
		This value is used to calculate the UDP port.
		Notes: If the board is in the main rack not the extension rack, 
		The LANXPORT must be the same as SLOT number, if not, the LT board will not be up state.
		ALCATEL NOTE 
		ACCESS: RW 
		USAGE: MAN 
		PERSIST: YES 
		INSRVMOD: NO 
		RANGE: From 1 to 24 
		DEFVALUE: NA 
		UNITS: NA 
		SPARSE: NO 
		DESCR: NA  "
   ::=  {accessBoardEntry  6}
  
    accessBoardPlannedType OBJECT-TYPE
   	SYNTAX DisplayString
   	ACCESS read-write
   	STATUS mandatory
        DESCRIPTION  "
                A string representing the board (POLT-A,NPOT-A,BALT-B,NBAT-A,NBLT-B,...) that is
                planned in the slot. If the board is planned, the string consists of a mnemonic that
                identifies the board type.
                Following mnemonics are valid:
                <BOARD_MNEMONIC> A board of a specific type. Refer to the ETSI and
                                US Configurations documents for the list of boards 
                                that are supported in a given release.
                                ODM board types are planned with the board mnemonic, 
                                they are treated as unmanaged boards.
                NOT_PLANNED   No board is planned in the slot.
		ALCATEL NOTE 
		ACCESS: RW 
		USAGE: MAN 
		PERSIST: YES 
		INSRVMOD: NO 
		RANGE: NA 
		DEFVALUE: NA 
		UNITS: NA 
		SPARSE: NO 
		DESCR: NA  "
   ::= {accessBoardEntry 7}

   accessBoardActualType        OBJECT-TYPE
        SYNTAX  DisplayString
        ACCESS   read-only
        STATUS  mandatory
        DESCRIPTION  "
                A string representing the board (POLT-A,NPOT-A,BALT-B,NBAT-A,NBLT-B,...) that is 
                actually present in the slot.
                Following values are possible:
                <BOARD_MNEMONIC> Indicates the detected board-type. Uses same mnemonics as
                                described in object assessBoardPlannedType.
                UNKNOWN         The type of the detected board is unknown
                                and the planned board type is not UNMANAGED.
		ALCATEL NOTE 
		ACCESS: RO 
		USAGE: MAN 
		PERSIST: NO 
		INSRVMOD: NO 
		RANGE: NA 
		DEFVALUE: UNKNOWN 
		UNITS: NA 
		SPARSE: NO 
		DESCR: NA  "
	DEFVAL {"UNKNOWN"}
   ::=  {accessBoardEntry  8}

   accessTerminationTable OBJECT-TYPE
      SYNTAX SEQUENCE OF AccessTerminationEntry
      ACCESS not-accessible
      STATUS mandatory
      DESCRIPTION "List of configured user ports."
   ::= {accessTerminationConfig 1}
   
   accessTerminationEntry OBJECT-TYPE
      SYNTAX AccessTerminationEntry
      ACCESS not-accessible
      STATUS mandatory
      DESCRIPTION "Entry holding configuration information for a configured user port."
      INDEX {accTerminationHldrEquipmentId, accTerminationUserPortId}
   ::= {accessTerminationTable 1}
   
   AccessTerminationEntry ::= SEQUENCE
   {
      accTerminationHldrEquipmentId AccessEquipmentId, 
      accTerminationUserPortId TerminationUserPortId, 
      accTerminationRowStatus RowStatus, 
      accTerminationtId AccessTerminationId, 
      accTerminationAssocMedGwyId MediaGatewayId, 
      accTerminationOperStatus INTEGER, 
      accTerminationAdminStatus INTEGER, 
      accTerminationLineCharact INTEGER, 
      accTerminationUserPortType INTEGER, 
      accTerminationPacketSwitchType INTEGER, 
      accTerminationL1ActivateType  INTEGER, 
      accTerminationImpedance       INTEGER, 
      accTerminationGain       INTEGER, 
      accTerminationIdStr	DisplayString, 
      accTerminationLockType		INTEGER, 
      accTerminationLockDelay	INTEGER, 
      accTerminationVoiceDscp INTEGER, 
      accTerminationVoiceDot1P INTEGER, 
      accTerminationETSIClipDataMode INTEGER 
   }
   
   accTerminationHldrEquipmentId OBJECT-TYPE
      SYNTAX AccessEquipmentId
      ACCESS not-accessible
      STATUS mandatory
      DESCRIPTION "Internal identifier of the ISAM-V NE holding
                   the board owner of this user port."
   ::= {accessTerminationEntry 1}
   
   accTerminationUserPortId OBJECT-TYPE
      SYNTAX TerminationUserPortId
      ACCESS not-accessible
      STATUS mandatory
      DESCRIPTION "User Port identifier composed of the rack number (4 bits),
                   subrack number (4 bits), slot number (8 bits) and
                   port number (16 bits)."
   ::= {accessTerminationEntry 2}
   
   accTerminationRowStatus OBJECT-TYPE
      SYNTAX RowStatus
      ACCESS read-write
      STATUS mandatory
      DESCRIPTION "Allows to control the creation and deletion
                   of rows in this table."
   ::= {accessTerminationEntry 3}
   
   accTerminationtId OBJECT-TYPE
      SYNTAX AccessTerminationId
      ACCESS read-write
      STATUS mandatory
      DESCRIPTION "Unique identifier of this termination,for pstn termination,its range
                   is [0,32767],for isdn termination, its range is [0,8175]."
   ::= {accessTerminationEntry 4}
   
   accTerminationAssocMedGwyId OBJECT-TYPE
      SYNTAX MediaGatewayId
      ACCESS read-write
      STATUS mandatory
      DESCRIPTION "Identifier of the associated media gateway."
   ::= {accessTerminationEntry 5}
   
   accTerminationOperStatus OBJECT-TYPE
      SYNTAX INTEGER
      {
         up (1),
         down (2),
         shuttingdown (3)
      }
      ACCESS read-only
      STATUS mandatory
      DESCRIPTION "The current operational state of this user port.
      		ALCATEL NOTE 
		ACCESS: RO 
		USAGE: MAN 
		PERSIST: NO 
		INSRVMOD: NO 
		RANGE: NA 
		DEFVALUE: NA 
		UNITS: NA 
		SPARSE: NO 
		DESCR: NA ."
   ::= {accessTerminationEntry 6}
   
   accTerminationAdminStatus OBJECT-TYPE
      SYNTAX INTEGER
      {
         locked (1),
         unlocked (2)
      }
      ACCESS read-write
      STATUS mandatory
      DESCRIPTION "The current administrative state of this user port."
      DEFVAL {locked}
   ::= {accessTerminationEntry 7}
   
   accTerminationLineCharact OBJECT-TYPE
      SYNTAX INTEGER
      ACCESS read-write
      STATUS mandatory
      DESCRIPTION "Line characteristics of the termination. Possible values
                   are 25 meaning 25 mA feeding and
                   40 meaning 40 mA feeding."
      DEFVAL {25}
   ::= {accessTerminationEntry 8}

   accTerminationUserPortType OBJECT-TYPE
   	SYNTAX INTEGER
   	{
   		pstn(1),
   		isdn(2)
   	}
   	ACCESS read-write
   	STATUS mandatory
   	DESCRIPTION "The type of the user port. "
        DEFVAL {pstn}
   ::= {accessTerminationEntry 9}

   accTerminationPacketSwitchType OBJECT-TYPE
   	SYNTAX INTEGER
   	{
   		enable(1),
   		disable(2)
   	}
   	ACCESS read-write
   	STATUS mandatory
   	DESCRIPTION "The type of the packet switch type. "
	DEFVAL {disable}
   ::= {accessTerminationEntry 10}

   accTerminationL1ActivateType OBJECT-TYPE
   	SYNTAX INTEGER
   	{
   		permanent(1),
   		percall(2)
   	}
   	ACCESS read-write
   	STATUS mandatory
   	DESCRIPTION "The type of the Layer1 activate type. "
 	DEFVAL {permanent}
   ::= {accessTerminationEntry 11}

  accTerminationImpedance OBJECT-TYPE
      SYNTAX INTEGER
      ACCESS read-write
      STATUS mandatory
      DESCRIPTION "Impedance index (1-15), 1 means default value.
                   1: default value.
                   2: 200 Ohm+(680 Ohm//100nF)
                   3: 220 Ohm+(820Ohm//120nF)
                   4: 220 Ohm+(820 Ohm//120nF) miniSplitter
                   5: 270 Ohm+(750 Ohm//150nF)
                   6: 300 Ohm+(1000 Ohm//220nF)
                   7: 370 Ohm+(620 Ohm//310nF)
                   8: 600 Ohm
                   9: 900 Ohm
                   10: 370 Ohm+(620 Ohm//310nF) + Splitter
                   11: schmReserved1
                   12: schmReserved2
                   13: schmReserved3
                   14: schmReserved4
                   15: schmReserved5

                   ALCATEL NOTE: 
                     PERSIST: NO 
                     INSRVMOD: NO 
                     RANGE: NA 
                     DEFVALUE: 1 
                     UNITS: NA"
      DEFVAL {1}
   ::= {accessTerminationEntry 12}

   accTerminationGain OBJECT-TYPE
   	SYNTAX INTEGER(-8..8)
   	ACCESS read-write
   	STATUS mandatory
   	DESCRIPTION "Line Gain. "
   	DEFVAL {0}
   ::= {accessTerminationEntry 13}

   accTerminationIdStr	OBJECT-TYPE
   	SYNTAX	DisplayString
   	ACCESS	read-only
   	STATUS	mandatory
   	DESCRIPTION	"The String of the access Termination Id. 
		In this string, it use the digit to replace the medGwyPstnTermFormatStr or
		medGwyIsdnTermFormatStr. The max length is also 72.
		The string is something like the 'AL/Dslam_Id/rack/shelf/slot/port' for PSTN User. 
		And 'BA/Dslam_Id/rack/shelf/slot/port' for ISDN User. It does not contain channel.
		because ISDN User both contain two channels.
		ALCATEL NOTE 
		ACCESS: RO 
		USAGE: MAN 
		PERSIST: NO 
		INSRVMOD: NO 
		RANGE: NA 
		DEFVALUE: NA 
		UNITS: NA 
		SPARSE: NO 
		DESCR: NA ."
   ::= {accessTerminationEntry 14}

   accTerminationLockType	OBJECT-TYPE
   	SYNTAX	INTEGER
   	{
   		force (1),
   		graceful (2)
   	}
   	ACCESS	write-only
   	STATUS	mandatory
   	DESCRIPTION	"The termination lock type.
	Should be set ONLY if the AdminStatus is locked.   	
		ALCATEL NOTE 
		ACCESS: WO 
		USAGE: MAN 
		PERSIST: NO 
		INSRVMOD: NO 
		RANGE: NA 
		DEFVALUE: force 
		UNITS: NA 
		SPARSE: NO 
		DESCR: NA "
   	DEFVAL	{force}
   ::= {accessTerminationEntry 15}  

   accTerminationLockDelay	OBJECT-TYPE
   	SYNTAX	INTEGER (0..3600000)
   	ACCESS	write-only
   	STATUS	mandatory
   	DESCRIPTION	"The delay timer before lock the access termination, 
		The object is only valid when accTerminationLockType  is equal to graceful(2). . 
		The range of this object is equal and large than zero. 
		ALCATEL NOTE 
		ACCESS: WO 
		USAGE: MAN 
		PERSIST: NO 
		INSRVMOD: NO 
		RANGE: From 0 to 3600000 
		DEFVALUE: 0 
		UNITS: MILLISECOND 
		SPARSE: NO 
		DESCR: NA "
   	DEFVAL	{0}
   ::= {accessTerminationEntry 16}

   accTerminationVoiceDscp OBJECT-TYPE
   	SYNTAX INTEGER(-1..63)
   	ACCESS read-write
   	STATUS mandatory
   	DESCRIPTION "Voice DSCP. "
   	DEFVAL {-1}
   ::= {accessTerminationEntry 17}

   accTerminationVoiceDot1P OBJECT-TYPE
   	SYNTAX INTEGER(-1..7)
   	ACCESS read-write
   	STATUS mandatory
   	DESCRIPTION "Voice P-bit. "
   	DEFVAL {-1}
   ::= {accessTerminationEntry 18}

   accTerminationETSIClipDataMode OBJECT-TYPE
	SYNTAX INTEGER
		{
		cdevalue(1),
		fsk(2),
		dtmf(3)
		}
	ACCESS read-write
	STATUS mandatory
	DESCRIPTION
		" The ETSI clip data transmission protocol of the access termination. 
		  The clip data mode can only be configured in PSTN line cards. 
			cdevalue(1)	- CDE configuration will be applied for ETSI CLIP.
			fsk(2)	- fsk will be applied for ETSI CLIP.
			dtmf(3) - dtmf will be applied for ETSI CLIP.
			
		ALCATEL-LUCENT NOTE:
			ACCESS:     read-write
	        USAGE:      OPT
			PERSIST:  	Yes
			INSRVMOD: 	YES
			RANGE:	    1 | 2 | 3
			DEFVALUE: 	1
			UNITS:	    NA	
	        SPARSE:     NO "
	DEFVAL {cdevalue} 
	::= { accessTerminationEntry 19 }

   terminationExtTable OBJECT-TYPE
      SYNTAX SEQUENCE OF TerminationExtEntry
      ACCESS not-accessible
      STATUS mandatory
      DESCRIPTION "Virtual list of configured user ports indexed by
                   the associated media gateway, extended for isdn port."
   ::= {accessTerminationConfig 3}
   
   terminationExtEntry OBJECT-TYPE
      SYNTAX TerminationExtEntry
      ACCESS not-accessible
      STATUS mandatory
      DESCRIPTION "Virtual entry holding configuration information for a
                   configured user port."
      INDEX {terminationExtAssocMedGwyId, terminationExtUserPortType, terminationExtId}
   ::= {terminationExtTable 1}
   
   TerminationExtEntry ::= SEQUENCE
   {
      terminationExtAssocMedGwyId MediaGatewayId, 
      terminationExtUserPortType INTEGER, 
      terminationExtId AccessTerminationId, 
      terminationExtHldrEquipmentId AccessEquipmentId, 
      terminationExtUserPortId TerminationUserPortId 
   }
   
   terminationExtAssocMedGwyId OBJECT-TYPE
      SYNTAX MediaGatewayId
      ACCESS not-accessible
      STATUS mandatory
      DESCRIPTION "Identifier of the associated media gateway."
   ::= {terminationExtEntry 1}
     
   terminationExtUserPortType OBJECT-TYPE
   	SYNTAX INTEGER
   	{
   		pstn(1),
   		isdn(2)
   	}
   	ACCESS not-accessible
   	STATUS mandatory
   	DESCRIPTION "The type of the user port." 
   ::= { terminationExtEntry 2}

   terminationExtId OBJECT-TYPE
      SYNTAX AccessTerminationId
      ACCESS not-accessible
      STATUS mandatory
      DESCRIPTION "Unique identifier of this termination."
   ::= {terminationExtEntry 3}
  
   terminationExtHldrEquipmentId OBJECT-TYPE
      SYNTAX AccessEquipmentId
      ACCESS read-only
      STATUS mandatory
      DESCRIPTION "Internal identifier of the ISAM-V NE holding
                   the board owner of this user port."
   ::= {terminationExtEntry 4}

   terminationExtUserPortId OBJECT-TYPE
      SYNTAX TerminationUserPortId
      ACCESS read-only
      STATUS mandatory
      DESCRIPTION "User port identifier composed of the rack number (4 bits),
                   subrack number (4 bits), slot number (8 bits) and
                   port number (16 bits)."
   ::= {terminationExtEntry 5}
   
   ivpsParams OBJECT IDENTIFIER ::= {ivpsConfig 1}
   
   ivpsBasicParamsTable OBJECT-TYPE
    SYNTAX SEQUENCE OF IvpsBasicParamsEntry
    ACCESS not-accessible
    STATUS mandatory
    DESCRIPTION "The IVPS basic config params table , including all XLES params and Private params." 
   ::= {ivpsParams 14}
   
   ivpsBasicParamsEntry OBJECT-TYPE
      SYNTAX IvpsBasicParamsEntry
      ACCESS not-accessible
      STATUS mandatory
      DESCRIPTION "The IVPS basic config params entry." 
      INDEX { ivpsBasicParamIndex }
   ::= {ivpsBasicParamsTable 1}
    
   IvpsBasicParamsEntry ::= SEQUENCE
   {
      ivpsBasicParamIndex               INTEGER,
      ivpsBasicParamXLESIPAddress       IpAddress,    
      ivpsBasicParamXLESUDPPort         INTEGER (0..65535),  
      ivpsBasicParamXLESSubnetMask      IpAddress, 
      ivpsBasicParamXLESNextHop         IpAddress,   
      ivpsBasicParamXLESVLAN            INTEGER (0..4093), 
      ivpsBasicParamPrivateIPAddress    IpAddress,
      ivpsBasicParamPrivateSubnetMask   IpAddress,
      ivpsBasicParamPrivateVLAN         INTEGER (0..4093)      
   }   
   
   ivpsBasicParamIndex OBJECT-TYPE
    SYNTAX INTEGER
    ACCESS not-accessible
    STATUS mandatory
    DESCRIPTION "Index of the table. always equals to 1." 
   ::= {ivpsBasicParamsEntry 1}   

   ivpsBasicParamXLESIPAddress OBJECT-TYPE
      SYNTAX IpAddress
      ACCESS read-write
      STATUS mandatory
      DESCRIPTION "Signalling IP address of this IVPS."
   ::= {ivpsBasicParamsEntry 2}
   
   ivpsBasicParamXLESUDPPort OBJECT-TYPE
      SYNTAX INTEGER (0..65535)
      ACCESS read-only
      STATUS mandatory
      DESCRIPTION "Signalling UDP port of this IVPS."
   ::= {ivpsBasicParamsEntry 3}
   
   ivpsBasicParamXLESSubnetMask OBJECT-TYPE
      SYNTAX IpAddress
      ACCESS read-write
      STATUS mandatory
      DESCRIPTION "Signalling subnet mask of this IVPS."
   ::= {ivpsBasicParamsEntry 4}
   
   ivpsBasicParamXLESNextHop OBJECT-TYPE
      SYNTAX IpAddress
      ACCESS read-write
      STATUS mandatory
      DESCRIPTION "Signalling IP address for the next routing hop in this IVPS."
   ::= {ivpsBasicParamsEntry 5}

   ivpsBasicParamXLESVLAN OBJECT-TYPE
      SYNTAX INTEGER (0..4093)
      ACCESS read-write
      STATUS mandatory
      DESCRIPTION "Voice and signalling VLAN of this IVPS. 0 for clean"
   ::= {ivpsBasicParamsEntry 6}

   ivpsBasicParamPrivateIPAddress	OBJECT-TYPE
   	SYNTAX	IpAddress
   	ACCESS	read-write
   	STATUS	mandatory
   	DESCRIPTION	"The private Ip Address of IVPS. 
		The ivpsPrivateIPAddress is used for the voice communication.
		ALCATEL NOTE 
		ACCESS: RW 
		USAGE: MAN 
		PERSIST: YES 
		INSRVMOD: NO 
		RANGE: NA 
		DEFVALUE: 0.0.0.0 
		UNITS: NA 
		SPARSE: NO 
		DESCR: NA "
	DEFVAL {'00000000'H}
   ::= {ivpsBasicParamsEntry 7}

   ivpsBasicParamPrivateSubnetMask	OBJECT-TYPE
   	SYNTAX	IpAddress
   	ACCESS	read-write
   	STATUS	mandatory
   	DESCRIPTION	"The private Subnet Mask of IVPS.
		The ivpsPrivateSubnetMask is used to distinguish the privateSubnet.
		ALCATEL NOTE 
		ACCESS: RW 
		USAGE: MAN 
		PERSIST: YES 
		INSRVMOD: NO 
		RANGE: NA 
		DEFVALUE: 0.0.0.0 
		UNITS: NA 
		SPARSE: NO 
		DESCR: NA "
	DEFVAL {'00000000'H}
   ::= {ivpsBasicParamsEntry 8}

   ivpsBasicParamPrivateVLAN OBJECT-TYPE
      SYNTAX INTEGER (0..4093)
      ACCESS read-write
      STATUS mandatory
      DESCRIPTION "private VLAN of this IVPS. 0 means use the same as XLES Vlan.
      Also this Vlan need configured in the LANX, only configure at the LT port.
      		ALCATEL NOTE 
		ACCESS: RW 
		USAGE: MAN 
		PERSIST: YES 
		INSRVMOD: NO 
		RANGE: NA 
		DEFVALUE: NA
		UNITS: NA 
		SPARSE: NO 
		DESCR: NA "
   ::= {ivpsBasicParamsEntry 9}
   
   ivpsSpontaneousChanges OBJECT IDENTIFIER ::= {ivpsConfig 4}

   ivpsNumberOfSpontaneousChanges OBJECT-TYPE
      SYNTAX Counter
      ACCESS read-only
      STATUS mandatory
      DESCRIPTION
         "This is a counter indicating the number of spontaneous
          changes occured in the IVPS since the system started up.
          Its value is reported via the changeOccured TRAP when a
          change in any object is detected by the IVPS.
          These changes might be got from a Manager by getting
          the value of the ivpsMediaGatewayStatusBitmap and all
          the rows in the ivpsAccTermStatusTable"

      ::= { ivpsSpontaneousChanges 1 }
   
   ivpsMediaGatewayStatusBitmap OBJECT-TYPE
      SYNTAX OCTET STRING
      ACCESS read-only
      STATUS mandatory
      DESCRIPTION
         "This bitmap represents the current values of the 
          mediaGatewayOperStatus and medGwyCtrlrActiveAddress
          atributes of all the currently created Media Gateways.
          
          It contains n bytes: one for each Media Gateway.
          n = Maximum number of Media Gateways (1 in R1)

          Layout:
             MG-1-Status   MG-2-Status      MG-N-Status
            ------------- -------------    -------------
               Byte 1        Byte 2     ...    Byte n

          MG-i-Status Layout:
            - Bit 0 (LSB): mediaGatewayOperStatus for i-th
              Media Gateway.
              Syntax: 1 = Up, 0 = Down
            - Bits 1..2: medGwyCtrlrActiveAddress for i-th
              Media Gateway.(LSB, bit 2 is big)
              Syntax: two bits integer: 1 = primary,
                      2 = secondary, 3 = none, 4 = other
                      note: value bit2 bit1
                                1    0    1
                                2    1    0
                                3    1    1
                                4    0    0
            - Bit 3 : reserved
            	
            	note: in the following, the 'SGI' refer to the signaling gateway
            	      belong to i-th media gateway.
            	
            - Bit 4 : whether SGI is configurated.
              Syntax: 1 = configurated, 0 = not configurated                      
            - Bit 5 : signallingGatewayOperStatus for SGI
              Syntax: 1 = Up, 0 = Down
            - Bits 6..7: signallingGatewayInterfaceAssocASP for SGI
              Syntax: two bits integer: (LSB, bit 7 is big)
                      0 = None,      1 = primary,
                      2 = secondary, 3 = both
                      note: value bit7 bit6
                                0    0    0
                                1    0    1
                                2    1    0
                                3    1    1"
      ::= { ivpsSpontaneousChanges 2 }
      
   ivpsAccEquipmentBitmap OBJECT-TYPE
      SYNTAX Counter
      ACCESS read-only
      STATUS mandatory
      DESCRIPTION
         "This bitmap represents the currently declared Access Equipments
          in this IVPS.
          
          It contains 256 bits (in 32 bytes): one for each Access Equipment. 
          A bit set to one indicates that the corresponding Access Equipment
          is declared in the IVPS. A bit set to zero indicates that such Access
          Equipment is not declared.
          
          To find the accessEquipmentId identifying the corresponding Access Equipment,
          the following formula might be applied:
          
                 accessEquipmentId = ((BN - 1) * 8) + bn
                 BN = Byte Number (1..32)
                 bn = bit number (1..8 (msb))"
            
      ::= { ivpsSpontaneousChanges 3 }
   
   ivpsAccTermStatusTable OBJECT-TYPE
      SYNTAX SEQUENCE OF IvpsAccTermStatusEntry
      ACCESS not-accessible
      STATUS mandatory
      DESCRIPTION
         "This table contains one entry for each created
          Access Equipment. Each entry is indexed by the
          Access Equipment Id. and holds a Bitmap with
          the current Operational Status of all the
          Access Terminations that are configured under
          this Access Equipment."
   ::= { ivpsSpontaneousChanges 4 }
   
   ivpsAccTermStatusEntry OBJECT-TYPE
      SYNTAX IvpsAccTermStatusEntry
      ACCESS not-accessible
      STATUS mandatory
      DESCRIPTION
         "This entry holds a Bitmap with the current
          Operational Status of all the Access Terminations
          that are configured under the Access Equipment
          identified by the ivpsHldrAccEquipmentId index."
      INDEX { ivpsHldrAccEquipmentId }
   ::= { ivpsAccTermStatusTable 1 }
   
   IvpsAccTermStatusEntry ::= SEQUENCE
   {
      ivpsHldrAccEquipmentId AccessEquipmentId, 
      ivpsHldrAccEqptNbrOfChanges Counter,
      ivpsAccTermStatusBitmap OCTET STRING 
   }
   
   ivpsHldrAccEquipmentId OBJECT-TYPE
      SYNTAX AccessEquipmentId
      ACCESS not-accessible
      STATUS mandatory
      DESCRIPTION
         "Internal identifier of the Access Equipment holding
          the Access Terminations whose status is represented
          in this bitmap."
   ::= { ivpsAccTermStatusEntry 1 }
   
   ivpsHldrAccEqptNbrOfChanges OBJECT-TYPE
      SYNTAX Counter
      ACCESS read-only
      STATUS mandatory
      DESCRIPTION
         "This is a counter indicating the number of spontaneous 
         changes occured in the Access Equipment identified by 
         the ivpsHldrAccEqptId index since the system started up."
      ::= { ivpsAccTermStatusEntry 2 }
   
   ivpsAccTermStatusBitmap OBJECT-TYPE
      SYNTAX OCTET STRING
      ACCESS read-only
      STATUS mandatory
      DESCRIPTION
         "This Bitmap represents the current value of the
          accTerminationOperStatus attribute for all the Access
          Terminations that are created under the Access Boards
          that are in turn created under the Access Equipment
          identified by the ivpsHldrAccEquipmentId index.
                   
          It is a variable length Bitmap that contains n*11 bytes:
          each set of 11 bytes represents the information related
          to one created Access Board.
          n = Number of Access Boards created under this
              Access Equipment (maximum = The max number of 
              one node can support, now define it as 24).

          Each set of 11 bytes has the following layout:
          
         RackNumber  ShelfNumber     SlotNumber    72-Bits-UsePortStatusBitmap
            ------------- ------------------------------
           4bits MSB      4bits LSB           Byte 2           Byte 3...Byte 11
                       Byte  1
          
	   *RackNumber: integer value holding the number of rack
	                 where the Access Board is inserted(1..16)
	                 
	   *ShelfNumber: integer value holding the number of shelf
	   		   where the Access Board is inserted(1..16)
	   		   
          * SlotNumber: integer value holding the number of slot
                        where the Access Board is inserted (1..16)
          
          * 72-Bits-UsePortStatusBitmap Layout:
            - Bit 0 (LSB): accTerminationOperStatus for the
                           Access Termination associated to
                           the first User Port in this Access
                           Board.

            - Bit 1:        accTerminationOperStatus for the
                            Access Termination associated to
                            the second User Port in this Access
                            Board.
          
            - Bit 71 (MSB): accTerminationOperStatus for the
                            Access Termination associated to
                            the 72-th User Port in this Access
                            Board. "
   ::= { ivpsAccTermStatusEntry 3 }   
   
   ivpsTraps OBJECT IDENTIFIER ::= {ivpsConfig 2}

   ivpsStatusChangeSource OBJECT-TYPE
      SYNTAX OBJECT IDENTIFIER
      ACCESS not-accessible
      STATUS mandatory
      DESCRIPTION "OID of the changing object"
   ::= {ivpsTraps 1}
   
   ivpsStatusChangeValue OBJECT-TYPE
      SYNTAX INTEGER (0..65535)
      ACCESS not-accessible
      STATUS mandatory
      DESCRIPTION "New value of the changing object"
   ::= {ivpsTraps 2}

    ivpsCapacity OBJECT IDENTIFIER ::={ivpsConfig 5}

    capaLineImpedanceBitmap OBJECT-TYPE
      SYNTAX OCTET STRING(SIZE(0..31))
      ACCESS read-only
      STATUS mandatory
      DESCRIPTION "This bitmap represents the current supported line impedance scheme
                  index, each bit stands for a line impedance type.
              Bit 0:reserved
              Bit 1:reserved
              Bit 2:200 Ohm+(680 Ohm//100nF)
	      Bit 3:220 Ohm+(820 Ohm//120nF)
	      Bit 4:220 Ohm+(820 Ohm//120nF) miniSplitter
	      Bit 5:270 Ohm+(750 Ohm//150nF)
	      Bit 6:300 Ohm+(1000 Ohm//220nF)
	      Bit 7:370 Ohm+(620 Ohm//310nF)
	      Bit 8:600 Ohm
	      Bit 9:900 Ohm
	      Bit 10:370 Ohm+(620 Ohm//310nF) + Splitter
              Bit 11:schmReserved1
              Bit 12:schmReserved2
              Bit 13:schmReserved3
              Bit 14:schmReserved4
              Bit 15:schmReserved5

	      Bit 16-31:reserved
              Syntax:1--support, 0--unsupport."
   ::={ivpsCapacity 1}

    ivpsDBParams OBJECT IDENTIFIER ::={ivpsConfig 6}

    ivpsSaveConfiguration OBJECT-TYPE
   	SYNTAX	INTEGER
   	{
   		save(1)
   	}
      ACCESS write-only
      STATUS mandatory
      DESCRIPTION "When this object is set to 'save', all unsaved configuration
            of XVPS will be saved to NT."
   ::={ivpsDBParams 1}

    ivpsSaveConfigProgress OBJECT-TYPE
   	SYNTAX	INTEGER
   	{
   		ongoing(1),
   		finishedAndSuccessful(2),
   		finishedButFailed(3)
   	}
      ACCESS read-only
      STATUS mandatory
      DESCRIPTION "This object is used to sepcify the current status of saving configuration
           progress. The value can be one of the following three:ongoing(1),finishedAndSuccessful(2),
           finishedButFailed(3). "
   ::={ivpsDBParams 2}

  LTSessionCmd ::= INTEGER
  {
    create(1),      	
    starttest(2),    	
    sendinfo(3),  	    
    startinfo(4),      	
    destroy(5),         
    receiveSubTest(6),  
    startSubTest(7),    
    repeat(8),          
    endtest(9)          
  }           
                      
  LTSessionState ::= INTEGER
  {
	  idle(1),               
	  revcmd(2),         
	  runcmd(3),         
	  revinfo(4),          
	  testover(5),        
	  stateerror(6),      
	  testhold(7)         
  }
  
  LTLineIdStatus ::= INTEGER
  {
  	intest(1),         
  	testover(2),       
  	rstpartlyready(3)  
  }

   LTLineIdHookChangeStatus ::= INTEGER
  {
  	fromOffhooktoOnhook(1),   
  	fromOnhooktoOffhook(2)    
  }

  LTTestMode ::= INTEGER
  {
    single(1),       
    block(2),        
    continuous(3),   
    interactive(4),  
    cablepair(5)     
  }
  
LTSessionInputErrCode ::= INTEGER
{
	noErr(0),				 
	ltTestParamNumInconsistent(1),           
 	ltTestParamNumOutOfRange(2),             
	testTypeNeedNoParam(3),                  
        testParamForNonTestingType(4),           
	missingltTestParamConfiguration(5),  	 
	missingltTimeOutPeriod(6),               
  	ltTimeOutPeriodNotEnough(7),	         
	ltLineNumInconsistent(8),          	 
	ltLineNumOutOfRange(9),		         
	invalidLineId(10),              	 
        duplicatedLineId(11),                    
    	missingltTestType(12),                   
	invalidTestType(13),		         
	thresholdNumOutOfRange(14),	         
	testTypeNeedNoThreshold(15),             
	thresholdForNonTestingType(16),    	 
	testTypeMismatchTestMode(17),            
	ltlineNumMismatchTestModeOrTestType(18), 
	wrongLineStatusForSubTest(19),       	 
	oneTestItemForBlockOrContinousTest(20),  
        lineIdInNonTestingStatus(21),               
        testModeNotSupportRepeatTest(22),           
        sessionStateIncorrect(23),                  
	systemInternalError(24), 		    
        sessionInactiveTimerOutOfRange(25)          

}
                      
  LTCommonErrCode ::= INTEGER
  { 
    testFinished(1),                    
    testStopedbyTimeOut(2),             
    testCanceledbyOperator(3),          
    testBreakedbyUser(5),               
    testPPFailed(6),                    
    testLineBusyInTestNow(8),           
    testLongTimeNoNextOperator(9),      
    testLineStatusError(11),            
    testOutofMemory(12),                
    testTimerOperateFail(13),           
    testTypeEmpty(14),                  
    testTypeLogicError(15),             
    testTypeUnknown(16),                
    testParaLineIDError(17),            
    testParaOperateError(18),           
    testParaSerialNumError(19),         
    testCurrentLineInTesting(21),       
    testOtherFail(22),                  
    testEndedbyOperator(23),            
    testOnHookbyOperator(24),           
    testParaValueError(26),             
    
    sessionTimeout(105),                
    invalidPortID(106),                 
    pOLTMessageMissing(107),            
    redundancyPorts(110),               
    wrongEndTestSequenceNumber(112),    
    portDisable(114),                   
    pOLTFail(117),                      
    portUnknownState(118),              
    outOfMem(119),                      
    newTimerErr(120),                   
    startTimerErr(121),                 
    sendMsgErr(122),                    
    getPortIpudpErr(123),               
    portEnableLock(124),                
    portDisableUnlock(125),             
    portDisableLock(126),               
    abortTimerErr(127),                 
    emptyTestType(128),                 
    testTypeMismatchWithMode(129),      
    portDisableNetUnlock(130),          
    portDisableVaUnlockGroundKey(131),        
    portDisableVaUnlockOverCurrent(132),      
    portDisableVaUnlockOverTemperature(133),  
    portDisableNetLock(134),                  
    portDisableVaLockGroundKey(135),          
    portDisableVaLockOverCurrent(136),        
    portDisableVaLockOverTemperature(137),    
    portNotSupportLineTest(138),               
    portUndergoinginMTATest(139),            
    testCurrentLTboardInTesting(140)      
    
  }

  LTErrCode ::= INTEGER    
  {
    pPSuccess(1),
    pPErrNomMeasurementFailed(2),
    pPErrNomHookDetected(3),
    pPErrNomAlreadyRunning(4),
    pPErrNomNotImplemented(5),       
    pPErrNetOffhookDETECTED(6),
    pPErrNetInvalidOPMODE(7),
    pPErrNetOther(8),
    pPErrNetVinUnsupp(9),
    pPErrNetSlicUnsupp(10),
    testBeyondCDEThreshold(11),               
    testTimeout(12),
    testInterrupted(13),             
    testErrOther(14),
    testErrofVinetic(15),            
    testErrLineIsOnHook(16),         
    testErrLineIsOffHook(17),        
    testBeyondConfigedThreshold(18)  
  }        

  LTTestType ::= INTEGER
  {
    eFEACofUserLineTestingTR(1),              
    eFEACofUserLineTestingTG(2),              
    eFEACofUserLineTestingRG(3),              
    eFOACofUserLineTestingTR(4),              
    eFOACofUserLineTestingTG(5),              
    eFOACofUserLineTestingRG(6),              
    eFEDCofUserLineTestingTR(7),              
    eFEDCofUserLineTestingTG(8),              
    eFEDCofUserLineTestingRG(9),              
    eFODCofUserLineTestingTR(10),             
    eFODCofUserLineTestingTG(11),             
    eFODCofUserLineTestingRG(12),             
    eFeedingCurrentTesting(13),                    
    eFEDCofUserLineTestingRT(14),             
    eInsulatingRofUserLineTestingTR(15),      
    eInsulatingRofUserLineTestingRT(16),      
    eInsulatingRofUserLineTestingTG(17),      
    eInsulatingRofUserLineTestingRG(18),      
    eInsulatingRBatofUserLineTestingT(19),   
    eInsulatingRBatofUserLineTestingR(20),   
    eCofUserLineTestingTR(21),                
    eCofUserLineTestingRT(22),                
    eCofUserLineTestingTG(23),                
    eCofUserLineTestingRG(24),                
    eImpedanceofUserCircuitTestingTR(25),     
    eImpedanceofUserCircuitTestingRT(26),     
    eImpedanceofUserCircuitTestingTG(27),     
    eImpedanceofUserCircuitTestingRG(28),     
    eLowCapcitancePhoneDetect(29),            
    eReservedForFuture(30),                   
    eDTDelayofUserCircuitTesting(31),         
    eTerminationTesting(32),                  
    eNormalACCurrentTestTestingTR(33),        
    eNormalACCurrentTestTestingTG(34),        
    eNormalACCurrentTestTestingRG(35),        
    eNormalDCCurrentTestTestingTR(36),        
    eNormalDCCurrentTestTestingTG(37),        
    eNormalDCCurrentTestTestingRG(38),        
    eNormalNoiseLevelTesting(40),             
    eNormalContitionHowlerTesting(42),        
    eStatusMonitoredTesting(44),              
    eCablePairIdentification(45),             
    eTalkingtest(46),                         
    eLinereverse(47),                         
    ePrivateMeterPulses(48),                  
    eRingSubscriber(49),                      
    eDPDTMFSignal(50),                        
    eRofUserLoopTesting(51),                 
    eCapacitanceOfSignature(52),             
    eResistanceOfRinger(53),                   
    eISDNLoopBack(54)				
  }
  
  LTHowlerToneTestResult ::= INTEGER
  {
    playSuccessfulAndOnHookNormal(1),
    playSuccessfulAndTestTerminated(2),
    playSuccessfulButOnHookTimeout(3), 
    playFailed(4)
  } 
  
  LTStatusMonitoredTestResult ::= INTEGER
  {
    eStatusMonitoredBlock(2),  
    eStatusMonitoredIdle(3), 
    eStatusMonitoredBusy(4), 
    eStatusMonitoredParking(5),
    eStatusMonitoredShort(6) 
  }

  LTTraceToneTestResult ::= INTEGER
  {
    playTraceToneOKTestTerminated(1),
    playTraceToneOKTimeout(2),
    playTraceToneFailed(3),
    stopTraceToneFailed(4)
  }

  LTMeterTestResult ::= INTEGER
  {
    meterSuccess(1),
    meterFailed (2)
  }

  LTLineReverseTestResult ::= INTEGER
  {
    lineReverseOKTestTerminated(1),
    lineReverseOKTimeout(2),
    lineReverseFailed(3)
  }

  LTRingSubscriberTestResult ::= INTEGER
  {
    ringSuccessfulAndTestTerminated(1),
    ringSuccessfulAndStopedByOffHook(2),
    ringSuccessfulAndTimeout(3), 
    ringFailed(4),
    ringFailedBecausePortisOffHook(5),
    ringStopFailed(6)
  } 

  LTDPDTMFSignalTestResult ::= INTEGER
  {
    numberDP1(1),
    numberDP2(2),
    numberDP3(3),
    numberDP4(4),
    numberDP5(5),
    numberDP6(6),
    numberDP7(7),
    numberDP8(8),
    numberDP9(9),
    numberDP0(10),
    starDP(11),      
    poundDP(12),     
    numberDTMF1(65537),      
    numberDTMF2(65538),      
    numberDTMF3(65539),      
    numberDTMF4(65540),      
    numberDTMF5(65541),      
    numberDTMF6(65542),      
    numberDTMF7(65543),      
    numberDTMF8(65544),      
    numberDTMF9(65545),      
    numberDTMF0(65546),      
    starDTMF(65547),      
    poundDTMF(65548)      
  } 

LTLoopbackTestResult ::= INTEGER
{
    testSuccess(1),
    l1LoopFailOnNT(2),
    l1PatternFailOnNT(3),
    l1LoopFailOnLT(4),
    l1PatternFailOnLT(5),
    l1LoopFailOnNTandLT(6),
    l1LoopFailonNTPatternFailOnLT(7),
    l1PatternFailOnNTLoopFailOnLT(8),
    l1PatternFailOnNTandLT(9)
}
  
ltSessionIdAvaiable OBJECT-TYPE
      SYNTAX INTEGER(0..255)
      ACCESS read-only
      STATUS mandatory
      DESCRIPTION "the byte indicate the next available sessionId. 
      Actually, its range is  [1,ltMaxNumberOfSession]. 
      As ltMaxNumberOfSession is set 8 in ALCATEL-LUCENT, so its range is [1,8]      
       0: No available sessionId. 
       1-ltMaxNumberOfSession: the available sessionId.
       
	ALCATEL-LUCENT NOTE:
		ACCESS:     RO
		USAGE:       MAND
		PERSIST:   	NO
		INSRVMOD: 	NA
		RANGE:	(1..8)
		DEFVALUE:  NA
		UNITS:	NA
		SPARSE: NO"
   ::= {ltLineTest 1}

ltMaxNumberOfSession OBJECT-TYPE
      SYNTAX INTEGER(0..255)
      ACCESS read-only
      STATUS mandatory
      DESCRIPTION "the byte indicate the max number of sessions. 
       If this number is (n), then the ltSessionId of ltSessionTable is in [1, n]. 
	ALCATEL-LUCENT NOTE:
		ACCESS:     RO
		USAGE:       MAND
		PERSIST:   	NO
		INSRVMOD: 	NA
		RANGE:	(0..255)
		DEFVALUE:  NA
		UNITS:	NA
		SPARSE: NO"
   ::= {ltLineTest 2}
      
ltSessionTable OBJECT-TYPE
    SYNTAX SEQUENCE OF LtSessionEntry
    ACCESS not-accessible
    STATUS mandatory
    DESCRIPTION "Test Session Table. For network manager to create session, destroy session. 
      ALCATEL-LCENT NOTE: 
		TABLESIZE: 8(because ltMaxNumberOfSession is as 8)
		DESCR:NA."   
 ::= {ltLineTest 3}

ltSessionEntry OBJECT-TYPE
    SYNTAX LtSessionEntry
    ACCESS not-accessible
    STATUS mandatory
    DESCRIPTION "Test Session Table Entry." 
    INDEX { ltSessionId }
   ::= {ltSessionTable 1}
   
LtSessionEntry ::= SEQUENCE
{
   ltSessionId      INTEGER,
   ltSessionCmd     LTSessionCmd,   
   ltSessionStatus  LTSessionState,
   ltSessionOwnerId Gauge,
   ltTimeOutPeriod  Gauge, 
   ltLineNum        INTEGER, 
   ltTestTypeHigh   Gauge, 
   ltTestTypeLow    Gauge,  
   ltTestParamNum   INTEGER,
   ltTestMode       LTTestMode,
   ltTestTypeString OCTET STRING (SIZE (1..255)),   
   ltSessionInputErrCode  LTSessionInputErrCode,
   ltSessionInactiveTimer INTEGER    
}

ltSessionId OBJECT-TYPE
    SYNTAX INTEGER(1..255)
    ACCESS not-accessible
    STATUS mandatory
    DESCRIPTION "Index of the table. 
    Actually, its range is  [1,ltMaxNumberOfSession]. 
    As ltMaxNumberOfSession is set 8 in ALCATEL-LUCENT, so its range is [1,8]  
 	ALCATEL-LUCENT NOTE:
		ACCESS:     NA
		USAGE:       NA
		PERSIST:   	NO
		INSRVMOD: 	NA
		RANGE:	(1..8)
		DEFVALUE:  NA
		UNITS:	NA
		SPARSE: NO"
  ::= {ltSessionEntry 1}
   
ltSessionCmd   OBJECT-TYPE
   SYNTAX     LTSessionCmd
   ACCESS     read-write
   STATUS     mandatory
   DESCRIPTION "This MIB object is used to control the actions on the Test session 
    create create a test session, ready for test data transfering 
    starttest transfer data done, start a test 
    sendinfo start to transfer info data for an underway testing, to cancel 1 or some lines' test task 
    startinfo transfer info data done, start info operation 
    destroy destroy a test session 
    receiveSubTest start to transfer the sub test's data 
    startSubTest transfer sub test's data done, start the sub test 
    repeat repeat the last test, just for continuous mode test. 
    endtest end current test session. 
	ALCATEL-LUCENT NOTE:
		ACCESS:     RW
		USAGE:       MAND
		PERSIST:   	NO
		INSRVMOD: 	NA
		RANGE:	NA
		DEFVALUE:  NA
		UNITS:	NA
		SPARSE: NO"
	::= {ltSessionEntry 2}  

ltSessionStatus   OBJECT-TYPE
     SYNTAX     LTSessionState
     ACCESS     read-only
     STATUS     mandatory
     DESCRIPTION "This MIB object is used to show the session status
	    idle				indicate the session is not initialized, you can create it.
	    revcmd			indicate the session is recieving TEST cmd.
	    runcmd			indicate the session is running TEST cmd.
	    revinfo			indicate the session is recieving INFO cmd.
	    testover		indicate the session test is finished, you can get test result.
	    stateerror	something is wrong. 
	    testhold		indicate the session is held for sub test of talking test or 1 round is finished in continuous test. 
	ALCATEL-LUCENT NOTE:
		ACCESS:     RO
		USAGE:       MAND
		PERSIST:   	NO
		INSRVMOD: 	NA
		RANGE:	NA
		DEFVALUE:  NA
		UNITS:	NA
		SPARSE: NO"
  ::= { ltSessionEntry 3}  

ltSessionOwnerId   OBJECT-TYPE
     SYNTAX     Gauge
     ACCESS     read-write
     STATUS     mandatory
     DESCRIPTION "OwnerId of the session. This is appointed by network manager itself.
	ALCATEL-LUCENT NOTE:
		ACCESS:     RW
		USAGE:       MAND
		PERSIST:   	NO
		INSRVMOD: 	NA
		RANGE:	NA
		DEFVALUE:  NA
		UNITS:	NA
		SPARSE: NO"
  ::= { ltSessionEntry 4}  
	  
ltTimeOutPeriod   OBJECT-TYPE
   SYNTAX     Gauge
   ACCESS     read-write
   STATUS     mandatory
   DESCRIPTION "A parameter used to set the whole test timer including all test items of all lines for the session. Unit(s)
ltTimeOutPeriod should be larger than or equal to the sum of all lines' limited time plus line test management time (TIME_LENGTH_BUFFER_BASED_LT_NEED<2s>).
Each line's limited time is the sum of all the test items' limited time in this line.

Line Test management time per session.
TIME_LENGTH_BUFFER_BASED_LT_NEED                    2s

Below is the limitd time of each test item of each line for NBLT MELT 
TIME_LENGTH_LIMITE_GROUP                            15s+5s(5s is the delay time of discharge)
TIME_LENGTH_LIMITE_FE_AC_OF_USERLINE                3s
TIME_LENGTH_LIMITE_FO_AC_OF_USERLINE                10s
TIME_LENGTH_LIMITE_FE_DC_OF_USERLINE                3s
TIME_LENGTH_LIMITE_FO_DC_OF_USERLINE                10s+5s(5s is the delay time of discharge)
TIME_LENGTH_LIMITE_FEEDING_CURRENT                  3s
TIME_LENGTH_LIMITE_R_OF_USERLOOP                    6s
TIME_LENGTH_LIMITE_INSULATING_R_OF_USERLINE         6s
TIME_LENGTH_LIMITE_C_OF_USERLINE                    5s
IME_LENGTH_LIMITE_IMPEDANCE_OF_USERCIRCUIT          5s
TIME_LENGTH_LIMITE_LOW_CAP_DETECT                   6s
TIME_LENGTH_LIMITE_DT_DELAY_OF_USERCIRCUIT          3s
TIME_LENGTH_LIMITE_M_SOCKET                         6s 
TIME_LENGTH_LIMITE_NORMAL_AC_CURRENTTEST            66s
TIME_LENGTH_LIMITE_NORMAL_DC_CURRENTTEST            66s
TIME_LENGTH_LIMITE_NORMAL_NOISE_LeveL               66s
TIME_LENGTH_LIMITE_NORMAL_CONDITION_Howler          120s
TIME_LENGTH_LIMITE_STATUS_MONITORED                 3s
TIME_LENGTH_LIMITE_CABLE_PAIR_IDENTITY              65s
TIME_LENGTH_LIMITE_TALKING                          3s 
TIME_LENGTH_LIMITE_TALKING_HOLDING                  600s 
TIME_LENGTH_LIMITE_TALKING_TEST_LINE_REVERSE        5s
TIME_LENGTH_LIMITE_TALKING_TEST_METER_PULSE         6s
TIME_LENGTH_LIMITE_TALKING_TEST_RING                60s
TIME_LENGTH_LIMITE_TALKING_TEST_DTMF                60s
Below is the limitd time of each test item of each line for xDSL line test(BBLT MELT)
TIME_LENGTH_LIMITE_GROUP_MELT                       18s
TIME_LENGTH_LIMITE_INCLUDE_ETSI_SIGNATURE_MELT      18
TIME_LENGTH_LIMITE_FO_AC_OF_USERLINE_MELT           5s
TIME_LENGTH_LIMITE_FO_DC_OF_USERLINE_MELT           5s
TIME_LENGTH_LIMITE_INSULATING_R_OF_USERLINE_MELT    18s
TIME_LENGTH_LIMITE_C_OF_USERLINE_MELT               18s
TIME_LENGTH_LIMITE_CABLE_PAIR_IDENTITY              65s
	ALCATEL-LUCENT NOTE:
		ACCESS:     RW
		USAGE:       MAND
		PERSIST:   	NO
		INSRVMOD: 	NA
		RANGE:	NA
		DEFVALUE:  NA
		UNITS:	NA
		SPARSE: NO"
  ::= {ltSessionEntry 5}  

ltLineNum   OBJECT-TYPE
   SYNTAX     INTEGER(1..255)
   ACCESS     read-write
   STATUS     mandatory
   DESCRIPTION "A parameter for the session. Indicate how many LINEs in the session for test, 
             it's to say there are ltLineNum rows in ltLineIdTable for this session. range: [1,72]
	ALCATEL-LUCENT NOTE:
		ACCESS:     RW
		USAGE:       MAND
		PERSIST:   	NO
		INSRVMOD: 	NA
		RANGE:	(1..72)
		DEFVALUE:  NA
		UNITS:	NA
		SPARSE: NO"
  ::= {ltSessionEntry 6}  
	  
ltTestTypeHigh   OBJECT-TYPE
   SYNTAX     Gauge
   ACCESS     read-write
   STATUS     mandatory
   DESCRIPTION "A parameter for the session. Indicate line test items. With ltTestTypeLow they  
                         are a 64bit bitmap for test items.
    --bit31, FE_AC_of_UserLine_Testing(tr),              unit : uV (10-6V) 
    --bit30, FE_AC_of_UserLine_Testing(tg),              unit : uV (10-6V) 
    --bit29, FE_AC_of_UserLine_Testing(rg),              unit : uV (10-6V) 
    --bit28, FO_AC_of_UserLine_Testing(tr),              unit : uV (10-6V) 
    --bit27, FO_AC_of_UserLine_Testing(tg),              unit : uV (10-6V) 
    --bit26, FO_AC_of_UserLine_Testing(rg),              unit : uV (10-6V) 
    --bit25, FE_DC_of_UserLine_Testing(tr),              unit : uV (10-6V) 
    --bit24, FE_DC_of_UserLine_Testing(tg),              unit : uV (10-6V)
    --bit23, FE_DC_of_UserLine_Testing(rg),              unit : uV (10-6V)
    --bit22, FO_DC_of_UserLine_Testing(tr),              unit : uV (10-6V) 
    --bit21, FO_DC_of_UserLine_Testing(tg),              unit : uV (10-6V) 
    --bit20, FO_DC_of_UserLine_Testing(rg),              unit : uV (10-6V) 
    --bit19, Feeding_Current_Testing,                    unit : uA (10-6A)                
    --bit18, FE_DC_of_UserLine_Testing(rt),              unit : uV (10-6V)                     
    --bit17, Insulating_R_of_UserLine_Testing(tr),       unit : ohm
    --bit16, Insulating_R_of_UserLine_Testing(rt),       unit :ohm
    --bit15, Insulating_R_of_UserLine_Testing(tg),       unit : ohm
    --bit14, Insulating_R_of_UserLine_Testing(rg),       unit : ohm
    --bit13, Insulating_R_Bat_of_UserLine_Testin(gt),   unit : ohm
    --bit12, Insulating_R_Bat_of_UserLine_Testin(gr),   unit : ohm
    --bit11, C_of_UserLine_Testing(tr),                  unit : pF
    --bit10, C_of_UserLine_Testing(rt),                  unit : pF
    --bit09, C_of_UserLine_Testing(tg),                  unit : pF
    --bit08, C_of_UserLine_Testing(rg),                  unit : pF
    --bit07, Impedance_of_UserCircuit_Testing(tr),       unit : ohm
    --bit06, Impedance_of_UserCircuit_Testing(rt),       unit : ohm
    --bit05, Impedance_of_UserCircuit_Testing(tg),       unit : ohm
    --bit04, Impedance_of_UserCircuit_Testing(rg),       unit : ohm
    --bit03, Low_Capcitance_PhoneDetect,                 TRUE(1) or FLASE(0)
    --bit02, Reserved_For_Future,                        Reserved
    --bit01, DT_Delay_of_UserCircuit_Testing,        unit : ms                          
    --bit00, Termination_Testing(M Socket),          TRUE(1) or FLASE(0)      
	ALCATEL-LUCENT NOTE:
		ACCESS:     RW
		USAGE:       MAND
		PERSIST:   	NO
		INSRVMOD: 	NA
		RANGE:	NA
		DEFVALUE:  NA
		UNITS:	NA
		SPARSE: NO"
 ::= {ltSessionEntry 7}  
 
ltTestTypeLow   OBJECT-TYPE
   SYNTAX     Gauge
   ACCESS     read-write
   STATUS     mandatory
   DESCRIPTION "A parameter for the session. Indicate line test items. With ltTestTypeHigh they  
                           are a 64bit bitmap for test items
    --bit31, Normal_AC_CurrentTest_Testing(tr),          unit : uV (10-6V) 
    --bit30, Normal_AC_CurrentTest_Testing(tg),          unit : uV (10-6V) 
    --bit29, Normal_AC_CurrentTest_Testing(rg),          unit : uV (10-6V) 
    --bit28, Normal_DC_CurrentTest_Testing(tr),          unit : uV (10-6V) 
    --bit27, Normal_DC_CurrentTest_Testing(tg),          unit : uV (10-6V) 
    --bit26, Normal_DC_CurrentTest_Testing(rg),          unit : uV (10-6V) 
    --bit24, Normal_Noise_Level_Testing,                 unit : 0.001dbm                   
    --bit22, Normal_Contition_Howler_Testing,              enum LTHowlerToneTestResult 
    --bit20, Status_Monitored_Testing,                     enum LTStatusMonitoredTestResult
    --bit19, Cable Pair Identification Test,               enum LTTraceToneTestResult
    --bit18, Talking test (father test item),              enum LTMeterTestResult
    --bit17, Line Reverse test,   subtest of talking test, enum LTLineReverseTestResult
    --bit16, Private Meter Pulses test,   subtest of talking test, logic result
    --bit15, Ring Subscriber with Auto Ring test, subtest of talking test, enum LTRingSubscriberTestResult
    --bit14, DP/DTMF Signal test, subtest of talking test, enum LTDPDTMFSignalTestResult
    --bit13, R_of_UserLoop_Testing,                       unit : ohm    
    --bit12, Capacitance of Signature,               unit:pF
    --bit11, Resistance of Ringer,                    unit:ohm
    --bit10,ISDN Loop Back,					enum LTLoopbackTestResult
    --bit0-10, Reserved. 
    bitmap construct rules:
		we sort all tests into 5 different class by their attribute, and only tests of the same attribute could exist in one session. 
		1) all attribute was defined here: 
		enum eLineTestAttribute{ 
		   Electric, //0, electric parameter test(R,vol,C,current) 
		   DialTone, //1, especially for dail tone test, 
		   AC_DC_CURRENT, //2, especially for AC/DC current test, for it need 2 commands: START or END. 
		   NOISE_LEVEL, //3, only for noise level 
		   HowlerTone, //4, only for howler tone test. 
		   StatusMonitored, //5, only for statusMonitored test. 
	           Talking, //6, for all talking test
                  CabIdentify, //7, only for cable pair identify
	          Butt_LineTestAttribute // 8 	}; 
		2) the relationship between every test and these attribute was described like this table: 
		eFE_AC_of_UserLine_Testing_tr , Electric
		eFE_AC_of_UserLine_Testing_tg , Electric
		eFE_AC_of_UserLine_Testing_rg , Electric
		eFO_AC_of_UserLine_Testing_tr , Electric 
		eFO_AC_of_UserLine_Testing_tg , Electric 
		eFO_AC_of_UserLine_Testing_rg , Electric 
		eFE_DC_of_UserLine_Testing_tr , Electric 
		eFE_DC_of_UserLine_Testing_tg , Electric 
		eFE_DC_of_UserLine_Testing_rg , Electric 
		eFO_DC_of_UserLine_Testing_tr , Electric 
		eFO_DC_of_UserLine_Testing_tg , Electric 
		eFO_DC_of_UserLine_Testing_rg , Electric 
		eFeeding_Current_Testing ,      Electric 
		eR_of_UserLoop_Testing ,        Electric 
		eInsulating_R_of_UserLine_Testing_tr , Electric 
		eInsulating_R_of_UserLine_Testing_rt , Electric 
		eInsulating_R_of_UserLine_Testing_tg , Electric 
		eInsulating_R_of_UserLine_Testing_rg , Electric 
		eInsulating_R_Bat_of_UserLine_Testing_t, Electric 
		eInsulating_R_Bat_of_UserLine_Testing_r, Electric 
		eC_of_UserLine_Testing_tr , Electric 
		eC_of_UserLine_Testing_rt , Electric 
		eC_of_UserLine_Testing_tg , Electric 
		eC_of_UserLine_Testing_rg , Electric 
		eImpedance_of_UserCircuit_Testing_tr , Electric 
		eImpedance_of_UserCircuit_Testing_rt , Electric 
		eImpedance_of_UserCircuit_Testing_tg , Electric 
		eImpedance_of_UserCircuit_Testing_rg , Electric 
		eLowCapcitancePhoneDetect,             Electric 
		eReservedForFuture,                    --- 
		eDT_Delay_of_UserCircuit_Testing , DialTone 
		eTermination_Testing , Electric 
		eNormal_AC_CurrentTest_Testing_tr , AC_DC_CURRENT 
		eNormal_AC_CurrentTest_Testing_tg , AC_DC_CURRENT 
		eNormal_AC_CurrentTest_Testing_rg , AC_DC_CURRENT 
		eNormal_DC_CurrentTest_Testing_tr , AC_DC_CURRENT 
		eNormal_DC_CurrentTest_Testing_tg , AC_DC_CURRENT 
		eNormal_DC_CurrentTest_Testing_rg , AC_DC_CURRENT 
		eNormal_Noise_Level_Testing , NOISE_LEVEL 
		eNormal_Contition_Howler_Testing , HowlerTone 
		eStatus_Monitored_Testing , StatusMonitored 
		eBulk_Testing ,  Electric 
		eGroup_Testing , Electric
		eCablePairIdentification, CabIdentify
		eTalkingtest,             Talking
		eLine reverse,            Talking
		ePrivateMeterPulses,      Talking
		eRingSubscriber,          Talking
		eDP_DTMFSignal,           Talking		  
		eFE_DC_of_UserLine_Testing_rt , Electric
		eCapacitance_Of_Signature,   Electric
		eResistance_Of_Ringer,      Electric
		eISDNLoopBack, ISDN_loopback_test
	ALCATEL-LUCENT NOTE:
		ACCESS:     RW
		USAGE:       MAND
		PERSIST:   	NO
		INSRVMOD: 	NA
		RANGE:	NA
		DEFVALUE:  NA
		UNITS:	NA
		SPARSE: NO"
	::= {ltSessionEntry 8}	

ltTestParamNum   OBJECT-TYPE
   SYNTAX     INTEGER(0..255)
   ACCESS     read-write
   STATUS     mandatory
   DESCRIPTION "A parameter for the session. Indicate how many PARAM lines in the session for test,  it's to say there are ltTestParamNum rows in ltTestParamTable for this session.
	ALCATEL-LUCENT NOTE:
		ACCESS:     RW
		USAGE:       MAND
		PERSIST:   	NO
		INSRVMOD: 	NA
		RANGE:	(0..64)
		DEFVALUE:  NA
		UNITS:	NA
		SPARSE: NO"
  ::= {ltSessionEntry 9}

ltTestMode   OBJECT-TYPE
   SYNTAX     LTTestMode
   ACCESS     read-write
   STATUS     mandatory
   DESCRIPTION "the test mode means whether test should be repeat and which way it repeats.
    single				default value, means the test needn't repeat in program, it will end after one time.
    block					20 rounds test will be done automatically by NBLT after test start, all results would be report together.
    continuous		operator's program will send repeat command to NBLT to start a new round after receive last round's result.
    interactive		the interactive test.
    cablepair			the cable pair test.
	ALCATEL-LUCENT NOTE:
		ACCESS:     RW
		USAGE:       MAND
		PERSIST:   	NO
		INSRVMOD: 	NA
		RANGE:	NA
		DEFVALUE:  NA
		UNITS:	NA
		SPARSE: NO"
  ::= {ltSessionEntry 10}  
	
ltTestTypeString OBJECT-TYPE
   SYNTAX     OCTET STRING (SIZE (1..255))
   ACCESS     read-write
   STATUS     optional
   DESCRIPTION "ready to transfer test type info from ltTestTypeHigh/ltTestTypeLow.	in R3.3v, we defined the this object to replace ltTestTypeHigh/ltTestTypeLow to record the information of which test types operator want to test. Because the ltTestTypeString can including more bits. But 5530 does not want make MIB objects discard, so this object defined but not in use.
	ALCATEL-LUCENT NOTE:
		ACCESS:     RW
		USAGE:       OPT
		PERSIST:   	NO
		INSRVMOD: 	NA
		RANGE:	NA
		DEFVALUE:  NA
		UNITS:	NA
		SPARSE: NO"
  ::= {ltSessionEntry 11}  

ltSessionInputErrCode OBJECT-TYPE
   SYNTAX     LTSessionInputErrCode
   ACCESS     read-only
   STATUS     mandatory
   DESCRIPTION " when start test fails with genErr, this object indicates the detailed reason of the failure. This object is not suitable for H248 linetest, should be ignored..
 	noErr(0),				 -- 0  no error.
	ltTestParamNumInconsistent(1),           -- 1  the actual input param number in ltTestParamTable is not equal to ltTestParamNum.
 	ltTestParamNumOutOfRange(2),             -- 2  the input param number is out of range, from 0 to 4 is allowed.  
	testTypeNeedNoParam(3),                  -- 3  the input test param is meaningless, because those test types not need any test param.
        testParamForNonTestingType(4),           -- 4  the input test param for those test types which are not in current test session.
	missingltTestParamConfiguration(5),  	 -- 5  missing test param configuration for those test types which must have test param.
	missingltTimeOutPeriod(6),               -- 6  missing ltTimeOutPeriod value.
  	ltTimeOutPeriodNotEnough(7),	         -- 7  the input ltTimeOutPeriod is not enough for test.
	ltLineNumInconsistent(8),          	 -- 8  the actual input line number in ltLineIdTable is not equal to ltLineNum.
	ltLineNumOutOfRange(9),		         -- 9  the input line number is out of range, from 1 to 72 is allowed.
	invalidLineId(10),              	 -- 10 the input lineId is invalid.
        duplicatedLineId(11),                    -- 11 the same lineId configed twice
    	missingltTestType(12),                   -- 12 missing ltTestTypeHigh and ltTestTypeLow.
	invalidTestType(13),		         -- 13 the input ltTestTypeHigh and ltTestTypeLow is incorrect.
	thresholdNumOutOfRange(14),	         -- 14 input too many threshold, the number of threshold from 0 to 39 is allowed.
	testTypeNeedNoThreshold(15),             -- 15 the input threshold is meaningless, because those test types do not need any threshold.
	thresholdForNonTestingType(16),    	 -- 16 the input threshold for those test types which are not in current test session.
	testTypeMismatchTestMode(17),            -- 17 the input test type does not match with the test mode.
	ltlineNumMismatchTestModeOrTestType(18), -- 18 the input line number is not match test mode and test type. All talking test, cable pair test, block test and continuous test only support one line for certain test.
	wrongLineStatusForSubTest(19),       	 -- 19 the line status for subtest is not in holding or the line which has no father test first.
	oneTestItemForBlockOrContinousTest(20),  -- 20 block test and continous test must be only one test type
        lineIdInNonTestingStatus(21),               -- 21 the input lineId is not in testing status.
        testModeNotSupportRepeatTest(22),           -- 22 repeate test can only be done in continous test mode
        sessionStateIncorrect(23),                  -- 23 the command not allowed in current session state
	systemInternalError(24), 		    -- 24 internal system error.
        sessionInactiveTimerOutOfRange(25)          -- 25 ltSessionInactiveTimer value out of range
	
	ALCATEL-LUCENT NOTE:
		ACCESS:     RO
		USAGE:       MAN
		PERSIST:   	NO
		INSRVMOD: 	NA
		RANGE:	NA
		DEFVALUE:  NA
		UNITS:	NA
		SPARSE: NO"
  ::= {ltSessionEntry 12}  

ltSessionInactiveTimer OBJECT-TYPE
   SYNTAX     INTEGER(0..65535) 
   ACCESS     read-write
   STATUS     mandatory
   DESCRIPTION "The parameter used to set the timer to destroy the session when it is inactive.
The value can be 0 or from 120 to 65535. value 0 means never destroy the session automatically. and if configured not-zero, the value should be from 120 to 65535 seconds.
The timer can be configured only in session REV_CMD state, in other states, the configuration will NOT allowed.
This active timer is effective in all session states(REV_CMD, REV_INFO, TEST_HOLD and TEST_OVER) except for test running(RUN_CMD).
If there is no GET or SET operations during this period means the session is inactive, then the session will be destroyed automatically when timeout.
Any snmp GET or SET operation will make the timer restart.
If no value is set for this parameter, default value 0 will be used that means never destroy the session automatically in any session states.
For MEGACO Line Test, this object should be ignored.

    ALCATEL-LUCENT NOTE:
                ACCESS:     RW
                USAGE:      OPT 
                PERSIST:        NO
                INSRVMOD:       NA
                RANGE:  (0..65535)
                DEFVALUE: 0
                UNITS:  seconds
                SPARSE: NO"
  ::= {ltSessionEntry 13}

ltLineIdTable OBJECT-TYPE
      SYNTAX SEQUENCE OF LtLineIdEntry
      ACCESS not-accessible
      STATUS mandatory
      DESCRIPTION "LineId Table.
      ALCATEL-LUCENT NOTE: 
		TABLESIZE: 72
		DESCR:NA."   
   ::= {ltLineTest 4}
   
ltLineIdEntry OBJECT-TYPE
      SYNTAX LtLineIdEntry
      ACCESS not-accessible
      STATUS mandatory
      DESCRIPTION "LineId Table Entry." 
      INDEX { ltAssoSessionId, ltLineId }
   ::= {ltLineIdTable 1}
   
LtLineIdEntry ::= SEQUENCE
{
      ltAssoSessionId         INTEGER,    
      ltLineId                Gauge,  
      ltLineIdStatus          LTLineIdStatus, 
      ltRpCommonStat          LTCommonErrCode,   
      ltRpValNum              Gauge, 
      ltLineHookChangeStatus  LTLineIdHookChangeStatus
}

ltAssoSessionId OBJECT-TYPE
      SYNTAX INTEGER(1..255)
      ACCESS not-accessible
      STATUS mandatory
      DESCRIPTION "Index of the table. This sessionId associated with ltSessionId in ltSessionTable. 
      Actually, its range is  [1,ltMaxNumberOfSession]. 
      As ltMaxNumberOfSession is set 8 in ALCATEL-LUCENT, so its range is [1,8] 
	ALCATEL-LUCENT NOTE:
		ACCESS:     NA
		USAGE:       MAND
		PERSIST:   	NO
		INSRVMOD: 	NA
		RANGE:	[1..8]
		DEFVALUE:  NA
		UNITS:	NA
		SPARSE: NO"
   ::= { ltLineIdEntry 1}
   
ltLineId   OBJECT-TYPE
     SYNTAX     Gauge
     ACCESS     not-accessible
     STATUS     mandatory
     DESCRIPTION "This is the Index of LineId Table, It's the identifier of Line, such as 0x01110706
         +--------------+ 
         |    nodeId    |   8 bits. this is the same to EQPTID 
         +--------------+ 
         | Rack |SubRack|   8 bits. 
         +--------------+ 
         |     slot     | 
         +--------------+ 
         |    lineId    | 
         +--------------+ 
   Rack,SubRack and lineId are 1-based. For example: for the port numbers: range from 0x01~0x30. 
       For slot: LT1: 01  LT2: 02 
   Example: 0x 01110510   
            0x 01   11                  05   10 
            (node1) (rack 1,subrack1) (LT5) (port 16)
            
   the mapping between ltLineId(logicIndex) and ifIndex:   
       Change from line test ID to ifindex:
 		       line test line ID format : 0xAABBCCDD
 		       ifindex format:          : 0xBBCC00DD-1
       Change form ifindex to line test ID:
           ifindex format:          : 0xXXYY00ZZ
           line test line ID format : 0x01XXYYZZ+1

	ALCATEL-LUCENT NOTE:
		ACCESS:     NA
		USAGE:       MAND
		PERSIST:   	NO
		INSRVMOD: 	NA
		RANGE:	NA
		DEFVALUE:  NA
		UNITS:	NA
		SPARSE: NO"
    ::= {ltLineIdEntry 2}   
    
ltLineIdStatus     OBJECT-TYPE
     SYNTAX     LTLineIdStatus
     ACCESS     read-write
     STATUS     mandatory
     DESCRIPTION "This is the line status. Include (NOT_IN_TEST, SET_TEST, RESULT_READY)
                  for write   1: create a row for test
                  for read    0: not created
                              2: this line test is over and result is ready  
	ALCATEL-LUCENT NOTE:
		ACCESS:     RW
		USAGE:       MAND
		PERSIST:   	NO
		INSRVMOD: 	NA
		RANGE:	0 | 1 | 2
		DEFVALUE:  NA
		UNITS:	NA
		SPARSE: NO"
 ::= {ltLineIdEntry 3}   
 
ltRpCommonStat   OBJECT-TYPE
 SYNTAX     LTCommonErrCode
     ACCESS     read-only
     STATUS     mandatory
     DESCRIPTION "Result status means the test result status. Filled by LT and interpret by network manager 
	ALCATEL-LUCENT NOTE:
		ACCESS:     RO
		USAGE:       MAND
		PERSIST:   	NO
		INSRVMOD: 	NA
		RANGE:	NA
		DEFVALUE:  NA
		UNITS:	NA
		SPARSE: NO"
  ::= {ltLineIdEntry 4} 
  
ltRpValNum   OBJECT-TYPE
     SYNTAX     Gauge
     ACCESS     read-only
     STATUS     mandatory
     DESCRIPTION "Available results numbers. Indicate the network manager to retrieve the test result. 
      That's to say there are ltRpValNum rows results in ltLineIdExtReportTable associated with the lineId.
	ALCATEL-LUCENT NOTE:
		ACCESS:     RO
		USAGE:       MAND
		PERSIST:   	NO
		INSRVMOD: 	NA
		RANGE:	NA
		DEFVALUE:  NA
		UNITS:	NA
		SPARSE: NO"
  ::= {ltLineIdEntry 5}  
  
  ltLineHookChangeStatus   OBJECT-TYPE
	     SYNTAX     LTLineIdHookChangeStatus
	     ACCESS     read-only
	     STATUS     mandatory
	     DESCRIPTION "Line hook state change.
	                  1: off hook to on hook,
	                  2: on hook to off hook,
	                  others: undefined.
	ALCATEL-LUCENT NOTE:
		ACCESS:     RO
		USAGE:       MAND
		PERSIST:   	NO
		INSRVMOD: 	NA
		RANGE:	1 | 2
		DEFVALUE:  NA
		UNITS:	NA
		SPARSE: NO"
	  ::= {ltLineIdEntry 6} 
	  	  
ltTestParamTable OBJECT-TYPE
	      SYNTAX SEQUENCE OF LtTestParamEntry
	      ACCESS not-accessible
	      STATUS mandatory
	      DESCRIPTION "This Table is used for network manager to set some parameters used in the test.  you can refer to the table in MIB usage for more detailed
     	 ALCATEL-LUCENT NOTE: 
		TABLESIZE: 512(because ltMaxNumberOfSession is 8 and the max test item num of a session is 64, so the table size is 64*ltMaxNumberOfSession=512)
		DESCR:NA."               
	   ::= {ltLineTest 6}	      

ltTestParamEntry OBJECT-TYPE
	      SYNTAX LtTestParamEntry
	      ACCESS not-accessible
	      STATUS mandatory
	      DESCRIPTION "Test Param Table Entry.
	      you can refer to the able in MIB usage for more detailed" 
	      INDEX { ltTestParamAssoSessionId, ltTestType }
	   ::= {ltTestParamTable 1}
	   
LtTestParamEntry ::= SEQUENCE
{
   ltTestParamAssoSessionId INTEGER,
	 ltTestType             LTTestType, 
	 ltValue1               INTEGER, 
	 ltValue2               INTEGER, 
	 ltValue3               INTEGER, 
	 ltValue4               INTEGER, 
	 ltValue5               INTEGER,
	 thresholdMin        INTEGER,
	 thresholdMax        INTEGER
} 
	
ltTestParamAssoSessionId OBJECT-TYPE
      SYNTAX INTEGER(1..255)
      ACCESS not-accessible
      STATUS mandatory
      DESCRIPTION "Index of the table. This value associated with ltSessionId in ltSessionTable. 
      It's range is [1..ltMaxNumberOfSession]. Since ltMaxNumberOfSession is 8, so its range is [1..8].
	ALCATEL-LUCENT NOTE:
		ACCESS:     NA
		USAGE:       MAND
		PERSIST:   	NO
		INSRVMOD: 	NA
		RANGE:	[1..8]
		DEFVALUE:  NA
		UNITS:	NA
		SPARSE: NO"
   ::= { ltTestParamEntry 1}

ltTestType OBJECT-TYPE
      SYNTAX     LTTestType
	ACCESS     not-accessible
	STATUS     mandatory
	DESCRIPTION "Index of the table. The test item associated with the test parameter row
	ALCATEL-LUCENT NOTE:
		ACCESS:     NA
		USAGE:       MAND
		PERSIST:   	NO
		INSRVMOD: 	NA
		RANGE:	NA
		DEFVALUE:  NA
		UNITS:	NA
		SPARSE: NO"
	  ::= {ltTestParamEntry 2} 

ltValue1   OBJECT-TYPE
	     SYNTAX     INTEGER
	     ACCESS     read-write
	     STATUS     mandatory
	     DESCRIPTION "Test parameter value1
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 3}  	  
	  
ltValue2   OBJECT-TYPE
SYNTAX     INTEGER
	     ACCESS     read-write
	     STATUS     mandatory
	     DESCRIPTION "Test parameter value2
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 4} 

ltValue3   OBJECT-TYPE
	     SYNTAX     INTEGER
	     ACCESS     read-write
	     STATUS     mandatory
	     DESCRIPTION "Test parameter value3
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 5} 

ltValue4   OBJECT-TYPE
	     SYNTAX     INTEGER
	     ACCESS     read-write
	     STATUS     mandatory
	     DESCRIPTION "Test parameter value4
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 6} 
	  
ltValue5   OBJECT-TYPE
	     SYNTAX     INTEGER
	     ACCESS     read-write
	     STATUS     mandatory
	     DESCRIPTION "Test parameter value5
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 7}  
	  
thresholdMin   OBJECT-TYPE
	     SYNTAX     INTEGER
	     ACCESS     read-write
	     STATUS     mandatory
	     DESCRIPTION "threshold min of this test type.
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 8}  
	  
thresholdMax   OBJECT-TYPE
	     SYNTAX     INTEGER
	     ACCESS     read-write
	     STATUS     mandatory
	     DESCRIPTION "threshold max of this test type
	ALCATEL-LUCENT NOTE:
		ACCESS:     RW
		USAGE:       MAND
		PERSIST:   	NO
		INSRVMOD: 	NA
		RANGE:	NA
		DEFVALUE:  NA
		UNITS:	NA
		SPARSE: NO"
	  ::= {ltTestParamEntry 9}  
	  
ltReport OBJECT IDENTIFIER ::= {ltLineTest 7}

ltTrapSessionId   OBJECT-TYPE
	     SYNTAX     INTEGER
	     ACCESS     read-only
	     STATUS     mandatory
	     DESCRIPTION "Trap sessionId associated with ltSessionId in ltSessionTable. 
	ALCATEL-LUCENT NOTE:
		ACCESS:     NA
		USAGE:       MAND
		PERSIST:   	NO
		INSRVMOD: 	NA
		RANGE:	NA
		DEFVALUE:  NA
		UNITS:	NA
		SPARSE: NO"
	  ::= {ltReport 1}  	
	    
ltTrapCmd   OBJECT-TYPE
	     SYNTAX     INTEGER 
	     ACCESS     read-only
	     STATUS     mandatory
	     DESCRIPTION "Trap cmd indicate with event happened in ivps. 
                     1: test over,
                     2: sub talking test or 1 round of continuous test finished, result is ready and session is in hold. 
                     3: line hook state change,
                     others: undefined.
	ALCATEL-LUCENT NOTE:
		ACCESS:     NA
		USAGE:       MAND
		PERSIST:   	NO
		INSRVMOD: 	NA
		RANGE:	1 | 2 | 3
		DEFVALUE:  NA
		UNITS:	NA
		SPARSE: NO"
	  ::= {ltReport 2}  	
	  
ltTrapLineId   OBJECT-TYPE
	     SYNTAX     Gauge
	     ACCESS     read-only
	     STATUS     mandatory
	     DESCRIPTION "concerned Line in the event(Cmd). If only one line in test concerned with the Cmd, this value is set to the actual lineId, else the value is set to 0xFFFF.
	ALCATEL-LUCENT NOTE:
		ACCESS:     NA
		USAGE:       MAND
		PERSIST:   	NO
		INSRVMOD: 	NA
		RANGE:	NA
		DEFVALUE:  NA
		UNITS:	NA
		SPARSE: NO"
	  ::= {ltReport 3}  	
	  
ltTrapStatus   OBJECT-TYPE
	     SYNTAX     Gauge
	     ACCESS     read-only
	     STATUS     mandatory
	     DESCRIPTION "reserved object, not defined in this version.
        ALCATEL-LUCENT NOTE:
		ACCESS:     NA
		USAGE:       MAND
		PERSIST:   	NO
		INSRVMOD: 	NA
		RANGE:	NA
		DEFVALUE:  NA
		UNITS:	NA
		SPARSE: NO"
	  ::= {ltReport 4} 

ltTrapLineHookStatus   OBJECT-TYPE
	     SYNTAX     Gauge
	     ACCESS     read-only
	     STATUS     mandatory
	     DESCRIPTION "Line hook state, this object is only relevant for NBLT;
                          for BBLT it should be ignored.
	                  1: on hook
	                  2: off hook,
	                  others: undefined.
	ALCATEL-LUCENT NOTE:
		ACCESS:     NA
		USAGE:       MAND
		PERSIST:   	NO
		INSRVMOD: 	NA
		RANGE:	1 | 2
		DEFVALUE:  NA
		UNITS:	NA
		SPARSE: NO"
	  ::= {ltReport 5} 

ltLineIdExtReportTable OBJECT-TYPE
      SYNTAX SEQUENCE OF LtLineIdExtReportEntry 
      ACCESS not-accessible
      STATUS mandatory
      DESCRIPTION "LineIdReport Multi Results Table.
     	 ALCATEL-LUCENT NOTE: 
		TABLESIZE: 28800
		DESCR:NA."               
   ::= {ltLineTest 8}   
   
ltLineIdExtReportEntry  OBJECT-TYPE
      SYNTAX LtLineIdExtReportEntry 
      ACCESS not-accessible
      STATUS mandatory
      DESCRIPTION "LineIdReport Multi Results Table Entry."
      INDEX { ltExtRpAssoSessionId , ltExtRpAssoLineId, ltExtRpTestType, ltExtRpRstIndex }
   ::= {ltLineIdExtReportTable 1}
   
LtLineIdExtReportEntry ::= SEQUENCE
{
   ltExtRpAssoSessionId INTEGER,    
   ltExtRpAssoLineId    Gauge,  
   ltExtRpTestType      LTTestType, 
   ltExtRpRstIndex      INTEGER,
   ltExtRpStat          LTErrCode,   
   ltExtRpVal           INTEGER,
   ltExtRpVal2          INTEGER,
   ltExtRpVal3          INTEGER,
   ltExtRpVal4          INTEGER,
   ltExtRpVal5          INTEGER
}

ltExtRpAssoSessionId  OBJECT-TYPE
      SYNTAX INTEGER(1..255)
      ACCESS not-accessible
      STATUS mandatory
      DESCRIPTION "Index of the table. This sessionId associates with ltAssoSessionId in ltLineIdTable.
      Actually, its range is  [1,ltMaxNumberOfSession]. 
      As ltMaxNumberOfSession is set 8 in ALCATEL-LUCENT, so its range is [1,8] 
	ALCATEL-LUCENT NOTE:
		ACCESS:     NA
		USAGE:       MAND
		PERSIST:   	NO
		INSRVMOD: 	NA
		RANGE:	[1..8]
		DEFVALUE:  NA
		UNITS:	NA
		SPARSE: NO"
   ::= { ltLineIdExtReportEntry 1}
   
ltExtRpAssoLineId   OBJECT-TYPE
     SYNTAX     Gauge
     ACCESS     not-accessible
     STATUS     mandatory
     DESCRIPTION "This is the Index of LineIdReport Table, 
     It assocuates with ltAssoLineId in ltLineIdTable
	ALCATEL-LUCENT NOTE:
		ACCESS:     NA
		USAGE:       MAND
		PERSIST:   	NO
		INSRVMOD: 	NA
		RANGE:	NA
		DEFVALUE:  NA
		UNITS:	NA
		SPARSE: NO"
    ::= {ltLineIdExtReportEntry 2}   
    
ltExtRpTestType     OBJECT-TYPE
     SYNTAX     LTTestType
     ACCESS     not-accessible
     STATUS     mandatory
     DESCRIPTION " This value associated with ltTestType in LtTestParamEntry.     
	ALCATEL-LUCENT NOTE:
		ACCESS:     NA
		USAGE:       MAND
		PERSIST:   	NO
		INSRVMOD: 	NA
		RANGE:	NA
		DEFVALUE:  NA
		UNITS:	NA
		SPARSE: NO"
 ::= {ltLineIdExtReportEntry 3}   
 
ltExtRpRstIndex   OBJECT-TYPE
     SYNTAX     INTEGER(0..255)
     ACCESS     not-accessible
     STATUS     mandatory
     DESCRIPTION "This is the Index of Multi Results, Current from 1 to 20
	ALCATEL-LUCENT NOTE:
		ACCESS:     NA
		USAGE:       MAND
		PERSIST:   	NO
		INSRVMOD: 	NA
		RANGE:	[1..20]
		DEFVALUE:  NA
		UNITS:	NA
		SPARSE: NO"
    ::= {ltLineIdExtReportEntry 4}   
  	
ltExtRpStat   OBJECT-TYPE
     SYNTAX     LTErrCode
     ACCESS     read-only
     STATUS     mandatory
     DESCRIPTION "Result status means the test result status. Filled by LT and interpret by network manager
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 5}
  
ltExtRpVal   OBJECT-TYPE
     SYNTAX     INTEGER
     ACCESS     read-only
     STATUS     mandatory
     DESCRIPTION "value report from LT.
    line test result value 1 of the specified line and test type
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 6}  
ltExtRpVal2   OBJECT-TYPE
     SYNTAX     INTEGER
     ACCESS     read-only
     STATUS     mandatory
     DESCRIPTION "value report from LT.
     line test result value 2 of the specified line and test type, reserved for future use
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 7} 

ltExtRpVal3   OBJECT-TYPE
     SYNTAX     INTEGER
     ACCESS     read-only
     STATUS     mandatory
     DESCRIPTION "value report from LT.
        line test result value 3 of the specified line and test type , reserved for future use
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 8}

ltExtRpVal4   OBJECT-TYPE
     SYNTAX     INTEGER
     ACCESS     read-only
     STATUS     mandatory
     DESCRIPTION "value report from LT.
        line test result value 4 of the specified line and test type , reserved for future use
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 9}

ltExtRpVal5   OBJECT-TYPE
     SYNTAX     INTEGER
     ACCESS     read-only
     STATUS     mandatory
     DESCRIPTION "value report from LT.
        line test result value 5 of the specified line and test type , reserved for future use
	ALCATEL-LUCENT NOTE:
		ACCESS:     RO
		USAGE:       MAND
		PERSIST:   	NO
		INSRVMOD: 	NA
		RANGE:	NA
		DEFVALUE:  NA
		UNITS:	NA
		SPARSE: NO"
  ::= {ltLineIdExtReportEntry 10}  

   signallingGatewayInterfaceTable OBJECT-TYPE
      SYNTAX SEQUENCE OF SignallingGatewayInterfaceEntry
      ACCESS not-accessible
      STATUS mandatory
      DESCRIPTION "List of signalling gateways configured for this MGI."
   ::= {signallingGatewayInterfaceConfig 1}

   signallingGatewayInterfaceEntry OBJECT-TYPE
      SYNTAX SignallingGatewayInterfaceEntry
      ACCESS not-accessible
      STATUS mandatory
      DESCRIPTION "Entry holding configuration information for a gateway."
      INDEX {signallingGatewayInterfaceId}
   ::= {signallingGatewayInterfaceTable 1}

   SignallingGatewayInterfaceEntry ::= SEQUENCE
   {
      signallingGatewayInterfaceId SignallingGatewayInterfaceId, 
      signallingGatewayInterfaceRowStatus RowStatus, 
      signallingGatewayInterfacePrimaryASPIPAddress IpAddress, 
      signallingGatewayInterfacePrimarySCTPPort INTEGER, 
      signallingGatewayInterfaceSecondaryASPIPAddress IpAddress, 
      signallingGatewayInterfaceSecondarySCTPPort INTEGER, 
      signallingGatewayInterfaceAssocASP INTEGER, 
      signallingGatewayInterfaceIPAddress IpAddress, 
      signallingGatewayInterfaceSCTPPort INTEGER, 
      signallingGatewayInterfaceUserLabel DisplayString, 
      signallingGatewayInterfaceMGI MediaGatewayId, 
      signallingGatewayInterfaceAdminStatus INTEGER, 
      signallingGatewayInterfaceOperStatus INTEGER 
   }

   signallingGatewayInterfaceId OBJECT-TYPE
      SYNTAX SignallingGatewayInterfaceId
      ACCESS not-accessible
      STATUS mandatory
      DESCRIPTION "The unique signaling gateway Interface Id which identifies this
                   signaling gateway. Notice: this ID should be same to the ID of MGI it belongs to."
   ::= {signallingGatewayInterfaceEntry 1}

   signallingGatewayInterfaceRowStatus OBJECT-TYPE
      SYNTAX RowStatus
      ACCESS read-write
      STATUS mandatory
      DESCRIPTION "Allows to control the creation and deletion
                   of rows in this table."
   ::= {signallingGatewayInterfaceEntry 2}

   signallingGatewayInterfacePrimaryASPIPAddress OBJECT-TYPE
   	SYNTAX IpAddress
   	ACCESS read-write
      STATUS mandatory   	
   	DESCRIPTION "The IP Address of the Primary ASP."
   ::= {signallingGatewayInterfaceEntry 3}

   signallingGatewayInterfacePrimarySCTPPort OBJECT-TYPE
   	SYNTAX INTEGER(0..65535)
   	ACCESS read-write
      STATUS mandatory   	   	
   	DESCRIPTION "The SCTP Port of the Primary ASP"
   ::= {signallingGatewayInterfaceEntry 4}

   signallingGatewayInterfaceSecondaryASPIPAddress OBJECT-TYPE
   	SYNTAX IpAddress
   	ACCESS read-write
      STATUS mandatory   	   	
   	DESCRIPTION "The IP Address of the Secondary ASP "
   ::= {signallingGatewayInterfaceEntry 5}

   signallingGatewayInterfaceSecondarySCTPPort OBJECT-TYPE
   	SYNTAX INTEGER(0..65535)
   	ACCESS read-write
      STATUS mandatory   	   	
   	DESCRIPTION "The SCTP Port of the Secondary ASP"
        DEFVAL {9900}
   ::= {signallingGatewayInterfaceEntry 6}

   signallingGatewayInterfaceAssocASP OBJECT-TYPE
   	SYNTAX INTEGER
   	{ none  (0),
	    primary (1),
	    secondary (2),
	    both (3)
  	}
   	ACCESS read-only
      STATUS mandatory   	   	
   	DESCRIPTION "The Associated ASP "
   ::= {signallingGatewayInterfaceEntry 7}

   signallingGatewayInterfaceIPAddress OBJECT-TYPE
   	SYNTAX IpAddress
   	ACCESS read-write
      STATUS mandatory   	   	
   	DESCRIPTION "The IP Address of the signalling gateway interface."
   ::= {signallingGatewayInterfaceEntry 8}

   signallingGatewayInterfaceSCTPPort OBJECT-TYPE
   	SYNTAX INTEGER(0..65535)
   	ACCESS read-only
      STATUS mandatory   	   	
   	DESCRIPTION "The SCTP Port of the signalling gateway interface."
   ::= {signallingGatewayInterfaceEntry 9}

   signallingGatewayInterfaceUserLabel OBJECT-TYPE
   	SYNTAX DisplayString
   	ACCESS read-write
      STATUS mandatory   	   	
   	DESCRIPTION "The User Label of the signalling gateway interface.
   	             The max number of the string is 64.
   	             The string accept all printable characters.
   	             It is mandatory parameters of signalling Gateway interface.
			           ALCATEL NOTE:
                 SUPPORT:        YES
                 PERSIST:        YES
                 INSRVMOD:       NA
                 RANGE:  NA
                 DEFVALUE: NA
                 UNITS:  NA"
   ::= {signallingGatewayInterfaceEntry 10}

   signallingGatewayInterfaceMGI OBJECT-TYPE
   	SYNTAX MediaGatewayId
   	ACCESS read-write
      STATUS mandatory   	   	
   	DESCRIPTION "The media gateway inteface ID associated with the 
   				signalling gateway interface."
   ::= {signallingGatewayInterfaceEntry 11}

   signallingGatewayInterfaceAdminStatus OBJECT-TYPE
      SYNTAX INTEGER
      {
         locked (1),
         unlocked (2)
      }
      ACCESS read-write
      STATUS mandatory
      DESCRIPTION "The current administrative state of the gateway."
      DEFVAL {locked}
   ::= {signallingGatewayInterfaceEntry 12}

   signallingGatewayInterfaceOperStatus OBJECT-TYPE
      SYNTAX INTEGER
      {
         up (1), 
         down (2)
      }
      ACCESS read-only
      STATUS mandatory
      DESCRIPTION "The current operational state of the gateway."
   ::= {signallingGatewayInterfaceEntry 13}
   
   signallingGatewayInterfaceNextId OBJECT-TYPE
      SYNTAX TestAndIncr
      ACCESS read-only
      STATUS mandatory
      DESCRIPTION "Next free identifier for a new signallingGatewayInterfaceEntry."
   ::= {signallingGatewayInterfaceConfig 2}
   
END
