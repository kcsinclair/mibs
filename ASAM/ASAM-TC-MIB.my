-- orig ASAM-TC-MIB

ASAM-TC-MIB DEFINITIONS ::= BEGIN

IMPORTS
    asam  FROM SYSTEM-MIB
    Gauge FROM RFC1155-SMI;

AsamProfileIndex    ::= INTEGER(1..65535)

AsamProfileIndexOrZero ::= INTEGER(0..65535)

AsamNextProfileIndex ::= INTEGER(0..65535)

AsamMaxProfileIndex ::= INTEGER(0..65535)

AsamProfilePointer  ::= INTEGER(0..65535)

AsamProfileName     ::= OCTET STRING (SIZE(1..32))

AsamProfileScope    ::= INTEGER {
                           localScope  (1),
                           networkScope(2) 
                        }

AsamProfileRefCount ::= INTEGER(0..65535) 
AsamProfileRefCount32 ::= INTEGER(0..4294967295)

LogLastEntry   ::=  INTEGER (0..4294967295)

LogReset       ::=  INTEGER {
                           resetCompleted      (1),
                           reset               (2)}

LogBufferSize  ::=  INTEGER (0..4294967295)

LogFullAction  ::=  INTEGER {
                            wrap     (1), 
                            halt     (2)}

LogOverflowed  ::=  INTEGER {
                    	 notoverflowed       (1), 
                     	 overflowed  	     (2)}

LogIndex       ::=  INTEGER (0..4294967295)

Uint32 ::= Gauge (0 .. 4294967295)

   NetworkTimeInSeconds ::= INTEGER (0..4294967295) 
      
   NetworkTimeInMiliSeconds ::= INTEGER (0..4294967295) 
      
END

-- orig ipconfig.mib
