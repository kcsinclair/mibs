-- orig ATM-M4_MIB

ATM-M4-MIB DEFINITIONS ::= BEGIN

IMPORTS
     OBJECT-TYPE
        FROM RFC-1212
     enterprises
        FROM RFC1155-SMI
     TruthValue, TimeStamp,TestAndIncr,AutonomousType
        FROM SNMPv2-TC
     ifIndex,OwnerString
        FROM ITF-MIB

      atmVclVpi, atmVclVci
        FROM ATM-MIB
;

atmForum                OBJECT IDENTIFIER ::= { enterprises 353 }
atmForumNetworkManagement    OBJECT IDENTIFIER ::= { atmForum 5 }
atmfM4      OBJECT IDENTIFIER ::= { atmForumNetworkManagement 1 }
atmfM4SnmpNEView               OBJECT IDENTIFIER ::= { atmfM4 3 }
atmfM4MIB           OBJECT IDENTIFIER ::= { atmfM4SnmpNEView 1 }
atmfM4MIBObjects    OBJECT IDENTIFIER ::= { atmfM4MIB 1 }

atmfM4VcTestTable OBJECT-TYPE
     SYNTAX    SEQUENCE OF    AtmfM4VcTestEntry
     ACCESS    not-accessible
     STATUS    mandatory
     DESCRIPTION
          "The ATM Forum M4 VC Termination Point Test table.
          This table allows tests to be run on VCL and VCC
          termination points.

          The operation of this table is entirely analogous to
          that of the ifTestTable in RFC 1573 (which was later
          deprecated in RFC 2233), except that the indexes into
          this table are different."
     ::= { atmfM4MIBObjects 26 }

atmfM4VcTestEntry OBJECT-TYPE
     SYNTAX    AtmfM4VcTestEntry
     ACCESS    not-accessible
     STATUS    mandatory
     DESCRIPTION
          "An entry containing objects for invoking tests on a
          VCL or VCC termination point."
     INDEX          { ifIndex,
                    atmVclVpi,
                    atmVclVci,
                    atmfM4VcTestObject }
     ::= { atmfM4VcTestTable 1 }

AtmfM4VcTestEntry ::= SEQUENCE {
     atmfM4VcTestObject  INTEGER,
     atmfM4VcTestId      TestAndIncr,
     atmfM4VcTestStatus  INTEGER,
     atmfM4VcTestType    AutonomousType,
     atmfM4VcTestResult  INTEGER,
     atmfM4VcTestCode    OBJECT IDENTIFIER,
     atmfM4VcTestOwner   OwnerString
          }

atmfM4VcTestObject OBJECT-TYPE
     SYNTAX    INTEGER {
                    vclTp(1),
                    vccTp(2)
                         }
     ACCESS    not-accessible
     STATUS    mandatory
     DESCRIPTION
          "Specifies whether the test applies to the VCL termination
          point with the specified VPI and VCI values, or to the VCC
          termination point.
          ALCATEL NOTE: A VCL termination point is identified uniquely 
                        by its Ifindex, its VPI value and its VCI value.
                        A VCC termination point is identified uniquely
                        by its Ifindex, its VPI value and its VCI value.
                        In other words, the entry in the AtmfM4VcTestTable
                        indexed by (Ifindex=x, atmVclVpi=y, atmVclVci=z,
                        vclTp) and the entry in the AtmfM4VcTestTable 
                        indexed by (Ifindex=x, atmVplVpi=y, atmVclVci=z, 
                        vccTp) are identical."
     ::= { atmfM4VcTestEntry 1 }

atmfM4VcTestId         OBJECT-TYPE
     SYNTAX   TestAndIncr
     ACCESS   read-write
     STATUS   mandatory    
     DESCRIPTION
          "This object identifies the current invocation of the
          interface's test."
     ::= { atmfM4VcTestEntry 2 }

atmfM4VcTestStatus     OBJECT-TYPE
     SYNTAX   INTEGER { notInUse(1), inUse(2) }
     ACCESS   read-write
     STATUS   mandatory    
     DESCRIPTION
          "This object indicates whether or not some manager
          currently has the necessary 'ownership' required to
          invoke a test on this interface.  A write to this
          object is only successful when it changes its value
          from 'notInUse(1)' to 'inUse(2)'.  After completion of
          a test, the agent resets the value back to
          'notInUse(1)'."
     ::= { atmfM4VcTestEntry 3 }

atmfM4VcTestType       OBJECT-TYPE
     SYNTAX   AutonomousType
     ACCESS   read-write
     STATUS   mandatory    
     DESCRIPTION
          "A control variable used to start and stop operator-
          initiated interface tests.  Most OBJECT IDENTIFIER
          values assigned to tests are defined elsewhere, in
          association with specific types of interface.
          However, this document assigns a value for a full-
          duplex loopback test, and defines the special meanings
          of the subject identifier:

              noTest  OBJECT IDENTIFIER ::= { 0 0 }

          When the value noTest is written to this object, no
          action is taken unless a test is in progress, in which
          case the test is aborted.  Writing any other value to
          this object is only valid when no test is currently in
          progress, in which case the indicated test is
          initiated.

          When read, this object always returns the most recent
          value that atmfM4VcTestType was set to.  If it has not been
          set since the last initialization of the network
          management subsystem on the agent, a value of noTest
          is returned."
     ::= { atmfM4VcTestEntry 4 }

atmfM4VcTestResult  OBJECT-TYPE
     SYNTAX       INTEGER {
                      none(1),          
                      success(2),
                      inProgress(3),
                      notSupported(4),
                      unAbleToRun(5),   
                      aborted(6),
                      failed(7)
                  }
     ACCESS   read-only
     STATUS   mandatory    
     DESCRIPTION
          "This object contains the result of the most recently
          requested test, or the value none(1) if no tests have
          been requested since the last reset.  Note that this
          facility provides no provision for saving the results
          of one test when starting another, as could be
          required if used by multiple managers concurrently."
     ::= { atmfM4VcTestEntry 5 }

atmfM4VcTestCode  OBJECT-TYPE
     SYNTAX   OBJECT IDENTIFIER
     ACCESS   read-only
     STATUS   mandatory    
     DESCRIPTION
          "This object contains a code which contains more
          specific information on the test result, for example
          an error-code after a failed test.  Error codes and
          other values this object may take are specific to the
          type of interface and/or test.  The value may have the
          semantics of either the AutonomousType or
          RowPointer textual conventions as defined in RFC
          1903 [15].  The identifier:

              testCodeUnknown  OBJECT IDENTIFIER ::= { 0 0 }

          is defined for use if no additional result code is
          available."
     ::= { atmfM4VcTestEntry 6 }

atmfM4VcTestOwner      OBJECT-TYPE
     SYNTAX   OwnerString
     ACCESS   read-write
     STATUS   mandatory    
     DESCRIPTION
          "The entity which currently has the 'ownership'
          required to invoke a test on this termination point."
     ::= { atmfM4VcTestEntry 7 }

END
