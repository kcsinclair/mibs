-- These MIBs were created on 05/27/2001
-- This module defines enterprise MIBs for email notification setting
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    email notification settings
--
--  Last modified date: 05/03/2004
--  Modified copyright and contact info
--    
--  Last modified date: 09/28/2001
--    
--  Last modified date: 11/10/2003
--  Correct wrong title
--

NETSCREEN-SET-EMAIL-MIB DEFINITIONS ::= BEGIN
IMPORTS

    DisplayString 	FROM RFC1213-MIB 
    netscreenSetting FROM NETSCREEN-SMI;

    nsSetEmail OBJECT IDENTIFIER ::= { netscreenSetting 7 }
   
    nsSetEmailEnable OBJECT-TYPE
        SYNTAX  INTEGER {
             disable(0),
             enabled(1)
        }
        ACCESS  read-only
        STATUS  mandatory
        DESCRIPTION
            "Enable E-mail Notification for Alarms"
        ::= { nsSetEmail 1 }
    
    nsSetEmailSMTP OBJECT-TYPE
        SYNTAX  DisplayString(SIZE(0..32))
        ACCESS  read-only
        STATUS  mandatory
        DESCRIPTION
            "SMTP server name"
        ::= { nsSetEmail 2 }

    nsSetEmailLog OBJECT-TYPE
        SYNTAX  INTEGER {
        	disable(0),
        	enabled(1)
       	} 
        ACCESS  read-only
        STATUS  mandatory
        DESCRIPTION
            "Include Traffic Log in email"
        ::= { nsSetEmail 3 }

    nsSetEmailAddr1 OBJECT-TYPE
        SYNTAX  DisplayString (SIZE(0..64))
        ACCESS  read-only
        STATUS  mandatory
        DESCRIPTION
            "E-mail receiver address one"
        ::= { nsSetEmail 4 }

    nsSetEmailAddr2 OBJECT-TYPE
        SYNTAX  DisplayString (SIZE(0..64))
        ACCESS  read-only
        STATUS  mandatory
        DESCRIPTION
            "E-mail receiver address two"
        ::= { nsSetEmail 5 }

END
