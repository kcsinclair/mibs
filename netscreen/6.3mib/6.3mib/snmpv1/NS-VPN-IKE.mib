-- These MIBs were created on 05/14/2001
-- This module defines enterprise MIBs for VPN IKE info
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    VPN IKE info
--
--  Last modified date: 05/03/2004
--  Modified copyright and contact info
--
--  Last modified date: 09/28/2001
--    
--  Last modified date: 11/13/2003
--  Correct spelling mistake
--    

NETSCREEN-VPN-IKE-MIB DEFINITIONS ::= BEGIN
IMPORTS

    DisplayString 	FROM RFC1213-MIB 
    netscreenVpn    FROM NETSCREEN-SMI;
    nsVpnIke 	OBJECT IDENTIFIER ::= {netscreenVpn 3}
    
	nsVpnIkeTable OBJECT-TYPE
		SYNTAX  SEQUENCE OF NsVpnIkeEntry
		ACCESS  not-accessible
		STATUS  mandatory
		DESCRIPTION 
		        "IPSec supports the automated generation and negotiation of keys and
		        security associations using the Internet Key Exchange(IKE) protocol.
		        This table collects the IKE configuration in NetScreen device."
		::= { nsVpnIke 1 }

    nsVpnIkeEntry OBJECT-TYPE
        SYNTAX  NsVpnIkeEntry
        ACCESS  not-accessible
        STATUS  mandatory
        DESCRIPTION
               "Each entry in the nsVpnIkeTable holds a set of configuration parameters
               associated with an IKE."
        INDEX   { nsVpnIkeIndex }
        ::= { nsVpnIkeTable 1 }

	NsVpnIkeEntry ::=
		SEQUENCE {
          nsVpnIkeIndex
              INTEGER,
		  nsVpnIkeName
		      DisplayString,
		  nsVpnIkeReplayProc
		      INTEGER,
		  nsVpnIkeGWTun
		      DisplayString,
		  nsVpnIkePh2ProOne
		  	  DisplayString,
		  nsVpnIkePh2ProTwo
		  	  DisplayString,
		  nsVpnIkePh2ProThree
		  	  DisplayString,
		  nsVpnIkePh2ProFour
		  	  DisplayString,
		  nsVpnIkeMonitorEnable
		      INTEGER,
		  nsVpnIkeTransMode
		      INTEGER,
		  nsVpnIkeVsys
		      INTEGER
       }

	nsVpnIkeIndex OBJECT-TYPE
    	SYNTAX  INTEGER
        ACCESS  read-only
        STATUS  mandatory
        DESCRIPTION
             "A unique value for  ike table.  Its value
              ranges between 0 and 65535 and may not be contiguous." 
        ::= { nsVpnIkeEntry 1 }

	nsVpnIkeName OBJECT-TYPE
        SYNTAX  DisplayString (SIZE (0..32))
    	ACCESS  read-only
        STATUS  mandatory
        DESCRIPTION
             "Each IKE configuration can have a readable name."
        ::= { nsVpnIkeEntry 2 }

	nsVpnIkeReplayProc OBJECT-TYPE
        SYNTAX  INTEGER {
        	disable(0),
        	enabled(1)
        }
    	ACCESS  read-only
        STATUS  mandatory
        DESCRIPTION
             "Enable Replay Protection "
        ::= { nsVpnIkeEntry 3 }

	nsVpnIkeGWTun OBJECT-TYPE
        SYNTAX  DisplayString(SIZE(0..32))
    	ACCESS  read-only
        STATUS  mandatory
        DESCRIPTION
             "Remote Gateway Tunnel Name "
        ::= { nsVpnIkeEntry 4 }

	nsVpnIkePh2ProOne OBJECT-TYPE
        SYNTAX  DisplayString(SIZE(0..32))
    	ACCESS  read-only
        STATUS  mandatory
        DESCRIPTION
             "Phase 2 Proposal one "
        ::= { nsVpnIkeEntry 5 }

	nsVpnIkePh2ProTwo OBJECT-TYPE
        SYNTAX  DisplayString(SIZE(0..32))
    	ACCESS  read-only
        STATUS  mandatory
        DESCRIPTION
             "Phase 2 Proposal two"
        ::= { nsVpnIkeEntry 6 }

	nsVpnIkePh2ProThree OBJECT-TYPE
        SYNTAX  DisplayString(SIZE(0..32))
    	ACCESS  read-only
        STATUS  mandatory
        DESCRIPTION
             "Phase 2 Proposal three"
        ::= { nsVpnIkeEntry 7 }

	nsVpnIkePh2ProFour OBJECT-TYPE
        SYNTAX  DisplayString(SIZE(0..32))
    	ACCESS  read-only
        STATUS  mandatory
        DESCRIPTION
             "Phase 2 Proposal four "
        ::= { nsVpnIkeEntry 8 }

	nsVpnIkeMonitorEnable OBJECT-TYPE
        SYNTAX  INTEGER {
             disable(0),
             enabled(1)
        }
    	ACCESS  read-only
        STATUS  mandatory
        DESCRIPTION
             "Enable to monitor VPN tunnel's link status."
        ::= { nsVpnIkeEntry 9 }

	nsVpnIkeTransMode OBJECT-TYPE
        SYNTAX  INTEGER {
             disable(0),
             enabled(1)
        }
    	ACCESS  read-only
        STATUS  mandatory
        DESCRIPTION
             "Transport Mode   Enable (For L2TP-over-IPSec only)  "
        ::= { nsVpnIkeEntry 10 }

	nsVpnIkeVsys OBJECT-TYPE
        SYNTAX  INTEGER
    	ACCESS  read-only
        STATUS  mandatory
        DESCRIPTION
             "vsys the configuration belongs to."
        ::= { nsVpnIkeEntry 11 }
       
END
