-- These MIBs were created on 08/027/2000
-- This module defines enterprise MIBs for VPN IP pool
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    VPN IP Pool
--
--  Last modified date: 05/03/2004
--  Modified copyright and contact info
--
--  Last modified date: 09/28/2001
--    
--  Last modified date: 11/13/2003
--  Correct spelling mistake
--    

NETSCREEN-IPPOOL-MIB DEFINITIONS ::= BEGIN
IMPORTS

    DisplayString 	FROM RFC1213-MIB 
    netscreenVpn    FROM NETSCREEN-SMI;
    nsVpnIpPool 	OBJECT IDENTIFIER ::= {netscreenVpn 9}
    
	nsVpnIpPoolTable OBJECT-TYPE
		SYNTAX  SEQUENCE OF NsVpnIpPoolEntry
		ACCESS  not-accessible
		STATUS  mandatory
		DESCRIPTION 
		        "This table collects all ip pool configuration in NetScreen device. "
		::= { nsVpnIpPool 1 }

    nsVpnIpPoolEntry OBJECT-TYPE
        SYNTAX  NsVpnIpPoolEntry
        ACCESS  not-accessible
        STATUS  mandatory
        DESCRIPTION
               "Each entry in the nsVpnIpPoolEntry holds a set of configuration parameters
               associated with an instance IP pool."
        INDEX   { nsVpnIpPoolIndex }
        ::= { nsVpnIpPoolTable 1 }

	NsVpnIpPoolEntry ::=
		SEQUENCE {
          nsVpnIpPoolIndex
              INTEGER,
		  nsVpnIpPoolName
		      DisplayString,
		  nsVpnIpPoolStartIp
		      IpAddress,
		  nsVpnIpPoolEndIp
		      IpAddress,
          nsVpnIpPoolIpUsed
              INTEGER
       }

	nsVpnIpPoolIndex OBJECT-TYPE
    	SYNTAX  INTEGER
        ACCESS  read-only
        STATUS  mandatory
        DESCRIPTION
             "A unique value for ip pool.  Its value
              ranges between 0 and 65535 and may not be contiguous." 
        ::= { nsVpnIpPoolEntry 1 }

	nsVpnIpPoolName OBJECT-TYPE
        SYNTAX  DisplayString (SIZE (0..32))
    	ACCESS  read-only
        STATUS  mandatory
        DESCRIPTION
             "ip pool name"
        ::= { nsVpnIpPoolEntry 2 }

	nsVpnIpPoolStartIp OBJECT-TYPE
        SYNTAX  IpAddress
    	ACCESS  read-only
        STATUS  mandatory
        DESCRIPTION
             "IP pool’s start ip address."
        ::= { nsVpnIpPoolEntry 3 }

	nsVpnIpPoolEndIp OBJECT-TYPE
        SYNTAX  IpAddress
    	ACCESS  read-only
        STATUS  mandatory
        DESCRIPTION
             "IP pool’s end ip address."
        ::= { nsVpnIpPoolEntry 4 }

	nsVpnIpPoolIpUsed OBJECT-TYPE
    	SYNTAX  INTEGER
        ACCESS  read-only
        STATUS  mandatory
        DESCRIPTION
             "Total number of addresses in use from this pool." 
        ::= { nsVpnIpPoolEntry 5 }
        
END
