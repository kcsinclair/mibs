-- These MIBs were created on 05/27/2001
-- This module defines enterprise MIBs for syslog setting
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    syslog settings
--
--  Last modified date: 05/03/2004
--  Modified copyright and contact info
--    
--  Last modified date: 09/28/2001
--    
--  Last modified date: 11/10/2003
--  Correct spelling mistake
--    

NETSCREEN-SET-LOG-MIB DEFINITIONS ::= BEGIN
IMPORTS

    DisplayString 	FROM RFC1213-MIB 
    netscreenSetting FROM NETSCREEN-SMI;

    nsSetLog    OBJECT IDENTIFIER ::= { netscreenSetting 8 }
    nsSetLogEnable OBJECT-TYPE
        SYNTAX  INTEGER {
             disable(0),
             enabled(1)
        }
        ACCESS  read-only
        STATUS  mandatory
        DESCRIPTION
            "Enable Syslog messages"
        ::= { nsSetLog 1 }
    
    nsSetLogVPNEnable OBJECT-TYPE
        SYNTAX  INTEGER {
             disable(0),
             enabled(1)
        }
        ACCESS  read-only
        STATUS  mandatory
        DESCRIPTION
            "Secure syslog message traffic using VPN encryption"
        ::= { nsSetLog 2 }

    nsSetLogTraffic OBJECT-TYPE
        SYNTAX  INTEGER {
        	disable(0),
        	enabled(1)
       	} 
        ACCESS  read-only
        STATUS  mandatory
        DESCRIPTION
            "Including traffic log when recording administration log "
        ::= { nsSetLog 3 }

    nsSetLogHostName OBJECT-TYPE
        SYNTAX  DisplayString (SIZE(0..32))
        ACCESS  read-only
        STATUS  mandatory
        DESCRIPTION
            "syslog server name or ip address"
        ::= { nsSetLog 4 }

    nsSetLogPort OBJECT-TYPE
        SYNTAX  INTEGER
        ACCESS  read-only
        STATUS  mandatory
        DESCRIPTION
            "syslog server port number"
        ::= { nsSetLog 5 }

    nsSetLogSecFacility OBJECT-TYPE
        SYNTAX  INTEGER {
        	local0(16),
        	local1(17),
        	local2(18),
        	local3(19),
        	local4(20),
        	local5(21),
        	local6(22),
        	local7(23),        	
        	auth-sec(4)
       	} 
        ACCESS  read-only
        STATUS  mandatory
        DESCRIPTION
            "Security Facility of syslog server"
        ::= { nsSetLog 6 }
        
    nsSetLogFacility OBJECT-TYPE
        SYNTAX  INTEGER {
        	local0(16),
        	local1(17),
        	local2(18),
        	local3(19),
        	local4(20),
        	lcoal5(21),
        	local6(22),
        	loca7(23),        	
        	auth-sec(4)
       	} 
        ACCESS  read-only
        STATUS  mandatory
        DESCRIPTION
            "Facility of syslog server "
        ::= { nsSetLog 7 }
        
    nsSetLogLevel OBJECT-TYPE
        SYNTAX  INTEGER {
        	emergency(0),
        	aleart(1),
        	critical(2),
        	error(3), 
        	warning(4),
        	notice(5),
        	info(6),
        	debug(7)
       	} 
        ACCESS  read-only
        STATUS  mandatory
        DESCRIPTION
            "Only log messages with a priority level of
             EMERGENCY/ALERT/CRITICAL/ERROR/WARNING/NOTICE/INFO/DEBUG
             or higher"
        ::= { nsSetLog 8 }
    
    nsSetLogWebTrendsEnable OBJECT-TYPE
        SYNTAX  INTEGER {
        	disable(0),
        	enabled(1)
       	} 
        ACCESS  read-only
        STATUS  mandatory
        DESCRIPTION
            "Enable WebTrends Firewall syslog report."
        ::= { nsSetLog 9 }

    nsSetLogWebTrendsVPNEnable OBJECT-TYPE
        SYNTAX  INTEGER {
             disable(0),
             enabled(1)
        }
        ACCESS  read-only
        STATUS  mandatory
        DESCRIPTION
            "Secure WebTrends message via VPN encryption "
        ::= { nsSetLog 10 }

    nsSetLogWebTrendsHostName OBJECT-TYPE
        SYNTAX  DisplayString (SIZE(0..32))
        ACCESS  read-only
        STATUS  mandatory
        DESCRIPTION
            "WebTrends Host Name"
        ::= { nsSetLog 11 }

    nsSetLogWebTrendsPort OBJECT-TYPE
        SYNTAX  INTEGER
        ACCESS  read-only
        STATUS  mandatory
        DESCRIPTION
            "WebTrends Host Port"
        ::= { nsSetLog 12 }

    
END
