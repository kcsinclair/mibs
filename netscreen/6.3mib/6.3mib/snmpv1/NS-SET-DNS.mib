-- These MIBs were created on 05/027/2001
-- This module defines enterprise MIBs for DNS Configuration
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    all the configuration info  
--
--  Last modified date: 05/03/2004
--  Modified copyright and contact info
--    
--  Last modified date: 09/28/2001
--    
--  Last modified date: 11/10/2003
--  Correct wrong title
--

NETSCREEN-SET-DNS-MIB DEFINITIONS ::= BEGIN
IMPORTS

    DisplayString 	FROM RFC1213-MIB 
    netscreenSetting FROM NETSCREEN-SMI;
    
    nsSetDNS     OBJECT IDENTIFIER ::= { netscreenSetting 3 }

	nsConfigDnsPriSer OBJECT-TYPE
        SYNTAX  IpAddress
    	ACCESS  read-only
        STATUS  mandatory
        DESCRIPTION
             "Primary DNS server ip address"
        ::= { nsSetDNS 1 }

	nsConfigDnsSecSer OBJECT-TYPE
        SYNTAX  IpAddress
    	ACCESS  read-only
        STATUS  mandatory
        DESCRIPTION
             "Secondary DNS server ip address"
        ::= { nsSetDNS 2 }

	nsConfigDnsRefEnable OBJECT-TYPE
        SYNTAX  INTEGER {
        		disable(0),
        		enabled(1)
        }
    	ACCESS  read-only
        STATUS  mandatory
        DESCRIPTION
             "Enable refresh DNS every day."
        ::= { nsSetDNS 3 }

	nsConfigDnsRefTime OBJECT-TYPE
        SYNTAX  DisplayString (SIZE(6))
    	ACCESS  read-only
        STATUS  mandatory
        DESCRIPTION
             "DNS refresh time."
        ::= { nsSetDNS 4 }

END
