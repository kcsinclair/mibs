-- These MIBs were created on 05/27/2001
-- This module defines enterprise MIBs for NS web setting
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    NS web setting
--
--  Last modified date: 05/03/2004
--  Modified copyright and contact info
--    
--  Last modified date: 09/28/2001
--    
--  Last modified date: 11/12/2003
--  Correct spelling mistake
--    

NETSCREEN-SET-WEB-MIB DEFINITIONS ::= BEGIN
IMPORTS

    DisplayString 	FROM RFC1213-MIB 
    netscreenSetting FROM NETSCREEN-SMI;
                              
    nsSetWebUI OBJECT IDENTIFIER ::= { netscreenSetting 12 }                              
    nsSetWebUICfgTable OBJECT-TYPE 
    	SYNTAX SEQUENCE OF NsSetWebUICfgEntry
    	ACCESS not-accessible
    	STATUS mandatory
    	DESCRIPTION
    	        "NetScreen devices provide WebUI for easy administration. This
    	        table collects admin settings relating to WebUI."
    	::= { nsSetWebUI 1 }

    nsSetWebUICfgEntry OBJECT-TYPE
        SYNTAX  NsSetWebUICfgEntry
        ACCESS  not-accessible
        STATUS  mandatory
        DESCRIPTION
               "An entry containing WebUI admin configuration."
        INDEX   { nsSetWebVsys }
        ::= { nsSetWebUICfgTable 1 }

	NsSetWebUICfgEntry ::=
		SEQUENCE {
          nsSetWebVsys
          	  INTEGER,
          nsSetWebIdleTimeout	  
              INTEGER,
		  nsSetWebTimeout
		      INTEGER,
		  nsSetWebPort
		      INTEGER,  
		  nsSetWebSSLPort      
		      INTEGER,
		  nsSetWebSSLCertificate
		      DisplayString,
		  nsSetWebSSLCipher
		      INTEGER
        }   
    nsSetWebVsys OBJECT-TYPE
        SYNTAX  INTEGER
        ACCESS  read-only
        STATUS  mandatory
        DESCRIPTION
            "Virtual system name the configuration belongs to. Also used as table index."
        ::= { nsSetWebUICfgEntry 1 }

    nsSetWebIdleTimeout OBJECT-TYPE
        SYNTAX  INTEGER {
             disable(0),
             enabled(1)
        }
        ACCESS  read-only
        STATUS  mandatory
        DESCRIPTION
            "Enable Web Management Idle Timeout"
        ::= { nsSetWebUICfgEntry 2 }

    nsSetWebTimeout OBJECT-TYPE
        SYNTAX  INTEGER 
        ACCESS  read-only
        STATUS  mandatory
        DESCRIPTION
            "Web Management Idle Timeout Setting "
        ::= { nsSetWebUICfgEntry 3 }

    nsSetWebPort OBJECT-TYPE
        SYNTAX  INTEGER 
        ACCESS  read-only
        STATUS  mandatory
        DESCRIPTION
            "Web Management Http port number setting."
        ::= { nsSetWebUICfgEntry 4 }

    nsSetWebSSLPort OBJECT-TYPE
        SYNTAX  INTEGER 
        ACCESS  read-only
        STATUS  mandatory
        DESCRIPTION
            "Web Management http ssl port number setting."
        ::= { nsSetWebUICfgEntry 5 }

    nsSetWebSSLCertificate OBJECT-TYPE
        SYNTAX  DisplayString(SIZE(0..255))  
        ACCESS  read-only
        STATUS  mandatory
        DESCRIPTION
            "SSL certificate web management."
        ::= { nsSetWebUICfgEntry 6 }

    nsSetWebSSLCipher OBJECT-TYPE
        SYNTAX  INTEGER {
            rc4-md5(0),
            rc4-40-md5(1),
            des-sha(2),
			triple-des-sha(3)
        }
        ACCESS  read-only
        STATUS  mandatory
        DESCRIPTION
            "Web Management via SSL cipher algorithm"
        ::= { nsSetWebUICfgEntry 7 }
    
END
