-- These MIBs were created on 05/08/2000
-- This module defines enterprise MIBs for Virtual systems
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    Virtual Systems 
--
--  Last modified date: 05/03/2004
--  Modified copyright and contact info
--
--  Last modified date: 09/28/2001
--    
--  Last modified date: 11/13/2003
--  Correct spelling mistake
--    

NETSCREEN-VSYS-MIB DEFINITIONS ::= BEGIN
IMPORTS

    DisplayString 	FROM RFC1213-MIB 
    netscreenVsys    FROM NETSCREEN-SMI;
    nsVsysCfg 	OBJECT IDENTIFIER ::= {netscreenVsys 1}
    
	nsVsysCfgTable OBJECT-TYPE
		SYNTAX  SEQUENCE OF NsVsysCfgEntry
		ACCESS  not-accessible
		STATUS  mandatory
		DESCRIPTION 
		        "NetScreen-500, NetScreen-1000 and above series support virtual system.
		        This table collects the vsys configuration in NetScreen device."
		::= { nsVsysCfg 1 }

    nsVsysCfgEntry OBJECT-TYPE
        SYNTAX  NsVsysCfgEntry
        ACCESS  not-accessible
        STATUS  mandatory
        DESCRIPTION
               "Each entry in the table holds a set of configuration parameters associated 
               with an instance of virtual system."
        INDEX   { nsVsysCfgId }
        ::= { nsVsysCfgTable 1 }

	NsVsysCfgEntry ::=
		SEQUENCE {
          nsVsysCfgId
              INTEGER,
		  nsVsysCfgName
		      DisplayString
       }

	nsVsysCfgId OBJECT-TYPE
    	SYNTAX  INTEGER
        ACCESS  read-only
        STATUS  mandatory
        DESCRIPTION
             "A unique ID for each virtual system." 
        ::= { nsVsysCfgEntry 1 }

	nsVsysCfgName OBJECT-TYPE
        SYNTAX  DisplayString (SIZE (0..32))
    	ACCESS  read-only
        STATUS  mandatory
        DESCRIPTION
             "virtual system name."
        ::= { nsVsysCfgEntry 2 }       
END
