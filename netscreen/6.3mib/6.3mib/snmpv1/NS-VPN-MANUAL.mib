-- These MIBs were created on 05/14/2001
-- This module defines enterprise MIBs for VPN Manual Key 
-- 
-- Copyright (c) 1999-2004, Juniper Networks, Inc.
-- All rights reserved.
-- 
-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Last modified date: 05/03/2004
--  Modified copyright and contact info
--
--  Last modified date: 09/28/2001
--
--  05/21/02 zwang add sha-256 in nsVpnManualKeyEspAuthAlg
--
--  Last modified date: 11/13/2003
--  Correct spelling mistake
--    

NETSCREEN-VPN-MANUAL-MIB DEFINITIONS ::= BEGIN
IMPORTS

    DisplayString 	FROM RFC1213-MIB 
    netscreenVpn    FROM NETSCREEN-SMI;
    nsVpnManualKey 	OBJECT IDENTIFIER ::= {netscreenVpn 2}
    
	nsVpnManualKeyTable OBJECT-TYPE
		SYNTAX  SEQUENCE OF NsVpnManualKeyEntry
		ACCESS  not-accessible
		STATUS  mandatory
		DESCRIPTION 
		        "This table specifies the configuration attributes for NetScreen
		        device's manual key setting."
		::= { nsVpnManualKey 1 }

    nsVpnManualKeyEntry OBJECT-TYPE
        SYNTAX  NsVpnManualKeyEntry
        ACCESS  not-accessible
        STATUS  mandatory
        DESCRIPTION
               "Each entry in the nsVpnManualKeyTable holds a set of configuration 
               parameters associated with an instance of manual key."
        INDEX   { nsVpnManualKeyIndex }
        ::= { nsVpnManualKeyTable 1 }

	NsVpnManualKeyEntry ::=
		SEQUENCE {
          nsVpnManualKeyIndex
              INTEGER,
		  nsVpnManualKeyTunName
		      DisplayString,
		  nsVpnManualKeyGW
		      IpAddress,
		  nsVpnManualKeySILocal
		      INTEGER,
		  nsVpnManualKeySIRemote
		  	  INTEGER,
		  nsVpnManualKeyTunnelType
		      INTEGER,
		  nsVpnManualKeyEspEncAlg
		      INTEGER,
		  nsVpnManualKeyEspAuthAlg
		      INTEGER,
		  nsVpnManualKeyAhHash
		      INTEGER,
		  nsVpnManualKeyMonitorEnable
		      INTEGER,
		  nsVpnManualKeyTunToTrust
		      INTEGER,
		  nsVpnManualKeyVsys
		      INTEGER
       }

	nsVpnManualKeyIndex OBJECT-TYPE
    	SYNTAX  INTEGER
        ACCESS  read-only
        STATUS  mandatory
        DESCRIPTION
             "A unique value for manual key table.  Its value
              ranges between 0 and 65535 and may not be contiguous."
        ::= { nsVpnManualKeyEntry 1 }

	nsVpnManualKeyTunName OBJECT-TYPE
        SYNTAX  DisplayString (SIZE (0..32))
    	ACCESS  read-only
        STATUS  mandatory
        DESCRIPTION
             "VPN tunnel name that uses this manual key configuration."
        ::= { nsVpnManualKeyEntry 2 }

	nsVpnManualKeyGW OBJECT-TYPE
        SYNTAX  IpAddress
    	ACCESS  read-only
        STATUS  mandatory
        DESCRIPTION
             "VPN tunnel peer gateway IP address."
        ::= { nsVpnManualKeyEntry 3 }

	nsVpnManualKeySILocal OBJECT-TYPE
        SYNTAX  INTEGER
    	ACCESS  read-only
        STATUS  mandatory
        DESCRIPTION
             "Local Security Index."
        ::= { nsVpnManualKeyEntry 4 }

	nsVpnManualKeySIRemote OBJECT-TYPE
        SYNTAX  INTEGER
    	ACCESS  read-only
        STATUS  mandatory
        DESCRIPTION
             "Remote Security Index."
        ::= { nsVpnManualKeyEntry 5 }

	nsVpnManualKeyTunnelType OBJECT-TYPE
        SYNTAX  INTEGER {
             esp(0),
             ah(1)
        }
    	ACCESS  read-only
        STATUS  mandatory
        DESCRIPTION
             "VPN tunnel type."
        ::= { nsVpnManualKeyEntry 6 }

	nsVpnManualKeyEspEncAlg OBJECT-TYPE
        SYNTAX  INTEGER {
             null(0),
             des-cbc(1),
             tripple-des-cbc(2),
			 aes-cbc(3),
			 aes-192(4),
			 aes-256(5)
        }
    	ACCESS  read-only
        STATUS  mandatory
        DESCRIPTION
             "ESP Encryption Algorithm when manual key vpn tunnel type is ESP."
        ::= { nsVpnManualKeyEntry 7 }
                  		  
	nsVpnManualKeyEspAuthAlg OBJECT-TYPE
        SYNTAX  INTEGER {
             null(0),
             md5(1),
             sha(2),
             sha256(3)
        }
    	ACCESS  read-only
        STATUS  mandatory
        DESCRIPTION
             "ESP Authentication Algorithm when manual key vpn tunnel type is ESP."
        ::= { nsVpnManualKeyEntry 8 }

	nsVpnManualKeyAhHash OBJECT-TYPE
        SYNTAX  INTEGER {
             null(0),
             md5(1),
             sha(2)
        }
    	ACCESS  read-only
        STATUS  mandatory
        DESCRIPTION
             "AH Hash Algorithm when manual key vpn tunnel type is AH."
        ::= { nsVpnManualKeyEntry 9 }

	nsVpnManualKeyMonitorEnable OBJECT-TYPE
        SYNTAX  INTEGER {
             disable(0),
             enabled(1)
        }
    	ACCESS  read-only
        STATUS  mandatory
        DESCRIPTION
             "Enable monitor vpn tunnel's link status."
        ::= { nsVpnManualKeyEntry 10 }

	nsVpnManualKeyTunToTrust OBJECT-TYPE
        SYNTAX  INTEGER {
             disable(0),
             enabled(1)
        }
    	ACCESS  read-only
        STATUS  mandatory
        DESCRIPTION
             "Tunnel to Trusted Interface"
        ::= { nsVpnManualKeyEntry 11 }

	nsVpnManualKeyVsys OBJECT-TYPE
        SYNTAX  INTEGER
    	ACCESS  read-only
        STATUS  mandatory
        DESCRIPTION
             "vsys this vpn manual key setting belongs to."
        ::= { nsVpnManualKeyEntry 12 }
       
END
