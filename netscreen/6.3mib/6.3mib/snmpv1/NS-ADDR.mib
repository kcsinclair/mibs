-- These MIBs were created on 05/14/2001
-- This module defines enterprise MIBs for address book
-- 
-- Copyright (c) 1999 - 2004 by Juniper Networks, Inc.
-- All rights reserved.
-- 
-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    all the entries in the Address Book 
--
--  Last modified date: 05/03/2004
--  Modified copyright and contact info
--
--  Last modified date: 09/28/2001
--    
--  Last modified date: 11/10/2003
--  Correct spelling mistake 
--

NETSCREEN-ADDR-MIB DEFINITIONS ::= BEGIN
IMPORTS

    DisplayString 	FROM RFC1213-MIB 
    netscreenAddr 	FROM NETSCREEN-SMI;


          nsAddrTable OBJECT-TYPE
              SYNTAX  SEQUENCE OF NsAddrEntry
              ACCESS  not-accessible
              STATUS  mandatory
              DESCRIPTION
                      "The NetScreen ScreenOS classifies the addresses of all other devices by
                      location and netmask. For example trusted addresses are located behind the
                      trusted interface. This table collects all address items that exist in ScreenOS"
              ::= { netscreenAddr 1 }

          nsAddrEntry OBJECT-TYPE
              SYNTAX  NsAddrEntry
              ACCESS  not-accessible
              STATUS  mandatory
              DESCRIPTION
                      "Address entry collects some attributes of the address item."
              INDEX   { nsAddrIndex }
              ::= { nsAddrTable 1 }
       
          NsAddrEntry ::=
              SEQUENCE {
             		nsAddrIndex 
             			INTEGER,
					nsAddrName
						DisplayString,
					nsAddrVsys
						INTEGER,
					nsAddrZone
						INTEGER,
					nsAddrIpOrDomain 
						DisplayString,
					nsAddrNetmask 
						IpAddress,
					nsAddrComment 
						DisplayString
			  }

          nsAddrIndex OBJECT-TYPE
              SYNTAX  INTEGER
              ACCESS  read-only
              STATUS  mandatory
              DESCRIPTION
                      "A unique value for each address.  Its value
                      ranges between 0 and 65535 and may not be contiguous."
              ::= { nsAddrEntry 1 }

          nsAddrName OBJECT-TYPE
              SYNTAX  DisplayString(SIZE(0..32))
              ACCESS  read-only
              STATUS  mandatory
              DESCRIPTION
                      "Address item name."
              ::= { nsAddrEntry 2 }

          nsAddrVsys OBJECT-TYPE
              SYNTAX  INTEGER
              ACCESS  read-only
              STATUS  mandatory
              DESCRIPTION
                      "Virtual system name this address belongs to."
              ::= { nsAddrEntry 3 }

          nsAddrZone OBJECT-TYPE
              SYNTAX  INTEGER
              ACCESS  read-only
              STATUS  mandatory
              DESCRIPTION
                      "Security zone name this address belongs to."
              ::= { nsAddrEntry 4 }

          nsAddrIpOrDomain OBJECT-TYPE
              SYNTAX  DisplayString(SIZE(0..32))
              ACCESS  read-only
              STATUS  mandatory
              DESCRIPTION
                      "Address item's ip address or domain name."
              ::= { nsAddrEntry 5 }

          nsAddrNetmask OBJECT-TYPE
              SYNTAX  IpAddress
              ACCESS  read-only
              STATUS  mandatory
              DESCRIPTION
                      "Subnet mask address use."
              ::= { nsAddrEntry 6 }

          nsAddrComment OBJECT-TYPE
              SYNTAX  DisplayString(SIZE(0..32))
              ACCESS  read-only
              STATUS  mandatory
              DESCRIPTION
                      "Comments on this address."
              ::= { nsAddrEntry 7 }
END
