-- These MIBs were created on 05/14/2001
-- This module defines enterprise MIBs for VPN Phase 1
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Last modified date: 05/03/2004
--  Modified copyright and contact info
--
--  Last modified date: 09/28/2001
--    
--  Last modified date: 11/13/2003
--  Correct spelling mistake
--    

NETSCREEN-VPN-PHASEONE-MIB DEFINITIONS ::= BEGIN
IMPORTS

    DisplayString 	FROM RFC1213-MIB 
    netscreenVpn    FROM NETSCREEN-SMI;
    nsVpnPhaseOneCfg 	OBJECT IDENTIFIER ::= {netscreenVpn 5}
    
	nsVpnPhOneTable OBJECT-TYPE
		SYNTAX  SEQUENCE OF NsVpnPhOneEntry
		ACCESS  not-accessible
		STATUS  mandatory
		DESCRIPTION 
		        "To establish an IKE IPSec tunnel, two phases of negotiation are required.
		        This table specifies the configuration attributes for Phase One negotiation.
		        In Phase 1, the participants establish a secure channel in which to negotiate
		        the IPSec SAs."
		::= { nsVpnPhaseOneCfg 1 }  

    nsVpnPhOneEntry OBJECT-TYPE
        SYNTAX  NsVpnPhOneEntry
        ACCESS  not-accessible
        STATUS  mandatory
        DESCRIPTION
               "Each entry in the nsVpnPhOneTable holds a set of configuration parameters
               associated with an instance of Phase 1 setting."
        INDEX   { nsVpnPhOneIndex }
        ::= { nsVpnPhOneTable 1 }

	NsVpnPhOneEntry ::=
		SEQUENCE {
          nsVpnPhOneIndex
              INTEGER,
		  nsVpnPhOneName
		      DisplayString,
		  nsVpnPhOneAuthMethod
		      INTEGER,
		  nsVpnPhOneDhGroup
		      INTEGER,
		  nsVpnPhOneEncryp
		  	  INTEGER,
		  nsVpnPhOneHash
		  	  INTEGER,
		  nsVpnPhOneLifetime
		  	  INTEGER,
		  nsVpnPhOneLifetimeMeasure
		      INTEGER,
		  nsVpnPhOneVsys
		      INTEGER
       }

	nsVpnPhOneIndex OBJECT-TYPE
    	SYNTAX  INTEGER
        ACCESS  read-only
        STATUS  mandatory
        DESCRIPTION
             "A unique value for phase one table.  Its value
              ranges between 1 and 65535 and may not be contiguous. 
              The index has no other meaning but a pure index" 
        ::= { nsVpnPhOneEntry 1 }

	nsVpnPhOneName OBJECT-TYPE
        SYNTAX  DisplayString (SIZE (0..32))
    	ACCESS  read-only
        STATUS  mandatory
        DESCRIPTION
             "Phase one proposal name."
        ::= { nsVpnPhOneEntry 2 }

	nsVpnPhOneAuthMethod OBJECT-TYPE
        SYNTAX  INTEGER {
        	preshare(0),
        	rsa-sig(1),
        	dsa-sig(2),
        	rsa-enc(3),
        	rsa-rev(4)
        }
    	ACCESS  read-only
        STATUS  mandatory
        DESCRIPTION
             "Phase one proposal authentication method."
        ::= { nsVpnPhOneEntry 3 }

	nsVpnPhOneDhGroup OBJECT-TYPE
        SYNTAX  INTEGER
    	ACCESS  read-only
        STATUS  mandatory
        DESCRIPTION
             "Phase one proposal Diffie-Hellman exchange group id."
        ::= { nsVpnPhOneEntry 4 }

	nsVpnPhOneEncryp OBJECT-TYPE
        SYNTAX  INTEGER {
        	      null(0),
        	      des(1),
        	      des3(2),
				  aes(3),
				  aes-192(4),
				  aes-256(5)
        }
    	ACCESS  read-only
        STATUS  mandatory
        DESCRIPTION
             "Phase one proposal encryption exchange id."
        ::= { nsVpnPhOneEntry 5 }

	nsVpnPhOneHash OBJECT-TYPE
        SYNTAX  INTEGER {
                  null(0),
        	      md5(1),
        	      sha(2)
        }
    	ACCESS  read-only
        STATUS  mandatory
        DESCRIPTION
             "Phase one proposal hash algorithm."
        ::= { nsVpnPhOneEntry 6 }

	nsVpnPhOneLifetime OBJECT-TYPE
        SYNTAX  INTEGER
    	ACCESS  read-only
        STATUS  mandatory
        DESCRIPTION
             "Lifetime of this phase one setting."
        ::= { nsVpnPhOneEntry 7 }

	nsVpnPhOneLifetimeMeasure OBJECT-TYPE
        SYNTAX  INTEGER {
        	second(0),
        	minute(1),
        	hours(2),
        	days(3)
        }
    	ACCESS  read-only
        STATUS  mandatory
        DESCRIPTION
             "life time measurement."
        ::= { nsVpnPhOneEntry 8 }

	nsVpnPhOneVsys OBJECT-TYPE
        SYNTAX  INTEGER
    	ACCESS  read-only
        STATUS  mandatory
        DESCRIPTION
             "vsys this phase one proposal configuration belongs to."
        ::= { nsVpnPhOneEntry 9 }
       
END
