-- These MIBs were created on 05/08/2000
-- This module defines enterprise MIBs for security zones
-- 
-- Copyright (c) 1999-2004, Juniper Networks, Inc.
-- All rights reserved.
-- 
-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    Security Zones
--
--  Last modified date: 05/03/2004
--  Modified copyright and contact info
--
--  Last modified date: 09/28/2001
--    
--  Last modified date: 11/13/2003
--  Correct spelling mistake
--    

NETSCREEN-ZONE-MIB DEFINITIONS ::= BEGIN
IMPORTS

    DisplayString 	FROM RFC1213-MIB 
    netscreenZone    FROM NETSCREEN-SMI;
    nsZoneCfg 	OBJECT IDENTIFIER ::= {netscreenZone 1}
    
	nsZoneCfgTable OBJECT-TYPE
		SYNTAX  SEQUENCE OF NsZoneCfgEntry
		ACCESS  not-accessible
		STATUS  mandatory
		DESCRIPTION 
		        "NetScreen device can have lots of secure zone. This table collects
		        the zones exiting in NetScreen device."
		::= { nsZoneCfg 1 }

    nsZoneCfgEntry OBJECT-TYPE
        SYNTAX  NsZoneCfgEntry
        ACCESS  not-accessible
        STATUS  mandatory
        DESCRIPTION
               "Each entry in the table holds a set of configuration parameters associated 
               with an instance of secure zone."
        INDEX   { nsZoneCfgId }
        ::= { nsZoneCfgTable 1 }

	NsZoneCfgEntry ::=
		SEQUENCE {
          nsZoneCfgId
              INTEGER,
		  nsZoneCfgName
		      DisplayString,
		  nsZoneCfgType
			  INTEGER,
		  nsZoneCfgVsys
			  INTEGER 
		}

	nsZoneCfgId OBJECT-TYPE
    	SYNTAX  INTEGER
        ACCESS  read-only
        STATUS  mandatory
        DESCRIPTION
             "A unique value for zone table.  Its value
              ranges between 1 and 65535 and may not be contiguous. 
              the index has no other meaning but a pure index" 
        ::= { nsZoneCfgEntry 1 }

	nsZoneCfgName OBJECT-TYPE
        SYNTAX  DisplayString (SIZE (0..32))
    	ACCESS  read-only
        STATUS  mandatory
        DESCRIPTION
             "Secure zone name."
        ::= { nsZoneCfgEntry 2 }       

    nsZoneCfgType OBJECT-TYPE
        SYNTAX  INTEGER {
			regular(0),
			layer2(1),
			tunnel(2),
			null(3),
			func(4)
		}
        ACCESS  read-only
        STATUS  mandatory
        DESCRIPTION
             "Secure zone type. Regular is sec(L3) and layer2 is sec(L2) type"
        ::= { nsZoneCfgEntry 3 }

    nsZoneCfgVsys OBJECT-TYPE
        SYNTAX  INTEGER
        ACCESS  read-only
        STATUS  mandatory
        DESCRIPTION
             "VSYS this security zone belongs to."
        ::= { nsZoneCfgEntry 4 }
END
