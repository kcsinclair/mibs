-- These MIBs were created on 05/27/2001
-- This module defines enterprise MIBs for Configuration monitoring
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    all the configuration info  
--
--  Last modified date: 05/03/2004
--  Modified copyright and contact info
--    
--  Last modified date: 09/28/2001
--    
--  Last modified date: 11/10/2003
--  Correct spelling mistake
--    
--  Last modified date: 07/14/2005
--  obsolete nsSetGenSysIp
--    

NETSCREEN-SET-GEN-MIB DEFINITIONS ::= BEGIN
IMPORTS
    DisplayString 	FROM RFC1213-MIB 
    netscreenSetting FROM NETSCREEN-SMI;
    
    nsSetGeneral OBJECT IDENTIFIER ::= { netscreenSetting 1 }

    nsSetGenSysIp OBJECT-TYPE
        SYNTAX  IpAddress
        ACCESS  read-only
        STATUS  obsolete
        DESCRIPTION
            "System Ip address,obsoleted after ScreenOS 5.0"
        ::= { nsSetGeneral 1 }

	nsSetGenHostName OBJECT-TYPE
        SYNTAX  DisplayString (SIZE(0..32))
    	ACCESS  read-only
        STATUS  mandatory
        DESCRIPTION
             "Host name of NetScreen device."
        ::= { nsSetGeneral 2 }

	nsSetGenDomain OBJECT-TYPE
        SYNTAX  DisplayString (SIZE(0..32))
    	ACCESS  read-only
        STATUS  mandatory
        DESCRIPTION
             "Domain name of NetScreen device."
        ::= { nsSetGeneral 3 }

	nsSetGenOpMode OBJECT-TYPE
        SYNTAX  DisplayString(SIZE(0..32))
        ACCESS  read-only
        STATUS  mandatory
        DESCRIPTION
             "NetScreen device can work in one of the tree mode: transparent, NAT 
             and route. This attribute indicates which operation mode it use."
        ::= { nsSetGeneral 4 }

	nsSetGenSwVer OBJECT-TYPE
        SYNTAX  DisplayString (SIZE(0..128))
    	ACCESS  read-only
        STATUS  mandatory
        DESCRIPTION
             "NetSceen OS version."
        ::= { nsSetGeneral 5 }

	nsSetGenLicInfo OBJECT-TYPE
        SYNTAX  DisplayString (SIZE(0..255))
    	ACCESS  read-only
        STATUS  mandatory
        DESCRIPTION
             "NetScreen OS license information."
        ::= { nsSetGeneral 6 }

    nsSetGenSCSAdminEnable OBJECT-TYPE
        SYNTAX  INTEGER {
             disable(0),
             enabled(1)
        }
        ACCESS  read-only
        STATUS  mandatory
        DESCRIPTION
            "enable Command Security Shell"
        ::= { nsSetGeneral 7 }

    nsSetGenDropSelfLogPac OBJECT-TYPE
        SYNTAX  INTEGER {
             disable(0),
             enabled(1)
        }
        ACCESS  read-only
        STATUS  mandatory
        DESCRIPTION
            "Log Packets to Self that are dropped"
        ::= { nsSetGeneral 8 }
END
