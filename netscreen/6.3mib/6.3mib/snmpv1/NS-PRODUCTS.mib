-- These MIBs were created on 08/02/2000
--
-- Copyright (c) 1999-2004, Juniper Networks, Inc.
-- All rights reserved.
-- 
-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object identifiers that are
--    assigned to various hardware platforms, and hence are
--    returned as values for sysObjectID
--    
--  Last modified date: 05/03/2004
--  Modified copyright and contact info
--    
--  Last modified date: 1/20/2004
--    Add netscreenHardwareSecurityClient

NETSCREEN-PRODUCTS-MIB DEFINITIONS ::= BEGIN
IMPORTS
  netscreenProducts FROM NETSCREEN-SMI;
    
  netscreenGeneric OBJECT IDENTIFIER ::= { netscreenProducts 1 }
  netscreenNs5 	OBJECT IDENTIFIER ::= { netscreenProducts 2 }
  netscreenNs10 	OBJECT IDENTIFIER ::= { netscreenProducts 3 }
  netscreenNs100 	OBJECT IDENTIFIER ::= { netscreenProducts 4 }
  netscreenNs1000 OBJECT IDENTIFIER ::= { netscreenProducts 5 }
  netscreenNs500 	OBJECT IDENTIFIER ::= { netscreenProducts 6 }
  netscreenNs50 	OBJECT IDENTIFIER ::= { netscreenProducts 7 }
  netscreenNs25 	OBJECT IDENTIFIER ::= { netscreenProducts 8 }
  netscreenNs204 	OBJECT IDENTIFIER ::= { netscreenProducts 9 }
  netscreenNs208 	OBJECT IDENTIFIER ::= { netscreenProducts 10 }
  netscreenNs5XT 	OBJECT IDENTIFIER ::= { netscreenProducts 11 }
  netscreenNs5XP 	OBJECT IDENTIFIER ::= { netscreenProducts 12 }
  netscreenNs5000 	OBJECT IDENTIFIER ::= { netscreenProducts 13 }
  netscreenNs5GT 	OBJECT IDENTIFIER ::= { netscreenProducts 14 }
  netscreenHardwareSecurityClient 	OBJECT IDENTIFIER ::= { netscreenProducts 15 }
  netscreenISG2000 	OBJECT IDENTIFIER ::= { netscreenProducts 16 }
  netscreen-5GT-ADSL-AnnexA OBJECT IDENTIFIER ::= { netscreenProducts 17 }
  netscreen-5GT-ADSL-AnnexB OBJECT IDENTIFIER ::= { netscreenProducts 19 }
  netscreen-5GT-WLAN OBJECT IDENTIFIER ::= { netscreenProducts 21 }
  netscreen-5GT-ADSL-AnnexA-WLAN OBJECT IDENTIFIER ::= { netscreenProducts 23 }
  netscreen-5GT-ADSL-AnnexB-WLAN OBJECT IDENTIFIER ::= { netscreenProducts 25 }
  netscreenISG1000 	OBJECT IDENTIFIER ::= { netscreenProducts 28 }
  netscreenSSG5 	OBJECT IDENTIFIER ::= { netscreenProducts 29 }
  netscreenSSG5-ISDN 	OBJECT IDENTIFIER ::= { netscreenProducts 30 }
  netscreenSSG5-v92 	OBJECT IDENTIFIER ::= { netscreenProducts 31 }
  netscreenSSG5-WLAN 	OBJECT IDENTIFIER ::= { netscreenProducts 32 }
  netscreenSSG5-ISDN-WLAN 	OBJECT IDENTIFIER ::= { netscreenProducts 33 }
  netscreenSSG5-v92-WLAN 	OBJECT IDENTIFIER ::= { netscreenProducts 34 }
  netscreenSSG20 	OBJECT IDENTIFIER ::= { netscreenProducts 35 }
  netscreenSSG20-WLAN 	OBJECT IDENTIFIER ::= { netscreenProducts 36 }
  netscreenSSG520 	OBJECT IDENTIFIER ::= { netscreenProducts 50 }
  netscreenSSG550 	OBJECT IDENTIFIER ::= { netscreenProducts 51 }
  netscreenSSG140 	OBJECT IDENTIFIER ::= { netscreenProducts 52 }
  netscreenSSG320 	OBJECT IDENTIFIER ::= { netscreenProducts 54 }
  netscreenSSG350 	OBJECT IDENTIFIER ::= { netscreenProducts 55 }
END
