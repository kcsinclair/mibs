-- These MIBs were created on 05/27/2001
-- This module defines enterprise MIBs for Schedule
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    scheduled entries 
--
--  Last modified date: 05/03/2004
--  Modified copyright and contact info
--    
--  Last modified date: 09/28/2001
--    
--  Last modified date: 11/10/2003
--  Correct spelling mistake
--

NETSCREEN-SCHEDULE-MIB DEFINITIONS ::= BEGIN
IMPORTS

    DisplayString 	FROM RFC1213-MIB 
    netscreenSchedule 	FROM NETSCREEN-SMI;
    
	nsSchOnceTable OBJECT-TYPE
		SYNTAX  SEQUENCE OF NsSchOnceEntry
		ACCESS  not-accessible
		STATUS  mandatory
		DESCRIPTION 
		        "By associating a schedule to a NetScreen device setting, user can determine
		        when that setting is in effect. This table specifies the configuration of 
		        schedules as a one-time event."
		::= { netscreenSchedule 1 }

    nsSchOnceEntry OBJECT-TYPE
        SYNTAX  NsSchOnceEntry
        ACCESS  not-accessible
        STATUS  mandatory
        DESCRIPTION
               "Each entry in the nsSchOnceTable holds a set of configuration parameters associated
               with an instance of one-time schedule."
        INDEX   { nsSchOnceIndex }
        ::= { nsSchOnceTable 1 }

	NsSchOnceEntry ::=
		SEQUENCE {
          nsSchOnceIndex
              INTEGER,
		  nsSchOnceName
		      DisplayString,
		  nsSchOnceStartTime
		      DisplayString,
		  nsSchOnceStopTime 
		      DisplayString,
		  nsSchOnceComments 
		      DisplayString,
          nsSchOnceVsys
              INTEGER
        }

	nsSchOnceIndex OBJECT-TYPE
    	SYNTAX  INTEGER
        ACCESS  read-only
        STATUS  mandatory
        DESCRIPTION
             "A unique value for schedule.  Its value
              ranges between 1 and 65535 and may not be contiguous. 
              The index has no other meaning but a pure index" 
        ::= { nsSchOnceEntry 1 }

	nsSchOnceName OBJECT-TYPE
        SYNTAX  DisplayString (SIZE (0..32))
    	ACCESS  read-only
        STATUS  mandatory
        DESCRIPTION
             "schedule's name."
        ::= { nsSchOnceEntry 2 }

	nsSchOnceStartTime OBJECT-TYPE
        SYNTAX  DisplayString (SIZE (0..32))
    	ACCESS  read-only
        STATUS  mandatory
        DESCRIPTION
             "schedule's start time."
        ::= { nsSchOnceEntry 3 }


	nsSchOnceStopTime OBJECT-TYPE
        SYNTAX  DisplayString (SIZE (0..32))
    	ACCESS  read-only
        STATUS  mandatory
        DESCRIPTION
             "schedule's stop time."
        ::= { nsSchOnceEntry 4 }

	nsSchOnceComments OBJECT-TYPE
        SYNTAX  DisplayString (SIZE (0..32))
    	ACCESS  read-only
        STATUS  mandatory
        DESCRIPTION
             "Comments for this schedule."
        ::= { nsSchOnceEntry 5 }

	nsSchOnceVsys OBJECT-TYPE
    	SYNTAX  INTEGER
        ACCESS  read-only
        STATUS  mandatory
        DESCRIPTION
              "The vsys this entry belongs to" 
        ::= { nsSchOnceEntry 6 }

	nsSchRecurTable OBJECT-TYPE
		SYNTAX  SEQUENCE OF NsSchRecurEntry
		ACCESS  not-accessible
		STATUS  mandatory
		DESCRIPTION 
		        "By associating a schedule to a NetScreen device setting, user can determine
		        when that setting is in effect. This table specifies the configuration of 
		        schedules on a recurring basis."
		::= { netscreenSchedule 2 }

    nsSchRecurEntry OBJECT-TYPE
        SYNTAX  NsSchRecurEntry
        ACCESS  not-accessible
        STATUS  mandatory
        DESCRIPTION
               "Each entry in the nsSchOnceTable holds a set of configuration parameters associated
               with an instance of re-occurring schedule."
        INDEX   { nsSchRecurIndex }
        ::= { nsSchRecurTable 1 }

	NsSchRecurEntry ::=
		SEQUENCE {
          nsSchRecurIndex
              INTEGER,
		  nsSchRecurName
		      DisplayString,
		  nsSchRecurWeekday
		  	  INTEGER,
		  nsSchRecurStartTime1
		      DisplayString,
		  nsSchRecurStopTime1 
		      DisplayString,
		  nsSchRecurStartTime2
		      DisplayString,
		  nsSchRecurStopTime2 
		      DisplayString,
		  nsSchRecurComments 
		      DisplayString,
          nsSchRecurVsys
              INTEGER
        }

	nsSchRecurIndex OBJECT-TYPE
    	SYNTAX  INTEGER
        ACCESS  read-only
        STATUS  mandatory
        DESCRIPTION
             "A unique value for schedule.  Its value
              ranges between 1 and 65535 and may not be contiguous. 
              The index has no other meaning but a pure index" 
        ::= { nsSchRecurEntry 1 }

	nsSchRecurName OBJECT-TYPE
        SYNTAX  DisplayString (SIZE (0..32))
    	ACCESS  read-only
        STATUS  mandatory
        DESCRIPTION
             "schedule's name"
        ::= { nsSchRecurEntry 2 }

	nsSchRecurWeekday OBJECT-TYPE
        SYNTAX  INTEGER {
        	sun(0),
        	mon(1),
        	tue(2),
        	wed(3),
        	thu(4),
        	fri(5),
        	sat(6)
        }  	
    	ACCESS  read-only
        STATUS  mandatory
        DESCRIPTION
             "Schedule’s starts date, using week day to determine."
        ::= { nsSchRecurEntry 3 }

	nsSchRecurStartTime1 OBJECT-TYPE
        SYNTAX  DisplayString (SIZE (0..32))
    	ACCESS  read-only
        STATUS  mandatory
        DESCRIPTION
             "schedule's start time one."
        ::= { nsSchRecurEntry 4 }


	nsSchRecurStopTime1 OBJECT-TYPE
        SYNTAX  DisplayString (SIZE (0..32))
    	ACCESS  read-only
        STATUS  mandatory
        DESCRIPTION
             "schedule's stop time one."
        ::= { nsSchRecurEntry 5 }

	nsSchRecurStartTime2 OBJECT-TYPE
        SYNTAX  DisplayString (SIZE (0..32))
    	ACCESS  read-only
        STATUS  mandatory
        DESCRIPTION
             "schedule start time two."
        ::= { nsSchRecurEntry 6 }


	nsSchRecurStopTime2 OBJECT-TYPE
        SYNTAX  DisplayString (SIZE (0..32))
    	ACCESS  read-only
        STATUS  mandatory
        DESCRIPTION
             "schedule stop time two."
        ::= { nsSchRecurEntry 7 }

	nsSchRecurComments OBJECT-TYPE
        SYNTAX  DisplayString (SIZE (0..64))
    	ACCESS  read-only
        STATUS  mandatory
        DESCRIPTION
             "comments for the schedule."
        ::= { nsSchRecurEntry 8 }

	nsSchRecurVsys OBJECT-TYPE
    	SYNTAX  INTEGER
        ACCESS  read-only
        STATUS  mandatory
        DESCRIPTION
             "The vsys this entry belongs to"
        ::= { nsSchRecurEntry 9 }


END
