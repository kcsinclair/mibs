-- These MIBs were created on 01/08/2001
-- This module defines enterprise MIBs DI Setting.
-- 
-- Copyright (c) 1999-2004, Juniper Networks, Inc.
-- All rights reserved.
--
-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Last modified date: 05/03/2004
--  Modified copyright and contact info
--
--  Last modified date: 09/28/2001
--  
--  Add new screen field
--  zhong wang 
--
--  Last modified data: 04/26/2002
--  (1) screen option on zone setting
--  (2) add a new screen option
--  ZHONG WANG
-- 

NETSCREEN-IDS-MIB DEFINITIONS ::= BEGIN
IMPORTS

    DisplayString 	FROM RFC1213-MIB 
    netscreenIDS 	FROM NETSCREEN-SMI;
    
    nsIdsProtect OBJECT IDENTIFIER ::= { netscreenIDS 1 }
    nsIdsProtectSetTable OBJECT-TYPE
    	SYNTAX SEQUENCE OF NsIdsProtectSetEntry
    	ACCESS not-accessible
    	STATUS mandatory
    	DESCRIPTION
    		"NetScreen ScreenOS can allow DI protection on each of NetScreen
    		device's physical interface. This table collects the DI protection
    		configuration on each physical interface."
		::= {nsIdsProtect 1}

	nsIdsProtectSetEntry OBJECT-TYPE
		SYNTAX  NsIdsProtectSetEntry
		ACCESS  not-accessible
		STATUS  mandatory
		DESCRIPTION
			"Hold the DI setting attribute."
		INDEX   { nsIdsProtectZoneIdx }
              ::= { nsIdsProtectSetTable 1 }
       
	NsIdsProtectSetEntry ::=
		SEQUENCE {
			nsIdsProtectZoneIdx
				INTEGER,
			nsIdsDetectPingOfDeath
				INTEGER,
			nsIdsDetectTearDrop
				INTEGER,
			nsIdsDetectWinNuke
				INTEGER,
			nsIdsFilterIpSrcRoute 
				INTEGER,
			nsIdsDetectPortScan 
				INTEGER,
			nsIdsDetectAddrSweep 
				INTEGER,
			nsIdsDetectLand
				INTEGER,
			nsIdsBlockComponent
				INTEGER,
			nsIdsDetectIpSpoof
				INTEGER,
			nsIdsDetectSyn
				INTEGER,
			nsIdsDetectIcmpFlood
				INTEGER,
			nsIdsDetectUdpFlood
				INTEGER,
			nsIdsDetectSynFrag
				INTEGER,
			nsIdsDetectTcpNoFlag
				INTEGER,
			nsIdsDetectIpUnknownProt
				INTEGER,
			nsIdsDetectIpOptBad
				INTEGER,
			nsIdsDetectIpOptRecord
				INTEGER,
			nsIdsDetectIpOptTimestamp
				INTEGER,
			nsIdsDetectIpOptSCHT
				INTEGER,
			nsIdsDetectIpOptLSR
				INTEGER,
			nsIdsDetectIpOptSSR
				INTEGER,
			nsIdsDetectIpOptStream
				INTEGER,
			nsIdsDetectIcmpFrag
				INTEGER,
			nsIdsDetectIcmpLarge
				INTEGER,
			nsIdsDetectTcpSynFin
				INTEGER,
			nsIdsDetectTcpFinNoAck
				INTEGER,
			nsIdsHttpMalUrl
				INTEGER,
			nsIdsSessMalNum
				INTEGER,
			nsIdsDetectSynAckAck
				INTEGER,				
			nsIdsDetectIpFrag
				INTEGER				
		}
    
	nsIdsProtectZoneIdx OBJECT-TYPE
		SYNTAX  INTEGER
		ACCESS  read-only
		STATUS  mandatory
		DESCRIPTION
			"unique zone id."
	::= { nsIdsProtectSetEntry 1 }

	nsIdsDetectPingOfDeath OBJECT-TYPE
		SYNTAX  INTEGER {
			disable(0),
			enabled(1)
		}
		ACCESS  read-only
		STATUS  mandatory
		DESCRIPTION
			"Detect Ping of Death."
	::= { nsIdsProtectSetEntry 2 }

	nsIdsDetectTearDrop OBJECT-TYPE
		SYNTAX  INTEGER {
			disable(0),
			enabled(1)
		}
		ACCESS  read-only
		STATUS  mandatory
		DESCRIPTION
			"Detect Tear Drop Attack."
	::= { nsIdsProtectSetEntry 3 }

	nsIdsDetectWinNuke OBJECT-TYPE
		SYNTAX  INTEGER {
			disable(0),
			enabled(1)
		}
		ACCESS  read-only
		STATUS  mandatory
		DESCRIPTION
			"Detect Win Nuke Attack."
	::= { nsIdsProtectSetEntry 4 }

	nsIdsFilterIpSrcRoute OBJECT-TYPE
		SYNTAX  INTEGER {
			disable(0),
			enabled(1)
		}
		ACCESS  read-only
		STATUS  mandatory
		DESCRIPTION
			"Detect Filter IP Source Route Option attack."
	::= { nsIdsProtectSetEntry 5 }

	nsIdsDetectPortScan OBJECT-TYPE
		SYNTAX  INTEGER {
			disable(0),
			enabled(1)
		}
		ACCESS  read-only
		STATUS  mandatory
		DESCRIPTION
			"Detect Port Scan Death attack."
	::= { nsIdsProtectSetEntry 6 }

	nsIdsDetectAddrSweep OBJECT-TYPE
		SYNTAX  INTEGER {
			disable(0),
			enabled(1)
		}
		ACCESS  read-only
		STATUS  mandatory
		DESCRIPTION
			"Detect Address Sweep Attack."
	::= { nsIdsProtectSetEntry 7 }

	nsIdsDetectLand OBJECT-TYPE
		SYNTAX  INTEGER {
			disable(0),
			enabled(1)
		}
		ACCESS  read-only
		STATUS  mandatory
		DESCRIPTION
			"Detect Land Attack."
	::= { nsIdsProtectSetEntry 8 }

	nsIdsBlockComponent OBJECT-TYPE
		SYNTAX  INTEGER {
			disable(0),
			enabled(1)
		}
		ACCESS  read-only
		STATUS  mandatory
		DESCRIPTION
			"Block Java/ActiveX/ZIP/EXE Component."
	::= { nsIdsProtectSetEntry 9 }

	nsIdsDetectIpSpoof OBJECT-TYPE
		SYNTAX  INTEGER {
			disable(0),
			enabled(1)
		}
		ACCESS  read-only
		STATUS  mandatory
		DESCRIPTION
			"Detect IP Spoofing attack."
	::= { nsIdsProtectSetEntry 10 }

	nsIdsDetectSyn OBJECT-TYPE
		SYNTAX  INTEGER {
			disable(0),
			enabled(1)
		}
		ACCESS  read-only
		STATUS  mandatory
		DESCRIPTION
			"Detect SYN attack."
	::= { nsIdsProtectSetEntry 11 }
	
	nsIdsDetectIcmpFlood OBJECT-TYPE
		SYNTAX  INTEGER {
			disable(0),
			enabled(1)
		}
		ACCESS  read-only
		STATUS  mandatory
		DESCRIPTION
			"Detect ICMP Flood attack."
	::= { nsIdsProtectSetEntry 12 }

	nsIdsDetectUdpFlood OBJECT-TYPE
		SYNTAX  INTEGER {
			disable(0),
			enabled(1)
		}
		ACCESS  read-only
		STATUS  mandatory
		DESCRIPTION
			"Detect UDP Flood attack."
	::= { nsIdsProtectSetEntry 13 }

	nsIdsDetectSynFrag OBJECT-TYPE
		SYNTAX  INTEGER {
			disable(0),
			enabled(1)
		}
		ACCESS  read-only
		STATUS  mandatory
		DESCRIPTION
			"Detect SYN fragment"
	::= { nsIdsProtectSetEntry 14 }

	nsIdsDetectTcpNoFlag OBJECT-TYPE
		SYNTAX  INTEGER {
			disable(0),
			enabled(1)
		}
		ACCESS  read-only
		STATUS  mandatory
		DESCRIPTION
			"Detect TCP without flag set."
	::= { nsIdsProtectSetEntry 15 }

	nsIdsDetectIpUnknownProt OBJECT-TYPE
		SYNTAX  INTEGER {
			disable(0),
			enabled(1)
		}
		ACCESS  read-only
		STATUS  mandatory
		DESCRIPTION
			"Detect Unknown protocol IP packet."
	::= { nsIdsProtectSetEntry 16 }

	nsIdsDetectIpOptBad OBJECT-TYPE
		SYNTAX  INTEGER {
			disable(0),
			enabled(1)
		}
		ACCESS  read-only
		STATUS  mandatory
		DESCRIPTION
			"Detect IP bad option."
	::= { nsIdsProtectSetEntry 17 }

	nsIdsDetectIpOptRecord OBJECT-TYPE
		SYNTAX  INTEGER {
			disable(0),
			enabled(1)
		}
		ACCESS  read-only
		STATUS  mandatory
		DESCRIPTION
			"Detect IP record option."
	::= { nsIdsProtectSetEntry 18 }

	nsIdsDetectIpOptTimestamp OBJECT-TYPE
		SYNTAX  INTEGER {
			disable(0),
			enabled(1)
		}
		ACCESS  read-only
		STATUS  mandatory
		DESCRIPTION
			"Detect IP timestamp option."
	::= { nsIdsProtectSetEntry 19 }

	nsIdsDetectIpOptSCHT OBJECT-TYPE
		SYNTAX  INTEGER {
			disable(0),
			enabled(1)
		}
		ACCESS  read-only
		STATUS  mandatory
		DESCRIPTION
			"Detect IP security option."
	::= { nsIdsProtectSetEntry 20 }

	nsIdsDetectIpOptLSR OBJECT-TYPE
		SYNTAX  INTEGER {
			disable(0),
			enabled(1)
		}
		ACCESS  read-only
		STATUS  mandatory
		DESCRIPTION
			"Detect Loose source route."
	::= { nsIdsProtectSetEntry 21 }

	nsIdsDetectIpOptSSR OBJECT-TYPE
		SYNTAX  INTEGER {
			disable(0),
			enabled(1)
		}
		ACCESS  read-only
		STATUS  mandatory
		DESCRIPTION
			"Detect strict source route."
	::= { nsIdsProtectSetEntry 22 }

	nsIdsDetectIpOptStream OBJECT-TYPE
		SYNTAX  INTEGER {
			disable(0),
			enabled(1)
		}
		ACCESS  read-only
		STATUS  mandatory
		DESCRIPTION
			"Detect IP stream option."
	::= { nsIdsProtectSetEntry 23 }

	nsIdsDetectIcmpFrag OBJECT-TYPE
		SYNTAX  INTEGER {
			disable(0),
			enabled(1)
		}
		ACCESS  read-only
		STATUS  mandatory
		DESCRIPTION
			"Detect ICMP fragment."
	::= { nsIdsProtectSetEntry 24 }
	
	nsIdsDetectIcmpLarge OBJECT-TYPE
		SYNTAX  INTEGER {
			disable(0),
			enabled(1)
		}
		ACCESS  read-only
		STATUS  mandatory
		DESCRIPTION
			"Detect large ICMP packet."
	::= { nsIdsProtectSetEntry 25 }

	nsIdsDetectTcpSynFin OBJECT-TYPE
		SYNTAX  INTEGER {
			disable(0),
			enabled(1)
		}
		ACCESS  read-only
		STATUS  mandatory
		DESCRIPTION
			"Detect TCP syn fin both set."
	::= { nsIdsProtectSetEntry 26 }

	nsIdsDetectTcpFinNoAck OBJECT-TYPE
		SYNTAX  INTEGER {
			disable(0),
			enabled(1)
		}
		ACCESS  read-only
		STATUS  mandatory
		DESCRIPTION
			"Detect TCP fin set without ack bit set."
	::= { nsIdsProtectSetEntry 27 }

	nsIdsHttpMalUrl OBJECT-TYPE
		SYNTAX  INTEGER {
			disable(0),
			enabled(1)
		}
		ACCESS  read-only
		STATUS  mandatory
		DESCRIPTION
			"Detect malicious URL."
	::= { nsIdsProtectSetEntry 28 }

	nsIdsSessMalNum OBJECT-TYPE
		SYNTAX  INTEGER {
			disable(0),
			enabled(1)
		}
		ACCESS  read-only
		STATUS  mandatory
		DESCRIPTION
			"Detect malicious session connection."
	::= { nsIdsProtectSetEntry 29 }

    nsIdsDetectSynAckAck OBJECT-TYPE
        SYNTAX  INTEGER {
            disable(0),
            enabled(1)
        }
        ACCESS  read-only
        STATUS  mandatory
        DESCRIPTION
            "Detect SYN ACK ACK DoS."
    ::= { nsIdsProtectSetEntry 30 }

    nsIdsDetectIpFrag OBJECT-TYPE
        SYNTAX  INTEGER {
            disable(0),
            enabled(1)
        }
        ACCESS  read-only
        STATUS  mandatory
        DESCRIPTION
            "Block IP fragment packet."
    ::= { nsIdsProtectSetEntry 31 }

    nsIdsProtectThreshTable OBJECT-TYPE
    	SYNTAX SEQUENCE OF NsIdsProtectThreshEntry
    	ACCESS not-accessible
    	STATUS mandatory
    	DESCRIPTION
    		"NetScreen ScreenOS can allow DI protection on each of NetScreen
    		device's physical interface. This table collects the DI protection
    		configuration on each physical interface."
		::= {nsIdsProtect 2}

	nsIdsProtectThreshEntry OBJECT-TYPE
		SYNTAX  NsIdsProtectThreshEntry
		ACCESS  not-accessible
		STATUS  mandatory
		DESCRIPTION
			"Hold the DI setting attribute."
		INDEX   { nsIdsProtectThreshZoneIdx }
              ::= { nsIdsProtectThreshTable 1 }
              
	NsIdsProtectThreshEntry ::=
		SEQUENCE {
			nsIdsProtectThreshZoneIdx
				INTEGER,
			nsIdsSynAttackThresh
				INTEGER,
			nsIdsSynAttackTimeout
				INTEGER,
			nsIdsSynAttackAlmTh
				INTEGER,
			nsIdsSynAttackQueSize 
				INTEGER,
			nsIdsSynAttackAgeTime 
				INTEGER,
			nsIdsIcmpFloodThresh 
				INTEGER,
			nsIdsUdpFloodThresh 
				INTEGER,
			nsIdsPortScanThresh 
				INTEGER,
			nsIdsIpSweepThresh 
				INTEGER,
			nsIdsSynAckAckThres 
				INTEGER
		}

	nsIdsProtectThreshZoneIdx OBJECT-TYPE
		SYNTAX  INTEGER
		ACCESS  read-only
		STATUS  mandatory
		DESCRIPTION
			"unique zone id."
	::= { nsIdsProtectThreshEntry 1 }

	nsIdsSynAttackThresh OBJECT-TYPE
              SYNTAX  INTEGER 
              ACCESS  read-only
              STATUS  mandatory
              DESCRIPTION
                      "SYN attack threshold."
              ::= { nsIdsProtectThreshEntry 2 }
	nsIdsSynAttackTimeout OBJECT-TYPE
              SYNTAX  INTEGER 
              ACCESS  read-only
              STATUS  mandatory
              DESCRIPTION
                      "SYN attack timeout."
              ::= { nsIdsProtectThreshEntry 3 }
	nsIdsSynAttackAlmTh OBJECT-TYPE
              SYNTAX  INTEGER 
              ACCESS  read-only
              STATUS  mandatory
              DESCRIPTION
                      "SYN attack alarm threshold."
              ::= { nsIdsProtectThreshEntry 4 }
	nsIdsSynAttackQueSize OBJECT-TYPE
              SYNTAX  INTEGER 
              ACCESS  read-only
              STATUS  mandatory
              DESCRIPTION
                      "SYN attack queue size."
              ::= { nsIdsProtectThreshEntry 5 }
	nsIdsSynAttackAgeTime OBJECT-TYPE
              SYNTAX  INTEGER 
              ACCESS  read-only
              STATUS  mandatory
              DESCRIPTION
                      "SYN flood age time."
              ::= { nsIdsProtectThreshEntry 6 }
	nsIdsIcmpFloodThresh OBJECT-TYPE
              SYNTAX  INTEGER 
              ACCESS  read-only
              STATUS  mandatory
              DESCRIPTION
                      "ICMP attack alarm threshold."
              ::= { nsIdsProtectThreshEntry 7 }

	nsIdsUdpFloodThresh OBJECT-TYPE
              SYNTAX  INTEGER 
              ACCESS  read-only
              STATUS  mandatory
              DESCRIPTION
                      "UDP attack alarm threshold."
              ::= { nsIdsProtectThreshEntry 8 }

	nsIdsPortScanThresh OBJECT-TYPE
              SYNTAX  INTEGER 
              ACCESS  read-only
              STATUS  mandatory
              DESCRIPTION
                      "ICMP attack alarm threshold."
              ::= { nsIdsProtectThreshEntry 9 }

	nsIdsIpSweepThresh OBJECT-TYPE
              SYNTAX  INTEGER 
              ACCESS  read-only
              STATUS  mandatory
              DESCRIPTION
                      "UDP attack alarm threshold."
              ::= { nsIdsProtectThreshEntry 10 }

	nsIdsSynAckAckThres OBJECT-TYPE
              SYNTAX  INTEGER 
              ACCESS  read-only
              STATUS  mandatory
              DESCRIPTION
                      "SYN ack ack alarm threshold."
              ::= { nsIdsProtectThreshEntry 11 }

	nsIdsAttkMonTable OBJECT-TYPE
		SYNTAX  SEQUENCE OF NsIdsAttkMonEntry
		ACCESS  not-accessible
		STATUS  mandatory
		DESCRIPTION 
		        "The table monitors the intrusion attack attemps amount to
		        NetScreen Device."
		::= { netscreenIDS 2 }

    nsIdsAttkMonEntry OBJECT-TYPE
        SYNTAX  NsIdsAttkMonEntry
        ACCESS  not-accessible
        STATUS  mandatory
        DESCRIPTION
               "An entry containing intrusion attack couters."
        INDEX   { nsIdsAttkMonIfIdx }
        ::= { nsIdsAttkMonTable 1 }

    NsIdsAttkMonEntry ::=
        SEQUENCE {
        	nsIdsAttkMonIfIdx
            	INTEGER,
            nsIdsAttkMonVsys
                INTEGER,
            nsIdsAttkMonSynAttk
                Counter,
            nsIdsAttkMonTearDrop
                Counter,
            nsIdsAttkMonSrcRoute
                Counter,
            nsIdsAttkMonPingDeath
                Counter,
            nsIdsAttkMonAddrSpoof
                Counter,
            nsIdsAttkMonLand
                Counter,
            nsIdsAttkMonIcmpFlood
                Counter,
            nsIdsAttkMonUdpFlood
                Counter,
            nsIdsAttkMonWinnuke
                Counter,
            nsIdsAttkMonPortScan
                Counter,
            nsIdsAttkMonIpSweep
                Counter,
			nsAttkMonSynFrag
				Counter,
			nsAttkMonTcpNoFlag
				Counter,
			nsAttkMonIpUnknownProt
				Counter,
			nsAttkMonIpOptBad
				Counter,
			nsAttkMonIpOptRecord
				Counter,
			nsAttkMonIpOptTimestamp
				Counter,
			nsAttkMonIpOptSCHT
				Counter,
			nsAttkMonIpOptLSR
				Counter,
			nsAttkMonIpOptSSR
				Counter,
			nsAttkMonIpOptStream
				Counter,
			nsAttkMonIcmpFrag
				Counter,
			nsAttkMonIcmpLarge
				Counter,
			nsAttkMonTcpSynFin
				Counter,
			nsAttkMonTcpFinNoAck
				Counter,
			nsAttkMonHttpMalUrl
				Counter,
			nsAttkMonSessMalNum
				Counter,				                
			nsAttkMonSynAckAck
				Counter,
			nsAttkMonIpFrag
				Counter,				                
        	nsIdsAttkMonIfInfo
            	INTEGER
        }

    nsIdsAttkMonIfIdx OBJECT-TYPE
    	SYNTAX  INTEGER
        ACCESS  read-only
        STATUS  mandatory
        DESCRIPTION
                "unique interface id." 
        ::= { nsIdsAttkMonEntry 1 }
    nsIdsAttkMonVsys OBJECT-TYPE
        SYNTAX  INTEGER
        ACCESS  read-only
        STATUS  mandatory
        DESCRIPTION
                "according NetScreen's concepts. each interface belongs to one virtual
                 system. This attribute displays the virtual system name an interface
                 belongs to." 
        ::= { nsIdsAttkMonEntry 2 } 
    nsIdsAttkMonSynAttk OBJECT-TYPE
    	SYNTAX  Counter
        ACCESS  read-only
        STATUS  mandatory
        DESCRIPTION
                "sync attack packet counter." 
        ::= { nsIdsAttkMonEntry 3 }
    nsIdsAttkMonTearDrop OBJECT-TYPE
    	SYNTAX  Counter
        ACCESS  read-only
        STATUS  mandatory
        DESCRIPTION
                "tear drop attack packet counter." 
        ::= { nsIdsAttkMonEntry 4 }
    nsIdsAttkMonSrcRoute OBJECT-TYPE
    	SYNTAX  Counter
        ACCESS  read-only
        STATUS  mandatory
        DESCRIPTION
                "source route option attack packet counter." 
        ::= { nsIdsAttkMonEntry 5 }
    nsIdsAttkMonPingDeath OBJECT-TYPE
    	SYNTAX  Counter
        ACCESS  read-only
        STATUS  mandatory
        DESCRIPTION
                "ping of death attack packet counter." 
        ::= { nsIdsAttkMonEntry 6 }
    nsIdsAttkMonAddrSpoof OBJECT-TYPE
    	SYNTAX  Counter
        ACCESS  read-only
        STATUS  mandatory
        DESCRIPTION
                "address spoofing attack packet counter." 
        ::= { nsIdsAttkMonEntry 7 }
    nsIdsAttkMonLand OBJECT-TYPE
    	SYNTAX  Counter
        ACCESS  read-only
        STATUS  mandatory
        DESCRIPTION
                "land attack packet counter." 
        ::= { nsIdsAttkMonEntry 8 }
    nsIdsAttkMonIcmpFlood OBJECT-TYPE
    	SYNTAX  Counter
        ACCESS  read-only
        STATUS  mandatory
        DESCRIPTION
                "ICMP flood attack packet counter." 
        ::= { nsIdsAttkMonEntry 9 }
    nsIdsAttkMonUdpFlood OBJECT-TYPE
    	SYNTAX  Counter
        ACCESS  read-only
        STATUS  mandatory
        DESCRIPTION
                "udp flood attack packet counter." 
        ::= { nsIdsAttkMonEntry 10 }
    nsIdsAttkMonWinnuke OBJECT-TYPE
    	SYNTAX  Counter
        ACCESS  read-only
        STATUS  mandatory
        DESCRIPTION
                "weired netbios attack packet counter." 
        ::= { nsIdsAttkMonEntry 11 }
    nsIdsAttkMonPortScan OBJECT-TYPE
    	SYNTAX  Counter
        ACCESS  read-only
        STATUS  mandatory
        DESCRIPTION
                "port scan attempt attack packet counter." 
        ::= { nsIdsAttkMonEntry 12 }
    nsIdsAttkMonIpSweep OBJECT-TYPE
    	SYNTAX  Counter
        ACCESS  read-only
        STATUS  mandatory
        DESCRIPTION
                "address sweep attemp attack packet counter." 
        ::= { nsIdsAttkMonEntry 13 }

	nsAttkMonSynFrag OBJECT-TYPE
		SYNTAX  Counter 
		ACCESS  read-only
		STATUS  mandatory
		DESCRIPTION
			"Detect SYN fragment"
	::= { nsIdsAttkMonEntry 14 }

	nsAttkMonTcpNoFlag OBJECT-TYPE
		SYNTAX  Counter 
		ACCESS  read-only
		STATUS  mandatory
		DESCRIPTION
			"Detect TCP without flag set."
	::= { nsIdsAttkMonEntry 15 }

	nsAttkMonIpUnknownProt OBJECT-TYPE
		SYNTAX  Counter 
		ACCESS  read-only
		STATUS  mandatory
		DESCRIPTION
			"Detect Unknown protocol IP packet."
	::= { nsIdsAttkMonEntry 16 }

	nsAttkMonIpOptBad OBJECT-TYPE
		SYNTAX  Counter 
		ACCESS  read-only
		STATUS  mandatory
		DESCRIPTION
			"Detect IP bad option."
	::= { nsIdsAttkMonEntry 17 }

	nsAttkMonIpOptRecord OBJECT-TYPE
		SYNTAX  Counter 
		ACCESS  read-only
		STATUS  mandatory
		DESCRIPTION
			"Detect IP record option."
	::= { nsIdsAttkMonEntry 18 }

	nsAttkMonIpOptTimestamp OBJECT-TYPE
		SYNTAX  Counter 
		ACCESS  read-only
		STATUS  mandatory
		DESCRIPTION
			"Detect IP timestamp option."
	::= { nsIdsAttkMonEntry 19 }

	nsAttkMonIpOptSCHT OBJECT-TYPE
		SYNTAX  Counter 
		ACCESS  read-only
		STATUS  mandatory
		DESCRIPTION
			"Detect IP security option."
	::= { nsIdsAttkMonEntry 20 }

	nsAttkMonIpOptLSR OBJECT-TYPE
		SYNTAX  Counter 
		ACCESS  read-only
		STATUS  mandatory
		DESCRIPTION
			"Detect Loose source route."
	::= { nsIdsAttkMonEntry 21 }

	nsAttkMonIpOptSSR OBJECT-TYPE
		SYNTAX  Counter 
		ACCESS  read-only
		STATUS  mandatory
		DESCRIPTION
			"Detect strict source route."
	::= { nsIdsAttkMonEntry 22 }

	nsAttkMonIpOptStream OBJECT-TYPE
		SYNTAX  Counter 
		ACCESS  read-only
		STATUS  mandatory
		DESCRIPTION
			"Detect IP stream option."
	::= { nsIdsAttkMonEntry 23 }

	nsAttkMonIcmpFrag OBJECT-TYPE
		SYNTAX  Counter 
		ACCESS  read-only
		STATUS  mandatory
		DESCRIPTION
			"Detect ICMP fragment."
	::= { nsIdsAttkMonEntry 24 }
	
	nsAttkMonIcmpLarge OBJECT-TYPE
		SYNTAX  Counter 
		ACCESS  read-only
		STATUS  mandatory
		DESCRIPTION
			"Detect large ICMP packet."
	::= { nsIdsAttkMonEntry 25 }

	nsAttkMonTcpSynFin OBJECT-TYPE
		SYNTAX  Counter 
		ACCESS  read-only
		STATUS  mandatory
		DESCRIPTION
			"Detect TCP syn fin both set."
	::= { nsIdsAttkMonEntry 26 }

	nsAttkMonTcpFinNoAck OBJECT-TYPE
		SYNTAX  Counter 
		ACCESS  read-only
		STATUS  mandatory
		DESCRIPTION
			"Detect TCP fin set without ack bit set."
	::= { nsIdsAttkMonEntry 27 }

	nsAttkMonHttpMalUrl OBJECT-TYPE
		SYNTAX  Counter 
		ACCESS  read-only
		STATUS  mandatory
		DESCRIPTION
			"Detect malicious URL."
	::= { nsIdsAttkMonEntry 28 }

	nsAttkMonSessMalNum OBJECT-TYPE
		SYNTAX  Counter 
		ACCESS  read-only
		STATUS  mandatory
		DESCRIPTION
			"Detect malicious session connection."
	::= { nsIdsAttkMonEntry 29 }

	nsAttkMonSynAckAck OBJECT-TYPE
		SYNTAX  Counter 
		ACCESS  read-only
		STATUS  mandatory
		DESCRIPTION
			"Detect SYN ACK ACK attack."
	::= { nsIdsAttkMonEntry 30 }
	nsAttkMonIpFrag OBJECT-TYPE
		SYNTAX  Counter 
		ACCESS  read-only
		STATUS  mandatory
		DESCRIPTION
			"Block IP fragment packet."
	::= { nsIdsAttkMonEntry 31 }
    nsIdsAttkMonIfInfo OBJECT-TYPE
    	SYNTAX  INTEGER
        ACCESS  read-only
        STATUS  mandatory
        DESCRIPTION
                "Internal id assigned to this interface. Stays persistent across resets." 
        ::= { nsIdsAttkMonEntry 32 }
END
