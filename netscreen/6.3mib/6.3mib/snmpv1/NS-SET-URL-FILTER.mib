-- These MIBs were created on 05/027/2001
-- This module defines enterprise MIBs for URL filtering
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    all the configuration info  
--
--  Last modified date: 05/03/2004
--  Modified copyright and contact info
--    
--  Last modified date: 09/28/2001
--    
--  Last modified date: 11/12/2003
--  Correct spelling mistake
--    

NETSCREEN-SET-URL-FILTER-MIB DEFINITIONS ::= BEGIN
IMPORTS

    DisplayString 	FROM RFC1213-MIB 
    netscreenSetting FROM NETSCREEN-SMI;
    
    nsSetURLFilter OBJECT IDENTIFIER ::= { netscreenSetting 4 }

	nsSetUrlFilterViaWebsense OBJECT-TYPE
        SYNTAX  INTEGER {
        		disable(0),
        		enabled(1)
        }
    	ACCESS  read-only
        STATUS  mandatory
        DESCRIPTION
             "Enable URL Filtering via Websense Server."
        ::= { nsSetURLFilter 1 }

	nsSetUrlServerName OBJECT-TYPE
        SYNTAX  DisplayString(SIZE(0..32))
    	ACCESS  read-only
        STATUS  mandatory
        DESCRIPTION
             "Websense Server Name."
        ::= { nsSetURLFilter 2 }
    
	nsSetUrlServerPort OBJECT-TYPE
        SYNTAX  INTEGER
    	ACCESS  read-only
        STATUS  mandatory
        DESCRIPTION
             "Websense Server Port."
        ::= { nsSetURLFilter 3 }

	nsSetUrlCommTimeout OBJECT-TYPE
        SYNTAX  INTEGER (0..240)
    	ACCESS  read-only
        STATUS  mandatory
        DESCRIPTION
             "Communication timeout threshold of url filtering."
        ::= { nsSetURLFilter 4 }

	nsSetUrlServerStatus OBJECT-TYPE
        SYNTAX  INTEGER {
        	not-applicable(0),
        	running(1),
        	down(2)
        }
    	ACCESS  read-only
        STATUS  mandatory
        DESCRIPTION
             "Current server status."
        ::= { nsSetURLFilter 5 }

	nsSetUrlSerLostHdlWay OBJECT-TYPE
        SYNTAX  INTEGER {
        	block-all(0),
        	permit-all(1)
        }
    	ACCESS  read-only
        STATUS  mandatory
        DESCRIPTION
             "If connectivity to the Websense server is lost,
              the way of handling HTTP requests."
        ::= { nsSetURLFilter 6 }

	nsSetUrlBlockMsgType OBJECT-TYPE
        SYNTAX  INTEGER {
        	websense(0),
        	netscreen(1)
        }
    	ACCESS  read-only
        STATUS  mandatory
        DESCRIPTION
             "URL filter block message type."
        ::= { nsSetURLFilter 7 }

	nsSetUrlNsBlockMsg OBJECT-TYPE
        SYNTAX  DisplayString(SIZE(0..220))
    	ACCESS  read-only
        STATUS  mandatory
        DESCRIPTION
             "NetScreen device block message."
        ::= { nsSetURLFilter 8 }


END
