-- These MIBs were created on 05/27/2001
-- This module defines enterprise MIBs for time and NTP setting
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    NTP setting 
--
--  Last modified date: 05/03/2004
--  Modified copyright and contact info
--    
--  Last modified date: 09/28/2001
--    
--  Last modified date: 11/12/2003
--  Correct wrong title
--

NETSCREEN-SET-SYSTIME-MIB DEFINITIONS ::= BEGIN
IMPORTS

    DisplayString 	FROM RFC1213-MIB 
    netscreenSetting FROM NETSCREEN-SMI;
    
    nsSetSysTime OBJECT IDENTIFIER ::= { netscreenSetting 6 }
    nsSetSysTimeGmtOffset OBJECT-TYPE
        SYNTAX  INTEGER
        ACCESS  read-only
        STATUS  mandatory
        DESCRIPTION
            "GMT time offset of system time"
        ::= { nsSetSysTime 1 }

    nsSetSysTimeDaySaving OBJECT-TYPE
        SYNTAX  INTEGER {
             disable(0),
             enabled(1)
        }
        ACCESS  read-only
        STATUS  mandatory
        DESCRIPTION
            "enable daylight time saving method."
        ::= { nsSetSysTime 2 }
        
    nsSetSysTimeNTP OBJECT IDENTIFIER ::= { nsSetSysTime 3 }    
    nsSetNtpEnable OBJECT-TYPE
        SYNTAX  INTEGER {
             disable(0),
             enabled(1)
        }
        ACCESS  read-only
        STATUS  mandatory
        DESCRIPTION
            "Enable Network Time Protocol"
        ::= { nsSetSysTimeNTP 1 }
    
    nsSetNtpServer OBJECT-TYPE
        SYNTAX  IpAddress
        ACCESS  read-only
        STATUS  mandatory
        DESCRIPTION
            "Network Time Server ip"
        ::= { nsSetSysTimeNTP 2 }

    nsSetNtpUpdateInterval OBJECT-TYPE
        SYNTAX  INTEGER 
        ACCESS  read-only
        STATUS  mandatory
        DESCRIPTION
            "If NetScreen device use NTP to get system time. This object indicate
            the update system clock time interval."
        ::= { nsSetSysTimeNTP 3 }
END
