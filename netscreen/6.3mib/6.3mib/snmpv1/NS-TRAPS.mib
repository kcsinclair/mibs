-- These MIBs were created on 08/02/2000
--
-- Copyright (c) 1999-2004, Juniper Networks, Inc.
-- All rights reserved.
--
-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--  Added trap types 15, it is still in use
--  Last modified date: Mar 17, 2008
--  Added 5 new trap types - 800-804, 
--  Last modified date: 10/17/2005
--  Added 4 new trap types - ipv6 ip conflicts(101), dip util raise(102) and clear(103), 
--  ids-icmp-ping-id-zero(441).
--  Last modified date: 03/03/2005
--  Removed nsTrapType 15, 18 and 1000
--  Last modified date: 09/10/2004
--  Modified copyright and contact info
--  Last modified date: 05/03/2004
--  Add global-report manager specific trap
--  Last modified date: 09/28/2001
--  Add new traps (430~434)
--  Last modified date: 1/23/2004
--  Add traffic traps (1,2) and route traps (205~225)
--  Last modified date: 3/24/2004
-- 

NETSCREEN-TRAP-MIB DEFINITIONS ::= BEGIN
IMPORTS
    enterprises FROM RFC1155-SMI
    DisplayString FROM RFC1213-MIB
    netscreen, netscreenTrapInfo FROM NETSCREEN-SMI;
    
netscreenTrapType OBJECT-TYPE 
	SYNTAX  INTEGER {
		traffic-sec(1),  -- Traffic per-second threshold
		traffic-min(2),  -- Traffic per-minute threshold
	    multi-auth-fail(3), -- Multiple user auth fail alarm type
		winnuke(4), 		-- Winnuke pak
		syn-attack(5), 	-- Syn attack
		tear-drop(6),		-- tear-drop attack
		ping-death(7), 	-- Ping of Death attack
		ip-spoofing(8),	-- IP spoofing attack
		ip-src-route(9),	-- IP source routing attack
		land(10),		-- land attack
		icmp-flood(11),	-- ICMP flooding attack
		udp-flood(12),	-- UDP flooding attack	
	
		illegal-cms-svr(13),	-- Illegal server IP to connect to CMS port		
		url-block-srv(14),	-- URL blocking server connection alarm
		high-availability(15),	-- high availability
	 
		port-scan(16),	-- Port Scan attack
		addr-sweep(17),	-- address sweep attack
		deny-policy(18), -- deny by policy attack
		device-dead(19), -- device is dead		  
		low-memory(20),	-- memory low
				  
		dns-srv-down(21),	-- DNS server unreachable
		generic-HW-fail(22),	-- Fan, Power Supply failure
		lb-srv-down(23),	-- Load balance server unreachable
		log-full(24),		-- log buffer overflow
		x509(25),		-- X509 related	
		vpn-ike(26),		-- VPN and IKE related
		admin(27),		-- admin realted
		sme(28),		-- Illegal src ip to connect to sme port
		dhcp(29),		-- DHCP related 
		cpu-usage-high(30),	-- CPU usage is high
		ip-conflict(31),			-- Interface IP conflict 
		attact-malicious-url(32),	-- Microsoft IIS server vulnerability 
		session-threshold(33),		-- session threshold is exceeded 
		ssh-alarm(34),				-- SSH related alarms 
        audit-storage(35), -- Audit storage related alarms
        memory-normal(36), -- memory normal
        cpu-usage-normal(37), -- cpu usage normal
        rxbd-low-alarm(39), -- driver's rx bd shortage
		vpn-tunnel-up(40),	-- VPN tunnel from down to up	
		vpn-tunnel-down(41),	-- VPN tunnel from up to down	
		vpn-replay-attack(42),		-- VPN replay detected
        vpn-l2tp-tunnel-remove(43),     -- VPN tunnel removed
        vpn-l2tp-tunnel-remove-err(44), -- VPN tunnel removed and error detected 
        vpn-l2tp-call-remove(45),       -- VPN call removed
        vpn-l2tp-call-remove-err(46),   -- VPN call removed and error detected
		vpn-ias-too-many(47),	-- Number of IAS exceeds configured maximum
		vpn-ias-over-threshold(48),	-- Number of IAS crossed configured upper threshold
		vpn-ias-under-threshold(49),	-- Number of IAS crossed configured lower threshold
		vpn-ias-ike-error(50),	-- IKE error occured for the IAS session
		allocated-session-threshold(51),	-- allocated session exceed threshold
        av-csp-alarm(52), -- av-csp related alarm
        av-alarm(53), -- av related alarm
        apppry-alarm(54), -- apppry related alarm
		nsrp-rto-up(60),      -- NSRP rto self unit status change from up to down     
		nsrp-rto-down(61),      -- NSRP rto self unit status change from down to up     
		nsrp-trackip-success(62),     -- NSRP track ip successed      
		nsrp-trackip-failed(63),      -- NSRP track ip failed 
		nsrp-trackip-failover(64),    -- NSRP track ip fail over
		nsrp-inconsistent-configuration(65),	-- NSRP inconsistent configuration between master and backup
        trackip-status(66), -- track ip status related alarm
		nsrp-vsd-init(70),    -- NSRP vsd  group status change to elect
		nsrp-vsd-master(71),  -- NSRP vsd  group status change to master
		nsrp-vsd-pbackup(72), -- NSRP vsd  group status change to primary backup
		nsrp-vsd-backup(73),  -- NSRP vsd  group status change to backup
		nsrp-vsd-ineligible(74),       -- NSRP vsd  group status change to ineligible
		nsrp-vsd-inoperable(75),	-- NSRP VSD group status change to inoperable
		nsrp-vsd-req-hearbeat-2nd(76),	-- NSRP VSD request heartbeat from 2nd HA path 
		nsrp-vsd-reply-2nd(77),		-- NSRP VSD reply to 2nd path request 
		nsrp-rto-duplicated(78),	-- NSRP duplicated RTO group found 
	
        ip-dup-master(79),  -- NSRP duplicated VSD group master
        di-heap-create-fail(80),  -- MEM cannot find usable memory for current pool
        mem-alloc-fail(81),  -- MEM cannot find usable in any pool
        vrrp-status-alarm(82),  -- VRRP status related alarm
        sccp-alarm(83),  -- SCCP related alarm
        mgcp-reinit(84),  -- MGCP related alarm
        mlfr-alarm(85),  -- MLFR related alarm
        fr-alarm(86),  -- FR related alarm
        cisco-hdlc-alarm(87),  -- CISCO HDLC related alarm
        pppow-alarm(88),  -- PPPOW related alarm
        h323-alarm(89),  -- H323 related alarm
        isdn-alarm(90),  -- ISDN related alarm
		interface-backup(91),  -- interface backup
		wan-card-function(92),  -- Card function is abnormal
		usb-device-operation(93),   -- A USB key is plug/unplug from USB port 
		interface-failure(94),  -- interface failure
		ppp-no-ip-cfg(95),   -- No ppp IP pool configured 
		ppp-no-ip-in-pool(96),   -- IP pool exhausted. No ip to assign
       	ip-addr-event(101),			-- Any change to interface IP address can use the type
		dip-util-raise(102),		-- DIP utilization reaches raised threshold limit
		dip-util-clear(103),		-- DIP utilization reaches clear threshold limit
        dot1x-alarm(105),   -- DOT1X related alarm
        vpn-ias-radius-error(110),  -- VPN IAS radius error
        vpn-ikeid-enum-attack(111),  -- VPN IKEID enum attack
        vpn-softlimit-reached(112),  -- VPN soft limit reached
        vpn-ikedos-attack(113),   -- VPN IKE dos attack
        vpn-acvpn-profile-error(114),  -- VPN acvpn profile error
	    route-sys-entry-ex(200),  -- exceed maximum routing entry allowed for the system
	    route-vr-entry-ex(201),  -- exceed maximum routing entry allowed for a vr
	    route-ospf-hello-flood(202),  -- exceed the hello packet threshold per hello interval
	    route-ospf-lsa-flood(203),   -- exceed the lsa packet threshold per lsa threshold
	    route-rip-update-flood(204),  -- exceed the update4 packet threshold per update time in rip
		route-alarm(205),				-- Errors in route module (exceed limit, malloc failure, add-perfix failure etc) 
		osfp-flood(206),					-- LSA/Hello packets flood in OSPF, route redistribution exceed limit, 
		rip-flood(207),					-- Update packet floods in RIP 
		bgp-established(208),			-- Peer forms adjacency completely
		bgp-backwardtransition(209),		-- Peer's adjacency is torn down, goes to Idle state
		ospf-virtifstatechange(210),		-- change in virtual link's state (down, point-to-point etc)
		ospf-nbrstatechange(211),		-- change in neighbor's state on regular interface (down, 2way, full etc)
		ospf-virtnbrstatechange(212),	-- change in neighbor's state on virtual link (down, full etc)
		ospf-ifconfigerror(213),			-- authentication mismatch/area mismatch etc on regular interface
		ospf-virtifconfigerror(214),		-- authentication mismatch/area mismatch etc on virtual link
		ospf-ifauthfailure(215),			-- Authentication eror on regular interface
		ospf-virtifauthfailure(216),		-- Authentication eror on virtual link
		ospf-ifrxbadpacket(217),			-- lsa received with invalid lsa-type on regular interface
		ospf-virtifrxbadpacket(218),		-- lsa received with invalid lsa-type on virtual link
		ospf-txretransmit(219),			-- retransmission to neighbor on regular interface
		ospf-virtiftxretransmit(220),	-- retransmission to neighbor on virtual link
		ospf-originatelsa(221),			-- new LSA generated by local router
		ospf-maxagelsa(222),				-- LSA aged out
		ospf-lsdboverflow(223),			-- when total LSAs in database exceed predefined limit
		ospf-lsdbapproachingoverflow(224), -- when total LSAs in database approach predefined limit
		ospf-ifstatechange(225),			-- change in regular interface state (up/down, dr/bdr etc)

	    bgp-alarm(226),  -- BGP related alarm
	    ripng-flood(227),  -- packet floods in RIPng
	    route-ripng-update-flood(228),  -- exceed the update4 packet threshold per update time in ripng
	    pbr-alarm(229),  -- PBR related alarm
	    nhrp-alarm(230),  -- NHRP related alarm
	    ospfv3-alarm(231),  -- OSPFV3 related alarm
		ids-component(400),			-- block java/active-x component
		ids-icmp-flood(401),		-- icmp flood attack
		ids-udp-flood(402),			-- udp flood attack
		ids-winnuke(403),			-- winnuke attack
		ids-port-scan(404),			-- port scan attack
		ids-addr-sweep(405),		-- address sweep attack
		ids-tear-drop(406),			-- tear drop attack
		ids-syn(407),				-- syn flood attack
		ids-ip-spoofing(408),		-- ip spoofing attack 
		ids-ping-death(409),		-- ping of death attack
		ids-ip-source-route(410),	-- filter ip packet with source route option
		ids-land(411),				-- land attack
		syn-frag-attack(412), -- screen syn fragment attack
		tcp-without-flag(413),  -- screen tcp packet without flag attack
		unknow-ip-packet(414), -- screen unknown ip packet  
		bad-ip-option(415), -- screen	bad ip option
        ip-option-record(416),  -- screen ip option record 
        ip-option-timestamp(417),  -- screen ip option timestamp
        ip-option-scht(418),  -- screen ip option scht
        ip-option-lsr(419),  -- screen ip option lsr
        ip-option-ssr(420),  -- screen ip option ssr
        ip-option-stream(421),  -- screen ip option stream
        icmp-fragment(422),  -- screen icmp fragment packet
        too-large-icmp(423),  -- screen too large icmp packet
        tcp-syn-fin(424),  -- screen tcp flag syn-fin set
        tcp-fin-no-ack(425),  -- screen tcp fin without ack
        tcp-mal-url(426),  -- screen mal url
        tcp-sess-mal-num(427),  -- screen sess mal num

        -- avoid replying to syns after excessive 3 way TCP handshakes from
        -- same src ip but not proceeding with user auth. (not replying to
        -- username/password)..
        ids-tcp-syn-ack-ack(428),

        ids-ip-block-frag(429),  -- ip fragment
		dst-ip-session-limit(430),	-- Dst IP-based session limiting
		ids-block-zip(431),			-- HTTP component blocking for .zip files
		ids-block-jar(432),			-- HTTP component blocking for Java applets
		ids-block-exe(433),			-- HTTP component blocking for .exe files
		ids-block-activex(434),		-- HTTP component blocking for ActiveX controls
        tcp-syn-mac(435),  -- screenos tcp syn mac
        ids-nac-attack(436),  -- screenos nac attack
        ids-icmp-ping-id-zero(441),  -- icmp ping id 0
        tcp-sweep(442),  -- tcp sweep
        udp-sweep(443),  -- udp sweep
		av-scan-mgr(554),  -- AV Scan Manager Alarm, sofeware trap
        mcast-base(600),  -- starting value for multicast alarm
        mcore-alarm(601),  -- mcore related alarm
        spim-alarm(602),  -- spim related alarm
        sm-base(700),  -- starting value for Security Module alarm
        sm-down(701),  -- Security Module down detected
        sm-packet-drop(702),  -- Security Module packet droped detected
        sm-overload(703),  -- Security Module memory, CPU and session detected
        sm-cpu-unresponsive(704),  -- Security Module CPU unresponsive detected
        sm-engine-unresponsive(705),  -- Security Module Engine unresponsive
        sm-policy-abnormal(706),  -- Secruity Module Policy Abnormal
        switch(751),  -- switch alarm
        sfp(752), -- sfp alarm
		cpu-limit-s2f-forced(800),   --Shared to fair transition forced
		cpu-limit-s2f-auto(801),     --Shared to fair transition auto
		cpu-limit-f2s-forced(802),   --Fair to shared transition forced
		cpu-limit-f2s-timeout(803),  --Fair to shared transition because of timeout
		cpu-limit-f2s-auto(804)      --Fair to shared transition auto
        sec-potential-voilation(805),  --Flow potential violation
        flow-sess-cache(806),  --Flow session cache alarm     
        vsys-session-limit(850)   --vsys session limit alarm   
	}
	ACCESS  not-accessible
	STATUS  mandatory
	DESCRIPTION
		"The integer value of the raised alarm type.
		Note that the type should be interpreted within a specific trap"
	::= { netscreenTrapInfo 1 }

netscreenTrapDesc OBJECT-TYPE 
	SYNTAX  DisplayString (SIZE (0..255))
	ACCESS  not-accessible
	STATUS  mandatory
	DESCRIPTION
		"The textual description of the alarm"
	::= { netscreenTrapInfo 3 }

netscreenTrapHw TRAP-TYPE
	ENTERPRISE netscreen
	VARIABLES  { netscreenTrapType, netscreenTrapDesc  }
	DESCRIPTION
		"This trap indicates that some kind of hardware problem has occured."
	::= 100

netscreenTrapFw TRAP-TYPE
	ENTERPRISE netscreen
	VARIABLES  { netscreenTrapType, netscreenTrapDesc  }
	DESCRIPTION
                "This trap indicates that some kind of firewall functions has been triggered."
             ::= 200

netscreenTrapSw TRAP-TYPE
             ENTERPRISE netscreen
             VARIABLES  { netscreenTrapType, netscreenTrapDesc  }
             DESCRIPTION
                "This trap indicates that some kind of software problem has occured."
             ::= 300

netscreenTrapTrf TRAP-TYPE
             ENTERPRISE netscreen
             VARIABLES  { netscreenTrapType, netscreenTrapDesc  }
             DESCRIPTION
                "This trap indicates that some kind of traffic conditions has been triggered."
             ::= 400

netscreenTrapVpn TRAP-TYPE
             ENTERPRISE netscreen
             VARIABLES  { netscreenTrapType, netscreenTrapDesc  }
             DESCRIPTION
                "This trap indicates that VPN tunnel status has occured."
             ::= 500

netscreenTrapNsrp TRAP-TYPE
             ENTERPRISE netscreen
             VARIABLES  { netscreenTrapType, netscreenTrapDesc  }
             DESCRIPTION
                "This trap indicates that NSRP status has occured."
             ::= 600
	     
netscreenTrapGPRO TRAP-TYPE
             ENTERPRISE netscreen
             VARIABLES  { netscreenTrapType, netscreenTrapDesc  }
             DESCRIPTION
                "This trap indicates that some kind of Global PRO problems has occurred."
             ::= 700

netscreenTrapDrp TRAP-TYPE
             ENTERPRISE netscreen
             VARIABLES  { netscreenTrapType, netscreenTrapDesc  }
             DESCRIPTION
                "This trap indicates that Drp status has occured."
             ::= 800

netscreenTrapIFFailover TRAP-TYPE
             ENTERPRISE netscreen
             VARIABLES  { netscreenTrapType, netscreenTrapDesc  }
             DESCRIPTION
                "This trap indicates that interface fail over status has occured."
             ::= 900

netscreenTrapIDPAttack TRAP-TYPE
             ENTERPRISE netscreen
             VARIABLES  { netscreenTrapType, netscreenTrapDesc  }
             DESCRIPTION
                "This trap indicates that IDP attack status has occured."
             ::= 1000
END
