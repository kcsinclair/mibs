-- These MIBs were created on 05/27/2001
-- This module defines enterprise MIBs for Global, Global-Pro and NSM setting
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    Global, Global-Pro and NSM settings
--
--  Last modified date: 05/03/2004
--  Modified copyright and contact info
--    
--  Last modified date: 09/28/2001
--    

NETSCREEN-SET-GLB-MIB DEFINITIONS ::= BEGIN
IMPORTS

    DisplayString 	FROM RFC1213-MIB 
    netscreenSetting FROM NETSCREEN-SMI;

    nsSetGlbMng OBJECT IDENTIFIER ::= { netscreenSetting 10 }
    nsSetGlbMngVPNEnable OBJECT-TYPE
        SYNTAX  INTEGER {
             disable(0),
             enabled(1)
        }
        ACCESS  read-only
        STATUS  mandatory
        DESCRIPTION
            "Secure NS Global Manager/PRO traffic via VPN encryption."
        ::= { nsSetGlbMng 1 }

    nsSetGlbMngEnable OBJECT-TYPE
        SYNTAX  INTEGER {
             disable(0),
             enabled(1)
        }
        ACCESS  read-only
        STATUS  mandatory
        DESCRIPTION
            "Enable Global Manager service on NetScreen device."
        ::= { nsSetGlbMng 2 }

    nsSetGlbProEnable OBJECT-TYPE
        SYNTAX  INTEGER {
             disable(0),
             enabled(1)
        }
        ACCESS  read-only
        STATUS  mandatory
        DESCRIPTION
            "Enable Global Pro Management service on NetScreen device."
        ::= { nsSetGlbMng 3 }
    
    nsSetGlbManagerSetting OBJECT IDENTIFIER ::= {nsSetGlbMng 4 }
    nsSetGlbMngSerName OBJECT-TYPE
        SYNTAX  DisplayString (SIZE(0..32))
        ACCESS  read-only
        STATUS  mandatory
        DESCRIPTION
            "Server Name of Global Manager service."
        ::= { nsSetGlbManagerSetting 1 }
    nsSetGlbMngSerTCP OBJECT-TYPE
        SYNTAX  INTEGER
        ACCESS  read-only
        STATUS  mandatory
        DESCRIPTION
            "TCP port number of Global Manager service."
        ::= { nsSetGlbManagerSetting 2 }
    nsSetGlbMngSerUDP OBJECT-TYPE
        SYNTAX  INTEGER
        ACCESS  read-only
        STATUS  mandatory
        DESCRIPTION
            "UDP port number of Global Manager service."
        ::= { nsSetGlbManagerSetting 3 }
    nsSetGlbMngLocal OBJECT-TYPE
        SYNTAX  INTEGER
        ACCESS  read-only
        STATUS  mandatory
        DESCRIPTION
            "Global Manager service listening port number(NS device side)."
        ::= { nsSetGlbManagerSetting 4 }

    nsSetGlbProManagerSetting OBJECT IDENTIFIER ::= {nsSetGlbMng 5 }
    nsSetGlbProPriSer OBJECT-TYPE
        SYNTAX  IpAddress
        ACCESS  read-only
        STATUS  mandatory
        DESCRIPTION
            "Primary IP Address of Global PRO Server."
        ::= { nsSetGlbProManagerSetting 1 }
    nsSetGlbProSecSer OBJECT-TYPE
        SYNTAX  IpAddress
        ACCESS  read-only
        STATUS  mandatory
        DESCRIPTION
            "Secondary IP Address of Global PRO Server"
        ::= { nsSetGlbProManagerSetting 2 }    
        
    nsSetGlbMngSetting OBJECT IDENTIFIER ::= {nsSetGlbMng 6 }
    nsSetGlbMngProtDist OBJECT-TYPE
        SYNTAX  INTEGER {
             disable(0),
             enabled(1)
        }
        ACCESS  read-only
        STATUS  mandatory
        DESCRIPTION
            "Enable Protocol Distribution in global management service."
        ::= { nsSetGlbMngSetting 1 }

    nsSetGlbMngEthStatis OBJECT-TYPE
        SYNTAX  INTEGER {
             disable(0),
             enabled(1)
        }
        ACCESS  read-only
        STATUS  mandatory
        DESCRIPTION
            "Enable Ethernet Statistics in global management service."
        ::= { nsSetGlbMngSetting 2 }

    nsSetGlbMngAttStatis OBJECT-TYPE
        SYNTAX  INTEGER {
             disable(0),
             enabled(1)
        }
        ACCESS  read-only
        STATUS  mandatory
        DESCRIPTION
            "Enable Attack Statistics in global management service."
        ::= { nsSetGlbMngSetting 3 }

    nsSetGlbMngPlyStatis OBJECT-TYPE
        SYNTAX  INTEGER {
             disable(0),
             enabled(1)
        }
        ACCESS  read-only
        STATUS  mandatory
        DESCRIPTION
            "Enable Policy Statistics in global management service."
        ::= { nsSetGlbMngSetting 4 }

    nsSetGlbMngFlowStatis OBJECT-TYPE
        SYNTAX  INTEGER {
             disable(0),
             enabled(1)
        }
        ACCESS  read-only
        STATUS  mandatory
        DESCRIPTION
            "Enable Flow Statistics in global management service."
        ::= { nsSetGlbMngSetting 5 }

    nsSetGlbMngTrafAlm OBJECT-TYPE
        SYNTAX  INTEGER {
             disable(0),
             enabled(1)
        }
        ACCESS  read-only
        STATUS  mandatory
        DESCRIPTION
            "Enable Traffic Alarms in global management service."
        ::= { nsSetGlbMngSetting 6 }

    nsSetGlbMngAttAlm OBJECT-TYPE
        SYNTAX  INTEGER {
             disable(0),
             enabled(1)
        }
        ACCESS  read-only
        STATUS  mandatory
        DESCRIPTION
            "Enable Attack Alarms in global management service."
        ::= { nsSetGlbMngSetting 7 }

    nsSetGlbMngEvtAlm OBJECT-TYPE
        SYNTAX  INTEGER {
             disable(0),
             enabled(1)
        }
        ACCESS  read-only
        STATUS  mandatory
        DESCRIPTION
            "Enable Event Alarms in global management service."
        ::= { nsSetGlbMngSetting 8 }

    nsSetGlbMngCfgLog OBJECT-TYPE
        SYNTAX  INTEGER {
             disable(0),
             enabled(1)
        }
        ACCESS  read-only
        STATUS  mandatory
        DESCRIPTION
            "Enable Configuration Logs in global management service."
        ::= { nsSetGlbMngSetting 9 }

    nsSetGlbMngTrafLog OBJECT-TYPE
        SYNTAX  INTEGER {
             disable(0),
             enabled(1)
        }
        ACCESS  read-only
        STATUS  mandatory
        DESCRIPTION
            "Enable Traffic Logs in global management service."
        ::= { nsSetGlbMngSetting 10 }

    nsSetGlbMngInfoLog OBJECT-TYPE
        SYNTAX  INTEGER {
             disable(0),
             enabled(1)
        }
        ACCESS  read-only
        STATUS  mandatory
        DESCRIPTION
            "Enable Information Logs in global management service."
        ::= { nsSetGlbMngSetting 11 }

    nsSetGlbMngSelfLog OBJECT-TYPE
        SYNTAX  INTEGER {
             disable(0),
             enabled(1)
        }
        ACCESS  read-only
        STATUS  mandatory
        DESCRIPTION
            "Enable Self Logs in global management service."
        ::= { nsSetGlbMngSetting 12 }
    
END
