-- These MIBs were created on 05/27/2001
-- This module defines enterprise MIBs for SNMP setting
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    SNMP settings
--
--  Last modified date: 05/03/2004
--  Modified copyright and contact info
--    
--  Last modified date: 09/28/2001
--    
--  Last modified date: 11/10/2003
--  Correct spelling mistake
--    

NETSCREEN-SET-SNMP-MIB DEFINITIONS ::= BEGIN
IMPORTS

    DisplayString 	FROM RFC1213-MIB 
    netscreenSetting FROM NETSCREEN-SMI;

    nsSetSNMP OBJECT IDENTIFIER ::= { netscreenSetting 9 }

    nsSetSnmpSysName OBJECT-TYPE
        SYNTAX  DisplayString (SIZE(0..255)) 
        ACCESS  read-only
        STATUS  mandatory
        DESCRIPTION
            "SNMP agent's sysname."
        ::= { nsSetSNMP 1 }

    nsSetSnmpContact OBJECT-TYPE
        SYNTAX  DisplayString (SIZE(0..255)) 
        ACCESS  read-only
        STATUS  mandatory
        DESCRIPTION
            "contact name."
        ::= { nsSetSNMP 2 }

    nsSetSnmpLocation OBJECT-TYPE
        SYNTAX  DisplayString (SIZE(0..255)) 
        ACCESS  read-only
        STATUS  mandatory
        DESCRIPTION
            "SNMP agent Location."
        ::= { nsSetSNMP 3 }

    nsSetSnmpVPNEnable OBJECT-TYPE
        SYNTAX  INTEGER {
             disable(0),
             enabled(1)
        }
        ACCESS  read-only
        STATUS  mandatory
        DESCRIPTION
            "Secure SNMP traffic via VPN encryption "
        ::= { nsSetSNMP 4 }

    nsSetSnmpCommHostTable OBJECT-TYPE 
    	SYNTAX SEQUENCE OF NsSetSnmpCommHostEntry
    	ACCESS not-accessible
    	STATUS mandatory
    	DESCRIPTION
    	        "The snmp community and host table"
    	::= { nsSetSNMP 5  }

    nsSetSnmpCommHostEntry OBJECT-TYPE
        SYNTAX  NsSetSnmpCommHostEntry
        ACCESS  not-accessible
        STATUS  mandatory
        DESCRIPTION
               "An entry containing community and hosts information"
        INDEX   { nsSetSnmpCommHostIndex }
        ::= { nsSetSnmpCommHostTable 1 }

	NsSetSnmpCommHostEntry ::=
		SEQUENCE {
          nsSetSnmpCommHostIndex
              INTEGER,
 		  nsSetSnmpCommunity 
		      DisplayString,
		  nsSetSnmpHostInComm
		      IpAddress,
		  nsSetSnmpWritePermit
		  	  INTEGER,
		  nsSetSnmpTrapPermit
		  	  INTEGER,
		  nsSetSnmpTrafficAlarmPermit
		  	  INTEGER
        }

	nsSetSnmpCommHostIndex OBJECT-TYPE
    	SYNTAX  INTEGER
        ACCESS  read-only
        STATUS  mandatory
        DESCRIPTION
             "A unique value for snmp community & host table.  Its value
              ranges between 0 and 65535 and may not be contiguous." 
        ::= { nsSetSnmpCommHostEntry 1 }

	nsSetSnmpCommunity OBJECT-TYPE
    	SYNTAX  DisplayString (SIZE(0..32))
        ACCESS  read-only
        STATUS  mandatory
        DESCRIPTION
             "SNMP community name." 
        ::= { nsSetSnmpCommHostEntry 2 }

	nsSetSnmpHostInComm OBJECT-TYPE
    	SYNTAX  IpAddress
        ACCESS  read-only
        STATUS  mandatory
        DESCRIPTION
             "SNMP host ip address." 
        ::= { nsSetSnmpCommHostEntry 3 }

    nsSetSnmpWritePermit OBJECT-TYPE
        SYNTAX  INTEGER {
             no(0),
             yes(1)
        }
        ACCESS  read-only
        STATUS  mandatory
        DESCRIPTION
            "Permission to write."
        ::= { nsSetSnmpCommHostEntry 4 }

    nsSetSnmpTrapPermit OBJECT-TYPE
        SYNTAX  INTEGER {
             no(0),
             yes(1)
        }
        ACCESS  read-only
        STATUS  mandatory
        DESCRIPTION
            "Permission to receive trap."
        ::= { nsSetSnmpCommHostEntry 5 }

    nsSetSnmpTrafficAlarmPermit OBJECT-TYPE
        SYNTAX  INTEGER {
             no(0),
             yes(1)
        }
        ACCESS  read-only
        STATUS  mandatory
        DESCRIPTION
            "Permission of including traffic alarm in trap."
        ::= { nsSetSnmpCommHostEntry 6 }

END
