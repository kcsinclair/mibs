-- These MIBs were created on 05/027/2001
-- This module defines enterprise MIBs for DHCP Configuration
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Descr
--    This module defines the object that are used to monitor
--    all the configuration info  
--
--  Last modified date: 05/03/2004
--  Modified copyright and contact info
--    
--  Last modified date: 09/28/2001
--  
--  change dhcp configuration per physical interface
--  Last modified date: 12/12/2001
--    
--  Last modified date: 11/10/2003
--  Correct wrong title
--

NETSCREEN-SET-DHCP-MIB DEFINITIONS ::= BEGIN
IMPORTS

    DisplayString 	FROM RFC1213-MIB 
    netscreenSetting FROM NETSCREEN-SMI;
    
    nsSetDHCP OBJECT IDENTIFIER ::= { netscreenSetting 5 }
    
    nsSetDhcpTable OBJECT-TYPE
    	SYNTAX SEQUENCE OF NsSetDhcpEntry
    	ACCESS not-accessible
    	STATUS mandatory
    	DESCRIPTION
    		"NetScreen ScreenOS can allow dhcp service on each of NetScreen
    		device's physical interface. This table collects the dhcp 
    		configuration on each physical interface."
		::= {nsSetDHCP 1}

	nsSetDhcpEntry OBJECT-TYPE
		SYNTAX  NsSetDhcpEntry
		ACCESS  not-accessible
		STATUS  mandatory
		DESCRIPTION
			"Hold the firewall setting attribute."
		INDEX   { nsSetDhcpIfIdx }
              ::= { nsSetDhcpTable 1 }
       
   
	NsSetDhcpEntry ::=
		SEQUENCE {
			nsSetDhcpIfIdx
				INTEGER,
			nsSetDHCPService
				INTEGER,
			nsSetDHCPRelayServer
				DisplayString,
			nsSetDHCPVpnEncryp
				INTEGER,
			nsSetDhcpIfInfo
				INTEGER
			}
				
	nsSetDhcpIfIdx OBJECT-TYPE
		SYNTAX  INTEGER
		ACCESS  read-only
		STATUS  mandatory
		DESCRIPTION
			"Unique interface id."
	::= { nsSetDhcpEntry 1 }

	nsSetDHCPService OBJECT-TYPE
        SYNTAX  INTEGER {
        		none(0),
        		dhcp-relay-agent(1),
        		dhcp-server(2)
        }
    	ACCESS  read-only
        STATUS  mandatory
        DESCRIPTION
             "DHCP service type for trusted network."
        ::= { nsSetDhcpEntry 2 }
        
	nsSetDHCPRelayServer OBJECT-TYPE
        SYNTAX  DisplayString(SIZE(0..128))
    	ACCESS  read-only
        STATUS  mandatory
        DESCRIPTION
             "DHCP relay agent server name."
        ::= { nsSetDhcpEntry 3 }
        
	nsSetDHCPVpnEncryp OBJECT-TYPE
        SYNTAX  INTEGER {
        		disable(0),
        		enabled(1)
        }
    	ACCESS  read-only
        STATUS  mandatory
        DESCRIPTION
             "Secure DHCP relay agent traffic via VPN encryption."
        ::= { nsSetDhcpEntry 4 }

	nsSetDhcpIfInfo OBJECT-TYPE
		SYNTAX  INTEGER
		ACCESS  read-only
		STATUS  mandatory
		DESCRIPTION
			"Internal id assigned to this interface. Stays persistent across resets."
	::= { nsSetDhcpEntry 5 }

END
