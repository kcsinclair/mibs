-- This module defines UAC MIBs for modular ScreenOS platforms
-- Copyright (c) 1999-2010, Juniper Networks, Inc.
-- All rights reserved.
-- netscreenUACMibModule MODULE-IDENTITY
--    LAST-UPDATED  "201004140000Z" -- Apr 14, 2010
--    ORGANIZATION
--        "Juniper Networks, Inc."
--    CONTACT-INFO
--        "Customer Support
--
--         1194 North Mathilda Avenue 
--         Sunnyvale, California 94089-1206
--         USA

--         Tel: 1-800-638-8296
--         E-mail: customerservice@juniper.net
--         HTTP://www.juniper.net"
--    DESCRIPTION
--        "This module defines the object that are used to monitor all
--        UAC"
--    REVISION      "201004140000Z" -- Apr 14, 2010
--    DESCRIPTION
--        "Creation Date"
--   ::= { netscreenUAC 0 }

NETSCREEN-UAC-MIB DEFINITIONS ::= BEGIN
IMPORTS
    DisplayString 	FROM RFC1213-MIB
   	netscreenUAC 	FROM NETSCREEN-SMI;
   	
   	nsUACActiveUsers OBJECT-TYPE
    SYNTAX        INTEGER
    MAX-ACCESS    read-only
    STATUS        current
    DESCRIPTION
        "Active users on this box, base on auth entry from UAC controler"
    ::= { netscreenUAC 1 }
    
    nsUACControlerStatusTable OBJECT-TYPE
    SYNTAX        SEQUENCE OF NsUACControlerStatusEntry 
    MAX-ACCESS    not-accessible
    STATUS        current
    DESCRIPTION
        "NetScreen UAC controler status table"
    ::= { netscreenUAC 2}

     
    nsUACControlerStatusEntry OBJECT-TYPE
    SYNTAX        NsUACControlerStatusEntry 
    MAX-ACCESS    not-accessible
    STATUS        current
    DESCRIPTION
        "Each entry in the table holds a set of configuration
         parameters associated  with an instance of secure UAC."
    INDEX
        { nsUACControlerID}
    ::= { nsUACControlerStatusTable 1 } 
         
	NsUACControlerStatusEntry ::= SEQUENCE
	{
	    nsUACControlerId         INTEGER,
	    nsUACControlerName       DisplayString,
	    nsUACControlerHost       DisplayString,
	    nsUACConnectionStatus     INTEGER
	}

     
    nsUACControlerId OBJECT-TYPE
    SYNTAX        INTEGER (1..8)
    MAX-ACCESS    read-only
    STATUS        mandatory
    DESCRIPTION
        "A unique value for UAC table.  Its value ranges between 1 and
         65535 and may not be contiguous.  the index has no other
         meaning but a pure index"
    ::= { nsUACControlerStatusEntry 1 }

	nsUACControlerName OBJECT-TYPE
	    SYNTAX        DisplayString (SIZE(0..32))
	    MAX-ACCESS    read-only
	    STATUS        mandatory
	    DESCRIPTION
	        "Secure UAC name."
	    ::= { nsUACControlerStatusEntry 2 }
	
	
	nsUACControlerHost OBJECT-TYPE
	    SYNTAX        DisplayString (SIZE(0..32))
	    MAX-ACCESS    read-only
	    STATUS        mandatory
	    DESCRIPTION
	        "Secure UAC name."
	    ::= { nsUACControlerStatusEntry 3 }
	
	nsUACConnectionStatus OBJECT-TYPE
	    SYNTAX        INTEGER {
	        disconnected(0),
	        connecting(1),
	    }
	    MAX-ACCESS    read-only
	    STATUS        mandatory
	    DESCRIPTION
	        "UAC controler status table"
	    ::= { nsUACControlerStatusEntry 4 }
	    
   	nsUACGlobalStatus OBJECT-TYPE
	    SYNTAX        INTEGER {
	        disconnected(0),
	        connected(1),
	    }
    	MAX-ACCESS    read-only
    	STATUS        current
    	DESCRIPTION
        	"To indicate whether there is at least one heaty IC-IE connection"
    	::= { netscreenUAC 3 }
END
