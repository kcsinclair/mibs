-- These MIBs were created on 05/02/2001
-- This module defines enterprise MIBs for ARP
-- 
-- Copyright (c) 1999-2004, Juniper Networks, Inc.
-- All rights reserved.
-- 

-- MODULE-IDENTITY
--  OrgName
--    Juniper Networks, Inc.
--  ContactInfo
--     Customer Support
--     
--     1194 North Mathilda Avenue 
--     Sunnyvale, California 94089-1206
--     USA
--     
--     Tel: 1-800-638-8296
--     E-mail: customerservice@juniper.net
--     HTTP://www.juniper.net"
--
--  Last modified date: 05/03/2004
--  Modified copyright and contact info
--    
--  Last modified date: 09/28/2001
--    
--  Last modified date: 11/10/2003
--  Correct spelling mistake 
--

NETSCREEN-IP-ARP-MIB DEFINITIONS ::= BEGIN
IMPORTS

    DisplayString,PhysAddress 	FROM RFC1213-MIB 
    netscreenIp  FROM NETSCREEN-SMI;

    
    nsIpArp OBJECT IDENTIFIER ::= { netscreenIp 1}

	nsIpArpAOD OBJECT-TYPE
		SYNTAX INTEGER {
			disable(0),
			enabled(1)
		}
		ACCESS not-accessible
		STATUS mandatory
		DESCRIPTION 
			"ARP always on destination."
		::= {nsIpArp 1}
	
	nsIpArpCachUpdate OBJECT-TYPE
		SYNTAX INTEGER {
			disable(0),
			enabled(1)
		}
		ACCESS not-accessible
		STATUS mandatory
		DESCRIPTION 
			"ARP cache update."
	    ::= { nsIpArp 2}
	    
	nsIpArpTable OBJECT-TYPE
		SYNTAX  SEQUENCE OF NsIpArpEntry
		ACCESS  not-accessible
		STATUS  mandatory
		DESCRIPTION 
		        "This table collects all the ARP entries existing in NetScreen device."
		::= { nsIpArp 3 }

    nsIpArpEntry OBJECT-TYPE
        SYNTAX  NsIpArpEntry
        ACCESS  not-accessible
        STATUS  mandatory
        DESCRIPTION
               "An entry containing attributes of arp info"
        INDEX   { nsIpArpIndex }
        ::= { nsIpArpTable 1 }

	NsIpArpEntry ::=
		SEQUENCE {
          nsIpArpIndex
              INTEGER,
		  nsIpArpIp
		      IpAddress,
		  nsIpArpMac
		      PhysAddress,
		  nsIpArpVsys
		      INTEGER,
		  nsIpArpIfIdx
		      INTEGER,
		  nsIpArpState
		  	  INTEGER,
		  nsIpArpAge
		  	  INTEGER,
		  nsIpArpRetry
		  	  INTEGER,
		  nsIpArpPakQue
		  	  INTEGER 	  
       }

	nsIpArpIndex OBJECT-TYPE
    	SYNTAX  INTEGER
        ACCESS  read-only
        STATUS  mandatory
        DESCRIPTION
             "A unique value for arp table.  Its value
              ranges between 0 and 65535 and may not be contiguous." 
        ::= { nsIpArpEntry 1 }

	nsIpArpIp OBJECT-TYPE
        SYNTAX  IpAddress
    	ACCESS  read-only
        STATUS  mandatory
        DESCRIPTION
             "IP address."
        ::= { nsIpArpEntry 2 }

	nsIpArpMac OBJECT-TYPE
        SYNTAX  PhysAddress
    	ACCESS  read-only
        STATUS  mandatory
        DESCRIPTION
             "MAC address."
        ::= { nsIpArpEntry 3 }

	nsIpArpVsys OBJECT-TYPE
        SYNTAX  INTEGER
    	ACCESS  read-only
        STATUS  mandatory
        DESCRIPTION
             "Virtual system id this entry belongs to."
        ::= { nsIpArpEntry 4 }

	nsIpArpIfIdx OBJECT-TYPE
        SYNTAX  INTEGER
    	ACCESS  read-only
        STATUS  mandatory
        DESCRIPTION
             "Interface location."
        ::= { nsIpArpEntry 5 }

	nsIpArpState OBJECT-TYPE
        SYNTAX  INTEGER {
            pending(1),
            valid(2),
            delete(3),
            static(4)
        }
    	ACCESS  read-only
        STATUS  mandatory
        DESCRIPTION
             "ARP entry state."
        ::= { nsIpArpEntry 6 }

	nsIpArpAge OBJECT-TYPE
        SYNTAX  INTEGER
    	ACCESS  read-only
        STATUS  mandatory
        DESCRIPTION
             "ARP entry age."
        ::= { nsIpArpEntry 7 }

	nsIpArpRetry OBJECT-TYPE
        SYNTAX  INTEGER
    	ACCESS  read-only
        STATUS  mandatory
        DESCRIPTION
             "ARP entry retry time."
        ::= { nsIpArpEntry 8 }

	nsIpArpPakQue OBJECT-TYPE
        SYNTAX  INTEGER
    	ACCESS  read-only
        STATUS  mandatory
        DESCRIPTION
             "ARP entry package queue."
        ::= { nsIpArpEntry 9 }
END
