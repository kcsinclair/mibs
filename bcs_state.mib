BCS-STATE-MIB DEFINITIONS ::= BEGIN

IMPORTS
    
        OBJECT-TYPE, MODULE-IDENTITY     
                FROM SNMPv2-SMI
        bcs
                FROM BCS-IDENT-MIB;

bcsState      MODULE-IDENTITY
        LAST-UPDATED "200702140000Z"

        ORGANIZATION "Motorola Connected Home Solutions"
        CONTACT-INFO "Motorola Technical Response Center
                      Inside USA     1-888-944-HELP (1-888-944-4357)
                      Outside USA    1-215-323-0044
                      TRC Hours:
                      Monday through Friday 8am - 7pm Eastern Standard Time
                      Saturdays            10am - 5pm Eastern Standard Time"

        DESCRIPTION  "The MIB module for the BCS common state objects.
		      The MIB Tree for is shown below."

         ::= {bcs 2}

                

--  MIB Tree
--
--  The following diagram defining the objects in this MIB is for
--  reference purposes only.
--
--    bcs
--        |
--        +..bcsIdent
--        |
--        .
--        .
--        .
--        |
--        |         
--        +..bcsState
--        |    |
--        |    +..unitAdministrativeState
--        |    |
--        |    +..unitOperationalState
--        |    |
--        |    +..unitUsageState
--        |    |
--        |    +..unitProceduralStatus
--        |    |
--        |    +..unitAlarmStatus
--        |    |
--        |    +..unitAvailabilityStatus
--        |    |
--        |    +..unitControlStatus
--        |    |
--        |    +..unitStandbyStatus
--        |    |
--        |    +..unitUnknownStatus
--        |    |
--        |    +..unitTestStatus
--        |
--        +..bcsTraps
--        |
--        |

-- The State/Status Group.
--
--   State/status refers to the state/status of the computing/network
--   element on which the SNMP agent is running. If the agent is a
--   proxy agent, the state group does not relate to the state/status
--   of the elements being proxied. The state/status group also does
--   not directly relate to the state/status of the components of the
--   network element such as CCAs.
--
--   The state/status uf individual unit components, CCAs, etc. and
--   the state/status of proxied elements should be defined using
--   subsets of the variables/values defined here.
--
--   The state group is mandatory for all SNMP managed GI network
--   elements although different agents may shoose to support
--   only a subset of the group as best suited for the application.
--   If a state variable is not supported by an agent, the agent
--   will return the error code noSuchName. However, the 
--   state group should be the only group defining the state/status
--   of the entire network element being managed. GI defined MIB should
--   avoid using any other variables to define the state of the entire 
--   network element.
-- 
--   Defined state/status variables and values and state transitions
--   correspond to the ITU-T X.700 series standards and are
--   defined in ISO/IEC 10164-2. The defined include:
--
--       - the administrative state
--       - the operational state
--       - the usage state
--       - the procedural status
--       - the alarm status
--       - the availability status
--       - the control status
--       - the standy status
--       - the unknown status

unitAdministrativeState  OBJECT-TYPE
                SYNTAX  INTEGER 
                        {
                         locked         (1),
                         unlocked       (2),
                         shuttingDown   (3)
                        }
                MAX-ACCESS  read-write
                STATUS  current
                DESCRIPTION "This state should be always supported.
                     The current Adminsitrative state of the unit is defined
		     in ISO/IEC 10164-2."
                REFERENCE   " -- "
        ::= { bcsState 1 }

unitOperationalState  OBJECT-TYPE
                SYNTAX  INTEGER 
                        {
                          enabled    (1),
                          disabled   (2)
                        }
                MAX-ACCESS  read-only
                STATUS  current
                DESCRIPTION "The current Operational state of the unit as
		     defined in ISO/IEC 10164-2"
                REFERENCE   " -- "
        ::= { bcsState 2 }
        
unitUsageState  OBJECT-TYPE
                SYNTAX  INTEGER 
                        {
                         idle     (1),
                         active   (2),
                         busy     (3)
                        }
                MAX-ACCESS  read-only
                STATUS  current
                DESCRIPTION "The current Usage state of the unit as defined in
                     ISO/IEC 10164-2"
                REFERENCE   " -- " 
        ::= { bcsState 3 }
    
unitProceduralStatus  OBJECT-TYPE
                SYNTAX  INTEGER 
                        {
                         initializationRequired   (1),
                         notInitialized           (2),
                         initializing             (3),
                         reporting                (4),
                         terminating              (5),
                         ready                    (6)
                        }
                MAX-ACCESS  read-write
                STATUS  current
                DESCRIPTION "This state should be always supported.
                     This object controls the Procedural status 
                     as defined in ISO/IEC 10164-2 and state-machine"
                REFERENCE   " -- " 
        ::= { bcsState 4 }        

unitAlarmStatus  OBJECT-TYPE
                SYNTAX  INTEGER 
                        {
                         ok                 (1),
                         undetermined       (2),
                         warning            (3),
                         minor              (4),
                         major              (5),
                         critical           (6)
                        }
                MAX-ACCESS  read-write
                STATUS  current
                DESCRIPTION "This state should be always supported.
                     This object defines the Alarm status described
                     by ISO/IEC 10164-2 and state-machine; however,
                     the actual values used are based on perceived 
                     severity values defined by ISO/IEC 10164-4."
                REFERENCE   " -- "
        ::= { bcsState 5 }        

unitAvailabilityStatus  OBJECT-TYPE
                SYNTAX  INTEGER 
                        {
                         inTest         (1),
                         failed         (2),
                         powerOff       (3),
                         offLine        (4),
                         offDuty        (5),
                         dependency     (6),
                         degraded       (7),
                         notInstalled   (8),
                         logFull        (9),
                         available      (10)
                        }
                MAX-ACCESS  read-only
                STATUS  current
                DESCRIPTION "This object controls the Availability status
                     as defined in ISO/IEC 10164-2 and state-machine"
                REFERENCE   " -- "
        ::= { bcsState 6 }        

unitControlStatus  OBJECT-TYPE
                SYNTAX  INTEGER
                        {
                         subjectToTest    (32767),
                         partLocked       (1),
                         reservedToTest   (2),
                         suspended        (3),
                         free             (4)
                        }
                MAX-ACCESS  read-write
                STATUS  current
                DESCRIPTION "This object controls the Control status
                     as defined in ISO/IEC 10164-2 and state-machine"
                REFERENCE   " -- "
        ::= { bcsState 7 }        

unitStandbyStatus  OBJECT-TYPE
                SYNTAX  INTEGER 
                        {
                         hotStandby         (1),
                         coldStandby        (2),
                         providingService   (3)
                        }
                MAX-ACCESS  read-only
                STATUS  current
                DESCRIPTION "This object controls the Standby status
                     as defined in ISO/IEC 10164-2 and state-machine"
                REFERENCE   " -- " 
        ::= { bcsState 8 }        

unitUnknownStatus  OBJECT-TYPE
                SYNTAX  INTEGER 
                        {
                         true(1),
                         false(2)
                        }
                MAX-ACCESS  read-write
                STATUS  current
                DESCRIPTION "This object defines the unknown status
                     as defined in ISO/IEC 10164-2 and state-machine"
                REFERENCE   " -- "
        ::= { bcsState 9 }        

END
