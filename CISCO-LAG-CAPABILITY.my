-- *****************************************************************
-- CISCO-LAG-CAPABILITY.my:
-- Cisco CISCO-LAG-MIB AGENT-CAPABILITIES
--   
-- September 2003, Edward Pham
-- February 2004, Edward Pham
--   
-- Copyright (c) 2003, 2004, 2006, 2007, 2009-2011 by Cisco Systems Inc.
-- All rights reserved.
-- *****************************************************************

CISCO-LAG-CAPABILITY DEFINITIONS ::= BEGIN

IMPORTS
    MODULE-IDENTITY,
    Unsigned32
        FROM SNMPv2-SMI
    AGENT-CAPABILITIES
        FROM SNMPv2-CONF
    ciscoAgentCapability
        FROM CISCO-SMI;


ciscoLagCapability MODULE-IDENTITY
    LAST-UPDATED    "201109270000Z"
    ORGANIZATION    "Cisco Systems, Inc."
    CONTACT-INFO
            "Cisco Systems
            Customer Service

            Postal: 170 West Tasman Drive
            San Jose, CA  95134
            USA

            Tel: +1 800 553-NETS

            E-mail: cs-lan-switch-snmp@cisco.com,
            cs-etherchan@cisco.com"
    DESCRIPTION
        "The capabilities description of CISCO-LAG-MIB."
    REVISION        "201109270000Z"
    DESCRIPTION
        "Added capability statement clagCapV15R0001SYPCat6k.

        Added VARIATION for clagAggDistributionProtocol object
        in clagCapCatOSV08R0101 agent capabilty statement ."
    REVISION        "201011010000Z"
    DESCRIPTION
        "Added capability statement clagCapV12R0250SYPCat6K."
    REVISION        "200911190000Z"
    DESCRIPTION
        "Added capability statement clagCapV12R0252SGPCat4K."
    REVISION        "200707101000Z"
    DESCRIPTION
        "Added capability statement clagCapV12R0233SXHPCat6K."
    REVISION        "200606151200Z"
    DESCRIPTION
        "Added capability statements
        clagCapV12R0218SXF5PCat6KPfc2 and
        clagCapV12R0218SXF5PCat6KPfc3."
    REVISION        "200402040000Z"
    DESCRIPTION
        "Initial version of this MIB module."
    ::= { ciscoAgentCapability 332 }


clagCapV12R0111bEXCat6K AGENT-CAPABILITIES
    PRODUCT-RELEASE "Cisco IOS 12.1(11b)EX on Catalyst 6000/6500
                    and Cisco 7600 series devices."
    STATUS          current
    DESCRIPTION
        "CISCO-LAG-MIB capabilities."

    SUPPORTS        CISCO-LAG-MIB
    INCLUDES        {
                        clagAggProtocolGroup,
                        clagAggPortGroup,
                        clagAggDistributionGroup
                    }
    VARIATION       clagAggDistributionProtocol
    SYNTAX          INTEGER  {
                        ip(1),
                        mac(2),
                        port(3)
                    }
    DESCRIPTION
        "Only support ip(1), mac(2), port(3)."

    ::= { ciscoLagCapability 1 }

clagCapV12R0217SXCat6KPfc2 AGENT-CAPABILITIES
    PRODUCT-RELEASE "Cisco IOS 12.2(17)SX on Catalyst 6000/6500
                    and Cisco 7600 series devices with PFC2 card."
    STATUS          current
    DESCRIPTION
        "CISCO-LAG-MIB capabilities."

    SUPPORTS        CISCO-LAG-MIB
    INCLUDES        {
                        clagAggProtocolGroup,
                        clagAggPortGroup,
                        clagAggDistributionGroup
                    }
    VARIATION       clagAggDistributionProtocol
    SYNTAX          INTEGER  {
                        ip(1),
                        mac(2),
                        port(3)
                    }
    DESCRIPTION
        "Only a limited set of enumerated values is supported."

    ::= { ciscoLagCapability 2 }

clagCapV12R0217SXCat6KPfc3 AGENT-CAPABILITIES
    PRODUCT-RELEASE "Cisco IOS 12.2(17)SX on Catalyst 6000/6500
                    and Cisco 7600 series devices with PFC3 card."
    STATUS          current
    DESCRIPTION
        "CISCO-LAG-MIB capabilities."

    SUPPORTS        CISCO-LAG-MIB
    INCLUDES        {
                        clagAggProtocolGroup,
                        clagAggPortGroup,
                        clagAggDistributionGroup,
                        clagAggDistributionMplsGroup
                    }
    VARIATION       clagAggDistributionProtocol
    SYNTAX          INTEGER  {
                        ip(1),
                        mac(2),
                        port(3)
                    }
    DESCRIPTION
        "Only a limited set of enumerated values is supported."

    ::= { ciscoLagCapability 3 }

clagCapCatOSV08R0101 AGENT-CAPABILITIES
    PRODUCT-RELEASE "Cisco CatOS 8.1(1)."
    STATUS          current
    DESCRIPTION
        "CISCO-LAG-MIB capabilities."

    SUPPORTS        CISCO-LAG-MIB
    INCLUDES        {
                        clagAggProtocolGroup,
                        clagAggPortGroup,
                        clagAggDistributionGroup
                    }
    VARIATION       clagAggDistributionProtocol
    SYNTAX          INTEGER  {
                        ip(1),
                        mac(2),
                        port(3),
                        vlanIpPort(4)
                    }
    DESCRIPTION     "The enumerated values supported are all those
                    defined at the time this clause was written."

    ::= { ciscoLagCapability 4 }

clagCapV12R0218SXF5PCat6KPfc2 AGENT-CAPABILITIES
    PRODUCT-RELEASE "Cisco IOS 12.2(18)SXF5 on Catalyst 6000/6500
                    and Cisco 7600 series devices with PFC2 card."
    STATUS          current
    DESCRIPTION
        "CISCO-LAG-MIB capabilities."

    SUPPORTS        CISCO-LAG-MIB
    INCLUDES        {
                        clagAggProtocolGroup,
                        clagAggPortGroup,
                        clagAggDistributionGroup,
                        clagAggMaxAggregatorsGroup
                    }
    VARIATION       clagAggDistributionProtocol
    SYNTAX          INTEGER  {
                        ip(1),
                        mac(2),
                        port(3)
                    }
    DESCRIPTION
        "Only a limited set of enumerated values is supported."

    ::= { ciscoLagCapability 5 }

clagCapV12R0218SXF5PCat6KPfc3 AGENT-CAPABILITIES
    PRODUCT-RELEASE "Cisco IOS 12.2(18)SXF5 on Catalyst 6000/6500
                    and Cisco 7600 series devices with PFC3 card."
    STATUS          current
    DESCRIPTION
        "CISCO-LAG-MIB capabilities."

    SUPPORTS        CISCO-LAG-MIB
    INCLUDES        {
                        clagAggProtocolGroup,
                        clagAggPortGroup,
                        clagAggDistributionGroup,
                        clagAggDistributionMplsGroup,
                        clagAggMaxAggregatorsGroup
                    }
    VARIATION       clagAggDistributionProtocol
    SYNTAX          INTEGER  {
                        ip(1),
                        mac(2),
                        port(3)
                    }
    DESCRIPTION
        "Only a limited set of enumerated values is supported."

    ::= { ciscoLagCapability 6 }

clagCapV12R0233SXHPCat6K AGENT-CAPABILITIES
    PRODUCT-RELEASE "Cisco IOS 12.2(33)SXH on Catalyst 6000/6500
                    devices."
    STATUS          current
    DESCRIPTION
        "CISCO-LAG-MIB capabilities."

    SUPPORTS        CISCO-LAG-MIB
    INCLUDES        {
                        clagAggProtocolGroup,
                        clagAggPortGroup,
                        clagAggDistributionGroup,
                        clagAggDistributionMplsGroup,
                        clagAggMaxAggregatorsGroup,
                        clagAggPortListGroup
                    }
    VARIATION       clagAggDistributionProtocol
    SYNTAX          INTEGER  {
                        ip(1),
                        mac(2),
                        port(3)
                    }
    DESCRIPTION
        "Only a limited set of enumerated values is supported."

    ::= { ciscoLagCapability 7 }

clagCapV12R0252SGPCat4K AGENT-CAPABILITIES
    PRODUCT-RELEASE "Cisco IOS 12.2(52)SG on Cat4K family devices."
    STATUS          current
    DESCRIPTION
        "CISCO-LAG-MIB capabilities."

    SUPPORTS        CISCO-LAG-MIB
    INCLUDES        {
                        clagAggProtocolGroup,
                        clagAggPortGroup,
                        clagAggDistributionGroup
                    }
    VARIATION       clagAggDistributionProtocol
    SYNTAX          INTEGER  {
                        ip(1),
                        mac(2),
                        port(3)
                    }
    DESCRIPTION
        "Only a limited set of enumerated values is supported."

    ::= { ciscoLagCapability 8 }

clagCapV12R0250SYPCat6K AGENT-CAPABILITIES
    PRODUCT-RELEASE "Cisco IOS 12.2(50)SY on Catalyst 6000/6500
                         devices."
    STATUS          current
    DESCRIPTION
        "CISCO-LAG-MIB capabilities."

    SUPPORTS        CISCO-LAG-MIB
    INCLUDES        {
                        clagAggProtocolGroup,
                        clagAggPortGroup,
                        clagAggDistributionGroup,
                        clagAggDistributionMplsGroup,
                        clagAggMaxAggregatorsGroup,
                        clagAggPortListGroup,
                        clagAggRateGroup,
                        clagAggChannelIfLacpGroup,
                        clagAggChannelIfMinLinkGroup,
                        clagAggChannelIfHashDistMethodGroup,
                        clagAggHashDistGlobalGroup
                    }
    VARIATION       clagAggDistributionProtocol
    SYNTAX          INTEGER  {
                        ip(1),
                        mac(2),
                        port(3)
                    }
    DESCRIPTION
        "Only a limited set of enumerated values is supported."

    VARIATION       clagAggChannelIfMaxBundle
    SYNTAX          Unsigned32 (1..8)
    DESCRIPTION
        "Only a limited set of values is supported."

    VARIATION       clagAggChannelIfMinLink
    SYNTAX          Unsigned32 (0 | 2..8)
    DESCRIPTION
        "Only a limited set of values is supported."

    ::= { ciscoLagCapability 9 }

clagCapV15R0001SYPCat6k AGENT-CAPABILITIES
    PRODUCT-RELEASE "Cisco IOS 15.0(1)SY on Catalyst 6000/6500
                    series devices."
    STATUS          current
    DESCRIPTION
        "CISCO-LAG-MIB capabilities."

    SUPPORTS        CISCO-LAG-MIB
    INCLUDES        {
                        clagAggProtocolGroup,
                        clagAggPortGroup,
                        clagAggDistributionGroup,
                        clagAggDistributionMplsGroup,
                        clagAggMaxAggregatorsGroup,
                        clagAggPortListGroup,
                        clagAggRateGroup,
                        clagAggChannelIfLacpGroup,
                        clagAggChannelIfMinLinkGroup,
                        clagAggChannelIfHashDistMethodGroup,
                        clagAggHashDistGlobalGroup
                    }
    VARIATION       clagAggChannelIfMaxBundle
    SYNTAX          Unsigned32 (1..8)
    DESCRIPTION
        "Only a limited set of values is supported."

    VARIATION       clagAggChannelIfMinLink
    SYNTAX          Unsigned32 (0 | 2..8)
    DESCRIPTION
        "Only a limited set of values is supported."

    VARIATION       clagAggDistributionProtocol
    SYNTAX          INTEGER  {
                        ip(1),
                        mac(2),
                        port(3),
                        vlanIpPort(4),
                        vlanIp(5),
                        ipPort(6)
                    }
    DESCRIPTION     "The enumerated values supported are all those
                    defined at the time this clause was written."

    ::= { ciscoLagCapability 10 }

END
