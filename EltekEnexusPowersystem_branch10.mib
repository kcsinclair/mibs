SP2-MIB DEFINITIONS ::= BEGIN

IMPORTS
	NOTIFICATION-TYPE, OBJECT-TYPE, MODULE-IDENTITY, 
	enterprises, Counter32, Integer32
		FROM SNMPv2-SMI
	NOTIFICATION-GROUP
		FROM SNMPv2-CONF
	DateAndTime, DisplayString
		FROM SNMPv2-TC
	eltek
		FROM ELTEK-COMMON-MIB;
		
-- Supported by SmartPack2 and Compack products
-- SNMP V1,V2c and V3

eNexus               OBJECT IDENTIFIER ::= { eltek 10 }

-- This branch contains all tables and oid's needed for Eltek's trap system

eltekTraps           OBJECT IDENTIFIER ::= { eNexus 1 }

-- These are variable bindings used by the traps defined in  powerSystemTraps branch. 

powerAlarmVars       OBJECT IDENTIFIER ::= { eltekTraps 1 }

-- The generic Subsystem Traps, a generic trap for each sub system.
-- There are many alarm sources for each subsystem.
-- 
--  A list of the power plant subsystems:
-- 
--  1. Battery
--  2. Load
--  3. Mains
--  4. Rectifiers
--  5. ControlSystem
--  6. DcDc
--  7. Inputs
--  8. Generator
--  9. solarCharger
--  10. windcharger
-- 
-- Each trap contains subsystem status, text description of the alarm source, 
-- alarm status var, subsystem Status OID, subsystem Status Value, 
-- OID of the variable indicated the Measured value and the Measured value itself.

powerSystemTraps     OBJECT IDENTIFIER ::= { eltekTraps 2 }

-- This branch contains OID's for configuration of the power system's
-- basic factory data and the power system's installation settings.
-- 
-- 

powerSystem          OBJECT IDENTIFIER ::= { eNexus 2 }

-- This branch contains OIDs related to the Mains/AC feed subsystem. 
-- Here you will find info about mains status, voltages, currents, fuses, and mains monitor units

mains                OBJECT IDENTIFIER ::= { eNexus 3 }

-- This is the monitor of number of failed phase(s), which is(are) in major or minor low alarm.

mainsMainsFailure    OBJECT IDENTIFIER ::= { mains 2 }

-- This branch contains information about AC Mains Monitor control unit.

mainsMonitors        OBJECT IDENTIFIER ::= { mains 5 }

-- This branch contains mains outage log.

mainsOutageLog       OBJECT IDENTIFIER ::= { mains 6 }

-- This branch contains OIDs related to the systems (Diesel)Generator subsystem. 
-- Here you will find info about the generator running status, start/stop criteria, fuel tank monitoring, 
-- and energy delivery history. 
-- 

generator            OBJECT IDENTIFIER ::= { eNexus 4 }

-- This branch contains information about generator energy logs.

generatorEnergyLog   OBJECT IDENTIFIER ::= { generator 23 }

-- This branch contains information about generator running hours.

generatorRunHoursLog  OBJECT IDENTIFIER ::= { generator 24 }

-- This branch contains information about generator fuel consumption.

generatorFuelConsumptionLog  OBJECT IDENTIFIER ::= { generator 25 }

-- This branch contains OIDs related to the Rectifiers subsystem. 
-- Here you will find info about the rectifiers status, capacity and health, currents and 
-- energy consumption history
-- 

rectifiers           OBJECT IDENTIFIER ::= { eNexus 5 }

-- This branch contains information about the total rectifier current, which is calculated 
-- by summing up current from each rectifier.

rectifiersCurrent    OBJECT IDENTIFIER ::= { rectifiers 2 }

-- This branch contains information about the used rectifier capacity.

rectifiersCapacity   OBJECT IDENTIFIER ::= { rectifiers 3 }

-- This branch contains information about the rectifier error monitor.

rectifiersError      OBJECT IDENTIFIER ::= { rectifiers 4 }

-- This branch contains information about rectifiers' energy logs.

rectifiersEnergyLog  OBJECT IDENTIFIER ::= { rectifiers 7 }

-- This branch contains OIDs related to the DCDC converter subsystem. 
-- Here you will find info about the dcdc status, capacity and health, currents and 
-- converted-energy history

dcdc                 OBJECT IDENTIFIER ::= { eNexus 6 }

-- This branch contains information about dcdc converters' energy logs.

dcdcEnergyLog        OBJECT IDENTIFIER ::= { dcdc 7 }

-- This branch contains OIDs related to the Solar charger subsystem. 
-- Here you will find info about the Solar charger status, capacity and health, currents and 
-- energy delivery history
-- 

solarChargers        OBJECT IDENTIFIER ::= { eNexus 7 }

-- This branch contains information about the total solar current.

solarChargersCurrent  OBJECT IDENTIFIER ::= { solarChargers 2 }

-- This branch contains information about the used solar charger capacity.

solarChargersCapacity  OBJECT IDENTIFIER ::= { solarChargers 3 }

-- This branch contains information about the solar error monitor.

solarChargersError   OBJECT IDENTIFIER ::= { solarChargers 4 }

-- This branch contains information about solar chargers' energy logs.

solarChargersEnergyLog  OBJECT IDENTIFIER ::= { solarChargers 7 }

-- This branch contains OIDs related to the Wind charger subsystem. 
-- Here you will find info about the Wind charger status, capacity and health, currents and 
-- energy delivery history

windChargers         OBJECT IDENTIFIER ::= { eNexus 8 }

-- This branch contains information about the total wind current.

windChargersCurrent  OBJECT IDENTIFIER ::= { windChargers 2 }

-- This branch contains information about the used wind charger capacity.

windChargersCapacity  OBJECT IDENTIFIER ::= { windChargers 3 }

-- This branch contains information about the wind error monitor.

windChargersError    OBJECT IDENTIFIER ::= { windChargers 4 }

-- This branch contains information about wind chargers' energy logs.

windChargersEnergyLog  OBJECT IDENTIFIER ::= { windChargers 7 }

-- This branch contains OIDs related to the Load subsystem. 
-- Here you will find info about load status, currents, fuses,  contactors
-- and load monitor units
-- 

load                 OBJECT IDENTIFIER ::= { eNexus 9 }

-- This is the monitor of total load current

loadCurrent          OBJECT IDENTIFIER ::= { load 2 }

-- This branch contains information about load energy logs.

loadEnergyLog        OBJECT IDENTIFIER ::= { load 8 }

-- This branch contains all avalable information about the power systems battery subsystem.
-- Here is data about battery health, condition, test results, monitoring equipment battery banks/strings, 
-- battery breakers and disconnection systems.

battery              OBJECT IDENTIFIER ::= { eNexus 10 }

-- This is one of many 'data monitors' found throughout the power system.  
-- The 'data monitors' is found on several levels on all subsystems and they all act as 
-- trap sources. Whenever a status changes in a 'data monitor', a trap in its parent
-- subsystem may be sendt.  The data monitor branches can easily be recognised by the 
-- presence of a xxxxTrapRepeatCounter node.

batteryVoltage       OBJECT IDENTIFIER ::= { battery 5 }

-- This is the total battery current.

batteryCurrents      OBJECT IDENTIFIER ::= { battery 6 }

-- Show The highest value of the enabled battery temperature measurements

batteryTemperatures  OBJECT IDENTIFIER ::= { battery 7 }

-- This is the estimated battery remaining discharge time until battery disconnection.

batteryTimeLeft      OBJECT IDENTIFIER ::= { battery 8 }

-- This is the remaining capacity before battery disconnection.

batteryRemainingCapacity  OBJECT IDENTIFIER ::= { battery 9 }

-- This is the used battery capacity

batteryUsedCapacity  OBJECT IDENTIFIER ::= { battery 10 }

-- This is the total battery capacity estimated from the latest battery test result.

batteryTotalCapacity  OBJECT IDENTIFIER ::= { battery 11 }

-- The battery quality is calculated from the latest battery test.

batteryQuality       OBJECT IDENTIFIER ::= { battery 12 }

-- This branch contains OIDs related to the Battery Disconnect. 

batteryLVBD          OBJECT IDENTIFIER ::= { battery 13 }

-- This branch contains information about battery charge current limit.

batteryChargeCurrentLimit  OBJECT IDENTIFIER ::= { battery 14 }

-- This branch contains information about battery boost

batteryBoost         OBJECT IDENTIFIER ::= { battery 15 }

-- This branch contains information about battery test

batteryTest          OBJECT IDENTIFIER ::= { battery 16 }
batteryTempComp      OBJECT IDENTIFIER ::= { battery 17 }

-- This brance contains information about battery banks

batteryBank          OBJECT IDENTIFIER ::= { battery 18 }

-- This branch contains information about battery monitor control unit.

batteryMonitors      OBJECT IDENTIFIER ::= { battery 19 }

-- This branch contains information about battery energy logs.

batteryEnergyLog     OBJECT IDENTIFIER ::= { battery 20 }

-- This branch contains information about battery discharge cycle logs.

batteryCycleLog      OBJECT IDENTIFIER ::= { battery 21 }

-- This branch is a container for the status of programmable inputs for
-- control units and I/O units.  The two dimensional tables are double indexed.
-- Input number index and control unit index.

inputs               OBJECT IDENTIFIER ::= { eNexus 11 }

-- This branch contains OIDs related to the systems Alarm output relays status. 
-- 

outputs              OBJECT IDENTIFIER ::= { eNexus 12 }

-- This branch contains OIDs related to the Controlsystem subsystem. 
-- Here you will find info about controller status and inventory. I/O units 
-- with outdoor related functionality is placed here. Current Monitors with 
-- programmable system types and functionalities.There is also some pushbuttons for 
-- resetting alarms and reread system inventory. 

controlSystem        OBJECT IDENTIFIER ::= { eNexus 13 }

-- SNMP trap configurations

snmp                 OBJECT IDENTIFIER ::= { controlSystem 4 }

-- This branch contains information about IO unit.

controlSystemIoUnits  OBJECT IDENTIFIER ::= { controlSystem 7 }

-- This branch contains control system inventory, including control unit description, status, serial 
-- number, hardware part number, hardware version, software part number and software version.

controlSystemInventory  OBJECT IDENTIFIER ::= { controlSystem 8 }

-- This branch contains information about current monitor.

currentMonitors      OBJECT IDENTIFIER ::= { controlSystem 9 }

-- This branch contains OIDs related to the systems alarm groups. The alarm groups are internal entities 
-- that serves as input sources for the Alarm outputs

alarmGroups          OBJECT IDENTIFIER ::= { eNexus 14 }

alarmSubsysSourceDescr  OBJECT-TYPE
	SYNTAX     DisplayString (SIZE(0..32))
	MAX-ACCESS accessible-for-notify
	STATUS     current
	DESCRIPTION 
		"A description of the source generating the trap for the Alarm Condition. 
		Used in alarmSubSystemTrap to describe the alarm source. 
		Example: 'batteryVoltageDescription'"
	::= { powerAlarmVars 1 }

-- status var and value of trap variables
-- 

alarmSubsysStatusOid  OBJECT-TYPE
	SYNTAX     OBJECT IDENTIFIER
	MAX-ACCESS accessible-for-notify
	STATUS     current
	DESCRIPTION 
		"The OID (name) of the object indicating the alarm-status for which the alarm is 
		generated.  The Status must be an INTEGER  type.
		
		Example: SP2-MIB::batteryVoltage.batteryVoltageStatus
		1.3.6.1.4.1.12148.10.3.5.2:
		
		This object maybe polled by the SNMP management application,
		to monitor the current Status object."
	::= { powerAlarmVars 2 }

alarmSubsysStatusValue  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS accessible-for-notify
	STATUS     current
	DESCRIPTION 
		"The value of the Status object of the subsystem for which the
		alarm-status is generated. The OID (name) of this object is
		indicated by alarmSubsysStatusOid above.
		
		
		Example: the value of SP2-MIB::batteryVoltage.batteryVoltageStatus
		one of: error (0), normal (1), minorAlarm (2), etc."
	::= { powerAlarmVars 3 }

alarmSubsysStatusOnOff  OBJECT-TYPE
	SYNTAX     INTEGER {
		off (0),
		on (1)
	}
	MAX-ACCESS accessible-for-notify
	STATUS     current
	DESCRIPTION 
		"This indicates if the abnormal condition is on or goes off."
	::= { powerAlarmVars 4 }

-- measured var and value of trap variables
-- 

alarmMeasuredVarOid  OBJECT-TYPE
	SYNTAX     OBJECT IDENTIFIER
	MAX-ACCESS accessible-for-notify
	STATUS     current
	DESCRIPTION 
		"The OID (name) of the measured-object indicating some
		measurement (e.g voltage) for which the alarm is generated.
		
		Example: SP2-MIB::batteryVoltage.batteryVoltageValue
		1.3.6.1.4.1.12148.10.3.5.1
		
		This object maybe polled by the SNMP management application,
		to monitor the current measurement."
	::= { powerAlarmVars 5 }

alarmMeasuredVarValue  OBJECT-TYPE
	SYNTAX     Integer32
	MAX-ACCESS accessible-for-notify
	STATUS     current
	DESCRIPTION 
		"The value of the measured-object for which the alarm-status
		is generated, for example 13 volt. The actual value is in
		units defined by the actual variable (e.g volts). The units
		must use INTEGER type.
		
		The OID (name) of this object is indicated by
		alarmMeasuredVarOid above.
		
		Example: Value of SP2-MIB::batteryVoltage.batteryVoltageValue
		'The measured battery voltage'"
	::= { powerAlarmVars 6 }

alarmTrapCounterVarValue  OBJECT-TYPE
	SYNTAX     Integer32
	MAX-ACCESS accessible-for-notify
	STATUS     current
	DESCRIPTION 
		""
	::= { powerAlarmVars 7 }

-- 

alarmPowerSystemTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the power system."
	::= { powerSystemTraps 1 }

-- alarm subsystem-name (Battery, Load, etc.)
-- text description of the alarm source
-- alarm status var
-- subsystem Status OID
-- subsystem Status Value
-- measured var
-- OID of the variable indicated the Measured value
-- Measured value

alarmBatteryTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the battery subsystem."
	::= { powerSystemTraps 2 }

-- alarm subsystem-name (Battery, Load, etc.)
-- text description of the alarm source
-- alarm status var
-- subsystem Status OID
-- subsystem Status Value
-- measured var
-- OID of the variable indicated the Measured value
-- Measured value

alarmLoadGroupTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the Load subsystem."
	::= { powerSystemTraps 3 }

-- alarm subsystem-name (Battery, Load, etc.)
-- text description of the alarm source
-- alarm status var
-- subsystem Status OID
-- subsystem Status Value
-- measured var
-- OID of the variable indicated the Measured value
-- Measured value

alarmMainsTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the Mains subsystem."
	::= { powerSystemTraps 4 }

-- alarm subsystem-name (Battery, Load, etc.)
-- text description of the alarm source
-- alarm status var
-- subsystem Status OID
-- subsystem Status Value
-- measured var
-- OID of the variable indicated the Measured value
-- Measured value

alarmRectifierTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the Rectifier subsystem."
	::= { powerSystemTraps 5 }

-- alarm subsystem-name (Battery, Load, etc.)
-- text description of the alarm source
-- alarm status var
-- subsystem Status OID
-- subsystem Status Value
-- measured var
-- OID of the variable indicated the Measured value
-- Measured value

alarmControlSystemTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the Control-system subsystem."
	::= { powerSystemTraps 6 }

-- alarm subsystem-name (Battery, Load, etc.)
-- text description of the alarm source
-- alarm status var
-- subsystem Status OID
-- subsystem Status Value
-- measured var
-- OID of the variable indicated the Measured value
-- Measured value

alarmDcDcTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the DCDC converter subsystem."
	::= { powerSystemTraps 7 }

-- alarm subsystem-name (Battery, Load, etc.)
-- text description of the alarm source
-- alarm status var
-- subsystem Status OID
-- subsystem Status Value
-- measured var
-- OID of the variable indicated the Measured value
-- Measured value

alarmInputsTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the Inputs subsystem."
	::= { powerSystemTraps 8 }

-- alarm subsystem-name (Battery, Load, etc.)
-- text description of the alarm source
-- alarm status var
-- subsystem Status OID
-- subsystem Status Value
-- measured var
-- OID of the variable indicated the Measured value
-- Measured value

alarmOutputsTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the Outputs subsystem."
	::= { powerSystemTraps 9 }

-- alarm subsystem-name (Battery, Load, etc.)
-- text description of the alarm source
-- alarm status var
-- subsystem Status OID
-- subsystem Status Value
-- measured var
-- OID of the variable indicated the Measured value
-- Measured value

alarmGeneratorTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the Generator subsystem."
	::= { powerSystemTraps 10 }

-- alarm subsystem-name (Battery, Load, etc.)
-- text description of the alarm source
-- alarm status var
-- subsystem Status OID
-- subsystem Status Value
-- measured var
-- OID of the variable indicated the Measured value
-- Measured value

alarmSolarChargerTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the SolarCharger subsystem."
	::= { powerSystemTraps 11 }

alarmWindChargerTrap  NOTIFICATION-TYPE
	OBJECTS { alarmSubsysSourceDescr, 
		alarmSubsysStatusOid, 
		alarmSubsysStatusValue, 
		alarmSubsysStatusOnOff, 
		alarmMeasuredVarOid, 
		alarmMeasuredVarValue, 
		alarmTrapCounterVarValue }
	STATUS     current
	DESCRIPTION 
		"This Trap is sent when an alarm condition occurs in the WindCharger subsystem."
	::= { powerSystemTraps 12 }

infoHeartBeatTrap  NOTIFICATION-TYPE
	OBJECTS { alarmSubsysSourceDescr }
	STATUS     current
	DESCRIPTION 
		"When enabled, this trap will be transmitted at regular inervals. This trap is not
		intended to be an alarm but more like some information that the system is alive and
		the link is up."
	::= { powerSystemTraps 13 }

powerSystemStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"A status value showing the overall condition of the power system."
	::= { powerSystem 1 }

powerSystemType  OBJECT-TYPE
	SYNTAX     INTEGER {
		smartpack2 (1),
		smartpackS (2),
		compack (3)
	}
	MAX-ACCESS read-only
	STATUS     current
	DESCRIPTION 
		"A value showing the type of the power system, which is named after the main controller."
	::= { powerSystem 2 }

powerSystemMode  OBJECT-TYPE
	SYNTAX     INTEGER {
		off (0),
		test (1),
		boost (2),
		float (3)
	}
	MAX-ACCESS read-only
	STATUS     current
	DESCRIPTION 
		"A summary status showing if the system is in test, boost or float mode
		"
	::= { powerSystem 3 }

powerSystemCompany  OBJECT-TYPE
	SYNTAX     DisplayString (SIZE(0..32))
	MAX-ACCESS read-write
	STATUS     current
	DESCRIPTION 
		"The Copmany name (as stored in the Control Unit)."
	::= { powerSystem 4 }

powerSystemSite  OBJECT-TYPE
	SYNTAX     DisplayString (SIZE(0..32))
	MAX-ACCESS read-write
	STATUS     current
	DESCRIPTION 
		"The system/site Location details (as stored in the Control Unit)."
	::= { powerSystem 5 }

powerSystemModel  OBJECT-TYPE
	SYNTAX     DisplayString (SIZE(0..32))
	MAX-ACCESS read-only
	STATUS     current
	DESCRIPTION 
		"The model/part number of the power system (as stored in the Control Unit)."
	::= { powerSystem 6 }

powerSystemSerialNumber  OBJECT-TYPE
	SYNTAX     DisplayString (SIZE(0..16))
	MAX-ACCESS read-write
	STATUS     current
	DESCRIPTION 
		"The serial number for the complete system."
	::= { powerSystem 7 }

powerSystemInstallDate  OBJECT-TYPE
	SYNTAX     DateAndTime
	MAX-ACCESS read-write
	STATUS     current
	DESCRIPTION 
		"The system's Installation date (as stored in the Control Unit)."
	::= { powerSystem 8 }

powerSystemNominalVoltage  OBJECT-TYPE
	SYNTAX     Integer32 (6..250)
	MAX-ACCESS read-only
	STATUS     current
	DESCRIPTION 
		"The nominal voltage rating. 12V/24V/48V/60V etc. systems."
	::= { powerSystem 9 }

powerSystemLongitude  OBJECT-TYPE
	SYNTAX     Integer32 (-180..180)
	MAX-ACCESS read-write
	STATUS     current
	DESCRIPTION 
		"A part of the systems global positioning data. The range +-180degrees
		Longitude lines are imaginary lines running from the north pole to the south pole. 
		Longitudes are usually (WGS84) referenced from Greenwich, England where it has 
		been established as Zero Degrees longitude. Latitude and Longitude together with
		the Elevation can be used for automagically placing system icons on 
		NMS/Sitemonitors system that support this.  "
	::= { powerSystem 10 }

powerSystemLongitudeDecimal  OBJECT-TYPE
	SYNTAX     Integer32
	MAX-ACCESS read-write
	STATUS     current
	DESCRIPTION 
		"The decimal part of dcSystemLatitude contains up to 7digits. This number is 
		in 1/1000000 degree fractions or 0,0000001 degree. A part of the systems global 
		positioning data. Longitude lines are imaginary lines running from the north pole to
		the south pole.  Longitudes are usually (WGS84) referenced from Greenwich, England where it has 
		been established as Zero Degrees longitude. Latitude and Longitude together with
		the Elevation can be used for automagically placing system icons on 
		NMS/Sitemonitors system that support this.  "
	::= { powerSystem 11 }

powerSystemLatitude  OBJECT-TYPE
	SYNTAX     Integer32 (-90..90)
	MAX-ACCESS read-write
	STATUS     current
	DESCRIPTION 
		"A part of the systems global positioning data. The latitude gives the location of a place 
		on Earth (or other planetary body) north or south of the equator. Lines of Latitude has 
		a range of  +-90 degrees and are the imaginary horizontal lines shown running 
		east-to-west (or west to east).  Latitude and Longitude together with
		the Elevation can be used for automagically placing system icons on 
		NMS/Sitemonitors system that support this. "
	::= { powerSystem 12 }

powerSystemLatitudeDecimal  OBJECT-TYPE
	SYNTAX     Integer32
	MAX-ACCESS read-write
	STATUS     current
	DESCRIPTION 
		"The decimal part of dcSystemLatitude contains up to 7digits. This number is 
		in 1/1000000 degree fractions or 0,0000001 degree. A part of the systems global 
		positioning data.
		Lines of Latitude has a range of  +-90 degrees and are the imaginary horizontal 
		lines shown running east-to-west (or west to east).  Latitude and Longitude together with
		the Elevation can be used for automagically placing system icons on 
		NMS/Sitemonitors system that support this. 
		
		
		Longitude lines are imaginary lines running from the north pole to
		the south pole.
		 
		Longitudes are usually (WGS84) referenced from Greenwich, England where it has 
		been established as Zero Degrees longitude. Latitude and Longitude together with
		the Elevation can be used for automagically placing system icons on 
		NMS/Sitemonitors system that support this.  "
	::= { powerSystem 13 }

powerSystemElevation  OBJECT-TYPE
	SYNTAX     Integer32
	MAX-ACCESS read-write
	STATUS     current
	DESCRIPTION 
		"A part of the systems global positioning data. This is the sites height above sealevel in Meters.
		The  Elevation together with Latituse and Longitude is used for automagically placing
		system icons on NMS/Sitemonitors system that support this."
	::= { powerSystem 14 }

powerSystemCurrentDecimalSetting  OBJECT-TYPE
	SYNTAX     INTEGER {
		ampere (0),
		deciAmpere (1)
	}
	MAX-ACCESS read-write
	STATUS     current
	DESCRIPTION 
		"A global flag telling if the current values in the system is Amperes or DeciAmpres"
	::= { powerSystem 15 }

powerSystemTemperatureScale  OBJECT-TYPE
	SYNTAX     INTEGER {
		celcius (0),
		fahrenheit (1)
	}
	MAX-ACCESS read-write
	STATUS     current
	DESCRIPTION 
		"A flag telling if the temperatures values in the system is of Celcius or Fahrenheit type"
	::= { powerSystem 16 }

powerSystemCapacityScale  OBJECT-TYPE
	SYNTAX     INTEGER {
		ah (0),
		percent (1)
	}
	MAX-ACCESS read-write
	STATUS     current
	DESCRIPTION 
		"A flag telling if the system's battery capacity value is a percentage
		of a fully charged battery, or in AmpereHours"
	::= { powerSystem 17 }

mainsStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of mains/AC feed subsystem."
	::= { mains 1 }

mainsMainsFailureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed phases is higher than the defined alarm level."
	::= { mainsMainsFailure 1 }

mainsMainsFailureDescription  OBJECT-TYPE
	SYNTAX     DisplayString (SIZE(0..16))
	MAX-ACCESS read-write
	STATUS     current
	DESCRIPTION 
		"A textual description of the mains phase failure monitor. This is stored in the system controller
		and can be changed by the user."
	::= { mainsMainsFailure 2 }

mainsMainsFailureTrapRepeatCounter  OBJECT-TYPE
	SYNTAX     Integer32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { mainsMainsFailure 3 }

mainsMainsFailureAlarmEnable  OBJECT-TYPE
	SYNTAX     INTEGER {
		disabled (0),
		enabled (1)
	}
	MAX-ACCESS read-write
	STATUS     current
	DESCRIPTION 
		"This value once enabled, the alarm condition of the monitor will be reported."
	::= { mainsMainsFailure 4 }

mainsMainsFailureValue  OBJECT-TYPE
	SYNTAX     Integer32
	MAX-ACCESS read-only
	STATUS     current
	DESCRIPTION 
		"The detected number of failed phases."
	::= { mainsMainsFailure 5 }

mainsMainsFailureMajorAlarmLevel  OBJECT-TYPE
	SYNTAX     Integer32
	MAX-ACCESS read-write
	STATUS     current
	DESCRIPTION 
		"The major alarm limit"
	::= { mainsMainsFailure 6 }

mainsMainsFailureMinorAlarmLevel  OBJECT-TYPE
	SYNTAX     Integer32
	MAX-ACCESS read-write
	STATUS     current
	DESCRIPTION 
		"The minor alarm limit"
	::= { mainsMainsFailure 7 }

mainsNumberOfPhases  OBJECT-TYPE
	SYNTAX     Integer32
	MAX-ACCESS read-write
	STATUS     current
	DESCRIPTION 
		"This value showing the number of phases of the mains subsystem."
	::= { mains 3 }

mainsVoltageTable  OBJECT-TYPE
	SYNTAX SEQUENCE OF MainsVoltageEntry
	MAX-ACCESS not-accessible
	STATUS     current
	DESCRIPTION 
		"This table contains information about mains voltage monitor"
	::= { mains 4 }

mainsVoltageEntry  OBJECT-TYPE
	SYNTAX 	MainsVoltageEntry
	MAX-ACCESS not-accessible
	STATUS     current
	DESCRIPTION 
		""
	INDEX { mainsVoltageIndex }
	::= { mainsVoltageTable 1 }

MainsVoltageEntry ::= SEQUENCE {
	mainsVoltageIndex
		Integer32,
	mainsVoltageStatus
		INTEGER,
	mainsVoltageDescription
		DisplayString,
	mainsVoltageTrapRepeatCounter
		Counter32,
	mainsVoltageAlarmEnable
		INTEGER,
	mainsVoltageValue
		Integer32,
	mainsVoltageMajorHighLevel
		Integer32,
	mainsVoltageMinorHighLevel
		Integer32,
	mainsVoltageMinorLowLevel
		Integer32,
	mainsVoltageMajorLowLevel
		Integer32
}

mainsVoltageIndex  OBJECT-TYPE
	SYNTAX     Integer32 (1..12)
	MAX-ACCESS not-accessible
	STATUS     current
	DESCRIPTION 
		"Index used for navigating the rows 1..12  of mainsVoltageTable"
	::= { mainsVoltageEntry 1 }

mainsVoltageStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains voltage."
	::= { mainsVoltageEntry 2 }

mainsVoltageDescription  OBJECT-TYPE
	SYNTAX     DisplayString (SIZE(0..16))
	MAX-ACCESS read-write
	STATUS     current
	DESCRIPTION 
		"A textual description of the mains voltage monitor. This is stored in the system controller
		and can be changed by the user.  "
	::= { mainsVoltageEntry 3 }

mainsVoltageTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsVoltageEntry 4 }

mainsVoltageAlarmEnable  OBJECT-TYPE
	SYNTAX     INTEGER {
		disabled (0),
		enabled (1)
	}
	MAX-ACCESS read-write
	STATUS     current
	DESCRIPTION 
		"This value once enabled, the alarm condition of the monitor will be reported."
	::= { mainsVoltageEntry 5 }

mainsVoltageValue  OBJECT-TYPE
	SYNTAX     Integer32
	MAX-ACCESS read-only
	STATUS     current
	DESCRIPTION 
		"The value of the measured mains voltage."
	::= { mainsVoltageEntry 6 }

mainsVoltageMajorHighLevel  OBJECT-TYPE
	SYNTAX     Integer32
	MAX-ACCESS read-write
	STATUS     current
	DESCRIPTION 
		"The major high alarm limit"
	::= { mainsVoltageEntry 7 }

mainsVoltageMinorHighLevel  OBJECT-TYPE
	SYNTAX     Integer32
	MAX-ACCESS read-write
	STATUS     current
	DESCRIPTION 
		"The minor high alarm limit"
	::= { mainsVoltageEntry 8 }

mainsVoltageMinorLowLevel  OBJECT-TYPE
	SYNTAX     Integer32
	MAX-ACCESS read-write
	STATUS     current
	DESCRIPTION 
		"The minor low alarm limit"
	::= { mainsVoltageEntry 9 }

mainsVoltageMajorLowLevel  OBJECT-TYPE
	SYNTAX     Integer32
	MAX-ACCESS read-write
	STATUS     current
	DESCRIPTION 
		"The major low alarm limit"
	::= { mainsVoltageEntry 10 }

mainsMonitorsNumberOfUnits  OBJECT-TYPE
	SYNTAX     Integer32 (0..14)
	MAX-ACCESS read-write
	STATUS     current
	DESCRIPTION 
		"This is the number of AC Mains Monitor CAN Nodes installed in the system."
	::= { mainsMonitors 1 }

mainsMonitorsTable  OBJECT-TYPE
	SYNTAX SEQUENCE OF MainsMonitorsEntry
	MAX-ACCESS not-accessible
	STATUS     current
	DESCRIPTION 
		"This table contains the number of voltage, current and frequency measurements in each AC Mains Monitor"
	::= { mainsMonitors 2 }

mainsMonitorsEntry  OBJECT-TYPE
	SYNTAX 	MainsMonitorsEntry
	MAX-ACCESS not-accessible
	STATUS     current
	DESCRIPTION 
		""
	INDEX { mainsMonitorIndex }
	::= { mainsMonitorsTable 1 }

MainsMonitorsEntry ::= SEQUENCE {
	mainsMonitorIndex
		Integer32,
	mainsMonitorNumberOfVoltages
		Integer32,
	mainsMonitorNumberOfCurrents
		Integer32,
	mainsMonitorNumberOfFrequencies
		Integer32
}

mainsMonitorIndex  OBJECT-TYPE
	SYNTAX     Integer32 (1..14)
	MAX-ACCESS not-accessible
	STATUS     current
	DESCRIPTION 
		"Index used for navigating the rows of mainsMonitorsTable
		The size of the table is defined by the system  "
	::= { mainsMonitorsEntry 1 }

mainsMonitorNumberOfVoltages  OBJECT-TYPE
	SYNTAX     Integer32 (0..3)
	MAX-ACCESS read-only
	STATUS     current
	DESCRIPTION 
		"The number of voltage measurements in the AC Mains Monitor"
	::= { mainsMonitorsEntry 2 }

mainsMonitorNumberOfCurrents  OBJECT-TYPE
	SYNTAX     Integer32 (0..3)
	MAX-ACCESS read-only
	STATUS     current
	DESCRIPTION 
		"The number of current measurements in the AC Mains Monitor"
	::= { mainsMonitorsEntry 3 }

mainsMonitorNumberOfFrequencies  OBJECT-TYPE
	SYNTAX     Integer32 (0..3)
	MAX-ACCESS read-only
	STATUS     current
	DESCRIPTION 
		"The number of frequency measurements in the AC Mains Monitor"
	::= { mainsMonitorsEntry 4 }

mainsMonitorVoltageTable  OBJECT-TYPE
	SYNTAX SEQUENCE OF MainsMonitorVoltageEntry
	MAX-ACCESS not-accessible
	STATUS     current
	DESCRIPTION 
		"This table contains information about mains voltage in AC Mains Monitor"
	::= { mainsMonitors 3 }

mainsMonitorVoltageEntry  OBJECT-TYPE
	SYNTAX 	MainsMonitorVoltageEntry
	MAX-ACCESS not-accessible
	STATUS     current
	DESCRIPTION 
		""
	INDEX { mainsMonitorIndex, 
		mainsMonitorPhaseIndex }
	::= { mainsMonitorVoltageTable 1 }

MainsMonitorVoltageEntry ::= SEQUENCE {
	mainsMonitorPhaseIndex
		Integer32,
	mainsMonitorVoltageStatus
		INTEGER,
	mainsMonitorVoltageDescription
		DisplayString,
	mainsMonitorVoltageTrapRepeatCounter
		Counter32,
	mainsMonitorVoltageAlarmEnable
		INTEGER,
	mainsMonitorVoltageValue
		Integer32,
	mainsMonitorVoltageMajorHighLevel
		Integer32,
	mainsMonitorVoltageMinorHighLevel
		Integer32,
	mainsMonitorVoltageMinorLowLevel
		Integer32,
	mainsMonitorVoltageMajorLowLevel
		Integer32
}

mainsMonitorPhaseIndex  OBJECT-TYPE
	SYNTAX     Integer32 (1..3)
	MAX-ACCESS not-accessible
	STATUS     current
	DESCRIPTION 
		"Index used for navigating the rows 1..3  of mainsMonitorVolatgeTable"
	::= { mainsMonitorVoltageEntry 1 }

mainsMonitorVoltageStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains voltage in AC Mains Monitor."
	::= { mainsMonitorVoltageEntry 2 }

mainsMonitorVoltageDescription  OBJECT-TYPE
	SYNTAX     DisplayString (SIZE(1..16))
	MAX-ACCESS read-write
	STATUS     current
	DESCRIPTION 
		"A textual description of the mains voltage in AC Mains Monitor. This is stored in the system controller
		and can be changed by the user."
	::= { mainsMonitorVoltageEntry 3 }

mainsMonitorVoltageTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsMonitorVoltageEntry 4 }

mainsMonitorVoltageAlarmEnable  OBJECT-TYPE
	SYNTAX     INTEGER {
		disabled (0),
		enabled (1)
	}
	MAX-ACCESS read-write
	STATUS     current
	DESCRIPTION 
		"This value once enabled, the alarm condition of the monitor will be reported."
	::= { mainsMonitorVoltageEntry 5 }

mainsMonitorVoltageValue  OBJECT-TYPE
	SYNTAX     Integer32
	MAX-ACCESS read-only
	STATUS     current
	DESCRIPTION 
		"The value of the measured mains voltage in AC Mains Monitor."
	::= { mainsMonitorVoltageEntry 6 }

mainsMonitorVoltageMajorHighLevel  OBJECT-TYPE
	SYNTAX     Integer32
	MAX-ACCESS read-write
	STATUS     current
	DESCRIPTION 
		"The major high alarm limit"
	::= { mainsMonitorVoltageEntry 7 }

mainsMonitorVoltageMinorHighLevel  OBJECT-TYPE
	SYNTAX     Integer32
	MAX-ACCESS read-write
	STATUS     current
	DESCRIPTION 
		"The minor high alarm limit"
	::= { mainsMonitorVoltageEntry 8 }

mainsMonitorVoltageMinorLowLevel  OBJECT-TYPE
	SYNTAX     Integer32
	MAX-ACCESS read-write
	STATUS     current
	DESCRIPTION 
		"The minor low alarm limit"
	::= { mainsMonitorVoltageEntry 9 }

mainsMonitorVoltageMajorLowLevel  OBJECT-TYPE
	SYNTAX     Integer32
	MAX-ACCESS read-write
	STATUS     current
	DESCRIPTION 
		"The major low alarm limit"
	::= { mainsMonitorVoltageEntry 10 }

mainsMonitorCurrentTable  OBJECT-TYPE
	SYNTAX SEQUENCE OF MainsMonitorCurrentEntry
	MAX-ACCESS not-accessible
	STATUS     current
	DESCRIPTION 
		"This table contains information about mains current in AC Mains Monitor"
	::= { mainsMonitors 4 }

mainsMonitorCurrentEntry  OBJECT-TYPE
	SYNTAX 	MainsMonitorCurrentEntry
	MAX-ACCESS not-accessible
	STATUS     current
	DESCRIPTION 
		""
	INDEX { mainsMonitorIndex, 
		mainsMonitorPhaseIndex }
	::= { mainsMonitorCurrentTable 1 }

MainsMonitorCurrentEntry ::= SEQUENCE {
	mainsMonitorCurrentStatus
		INTEGER,
	mainsMonitorCurrentDescription
		DisplayString,
	mainsMonitorCurrentTrapRepeatCounter
		Counter32,
	mainsMonitorCurrentAlarmEnable
		INTEGER,
	mainsMonitorCurrentValue
		Integer32,
	mainsMonitorCurrentMajorHighLevel
		Integer32,
	mainsMonitorCurrentMinorHighLevel
		Integer32
}

mainsMonitorCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains current in AC Mains Monitor."
	::= { mainsMonitorCurrentEntry 1 }

mainsMonitorCurrentDescription  OBJECT-TYPE
	SYNTAX     DisplayString (SIZE(1..16))
	MAX-ACCESS read-write
	STATUS     current
	DESCRIPTION 
		"A textual description of the mains current in AC Mains Monitor. This is stored in the system controller
		and can be changed by the user."
	::= { mainsMonitorCurrentEntry 2 }

mainsMonitorCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsMonitorCurrentEntry 3 }

mainsMonitorCurrentAlarmEnable  OBJECT-TYPE
	SYNTAX     INTEGER {
		disabled (0),
		enabled (1)
	}
	MAX-ACCESS read-write
	STATUS     current
	DESCRIPTION 
		"This value once enabled, the alarm condition of the monitor will be reported."
	::= { mainsMonitorCurrentEntry 4 }

mainsMonitorCurrentValue  OBJECT-TYPE
	SYNTAX     Integer32
	MAX-ACCESS read-only
	STATUS     current
	DESCRIPTION 
		"The value of the measured mains current in AC Mains Monitor."
	::= { mainsMonitorCurrentEntry 5 }

mainsMonitorCurrentMajorHighLevel  OBJECT-TYPE
	SYNTAX     Integer32
	MAX-ACCESS read-write
	STATUS     current
	DESCRIPTION 
		"The major high alarm limit"
	::= { mainsMonitorCurrentEntry 6 }

mainsMonitorCurrentMinorHighLevel  OBJECT-TYPE
	SYNTAX     Integer32
	MAX-ACCESS read-write
	STATUS     current
	DESCRIPTION 
		"The minor high alarm limit"
	::= { mainsMonitorCurrentEntry 7 }

mainsMonitorFrequencyTable  OBJECT-TYPE
	SYNTAX SEQUENCE OF MainsMonitorFrequencyEntry
	MAX-ACCESS not-accessible
	STATUS     current
	DESCRIPTION 
		"This table contains information about mains frequency in AC Mains Monitor"
	::= { mainsMonitors 5 }

mainsMonitorFrequencyEntry  OBJECT-TYPE
	SYNTAX 	MainsMonitorFrequencyEntry
	MAX-ACCESS not-accessible
	STATUS     current
	DESCRIPTION 
		""
	INDEX { mainsMonitorIndex }
	::= { mainsMonitorFrequencyTable 1 }

MainsMonitorFrequencyEntry ::= SEQUENCE {
	mainsMonitorFrequencyStatus
		INTEGER,
	mainsMonitorFrequencyDescription
		DisplayString,
	mainsMonitorFrequencyTrapRepeatCounter
		Counter32,
	mainsMonitorFrequencyAlarmEnable
		INTEGER,
	mainsMonitorFrequencyValue
		Integer32,
	mainsMonitorFrequencyMajorHighLevel
		Integer32,
	mainsMonitorFrequencyMinorHighLevel
		Integer32,
	mainsMonitorFrequencyMinorLowLevel
		Integer32,
	mainsMonitorFrequencyMajorLowLevel
		Integer32
}

mainsMonitorFrequencyStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured mains frequency in AC Mains Monitor."
	::= { mainsMonitorFrequencyEntry 1 }

mainsMonitorFrequencyDescription  OBJECT-TYPE
	SYNTAX     DisplayString (SIZE(0..16))
	MAX-ACCESS read-write
	STATUS     current
	DESCRIPTION 
		"A textual description of the mains frequency in AC Mains Monitor. This is stored in the system
		 controller 
		and can be changed by the user.  "
	::= { mainsMonitorFrequencyEntry 2 }

mainsMonitorFrequencyTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { mainsMonitorFrequencyEntry 3 }

mainsMonitorFrequencyAlarmEnable  OBJECT-TYPE
	SYNTAX     INTEGER {
		disabled (0),
		enabled (1)
	}
	MAX-ACCESS read-write
	STATUS     current
	DESCRIPTION 
		"This value once enabled, the alarm condition of the monitor will be reported."
	::= { mainsMonitorFrequencyEntry 4 }

mainsMonitorFrequencyValue  OBJECT-TYPE
	SYNTAX     Integer32
	MAX-ACCESS read-only
	STATUS     current
	DESCRIPTION 
		"The value of the measured mains frequency in AC Mains Monitor."
	::= { mainsMonitorFrequencyEntry 5 }

mainsMonitorFrequencyMajorHighLevel  OBJECT-TYPE
	SYNTAX     Integer32
	MAX-ACCESS read-write
	STATUS     current
	DESCRIPTION 
		"The major high alarm limit"
	::= { mainsMonitorFrequencyEntry 6 }

mainsMonitorFrequencyMinorHighLevel  OBJECT-TYPE
	SYNTAX     Integer32
	MAX-ACCESS read-write
	STATUS     current
	DESCRIPTION 
		"The minor high alarm limit"
	::= { mainsMonitorFrequencyEntry 7 }

mainsMonitorFrequencyMinorLowLevel  OBJECT-TYPE
	SYNTAX     Integer32
	MAX-ACCESS read-write
	STATUS     current
	DESCRIPTION 
		"The minor low alarm limit"
	::= { mainsMonitorFrequencyEntry 8 }

mainsMonitorFrequencyMajorLowLevel  OBJECT-TYPE
	SYNTAX     Integer32
	MAX-ACCESS read-write
	STATUS     current
	DESCRIPTION 
		"The major low alarm limit"
	::= { mainsMonitorFrequencyEntry 9 }

mainsMonitorEnergyLogAccumulatedTable  OBJECT-TYPE
	SYNTAX SEQUENCE OF MainsMonitorEnergyLogAccumulatedEntry
	MAX-ACCESS not-accessible
	STATUS     current
	DESCRIPTION 
		"This table contains the accumulated energy consumption measured in AC Mains Monitor"
	::= { mainsMonitors 6 }

mainsMonitorEnergyLogAccumulatedEntry  OBJECT-TYPE
	SYNTAX 	MainsMonitorEnergyLogAccumulatedEntry
	MAX-ACCESS not-accessible
	STATUS     current
	DESCRIPTION 
		""
	INDEX { mainsMonitorIndex }
	::= { mainsMonitorEnergyLogAccumulatedTable 1 }

MainsMonitorEnergyLogAccumulatedEntry ::= SEQUENCE {
	mainsMonitorEnergyLogAccumulated
		Integer32
}

mainsMonitorEnergyLogAccumulated  OBJECT-TYPE
	SYNTAX     Integer32
	MAX-ACCESS read-only
	STATUS     current
	DESCRIPTION 
		"The accumulated energy consumption value"
	::= { mainsMonitorEnergyLogAccumulatedEntry 1 }

mainsMonitorEnergyLogLastHoursNumberOfEntries  OBJECT-TYPE
	SYNTAX     Integer32 (0..52)
	MAX-ACCESS read-only
	STATUS     current
	DESCRIPTION 
		"This is the maximal number of entries stored in hourly energy log"
	::= { mainsMonitors 7 }

mainsMonitorEnergyLogLastHoursTable  OBJECT-TYPE
	SYNTAX SEQUENCE OF MainsMonitorEnergyLogLastHoursEntry
	MAX-ACCESS not-accessible
	STATUS     current
	DESCRIPTION 
		"This table contains energy consumption values logged every hour in AC Mains Monitor."
	::= { mainsMonitors 8 }

mainsMonitorEnergyLogLastHoursEntry  OBJECT-TYPE
	SYNTAX 	MainsMonitorEnergyLogLastHoursEntry
	MAX-ACCESS not-accessible
	STATUS     current
	DESCRIPTION 
		""
	INDEX { mainsMonitorIndex, 
		mainsMonitorEnergyLogLastHoursIndex }
	::= { mainsMonitorEnergyLogLastHoursTable 1 }

MainsMonitorEnergyLogLastHoursEntry ::= SEQUENCE {
	mainsMonitorEnergyLogLastHoursIndex
		Integer32,
	mainsMonitorEnergyLogLastHoursValue
		Integer32
}

mainsMonitorEnergyLogLastHoursIndex  OBJECT-TYPE
	SYNTAX     Integer32 (1..52)
	MAX-ACCESS not-accessible
	STATUS     current
	DESCRIPTION 
		"Index used for navigating the rows 1..52  of mainsMonitorEnergyLogLastHoursTable"
	::= { mainsMonitorEnergyLogLastHoursEntry 1 }

mainsMonitorEnergyLogLastHoursValue  OBJECT-TYPE
	SYNTAX     Integer32
	MAX-ACCESS read-only
	STATUS     current
	DESCRIPTION 
		"Energy consumption value logged every hour in AC Mains Monitor."
	::= { mainsMonitorEnergyLogLastHoursEntry 2 }

mainsMonitorEnergyLogLastDaysNumberOfEntries  OBJECT-TYPE
	SYNTAX     Integer32 (0..52)
	MAX-ACCESS read-only
	STATUS     current
	DESCRIPTION 
		"This is the maximal number of entries stored in daily energy log"
	::= { mainsMonitors 9 }

mainsMonitorEnergyLogLastDaysTable  OBJECT-TYPE
	SYNTAX SEQUENCE OF MainsMonitorEnergyLogLastDaysEntry
	MAX-ACCESS not-accessible
	STATUS     current
	DESCRIPTION 
		"This table contains energy consumption values logged every day in AC Mains Monitor."
	::= { mainsMonitors 10 }

mainsMonitorEnergyLogLastDaysEntry  OBJECT-TYPE
	SYNTAX 	MainsMonitorEnergyLogLastDaysEntry
	MAX-ACCESS not-accessible
	STATUS     current
	DESCRIPTION 
		""
	INDEX { mainsMonitorIndex, 
		mainsMonitorEnergyLogLastDaysIndex }
	::= { mainsMonitorEnergyLogLastDaysTable 1 }

MainsMonitorEnergyLogLastDaysEntry ::= SEQUENCE {
	mainsMonitorEnergyLogLastDaysIndex
		Integer32,
	mainsMonitorEnergyLogLastDaysValue
		Integer32
}

mainsMonitorEnergyLogLastDaysIndex  OBJECT-TYPE
	SYNTAX     Integer32 (1..52)
	MAX-ACCESS not-accessible
	STATUS     current
	DESCRIPTION 
		"Index used for navigating the rows 1..52  of mainsMonitorEnergyLogLastDaysTable"
	::= { mainsMonitorEnergyLogLastDaysEntry 1 }

mainsMonitorEnergyLogLastDaysValue  OBJECT-TYPE
	SYNTAX     Integer32
	MAX-ACCESS read-only
	STATUS     current
	DESCRIPTION 
		"Energy consumption value logged every day in AC Mains Monitor."
	::= { mainsMonitorEnergyLogLastDaysEntry 2 }

mainsMonitorEnergyLogLastWeeksNumberOfEntries  OBJECT-TYPE
	SYNTAX     Integer32 (0..52)
	MAX-ACCESS read-only
	STATUS     current
	DESCRIPTION 
		"This is the maximal number of entries stored in weekly energy log"
	::= { mainsMonitors 11 }

mainsMonitorEnergyLogLastWeeksTable  OBJECT-TYPE
	SYNTAX SEQUENCE OF MainsMonitorEnergyLogLastWeeksEntry
	MAX-ACCESS not-accessible
	STATUS     current
	DESCRIPTION 
		"This table contains energy consumption values logged every week in AC Mains Monitor."
	::= { mainsMonitors 12 }

mainsMonitorEnergyLogLastWeeksEntry  OBJECT-TYPE
	SYNTAX 	MainsMonitorEnergyLogLastWeeksEntry
	MAX-ACCESS not-accessible
	STATUS     current
	DESCRIPTION 
		""
	INDEX { mainsMonitorIndex, 
		mainsMonitorEnergyLogLastWeeksIndex }
	::= { mainsMonitorEnergyLogLastWeeksTable 1 }

MainsMonitorEnergyLogLastWeeksEntry ::= SEQUENCE {
	mainsMonitorEnergyLogLastWeeksIndex
		Integer32,
	mainsMonitorEnergyLogLastWeeksValue
		Integer32
}

mainsMonitorEnergyLogLastWeeksIndex  OBJECT-TYPE
	SYNTAX     Integer32 (1..52)
	MAX-ACCESS not-accessible
	STATUS     current
	DESCRIPTION 
		"Index used for navigating the rows 1..52  of mainsMonitorEnergyLogLastWeeksTable"
	::= { mainsMonitorEnergyLogLastWeeksEntry 1 }

mainsMonitorEnergyLogLastWeeksValue  OBJECT-TYPE
	SYNTAX     Integer32
	MAX-ACCESS read-only
	STATUS     current
	DESCRIPTION 
		"Energy consumption value logged every week in AC Mains Monitor."
	::= { mainsMonitorEnergyLogLastWeeksEntry 2 }

mainsOutageTotal  OBJECT-TYPE
	SYNTAX     Integer32
	MAX-ACCESS read-only
	STATUS     current
	DESCRIPTION 
		"This is the total mains outage time measured in hours."
	::= { mainsOutageLog 1 }

mainsOutageLogDaysNumberOfEntries  OBJECT-TYPE
	SYNTAX     Integer32 (0..52)
	MAX-ACCESS read-only
	STATUS     current
	DESCRIPTION 
		"This is the maximal number of entries stored in daily mains outage log."
	::= { mainsOutageLog 2 }

mainsOutageLogDaysTable  OBJECT-TYPE
	SYNTAX SEQUENCE OF MainsOutageLogDaysEntry
	MAX-ACCESS not-accessible
	STATUS     current
	DESCRIPTION 
		"This table contains daily mains outage time log."
	::= { mainsOutageLog 3 }

mainsOutageLogDaysEntry  OBJECT-TYPE
	SYNTAX 	MainsOutageLogDaysEntry
	MAX-ACCESS not-accessible
	STATUS     current
	DESCRIPTION 
		""
	INDEX { mainsOutageLogDaysIndex }
	::= { mainsOutageLogDaysTable 1 }

MainsOutageLogDaysEntry ::= SEQUENCE {
	mainsOutageLogDaysIndex
		Integer32,
	mainsOutageLogDaysValue
		Integer32
}

mainsOutageLogDaysIndex  OBJECT-TYPE
	SYNTAX     Integer32 (1..52)
	MAX-ACCESS not-accessible
	STATUS     current
	DESCRIPTION 
		"Index used for navigating the rows 1..52  of mainsOutageLogDaysTable"
	::= { mainsOutageLogDaysEntry 1 }

mainsOutageLogDaysValue  OBJECT-TYPE
	SYNTAX     Integer32
	MAX-ACCESS read-only
	STATUS     current
	DESCRIPTION 
		"Mains outage time value in minutes, logged every day."
	::= { mainsOutageLogDaysEntry 2 }

mainsOutageLogWeeksNumberOfEntries  OBJECT-TYPE
	SYNTAX     Integer32 (0..52)
	MAX-ACCESS read-only
	STATUS     current
	DESCRIPTION 
		"This is the maximal number of entries stored in weekly mains outage time log."
	::= { mainsOutageLog 4 }

mainsOutageLogWeeksTable  OBJECT-TYPE
	SYNTAX SEQUENCE OF MainsOutageLogWeeksEntry
	MAX-ACCESS not-accessible
	STATUS     current
	DESCRIPTION 
		"This table contains weekly mains outage time log."
	::= { mainsOutageLog 5 }

mainsOutageLogWeeksEntry  OBJECT-TYPE
	SYNTAX 	MainsOutageLogWeeksEntry
	MAX-ACCESS not-accessible
	STATUS     current
	DESCRIPTION 
		""
	INDEX { mainsOutageLogWeeksIndex }
	::= { mainsOutageLogWeeksTable 1 }

MainsOutageLogWeeksEntry ::= SEQUENCE {
	mainsOutageLogWeeksIndex
		Integer32,
	mainsOutageLogWeeksValue
		Integer32
}

mainsOutageLogWeeksIndex  OBJECT-TYPE
	SYNTAX     Integer32 (1..52)
	MAX-ACCESS not-accessible
	STATUS     current
	DESCRIPTION 
		"Index used for navigating the rows 1..52  of mainsOutageLogWeeksTable"
	::= { mainsOutageLogWeeksEntry 1 }

mainsOutageLogWeeksValue  OBJECT-TYPE
	SYNTAX     Integer32
	MAX-ACCESS read-only
	STATUS     current
	DESCRIPTION 
		"Mains outage time value in hours, logged every week."
	::= { mainsOutageLogWeeksEntry 2 }

mainsOutageLogMonthsNumberOfEntries  OBJECT-TYPE
	SYNTAX     Integer32 (0..52)
	MAX-ACCESS read-only
	STATUS     current
	DESCRIPTION 
		"This is the maximal number of entries stored in monthly mains outage time log."
	::= { mainsOutageLog 6 }

mainsOutageLogMonthsTable  OBJECT-TYPE
	SYNTAX SEQUENCE OF MainsOutageLogMonthsEntry
	MAX-ACCESS not-accessible
	STATUS     current
	DESCRIPTION 
		"This table contains monthly mains outage time log."
	::= { mainsOutageLog 7 }

mainsOutageLogMonthsEntry  OBJECT-TYPE
	SYNTAX 	MainsOutageLogMonthsEntry
	MAX-ACCESS not-accessible
	STATUS     current
	DESCRIPTION 
		""
	INDEX { mainsOutageLogMonthsIndex }
	::= { mainsOutageLogMonthsTable 1 }

MainsOutageLogMonthsEntry ::= SEQUENCE {
	mainsOutageLogMonthsIndex
		Integer32,
	mainsOutageLogMonthsValue
		Integer32
}

mainsOutageLogMonthsIndex  OBJECT-TYPE
	SYNTAX     Integer32 (1..52)
	MAX-ACCESS not-accessible
	STATUS     current
	DESCRIPTION 
		"Index used for navigating the rows 1..52  of mainsOutageLogMonthsTable"
	::= { mainsOutageLogMonthsEntry 1 }

mainsOutageLogMonthsValue  OBJECT-TYPE
	SYNTAX     Integer32
	MAX-ACCESS read-only
	STATUS     current
	DESCRIPTION 
		"Mains outage time value in hours, logged every month."
	::= { mainsOutageLogMonthsEntry 2 }

generatorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of generator subsystem."
	::= { generator 1 }

generatorFailStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of generator failure monitor."
	::= { generator 2 }

generatorActivation  OBJECT-TYPE
	SYNTAX     Integer32
	MAX-ACCESS read-only
	STATUS     current
	DESCRIPTION 
		"Indicate if the generator run output signal is activated."
	::= { generator 3 }

generatorDischargeValue  OBJECT-TYPE
	SYNTAX     Integer32
	MAX-ACCESS read-only
	STATUS     current
	DESCRIPTION 
		"This is the present discharge value in percentage of total capacity."
	::= { generator 4 }

generatorMainsDelay  OBJECT-TYPE
	SYNTAX     Integer32
	MAX-ACCESS read-only
	STATUS     current
	DESCRIPTION 
		"Elapsing time of mains failure."
	::= { generator 5 }

generatorChargeTime  OBJECT-TYPE
	SYNTAX     Integer32
	MAX-ACCESS read-only
	STATUS     current
	DESCRIPTION 
		"Elapsing time of charging with generator running."
	::= { generator 6 }

generatorCapacityControlledStartStopEnable  OBJECT-TYPE
	SYNTAX     INTEGER {
		disabled (0),
		enabled (1)
	}
	MAX-ACCESS read-write
	STATUS     current
	DESCRIPTION 
		"Battery charge/discharge level control of starting and stopping of generator "
	::= { generator 7 }

generatorCapacityStartOnDischargeLimit  OBJECT-TYPE
	SYNTAX     Integer32 (0..100)
	MAX-ACCESS read-write
	STATUS     current
	DESCRIPTION 
		"When the generatorCapacityControlled is enabled, the generator is started 
		when the remaining battery capacity drops below this limit in percentage of the total capacity."
	::= { generator 8 }

generatorCapacityStopOnChargeLimit  OBJECT-TYPE
	SYNTAX     Integer32 (0..100)
	MAX-ACCESS read-write
	STATUS     current
	DESCRIPTION 
		"When the generatorCapacityControlled is enabled, the generator is stopped 
		when the remaining battery capacity is greater than this limit in percentage of the total capacity."
	::= { generator 9 }

generatorCurrentLimitControlledStopEnable  OBJECT-TYPE
	SYNTAX     INTEGER {
		disabled (0),
		enabled (1)
	}
	MAX-ACCESS read-write
	STATUS     current
	DESCRIPTION 
		"Enables the generator to stop when the charge current drops below generatorCurrentLimitControlledStopValue. "
	::= { generator 10 }

generatorCurrentLimitControlledStopValue  OBJECT-TYPE
	SYNTAX     Integer32 (0..100)
	MAX-ACCESS read-write
	STATUS     current
	DESCRIPTION 
		"Generator stops when the charge current drop drops below this level. "
	::= { generator 11 }

generatorVoltageControlledStartEnable  OBJECT-TYPE
	SYNTAX     INTEGER {
		disabled (0),
		enabled (1)
	}
	MAX-ACCESS read-write
	STATUS     current
	DESCRIPTION 
		"Enable/disable voltage controlled generator activation."
	::= { generator 12 }

generatorVoltageControlStartVoltage  OBJECT-TYPE
	SYNTAX     Integer32
	MAX-ACCESS read-write
	STATUS     current
	DESCRIPTION 
		"The voltage limit to start generator."
	::= { generator 13 }

generatorVoltageControlStopAfter  OBJECT-TYPE
	SYNTAX     Integer32
	MAX-ACCESS read-write
	STATUS     current
	DESCRIPTION 
		"A time delay for stopping generator when generator is activated by voltage."
	::= { generator 14 }

generatorDailyRunEnable  OBJECT-TYPE
	SYNTAX     INTEGER {
		disabled (0),
		enabled (1)
	}
	MAX-ACCESS read-write
	STATUS     current
	DESCRIPTION 
		"Enable/disable generator daily run function."
	::= { generator 15 }

generatorDailyRunSetupTable  OBJECT-TYPE
	SYNTAX SEQUENCE OF GeneratorDailyRunSetupEntry
	MAX-ACCESS not-accessible
	STATUS     current
	DESCRIPTION 
		"This table contains configurations of generator daily run."
	::= { generator 16 }

generatorDailyRunSetupEntry  OBJECT-TYPE
	SYNTAX 	GeneratorDailyRunSetupEntry
	MAX-ACCESS not-accessible
	STATUS     current
	DESCRIPTION 
		""
	INDEX { generatorDailyRunDayIndex }
	::= { generatorDailyRunSetupTable 1 }

GeneratorDailyRunSetupEntry ::= SEQUENCE {
	generatorDailyRunDayIndex
		INTEGER,
	generatorDailyRunStartHour
		Integer32,
	generatorDailyRunStopHour
		Integer32
}

generatorDailyRunDayIndex  OBJECT-TYPE
	SYNTAX     INTEGER {
		sunday (1),
		monday (2),
		tuesday (3),
		wednesday (4),
		thursday (5),
		friday (6),
		saturday (7)
	}
	MAX-ACCESS not-accessible
	STATUS     current
	DESCRIPTION 
		"Index used for navigating the rows 1..7  of generatorDailyRunSetupTable"
	::= { generatorDailyRunSetupEntry 1 }

generatorDailyRunStartHour  OBJECT-TYPE
	SYNTAX     Integer32 (0..23)
	MAX-ACCESS read-write
	STATUS     current
	DESCRIPTION 
		"Generator daily starting time."
	::= { generatorDailyRunSetupEntry 2 }

generatorDailyRunStopHour  OBJECT-TYPE
	SYNTAX     Integer32 (0..23)
	MAX-ACCESS read-write
	STATUS     current
	DESCRIPTION 
		"Generator daily stopping time."
	::= { generatorDailyRunSetupEntry 3 }

generatorMonthlyRunEnable  OBJECT-TYPE
	SYNTAX     INTEGER {
		disabled (0),
		enabled (1)
	}
	MAX-ACCESS read-write
	STATUS     current
	DESCRIPTION 
		"Enable/disable generator monthly run function."
	::= { generator 17 }

generatorMonthlyRunStartTime  OBJECT-TYPE
	SYNTAX     Integer32 (0..23)
	MAX-ACCESS read-write
	STATUS     current
	DESCRIPTION 
		"Generator monthly run starting time."
	::= { generator 18 }

generatorMonthlyRunStartDayinMonth1  OBJECT-TYPE
	SYNTAX     Integer32 (1..32)
	MAX-ACCESS read-write
	STATUS     current
	DESCRIPTION 
		"Generator monthly run starting day #1."
	::= { generator 19 }

generatorMonthlyRunStartDayinMonth2  OBJECT-TYPE
	SYNTAX     Integer32 (1..32)
	MAX-ACCESS read-write
	STATUS     current
	DESCRIPTION 
		"Generator monthly run starting day #2."
	::= { generator 20 }

generatorTankNumberOfTanks  OBJECT-TYPE
	SYNTAX     Integer32 (0..2)
	MAX-ACCESS read-only
	STATUS     current
	DESCRIPTION 
		"Number of fuel tanks."
	::= { generator 21 }

generatorTankTable  OBJECT-TYPE
	SYNTAX SEQUENCE OF GeneratorTankEntry
	MAX-ACCESS not-accessible
	STATUS     current
	DESCRIPTION 
		"This table contains information about generator fuel tanks."
	::= { generator 22 }

generatorTankEntry  OBJECT-TYPE
	SYNTAX 	GeneratorTankEntry
	MAX-ACCESS not-accessible
	STATUS     current
	DESCRIPTION 
		""
	INDEX { generatorTankIndex }
	::= { generatorTankTable 1 }

GeneratorTankEntry ::= SEQUENCE {
	generatorTankIndex
		Integer32,
	generatorTankStatus
		INTEGER,
	generatorTankDescription
		DisplayString,
	generatorTankTrapRepeatCounter
		Counter32,
	generatorTankEnable
		INTEGER,
	generatorTankValue
		Integer32,
	generatorTankMajorHighLevel
		Integer32,
	generatorTankMinorHighLevel
		Integer32,
	generatorTankMinorLowLevel
		Integer32,
	generatorTankMajorLowLevel
		Integer32
}

generatorTankIndex  OBJECT-TYPE
	SYNTAX     Integer32 (1..2)
	MAX-ACCESS not-accessible
	STATUS     current
	DESCRIPTION 
		"Index used for navigating the rows 1..2  of generatorTankTable"
	::= { generatorTankEntry 1 }

generatorTankStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured fuel level in tank."
	::= { generatorTankEntry 2 }

generatorTankDescription  OBJECT-TYPE
	SYNTAX     DisplayString (SIZE(0..16))
	MAX-ACCESS read-write
	STATUS     current
	DESCRIPTION 
		"A textual description of the fuel level monitor. This is stored in the system controller
		and can be changed by the user.  "
	::= { generatorTankEntry 3 }

generatorTankTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { generatorTankEntry 4 }

generatorTankEnable  OBJECT-TYPE
	SYNTAX     INTEGER {
		disabled (0),
		enabled (1)
	}
	MAX-ACCESS read-write
	STATUS     current
	DESCRIPTION 
		"This value once enabled, the alarm condition of the monitor will be reported."
	::= { generatorTankEntry 5 }

generatorTankValue  OBJECT-TYPE
	SYNTAX     Integer32
	MAX-ACCESS read-only
	STATUS     current
	DESCRIPTION 
		"The value of the measured fuel level."
	::= { generatorTankEntry 6 }

generatorTankMajorHighLevel  OBJECT-TYPE
	SYNTAX     Integer32
	MAX-ACCESS read-write
	STATUS     current
	DESCRIPTION 
		"The major high alarm limit"
	::= { generatorTankEntry 7 }

generatorTankMinorHighLevel  OBJECT-TYPE
	SYNTAX     Integer32
	MAX-ACCESS read-write
	STATUS     current
	DESCRIPTION 
		"The minor high alarm limit"
	::= { generatorTankEntry 8 }

generatorTankMinorLowLevel  OBJECT-TYPE
	SYNTAX     Integer32
	MAX-ACCESS read-write
	STATUS     current
	DESCRIPTION 
		"The minor low alarm limit"
	::= { generatorTankEntry 9 }

generatorTankMajorLowLevel  OBJECT-TYPE
	SYNTAX     Integer32
	MAX-ACCESS read-write
	STATUS     current
	DESCRIPTION 
		"The major low alarm limit"
	::= { generatorTankEntry 10 }

generatorEnergyLogAccumulated  OBJECT-TYPE
	SYNTAX     Integer32
	MAX-ACCESS read-only
	STATUS     current
	DESCRIPTION 
		"This is the accumulated energy delivered through rectifiers from generator."
	::= { generatorEnergyLog 1 }

generatorEnergyLogLastHoursNumberOfEntries  OBJECT-TYPE
	SYNTAX     Integer32 (0..52)
	MAX-ACCESS read-only
	STATUS     current
	DESCRIPTION 
		"This is the maximal number of entries stored in generator hourly energy log."
	::= { generatorEnergyLog 2 }

generatorEnergyLogLastHoursTable  OBJECT-TYPE
	SYNTAX SEQUENCE OF GeneratorEnergyLogLastHoursEntry
	MAX-ACCESS not-accessible
	STATUS     current
	DESCRIPTION 
		"This table contains hourly energy log of generator."
	::= { generatorEnergyLog 3 }

generatorEnergyLogLastHoursEntry  OBJECT-TYPE
	SYNTAX 	GeneratorEnergyLogLastHoursEntry
	MAX-ACCESS not-accessible
	STATUS     current
	DESCRIPTION 
		""
	INDEX { generatorEnergyLogLastHoursIndex }
	::= { generatorEnergyLogLastHoursTable 1 }

GeneratorEnergyLogLastHoursEntry ::= SEQUENCE {
	generatorEnergyLogLastHoursIndex
		Integer32,
	generatorEnergyLogLastHoursValue
		Integer32
}

generatorEnergyLogLastHoursIndex  OBJECT-TYPE
	SYNTAX     Integer32 (1..52)
	MAX-ACCESS not-accessible
	STATUS     current
	DESCRIPTION 
		"Index used for navigating the rows 1..52  of generatorEnergyLogLastHoursTable"
	::= { generatorEnergyLogLastHoursEntry 1 }

generatorEnergyLogLastHoursValue  OBJECT-TYPE
	SYNTAX     Integer32
	MAX-ACCESS read-only
	STATUS     current
	DESCRIPTION 
		"Energy value logged every hour."
	::= { generatorEnergyLogLastHoursEntry 2 }

generatorEnergyLogLastDaysNumberOfEntries  OBJECT-TYPE
	SYNTAX     Integer32 (0..52)
	MAX-ACCESS read-only
	STATUS     current
	DESCRIPTION 
		"This is the maximal number of entries stored in generator daily energy log."
	::= { generatorEnergyLog 4 }

generatorEnergyLogLastDaysTable  OBJECT-TYPE
	SYNTAX SEQUENCE OF GeneratorEnergyLogLastDaysEntry
	MAX-ACCESS not-accessible
	STATUS     current
	DESCRIPTION 
		"This table contains daily energy log of generator."
	::= { generatorEnergyLog 5 }

generatorEnergyLogLastDaysEntry  OBJECT-TYPE
	SYNTAX 	GeneratorEnergyLogLastDaysEntry
	MAX-ACCESS not-accessible
	STATUS     current
	DESCRIPTION 
		""
	INDEX { generatorEnergyLogLastDaysIndex }
	::= { generatorEnergyLogLastDaysTable 1 }

GeneratorEnergyLogLastDaysEntry ::= SEQUENCE {
	generatorEnergyLogLastDaysIndex
		Integer32,
	generatorEnergyLogLastDaysValue
		Integer32
}

generatorEnergyLogLastDaysIndex  OBJECT-TYPE
	SYNTAX     Integer32 (1..52)
	MAX-ACCESS not-accessible
	STATUS     current
	DESCRIPTION 
		"Index used for navigating the rows 1..52  of generatorEnergyLogLastDaysTable"
	::= { generatorEnergyLogLastDaysEntry 1 }

generatorEnergyLogLastDaysValue  OBJECT-TYPE
	SYNTAX     Integer32
	MAX-ACCESS read-only
	STATUS     current
	DESCRIPTION 
		"Energy value logged every day"
	::= { generatorEnergyLogLastDaysEntry 2 }

generatorEnergyLogLastWeeksNumberOfEntries  OBJECT-TYPE
	SYNTAX     Integer32 (0..52)
	MAX-ACCESS read-only
	STATUS     current
	DESCRIPTION 
		"This is the maximal number of entries stored in generator weekly energy log."
	::= { generatorEnergyLog 6 }

generatorEnergyLogLastWeeksTable  OBJECT-TYPE
	SYNTAX SEQUENCE OF GeneratorEnergyLogLastWeeksEntry
	MAX-ACCESS not-accessible
	STATUS     current
	DESCRIPTION 
		"This table contains weekly energy log of generator."
	::= { generatorEnergyLog 7 }

generatorEnergyLogLastWeeksEntry  OBJECT-TYPE
	SYNTAX 	GeneratorEnergyLogLastWeeksEntry
	MAX-ACCESS not-accessible
	STATUS     current
	DESCRIPTION 
		""
	INDEX { generatorEnergyLogLastWeeksIndex }
	::= { generatorEnergyLogLastWeeksTable 1 }

GeneratorEnergyLogLastWeeksEntry ::= SEQUENCE {
	generatorEnergyLogLastWeeksIndex
		Integer32,
	generatorEnergyLogLastWeeksValue
		Integer32
}

generatorEnergyLogLastWeeksIndex  OBJECT-TYPE
	SYNTAX     Integer32 (1..52)
	MAX-ACCESS not-accessible
	STATUS     current
	DESCRIPTION 
		"Index used for navigating the rows 1..52  of generatorEnergyLogLastWeeksTable"
	::= { generatorEnergyLogLastWeeksEntry 1 }

generatorEnergyLogLastWeeksValue  OBJECT-TYPE
	SYNTAX     Integer32
	MAX-ACCESS read-only
	STATUS     current
	DESCRIPTION 
		"Energy value logged every week."
	::= { generatorEnergyLogLastWeeksEntry 2 }

generatorRunHoursTotalHours  OBJECT-TYPE
	SYNTAX     Integer32
	MAX-ACCESS read-only
	STATUS     current
	DESCRIPTION 
		"This is the total generator running hours."
	::= { generatorRunHoursLog 1 }

generatorRunHoursLogLastDaysNumberOfEntries  OBJECT-TYPE
	SYNTAX     Integer32 (0..52)
	MAX-ACCESS read-only
	STATUS     current
	DESCRIPTION 
		"This is the maximal number of entries stored in generator daily running hours log."
	::= { generatorRunHoursLog 2 }

generatorRunHoursLogLastDaysTable  OBJECT-TYPE
	SYNTAX SEQUENCE OF GeneratorRunHoursLogLastDaysEntry
	MAX-ACCESS not-accessible
	STATUS     current
	DESCRIPTION 
		"generator running time in minutes"
	::= { generatorRunHoursLog 3 }

generatorRunHoursLogLastDaysEntry  OBJECT-TYPE
	SYNTAX 	GeneratorRunHoursLogLastDaysEntry
	MAX-ACCESS not-accessible
	STATUS     current
	DESCRIPTION 
		""
	INDEX { generatorRunHoursLogLastDaysIndex }
	::= { generatorRunHoursLogLastDaysTable 1 }

GeneratorRunHoursLogLastDaysEntry ::= SEQUENCE {
	generatorRunHoursLogLastDaysIndex
		Integer32,
	generatorRunHoursLogLastDaysValue
		Integer32
}

generatorRunHoursLogLastDaysIndex  OBJECT-TYPE
	SYNTAX     Integer32 (1..52)
	MAX-ACCESS not-accessible
	STATUS     current
	DESCRIPTION 
		"Index used for navigating the rows 1..52  of generatorRunHoursLogLastDaysTable"
	::= { generatorRunHoursLogLastDaysEntry 1 }

generatorRunHoursLogLastDaysValue  OBJECT-TYPE
	SYNTAX     Integer32
	MAX-ACCESS read-only
	STATUS     current
	DESCRIPTION 
		"Generator running time in minutes, logged every day."
	::= { generatorRunHoursLogLastDaysEntry 2 }

generatorRunHoursLogLastWeeksNumberOfEntries  OBJECT-TYPE
	SYNTAX     Integer32 (0..52)
	MAX-ACCESS read-only
	STATUS     current
	DESCRIPTION 
		"This is the maximal number of entries stored in generator weekly running hours log."
	::= { generatorRunHoursLog 4 }

generatorRunHoursLogLastWeeksTable  OBJECT-TYPE
	SYNTAX SEQUENCE OF GeneratorRunHoursLogLastWeeksEntry
	MAX-ACCESS not-accessible
	STATUS     current
	DESCRIPTION 
		"generator running time in hours"
	::= { generatorRunHoursLog 5 }

generatorRunHoursLogLastWeeksEntry  OBJECT-TYPE
	SYNTAX 	GeneratorRunHoursLogLastWeeksEntry
	MAX-ACCESS not-accessible
	STATUS     current
	DESCRIPTION 
		""
	INDEX { generatorRunHoursLogLastWeeksIndex }
	::= { generatorRunHoursLogLastWeeksTable 1 }

GeneratorRunHoursLogLastWeeksEntry ::= SEQUENCE {
	generatorRunHoursLogLastWeeksIndex
		Integer32,
	generatorRunHoursLogLastWeeksValue
		Integer32
}

generatorRunHoursLogLastWeeksIndex  OBJECT-TYPE
	SYNTAX     Integer32 (1..52)
	MAX-ACCESS not-accessible
	STATUS     current
	DESCRIPTION 
		"Index used for navigating the rows 1..52  of generatorRunHoursLogLastWeeksTable"
	::= { generatorRunHoursLogLastWeeksEntry 1 }

generatorRunHoursLogLastWeeksValue  OBJECT-TYPE
	SYNTAX     Integer32
	MAX-ACCESS read-only
	STATUS     current
	DESCRIPTION 
		"Generator running time in hours, logged every week."
	::= { generatorRunHoursLogLastWeeksEntry 2 }

generatorRunHoursLogLastMonthsNumberOfEntries  OBJECT-TYPE
	SYNTAX     Integer32 (0..52)
	MAX-ACCESS read-only
	STATUS     current
	DESCRIPTION 
		"This is the maximal number of entries stored in generator monthly running hours log."
	::= { generatorRunHoursLog 6 }

generatorRunHoursLogLastMonthsTable  OBJECT-TYPE
	SYNTAX SEQUENCE OF GeneratorRunHoursLogLastMonthsEntry
	MAX-ACCESS not-accessible
	STATUS     current
	DESCRIPTION 
		"generator running time in hours"
	::= { generatorRunHoursLog 7 }

generatorRunHoursLogLastMonthsEntry  OBJECT-TYPE
	SYNTAX 	GeneratorRunHoursLogLastMonthsEntry
	MAX-ACCESS not-accessible
	STATUS     current
	DESCRIPTION 
		""
	INDEX { generatorRunHoursLogLastMonthsIndex }
	::= { generatorRunHoursLogLastMonthsTable 1 }

GeneratorRunHoursLogLastMonthsEntry ::= SEQUENCE {
	generatorRunHoursLogLastMonthsIndex
		Integer32,
	generatorRunHoursLogLastMonthsValue
		Integer32
}

generatorRunHoursLogLastMonthsIndex  OBJECT-TYPE
	SYNTAX     Integer32 (1..52)
	MAX-ACCESS not-accessible
	STATUS     current
	DESCRIPTION 
		"Index used for navigating the rows 1..52  of generatorRunHoursLogLastMonthsTable"
	::= { generatorRunHoursLogLastMonthsEntry 1 }

generatorRunHoursLogLastMonthsValue  OBJECT-TYPE
	SYNTAX     Integer32
	MAX-ACCESS read-only
	STATUS     current
	DESCRIPTION 
		"Generator running time in hours, logged every month."
	::= { generatorRunHoursLogLastMonthsEntry 2 }

generatorFuelConsumptionTotalUsedTable  OBJECT-TYPE
	SYNTAX SEQUENCE OF GeneratorFuelConsumptionTotalUsedEntry
	MAX-ACCESS not-accessible
	STATUS     current
	DESCRIPTION 
		"This table contains total fuel consumption for each tank."
	::= { generatorFuelConsumptionLog 1 }

generatorFuelConsumptionTotalUsedEntry  OBJECT-TYPE
	SYNTAX 	GeneratorFuelConsumptionTotalUsedEntry
	MAX-ACCESS not-accessible
	STATUS     current
	DESCRIPTION 
		""
	INDEX { generatorTankIndex }
	::= { generatorFuelConsumptionTotalUsedTable 1 }

GeneratorFuelConsumptionTotalUsedEntry ::= SEQUENCE {
	generatorFuelConsumptionTotalUsed
		Integer32
}

generatorFuelConsumptionTotalUsed  OBJECT-TYPE
	SYNTAX     Integer32
	MAX-ACCESS read-only
	STATUS     current
	DESCRIPTION 
		"Total fuel consumption value."
	::= { generatorFuelConsumptionTotalUsedEntry 1 }

generatorFuelConsumptionLogLastHoursNoOfEntries  OBJECT-TYPE
	SYNTAX     Integer32 (0..52)
	MAX-ACCESS read-only
	STATUS     current
	DESCRIPTION 
		"This is the maximal number of entries stored in generator hourly fuel consumption log."
	::= { generatorFuelConsumptionLog 2 }

generatorFuelConsumptionLogLastHoursTable  OBJECT-TYPE
	SYNTAX SEQUENCE OF GeneratorFuelConsumptionLogLastHoursEntry
	MAX-ACCESS not-accessible
	STATUS     current
	DESCRIPTION 
		"This table contains generator hourly fuel consumption log."
	::= { generatorFuelConsumptionLog 3 }

generatorFuelConsumptionLogLastHoursEntry  OBJECT-TYPE
	SYNTAX 	GeneratorFuelConsumptionLogLastHoursEntry
	MAX-ACCESS not-accessible
	STATUS     current
	DESCRIPTION 
		""
	INDEX { generatorTankIndex, 
		generatorFuelConsumptionLogLastHoursIndex }
	::= { generatorFuelConsumptionLogLastHoursTable 1 }

GeneratorFuelConsumptionLogLastHoursEntry ::= SEQUENCE {
	generatorFuelConsumptionLogLastHoursIndex
		Integer32,
	generatorFuelConsumptionLogLastHoursValue
		Integer32
}

generatorFuelConsumptionLogLastHoursIndex  OBJECT-TYPE
	SYNTAX     Integer32 (1..52)
	MAX-ACCESS not-accessible
	STATUS     current
	DESCRIPTION 
		"Index used for navigating the rows 1..52  of generatorFuelConsumptionLogLastHoursTable"
	::= { generatorFuelConsumptionLogLastHoursEntry 1 }

generatorFuelConsumptionLogLastHoursValue  OBJECT-TYPE
	SYNTAX     Integer32
	MAX-ACCESS read-only
	STATUS     current
	DESCRIPTION 
		"Generator fuel consumption value, logged every hour."
	::= { generatorFuelConsumptionLogLastHoursEntry 2 }

generatorFuelConsumptionLogLastDaysNoOfEntries  OBJECT-TYPE
	SYNTAX     Integer32 (0..52)
	MAX-ACCESS read-only
	STATUS     current
	DESCRIPTION 
		"This is the maximal number of entries stored in generator daily fuel consumption log."
	::= { generatorFuelConsumptionLog 4 }

generatorFuelConsumptionLogLastDaysTable  OBJECT-TYPE
	SYNTAX SEQUENCE OF GeneratorFuelConsumptionLogLastDaysEntry
	MAX-ACCESS not-accessible
	STATUS     current
	DESCRIPTION 
		"This table contains generator daily fuel consumption log."
	::= { generatorFuelConsumptionLog 5 }

generatorFuelConsumptionLogLastDaysEntry  OBJECT-TYPE
	SYNTAX 	GeneratorFuelConsumptionLogLastDaysEntry
	MAX-ACCESS not-accessible
	STATUS     current
	DESCRIPTION 
		""
	INDEX { generatorTankIndex, 
		generatorFuelConsumptionLogLastDaysIndex }
	::= { generatorFuelConsumptionLogLastDaysTable 1 }

GeneratorFuelConsumptionLogLastDaysEntry ::= SEQUENCE {
	generatorFuelConsumptionLogLastDaysIndex
		Integer32,
	generatorFuelConsumptionLogLastDaysValue
		Integer32
}

generatorFuelConsumptionLogLastDaysIndex  OBJECT-TYPE
	SYNTAX     Integer32 (1..52)
	MAX-ACCESS not-accessible
	STATUS     current
	DESCRIPTION 
		"Index used for navigating the rows 1..52  of generatorFuelConsumptionLogLastDaysTable"
	::= { generatorFuelConsumptionLogLastDaysEntry 1 }

generatorFuelConsumptionLogLastDaysValue  OBJECT-TYPE
	SYNTAX     Integer32
	MAX-ACCESS read-only
	STATUS     current
	DESCRIPTION 
		"Generator fuel consumption value, logged every day."
	::= { generatorFuelConsumptionLogLastDaysEntry 2 }

generatorFuelConsumptionLogLastWeeksNoOfEntries  OBJECT-TYPE
	SYNTAX     Integer32 (0..52)
	MAX-ACCESS read-only
	STATUS     current
	DESCRIPTION 
		"This is the maximal number of entries stored in generator weekly fuel consumption log."
	::= { generatorFuelConsumptionLog 6 }

generatorFuelConsumptionLogLastWeeksTable  OBJECT-TYPE
	SYNTAX SEQUENCE OF GeneratorFuelConsumptionLogLastWeeksEntry
	MAX-ACCESS not-accessible
	STATUS     current
	DESCRIPTION 
		"This table contains generator weekly fuel consumption log."
	::= { generatorFuelConsumptionLog 7 }

generatorFuelConsumptionLogLastWeeksEntry  OBJECT-TYPE
	SYNTAX 	GeneratorFuelConsumptionLogLastWeeksEntry
	MAX-ACCESS not-accessible
	STATUS     current
	DESCRIPTION 
		""
	INDEX { generatorTankIndex, 
		generatorFuelConsumptionLogLastWeeksIndex }
	::= { generatorFuelConsumptionLogLastWeeksTable 1 }

GeneratorFuelConsumptionLogLastWeeksEntry ::= SEQUENCE {
	generatorFuelConsumptionLogLastWeeksIndex
		Integer32,
	generatorFuelConsumptionLogLastWeeksValue
		Integer32
}

generatorFuelConsumptionLogLastWeeksIndex  OBJECT-TYPE
	SYNTAX     Integer32 (1..52)
	MAX-ACCESS not-accessible
	STATUS     current
	DESCRIPTION 
		"Index used for navigating the rows 1..52  of generatorFuelConsumptionLogLastWeeksTable"
	::= { generatorFuelConsumptionLogLastWeeksEntry 1 }

generatorFuelConsumptionLogLastWeeksValue  OBJECT-TYPE
	SYNTAX     Integer32
	MAX-ACCESS read-only
	STATUS     current
	DESCRIPTION 
		"Generator fuel consumption value, logged every week."
	::= { generatorFuelConsumptionLogLastWeeksEntry 2 }

rectifiersStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of rectifier subsystem."
	::= { rectifiers 1 }

rectifiersCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total rectifier current."
	::= { rectifiersCurrent 1 }

rectifiersCurrentDescription  OBJECT-TYPE
	SYNTAX     DisplayString (SIZE(0..16))
	MAX-ACCESS read-write
	STATUS     current
	DESCRIPTION 
		"A textual description of the total rectifier current monitor. This is stored in the system controller
		and can be changed by the user"
	::= { rectifiersCurrent 2 }

rectifiersCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifiersCurrent 3 }

rectifiersCurrentAlarmEnable  OBJECT-TYPE
	SYNTAX     INTEGER {
		disabled (0),
		enabled (1)
	}
	MAX-ACCESS read-write
	STATUS     current
	DESCRIPTION 
		"This value once enabled, the alarm condition of the monitor will be reported."
	::= { rectifiersCurrent 4 }

rectifiersCurrentValue  OBJECT-TYPE
	SYNTAX     Integer32
	MAX-ACCESS read-only
	STATUS     current
	DESCRIPTION 
		"The value of the measured total rectifier current."
	::= { rectifiersCurrent 5 }

rectifiersCurrentMajorAlarmLevel  OBJECT-TYPE
	SYNTAX     Integer32
	MAX-ACCESS read-write
	STATUS     current
	DESCRIPTION 
		"The major alarm limit"
	::= { rectifiersCurrent 6 }

rectifiersCurrentMinorAlarmLevel  OBJECT-TYPE
	SYNTAX     Integer32
	MAX-ACCESS read-write
	STATUS     current
	DESCRIPTION 
		"The minor alarm limit"
	::= { rectifiersCurrent 7 }

rectifiersCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured used rectifier capacity."
	::= { rectifiersCapacity 1 }

rectifiersCapacityDescription  OBJECT-TYPE
	SYNTAX     DisplayString (SIZE(0..16))
	MAX-ACCESS read-write
	STATUS     current
	DESCRIPTION 
		"A textual description of the used rectifier capacity monitor. This is stored in the system controller
		and can be changed by the user"
	::= { rectifiersCapacity 2 }

rectifiersCapacityTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifiersCapacity 3 }

rectifiersCapacityAlarmEnable  OBJECT-TYPE
	SYNTAX     INTEGER {
		disabled (0),
		enabled (1)
	}
	MAX-ACCESS read-write
	STATUS     current
	DESCRIPTION 
		"This value once enabled, the alarm condition of the monitor will be reported."
	::= { rectifiersCapacity 4 }

rectifiersCapacityValue  OBJECT-TYPE
	SYNTAX     Integer32
	MAX-ACCESS read-only
	STATUS     current
	DESCRIPTION 
		"The used rectifier capacity value presented in percentage of the total installed rectifier capacity."
	::= { rectifiersCapacity 5 }

rectifiersCapacityMajorAlarmLevel  OBJECT-TYPE
	SYNTAX     Integer32
	MAX-ACCESS read-write
	STATUS     current
	DESCRIPTION 
		"The major alarm limit"
	::= { rectifiersCapacity 6 }

rectifiersCapacityMinorAlarmLevel  OBJECT-TYPE
	SYNTAX     Integer32
	MAX-ACCESS read-write
	STATUS     current
	DESCRIPTION 
		"The minor alarm limit"
	::= { rectifiersCapacity 7 }

rectifiersErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { rectifiersError 1 }

rectifiersErrorDescription  OBJECT-TYPE
	SYNTAX     DisplayString (SIZE(0..16))
	MAX-ACCESS read-write
	STATUS     current
	DESCRIPTION 
		"A textual description of the rectifier error monitor. This is stored in the system controller
		and can be changed by the user"
	::= { rectifiersError 2 }

rectifiersErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { rectifiersError 3 }

rectifiersErrorEnable  OBJECT-TYPE
	SYNTAX     INTEGER {
		disabled (0),
		enabled (1)
	}
	MAX-ACCESS read-write
	STATUS     current
	DESCRIPTION 
		"This value once enabled, the alarm condition of the monitor will be reported."
	::= { rectifiersError 4 }

rectifiersErrorValue  OBJECT-TYPE
	SYNTAX     Integer32
	MAX-ACCESS read-only
	STATUS     current
	DESCRIPTION 
		"The number of failed rectifiers."
	::= { rectifiersError 5 }

rectifiersErrorMajorAlarmLevel  OBJECT-TYPE
	SYNTAX     Integer32
	MAX-ACCESS read-write
	STATUS     current
	DESCRIPTION 
		"The major alarm limit"
	::= { rectifiersError 6 }

rectifiersErrorMinorAlarmLevel  OBJECT-TYPE
	SYNTAX     Integer32
	MAX-ACCESS read-write
	STATUS     current
	DESCRIPTION 
		"The minor alarm limit"
	::= { rectifiersError 7 }

rectifiersNumberOfRectifiers  OBJECT-TYPE
	SYNTAX     Integer32 (0..100)
	MAX-ACCESS read-write
	STATUS     current
	DESCRIPTION 
		"Number of installed rectifiers."
	::= { rectifiers 5 }

rectifierTable  OBJECT-TYPE
	SYNTAX SEQUENCE OF RectifierEntry
	MAX-ACCESS not-accessible
	STATUS     current
	DESCRIPTION 
		"This table shows the information of each rectifier installed in the system."
	::= { rectifiers 6 }

rectifierEntry  OBJECT-TYPE
	SYNTAX 	RectifierEntry
	MAX-ACCESS not-accessible
	STATUS     current
	DESCRIPTION 
		""
	INDEX { rectifierIndex }
	::= { rectifierTable 1 }

RectifierEntry ::= SEQUENCE {
	rectifierIndex
		Integer32,
	rectifierStatus
		INTEGER,
	rectifierOutputCurrentValue
		Integer32,
	rectifierInputVoltageValue
		Integer32,
	rectifierType
		DisplayString,
	rectifierHwPartNumber
		DisplayString,
	rectifierHwVersion
		DisplayString,
	rectifierSwPartNumber
		DisplayString,
	rectifierSwVersion
		DisplayString
}

rectifierIndex  OBJECT-TYPE
	SYNTAX     Integer32 (1..100)
	MAX-ACCESS not-accessible
	STATUS     current
	DESCRIPTION 
		"Index used for navigating the rows 1..100  of rectifierTable"
	::= { rectifierEntry 1 }

rectifierStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of rectifier."
	::= { rectifierEntry 2 }

rectifierOutputCurrentValue  OBJECT-TYPE
	SYNTAX     Integer32
	MAX-ACCESS read-only
	STATUS     current
	DESCRIPTION 
		"The output current value of rectifier."
	::= { rectifierEntry 3 }

rectifierInputVoltageValue  OBJECT-TYPE
	SYNTAX     Integer32
	MAX-ACCESS read-only
	STATUS     current
	DESCRIPTION 
		"The input voltage value of rectifier."
	::= { rectifierEntry 4 }

rectifierType  OBJECT-TYPE
	SYNTAX     DisplayString (SIZE(0..27))
	MAX-ACCESS read-only
	STATUS     current
	DESCRIPTION 
		"Type of rectifier"
	::= { rectifierEntry 5 }

rectifierHwPartNumber  OBJECT-TYPE
	SYNTAX     DisplayString (SIZE(0..12))
	MAX-ACCESS read-only
	STATUS     current
	DESCRIPTION 
		"Hardware part number of rectifier"
	::= { rectifierEntry 6 }

rectifierHwVersion  OBJECT-TYPE
	SYNTAX     DisplayString (SIZE(0..6))
	MAX-ACCESS read-only
	STATUS     current
	DESCRIPTION 
		"Hardware version number of rectifier"
	::= { rectifierEntry 7 }

rectifierSwPartNumber  OBJECT-TYPE
	SYNTAX     DisplayString (SIZE(0..12))
	MAX-ACCESS read-only
	STATUS     current
	DESCRIPTION 
		"Part number of secondary software in rectifier"
	::= { rectifierEntry 8 }

rectifierSwVersion  OBJECT-TYPE
	SYNTAX     DisplayString (SIZE(0..6))
	MAX-ACCESS read-only
	STATUS     current
	DESCRIPTION 
		"Version number of secondary software in rectifier"
	::= { rectifierEntry 9 }

rectifiersEnergyLogAccumulated  OBJECT-TYPE
	SYNTAX     Integer32
	MAX-ACCESS read-only
	STATUS     current
	DESCRIPTION 
		"This is the accumulated energy delivered from rectifiers."
	::= { rectifiersEnergyLog 1 }

rectifiersEnergyLogLastHoursNumberOfEntries  OBJECT-TYPE
	SYNTAX     Integer32 (0..52)
	MAX-ACCESS read-only
	STATUS     current
	DESCRIPTION 
		"This is the maximal number of entries stored in rectifier hourly energy log."
	::= { rectifiersEnergyLog 2 }

rectifiersEnergyLogLastHoursTable  OBJECT-TYPE
	SYNTAX SEQUENCE OF RectifiersEnergyLogLastHoursEntry
	MAX-ACCESS not-accessible
	STATUS     current
	DESCRIPTION 
		"This table contains hourly energy log of rectifiers."
	::= { rectifiersEnergyLog 3 }

rectifiersEnergyLogLastHoursEntry  OBJECT-TYPE
	SYNTAX 	RectifiersEnergyLogLastHoursEntry
	MAX-ACCESS not-accessible
	STATUS     current
	DESCRIPTION 
		""
	INDEX { rectifiersEnergyLogLastHoursIndex }
	::= { rectifiersEnergyLogLastHoursTable 1 }

RectifiersEnergyLogLastHoursEntry ::= SEQUENCE {
	rectifiersEnergyLogLastHoursIndex
		Integer32,
	rectifiersEnergyLogLastHoursValue
		Integer32
}

rectifiersEnergyLogLastHoursIndex  OBJECT-TYPE
	SYNTAX     Integer32 (1..52)
	MAX-ACCESS not-accessible
	STATUS     current
	DESCRIPTION 
		"Index used for navigating the rows 1..52  of rectifiersEnergyLogLastHoursTable"
	::= { rectifiersEnergyLogLastHoursEntry 1 }

rectifiersEnergyLogLastHoursValue  OBJECT-TYPE
	SYNTAX     Integer32
	MAX-ACCESS read-only
	STATUS     current
	DESCRIPTION 
		"Energy value logged every hour."
	::= { rectifiersEnergyLogLastHoursEntry 2 }

rectifiersEnergyLogLastDaysNumberOfEntries  OBJECT-TYPE
	SYNTAX     Integer32 (0..52)
	MAX-ACCESS read-only
	STATUS     current
	DESCRIPTION 
		"This is the maximal number of entries stored in rectifier daily energy log."
	::= { rectifiersEnergyLog 4 }

rectifiersEnergyLogLastDaysTable  OBJECT-TYPE
	SYNTAX SEQUENCE OF RectifiersEnergyLogLastDaysEntry
	MAX-ACCESS not-accessible
	STATUS     current
	DESCRIPTION 
		"This table contains daily energy log of rectifiers."
	::= { rectifiersEnergyLog 5 }

rectifiersEnergyLogLastDaysEntry  OBJECT-TYPE
	SYNTAX 	RectifiersEnergyLogLastDaysEntry
	MAX-ACCESS not-accessible
	STATUS     current
	DESCRIPTION 
		""
	INDEX { rectifiersEnergyLogLastDaysIndex }
	::= { rectifiersEnergyLogLastDaysTable 1 }

RectifiersEnergyLogLastDaysEntry ::= SEQUENCE {
	rectifiersEnergyLogLastDaysIndex
		Integer32,
	rectifiersEnergyLogLastDaysValue
		Integer32
}

rectifiersEnergyLogLastDaysIndex  OBJECT-TYPE
	SYNTAX     Integer32 (1..52)
	MAX-ACCESS not-accessible
	STATUS     current
	DESCRIPTION 
		"Index used for navigating the rows 1..52  of rectifiersEnergyLogLastDaysTable"
	::= { rectifiersEnergyLogLastDaysEntry 1 }

rectifiersEnergyLogLastDaysValue  OBJECT-TYPE
	SYNTAX     Integer32
	MAX-ACCESS read-only
	STATUS     current
	DESCRIPTION 
		"Energy value logged every day."
	::= { rectifiersEnergyLogLastDaysEntry 2 }

rectifiersEnergyLogLastWeeksNumberOfEntries  OBJECT-TYPE
	SYNTAX     Integer32 (0..52)
	MAX-ACCESS read-only
	STATUS     current
	DESCRIPTION 
		"This is the maximal number of entries stored in rectifier weekly energy log."
	::= { rectifiersEnergyLog 6 }

rectifiersEnergyLogLastWeeksTable  OBJECT-TYPE
	SYNTAX SEQUENCE OF RectifiersEnergyLogLastWeeksEntry
	MAX-ACCESS not-accessible
	STATUS     current
	DESCRIPTION 
		"This table contains weekly energy log of rectifiers."
	::= { rectifiersEnergyLog 7 }

rectifiersEnergyLogLastWeeksEntry  OBJECT-TYPE
	SYNTAX 	RectifiersEnergyLogLastWeeksEntry
	MAX-ACCESS not-accessible
	STATUS     current
	DESCRIPTION 
		""
	INDEX { rectifiersEnergyLogLastWeeksIndex }
	::= { rectifiersEnergyLogLastWeeksTable 1 }

RectifiersEnergyLogLastWeeksEntry ::= SEQUENCE {
	rectifiersEnergyLogLastWeeksIndex
		Integer32,
	rectifiersEnergyLogLastWeeksValue
		Integer32
}

rectifiersEnergyLogLastWeeksIndex  OBJECT-TYPE
	SYNTAX     Integer32 (1..52)
	MAX-ACCESS not-accessible
	STATUS     current
	DESCRIPTION 
		"Index used for navigating the rows 1..52  of rectifiersEnergyLogLastWeekTable"
	::= { rectifiersEnergyLogLastWeeksEntry 1 }

rectifiersEnergyLogLastWeeksValue  OBJECT-TYPE
	SYNTAX     Integer32
	MAX-ACCESS read-only
	STATUS     current
	DESCRIPTION 
		"Energy value logged every week."
	::= { rectifiersEnergyLogLastWeeksEntry 2 }

dcdcNumberOfGroups  OBJECT-TYPE
	SYNTAX     Integer32 (0..5)
	MAX-ACCESS read-only
	STATUS     current
	DESCRIPTION 
		"Number of dcdc groups"
	::= { dcdc 1 }

dcdcGroupsTable  OBJECT-TYPE
	SYNTAX SEQUENCE OF DcdcGroupsEntry
	MAX-ACCESS not-accessible
	STATUS     current
	DESCRIPTION 
		"This table contains information about dcdc groups."
	::= { dcdc 2 }

dcdcGroupsEntry  OBJECT-TYPE
	SYNTAX 	DcdcGroupsEntry
	MAX-ACCESS not-accessible
	STATUS     current
	DESCRIPTION 
		""
	INDEX { dcdcGroupIndex }
	::= { dcdcGroupsTable 1 }

DcdcGroupsEntry ::= SEQUENCE {
	dcdcGroupIndex
		Integer32,
	dcdcGroupStatus
		INTEGER,
	dcdcGroupNumberOfDcdcConverters
		Integer32,
	dcdcGroupOutputVoltage
		Integer32,
	dcdcNumberOfCurrents
		Integer32,
	dcdcNumberOfCapacities
		Integer32,
	dcdcNumberOfAlarms
		Integer32
}

dcdcGroupIndex  OBJECT-TYPE
	SYNTAX     Integer32 (1..5)
	MAX-ACCESS not-accessible
	STATUS     current
	DESCRIPTION 
		""
	::= { dcdcGroupsEntry 1 }

dcdcGroupStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of dcdc group."
	::= { dcdcGroupsEntry 2 }

dcdcGroupNumberOfDcdcConverters  OBJECT-TYPE
	SYNTAX     Integer32
	MAX-ACCESS read-write
	STATUS     current
	DESCRIPTION 
		"Number of installed dcdc converters."
	::= { dcdcGroupsEntry 3 }

dcdcGroupOutputVoltage  OBJECT-TYPE
	SYNTAX     Integer32
	MAX-ACCESS read-write
	STATUS     current
	DESCRIPTION 
		"Output voltage of dcdc converters"
	::= { dcdcGroupsEntry 4 }

dcdcNumberOfCurrents  OBJECT-TYPE
	SYNTAX     Integer32 (0..5)
	MAX-ACCESS read-only
	STATUS     current
	DESCRIPTION 
		"Number of dcdc currents"
	::= { dcdcGroupsEntry 5 }

dcdcNumberOfCapacities  OBJECT-TYPE
	SYNTAX     Integer32 (0..5)
	MAX-ACCESS read-only
	STATUS     current
	DESCRIPTION 
		"Number of dcdc capacities"
	::= { dcdcGroupsEntry 6 }

dcdcNumberOfAlarms  OBJECT-TYPE
	SYNTAX     Integer32 (0..5)
	MAX-ACCESS read-only
	STATUS     current
	DESCRIPTION 
		"Number of dcdc alarms"
	::= { dcdcGroupsEntry 7 }

dcdcCurrentTable  OBJECT-TYPE
	SYNTAX SEQUENCE OF DcdcCurrentEntry
	MAX-ACCESS not-accessible
	STATUS     current
	DESCRIPTION 
		"This table contains information about the total dcdc current."
	::= { dcdc 3 }

dcdcCurrentEntry  OBJECT-TYPE
	SYNTAX 	DcdcCurrentEntry
	MAX-ACCESS not-accessible
	STATUS     current
	DESCRIPTION 
		""
	INDEX { dcdcGroupIndex }
	::= { dcdcCurrentTable 1 }

DcdcCurrentEntry ::= SEQUENCE {
	dcdcCurrentStatus
		INTEGER,
	dcdcCurrentDescription
		DisplayString,
	dcdcCurrentTrapRepeatCounter
		Counter32,
	dcdcCurrentAlarmEnable
		INTEGER,
	dcdcCurrentValue
		Integer32,
	dcdcCurrentMajorAlarmLevel
		Integer32,
	dcdcCurrentMinorAlarmLevel
		Integer32
}

dcdcCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total dcdc current."
	::= { dcdcCurrentEntry 1 }

dcdcCurrentDescription  OBJECT-TYPE
	SYNTAX     DisplayString (SIZE(0..16))
	MAX-ACCESS read-write
	STATUS     current
	DESCRIPTION 
		"A textual description of the total dcdc current monitor. This is stored in the system controller
		and can be changed by the user"
	::= { dcdcCurrentEntry 2 }

dcdcCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { dcdcCurrentEntry 3 }

dcdcCurrentAlarmEnable  OBJECT-TYPE
	SYNTAX     INTEGER {
		disabled (0),
		enabled (1)
	}
	MAX-ACCESS read-write
	STATUS     current
	DESCRIPTION 
		"This value once enabled, the alarm condition of the monitor will be reported."
	::= { dcdcCurrentEntry 4 }

dcdcCurrentValue  OBJECT-TYPE
	SYNTAX     Integer32
	MAX-ACCESS read-only
	STATUS     current
	DESCRIPTION 
		"The value of the measured total dcdc current."
	::= { dcdcCurrentEntry 5 }

dcdcCurrentMajorAlarmLevel  OBJECT-TYPE
	SYNTAX     Integer32
	MAX-ACCESS read-write
	STATUS     current
	DESCRIPTION 
		"The major alarm limit"
	::= { dcdcCurrentEntry 6 }

dcdcCurrentMinorAlarmLevel  OBJECT-TYPE
	SYNTAX     Integer32
	MAX-ACCESS read-write
	STATUS     current
	DESCRIPTION 
		"The minor alarm limit"
	::= { dcdcCurrentEntry 7 }

dcdcCapacityTable  OBJECT-TYPE
	SYNTAX SEQUENCE OF DcdcCapacityEntry
	MAX-ACCESS not-accessible
	STATUS     current
	DESCRIPTION 
		"This table contains information about the used dcdc capacity."
	::= { dcdc 4 }

dcdcCapacityEntry  OBJECT-TYPE
	SYNTAX 	DcdcCapacityEntry
	MAX-ACCESS not-accessible
	STATUS     current
	DESCRIPTION 
		""
	INDEX { dcdcGroupIndex }
	::= { dcdcCapacityTable 1 }

DcdcCapacityEntry ::= SEQUENCE {
	dcdcCapacityStatus
		INTEGER,
	dcdcCapacityDescription
		DisplayString,
	dcdcCapacityTrapRepeatCounter
		Counter32,
	dcdcCapacityAlarmEnable
		INTEGER,
	dcdcCapacityValue
		Integer32,
	dcdcCapacityMajorAlarmLevel
		Integer32,
	dcdcCapacityMinorAlarmLevel
		Integer32
}

dcdcCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured used dcdc capacity."
	::= { dcdcCapacityEntry 1 }

dcdcCapacityDescription  OBJECT-TYPE
	SYNTAX     DisplayString (SIZE(0..16))
	MAX-ACCESS read-write
	STATUS     current
	DESCRIPTION 
		"A textual description of the used dcdc capacity monitor. This is stored in the system controller
		and can be changed by the user"
	::= { dcdcCapacityEntry 2 }

dcdcCapacityTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes of"
	::= { dcdcCapacityEntry 3 }

dcdcCapacityAlarmEnable  OBJECT-TYPE
	SYNTAX     INTEGER {
		disabled (0),
		enabled (1)
	}
	MAX-ACCESS read-write
	STATUS     current
	DESCRIPTION 
		"This value once enabled, the alarm condition of the monitor will be reported."
	::= { dcdcCapacityEntry 4 }

dcdcCapacityValue  OBJECT-TYPE
	SYNTAX     Integer32
	MAX-ACCESS read-only
	STATUS     current
	DESCRIPTION 
		"The used dcdc capacity value presented in percentage of the total installed dcdc capacity."
	::= { dcdcCapacityEntry 5 }

dcdcCapacityMajorAlarmLevel  OBJECT-TYPE
	SYNTAX     Integer32
	MAX-ACCESS read-write
	STATUS     current
	DESCRIPTION 
		"The major alarm limit"
	::= { dcdcCapacityEntry 6 }

dcdcCapacityMinorAlarmLevel  OBJECT-TYPE
	SYNTAX     Integer32
	MAX-ACCESS read-write
	STATUS     current
	DESCRIPTION 
		"The minor alarm limit"
	::= { dcdcCapacityEntry 7 }

dcdcTable  OBJECT-TYPE
	SYNTAX SEQUENCE OF DcdcEntry
	MAX-ACCESS not-accessible
	STATUS     current
	DESCRIPTION 
		"This table shows the information of each dcdc converter installed in the system."
	::= { dcdc 5 }

dcdcEntry  OBJECT-TYPE
	SYNTAX 	DcdcEntry
	MAX-ACCESS not-accessible
	STATUS     current
	DESCRIPTION 
		""
	INDEX { dcdcGroupIndex, 
		dcdcIndex }
	::= { dcdcTable 1 }

DcdcEntry ::= SEQUENCE {
	dcdcIndex
		Integer32,
	dcdcStatus
		INTEGER,
	dcdcOutputCurrentValue
		Integer32,
	dcdcInputVoltageValue
		Integer32,
	dcdcType
		DisplayString,
	dcdcHwPartNumber
		DisplayString,
	dcdcHwVersion
		DisplayString,
	dcdcSwPartNumber
		DisplayString,
	dcdcSwVersion
		DisplayString
}

-- Index used for navigating the rows 1..100 of dcdcTable

dcdcIndex  OBJECT-TYPE
	SYNTAX     Integer32 (1..100)
	MAX-ACCESS not-accessible
	STATUS     current
	DESCRIPTION 
		"Index used for navigating the rows 1..100  of dcdcTable"
	::= { dcdcEntry 1 }

dcdcStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of dcdc converter"
	::= { dcdcEntry 2 }

dcdcOutputCurrentValue  OBJECT-TYPE
	SYNTAX     Integer32
	MAX-ACCESS read-only
	STATUS     current
	DESCRIPTION 
		"The output current value of dcdc."
	::= { dcdcEntry 3 }

dcdcInputVoltageValue  OBJECT-TYPE
	SYNTAX     Integer32
	MAX-ACCESS read-only
	STATUS     current
	DESCRIPTION 
		"The input voltage value of dcdc."
	::= { dcdcEntry 4 }

dcdcType  OBJECT-TYPE
	SYNTAX     DisplayString (SIZE(0..27))
	MAX-ACCESS read-only
	STATUS     current
	DESCRIPTION 
		"Type of dcdc converter"
	::= { dcdcEntry 5 }

dcdcHwPartNumber  OBJECT-TYPE
	SYNTAX     DisplayString (SIZE(0..12))
	MAX-ACCESS read-only
	STATUS     current
	DESCRIPTION 
		"Hardware part number of dcdc converter"
	::= { dcdcEntry 6 }

dcdcHwVersion  OBJECT-TYPE
	SYNTAX     DisplayString (SIZE(0..6))
	MAX-ACCESS read-only
	STATUS     current
	DESCRIPTION 
		"Hardware version number of dcdc converter"
	::= { dcdcEntry 7 }

dcdcSwPartNumber  OBJECT-TYPE
	SYNTAX     DisplayString (SIZE(0..12))
	MAX-ACCESS read-only
	STATUS     current
	DESCRIPTION 
		"Part number of secondary software in dcdc converter"
	::= { dcdcEntry 8 }

dcdcSwVersion  OBJECT-TYPE
	SYNTAX     DisplayString (SIZE(0..6))
	MAX-ACCESS read-only
	STATUS     current
	DESCRIPTION 
		"Version number of secondary software in dcdc converter"
	::= { dcdcEntry 9 }

dcdcErrorTable  OBJECT-TYPE
	SYNTAX SEQUENCE OF DcdcErrorEntry
	MAX-ACCESS not-accessible
	STATUS     current
	DESCRIPTION 
		"This table contains information about the dcdc error monitor."
	::= { dcdc 6 }

dcdcErrorEntry  OBJECT-TYPE
	SYNTAX 	DcdcErrorEntry
	MAX-ACCESS not-accessible
	STATUS     current
	DESCRIPTION 
		""
	INDEX { dcdcGroupIndex }
	::= { dcdcErrorTable 1 }

DcdcErrorEntry ::= SEQUENCE {
	dcdcErrorStatus
		INTEGER,
	dcdcErrorDescription
		DisplayString,
	dcdcErrorTrapRepeatCounter
		Counter32,
	dcdcErrorEnable
		INTEGER,
	dcdcErrorValue
		Integer32,
	dcdcErrorMajorAlarmLevel
		Integer32,
	dcdcErrorMinorAlarmLevel
		Integer32
}

dcdcErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { dcdcErrorEntry 1 }

dcdcErrorDescription  OBJECT-TYPE
	SYNTAX     DisplayString (SIZE(0..16))
	MAX-ACCESS read-write
	STATUS     current
	DESCRIPTION 
		"A textual description of the dcdc error monitor. This is stored in the system controller
		and can be changed by the user"
	::= { dcdcErrorEntry 2 }

dcdcErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { dcdcErrorEntry 3 }

dcdcErrorEnable  OBJECT-TYPE
	SYNTAX     INTEGER {
		disabled (0),
		enabled (1)
	}
	MAX-ACCESS read-write
	STATUS     current
	DESCRIPTION 
		"This value once enabled, the alarm condition of the monitor will be reported."
	::= { dcdcErrorEntry 4 }

dcdcErrorValue  OBJECT-TYPE
	SYNTAX     Integer32
	MAX-ACCESS read-only
	STATUS     current
	DESCRIPTION 
		"The number of failed dcdc converters."
	::= { dcdcErrorEntry 5 }

dcdcErrorMajorAlarmLevel  OBJECT-TYPE
	SYNTAX     Integer32
	MAX-ACCESS read-write
	STATUS     current
	DESCRIPTION 
		"The major alarm limit"
	::= { dcdcErrorEntry 6 }

dcdcErrorMinorAlarmLevel  OBJECT-TYPE
	SYNTAX     Integer32
	MAX-ACCESS read-write
	STATUS     current
	DESCRIPTION 
		"The minor alarm limit"
	::= { dcdcErrorEntry 7 }

dcdcEnergyLogAccumulatedTable  OBJECT-TYPE
	SYNTAX SEQUENCE OF DcdcEnergyLogAccumulatedEntry
	MAX-ACCESS not-accessible
	STATUS     current
	DESCRIPTION 
		"This is the accumulated energy delivered from dcdc converters."
	::= { dcdcEnergyLog 1 }

dcdcEnergyLogAccumulatedEntry  OBJECT-TYPE
	SYNTAX 	DcdcEnergyLogAccumulatedEntry
	MAX-ACCESS not-accessible
	STATUS     current
	DESCRIPTION 
		""
	INDEX { dcdcGroupIndex }
	::= { dcdcEnergyLogAccumulatedTable 1 }

DcdcEnergyLogAccumulatedEntry ::= SEQUENCE {
	dcdcEnergyLogAccumulated
		Integer32
}

dcdcEnergyLogAccumulated  OBJECT-TYPE
	SYNTAX     Integer32
	MAX-ACCESS read-only
	STATUS     current
	DESCRIPTION 
		"This is the accumulated energy delivered from dcdc converters."
	::= { dcdcEnergyLogAccumulatedEntry 1 }

dcdcEnergyLogLastHoursNumberOfEntries  OBJECT-TYPE
	SYNTAX     Integer32 (0..52)
	MAX-ACCESS read-only
	STATUS     current
	DESCRIPTION 
		"This is the maximal number of entries stored in dcdc hourly energy log."
	::= { dcdcEnergyLog 2 }

dcdcEnergyLogLastHoursTable  OBJECT-TYPE
	SYNTAX SEQUENCE OF DcdcEnergyLogLastHoursEntry
	MAX-ACCESS not-accessible
	STATUS     current
	DESCRIPTION 
		"This table contains hourly energy log of dcdc converters"
	::= { dcdcEnergyLog 3 }

dcdcEnergyLogLastHoursEntry  OBJECT-TYPE
	SYNTAX 	DcdcEnergyLogLastHoursEntry
	MAX-ACCESS not-accessible
	STATUS     current
	DESCRIPTION 
		""
	INDEX { dcdcGroupIndex, 
		dcdcEnergyLogLastHoursIndex }
	::= { dcdcEnergyLogLastHoursTable 1 }

DcdcEnergyLogLastHoursEntry ::= SEQUENCE {
	dcdcEnergyLogLastHoursIndex
		Integer32,
	dcdcEnergyLogLastHoursValue
		Integer32
}

dcdcEnergyLogLastHoursIndex  OBJECT-TYPE
	SYNTAX     Integer32 (1..52)
	MAX-ACCESS not-accessible
	STATUS     current
	DESCRIPTION 
		"Index used for navigating the rows 1..52 of dcdcEnergyLogLastHoursTable"
	::= { dcdcEnergyLogLastHoursEntry 1 }

dcdcEnergyLogLastHoursValue  OBJECT-TYPE
	SYNTAX     Integer32
	MAX-ACCESS read-only
	STATUS     current
	DESCRIPTION 
		"Energy value logged every hour."
	::= { dcdcEnergyLogLastHoursEntry 2 }

dcdcEnergyLogLastDaysNumberOfEntries  OBJECT-TYPE
	SYNTAX     Integer32 (0..52)
	MAX-ACCESS read-only
	STATUS     current
	DESCRIPTION 
		"This is the maximal number of entries stored in dcdc daily energy log."
	::= { dcdcEnergyLog 4 }

dcdcEnergyLogLastDaysTable  OBJECT-TYPE
	SYNTAX SEQUENCE OF DcdcEnergyLogLastDaysEntry
	MAX-ACCESS not-accessible
	STATUS     current
	DESCRIPTION 
		"This table contains daily energy log of dcdc converters."
	::= { dcdcEnergyLog 5 }

dcdcEnergyLogLastDaysEntry  OBJECT-TYPE
	SYNTAX 	DcdcEnergyLogLastDaysEntry
	MAX-ACCESS not-accessible
	STATUS     current
	DESCRIPTION 
		""
	INDEX { dcdcGroupIndex, 
		dcdcEnergyLogLastDaysIndex }
	::= { dcdcEnergyLogLastDaysTable 1 }

DcdcEnergyLogLastDaysEntry ::= SEQUENCE {
	dcdcEnergyLogLastDaysIndex
		Integer32,
	dcdcEnergyLogLastDaysValue
		Integer32
}

dcdcEnergyLogLastDaysIndex  OBJECT-TYPE
	SYNTAX     Integer32 (1..52)
	MAX-ACCESS not-accessible
	STATUS     current
	DESCRIPTION 
		"Index used for navigating the rows 1..52 of dcdcEnergyLogLastDaysTable"
	::= { dcdcEnergyLogLastDaysEntry 1 }

dcdcEnergyLogLastDaysValue  OBJECT-TYPE
	SYNTAX     Integer32
	MAX-ACCESS read-only
	STATUS     current
	DESCRIPTION 
		"Energy value logged every day."
	::= { dcdcEnergyLogLastDaysEntry 2 }

dcdcEnergyLogLastWeeksNumberOfEntries  OBJECT-TYPE
	SYNTAX     Integer32 (0..52)
	MAX-ACCESS read-only
	STATUS     current
	DESCRIPTION 
		"This is the maximal number of entries stored in dcdc weekly energy log."
	::= { dcdcEnergyLog 6 }

dcdcEnergyLogLastWeeksTable  OBJECT-TYPE
	SYNTAX SEQUENCE OF DcdcEnergyLogLastWeeksEntry
	MAX-ACCESS not-accessible
	STATUS     current
	DESCRIPTION 
		"This table contains weekly energy log of dcdc converters."
	::= { dcdcEnergyLog 7 }

dcdcEnergyLogLastWeeksEntry  OBJECT-TYPE
	SYNTAX 	DcdcEnergyLogLastWeeksEntry
	MAX-ACCESS not-accessible
	STATUS     current
	DESCRIPTION 
		""
	INDEX { dcdcGroupIndex, 
		dcdcEnergyLogLastWeeksIndex }
	::= { dcdcEnergyLogLastWeeksTable 1 }

DcdcEnergyLogLastWeeksEntry ::= SEQUENCE {
	dcdcEnergyLogLastWeeksIndex
		Integer32,
	dcdcEnergyLogLastWeeksValue
		Integer32
}

dcdcEnergyLogLastWeeksIndex  OBJECT-TYPE
	SYNTAX     Integer32 (1..52)
	MAX-ACCESS not-accessible
	STATUS     current
	DESCRIPTION 
		"Index used for navigating the rows 1..52 of dcdcEnergyLogLastWeekTable"
	::= { dcdcEnergyLogLastWeeksEntry 1 }

dcdcEnergyLogLastWeeksValue  OBJECT-TYPE
	SYNTAX     Integer32
	MAX-ACCESS read-only
	STATUS     current
	DESCRIPTION 
		"Energy value logged every week."
	::= { dcdcEnergyLogLastWeeksEntry 2 }

solarChargersStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of solar charger subsystem."
	::= { solarChargers 1 }

solarChargersCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total solar current."
	::= { solarChargersCurrent 1 }

solarChargersCurrentDescription  OBJECT-TYPE
	SYNTAX     DisplayString (SIZE(0..16))
	MAX-ACCESS read-write
	STATUS     current
	DESCRIPTION 
		"A textual description of the total solar current monitor. This is stored in the system controller
		and can be changed by the user"
	::= { solarChargersCurrent 2 }

solarChargersCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { solarChargersCurrent 3 }

solarChargersCurrentAlarmEnable  OBJECT-TYPE
	SYNTAX     INTEGER {
		disabled (0),
		enabled (1)
	}
	MAX-ACCESS read-write
	STATUS     current
	DESCRIPTION 
		"This value once enabled, the alarm condition of the monitor will be reported."
	::= { solarChargersCurrent 4 }

solarChargersCurrentValue  OBJECT-TYPE
	SYNTAX     Integer32
	MAX-ACCESS read-only
	STATUS     current
	DESCRIPTION 
		"The value of the measured total solar current."
	::= { solarChargersCurrent 5 }

solarChargersCurrentMajorAlarmLevel  OBJECT-TYPE
	SYNTAX     Integer32
	MAX-ACCESS read-write
	STATUS     current
	DESCRIPTION 
		"The major alarm limit"
	::= { solarChargersCurrent 6 }

solarChargersCurrentMinorAlarmLevel  OBJECT-TYPE
	SYNTAX     Integer32
	MAX-ACCESS read-write
	STATUS     current
	DESCRIPTION 
		"The minor alarm limit"
	::= { solarChargersCurrent 7 }

solarChargersCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured used solar capacity."
	::= { solarChargersCapacity 1 }

solarChargersCapacityDescription  OBJECT-TYPE
	SYNTAX     DisplayString (SIZE(0..16))
	MAX-ACCESS read-write
	STATUS     current
	DESCRIPTION 
		"A textual description of the used solar charger capacity monitor. This is stored in the system controller
		and can be changed by the user"
	::= { solarChargersCapacity 2 }

solarChargersCapacityTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { solarChargersCapacity 3 }

solarChargersCapacityAlarmEnable  OBJECT-TYPE
	SYNTAX     INTEGER {
		disabled (0),
		enabled (1)
	}
	MAX-ACCESS read-write
	STATUS     current
	DESCRIPTION 
		"This value once enabled, the alarm condition of the monitor will be reported."
	::= { solarChargersCapacity 4 }

solarChargersCapacityValue  OBJECT-TYPE
	SYNTAX     Integer32
	MAX-ACCESS read-only
	STATUS     current
	DESCRIPTION 
		"The used solar capacity value presented in percentage of the total installed solar capacity."
	::= { solarChargersCapacity 5 }

solarChargersCapacityMajorAlarmLevel  OBJECT-TYPE
	SYNTAX     Integer32
	MAX-ACCESS read-write
	STATUS     current
	DESCRIPTION 
		"The major alarm limit"
	::= { solarChargersCapacity 6 }

solarChargersCapacityMinorAlarmLevel  OBJECT-TYPE
	SYNTAX     Integer32
	MAX-ACCESS read-write
	STATUS     current
	DESCRIPTION 
		"The minor alarm limit"
	::= { solarChargersCapacity 7 }

solarChargersErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { solarChargersError 1 }

solarChargersErrorDescription  OBJECT-TYPE
	SYNTAX     DisplayString (SIZE(0..16))
	MAX-ACCESS read-write
	STATUS     current
	DESCRIPTION 
		"A textual description of the solar error monitor. This is stored in the system controller
		and can be changed by the user"
	::= { solarChargersError 2 }

solarChargersErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { solarChargersError 3 }

solarChargersErrorEnable  OBJECT-TYPE
	SYNTAX     INTEGER {
		disabled (0),
		enabled (1)
	}
	MAX-ACCESS read-write
	STATUS     current
	DESCRIPTION 
		"This value once enabled, the alarm condition of the monitor will be reported."
	::= { solarChargersError 4 }

solarChargersErrorValue  OBJECT-TYPE
	SYNTAX     Integer32
	MAX-ACCESS read-only
	STATUS     current
	DESCRIPTION 
		"The number of failed solar chargers."
	::= { solarChargersError 5 }

solarChargersErrorMajorAlarmLevel  OBJECT-TYPE
	SYNTAX     Integer32
	MAX-ACCESS read-write
	STATUS     current
	DESCRIPTION 
		"The major alarm limit"
	::= { solarChargersError 6 }

solarChargersErrorMinorAlarmLevel  OBJECT-TYPE
	SYNTAX     Integer32
	MAX-ACCESS read-write
	STATUS     current
	DESCRIPTION 
		"The minor alarm limit"
	::= { solarChargersError 7 }

solarChargersNumberOfSolarChargers  OBJECT-TYPE
	SYNTAX     Integer32 (0..100)
	MAX-ACCESS read-write
	STATUS     current
	DESCRIPTION 
		"Number of installed solar chargers."
	::= { solarChargers 5 }

solarChargerTable  OBJECT-TYPE
	SYNTAX SEQUENCE OF SolarChargerEntry
	MAX-ACCESS not-accessible
	STATUS     current
	DESCRIPTION 
		"This table shows the information of each solar charger installed in the system."
	::= { solarChargers 6 }

solarChargerEntry  OBJECT-TYPE
	SYNTAX 	SolarChargerEntry
	MAX-ACCESS not-accessible
	STATUS     current
	DESCRIPTION 
		""
	INDEX { solarChargerIndex }
	::= { solarChargerTable 1 }

SolarChargerEntry ::= SEQUENCE {
	solarChargerIndex
		Integer32,
	solarChargerStatus
		INTEGER,
	solarChargerOutputCurrentValue
		Integer32,
	solarChargerInputVoltageValue
		Integer32,
	solarChargerType
		DisplayString,
	solarChargerHwPartNumber
		DisplayString,
	solarChargerHwVersion
		DisplayString,
	solarChargerSwPartNumber
		DisplayString,
	solarChargerSwVersion
		DisplayString
}

solarChargerIndex  OBJECT-TYPE
	SYNTAX     Integer32 (1..100)
	MAX-ACCESS not-accessible
	STATUS     current
	DESCRIPTION 
		"Index used for navigating the rows 1..100 of solarChargerTable"
	::= { solarChargerEntry 1 }

solarChargerStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of solar charger."
	::= { solarChargerEntry 2 }

solarChargerOutputCurrentValue  OBJECT-TYPE
	SYNTAX     Integer32
	MAX-ACCESS read-only
	STATUS     current
	DESCRIPTION 
		"The output current value of solar charger."
	::= { solarChargerEntry 3 }

solarChargerInputVoltageValue  OBJECT-TYPE
	SYNTAX     Integer32
	MAX-ACCESS read-only
	STATUS     current
	DESCRIPTION 
		"The input voltage value of solar charger."
	::= { solarChargerEntry 4 }

solarChargerType  OBJECT-TYPE
	SYNTAX     DisplayString (SIZE(0..27))
	MAX-ACCESS read-only
	STATUS     current
	DESCRIPTION 
		"Type of solar charger"
	::= { solarChargerEntry 5 }

solarChargerHwPartNumber  OBJECT-TYPE
	SYNTAX     DisplayString (SIZE(0..12))
	MAX-ACCESS read-only
	STATUS     current
	DESCRIPTION 
		"Hardware part number of solar charger"
	::= { solarChargerEntry 6 }

solarChargerHwVersion  OBJECT-TYPE
	SYNTAX     DisplayString (SIZE(0..6))
	MAX-ACCESS read-only
	STATUS     current
	DESCRIPTION 
		"Hardware version number of solar charger"
	::= { solarChargerEntry 7 }

solarChargerSwPartNumber  OBJECT-TYPE
	SYNTAX     DisplayString (SIZE(0..12))
	MAX-ACCESS read-only
	STATUS     current
	DESCRIPTION 
		"Part number of secondary software in solar charger"
	::= { solarChargerEntry 8 }

solarChargerSwVersion  OBJECT-TYPE
	SYNTAX     DisplayString (SIZE(0..6))
	MAX-ACCESS read-only
	STATUS     current
	DESCRIPTION 
		"Version number of secondary software in solar charger"
	::= { solarChargerEntry 9 }

solarChargersEnergyLogAccumulated  OBJECT-TYPE
	SYNTAX     Integer32
	MAX-ACCESS read-only
	STATUS     current
	DESCRIPTION 
		"This is the accumulated energy delivered from solar chargers."
	::= { solarChargersEnergyLog 1 }

solarChargersEnergyLogLastHoursNumberOfEntries  OBJECT-TYPE
	SYNTAX     Integer32
	MAX-ACCESS read-only
	STATUS     current
	DESCRIPTION 
		"This is the maximal number of entries stored in solar charger hourly energy log."
	::= { solarChargersEnergyLog 2 }

solarChargersEnergyLogLastHoursTable  OBJECT-TYPE
	SYNTAX SEQUENCE OF SolarChargersEnergyLogLastHoursEntry
	MAX-ACCESS not-accessible
	STATUS     current
	DESCRIPTION 
		"This table contains hourly energy log of solar chargers."
	::= { solarChargersEnergyLog 3 }

solarChargersEnergyLogLastHoursEntry  OBJECT-TYPE
	SYNTAX 	SolarChargersEnergyLogLastHoursEntry
	MAX-ACCESS not-accessible
	STATUS     current
	DESCRIPTION 
		""
	INDEX { solarChargersEnergyLogLastHoursIndex }
	::= { solarChargersEnergyLogLastHoursTable 1 }

SolarChargersEnergyLogLastHoursEntry ::= SEQUENCE {
	solarChargersEnergyLogLastHoursIndex
		Integer32,
	solarChargersEnergyLogLastHoursValue
		Integer32
}

solarChargersEnergyLogLastHoursIndex  OBJECT-TYPE
	SYNTAX     Integer32 (1..52)
	MAX-ACCESS not-accessible
	STATUS     current
	DESCRIPTION 
		"Index used for navigating the rows 1..52 of solarChargersEnergyLogLastHoursTable"
	::= { solarChargersEnergyLogLastHoursEntry 1 }

solarChargersEnergyLogLastHoursValue  OBJECT-TYPE
	SYNTAX     Integer32
	MAX-ACCESS read-only
	STATUS     current
	DESCRIPTION 
		"Energy value logged every hour."
	::= { solarChargersEnergyLogLastHoursEntry 2 }

solarChargersEnergyLogLastDaysNumberOfEntries  OBJECT-TYPE
	SYNTAX     Integer32
	MAX-ACCESS read-only
	STATUS     current
	DESCRIPTION 
		"This is the maximal number of entries stored in solar charger daily energy log."
	::= { solarChargersEnergyLog 4 }

solarChargersEnergyLogLastDaysTable  OBJECT-TYPE
	SYNTAX SEQUENCE OF SolarChargersEnergyLogLastDaysEntry
	MAX-ACCESS not-accessible
	STATUS     current
	DESCRIPTION 
		"This table contains daily energy log of solar chargers."
	::= { solarChargersEnergyLog 5 }

solarChargersEnergyLogLastDaysEntry  OBJECT-TYPE
	SYNTAX 	SolarChargersEnergyLogLastDaysEntry
	MAX-ACCESS not-accessible
	STATUS     current
	DESCRIPTION 
		""
	INDEX { solarChargersEnergyLogLastDaysIndex }
	::= { solarChargersEnergyLogLastDaysTable 1 }

SolarChargersEnergyLogLastDaysEntry ::= SEQUENCE {
	solarChargersEnergyLogLastDaysIndex
		Integer32,
	solarChargersEnergyLogLastDaysValue
		Integer32
}

solarChargersEnergyLogLastDaysIndex  OBJECT-TYPE
	SYNTAX     Integer32 (1..52)
	MAX-ACCESS not-accessible
	STATUS     current
	DESCRIPTION 
		"Index used for navigating the rows 1..52 of solarChargersEnergyLogLastDaysTable"
	::= { solarChargersEnergyLogLastDaysEntry 1 }

solarChargersEnergyLogLastDaysValue  OBJECT-TYPE
	SYNTAX     Integer32
	MAX-ACCESS read-only
	STATUS     current
	DESCRIPTION 
		"Energy value logged every day."
	::= { solarChargersEnergyLogLastDaysEntry 2 }

solarChargersEnergyLogLastWeeksNumberOfEntries  OBJECT-TYPE
	SYNTAX     Integer32
	MAX-ACCESS read-only
	STATUS     current
	DESCRIPTION 
		"This is the maximal number of entries stored in solar charger weekly energy log."
	::= { solarChargersEnergyLog 6 }

solarChargersEnergyLogLastWeeksTable  OBJECT-TYPE
	SYNTAX SEQUENCE OF SolarChargersEnergyLogLastWeeksEntry
	MAX-ACCESS not-accessible
	STATUS     current
	DESCRIPTION 
		"This table contains weekly energy log of solar chargers."
	::= { solarChargersEnergyLog 7 }

solarChargersEnergyLogLastWeeksEntry  OBJECT-TYPE
	SYNTAX 	SolarChargersEnergyLogLastWeeksEntry
	MAX-ACCESS not-accessible
	STATUS     current
	DESCRIPTION 
		""
	INDEX { solarChargersEnergyLogLastWeeksIndex }
	::= { solarChargersEnergyLogLastWeeksTable 1 }

SolarChargersEnergyLogLastWeeksEntry ::= SEQUENCE {
	solarChargersEnergyLogLastWeeksIndex
		Integer32,
	solarChargersEnergyLogLastWeeksValue
		Integer32
}

solarChargersEnergyLogLastWeeksIndex  OBJECT-TYPE
	SYNTAX     Integer32 (1..52)
	MAX-ACCESS not-accessible
	STATUS     current
	DESCRIPTION 
		"Index used for navigating the rows 1..52 of solarChargersEnergyLogLastWeekTable"
	::= { solarChargersEnergyLogLastWeeksEntry 1 }

solarChargersEnergyLogLastWeeksValue  OBJECT-TYPE
	SYNTAX     Integer32
	MAX-ACCESS read-only
	STATUS     current
	DESCRIPTION 
		"Energy value logged every week."
	::= { solarChargersEnergyLogLastWeeksEntry 2 }

windChargersStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of wind charger subsystem."
	::= { windChargers 1 }

windChargersCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured total wind current."
	::= { windChargersCurrent 1 }

windChargersCurrentDescription  OBJECT-TYPE
	SYNTAX     DisplayString (SIZE(0..16))
	MAX-ACCESS read-write
	STATUS     current
	DESCRIPTION 
		"A textual description of the total wind current monitor. This is stored in the system controller
		and can be changed by the user"
	::= { windChargersCurrent 2 }

windChargersCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { windChargersCurrent 3 }

windChargersCurrentAlarmEnable  OBJECT-TYPE
	SYNTAX     INTEGER {
		disabled (0),
		enabled (1)
	}
	MAX-ACCESS read-write
	STATUS     current
	DESCRIPTION 
		"This value once enabled, the alarm condition of the monitor will be reported."
	::= { windChargersCurrent 4 }

windChargersCurrentValue  OBJECT-TYPE
	SYNTAX     Integer32
	MAX-ACCESS read-only
	STATUS     current
	DESCRIPTION 
		"The value of the measured total wind current."
	::= { windChargersCurrent 5 }

windChargersCurrentMajorAlarmLevel  OBJECT-TYPE
	SYNTAX     Integer32
	MAX-ACCESS read-write
	STATUS     current
	DESCRIPTION 
		"The major alarm limit"
	::= { windChargersCurrent 6 }

windChargersCurrentMinorAlarmLevel  OBJECT-TYPE
	SYNTAX     Integer32
	MAX-ACCESS read-write
	STATUS     current
	DESCRIPTION 
		"The minor alarm limit"
	::= { windChargersCurrent 7 }

windChargersCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured used wind charger capacity."
	::= { windChargersCapacity 1 }

windChargersCapacityDescription  OBJECT-TYPE
	SYNTAX     DisplayString (SIZE(0..16))
	MAX-ACCESS read-write
	STATUS     current
	DESCRIPTION 
		"A textual description of the used wind charger capacity monitor. This is stored in the system controller
		and can be changed by the user"
	::= { windChargersCapacity 2 }

windChargersCapacityTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { windChargersCapacity 3 }

windChargersCapacityAlarmEnable  OBJECT-TYPE
	SYNTAX     INTEGER {
		disabled (0),
		enabled (1)
	}
	MAX-ACCESS read-write
	STATUS     current
	DESCRIPTION 
		"This value once enabled, the alarm condition of the monitor will be reported."
	::= { windChargersCapacity 4 }

windChargersCapacityValue  OBJECT-TYPE
	SYNTAX     Integer32
	MAX-ACCESS read-only
	STATUS     current
	DESCRIPTION 
		"The used wind charger capacity value presented in percentage of the total installed wind charger capacity."
	::= { windChargersCapacity 5 }

windChargersCapacityMajorAlarmLevel  OBJECT-TYPE
	SYNTAX     Integer32
	MAX-ACCESS read-write
	STATUS     current
	DESCRIPTION 
		"The major alarm limit"
	::= { windChargersCapacity 6 }

windChargersCapacityMinorAlarmLevel  OBJECT-TYPE
	SYNTAX     Integer32
	MAX-ACCESS read-write
	STATUS     current
	DESCRIPTION 
		"The minor alarm limit"
	::= { windChargersCapacity 7 }

windChargersErrorStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"This status value shows if the number of failed units is higher than the defined alarm level."
	::= { windChargersError 1 }

windChargersErrorDescription  OBJECT-TYPE
	SYNTAX     DisplayString (SIZE(0..16))
	MAX-ACCESS read-write
	STATUS     current
	DESCRIPTION 
		"A textual description of the wind error monitor. This is stored in the system controller
		and can be changed by the user"
	::= { windChargersError 2 }

windChargersErrorTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { windChargersError 3 }

windChargersErrorEnable  OBJECT-TYPE
	SYNTAX     INTEGER {
		disabled (0),
		enabled (1)
	}
	MAX-ACCESS read-write
	STATUS     current
	DESCRIPTION 
		"This value once enabled, the alarm condition of the monitor will be reported."
	::= { windChargersError 4 }

windChargersErrorValue  OBJECT-TYPE
	SYNTAX     Integer32
	MAX-ACCESS read-only
	STATUS     current
	DESCRIPTION 
		"The number of failed wind chargers."
	::= { windChargersError 5 }

windChargersErrorMajorAlarmLevel  OBJECT-TYPE
	SYNTAX     Integer32
	MAX-ACCESS read-write
	STATUS     current
	DESCRIPTION 
		"The major alarm limit"
	::= { windChargersError 6 }

windChargersErrorMinorAlarmLevel  OBJECT-TYPE
	SYNTAX     Integer32
	MAX-ACCESS read-write
	STATUS     current
	DESCRIPTION 
		"The minor alarm limit"
	::= { windChargersError 7 }

windChargersNumberOfWindChargers  OBJECT-TYPE
	SYNTAX     Integer32 (0..254)
	MAX-ACCESS read-write
	STATUS     current
	DESCRIPTION 
		"Number of installed wind chargers."
	::= { windChargers 5 }

windChargerTable  OBJECT-TYPE
	SYNTAX SEQUENCE OF WindChargerEntry
	MAX-ACCESS not-accessible
	STATUS     current
	DESCRIPTION 
		"This table shows the information of each wind charger installed in the system."
	::= { windChargers 6 }

windChargerEntry  OBJECT-TYPE
	SYNTAX 	WindChargerEntry
	MAX-ACCESS not-accessible
	STATUS     current
	DESCRIPTION 
		""
	INDEX { windChargerIndex }
	::= { windChargerTable 1 }

WindChargerEntry ::= SEQUENCE {
	windChargerIndex
		Integer32,
	windChargerStatus
		INTEGER,
	windChargerOutputCurrentValue
		Integer32,
	windChargerInputVoltageValue
		Integer32,
	windChargerType
		DisplayString,
	windChargerHwPartNumber
		DisplayString,
	windChargerHwVersion
		DisplayString,
	windChargerSwPartNumber
		DisplayString,
	windChargerSwVersion
		DisplayString
}

windChargerIndex  OBJECT-TYPE
	SYNTAX     Integer32 (1..100)
	MAX-ACCESS not-accessible
	STATUS     current
	DESCRIPTION 
		"Index used for navigating the rows 1..100 of windChargerTable"
	::= { windChargerEntry 1 }

windChargerStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of wind charger."
	::= { windChargerEntry 2 }

windChargerOutputCurrentValue  OBJECT-TYPE
	SYNTAX     Integer32
	MAX-ACCESS read-only
	STATUS     current
	DESCRIPTION 
		"The output current value of wind charger."
	::= { windChargerEntry 3 }

windChargerInputVoltageValue  OBJECT-TYPE
	SYNTAX     Integer32
	MAX-ACCESS read-only
	STATUS     current
	DESCRIPTION 
		"The input voltage value of wind charger."
	::= { windChargerEntry 4 }

windChargerType  OBJECT-TYPE
	SYNTAX     DisplayString (SIZE(0..27))
	MAX-ACCESS read-only
	STATUS     current
	DESCRIPTION 
		"Type of wind charger"
	::= { windChargerEntry 5 }

windChargerHwPartNumber  OBJECT-TYPE
	SYNTAX     DisplayString (SIZE(0..12))
	MAX-ACCESS read-only
	STATUS     current
	DESCRIPTION 
		"Hardware part number of wind charger"
	::= { windChargerEntry 6 }

windChargerHwVersion  OBJECT-TYPE
	SYNTAX     DisplayString (SIZE(0..6))
	MAX-ACCESS read-only
	STATUS     current
	DESCRIPTION 
		"Hardware version number of wind charger"
	::= { windChargerEntry 7 }

windChargerSwPartNumber  OBJECT-TYPE
	SYNTAX     DisplayString (SIZE(0..12))
	MAX-ACCESS read-only
	STATUS     current
	DESCRIPTION 
		"Part number of secondary software in wind charger"
	::= { windChargerEntry 8 }

windChargerSwVersion  OBJECT-TYPE
	SYNTAX     DisplayString (SIZE(0..6))
	MAX-ACCESS read-only
	STATUS     current
	DESCRIPTION 
		"Version number of secondary software in wind charger"
	::= { windChargerEntry 9 }

windChargersEnergyLogAccumulated  OBJECT-TYPE
	SYNTAX     Integer32
	MAX-ACCESS read-only
	STATUS     current
	DESCRIPTION 
		"This is the accumulated energy delivered to/from wind chargers."
	::= { windChargersEnergyLog 1 }

windChargersEnergyLogLastHoursNumberOfEntries  OBJECT-TYPE
	SYNTAX     Integer32 (0..52)
	MAX-ACCESS read-only
	STATUS     current
	DESCRIPTION 
		"This is the maximal number of entries stored in wind charger hourly energy log."
	::= { windChargersEnergyLog 2 }

windChargersEnergyLogLastHoursTable  OBJECT-TYPE
	SYNTAX SEQUENCE OF WindChargersEnergyLogLastHoursEntry
	MAX-ACCESS not-accessible
	STATUS     current
	DESCRIPTION 
		"This table contains hourly energy log of wind chargers."
	::= { windChargersEnergyLog 3 }

windChargersEnergyLogLastHoursEntry  OBJECT-TYPE
	SYNTAX 	WindChargersEnergyLogLastHoursEntry
	MAX-ACCESS not-accessible
	STATUS     current
	DESCRIPTION 
		""
	INDEX { windChargersEnergyLogLastHoursIndex }
	::= { windChargersEnergyLogLastHoursTable 1 }

WindChargersEnergyLogLastHoursEntry ::= SEQUENCE {
	windChargersEnergyLogLastHoursIndex
		Integer32,
	windChargersEnergyLogLastHoursValue
		Integer32
}

windChargersEnergyLogLastHoursIndex  OBJECT-TYPE
	SYNTAX     Integer32 (1..52)
	MAX-ACCESS not-accessible
	STATUS     current
	DESCRIPTION 
		"Index used for navigating the rows 1..52 of windChargersEnergyLogLastHoursTable"
	::= { windChargersEnergyLogLastHoursEntry 1 }

windChargersEnergyLogLastHoursValue  OBJECT-TYPE
	SYNTAX     Integer32
	MAX-ACCESS read-only
	STATUS     current
	DESCRIPTION 
		"Energy value logged every hour."
	::= { windChargersEnergyLogLastHoursEntry 2 }

windChargersEnergyLogLastDaysNumberOfEntries  OBJECT-TYPE
	SYNTAX     Integer32 (0..52)
	MAX-ACCESS read-only
	STATUS     current
	DESCRIPTION 
		"This is the maximal number of entries stored in wind charger daily energy log."
	::= { windChargersEnergyLog 4 }

windChargersEnergyLogLastDaysTable  OBJECT-TYPE
	SYNTAX SEQUENCE OF WindChargersEnergyLogLastDaysEntry
	MAX-ACCESS not-accessible
	STATUS     current
	DESCRIPTION 
		"This table contains daily energy log of wind chargers."
	::= { windChargersEnergyLog 5 }

windChargersEnergyLogLastDaysEntry  OBJECT-TYPE
	SYNTAX 	WindChargersEnergyLogLastDaysEntry
	MAX-ACCESS not-accessible
	STATUS     current
	DESCRIPTION 
		""
	INDEX { windChargersEnergyLogLastDaysIndex }
	::= { windChargersEnergyLogLastDaysTable 1 }

WindChargersEnergyLogLastDaysEntry ::= SEQUENCE {
	windChargersEnergyLogLastDaysIndex
		Integer32,
	windChargersEnergyLogLastDaysValue
		Integer32
}

windChargersEnergyLogLastDaysIndex  OBJECT-TYPE
	SYNTAX     Integer32 (1..52)
	MAX-ACCESS not-accessible
	STATUS     current
	DESCRIPTION 
		"Index used for navigating the rows 1..52 of windChargersEnergyLogLastDaysTable"
	::= { windChargersEnergyLogLastDaysEntry 1 }

windChargersEnergyLogLastDaysValue  OBJECT-TYPE
	SYNTAX     Integer32
	MAX-ACCESS read-only
	STATUS     current
	DESCRIPTION 
		"Energy value logged every day."
	::= { windChargersEnergyLogLastDaysEntry 2 }

windChargersEnergyLogLastWeeksNumberOfEntries  OBJECT-TYPE
	SYNTAX     Integer32 (0..52)
	MAX-ACCESS read-only
	STATUS     current
	DESCRIPTION 
		"This is the maximal number of entries stored in wind charger weekly energy log."
	::= { windChargersEnergyLog 6 }

windChargersEnergyLogLastWeeksTable  OBJECT-TYPE
	SYNTAX SEQUENCE OF WindChargersEnergyLogLastWeeksEntry
	MAX-ACCESS not-accessible
	STATUS     current
	DESCRIPTION 
		"This table contains weekly energy log of wind chargers."
	::= { windChargersEnergyLog 7 }

windChargersEnergyLogLastWeeksEntry  OBJECT-TYPE
	SYNTAX 	WindChargersEnergyLogLastWeeksEntry
	MAX-ACCESS not-accessible
	STATUS     current
	DESCRIPTION 
		""
	INDEX { windChargersEnergyLogLastWeeksIndex }
	::= { windChargersEnergyLogLastWeeksTable 1 }

WindChargersEnergyLogLastWeeksEntry ::= SEQUENCE {
	windChargersEnergyLogLastWeeksIndex
		Integer32,
	windChargersEnergyLogLastWeeksValue
		Integer32
}

windChargersEnergyLogLastWeeksIndex  OBJECT-TYPE
	SYNTAX     Integer32 (1..52)
	MAX-ACCESS not-accessible
	STATUS     current
	DESCRIPTION 
		"Index used for navigating the rows 1..52 of windChargersEnergyLogLastWeekTable"
	::= { windChargersEnergyLogLastWeeksEntry 1 }

windChargersEnergyLogLastWeeksValue  OBJECT-TYPE
	SYNTAX     Integer32
	MAX-ACCESS read-only
	STATUS     current
	DESCRIPTION 
		"Energy value logged every week."
	::= { windChargersEnergyLogLastWeeksEntry 2 }

loadStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of load subsystem."
	::= { load 1 }

loadCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured load current."
	::= { loadCurrent 1 }

loadCurrentDescription  OBJECT-TYPE
	SYNTAX     DisplayString (SIZE(0..16))
	MAX-ACCESS read-write
	STATUS     current
	DESCRIPTION 
		"A textual description of the load current monitor. This is stored in the system controller
		and can be changed by the user. "
	::= { loadCurrent 2 }

loadCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { loadCurrent 3 }

loadCurrentAlarmEnable  OBJECT-TYPE
	SYNTAX     INTEGER {
		disabled (0),
		enabled (1)
	}
	MAX-ACCESS read-write
	STATUS     current
	DESCRIPTION 
		"This value once enabled, the alarm condition of the monitor will be reported."
	::= { loadCurrent 4 }

loadCurrentValue  OBJECT-TYPE
	SYNTAX     Integer32
	MAX-ACCESS read-only
	STATUS     current
	DESCRIPTION 
		"The value of the measured load current."
	::= { loadCurrent 5 }

loadCurrentMajorHighLevel  OBJECT-TYPE
	SYNTAX     Integer32
	MAX-ACCESS read-write
	STATUS     current
	DESCRIPTION 
		"The major high alarm limit"
	::= { loadCurrent 6 }

loadCurrentMinorHighLevel  OBJECT-TYPE
	SYNTAX     Integer32
	MAX-ACCESS read-write
	STATUS     current
	DESCRIPTION 
		"The minor high alarm limit"
	::= { loadCurrent 7 }

loadFusesStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of the load fuses."
	::= { load 3 }

loadNumberOfGroups  OBJECT-TYPE
	SYNTAX     Integer32 (1..8)
	MAX-ACCESS read-write
	STATUS     current
	DESCRIPTION 
		"Number of load groups"
	::= { load 4 }

loadGroupTable  OBJECT-TYPE
	SYNTAX SEQUENCE OF LoadGroupEntry
	MAX-ACCESS not-accessible
	STATUS     current
	DESCRIPTION 
		"This table contains information about load groups."
	::= { load 5 }

loadGroupEntry  OBJECT-TYPE
	SYNTAX 	LoadGroupEntry
	MAX-ACCESS not-accessible
	STATUS     current
	DESCRIPTION 
		""
	INDEX { loadGroupIndex }
	::= { loadGroupTable 1 }

LoadGroupEntry ::= SEQUENCE {
	loadGroupIndex
		Integer32,
	loadGroupStatus
		INTEGER,
	loadNumberOfLVLDs
		Integer32
}

loadGroupIndex  OBJECT-TYPE
	SYNTAX     Integer32 (1..8)
	MAX-ACCESS not-accessible
	STATUS     current
	DESCRIPTION 
		"Index used for navigating the rows 1..8  of loadGroupTable"
	::= { loadGroupEntry 1 }

loadGroupStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of load group"
	::= { loadGroupEntry 2 }

loadNumberOfLVLDs  OBJECT-TYPE
	SYNTAX     Integer32 (0..4)
	MAX-ACCESS read-only
	STATUS     current
	DESCRIPTION 
		"Number of LVLDs installed in load group"
	::= { loadGroupEntry 3 }

loadLVLDTable  OBJECT-TYPE
	SYNTAX SEQUENCE OF LoadLVLDEntry
	MAX-ACCESS not-accessible
	STATUS     current
	DESCRIPTION 
		"This table contains information about LVLDs"
	::= { load 6 }

loadLVLDEntry  OBJECT-TYPE
	SYNTAX 	LoadLVLDEntry
	MAX-ACCESS not-accessible
	STATUS     current
	DESCRIPTION 
		""
	INDEX { loadGroupIndex, 
		loadLVLDIndex }
	::= { loadLVLDTable 1 }

LoadLVLDEntry ::= SEQUENCE {
	loadLVLDIndex
		Integer32,
	loadLVLDStatus
		INTEGER,
	loadLVLDDescription
		DisplayString,
	loadLVLDTrapRepeatCounter
		Counter32,
	loadLVLDEnable
		INTEGER,
	loadLVLDValue
		Integer32,
	loadLVLDConnectVoltage
		Integer32,
	loadLVLDDisconnectVoltage
		Integer32
}

loadLVLDIndex  OBJECT-TYPE
	SYNTAX     Integer32 (1..8)
	MAX-ACCESS not-accessible
	STATUS     current
	DESCRIPTION 
		"Index used for navigating the rows 1..8  of loadLVLDTable"
	::= { loadLVLDEntry 1 }

loadLVLDStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of LVLD"
	::= { loadLVLDEntry 2 }

loadLVLDDescription  OBJECT-TYPE
	SYNTAX     DisplayString (SIZE(0..16))
	MAX-ACCESS read-write
	STATUS     current
	DESCRIPTION 
		"A textual description of the LVLD. This is stored in the system controller
		and can be changed by the user.  "
	::= { loadLVLDEntry 3 }

loadLVLDTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { loadLVLDEntry 4 }

loadLVLDEnable  OBJECT-TYPE
	SYNTAX     INTEGER {
		disabled (0),
		enabled (1)
	}
	MAX-ACCESS read-write
	STATUS     current
	DESCRIPTION 
		"This value once enabled, the alarm condition of the LVLD will be reported."
	::= { loadLVLDEntry 5 }

loadLVLDValue  OBJECT-TYPE
	SYNTAX     Integer32
	MAX-ACCESS read-only
	STATUS     current
	DESCRIPTION 
		"The measured value of the LVLD."
	::= { loadLVLDEntry 6 }

loadLVLDConnectVoltage  OBJECT-TYPE
	SYNTAX     Integer32
	MAX-ACCESS read-write
	STATUS     current
	DESCRIPTION 
		"The load Contactor's Reconnect Voltage"
	::= { loadLVLDEntry 7 }

loadLVLDDisconnectVoltage  OBJECT-TYPE
	SYNTAX     Integer32
	MAX-ACCESS read-write
	STATUS     current
	DESCRIPTION 
		"The load Contactor's Disconnect Voltage"
	::= { loadLVLDEntry 8 }

loadFuseTable  OBJECT-TYPE
	SYNTAX SEQUENCE OF LoadFuseEntry
	MAX-ACCESS not-accessible
	STATUS     current
	DESCRIPTION 
		"This table contains information about load fuse "
	::= { load 7 }

loadFuseEntry  OBJECT-TYPE
	SYNTAX 	LoadFuseEntry
	MAX-ACCESS not-accessible
	STATUS     current
	DESCRIPTION 
		""
	INDEX { loadGroupIndex }
	::= { loadFuseTable 1 }

LoadFuseEntry ::= SEQUENCE {
	loadFuseStatus
		INTEGER,
	loadFuseDescription
		DisplayString,
	loadFuseTrapRepeatCounter
		Counter32,
	loadFuseAlarmEnable
		INTEGER,
	loadFuseValue
		Integer32
}

loadFuseStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11)
	}
	MAX-ACCESS read-only
	STATUS     current
	DESCRIPTION 
		"The status of load fuse"
	::= { loadFuseEntry 1 }

loadFuseDescription  OBJECT-TYPE
	SYNTAX     DisplayString (SIZE(0..16))
	MAX-ACCESS read-write
	STATUS     current
	DESCRIPTION 
		"A textual description of the load fuse monitor. This is stored in the system controller
		and can be changed by the user. "
	::= { loadFuseEntry 2 }

loadFuseTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { loadFuseEntry 3 }

loadFuseAlarmEnable  OBJECT-TYPE
	SYNTAX     INTEGER {
		disabled (0),
		enabled (1)
	}
	MAX-ACCESS read-write
	STATUS     current
	DESCRIPTION 
		"This value once enabled, the alarm condition of the monitor will be reported."
	::= { loadFuseEntry 4 }

loadFuseValue  OBJECT-TYPE
	SYNTAX     Integer32
	MAX-ACCESS read-write
	STATUS     current
	DESCRIPTION 
		"The measured value of the load fuse."
	::= { loadFuseEntry 5 }

loadEnergyLogAccumulated  OBJECT-TYPE
	SYNTAX     Integer32
	MAX-ACCESS read-only
	STATUS     current
	DESCRIPTION 
		"This is the accumulated energy delivered to load."
	::= { loadEnergyLog 1 }

loadEnergyLogLastHoursNumberOfEntries  OBJECT-TYPE
	SYNTAX     Integer32 (0..52)
	MAX-ACCESS read-only
	STATUS     current
	DESCRIPTION 
		"This is the maximal number of entries stored in load hourly energy log."
	::= { loadEnergyLog 2 }

loadEnergyLogLastHoursTable  OBJECT-TYPE
	SYNTAX SEQUENCE OF LoadEnergyLogLastHoursEntry
	MAX-ACCESS not-accessible
	STATUS     current
	DESCRIPTION 
		""
	::= { loadEnergyLog 3 }

loadEnergyLogLastHoursEntry  OBJECT-TYPE
	SYNTAX 	LoadEnergyLogLastHoursEntry
	MAX-ACCESS not-accessible
	STATUS     current
	DESCRIPTION 
		""
	INDEX { loadEnergyLogLastHoursIndex }
	::= { loadEnergyLogLastHoursTable 1 }

LoadEnergyLogLastHoursEntry ::= SEQUENCE {
	loadEnergyLogLastHoursIndex
		Integer32,
	loadEnergyLogLastHoursValue
		Integer32
}

loadEnergyLogLastHoursIndex  OBJECT-TYPE
	SYNTAX     Integer32 (1..52)
	MAX-ACCESS not-accessible
	STATUS     current
	DESCRIPTION 
		"Index used for navigating the rows 1..52  of loadEnergyLogLastHoursTable"
	::= { loadEnergyLogLastHoursEntry 1 }

loadEnergyLogLastHoursValue  OBJECT-TYPE
	SYNTAX     Integer32
	MAX-ACCESS read-only
	STATUS     current
	DESCRIPTION 
		"Energy value logged every hour."
	::= { loadEnergyLogLastHoursEntry 2 }

loadEnergyLogLastDaysNumberOfEntries  OBJECT-TYPE
	SYNTAX     Integer32 (0..52)
	MAX-ACCESS read-only
	STATUS     current
	DESCRIPTION 
		"This is the maximal number of entries stored in load daily energy log."
	::= { loadEnergyLog 4 }

loadEnergyLogLastDaysTable  OBJECT-TYPE
	SYNTAX SEQUENCE OF LoadEnergyLogLastDaysEntry
	MAX-ACCESS not-accessible
	STATUS     current
	DESCRIPTION 
		""
	::= { loadEnergyLog 5 }

loadEnergyLogLastDaysEntry  OBJECT-TYPE
	SYNTAX 	LoadEnergyLogLastDaysEntry
	MAX-ACCESS not-accessible
	STATUS     current
	DESCRIPTION 
		""
	INDEX { loadEnergyLogLastDaysIndex }
	::= { loadEnergyLogLastDaysTable 1 }

LoadEnergyLogLastDaysEntry ::= SEQUENCE {
	loadEnergyLogLastDaysIndex
		Integer32,
	loadEnergyLogLastDaysValue
		Integer32
}

loadEnergyLogLastDaysIndex  OBJECT-TYPE
	SYNTAX     Integer32 (1..52)
	MAX-ACCESS not-accessible
	STATUS     current
	DESCRIPTION 
		"Index used for navigating the rows 1..52  of loadEnergyLogLastDaysTable"
	::= { loadEnergyLogLastDaysEntry 1 }

loadEnergyLogLastDaysValue  OBJECT-TYPE
	SYNTAX     Integer32
	MAX-ACCESS read-only
	STATUS     current
	DESCRIPTION 
		"Energy value logged every day."
	::= { loadEnergyLogLastDaysEntry 2 }

loadEnergyLogLastWeeksNumberOfEntries  OBJECT-TYPE
	SYNTAX     Integer32 (0..52)
	MAX-ACCESS read-only
	STATUS     current
	DESCRIPTION 
		"This is the maximal number of entries stored in load weekly energy log."
	::= { loadEnergyLog 6 }

loadEnergyLogLastWeeksTable  OBJECT-TYPE
	SYNTAX SEQUENCE OF LoadEnergyLogLastWeeksEntry
	MAX-ACCESS not-accessible
	STATUS     current
	DESCRIPTION 
		""
	::= { loadEnergyLog 7 }

loadEnergyLogLastWeeksEntry  OBJECT-TYPE
	SYNTAX 	LoadEnergyLogLastWeeksEntry
	MAX-ACCESS not-accessible
	STATUS     current
	DESCRIPTION 
		""
	INDEX { loadEnergyLogLastWeeksIndex }
	::= { loadEnergyLogLastWeeksTable 1 }

LoadEnergyLogLastWeeksEntry ::= SEQUENCE {
	loadEnergyLogLastWeeksIndex
		Integer32,
	loadEnergyLogLastWeeksValue
		Integer32
}

loadEnergyLogLastWeeksIndex  OBJECT-TYPE
	SYNTAX     Integer32 (1..52)
	MAX-ACCESS not-accessible
	STATUS     current
	DESCRIPTION 
		"Index used for navigating the rows 1..52  of loadEnergyLogLastWeekTable"
	::= { loadEnergyLogLastWeeksEntry 1 }

loadEnergyLogLastWeeksValue  OBJECT-TYPE
	SYNTAX     Integer32
	MAX-ACCESS read-only
	STATUS     current
	DESCRIPTION 
		"Energy value logged every week."
	::= { loadEnergyLogLastWeeksEntry 2 }

-- The reported status of the battery subsystem. The status reflects the condition 
-- of all underlying alarm monitors in the battery subsystem

batteryStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"A toplevel status for the battery subsystem.  The state of this reflects the status of all 
		underlying statuses for the battery. Any change in one of the 'data monitors' in 
		the battery subsystem will propagate up to this status indicator."
	::= { battery 1 }

batteryDescription  OBJECT-TYPE
	SYNTAX     DisplayString (SIZE(0..32))
	MAX-ACCESS read-write
	STATUS     current
	DESCRIPTION 
		"A descriptive name of the battery installed in the system."
	::= { battery 2 }

batteryReferenceVoltage  OBJECT-TYPE
	SYNTAX     Integer32 (840..60417)
	MAX-ACCESS read-write
	STATUS     current
	DESCRIPTION 
		"The Voltage at which the DC System float charges.
		Acts as reference voltage when running temperature compensated charging."
	::= { battery 3 }

batteryFusesStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the battery fuses/breakers can mainly be normal(1) or majorAlarm(3) and  
		some other rarely used values ."
	::= { battery 4 }

-- The status value for the measured battery voltage. If the battery voltage reach outside 
-- the limits set by the major/minor low/high level settings this status will change accordingly.

batteryVoltageStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured battery voltage."
	::= { batteryVoltage 1 }

batteryVoltageDescription  OBJECT-TYPE
	SYNTAX     DisplayString (SIZE(0..16))
	MAX-ACCESS read-write
	STATUS     current
	DESCRIPTION 
		"A textual description of the battery voltage monitor. This is stored in the system controller
		and can be changed by the user.  "
	::= { batteryVoltage 2 }

batteryVoltageTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryVoltage 3 }

batteryVoltageAlarmEnable  OBJECT-TYPE
	SYNTAX     INTEGER {
		disabled (0),
		enabled (1)
	}
	MAX-ACCESS read-write
	STATUS     current
	DESCRIPTION 
		"The measured battery voltage alarm enable/disable control"
	::= { batteryVoltage 4 }

batteryVoltageValue  OBJECT-TYPE
	SYNTAX     Integer32 (0..7500)
	MAX-ACCESS read-only
	STATUS     current
	DESCRIPTION 
		"The value of the measured battery voltage."
	::= { batteryVoltage 5 }

batteryVoltageMajorHighLevel  OBJECT-TYPE
	SYNTAX     Integer32 (4300..6000)
	MAX-ACCESS read-write
	STATUS     current
	DESCRIPTION 
		"The Major High Battery Voltage alarm limit set voltage"
	::= { batteryVoltage 6 }

batteryVoltageMinorHighLevel  OBJECT-TYPE
	SYNTAX     Integer32
	MAX-ACCESS read-write
	STATUS     current
	DESCRIPTION 
		"The Minor High Battery Voltage alarm limit set voltage"
	::= { batteryVoltage 7 }

batteryVoltageMinorLowLevel  OBJECT-TYPE
	SYNTAX     Integer32 (4300..6000)
	MAX-ACCESS read-write
	STATUS     current
	DESCRIPTION 
		"The Minor Low Battery Voltage alarm limit set voltage"
	::= { batteryVoltage 8 }

batteryVoltageMajorLowLevel  OBJECT-TYPE
	SYNTAX     Integer32 (4300..6000)
	MAX-ACCESS read-write
	STATUS     current
	DESCRIPTION 
		"The Major Low Battery Voltage alarm limit set voltage"
	::= { batteryVoltage 9 }

batteryCurrentsStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the measured battery current"
	::= { batteryCurrents 1 }

batteryCurrentsDescription  OBJECT-TYPE
	SYNTAX     DisplayString (SIZE(0..16))
	MAX-ACCESS read-write
	STATUS     current
	DESCRIPTION 
		"A textual description of the battery current monitor. This is stored in the system controller
		and can be changed by the user.  "
	::= { batteryCurrents 2 }

batteryCurrentsTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryCurrents 3 }

batteryCurrentsAlarmEnable  OBJECT-TYPE
	SYNTAX     INTEGER {
		disabled (0),
		enabled (1)
	}
	MAX-ACCESS read-write
	STATUS     current
	DESCRIPTION 
		"This value once enabled, the alarm condition of the monitor will be reported."
	::= { batteryCurrents 4 }

batteryCurrentsValue  OBJECT-TYPE
	SYNTAX     Integer32
	MAX-ACCESS read-only
	STATUS     current
	DESCRIPTION 
		"The measured total battery current.
		This is the sum of all the enabled shunt measurements in the system.
		Negative battery current indicates discharging of the batteries.
		Positive battery current indicates charging of the batteries.
		Note that the units measured may be i Amperes or in Deciamperes depending on global system settings"
	::= { batteryCurrents 5 }

batteryCurrentsMajorHighLevel  OBJECT-TYPE
	SYNTAX     Integer32
	MAX-ACCESS read-write
	STATUS     current
	DESCRIPTION 
		"The major high alarm limit"
	::= { batteryCurrents 6 }

batteryCurrentsMinorHighLevel  OBJECT-TYPE
	SYNTAX     Integer32
	MAX-ACCESS read-write
	STATUS     current
	DESCRIPTION 
		"The minor high alarm limit"
	::= { batteryCurrents 7 }

batteryCurrentsMinorLowLevel  OBJECT-TYPE
	SYNTAX     Integer32
	MAX-ACCESS read-write
	STATUS     current
	DESCRIPTION 
		"The minor low alarm limit"
	::= { batteryCurrents 8 }

batteryCurrentsMajorLowLevel  OBJECT-TYPE
	SYNTAX     Integer32
	MAX-ACCESS read-write
	STATUS     current
	DESCRIPTION 
		"The major low alarm limit"
	::= { batteryCurrents 9 }

batteryTemperaturesStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The state of the battery fuses/breakers can be either one of the defined enumerated values"
	::= { batteryTemperatures 1 }

batteryTemperaturesDescription  OBJECT-TYPE
	SYNTAX     DisplayString (SIZE(0..16))
	MAX-ACCESS read-write
	STATUS     current
	DESCRIPTION 
		"A textual description of the battery temperature monitor. This is stored in the system controller
		and can be changed by the user. "
	::= { batteryTemperatures 2 }

batteryTemperaturesTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryTemperatures 3 }

batteryTemperaturesAlarmEnable  OBJECT-TYPE
	SYNTAX     INTEGER {
		disabled (0),
		enabled (1)
	}
	MAX-ACCESS read-write
	STATUS     current
	DESCRIPTION 
		"This value once enabled, the alarm condition of the monitor will be reported."
	::= { batteryTemperatures 4 }

batteryTemperaturesValue  OBJECT-TYPE
	SYNTAX     Integer32 (0..9999)
	MAX-ACCESS read-only
	STATUS     current
	DESCRIPTION 
		"The highest value of the enabled battery temperature measurements.
		Depending on the global setting in the Control unit, this value will be presented in Celsius
		or Fahrenheit."
	::= { batteryTemperatures 5 }

batteryTemperaturesMajorHighLevel  OBJECT-TYPE
	SYNTAX     Integer32
	MAX-ACCESS read-write
	STATUS     current
	DESCRIPTION 
		"The major high alarm limit"
	::= { batteryTemperatures 6 }

batteryTemperaturesMinorHighLevel  OBJECT-TYPE
	SYNTAX     Integer32
	MAX-ACCESS read-write
	STATUS     current
	DESCRIPTION 
		"The minor high alarm limit"
	::= { batteryTemperatures 7 }

batteryTemperaturesMinorLowLevel  OBJECT-TYPE
	SYNTAX     Integer32
	MAX-ACCESS read-write
	STATUS     current
	DESCRIPTION 
		"The minor low alarm limit"
	::= { batteryTemperatures 8 }

batteryTemperaturesMajorLowLevel  OBJECT-TYPE
	SYNTAX     Integer32
	MAX-ACCESS read-write
	STATUS     current
	DESCRIPTION 
		"The major low alarm limit"
	::= { batteryTemperatures 9 }

batteryTimeLeftStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the estimated battery remaining backup time."
	::= { batteryTimeLeft 1 }

batteryTimeLeftDescription  OBJECT-TYPE
	SYNTAX     DisplayString (SIZE(0..16))
	MAX-ACCESS read-write
	STATUS     current
	DESCRIPTION 
		"A textual description of the battery discharge time monitor. This is stored in the system controller
		and can be changed by the user.  "
	::= { batteryTimeLeft 2 }

batteryTimeLeftTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryTimeLeft 3 }

batteryTimeLeftAlarmEnable  OBJECT-TYPE
	SYNTAX     INTEGER {
		disabled (0),
		enabled (1)
	}
	MAX-ACCESS read-write
	STATUS     current
	DESCRIPTION 
		"This value once enabled, the alarm condition of the monitor will be reported."
	::= { batteryTimeLeft 4 }

batteryTimeLeftValue  OBJECT-TYPE
	SYNTAX     Integer32
	MAX-ACCESS read-only
	STATUS     current
	DESCRIPTION 
		"The estimated value of battery remaining backup time."
	::= { batteryTimeLeft 5 }

batteryTimeLeftMinorAlarmLevel  OBJECT-TYPE
	SYNTAX     Integer32
	MAX-ACCESS read-write
	STATUS     current
	DESCRIPTION 
		"The minor alarm limit"
	::= { batteryTimeLeft 6 }

batteryTimeLeftMajorAlarmLevel  OBJECT-TYPE
	SYNTAX     Integer32
	MAX-ACCESS read-write
	STATUS     current
	DESCRIPTION 
		"The major alarm limit"
	::= { batteryTimeLeft 7 }

batteryRemainingCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery remaining capacity monitor."
	::= { batteryRemainingCapacity 1 }

batteryRemainingCapacityDescription  OBJECT-TYPE
	SYNTAX     DisplayString (SIZE(0..16))
	MAX-ACCESS read-write
	STATUS     current
	DESCRIPTION 
		"A textual description of the battery remaining capacity monitor. This is stored in the system controller
		and can be changed by the user."
	::= { batteryRemainingCapacity 2 }

batteryRemainingCapacityTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryRemainingCapacity 3 }

batteryRemainingCapacityAlarmEnable  OBJECT-TYPE
	SYNTAX     INTEGER {
		disabled (0),
		enabled (1)
	}
	MAX-ACCESS read-write
	STATUS     current
	DESCRIPTION 
		"This value once enabled, the alarm condition of the monitor will be reported."
	::= { batteryRemainingCapacity 4 }

batteryRemainingCapacityValue  OBJECT-TYPE
	SYNTAX     Integer32
	MAX-ACCESS read-only
	STATUS     current
	DESCRIPTION 
		"Battery remaining capacity (SOC) value estimated from the latest battery test result."
	::= { batteryRemainingCapacity 5 }

batteryRemainingCapacityMinorLowLevel  OBJECT-TYPE
	SYNTAX     Integer32
	MAX-ACCESS read-write
	STATUS     current
	DESCRIPTION 
		"The minor low alarm limit"
	::= { batteryRemainingCapacity 6 }

batteryRemainingCapacityMajorLowLevel  OBJECT-TYPE
	SYNTAX     Integer32
	MAX-ACCESS read-write
	STATUS     current
	DESCRIPTION 
		"The major low alarm limit"
	::= { batteryRemainingCapacity 7 }

batteryUsedCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery used capacity (DoD) monitor"
	::= { batteryUsedCapacity 1 }

batteryUsedCapacityDescription  OBJECT-TYPE
	SYNTAX     DisplayString (SIZE(0..16))
	MAX-ACCESS read-write
	STATUS     current
	DESCRIPTION 
		"A textual description of the battery used capacity (DoD) monitor. This is stored in the system controller
		and can be changed by the user.  "
	::= { batteryUsedCapacity 2 }

batteryUsedCapacityTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryUsedCapacity 3 }

batteryUsedCapacityAlarmEnable  OBJECT-TYPE
	SYNTAX     INTEGER {
		disabled (0),
		enabled (1)
	}
	MAX-ACCESS read-write
	STATUS     current
	DESCRIPTION 
		"This value once enabled, the alarm condition of the monitor will be reported."
	::= { batteryUsedCapacity 4 }

batteryUsedCapacityValue  OBJECT-TYPE
	SYNTAX     Integer32
	MAX-ACCESS read-only
	STATUS     current
	DESCRIPTION 
		"This is the estimated battery used capacity (DoD)."
	::= { batteryUsedCapacity 5 }

batteryUsedCapacityMajorAlarmLevel  OBJECT-TYPE
	SYNTAX     Integer32
	MAX-ACCESS read-write
	STATUS     current
	DESCRIPTION 
		"The major alarm limit"
	::= { batteryUsedCapacity 6 }

batteryUsedCapacityMinorAlarmLevel  OBJECT-TYPE
	SYNTAX     Integer32
	MAX-ACCESS read-write
	STATUS     current
	DESCRIPTION 
		"The minor alarm limit"
	::= { batteryUsedCapacity 7 }

batteryTotalCapacityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the total capacity monitor."
	::= { batteryTotalCapacity 1 }

batteryTotalCapacityDescription  OBJECT-TYPE
	SYNTAX     DisplayString (SIZE(0..16))
	MAX-ACCESS read-write
	STATUS     current
	DESCRIPTION 
		"A textual description of the battery total capacity monitor. This is stored in the system controller
		and can be changed by the user"
	::= { batteryTotalCapacity 2 }

batteryTotalCapacityTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryTotalCapacity 3 }

batteryTotalCapacityAlarmEnable  OBJECT-TYPE
	SYNTAX     INTEGER {
		disabled (0),
		enabled (1)
	}
	MAX-ACCESS read-write
	STATUS     current
	DESCRIPTION 
		"This value once enabled, the alarm condition of the monitor will be reported."
	::= { batteryTotalCapacity 4 }

batteryTotalCapacityValue  OBJECT-TYPE
	SYNTAX     Integer32
	MAX-ACCESS read-only
	STATUS     current
	DESCRIPTION 
		"This is the estimated total battery capacity (installed Ah - SoH) value."
	::= { batteryTotalCapacity 5 }

batteryTotalCapacityMinorLowLevel  OBJECT-TYPE
	SYNTAX     Integer32
	MAX-ACCESS read-write
	STATUS     current
	DESCRIPTION 
		"The minor low alarm limit"
	::= { batteryTotalCapacity 6 }

batteryTotalCapacityMajorLowLevel  OBJECT-TYPE
	SYNTAX     Integer32
	MAX-ACCESS read-write
	STATUS     current
	DESCRIPTION 
		"The major low alarm limit"
	::= { batteryTotalCapacity 7 }

batteryQualityStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of the battery quality (SoH) monitor."
	::= { batteryQuality 1 }

batteryQualityDescription  OBJECT-TYPE
	SYNTAX     DisplayString (SIZE(0..16))
	MAX-ACCESS read-write
	STATUS     current
	DESCRIPTION 
		"A textual description of the battery quality (SoH) monitor. This is stored in the system controller
		and can be changed by the user"
	::= { batteryQuality 2 }

batteryQualityTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { batteryQuality 3 }

batteryQualityAlarmEnable  OBJECT-TYPE
	SYNTAX     INTEGER {
		disabled (0),
		enabled (1)
	}
	MAX-ACCESS read-write
	STATUS     current
	DESCRIPTION 
		"This value once enabled, the alarm condition of the monitor will be reported."
	::= { batteryQuality 4 }

batteryQualityValue  OBJECT-TYPE
	SYNTAX     Integer32
	MAX-ACCESS read-only
	STATUS     current
	DESCRIPTION 
		"The calculated battery quality (SoH) based on the latest battery test"
	::= { batteryQuality 5 }

batteryQualityMinorAlarmLevel  OBJECT-TYPE
	SYNTAX     Integer32
	MAX-ACCESS read-write
	STATUS     current
	DESCRIPTION 
		"The minor alarm limit"
	::= { batteryQuality 6 }

batteryQualityMajorAlarmLevel  OBJECT-TYPE
	SYNTAX     Integer32
	MAX-ACCESS read-write
	STATUS     current
	DESCRIPTION 
		"The major alarm limit"
	::= { batteryQuality 7 }

batteryLVBDStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The Battery Contactor is connected, disconnected, disabled or in any other alarm condition"
	::= { batteryLVBD 1 }

batteryLVBDDescription  OBJECT-TYPE
	SYNTAX     DisplayString (SIZE(0..16))
	MAX-ACCESS read-write
	STATUS     current
	DESCRIPTION 
		"A textual description of the battery LVBD monitor. This is stored in the system controller
		and can be changed by the user.  "
	::= { batteryLVBD 2 }

batteryLVBDTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryLVBD 3 }

batteryLVBDEnable  OBJECT-TYPE
	SYNTAX     INTEGER {
		disabled (0),
		enabled (1)
	}
	MAX-ACCESS read-write
	STATUS     current
	DESCRIPTION 
		"This value once enabled, the alarm condition of the LVBD will be reported."
	::= { batteryLVBD 4 }

batteryLVBDValue  OBJECT-TYPE
	SYNTAX     Integer32
	MAX-ACCESS read-only
	STATUS     current
	DESCRIPTION 
		"The measured value of the LVBD."
	::= { batteryLVBD 5 }

batteryLVBDConnectVoltage  OBJECT-TYPE
	SYNTAX     Integer32
	MAX-ACCESS read-write
	STATUS     current
	DESCRIPTION 
		"The Battery Contactor's Reconnect Voltage"
	::= { batteryLVBD 6 }

batteryLVBDDisconnectVoltage  OBJECT-TYPE
	SYNTAX     Integer32
	MAX-ACCESS read-write
	STATUS     current
	DESCRIPTION 
		"The Battery Contactor's Disconnect Voltage"
	::= { batteryLVBD 7 }

batteryChargeCurrentLimitEnable  OBJECT-TYPE
	SYNTAX     INTEGER {
		disabled (0),
		enabled (1)
	}
	MAX-ACCESS read-write
	STATUS     current
	DESCRIPTION 
		"Enable/disable of the battery charge current limitation feature; 0=disable, 1=enable."
	::= { batteryChargeCurrentLimit 1 }

batteryChargeCurrentLimitValue  OBJECT-TYPE
	SYNTAX     Integer32 (0..32767)
	MAX-ACCESS read-write
	STATUS     current
	DESCRIPTION 
		"Battery charging current limit value. Used only when AC source is mains feed.
		Note that the units measured may be i Amperes or in Deciamperes depending on global system settings"
	::= { batteryChargeCurrentLimit 2 }

batteryBoostVoltage  OBJECT-TYPE
	SYNTAX     Integer32 (870..60418)
	MAX-ACCESS read-write
	STATUS     current
	DESCRIPTION 
		"The Voltage at which the DC System boost charges the batteries."
	::= { batteryBoost 1 }

batteryBoostCommand  OBJECT-TYPE
	SYNTAX     INTEGER {
		pushbutton (0),
		startboost (1),
		stopboost (2)
	}
	MAX-ACCESS read-write
	STATUS     current
	DESCRIPTION 
		"This pushbutton will start or stop a manual battery boost if the system allows it."
	::= { batteryBoost 2 }

batteryBoostCurrentThreshold  OBJECT-TYPE
	SYNTAX     Integer32
	MAX-ACCESS read-write
	STATUS     current
	DESCRIPTION 
		"The boosting will terminate when the charge current drops below the BoostCurrentThreshold limit."
	::= { batteryBoost 3 }

batteryBoostManualMaxDuration  OBJECT-TYPE
	SYNTAX     Integer32 (0..1440)
	MAX-ACCESS read-write
	STATUS     current
	DESCRIPTION 
		"A protection against overcharging.  
		When running manual boost, the boosting will always terminate at this point.  "
	::= { batteryBoost 4 }

batteryTestVoltage  OBJECT-TYPE
	SYNTAX     Integer32
	MAX-ACCESS read-write
	STATUS     current
	DESCRIPTION 
		"This is the battery test end voltage. The battery test will be terminated when the voltage
		drops below the end voltage."
	::= { batteryTest 1 }

batteryTestCommand  OBJECT-TYPE
	SYNTAX     INTEGER {
		pushbutton (0),
		starttest (1),
		stoptest (2)
	}
	MAX-ACCESS read-write
	STATUS     current
	DESCRIPTION 
		"This pushbutton will start or stop a manual battery test if the system allows it."
	::= { batteryTest 2 }

batteryTestNumberOfResults  OBJECT-TYPE
	SYNTAX     Integer32 (0..10)
	MAX-ACCESS read-only
	STATUS     current
	DESCRIPTION 
		"This is the number of valid battery test results stored in controller."
	::= { batteryTest 3 }

batteryTestResultTable  OBJECT-TYPE
	SYNTAX SEQUENCE OF BatteryTestResultEntry
	MAX-ACCESS not-accessible
	STATUS     current
	DESCRIPTION 
		"This table contains the battery test results stored in controller."
	::= { batteryTest 4 }

batteryTestResultEntry  OBJECT-TYPE
	SYNTAX 	BatteryTestResultEntry
	MAX-ACCESS not-accessible
	STATUS     current
	DESCRIPTION 
		""
	INDEX { batteryTestResultIndex }
	::= { batteryTestResultTable 1 }

BatteryTestResultEntry ::= SEQUENCE {
	batteryTestResultIndex
		Integer32,
	batteryTestResultStartDateTime
		DateAndTime,
	batteryTestResultDuration
		Integer32,
	batteryTestResultDischarged
		Integer32,
	batteryTestResultQuality
		Integer32
}

batteryTestResultIndex  OBJECT-TYPE
	SYNTAX     Integer32 (1..10)
	MAX-ACCESS not-accessible
	STATUS     current
	DESCRIPTION 
		"A index pointing to one of ten possible battery test results"
	::= { batteryTestResultEntry 1 }

batteryTestResultStartDateTime  OBJECT-TYPE
	SYNTAX     DateAndTime
	MAX-ACCESS read-only
	STATUS     current
	DESCRIPTION 
		"This is the time and date when the test started."
	::= { batteryTestResultEntry 2 }

batteryTestResultDuration  OBJECT-TYPE
	SYNTAX     Integer32
	MAX-ACCESS read-only
	STATUS     current
	DESCRIPTION 
		"This is the test duration in minutes."
	::= { batteryTestResultEntry 3 }

batteryTestResultDischarged  OBJECT-TYPE
	SYNTAX     Integer32
	MAX-ACCESS read-only
	STATUS     current
	DESCRIPTION 
		"This is the discharged Ah during test."
	::= { batteryTestResultEntry 4 }

batteryTestResultQuality  OBJECT-TYPE
	SYNTAX     Integer32
	MAX-ACCESS read-only
	STATUS     current
	DESCRIPTION 
		"This is the calculated battery quality (SoH)in percentage."
	::= { batteryTestResultEntry 5 }

batteryTempCompEnable  OBJECT-TYPE
	SYNTAX     INTEGER {
		disabled (0),
		enabled (1)
	}
	MAX-ACCESS read-write
	STATUS     current
	DESCRIPTION 
		"Enable (1) or Disable (0)  of Battery Temperature Compensated output regulation mode"
	::= { batteryTempComp 1 }

batteryBankNumberOfBanks  OBJECT-TYPE
	SYNTAX     Integer32 (0..8)
	MAX-ACCESS read-write
	STATUS     current
	DESCRIPTION 
		"Number of battery banks installed in system."
	::= { batteryBank 1 }

batteryBankTable  OBJECT-TYPE
	SYNTAX SEQUENCE OF BatteryBankEntry
	MAX-ACCESS not-accessible
	STATUS     current
	DESCRIPTION 
		""
	::= { batteryBank 2 }

batteryBankEntry  OBJECT-TYPE
	SYNTAX 	BatteryBankEntry
	MAX-ACCESS not-accessible
	STATUS     current
	DESCRIPTION 
		""
	INDEX { batteryBankIndex }
	::= { batteryBankTable 1 }

BatteryBankEntry ::= SEQUENCE {
	batteryBankIndex
		Integer32,
	batteryBankStatus
		INTEGER,
	batteryBankNumberOfTemperatures
		Integer32,
	batteryBankNumberOfCurrents
		Integer32,
	batteryBankNumberOfFuses
		Integer32
}

batteryBankIndex  OBJECT-TYPE
	SYNTAX     Integer32 (1..8)
	MAX-ACCESS not-accessible
	STATUS     current
	DESCRIPTION 
		"Index used for navigating the rows 1..8  of batteryBankTable "
	::= { batteryBankEntry 1 }

batteryBankStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of battery bank"
	::= { batteryBankEntry 2 }

batteryBankNumberOfTemperatures  OBJECT-TYPE
	SYNTAX     Integer32 (0..4)
	MAX-ACCESS read-only
	STATUS     current
	DESCRIPTION 
		"Number of temperature measurements in battery bank."
	::= { batteryBankEntry 3 }

batteryBankNumberOfCurrents  OBJECT-TYPE
	SYNTAX     Integer32 (0..4)
	MAX-ACCESS read-only
	STATUS     current
	DESCRIPTION 
		"Number of current measurements in battery bank."
	::= { batteryBankEntry 4 }

batteryBankNumberOfFuses  OBJECT-TYPE
	SYNTAX     Integer32 (0..4)
	MAX-ACCESS read-only
	STATUS     current
	DESCRIPTION 
		"Number of fuses installed in battery bank."
	::= { batteryBankEntry 5 }

batteryBankTemperatureTable  OBJECT-TYPE
	SYNTAX SEQUENCE OF BatteryBankTemperatureEntry
	MAX-ACCESS not-accessible
	STATUS     current
	DESCRIPTION 
		""
	::= { batteryBank 3 }

batteryBankTemperatureEntry  OBJECT-TYPE
	SYNTAX 	BatteryBankTemperatureEntry
	MAX-ACCESS not-accessible
	STATUS     current
	DESCRIPTION 
		""
	INDEX { batteryBankIndex, 
		batteryTemperatureIndex }
	::= { batteryBankTemperatureTable 1 }

BatteryBankTemperatureEntry ::= SEQUENCE {
	batteryTemperatureIndex
		Integer32,
	batteryTemperatureStatus
		INTEGER,
	batteryTemperatureDescription
		DisplayString,
	batteryTemperatureTrapRepeatCounter
		Counter32,
	batteryTemperatureAlarmEnable
		INTEGER,
	batteryTemperatureValue
		Integer32,
	batteryTemperatureMajorHighLevel
		Integer32,
	batteryTemperatureMinorHighLevel
		Integer32,
	batteryTemperatureMinorLowLevel
		Integer32,
	batteryTemperatureMajorLowLevel
		Integer32
}

batteryTemperatureIndex  OBJECT-TYPE
	SYNTAX     Integer32 (1..4)
	MAX-ACCESS not-accessible
	STATUS     current
	DESCRIPTION 
		"This index denotes which row in the temperature input table.
		The size of the table is defined by the batteryBankNumberOfTemp   "
	::= { batteryBankTemperatureEntry 1 }

batteryTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery temperature monitor"
	::= { batteryBankTemperatureEntry 2 }

batteryTemperatureDescription  OBJECT-TYPE
	SYNTAX     DisplayString (SIZE(0..16))
	MAX-ACCESS read-write
	STATUS     current
	DESCRIPTION 
		"A textual description of the battery temperature monitor. This is stored in the system controller
		and can be changed by the user. "
	::= { batteryBankTemperatureEntry 3 }

batteryTemperatureTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryBankTemperatureEntry 4 }

batteryTemperatureAlarmEnable  OBJECT-TYPE
	SYNTAX     INTEGER {
		disabled (0),
		enabled (1)
	}
	MAX-ACCESS read-write
	STATUS     current
	DESCRIPTION 
		"This value once enabled, the alarm condition of the monitor will be reported."
	::= { batteryBankTemperatureEntry 5 }

batteryTemperatureValue  OBJECT-TYPE
	SYNTAX     Integer32
	MAX-ACCESS read-only
	STATUS     current
	DESCRIPTION 
		"The measured battery temperature."
	::= { batteryBankTemperatureEntry 6 }

batteryTemperatureMajorHighLevel  OBJECT-TYPE
	SYNTAX     Integer32
	MAX-ACCESS read-write
	STATUS     current
	DESCRIPTION 
		"The major high alarm limit"
	::= { batteryBankTemperatureEntry 7 }

batteryTemperatureMinorHighLevel  OBJECT-TYPE
	SYNTAX     Integer32
	MAX-ACCESS read-write
	STATUS     current
	DESCRIPTION 
		"The minor high alarm limit"
	::= { batteryBankTemperatureEntry 8 }

batteryTemperatureMinorLowLevel  OBJECT-TYPE
	SYNTAX     Integer32
	MAX-ACCESS read-write
	STATUS     current
	DESCRIPTION 
		"The minor low alarm limit"
	::= { batteryBankTemperatureEntry 9 }

batteryTemperatureMajorLowLevel  OBJECT-TYPE
	SYNTAX     Integer32
	MAX-ACCESS read-write
	STATUS     current
	DESCRIPTION 
		"The major low alarm limit"
	::= { batteryBankTemperatureEntry 10 }

batteryBankCurrentTable  OBJECT-TYPE
	SYNTAX SEQUENCE OF BatteryBankCurrentEntry
	MAX-ACCESS not-accessible
	STATUS     current
	DESCRIPTION 
		""
	::= { batteryBank 4 }

batteryBankCurrentEntry  OBJECT-TYPE
	SYNTAX 	BatteryBankCurrentEntry
	MAX-ACCESS not-accessible
	STATUS     current
	DESCRIPTION 
		""
	INDEX { batteryBankIndex, 
		batteryCurrentIndex }
	::= { batteryBankCurrentTable 1 }

BatteryBankCurrentEntry ::= SEQUENCE {
	batteryCurrentIndex
		Integer32,
	batteryCurrentStatus
		INTEGER,
	batteryCurrentDescription
		DisplayString,
	batteryCurrentTrapRepeatCounter
		Counter32,
	batteryCurrentAlarmEnable
		INTEGER,
	batteryCurrentValue
		Integer32,
	batteryCurrentMajorHighLevel
		Integer32,
	batteryCurrentMinorHighLevel
		Integer32,
	batteryCurrentMinorLowLevel
		Integer32,
	batteryCurrentMajorLowLevel
		Integer32
}

batteryCurrentIndex  OBJECT-TYPE
	SYNTAX     Integer32 (1..4)
	MAX-ACCESS not-accessible
	STATUS     current
	DESCRIPTION 
		"This index denotes which row in the current input table.
		        The size of the table is defined by the system"
	::= { batteryBankCurrentEntry 1 }

batteryCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery current monitor"
	::= { batteryBankCurrentEntry 2 }

batteryCurrentDescription  OBJECT-TYPE
	SYNTAX     DisplayString (SIZE(0..16))
	MAX-ACCESS read-write
	STATUS     current
	DESCRIPTION 
		"A textual description of the battery current monitor. This is stored in the system controller
		and can be changed by the user. "
	::= { batteryBankCurrentEntry 3 }

batteryCurrentTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryBankCurrentEntry 4 }

batteryCurrentAlarmEnable  OBJECT-TYPE
	SYNTAX     INTEGER {
		disabled (0),
		enabled (1)
	}
	MAX-ACCESS read-write
	STATUS     current
	DESCRIPTION 
		"This value once enabled, the alarm condition of the monitor will be reported."
	::= { batteryBankCurrentEntry 5 }

batteryCurrentValue  OBJECT-TYPE
	SYNTAX     Integer32
	MAX-ACCESS read-only
	STATUS     current
	DESCRIPTION 
		"The measured battery current"
	::= { batteryBankCurrentEntry 6 }

batteryCurrentMajorHighLevel  OBJECT-TYPE
	SYNTAX     Integer32
	MAX-ACCESS read-write
	STATUS     current
	DESCRIPTION 
		"The major high alarm limit"
	::= { batteryBankCurrentEntry 7 }

batteryCurrentMinorHighLevel  OBJECT-TYPE
	SYNTAX     Integer32
	MAX-ACCESS read-write
	STATUS     current
	DESCRIPTION 
		"The minor high alarm limit"
	::= { batteryBankCurrentEntry 8 }

batteryCurrentMinorLowLevel  OBJECT-TYPE
	SYNTAX     Integer32
	MAX-ACCESS read-write
	STATUS     current
	DESCRIPTION 
		"The minor low alarm limit"
	::= { batteryBankCurrentEntry 9 }

batteryCurrentMajorLowLevel  OBJECT-TYPE
	SYNTAX     Integer32
	MAX-ACCESS read-write
	STATUS     current
	DESCRIPTION 
		"The major low alarm limit"
	::= { batteryBankCurrentEntry 10 }

batteryBankFuseTable  OBJECT-TYPE
	SYNTAX SEQUENCE OF BatteryBankFuseEntry
	MAX-ACCESS not-accessible
	STATUS     current
	DESCRIPTION 
		""
	::= { batteryBank 5 }

batteryBankFuseEntry  OBJECT-TYPE
	SYNTAX 	BatteryBankFuseEntry
	MAX-ACCESS not-accessible
	STATUS     current
	DESCRIPTION 
		""
	INDEX { batteryBankIndex, 
		batteryFuseIndex }
	::= { batteryBankFuseTable 1 }

BatteryBankFuseEntry ::= SEQUENCE {
	batteryFuseIndex
		Integer32,
	batteryFuseStatus
		INTEGER,
	batteryFuseDescription
		DisplayString,
	batteryFuseTrapRepeatCounter
		Counter32,
	batteryFuseAlarmEnable
		INTEGER,
	batteryFuseValue
		Integer32
}

batteryFuseIndex  OBJECT-TYPE
	SYNTAX     Integer32 (1..4)
	MAX-ACCESS not-accessible
	STATUS     current
	DESCRIPTION 
		"This index denotes which row in the fuse table.
		        The size of the table is defined by the system"
	::= { batteryBankFuseEntry 1 }

batteryFuseStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery fuse monitor"
	::= { batteryBankFuseEntry 2 }

batteryFuseDescription  OBJECT-TYPE
	SYNTAX     DisplayString (SIZE(0..16))
	MAX-ACCESS read-write
	STATUS     current
	DESCRIPTION 
		"A textual description of the battery fuse monitor. This is stored in the system controller
		and can be changed by the user."
	::= { batteryBankFuseEntry 3 }

batteryFuseTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off."
	::= { batteryBankFuseEntry 4 }

batteryFuseAlarmEnable  OBJECT-TYPE
	SYNTAX     INTEGER {
		disabled (0),
		enabled (1)
	}
	MAX-ACCESS read-write
	STATUS     current
	DESCRIPTION 
		"This value once enabled, the alarm condition of the monitor will be reported."
	::= { batteryBankFuseEntry 5 }

batteryFuseValue  OBJECT-TYPE
	SYNTAX     Integer32
	MAX-ACCESS read-only
	STATUS     current
	DESCRIPTION 
		"The measured value of battery fuse input."
	::= { batteryBankFuseEntry 6 }

batteryMonitorsNumberOfUnits  OBJECT-TYPE
	SYNTAX     Integer32
	MAX-ACCESS read-write
	STATUS     current
	DESCRIPTION 
		"The number of battery monitor installed in system."
	::= { batteryMonitors 1 }

batteryMonitorsTable  OBJECT-TYPE
	SYNTAX SEQUENCE OF BatteryMonitorsEntry
	MAX-ACCESS not-accessible
	STATUS     current
	DESCRIPTION 
		""
	::= { batteryMonitors 2 }

batteryMonitorsEntry  OBJECT-TYPE
	SYNTAX 	BatteryMonitorsEntry
	MAX-ACCESS not-accessible
	STATUS     current
	DESCRIPTION 
		""
	INDEX { batteryMonitorIndex }
	::= { batteryMonitorsTable 1 }

BatteryMonitorsEntry ::= SEQUENCE {
	batteryMonitorIndex
		Integer32,
	batteryMonitorNumberOfTemperatures
		Integer32,
	batteryMonitorNumberOfCurrents
		Integer32,
	batteryMonitorNumberOfFuses
		Integer32,
	batteryMonitorNumberOfSymmetries
		Integer32
}

batteryMonitorIndex  OBJECT-TYPE
	SYNTAX     Integer32 (1..8)
	MAX-ACCESS not-accessible
	STATUS     current
	DESCRIPTION 
		"Index used for navigating the rows 1..8  of batteryMonitorsTable"
	::= { batteryMonitorsEntry 1 }

batteryMonitorNumberOfTemperatures  OBJECT-TYPE
	SYNTAX     Integer32 (0..4)
	MAX-ACCESS read-only
	STATUS     current
	DESCRIPTION 
		"The number of temperature measurements in battery monitor."
	::= { batteryMonitorsEntry 2 }

batteryMonitorNumberOfCurrents  OBJECT-TYPE
	SYNTAX     Integer32 (0..4)
	MAX-ACCESS read-only
	STATUS     current
	DESCRIPTION 
		"The number of current measurements in battery monitor."
	::= { batteryMonitorsEntry 3 }

batteryMonitorNumberOfFuses  OBJECT-TYPE
	SYNTAX     Integer32 (0..4)
	MAX-ACCESS read-only
	STATUS     current
	DESCRIPTION 
		"The number of fuse measurements in battery monitor."
	::= { batteryMonitorsEntry 4 }

batteryMonitorNumberOfSymmetries  OBJECT-TYPE
	SYNTAX     Integer32 (0..4)
	MAX-ACCESS read-only
	STATUS     current
	DESCRIPTION 
		"The number of symmetry measurements in battery monitor."
	::= { batteryMonitorsEntry 5 }

batteryMonitorTemperatureTable  OBJECT-TYPE
	SYNTAX SEQUENCE OF BatteryMonitorTemperatureEntry
	MAX-ACCESS not-accessible
	STATUS     current
	DESCRIPTION 
		""
	::= { batteryMonitors 3 }

batteryMonitorTemperatureEntry  OBJECT-TYPE
	SYNTAX 	BatteryMonitorTemperatureEntry
	MAX-ACCESS not-accessible
	STATUS     current
	DESCRIPTION 
		""
	INDEX { batteryMonitorIndex, 
		batteryMonitorTemperatureIndex }
	::= { batteryMonitorTemperatureTable 1 }

BatteryMonitorTemperatureEntry ::= SEQUENCE {
	batteryMonitorTemperatureIndex
		Integer32,
	batteryMonitorTemperatureStatus
		INTEGER,
	batteryMonitorTemperatureDescription
		DisplayString,
	batteryMonitorTemperatureTrapRepeatCounter
		Counter32,
	batteryMonitorTemperatureAlarmEnable
		INTEGER,
	batteryMonitorTemperatureValue
		Integer32,
	batteryMonitorTemperatureMajorHighLevel
		Integer32,
	batteryMonitorTemperatureMinorHighLevel
		Integer32,
	batteryMonitorTemperatureMinorLowLevel
		Integer32,
	batteryMonitorTemperatureMajorLowLevel
		Integer32
}

batteryMonitorTemperatureIndex  OBJECT-TYPE
	SYNTAX     Integer32 (1..4)
	MAX-ACCESS not-accessible
	STATUS     current
	DESCRIPTION 
		"This index denotes which row in the temperature input table.
		The size of the table is defined by the batteryMonitorNumberOfTemperatures"
	::= { batteryMonitorTemperatureEntry 1 }

batteryMonitorTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery temperature monitor"
	::= { batteryMonitorTemperatureEntry 2 }

batteryMonitorTemperatureDescription  OBJECT-TYPE
	SYNTAX     DisplayString (SIZE(0..16))
	MAX-ACCESS read-write
	STATUS     current
	DESCRIPTION 
		"A textual description of the battery monitor temperature. This is stored in the system controller
		and can be changed by the user. "
	::= { batteryMonitorTemperatureEntry 3 }

batteryMonitorTemperatureTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off"
	::= { batteryMonitorTemperatureEntry 4 }

batteryMonitorTemperatureAlarmEnable  OBJECT-TYPE
	SYNTAX     INTEGER {
		disabled (0),
		enabled (1)
	}
	MAX-ACCESS read-write
	STATUS     current
	DESCRIPTION 
		"This value once enabled, the alarm condition of the monitor will be reported."
	::= { batteryMonitorTemperatureEntry 5 }

batteryMonitorTemperatureValue  OBJECT-TYPE
	SYNTAX     Integer32
	MAX-ACCESS read-only
	STATUS     current
	DESCRIPTION 
		"The measured battery temperature in battery monitor."
	::= { batteryMonitorTemperatureEntry 6 }

batteryMonitorTemperatureMajorHighLevel  OBJECT-TYPE
	SYNTAX     Integer32
	MAX-ACCESS read-write
	STATUS     current
	DESCRIPTION 
		"The major high alarm limit"
	::= { batteryMonitorTemperatureEntry 7 }

batteryMonitorTemperatureMinorHighLevel  OBJECT-TYPE
	SYNTAX     Integer32
	MAX-ACCESS read-write
	STATUS     current
	DESCRIPTION 
		"The minor high alarm limit"
	::= { batteryMonitorTemperatureEntry 8 }

batteryMonitorTemperatureMinorLowLevel  OBJECT-TYPE
	SYNTAX     Integer32
	MAX-ACCESS read-write
	STATUS     current
	DESCRIPTION 
		"The minor low alarm limit"
	::= { batteryMonitorTemperatureEntry 9 }

batteryMonitorTemperatureMajorLowLevel  OBJECT-TYPE
	SYNTAX     Integer32
	MAX-ACCESS read-write
	STATUS     current
	DESCRIPTION 
		"The major low alarm limit"
	::= { batteryMonitorTemperatureEntry 10 }

batteryMonitorCurrentTable  OBJECT-TYPE
	SYNTAX SEQUENCE OF BatteryMonitorCurrentEntry
	MAX-ACCESS not-accessible
	STATUS     current
	DESCRIPTION 
		""
	::= { batteryMonitors 4 }

batteryMonitorCurrentEntry  OBJECT-TYPE
	SYNTAX 	BatteryMonitorCurrentEntry
	MAX-ACCESS not-accessible
	STATUS     current
	DESCRIPTION 
		""
	INDEX { batteryMonitorIndex, 
		batteryMonitorCurrentIndex }
	::= { batteryMonitorCurrentTable 1 }

BatteryMonitorCurrentEntry ::= SEQUENCE {
	batteryMonitorCurrentIndex
		Integer32,
	batteryMonitorCurrentStatus
		INTEGER,
	batteryMonitorCurrentDescription
		DisplayString,
	batteryMonitorCurrentTrapRepeatCounter
		Counter32,
	batteryMonitorCurrentAlarmEnable
		INTEGER,
	batteryMonitorCurrentValue
		Integer32,
	batteryMonitorCurrentMajorHighLevel
		Integer32,
	batteryMonitorCurrentMinorHighLevel
		Integer32,
	batteryMonitorCurrentMinorLowLevel
		Integer32,
	batteryMonitorCurrentMajorLowLevel
		Integer32
}

batteryMonitorCurrentIndex  OBJECT-TYPE
	SYNTAX     Integer32 (1..4)
	MAX-ACCESS not-accessible
	STATUS     current
	DESCRIPTION 
		"This index denotes which row in the current input table.
		The size of the table is defined by the batteryMonitorNumberOfCurrents"
	::= { batteryMonitorCurrentEntry 1 }

batteryMonitorCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery current monitor"
	::= { batteryMonitorCurrentEntry 2 }

batteryMonitorCurrentDescription  OBJECT-TYPE
	SYNTAX     DisplayString (SIZE(0..16))
	MAX-ACCESS read-write
	STATUS     current
	DESCRIPTION 
		"A textual description of the battery monitor current. This is stored in the system controller
		and can be changed by the user. "
	::= { batteryMonitorCurrentEntry 3 }

batteryMonitorCurrentTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off"
	::= { batteryMonitorCurrentEntry 4 }

batteryMonitorCurrentAlarmEnable  OBJECT-TYPE
	SYNTAX     INTEGER {
		disabled (0),
		enabled (1)
	}
	MAX-ACCESS read-write
	STATUS     current
	DESCRIPTION 
		"This value once enabled, the alarm condition of the monitor will be reported."
	::= { batteryMonitorCurrentEntry 5 }

batteryMonitorCurrentValue  OBJECT-TYPE
	SYNTAX     Integer32
	MAX-ACCESS read-only
	STATUS     current
	DESCRIPTION 
		"The measured battery current in battery monitor."
	::= { batteryMonitorCurrentEntry 6 }

batteryMonitorCurrentMajorHighLevel  OBJECT-TYPE
	SYNTAX     Integer32
	MAX-ACCESS read-write
	STATUS     current
	DESCRIPTION 
		"The major high alarm limit"
	::= { batteryMonitorCurrentEntry 7 }

batteryMonitorCurrentMinorHighLevel  OBJECT-TYPE
	SYNTAX     Integer32
	MAX-ACCESS read-write
	STATUS     current
	DESCRIPTION 
		"The minor high alarm limit"
	::= { batteryMonitorCurrentEntry 8 }

batteryMonitorCurrentMinorLowLevel  OBJECT-TYPE
	SYNTAX     Integer32
	MAX-ACCESS read-write
	STATUS     current
	DESCRIPTION 
		"The minor low alarm limit"
	::= { batteryMonitorCurrentEntry 9 }

batteryMonitorCurrentMajorLowLevel  OBJECT-TYPE
	SYNTAX     Integer32
	MAX-ACCESS read-write
	STATUS     current
	DESCRIPTION 
		"The major low alarm limit"
	::= { batteryMonitorCurrentEntry 10 }

batteryMonitorFuseTable  OBJECT-TYPE
	SYNTAX SEQUENCE OF BatteryMonitorFuseEntry
	MAX-ACCESS not-accessible
	STATUS     current
	DESCRIPTION 
		""
	::= { batteryMonitors 5 }

batteryMonitorFuseEntry  OBJECT-TYPE
	SYNTAX 	BatteryMonitorFuseEntry
	MAX-ACCESS not-accessible
	STATUS     current
	DESCRIPTION 
		""
	INDEX { batteryMonitorIndex, 
		batteryMonitorFuseIndex }
	::= { batteryMonitorFuseTable 1 }

BatteryMonitorFuseEntry ::= SEQUENCE {
	batteryMonitorFuseIndex
		Integer32,
	batteryMonitorFuseStatus
		INTEGER,
	batteryMonitorFuseDescription
		DisplayString,
	batteryMonitorFuseTrapRepeatCounter
		Counter32,
	batteryMonitorFuseAlarmEnable
		INTEGER,
	batteryMonitorFuseValue
		Integer32
}

batteryMonitorFuseIndex  OBJECT-TYPE
	SYNTAX     Integer32 (1..4)
	MAX-ACCESS not-accessible
	STATUS     current
	DESCRIPTION 
		"This index denotes which row in the fuse table.
		The size of the table is defined by the batteryMonitorNumberOfFuses"
	::= { batteryMonitorFuseEntry 1 }

batteryMonitorFuseStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery fuse monitor"
	::= { batteryMonitorFuseEntry 2 }

batteryMonitorFuseDescription  OBJECT-TYPE
	SYNTAX     DisplayString (SIZE(0..16))
	MAX-ACCESS read-write
	STATUS     current
	DESCRIPTION 
		"A textual description of the battery monitor fuse. This is stored in the system controller
		and can be changed by the user. "
	::= { batteryMonitorFuseEntry 3 }

batteryMonitorFuseTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off"
	::= { batteryMonitorFuseEntry 4 }

batteryMonitorFuseAlarmEnable  OBJECT-TYPE
	SYNTAX     INTEGER {
		disabled (0),
		enabled (1)
	}
	MAX-ACCESS read-write
	STATUS     current
	DESCRIPTION 
		"This value once enabled, the alarm condition of the monitor will be reported."
	::= { batteryMonitorFuseEntry 5 }

batteryMonitorFuseValue  OBJECT-TYPE
	SYNTAX     Integer32
	MAX-ACCESS read-only
	STATUS     current
	DESCRIPTION 
		"The measured value of battery fuse in battery monitor."
	::= { batteryMonitorFuseEntry 6 }

batteryMonitorSymmetryTable  OBJECT-TYPE
	SYNTAX SEQUENCE OF BatteryMonitorSymmetryEntry
	MAX-ACCESS not-accessible
	STATUS     current
	DESCRIPTION 
		""
	::= { batteryMonitors 6 }

batteryMonitorSymmetryEntry  OBJECT-TYPE
	SYNTAX 	BatteryMonitorSymmetryEntry
	MAX-ACCESS not-accessible
	STATUS     current
	DESCRIPTION 
		""
	INDEX { batteryMonitorIndex, 
		batteryMonitorSymmetryIndex }
	::= { batteryMonitorSymmetryTable 1 }

BatteryMonitorSymmetryEntry ::= SEQUENCE {
	batteryMonitorSymmetryIndex
		Integer32,
	batteryMonitorSymmetryStatus
		INTEGER,
	batteryMonitorSymmetryDescription
		DisplayString,
	batteryMonitorSymmetryTrapRepeatCounter
		Counter32,
	batteryMonitorSymmetryAlarmEnable
		INTEGER,
	batteryMonitorSymmetryMeasureValue
		Integer32,
	batteryMonitorSymmetryDeltaValue
		Integer32,
	batteryMonitorSymmetryMajorAlarmLevel
		Integer32,
	batteryMonitorSymmetryMinorAlarmLevel
		Integer32
}

batteryMonitorSymmetryIndex  OBJECT-TYPE
	SYNTAX     Integer32 (1..8)
	MAX-ACCESS not-accessible
	STATUS     current
	DESCRIPTION 
		"This index denotes which row in the symmetry input table.
		The size of the table is defined by the batteryMonitorNumberOfSymmetries"
	::= { batteryMonitorSymmetryEntry 1 }

batteryMonitorSymmetryStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of battery symmetry monitor"
	::= { batteryMonitorSymmetryEntry 2 }

batteryMonitorSymmetryDescription  OBJECT-TYPE
	SYNTAX     DisplayString (SIZE(0..16))
	MAX-ACCESS read-write
	STATUS     current
	DESCRIPTION 
		"A textual description of the battery monitor symmetry. This is stored in the system controller
		and can be changed by the user. "
	::= { batteryMonitorSymmetryEntry 3 }

batteryMonitorSymmetryTrapRepeatCounter  OBJECT-TYPE
	SYNTAX     Counter32
	MAX-ACCESS accessible-for-notify
	STATUS     current
	DESCRIPTION 
		"The number of consecutive times this alam condition has been transmitted in a trap. 
		When trap repetition is enabled, this counter increments every time this trap is repeated.  
		The counter is automatically set to zero when the alarm condition is reset and the
		alarm goes off"
	::= { batteryMonitorSymmetryEntry 4 }

batteryMonitorSymmetryAlarmEnable  OBJECT-TYPE
	SYNTAX     INTEGER {
		disabled (0),
		enabled (1)
	}
	MAX-ACCESS read-write
	STATUS     current
	DESCRIPTION 
		"This value once enabled, the alarm condition of the monitor will be reported."
	::= { batteryMonitorSymmetryEntry 5 }

batteryMonitorSymmetryMeasureValue  OBJECT-TYPE
	SYNTAX     Integer32
	MAX-ACCESS read-only
	STATUS     current
	DESCRIPTION 
		"The measured battery symmetry voltage in battery monitor."
	::= { batteryMonitorSymmetryEntry 6 }

batteryMonitorSymmetryDeltaValue  OBJECT-TYPE
	SYNTAX     Integer32
	MAX-ACCESS read-only
	STATUS     current
	DESCRIPTION 
		"The measured battery symmetry delta voltage in battery monitor."
	::= { batteryMonitorSymmetryEntry 7 }

batteryMonitorSymmetryMajorAlarmLevel  OBJECT-TYPE
	SYNTAX     Integer32
	MAX-ACCESS read-write
	STATUS     current
	DESCRIPTION 
		"The major alarm limit"
	::= { batteryMonitorSymmetryEntry 8 }

batteryMonitorSymmetryMinorAlarmLevel  OBJECT-TYPE
	SYNTAX     Integer32
	MAX-ACCESS read-write
	STATUS     current
	DESCRIPTION 
		"The minor alarm limit"
	::= { batteryMonitorSymmetryEntry 9 }

batteryEnergyLogAccumulated  OBJECT-TYPE
	SYNTAX     Integer32
	MAX-ACCESS read-only
	STATUS     current
	DESCRIPTION 
		"This is the accumulated energy delivered to/from battery."
	::= { batteryEnergyLog 1 }

batteryEnergyLogLastHoursNumberOfEntries  OBJECT-TYPE
	SYNTAX     Integer32 (0..52)
	MAX-ACCESS read-only
	STATUS     current
	DESCRIPTION 
		"This is the maximal number of entries stored in battery hourly energy log."
	::= { batteryEnergyLog 2 }

batteryEnergyLogLastHoursTable  OBJECT-TYPE
	SYNTAX SEQUENCE OF BatteryEnergyLogLastHoursEntry
	MAX-ACCESS not-accessible
	STATUS     current
	DESCRIPTION 
		"This table contains hourly energy log of battery."
	::= { batteryEnergyLog 3 }

batteryEnergyLogLastHoursEntry  OBJECT-TYPE
	SYNTAX 	BatteryEnergyLogLastHoursEntry
	MAX-ACCESS not-accessible
	STATUS     current
	DESCRIPTION 
		""
	INDEX { batteryEnergyLogLastHoursIndex }
	::= { batteryEnergyLogLastHoursTable 1 }

BatteryEnergyLogLastHoursEntry ::= SEQUENCE {
	batteryEnergyLogLastHoursIndex
		Integer32,
	batteryEnergyLogLastHoursValue
		Integer32
}

batteryEnergyLogLastHoursIndex  OBJECT-TYPE
	SYNTAX     Integer32 (1..52)
	MAX-ACCESS not-accessible
	STATUS     current
	DESCRIPTION 
		"Index used for navigating the rows 1..52  of batteryEnergyLogLastHoursTable"
	::= { batteryEnergyLogLastHoursEntry 1 }

batteryEnergyLogLastHoursValue  OBJECT-TYPE
	SYNTAX     Integer32
	MAX-ACCESS read-only
	STATUS     current
	DESCRIPTION 
		"Energy value logged every hour."
	::= { batteryEnergyLogLastHoursEntry 2 }

batteryEnergyLogLastDaysNumberOfEntries  OBJECT-TYPE
	SYNTAX     Integer32 (0..52)
	MAX-ACCESS read-only
	STATUS     current
	DESCRIPTION 
		"This is the maximal number of entries stored in battery daily energy log."
	::= { batteryEnergyLog 4 }

batteryEnergyLogLastDaysTable  OBJECT-TYPE
	SYNTAX SEQUENCE OF BatteryEnergyLogLastDaysEntry
	MAX-ACCESS not-accessible
	STATUS     current
	DESCRIPTION 
		"This table contains daily energy log of battery."
	::= { batteryEnergyLog 5 }

batteryEnergyLogLastDaysEntry  OBJECT-TYPE
	SYNTAX 	BatteryEnergyLogLastDaysEntry
	MAX-ACCESS not-accessible
	STATUS     current
	DESCRIPTION 
		""
	INDEX { batteryEnergyLogLastDaysIndex }
	::= { batteryEnergyLogLastDaysTable 1 }

BatteryEnergyLogLastDaysEntry ::= SEQUENCE {
	batteryEnergyLogLastDaysIndex
		Integer32,
	batteryEnergyLogLastDaysValue
		Integer32
}

batteryEnergyLogLastDaysIndex  OBJECT-TYPE
	SYNTAX     Integer32 (1..52)
	MAX-ACCESS not-accessible
	STATUS     current
	DESCRIPTION 
		"Index used for navigating the rows 1..52  of batteryEnergyLogLastDaysTable"
	::= { batteryEnergyLogLastDaysEntry 1 }

batteryEnergyLogLastDaysValue  OBJECT-TYPE
	SYNTAX     Integer32
	MAX-ACCESS read-only
	STATUS     current
	DESCRIPTION 
		"Energy value logged every day."
	::= { batteryEnergyLogLastDaysEntry 2 }

batteryEnergyLogLastWeeksNumberOfEntries  OBJECT-TYPE
	SYNTAX     Integer32 (0..52)
	MAX-ACCESS read-only
	STATUS     current
	DESCRIPTION 
		"This is the maximal number of entries stored in battery weekly energy log."
	::= { batteryEnergyLog 6 }

batteryEnergyLogLastWeeksTable  OBJECT-TYPE
	SYNTAX SEQUENCE OF BatteryEnergyLogLastWeeksEntry
	MAX-ACCESS not-accessible
	STATUS     current
	DESCRIPTION 
		"This table contains weekly energy log of battery."
	::= { batteryEnergyLog 7 }

batteryEnergyLogLastWeeksEntry  OBJECT-TYPE
	SYNTAX 	BatteryEnergyLogLastWeeksEntry
	MAX-ACCESS not-accessible
	STATUS     current
	DESCRIPTION 
		""
	INDEX { batteryEnergyLogLastWeeksIndex }
	::= { batteryEnergyLogLastWeeksTable 1 }

BatteryEnergyLogLastWeeksEntry ::= SEQUENCE {
	batteryEnergyLogLastWeeksIndex
		Integer32,
	batteryEnergyLogLastWeeksValue
		Integer32
}

batteryEnergyLogLastWeeksIndex  OBJECT-TYPE
	SYNTAX     Integer32 (1..52)
	MAX-ACCESS not-accessible
	STATUS     current
	DESCRIPTION 
		"Index used for navigating the rows 1..52  of batteryEnergyLogLastWeekTable"
	::= { batteryEnergyLogLastWeeksEntry 1 }

batteryEnergyLogLastWeeksValue  OBJECT-TYPE
	SYNTAX     Integer32
	MAX-ACCESS read-only
	STATUS     current
	DESCRIPTION 
		"Energy value logged every week."
	::= { batteryEnergyLogLastWeeksEntry 2 }

batteryCycleLogTotalCycles  OBJECT-TYPE
	SYNTAX     Integer32
	MAX-ACCESS read-only
	STATUS     current
	DESCRIPTION 
		"This is the total number of battery discharge cycles."
	::= { batteryCycleLog 1 }

batteryCycleLogDaysNumberOfEntries  OBJECT-TYPE
	SYNTAX     Integer32 (0..52)
	MAX-ACCESS read-only
	STATUS     current
	DESCRIPTION 
		"This is the maximal number of entries stored in daily battery discharge cycle log."
	::= { batteryCycleLog 2 }

batteryCycleLogDaysTable  OBJECT-TYPE
	SYNTAX SEQUENCE OF BatteryCycleLogDaysEntry
	MAX-ACCESS not-accessible
	STATUS     current
	DESCRIPTION 
		"This table contains daily battery discharge cycle log."
	::= { batteryCycleLog 3 }

batteryCycleLogDaysEntry  OBJECT-TYPE
	SYNTAX 	BatteryCycleLogDaysEntry
	MAX-ACCESS not-accessible
	STATUS     current
	DESCRIPTION 
		""
	INDEX { batteryCycleLogDaysIndex }
	::= { batteryCycleLogDaysTable 1 }

BatteryCycleLogDaysEntry ::= SEQUENCE {
	batteryCycleLogDaysIndex
		Integer32,
	batteryCycleLogDaysValue
		Integer32
}

batteryCycleLogDaysIndex  OBJECT-TYPE
	SYNTAX     Integer32 (1..52)
	MAX-ACCESS not-accessible
	STATUS     current
	DESCRIPTION 
		"Index used for navigating the rows 1..52  of batteryCycleLogLastDaysTable"
	::= { batteryCycleLogDaysEntry 1 }

batteryCycleLogDaysValue  OBJECT-TYPE
	SYNTAX     Integer32
	MAX-ACCESS read-only
	STATUS     current
	DESCRIPTION 
		"Number of discharge cycles logged every day."
	::= { batteryCycleLogDaysEntry 2 }

batteryCycleLogWeeksNumberOfEntries  OBJECT-TYPE
	SYNTAX     Integer32 (0..52)
	MAX-ACCESS read-only
	STATUS     current
	DESCRIPTION 
		"This is the maximal number of entries stored in weeky battery discharge cycle log."
	::= { batteryCycleLog 4 }

batteryCycleLogWeeksTable  OBJECT-TYPE
	SYNTAX SEQUENCE OF BatteryCycleLogWeeksEntry
	MAX-ACCESS not-accessible
	STATUS     current
	DESCRIPTION 
		"This table contains weekly battery discharge cycle log."
	::= { batteryCycleLog 5 }

batteryCycleLogWeeksEntry  OBJECT-TYPE
	SYNTAX 	BatteryCycleLogWeeksEntry
	MAX-ACCESS not-accessible
	STATUS     current
	DESCRIPTION 
		""
	INDEX { batteryCycleLogWeeksIndex }
	::= { batteryCycleLogWeeksTable 1 }

BatteryCycleLogWeeksEntry ::= SEQUENCE {
	batteryCycleLogWeeksIndex
		Integer32,
	batteryCycleLogWeeksValue
		Integer32
}

batteryCycleLogWeeksIndex  OBJECT-TYPE
	SYNTAX     Integer32 (1..52)
	MAX-ACCESS not-accessible
	STATUS     current
	DESCRIPTION 
		"Index used for navigating the rows 1..52  of batteryCycleLogLastWeeksTable"
	::= { batteryCycleLogWeeksEntry 1 }

batteryCycleLogWeeksValue  OBJECT-TYPE
	SYNTAX     Integer32
	MAX-ACCESS read-only
	STATUS     current
	DESCRIPTION 
		"Number of discharge cycles logged every week."
	::= { batteryCycleLogWeeksEntry 2 }

batteryCycleLogMonthsNumberOfEntries  OBJECT-TYPE
	SYNTAX     Integer32 (0..52)
	MAX-ACCESS read-only
	STATUS     current
	DESCRIPTION 
		"This is the maximal number of entries stored in monthly battery discharge cycle log."
	::= { batteryCycleLog 6 }

batteryCycleLogMonthsTable  OBJECT-TYPE
	SYNTAX SEQUENCE OF BatteryCycleLogMonthsEntry
	MAX-ACCESS not-accessible
	STATUS     current
	DESCRIPTION 
		"This table contains monthly battery discharge cycle log."
	::= { batteryCycleLog 7 }

batteryCycleLogMonthsEntry  OBJECT-TYPE
	SYNTAX 	BatteryCycleLogMonthsEntry
	MAX-ACCESS not-accessible
	STATUS     current
	DESCRIPTION 
		""
	INDEX { batteryCycleLogMonthsIndex }
	::= { batteryCycleLogMonthsTable 1 }

BatteryCycleLogMonthsEntry ::= SEQUENCE {
	batteryCycleLogMonthsIndex
		Integer32,
	batteryCycleLogMonthsValue
		Integer32
}

batteryCycleLogMonthsIndex  OBJECT-TYPE
	SYNTAX     Integer32 (1..52)
	MAX-ACCESS not-accessible
	STATUS     current
	DESCRIPTION 
		"Index used for navigating the rows 1..52  of batteryCycleLogLastMonthTable"
	::= { batteryCycleLogMonthsEntry 1 }

batteryCycleLogMonthsValue  OBJECT-TYPE
	SYNTAX     Integer32
	MAX-ACCESS read-only
	STATUS     current
	DESCRIPTION 
		"Number of discharge cycles logged every month."
	::= { batteryCycleLogMonthsEntry 2 }

-- In smartpack2 system, highest inputControlUnitIndex corresponds to smartpack2 master controller

inputControlUnitsTable  OBJECT-TYPE
	SYNTAX SEQUENCE OF InputControlUnitsEntry
	MAX-ACCESS not-accessible
	STATUS     current
	DESCRIPTION 
		""
	::= { inputs 1 }

inputControlUnitsEntry  OBJECT-TYPE
	SYNTAX 	InputControlUnitsEntry
	MAX-ACCESS not-accessible
	STATUS     current
	DESCRIPTION 
		""
	INDEX { inputControlUnitIndex }
	::= { inputControlUnitsTable 1 }

InputControlUnitsEntry ::= SEQUENCE {
	inputControlUnitIndex
		Integer32,
	inputControlUnitNumberOfInputs
		Integer32
}

inputControlUnitIndex  OBJECT-TYPE
	SYNTAX     Integer32 (1..14)
	MAX-ACCESS not-accessible
	STATUS     current
	DESCRIPTION 
		"Index used for navigating the rows of inputControlUnitTable
		The size of the table is defined by the system  "
	::= { inputControlUnitsEntry 1 }

inputControlUnitNumberOfInputs  OBJECT-TYPE
	SYNTAX     Integer32 (0..8)
	MAX-ACCESS read-only
	STATUS     current
	DESCRIPTION 
		"Number of programmable inputs available in controller."
	::= { inputControlUnitsEntry 2 }

-- In smartpack2 system, highest inputControlUnitIndex corresponds to smartpack2 master controller

inputControlUnitInputTable  OBJECT-TYPE
	SYNTAX SEQUENCE OF InputControlUnitInputEntry
	MAX-ACCESS not-accessible
	STATUS     current
	DESCRIPTION 
		"This table contains the status of the programmable inputs for Control Units.
		"
	::= { inputs 2 }

inputControlUnitInputEntry  OBJECT-TYPE
	SYNTAX 	InputControlUnitInputEntry
	MAX-ACCESS not-accessible
	STATUS     current
	DESCRIPTION 
		""
	INDEX { inputControlUnitIndex, 
		inputControlUnitInputIndex }
	::= { inputControlUnitInputTable 1 }

InputControlUnitInputEntry ::= SEQUENCE {
	inputControlUnitInputIndex
		Integer32,
	inputControlUnitInputStatus
		INTEGER,
	inputControlUnitInputDescription
		DisplayString,
	inputControlUnitInputTrapRepeatCounter
		Counter32,
	inputControlUnitInputAlarmEnable
		INTEGER,
	inputControlUnitInputValue
		Integer32,
	inputControlUnitInputConfiguration
		INTEGER
}

inputControlUnitInputIndex  OBJECT-TYPE
	SYNTAX     Integer32 (1..8)
	MAX-ACCESS not-accessible
	STATUS     current
	DESCRIPTION 
		"Index used for navigating the rows  of inputControlUnitInputTable
		The size of the table is defined by the inputControlUnitNumberOfInputs   "
	::= { inputControlUnitInputEntry 1 }

inputControlUnitInputStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"Programmable input status.
		"
	::= { inputControlUnitInputEntry 2 }

inputControlUnitInputDescription  OBJECT-TYPE
	SYNTAX     DisplayString (SIZE(0..16))
	MAX-ACCESS read-write
	STATUS     current
	DESCRIPTION 
		"A textual description of the programmable input. This is stored in the system controller
		and can be changed by the user.  "
	::= { inputControlUnitInputEntry 3 }

inputControlUnitInputTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { inputControlUnitInputEntry 4 }

inputControlUnitInputAlarmEnable  OBJECT-TYPE
	SYNTAX     INTEGER {
		disabled (0),
		enabled (1)
	}
	MAX-ACCESS read-write
	STATUS     current
	DESCRIPTION 
		"This will enable or disable this inputs Alarm functionality.
		Setting 'disabled' here will turn off lock the status to 'disabled' state"
	::= { inputControlUnitInputEntry 5 }

inputControlUnitInputValue  OBJECT-TYPE
	SYNTAX     Integer32
	MAX-ACCESS read-write
	STATUS     current
	DESCRIPTION 
		"The inputs measured Value. Depending on the type of input, this may
		 represent a Voltage, a Temperature, a Current or a Boolean value.
		Note: This value can only be set for virtual input on SP2 master or Smartpack S. 
		When this value is set to '0', the input is deactivated; When this value is set to '1', 
		the input is activated; 
		if set to any other value, an Inconsistent Value error
		will be generated. "
	::= { inputControlUnitInputEntry 6 }

inputControlUnitInputConfiguration  OBJECT-TYPE
	SYNTAX     INTEGER {
		normallyOpen (1),
		normallyClosed (2),
		diodeMatrix (3),
		voltage (4),
		clock (5),
		virtual (6)
	}
	MAX-ACCESS read-write
	STATUS     current
	DESCRIPTION 
		"Configuration of the input type. Configurations available for different controllers are as follows:
		SP2 Master(clock, virtual), SP2 Basic(normally open, normally close),Compack(normally open,
		normallly close, diode matrix, voltage, clock)"
	::= { inputControlUnitInputEntry 7 }

inputIoUnitsTable  OBJECT-TYPE
	SYNTAX SEQUENCE OF InputIoUnitsEntry
	MAX-ACCESS not-accessible
	STATUS     current
	DESCRIPTION 
		""
	::= { inputs 3 }

inputIoUnitsEntry  OBJECT-TYPE
	SYNTAX 	InputIoUnitsEntry
	MAX-ACCESS not-accessible
	STATUS     current
	DESCRIPTION 
		""
	INDEX { inputIoUnitIndex }
	::= { inputIoUnitsTable 1 }

InputIoUnitsEntry ::= SEQUENCE {
	inputIoUnitIndex
		Integer32,
	inputIoUnitNumberOfInputs
		Integer32
}

inputIoUnitIndex  OBJECT-TYPE
	SYNTAX     Integer32 (1..14)
	MAX-ACCESS not-accessible
	STATUS     current
	DESCRIPTION 
		"Index used for navigating the rows of inputIoUnitsTable
		The size of the table is defined by the system  "
	::= { inputIoUnitsEntry 1 }

inputIoUnitNumberOfInputs  OBJECT-TYPE
	SYNTAX     Integer32 (0..8)
	MAX-ACCESS read-only
	STATUS     current
	DESCRIPTION 
		"Number of programmable inputs available in IO unit."
	::= { inputIoUnitsEntry 2 }

inputIoUnitProgInputTable  OBJECT-TYPE
	SYNTAX SEQUENCE OF InputIoUnitProgInputEntry
	MAX-ACCESS not-accessible
	STATUS     current
	DESCRIPTION 
		"This table contains the status of the programmable inputs for I/O monitor units.
		. "
	::= { inputs 4 }

-- This branch contains OIDs related to the systems generic input subsystem. 
-- Here you will find info about the programmable inputs found in system controllers, 
-- I/O monitors and AC Mains Monitor units.
-- 

inputIoUnitProgInputEntry  OBJECT-TYPE
	SYNTAX 	InputIoUnitProgInputEntry
	MAX-ACCESS not-accessible
	STATUS     current
	DESCRIPTION 
		""
	INDEX { inputIoUnitIndex, 
		inputIoUnitProgInputIndex }
	::= { inputIoUnitProgInputTable 1 }

InputIoUnitProgInputEntry ::= SEQUENCE {
	inputIoUnitProgInputIndex
		Integer32,
	inputIoUnitProgInputStatus
		INTEGER,
	inputIoUnitProgInputDescription
		DisplayString,
	inputIoUnitProgInputTrapRepeatCounter
		Counter32,
	inputIoUnitProgInputAlarmEnable
		INTEGER,
	inputIoUnitProgInputValue
		Integer32,
	inputIoUnitProgInputConfiguration
		INTEGER
}

inputIoUnitProgInputIndex  OBJECT-TYPE
	SYNTAX     Integer32 (1..6)
	MAX-ACCESS not-accessible
	STATUS     current
	DESCRIPTION 
		"The Index to the Input of the selected I/O monitor unit.
		Or the input number if you like."
	::= { inputIoUnitProgInputEntry 1 }

inputIoUnitProgInputStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"Programmable input status.
		"
	::= { inputIoUnitProgInputEntry 2 }

inputIoUnitProgInputDescription  OBJECT-TYPE
	SYNTAX     DisplayString (SIZE(0..16))
	MAX-ACCESS read-write
	STATUS     current
	DESCRIPTION 
		"A textual description of the programmable input in IO unit. This is stored in the system controller
		and can be changed by the user."
	::= { inputIoUnitProgInputEntry 3 }

inputIoUnitProgInputTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { inputIoUnitProgInputEntry 4 }

inputIoUnitProgInputAlarmEnable  OBJECT-TYPE
	SYNTAX     INTEGER {
		disabled (0),
		enabled (1)
	}
	MAX-ACCESS read-write
	STATUS     current
	DESCRIPTION 
		"This will enable or disable this inputs Alarm functionality.
		Setting 'disabled' here will turn off lock the status to 'disabled' state"
	::= { inputIoUnitProgInputEntry 5 }

inputIoUnitProgInputValue  OBJECT-TYPE
	SYNTAX     Integer32
	MAX-ACCESS read-only
	STATUS     current
	DESCRIPTION 
		"The inputs measured Value. Depending on the type of input, this may
		represent a Voltage, a Temperature, a Current or a Boolean value."
	::= { inputIoUnitProgInputEntry 6 }

inputIoUnitProgInputConfiguration  OBJECT-TYPE
	SYNTAX     INTEGER {
		normallyOpen (1),
		normallyClosed (2),
		diodeMatrix (3),
		voltage (4)
	}
	MAX-ACCESS read-write
	STATUS     current
	DESCRIPTION 
		"Configuration of the input type. Configurations available for IO unit are normally open,
		normally closed, diode matrix, voltage."
	::= { inputIoUnitProgInputEntry 7 }

outputControlUnitTable  OBJECT-TYPE
	SYNTAX SEQUENCE OF OutputControlUnitEntry
	MAX-ACCESS not-accessible
	STATUS     current
	DESCRIPTION 
		""
	::= { outputs 1 }

outputControlUnitEntry  OBJECT-TYPE
	SYNTAX 	OutputControlUnitEntry
	MAX-ACCESS not-accessible
	STATUS     current
	DESCRIPTION 
		""
	INDEX { outputControlUnitIndex }
	::= { outputControlUnitTable 1 }

OutputControlUnitEntry ::= SEQUENCE {
	outputControlUnitIndex
		Integer32,
	outputControlUnitNumberOfOutputs
		Integer32
}

outputControlUnitIndex  OBJECT-TYPE
	SYNTAX     Integer32 (1..14)
	MAX-ACCESS not-accessible
	STATUS     current
	DESCRIPTION 
		"Index used for navigating the rows of outputControlUnitTable
		The size of the table is defined by the system  "
	::= { outputControlUnitEntry 1 }

outputControlUnitNumberOfOutputs  OBJECT-TYPE
	SYNTAX     Integer32 (0..8)
	MAX-ACCESS read-only
	STATUS     current
	DESCRIPTION 
		"Number of outputs available in controller."
	::= { outputControlUnitEntry 2 }

outputControlUnitOutputTable  OBJECT-TYPE
	SYNTAX SEQUENCE OF OutputControlUnitOutputEntry
	MAX-ACCESS not-accessible
	STATUS     current
	DESCRIPTION 
		"This table contains the status of the outputs for Control Units."
	::= { outputs 2 }

outputControlUnitOutputEntry  OBJECT-TYPE
	SYNTAX 	OutputControlUnitOutputEntry
	MAX-ACCESS not-accessible
	STATUS     current
	DESCRIPTION 
		""
	INDEX { outputControlUnitIndex, 
		outputControlUnitOutputIndex }
	::= { outputControlUnitOutputTable 1 }

OutputControlUnitOutputEntry ::= SEQUENCE {
	outputControlUnitOutputIndex
		Integer32,
	outputControlUnitOutputStatus
		INTEGER,
	outputControlUnitOutputDescription
		DisplayString
}

outputControlUnitOutputIndex  OBJECT-TYPE
	SYNTAX     Integer32 (1..14)
	MAX-ACCESS not-accessible
	STATUS     current
	DESCRIPTION 
		"Index used for navigating the rows  of outputControlUnitoutputTable
		The size of the table is defined by the outputControlUnitNumberOfOutputs   "
	::= { outputControlUnitOutputEntry 1 }

outputControlUnitOutputStatus  OBJECT-TYPE
	SYNTAX     INTEGER {
		notenergized (0),
		energized (1),
		disconnected (2),
		connected (3)
	}
	MAX-ACCESS read-only
	STATUS     current
	DESCRIPTION 
		"General output relays may be 'energized' or 'not energized'. 'energized' and 
		'not energized' correspond 
		to normal and alarm condition respectively for normally
		activated configuration. 
		Latched contactors may have values 'disconnected' or 'connected' "
	::= { outputControlUnitOutputEntry 2 }

outputControlUnitOutputDescription  OBJECT-TYPE
	SYNTAX     DisplayString (SIZE(0..16))
	MAX-ACCESS read-write
	STATUS     current
	DESCRIPTION 
		"A textual description of the output. This is stored in the system controller
		and can be changed by the user. "
	::= { outputControlUnitOutputEntry 3 }

outputIoUnitTable  OBJECT-TYPE
	SYNTAX SEQUENCE OF OutputIoUnitEntry
	MAX-ACCESS not-accessible
	STATUS     current
	DESCRIPTION 
		""
	::= { outputs 3 }

outputIoUnitEntry  OBJECT-TYPE
	SYNTAX 	OutputIoUnitEntry
	MAX-ACCESS not-accessible
	STATUS     current
	DESCRIPTION 
		""
	INDEX { outputIoUnitIndex }
	::= { outputIoUnitTable 1 }

OutputIoUnitEntry ::= SEQUENCE {
	outputIoUnitIndex
		Integer32,
	outputIoUnitNumberOfOutputs
		Integer32
}

outputIoUnitIndex  OBJECT-TYPE
	SYNTAX     Integer32 (1..14)
	MAX-ACCESS not-accessible
	STATUS     current
	DESCRIPTION 
		"Index used for navigating the rows of outputIoUnitTable
		The size of the table is defined by the system  "
	::= { outputIoUnitEntry 1 }

outputIoUnitNumberOfOutputs  OBJECT-TYPE
	SYNTAX     Integer32 (0..8)
	MAX-ACCESS read-only
	STATUS     current
	DESCRIPTION 
		"Number of outputs available in IO unit."
	::= { outputIoUnitEntry 2 }

outputIoUnitOutputTable  OBJECT-TYPE
	SYNTAX SEQUENCE OF OutputIoUnitOutputEntry
	MAX-ACCESS not-accessible
	STATUS     current
	DESCRIPTION 
		"This table contains the status of the outputs for IO Units."
	::= { outputs 4 }

outputIoUnitOutputEntry  OBJECT-TYPE
	SYNTAX 	OutputIoUnitOutputEntry
	MAX-ACCESS not-accessible
	STATUS     current
	DESCRIPTION 
		""
	INDEX { outputIoUnitIndex, 
		outputIoUnitOutputIndex }
	::= { outputIoUnitOutputTable 1 }

OutputIoUnitOutputEntry ::= SEQUENCE {
	outputIoUnitOutputIndex
		Integer32,
	outputIoUnitOutputStatus
		INTEGER,
	outputIoUnitOutputDescription
		DisplayString
}

outputIoUnitOutputIndex  OBJECT-TYPE
	SYNTAX     Integer32 (1..14)
	MAX-ACCESS not-accessible
	STATUS     current
	DESCRIPTION 
		"Index used for navigating the rows  of outputIOUnitOutputTable
		The size of the table is defined by the outputIOUnitNumberOfOutputs "
	::= { outputIoUnitOutputEntry 1 }

outputIoUnitOutputStatus  OBJECT-TYPE
	SYNTAX     INTEGER {
		notenergized (0),
		energized (1),
		disconnected (2),
		connected (3)
	}
	MAX-ACCESS read-only
	STATUS     current
	DESCRIPTION 
		"General output relays may be 'energized' or 'not energized'. 
		Latched contactors may have values 'disconnected' or 'connected' "
	::= { outputIoUnitOutputEntry 2 }

outputIoUnitOutputDescription  OBJECT-TYPE
	SYNTAX     DisplayString (SIZE(0..16))
	MAX-ACCESS read-write
	STATUS     current
	DESCRIPTION 
		"A textual description of the output in IO unit. This is stored in the system controller
		and can be changed by the user. "
	::= { outputIoUnitOutputEntry 3 }

controlSystemStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of control system subsystem"
	::= { controlSystem 1 }

controlSystemClock  OBJECT-TYPE
	SYNTAX     DateAndTime (SIZE(8..11))
	MAX-ACCESS read-write
	STATUS     current
	DESCRIPTION 
		"This is the system time."
	::= { controlSystem 2 }

controlSystemNumberOfControlUnits  OBJECT-TYPE
	SYNTAX     Integer32 (1..14)
	MAX-ACCESS read-write
	STATUS     current
	DESCRIPTION 
		"Total number of controllers (SP2 Basic, Compack, Smartpack S, Smartpack)"
	::= { controlSystem 3 }

snmpSendOffTraps  OBJECT-TYPE
	SYNTAX     INTEGER {
		disabled (0),
		enabled (1)
	}
	MAX-ACCESS read-write
	STATUS     current
	DESCRIPTION 
		"When this is enabled, a trap is sent when a alarm condition goes off ."
	::= { snmp 1 }

snmpTrapRepeatRate  OBJECT-TYPE
	SYNTAX     Integer32 (0..1440)
	MAX-ACCESS read-write
	STATUS     current
	DESCRIPTION 
		"The time between every repeated trap when an alarm condition is on. 
		To turn repetetive traps off, set to zero.  Can be 0 to 1440 minutes i.e 24 hours."
	::= { snmp 2 }

snmpHeartBeatTrapRepeatRate  OBJECT-TYPE
	SYNTAX     Integer32 (0..1440)
	MAX-ACCESS read-write
	STATUS     current
	DESCRIPTION 
		"The time between every heartbeat trap when an alarm condition is on. 
		To turn heartbeat traps off, set to zero.  Can be 0 to 1440 minutes i.e 24 hours."
	::= { snmp 3 }

snmpInhibitTraps  OBJECT-TYPE
	SYNTAX     INTEGER {
		disabled (0),
		enabled (1)
	}
	MAX-ACCESS read-write
	STATUS     current
	DESCRIPTION 
		"When this is enabled, no trap is sent regardless of alarm conditions.
		"
	::= { snmp 4 }

controlSystemResetManualAlarms  OBJECT-TYPE
	SYNTAX     INTEGER {
		pushbutton (0),
		resetalarm (1)
	}
	MAX-ACCESS read-write
	STATUS     current
	DESCRIPTION 
		"Reset manual alarms and put buzzer into silence."
	::= { controlSystem 5 }

controlSystemResetNumberOfModules  OBJECT-TYPE
	SYNTAX     INTEGER {
		pushbutton (0),
		resetnumber (1)
	}
	MAX-ACCESS read-write
	STATUS     current
	DESCRIPTION 
		"If set to '1', the number of modules (rectifier, solar charger, wind charger, control units, etc.)
		will be reset, and only those modules communicating are counted."
	::= { controlSystem 6 }

controlSystemIoUnitsNumberOfUnits  OBJECT-TYPE
	SYNTAX     Integer32 (0..14)
	MAX-ACCESS read-write
	STATUS     current
	DESCRIPTION 
		"This is the number of IO units installed in the system."
	::= { controlSystemIoUnits 1 }

controlSystemIoUnitsTable  OBJECT-TYPE
	SYNTAX SEQUENCE OF ControlSystemIoUnitsEntry
	MAX-ACCESS not-accessible
	STATUS     current
	DESCRIPTION 
		""
	::= { controlSystemIoUnits 2 }

controlSystemIoUnitsEntry  OBJECT-TYPE
	SYNTAX 	ControlSystemIoUnitsEntry
	MAX-ACCESS not-accessible
	STATUS     current
	DESCRIPTION 
		""
	INDEX { controlSystemIoUnitIndex }
	::= { controlSystemIoUnitsTable 1 }

ControlSystemIoUnitsEntry ::= SEQUENCE {
	controlSystemIoUnitIndex
		Integer32,
	controlSystemIoUnitNumberOfTemperatures
		Integer32,
	controlSystemIoUnitNumberOfFans
		Integer32
}

controlSystemIoUnitIndex  OBJECT-TYPE
	SYNTAX     Integer32 (1..14)
	MAX-ACCESS not-accessible
	STATUS     current
	DESCRIPTION 
		"Index used for navigating the rows of controlSystemIoUnitTable
		The size of the table is defined by the system"
	::= { controlSystemIoUnitsEntry 1 }

controlSystemIoUnitNumberOfTemperatures  OBJECT-TYPE
	SYNTAX     Integer32 (0..4)
	MAX-ACCESS read-only
	STATUS     current
	DESCRIPTION 
		"Number of temperature measurements available in IO unit"
	::= { controlSystemIoUnitsEntry 2 }

controlSystemIoUnitNumberOfFans  OBJECT-TYPE
	SYNTAX     Integer32 (0..4)
	MAX-ACCESS read-only
	STATUS     current
	DESCRIPTION 
		"Number of fan measurements available in IO unit"
	::= { controlSystemIoUnitsEntry 3 }

controlSystemIoUnitTemperatureTable  OBJECT-TYPE
	SYNTAX SEQUENCE OF ControlSystemIoUnitTemperatureEntry
	MAX-ACCESS not-accessible
	STATUS     current
	DESCRIPTION 
		""
	::= { controlSystemIoUnits 3 }

controlSystemIoUnitTemperatureEntry  OBJECT-TYPE
	SYNTAX 	ControlSystemIoUnitTemperatureEntry
	MAX-ACCESS not-accessible
	STATUS     current
	DESCRIPTION 
		""
	INDEX { controlSystemIoUnitIndex, 
		controlSystemIoUnitTemperatureIndex }
	::= { controlSystemIoUnitTemperatureTable 1 }

ControlSystemIoUnitTemperatureEntry ::= SEQUENCE {
	controlSystemIoUnitTemperatureIndex
		Integer32,
	controlSystemIoUnitTemperatureStatus
		INTEGER,
	controlSystemIoUnitTemperatureDescription
		DisplayString,
	controlSystemIoUnitTemperatureTrapRepeatCounter
		Counter32,
	controlSystemIoUnitTemperatureAlarmEnable
		INTEGER,
	controlSystemIoUnitTemperatureValue
		Integer32,
	controlSystemIoUnitTemperatureMajorHighLevel
		Integer32,
	controlSystemIoUnitTemperatureMinorHighLevel
		Integer32,
	controlSystemIoUnitTemperatureMinorLowLevel
		Integer32,
	controlSystemIoUnitTemperatureMajorLowLevel
		Integer32
}

controlSystemIoUnitTemperatureIndex  OBJECT-TYPE
	SYNTAX     Integer32 (1..2)
	MAX-ACCESS not-accessible
	STATUS     current
	DESCRIPTION 
		"Index used for navigating the rows  of controlSystemIoUnitTemperatureTable
		The size of the table is defined by the controlSystemIoUnitNumberOfTemperatures"
	::= { controlSystemIoUnitTemperatureEntry 1 }

controlSystemIoUnitTemperatureStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of temperature monitor"
	::= { controlSystemIoUnitTemperatureEntry 2 }

controlSystemIoUnitTemperatureDescription  OBJECT-TYPE
	SYNTAX     DisplayString (SIZE(0..16))
	MAX-ACCESS read-write
	STATUS     current
	DESCRIPTION 
		"A textual description of the temperature monitor in control system. This is stored in the system controller
		and can be changed by the user."
	::= { controlSystemIoUnitTemperatureEntry 3 }

controlSystemIoUnitTemperatureTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { controlSystemIoUnitTemperatureEntry 4 }

controlSystemIoUnitTemperatureAlarmEnable  OBJECT-TYPE
	SYNTAX     INTEGER {
		disabled (0),
		enabled (1)
	}
	MAX-ACCESS read-write
	STATUS     current
	DESCRIPTION 
		"This value once enabled, the alarm condition of the monitor will be reported."
	::= { controlSystemIoUnitTemperatureEntry 5 }

controlSystemIoUnitTemperatureValue  OBJECT-TYPE
	SYNTAX     Integer32
	MAX-ACCESS read-only
	STATUS     current
	DESCRIPTION 
		"The measured temperature value."
	::= { controlSystemIoUnitTemperatureEntry 6 }

controlSystemIoUnitTemperatureMajorHighLevel  OBJECT-TYPE
	SYNTAX     Integer32
	MAX-ACCESS read-write
	STATUS     current
	DESCRIPTION 
		"The major high alarm limit"
	::= { controlSystemIoUnitTemperatureEntry 7 }

controlSystemIoUnitTemperatureMinorHighLevel  OBJECT-TYPE
	SYNTAX     Integer32
	MAX-ACCESS read-write
	STATUS     current
	DESCRIPTION 
		"The minor high alarm limit"
	::= { controlSystemIoUnitTemperatureEntry 8 }

controlSystemIoUnitTemperatureMinorLowLevel  OBJECT-TYPE
	SYNTAX     Integer32
	MAX-ACCESS read-write
	STATUS     current
	DESCRIPTION 
		"The minor low alarm limit"
	::= { controlSystemIoUnitTemperatureEntry 9 }

controlSystemIoUnitTemperatureMajorLowLevel  OBJECT-TYPE
	SYNTAX     Integer32
	MAX-ACCESS read-write
	STATUS     current
	DESCRIPTION 
		"The major low alarm limit"
	::= { controlSystemIoUnitTemperatureEntry 10 }

controlSystemIoUnitFanTable  OBJECT-TYPE
	SYNTAX SEQUENCE OF ControlSystemIoUnitFanEntry
	MAX-ACCESS not-accessible
	STATUS     current
	DESCRIPTION 
		""
	::= { controlSystemIoUnits 4 }

controlSystemIoUnitFanEntry  OBJECT-TYPE
	SYNTAX 	ControlSystemIoUnitFanEntry
	MAX-ACCESS not-accessible
	STATUS     current
	DESCRIPTION 
		""
	INDEX { controlSystemIoUnitIndex, 
		controlSystemIoUnitFanIndex }
	::= { controlSystemIoUnitFanTable 1 }

ControlSystemIoUnitFanEntry ::= SEQUENCE {
	controlSystemIoUnitFanIndex
		Integer32,
	controlSystemIoUnitFanSpeedValue
		Integer32,
	controlSystemIoUnitFanSpeedDeviation
		Integer32,
	controlSystemIoUnitFanControl
		Integer32
}

controlSystemIoUnitFanIndex  OBJECT-TYPE
	SYNTAX     Integer32 (1..2)
	MAX-ACCESS not-accessible
	STATUS     current
	DESCRIPTION 
		"Index used for navigating the rows 1..2 of ioUnitFan Table"
	::= { controlSystemIoUnitFanEntry 1 }

controlSystemIoUnitFanSpeedValue  OBJECT-TYPE
	SYNTAX     Integer32
	MAX-ACCESS read-only
	STATUS     current
	DESCRIPTION 
		"The measured fan speed"
	::= { controlSystemIoUnitFanEntry 2 }

controlSystemIoUnitFanSpeedDeviation  OBJECT-TYPE
	SYNTAX     Integer32
	MAX-ACCESS read-only
	STATUS     current
	DESCRIPTION 
		"The measured fan speed deviation"
	::= { controlSystemIoUnitFanEntry 3 }

controlSystemIoUnitFanControl  OBJECT-TYPE
	SYNTAX     Integer32
	MAX-ACCESS read-only
	STATUS     current
	DESCRIPTION 
		"Fan speed control value in percentage"
	::= { controlSystemIoUnitFanEntry 4 }

controlUnitNumberOfUnits  OBJECT-TYPE
	SYNTAX     Integer32 (1..254)
	MAX-ACCESS read-only
	STATUS     current
	DESCRIPTION 
		"Total number of control units installed in system."
	::= { controlSystemInventory 1 }

controlUnitTable  OBJECT-TYPE
	SYNTAX SEQUENCE OF ControlUnitEntry
	MAX-ACCESS not-accessible
	STATUS     current
	DESCRIPTION 
		"A table containing an inventory listing. Each row represent one of the system hardware 
		unit that is connected to the can bus. These units are system controllers, 
		battery monitors, I/O units, AC Mains Monitor boxes and load monitors.  Due to the system 
		architechture the tables index are not contiguous. Each unit type har its own address 
		range on the can bus.  All unit types except the system controller may contain 
		from 0 to 14 units.  The system controlller can never be zero.  Then there is no powersystem.
		
		"
	::= { controlSystemInventory 2 }

controlUnitEntry  OBJECT-TYPE
	SYNTAX 	ControlUnitEntry
	MAX-ACCESS not-accessible
	STATUS     current
	DESCRIPTION 
		"One row  in the table containing all hardware units connected to the canbus.   "
	INDEX { controlUnitIndex }
	::= { controlUnitTable 1 }

ControlUnitEntry ::= SEQUENCE {
	controlUnitIndex
		Integer32,
	controlUnitDescription
		DisplayString,
	controlUnitStatus
		INTEGER,
	controlUnitSerialNumber
		DisplayString,
	controlUnitHwPartNumber
		DisplayString,
	controlUnitHwVersion
		DisplayString,
	controlUnitSwPartNumber
		DisplayString,
	controlUnitSwVersion
		DisplayString
}

controlUnitIndex  OBJECT-TYPE
	SYNTAX     Integer32 (1..254)
	MAX-ACCESS not-accessible
	STATUS     current
	DESCRIPTION 
		"Index used for navigating the rows  of controlUnitTable
		The size of the table is defined by the controlUnitNumberOfUnits   "
	::= { controlUnitEntry 1 }

controlUnitDescription  OBJECT-TYPE
	SYNTAX     DisplayString (SIZE(0..32))
	MAX-ACCESS read-only
	STATUS     current
	DESCRIPTION 
		"A textual description of the control unit"
	::= { controlUnitEntry 2 }

controlUnitStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The overall status of the control unit."
	::= { controlUnitEntry 3 }

controlUnitSerialNumber  OBJECT-TYPE
	SYNTAX     DisplayString (SIZE(0..12))
	MAX-ACCESS read-only
	STATUS     current
	DESCRIPTION 
		"Serial number of the control unit."
	::= { controlUnitEntry 4 }

controlUnitHwPartNumber  OBJECT-TYPE
	SYNTAX     DisplayString (SIZE(0..12))
	MAX-ACCESS read-only
	STATUS     current
	DESCRIPTION 
		"Hardware part number of the control unit."
	::= { controlUnitEntry 5 }

controlUnitHwVersion  OBJECT-TYPE
	SYNTAX     DisplayString (SIZE(0..20))
	MAX-ACCESS read-only
	STATUS     current
	DESCRIPTION 
		"Hardware version of the control unit."
	::= { controlUnitEntry 6 }

controlUnitSwPartNumber  OBJECT-TYPE
	SYNTAX     DisplayString (SIZE(0..12))
	MAX-ACCESS read-only
	STATUS     current
	DESCRIPTION 
		"Software part number of the control unit."
	::= { controlUnitEntry 7 }

controlUnitSwVersion  OBJECT-TYPE
	SYNTAX     DisplayString (SIZE(0..20))
	MAX-ACCESS read-only
	STATUS     current
	DESCRIPTION 
		"Software version of the control unit."
	::= { controlUnitEntry 8 }

currentMonitorsNumberOfUnits  OBJECT-TYPE
	SYNTAX     Integer32 (0..14)
	MAX-ACCESS read-write
	STATUS     current
	DESCRIPTION 
		"This is the number of current monitors installed in the system."
	::= { currentMonitors 1 }

currentMonitorsTable  OBJECT-TYPE
	SYNTAX SEQUENCE OF CurrentMonitorsEntry
	MAX-ACCESS not-accessible
	STATUS     current
	DESCRIPTION 
		""
	::= { currentMonitors 2 }

currentMonitorsEntry  OBJECT-TYPE
	SYNTAX 	CurrentMonitorsEntry
	MAX-ACCESS not-accessible
	STATUS     current
	DESCRIPTION 
		""
	INDEX { currentMonitorIndex }
	::= { currentMonitorsTable 1 }

CurrentMonitorsEntry ::= SEQUENCE {
	currentMonitorIndex
		Integer32,
	currentMonitorType
		INTEGER,
	currentMonitorId
		Integer32,
	currentMonitorNumberOfFuses
		Integer32,
	currentMonitorNumberOfCurrents
		Integer32
}

currentMonitorIndex  OBJECT-TYPE
	SYNTAX     Integer32 (1..14)
	MAX-ACCESS not-accessible
	STATUS     current
	DESCRIPTION 
		"Index used for navigating the rows of currentMonitorsTable
		The size of the table is defined by the system"
	::= { currentMonitorsEntry 1 }

currentMonitorType  OBJECT-TYPE
	SYNTAX     INTEGER {
		stdLoadMonitor (1),
		loadCurrMonitor (2),
		rectCurrMonitor (3),
		dcdcCurrMonitor (4),
		solarCurrMonitor (5),
		windCurrMonitor (6),
		fuelcellCurrMonitor (7)
	}
	MAX-ACCESS read-only
	STATUS     current
	DESCRIPTION 
		"This shows if the current monitor is configured as standard load monitor (1), load current 
		monitor (2), rectifier current monitor (3), dcdc current monitor (4), solar current monitor (5),
		wind current monitor (6) or fuel cell current monitor (7)."
	::= { currentMonitorsEntry 2 }

currentMonitorId  OBJECT-TYPE
	SYNTAX     Integer32
	MAX-ACCESS read-only
	STATUS     current
	DESCRIPTION 
		"This is the unit index for each current monitor type."
	::= { currentMonitorsEntry 3 }

currentMonitorNumberOfFuses  OBJECT-TYPE
	SYNTAX     Integer32 (0..8)
	MAX-ACCESS read-only
	STATUS     current
	DESCRIPTION 
		"Number of fuse measurements in current monitor."
	::= { currentMonitorsEntry 4 }

currentMonitorNumberOfCurrents  OBJECT-TYPE
	SYNTAX     Integer32 (0..8)
	MAX-ACCESS read-only
	STATUS     current
	DESCRIPTION 
		"Number of current measurements in current monitor."
	::= { currentMonitorsEntry 5 }

currentMonitorFuseTable  OBJECT-TYPE
	SYNTAX SEQUENCE OF CurrentMonitorFuseEntry
	MAX-ACCESS not-accessible
	STATUS     current
	DESCRIPTION 
		""
	::= { currentMonitors 3 }

currentMonitorFuseEntry  OBJECT-TYPE
	SYNTAX 	CurrentMonitorFuseEntry
	MAX-ACCESS not-accessible
	STATUS     current
	DESCRIPTION 
		""
	INDEX { currentMonitorIndex, 
		currentMonitorFuseIndex }
	::= { currentMonitorFuseTable 1 }

CurrentMonitorFuseEntry ::= SEQUENCE {
	currentMonitorFuseIndex
		Integer32,
	currentMonitorFuseStatus
		INTEGER,
	currentMonitorFuseDescription
		DisplayString,
	currentMonitorFuseTrapRepeatCounter
		Counter32,
	currentMonitorFuseAlarmEnable
		INTEGER,
	currentMonitorFuseValue
		Integer32
}

currentMonitorFuseIndex  OBJECT-TYPE
	SYNTAX     Integer32 (1..8)
	MAX-ACCESS not-accessible
	STATUS     current
	DESCRIPTION 
		"Index used for navigating the rows  of currentMonitorFuseTable
		The size of the table is defined by the currentMonitorNumberOfFuses"
	::= { currentMonitorFuseEntry 1 }

currentMonitorFuseStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of fuse in current monitor"
	::= { currentMonitorFuseEntry 2 }

currentMonitorFuseDescription  OBJECT-TYPE
	SYNTAX     DisplayString (SIZE(1..16))
	MAX-ACCESS read-write
	STATUS     current
	DESCRIPTION 
		"A textual description of the fuse monitor. This is stored in the system controller
		and can be changed by the user."
	::= { currentMonitorFuseEntry 3 }

currentMonitorFuseTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { currentMonitorFuseEntry 4 }

currentMonitorFuseAlarmEnable  OBJECT-TYPE
	SYNTAX     INTEGER {
		disabled (0),
		enabled (1)
	}
	MAX-ACCESS read-write
	STATUS     current
	DESCRIPTION 
		"This value once enabled, the alarm condition of the monitor will be reported."
	::= { currentMonitorFuseEntry 5 }

currentMonitorFuseValue  OBJECT-TYPE
	SYNTAX     Integer32
	MAX-ACCESS read-only
	STATUS     current
	DESCRIPTION 
		"The measured fuse value."
	::= { currentMonitorFuseEntry 6 }

currentMonitorCurrentTable  OBJECT-TYPE
	SYNTAX SEQUENCE OF CurrentMonitorCurrentEntry
	MAX-ACCESS not-accessible
	STATUS     current
	DESCRIPTION 
		""
	::= { currentMonitors 4 }

currentMonitorCurrentEntry  OBJECT-TYPE
	SYNTAX 	CurrentMonitorCurrentEntry
	MAX-ACCESS not-accessible
	STATUS     current
	DESCRIPTION 
		""
	INDEX { currentMonitorIndex, 
		currentMonitorCurrentIndex }
	::= { currentMonitorCurrentTable 1 }

CurrentMonitorCurrentEntry ::= SEQUENCE {
	currentMonitorCurrentIndex
		Integer32,
	currentMonitorCurrentStatus
		INTEGER,
	currentMonitorCurrentDescription
		DisplayString,
	currentMonitorCurrentTrapRepeatCounter
		Counter32,
	currentMonitorCurrentAlarmEnable
		INTEGER,
	currentMonitorCurrentValue
		Integer32,
	currentMonitorCurrentMajorAlarmLevel
		Integer32,
	currentMonitorCurrentMinorAlarmLevel
		Integer32
}

currentMonitorCurrentIndex  OBJECT-TYPE
	SYNTAX     Integer32 (1..8)
	MAX-ACCESS not-accessible
	STATUS     current
	DESCRIPTION 
		"Index used for navigating the rows  of currentMonitorCurrentTable
		The size of the table is defined by the currentMonitorNumberOfCurrents"
	::= { currentMonitorCurrentEntry 1 }

currentMonitorCurrentStatus  OBJECT-TYPE
	SYNTAX     INTEGER {
		error (0),
		normal (1),
		minorAlarm (2),
		majorAlarm (3),
		disabled (4),
		disconnected (5),
		notPresent (6),
		minorAndMajor (7),
		majorLow (8),
		minorLow (9),
		majorHigh (10),
		minorHigh (11),
		event (12),
		valueVolt (13),
		valueAmp (14),
		valueTemp (15),
		valueUnit (16),
		valuePerCent (17),
		critical (18),
		warning (19)
	}
	MAX-ACCESS read-only
	STATUS     current
	DESCRIPTION 
		"The status of current in current monitor"
	::= { currentMonitorCurrentEntry 2 }

currentMonitorCurrentDescription  OBJECT-TYPE
	SYNTAX     DisplayString (SIZE(0..16))
	MAX-ACCESS read-write
	STATUS     current
	DESCRIPTION 
		"A textual description of the current monitor. This is stored in the system controller
		and can be changed by the user."
	::= { currentMonitorCurrentEntry 3 }

currentMonitorCurrentTrapRepeatCounter  OBJECT-TYPE
	SYNTAX     Counter32
	MAX-ACCESS accessible-for-notify
	STATUS     current
	DESCRIPTION 
		"The number of consecutive times this alamcondition has been transmitted in a trap. 
		When trap repetition is enabled, this counter increments every time this trap is repeated.  
		The counter is automatically set to zero when the alarm condition is reset and the
		alarm goes off"
	::= { currentMonitorCurrentEntry 4 }

currentMonitorCurrentAlarmEnable  OBJECT-TYPE
	SYNTAX     INTEGER {
		disabled (0),
		enabled (1)
	}
	MAX-ACCESS read-write
	STATUS     current
	DESCRIPTION 
		"This value once enabled, the alarm condition of the monitor will be reported."
	::= { currentMonitorCurrentEntry 5 }

currentMonitorCurrentValue  OBJECT-TYPE
	SYNTAX     Integer32
	MAX-ACCESS read-only
	STATUS     current
	DESCRIPTION 
		"The measured current value."
	::= { currentMonitorCurrentEntry 6 }

currentMonitorCurrentMajorAlarmLevel  OBJECT-TYPE
	SYNTAX     Integer32
	MAX-ACCESS read-write
	STATUS     current
	DESCRIPTION 
		"The major alarm limit"
	::= { currentMonitorCurrentEntry 7 }

currentMonitorCurrentMinorAlarmLevel  OBJECT-TYPE
	SYNTAX     Integer32
	MAX-ACCESS read-write
	STATUS     current
	DESCRIPTION 
		"The minor alarm limit"
	::= { currentMonitorCurrentEntry 8 }

currentMonitorEnergyLogAccumulatedTable  OBJECT-TYPE
	SYNTAX SEQUENCE OF CurrentMonitorEnergyLogAccumulatedEntry
	MAX-ACCESS not-accessible
	STATUS     current
	DESCRIPTION 
		"This table contains the accumulated energy consumption measured in current monitor"
	::= { currentMonitors 5 }

currentMonitorEnergyLogAccumulatedEntry  OBJECT-TYPE
	SYNTAX 	CurrentMonitorEnergyLogAccumulatedEntry
	MAX-ACCESS not-accessible
	STATUS     current
	DESCRIPTION 
		""
	INDEX { currentMonitorIndex, 
		currentMonitorCurrentIndex }
	::= { currentMonitorEnergyLogAccumulatedTable 1 }

CurrentMonitorEnergyLogAccumulatedEntry ::= SEQUENCE {
	currentMonitorEnergyLogAccumulated
		Integer32
}

currentMonitorEnergyLogAccumulated  OBJECT-TYPE
	SYNTAX     Integer32
	MAX-ACCESS read-only
	STATUS     current
	DESCRIPTION 
		"The accumulated energy consumption value"
	::= { currentMonitorEnergyLogAccumulatedEntry 1 }

currentMonitorEnergyLogLastHoursNumberOfEntries  OBJECT-TYPE
	SYNTAX     Integer32 (0..52)
	MAX-ACCESS read-only
	STATUS     current
	DESCRIPTION 
		"This is the maximal number of entries stored in hourly energy log"
	::= { currentMonitors 6 }

currentMonitorEnergyLogLastHoursTable  OBJECT-TYPE
	SYNTAX SEQUENCE OF CurrentMonitorEnergyLogLastHoursEntry
	MAX-ACCESS not-accessible
	STATUS     current
	DESCRIPTION 
		"This table contains energy consumption values logged every hour in current monitor."
	::= { currentMonitors 7 }

currentMonitorEnergyLogLastHoursEntry  OBJECT-TYPE
	SYNTAX 	CurrentMonitorEnergyLogLastHoursEntry
	MAX-ACCESS not-accessible
	STATUS     current
	DESCRIPTION 
		""
	INDEX { currentMonitorIndex, 
		currentMonitorCurrentIndex, 
		currentMonitorEnergyLogLastHoursIndex }
	::= { currentMonitorEnergyLogLastHoursTable 1 }

CurrentMonitorEnergyLogLastHoursEntry ::= SEQUENCE {
	currentMonitorEnergyLogLastHoursIndex
		Integer32,
	currentMonitorEnergyLogLastHoursValue
		Integer32
}

currentMonitorEnergyLogLastHoursIndex  OBJECT-TYPE
	SYNTAX     Integer32 (1..52)
	MAX-ACCESS not-accessible
	STATUS     current
	DESCRIPTION 
		"Index used for navigating the rows 1..52  of currentMonitorEnergyLogLastHoursTable"
	::= { currentMonitorEnergyLogLastHoursEntry 1 }

currentMonitorEnergyLogLastHoursValue  OBJECT-TYPE
	SYNTAX     Integer32
	MAX-ACCESS read-only
	STATUS     current
	DESCRIPTION 
		"Energy consumption value logged every hour in current monitor."
	::= { currentMonitorEnergyLogLastHoursEntry 2 }

currentMonitorEnergyLogLastDaysNumberOfEntries  OBJECT-TYPE
	SYNTAX     Integer32 (0..52)
	MAX-ACCESS read-only
	STATUS     current
	DESCRIPTION 
		"This is the maximal number of entries stored in daily energy log"
	::= { currentMonitors 8 }

currentMonitorEnergyLogLastDaysTable  OBJECT-TYPE
	SYNTAX SEQUENCE OF CurrentMonitorEnergyLogLastDaysEntry
	MAX-ACCESS not-accessible
	STATUS     current
	DESCRIPTION 
		"This table contains energy consumption values logged every day in current monitor."
	::= { currentMonitors 9 }

currentMonitorEnergyLogLastDaysEntry  OBJECT-TYPE
	SYNTAX 	CurrentMonitorEnergyLogLastDaysEntry
	MAX-ACCESS not-accessible
	STATUS     current
	DESCRIPTION 
		""
	INDEX { currentMonitorIndex, 
		currentMonitorCurrentIndex, 
		currentMonitorEnergyLogLastDaysIndex }
	::= { currentMonitorEnergyLogLastDaysTable 1 }

CurrentMonitorEnergyLogLastDaysEntry ::= SEQUENCE {
	currentMonitorEnergyLogLastDaysIndex
		Integer32,
	currentMonitorEnergyLogLastDaysValue
		Integer32
}

currentMonitorEnergyLogLastDaysIndex  OBJECT-TYPE
	SYNTAX     Integer32 (1..52)
	MAX-ACCESS not-accessible
	STATUS     current
	DESCRIPTION 
		"Index used for navigating the rows 1..52  of currentMonitorEnergyLogLastDaysTable"
	::= { currentMonitorEnergyLogLastDaysEntry 1 }

currentMonitorEnergyLogLastDaysValue  OBJECT-TYPE
	SYNTAX     Integer32
	MAX-ACCESS read-only
	STATUS     current
	DESCRIPTION 
		"Energy consumption value logged every day in current monitor."
	::= { currentMonitorEnergyLogLastDaysEntry 2 }

currentMonitorEnergyLogLastWeeksNumberOfEntries  OBJECT-TYPE
	SYNTAX     Integer32 (0..52)
	MAX-ACCESS read-only
	STATUS     current
	DESCRIPTION 
		"This is the maximal number of entries stored in weekly energy log"
	::= { currentMonitors 10 }

currentMonitorEnergyLogLastWeeksTable  OBJECT-TYPE
	SYNTAX SEQUENCE OF CurrentMonitorEnergyLogLastWeeksEntry
	MAX-ACCESS not-accessible
	STATUS     current
	DESCRIPTION 
		"This table contains energy consumption values logged every week in current monitor."
	::= { currentMonitors 11 }

currentMonitorEnergyLogLastWeeksEntry  OBJECT-TYPE
	SYNTAX 	CurrentMonitorEnergyLogLastWeeksEntry
	MAX-ACCESS not-accessible
	STATUS     current
	DESCRIPTION 
		""
	INDEX { currentMonitorIndex, 
		currentMonitorCurrentIndex, 
		currentMonitorEnergyLogLastWeeksIndex }
	::= { currentMonitorEnergyLogLastWeeksTable 1 }

CurrentMonitorEnergyLogLastWeeksEntry ::= SEQUENCE {
	currentMonitorEnergyLogLastWeeksIndex
		Integer32,
	currentMonitorEnergyLogLastWeeksValue
		Integer32
}

currentMonitorEnergyLogLastWeeksIndex  OBJECT-TYPE
	SYNTAX     Integer32 (1..52)
	MAX-ACCESS not-accessible
	STATUS     current
	DESCRIPTION 
		"Index used for navigating the rows 1..52  of currentMonitorEnergyLogLastWeekTable"
	::= { currentMonitorEnergyLogLastWeeksEntry 1 }

currentMonitorEnergyLogLastWeeksValue  OBJECT-TYPE
	SYNTAX     Integer32
	MAX-ACCESS read-only
	STATUS     current
	DESCRIPTION 
		"Energy consumption value logged every week in current monitor."
	::= { currentMonitorEnergyLogLastWeeksEntry 2 }

alarmGroupTable  OBJECT-TYPE
	SYNTAX SEQUENCE OF AlarmGroupEntry
	MAX-ACCESS not-accessible
	STATUS     current
	DESCRIPTION 
		""
	::= { alarmGroups 1 }

alarmGroupEntry  OBJECT-TYPE
	SYNTAX 	AlarmGroupEntry
	MAX-ACCESS not-accessible
	STATUS     current
	DESCRIPTION 
		""
	INDEX { alarmGroupIndex }
	::= { alarmGroupTable 1 }

AlarmGroupEntry ::= SEQUENCE {
	alarmGroupIndex
		Integer32,
	alarmGroupStatus
		INTEGER,
	alarmGroupDescription
		DisplayString
}

alarmGroupIndex  OBJECT-TYPE
	SYNTAX     Integer32 (1..49)
	MAX-ACCESS not-accessible
	STATUS     current
	DESCRIPTION 
		"Index used for navigating the rows 1..49 of alarmGroupTable"
	::= { alarmGroupEntry 1 }

alarmGroupStatus  OBJECT-TYPE
	SYNTAX     INTEGER {
		normal (0),
		alarm (1)
	}
	MAX-ACCESS read-only
	STATUS     current
	DESCRIPTION 
		"The status of alarm group"
	::= { alarmGroupEntry 2 }

alarmGroupDescription  OBJECT-TYPE
	SYNTAX     DisplayString (SIZE(0..16))
	MAX-ACCESS read-write
	STATUS     current
	DESCRIPTION 
		"A textual description of the alarm group. This is stored in the system controller
		and can be changed by the user."
	::= { alarmGroupEntry 3 }

powerSystemTrapsGroup  NOTIFICATION-GROUP
	NOTIFICATIONS { alarmBatteryTrap, 
		alarmControlSystemTrap, 
		alarmDcDcTrap, 
		alarmGeneratorTrap, 
		alarmInputsTrap, 
		alarmLoadGroupTrap, 
		alarmMainsTrap, 
		alarmOutputsTrap, 
		alarmPowerSystemTrap, 
		alarmRectifierTrap, 
		alarmSolarChargerTrap, 
		alarmWindChargerTrap }
	STATUS     current
	DESCRIPTION 
		"The powerSystem Trap goup. Entry point for the trap list."
	::= { eltekTraps 3 }
END


-- This MIB was created using NuDesign Team's Visual MIBuilder (Ver 4.4).
-- EOF EltekSmartPack2-1.1.mib
