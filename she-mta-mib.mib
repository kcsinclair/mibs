--
-- she-mta-mib.mib
-- MIB generated by MG-SOFT Visual MIB Builder Version 6.0  Build 88
-- Wednesday, September 17, 2008 at 09:42:17
--

-- Start of ClearCase branch-information of current release:
-- she-mta-mib.mib   /main/she_r2.8_grf/2
-- End of ClearCase branch-information.

	SHE-MTA-MIB DEFINITIONS ::= BEGIN
 
		IMPORTS
			she			
				FROM AN-MIB			
			InterfaceIndex			
				FROM IF-MIB			
			SheControlStatusType			
				FROM SHE-TC-MIB			
			OBJECT-GROUP, MODULE-COMPLIANCE, NOTIFICATION-GROUP			
				FROM SNMPv2-CONF			
			mib-2, Integer32, Unsigned32, OBJECT-TYPE, MODULE-IDENTITY, 
			NOTIFICATION-TYPE			
				FROM SNMPv2-SMI			
			TEXTUAL-CONVENTION			
				FROM SNMPv2-TC;
	
	
		sheMta MODULE-IDENTITY 
			LAST-UPDATED "200809171000Z"		-- September 17, 2008 at 10:00 GMT
			ORGANIZATION 
				"Nokia Siemens Network"
			CONTACT-INFO 
				"COO IP Transport
				14 Jiuxianqiao Road Beijing
				
				wei3.zhao@nsn.com
				#########################
				gerd.barchmann@nsn.com"
			DESCRIPTION 
				" Definition of mta feature control command"
			REVISION "200504280901Z"		-- April 28, 2005 at 09:01 GMT
			DESCRIPTION 
				"Definition of mta feature control command."
			REVISION "200803190901Z"		-- March 19, 2008 at 09:01 GMT
			DESCRIPTION 
				"Bring them to common SHE MIB package with R2.8."
			REVISION "200804081157Z"		-- April 08, 2008 at 11:57 GMT
			DESCRIPTION 
				"Correct definition of ControlRequestType and ControlRequestResultType."
			REVISION "200809170851Z"		-- September 17, 2008 at 08:51 GMT
			DESCRIPTION 
				"Smal corrections for defined values."
			::= { she 10 }

		
	
--
-- Textual conventions
--
	
		SheMtaControlRequestType ::= TEXTUAL-CONVENTION
			STATUS current
			DESCRIPTION 
				"The type for mta control commands."
			SYNTAX INTEGER
				{
				mtaActivateInward(1),
				mtaActivateOutward(2),
				mtaActivateMonitoring(3),
				mtaActivateForceInward(4),
				mtaActivateForceOutward(5),
				mtaDeactivate(6),
				mtaSetAutoFreeTimer(7)
				}

--  GENERAL VALUES FOR USER COMMAND HANDLING
-- RETURN VALUES
		SheMtaControlRequestResultType ::= TEXTUAL-CONVENTION
			STATUS current
			DESCRIPTION 
				"The result type for mta control commands."
			SYNTAX INTEGER
				{
				mtaNotSupported(8),
				mtaIUtoSPBnotFound(9),
				commExecStarted(30),
				paramFaulty(31),
				requestBusy(32),
				setDataFailed(34),
				aswTimeout(35),
				commandFailed(36),
				commandSucceeded(37)
				}

	
--
-- Node definitions
--
	
--  MIB contains the following groups
		sheMtaControl OBJECT IDENTIFIER ::= { sheMta 1 }

		
--  return values to be defined
-- GENERAL VALUES FOR USER COMMAND HANDLING
-- RETURN VALUES
-- --------------------------------------------------------------
--        Metallic Test Access control group for ADSL 
-- --------------------------------------------------------------
		sheMtaCtrlControlReq OBJECT-TYPE
			SYNTAX SheMtaControlRequestType
			MAX-ACCESS read-write
			STATUS current
			DESCRIPTION
				" Controls the metallic test access (MTA) feature
				(activate or deactivate) at ADSL line interfaces.
				 MTA is provided only for ADSL lines and for
				 one line at a given time. 
				 The plugin unit IU must be unlocked.
				 If MTA has been activated for a line the command
				 command mtaActivate implicitly deactivates MTA 
				 for that line and activates it on the new line.
				 MTA is service affecting.
				 The command mtaDeactivate terminates MTA.
				 MTA is terminated by the DSLAM autonomously if
				 the IU will be locked or performs a restart."
			::= { sheMtaControl 1 }

		
		sheMtaCtrlControlStatus OBJECT-TYPE
			SYNTAX SheControlStatusType
			MAX-ACCESS read-only
			STATUS current
			DESCRIPTION
				" The status of a control request. "
			::= { sheMtaControl 2 }

		
		sheMtaCtrlIfIndex OBJECT-TYPE
			SYNTAX InterfaceIndex
			MAX-ACCESS read-write
			STATUS current
			DESCRIPTION
				" The interface index of the ADSL central PPTP
				for which metallic test access shall be activated. "
			::= { sheMtaControl 3 }

		
		sheMtaCtrlIfIndexUnderTest OBJECT-TYPE
			SYNTAX InterfaceIndex
			MAX-ACCESS read-only
			STATUS current
			DESCRIPTION
				" If not 0 the interface index of the ADSL central PPTP
				for which metallic test access is already activated. "
			::= { sheMtaControl 4 }

		
		sheMtaAutoFreeTimer OBJECT-TYPE
			SYNTAX Unsigned32 (50..600)
			MAX-ACCESS read-write
			STATUS current
			DESCRIPTION
				" The time duration of relay switch on. "
			DEFVAL { 300 }
			::= { sheMtaControl 5 }

		
		sheMtaCtrlControlReqResult OBJECT-TYPE
			SYNTAX SheMtaControlRequestResultType
			MAX-ACCESS read-only
			STATUS current
			DESCRIPTION
				" The result of the last user command. "
			::= { sheMtaControl 6 }

		
		sheMtaCtrlControlTimeStamp OBJECT-TYPE
			SYNTAX Integer32
			MAX-ACCESS read-only
			STATUS current
			DESCRIPTION
				" The time stamp of the last command (end of command). "
			::= { sheMtaControl 7 }

		
		sheMtaNotifications OBJECT IDENTIFIER ::= { sheMta 2 }

		
--  --------------------------------------------------------------
-- Metallic Test Access Notifications for ADSL 
-- --------------------------------------------------------------  
		sheMtaAutoFreeEvent NOTIFICATION-TYPE
			OBJECTS { sheMtaCtrlControlStatus, sheMtaCtrlIfIndex, sheMtaAutoFreeTimer, sheMtaCtrlControlReqResult, sheMtaCtrlControlTimeStamp
				 }
			STATUS current
			DESCRIPTION 
				" End of mta grasping command and free testing subscriber line. "
			::= { sheMtaNotifications 1 }

		
		sheMtaMibConformance OBJECT IDENTIFIER ::= { sheMta 100 }

		
		sheMtaMibCompliances OBJECT IDENTIFIER ::= { sheMtaMibConformance 1 }

		
		sheMtaMibCompliance MODULE-COMPLIANCE
			STATUS current
			DESCRIPTION 
				"Description."
			MODULE -- this module
				MANDATORY-GROUPS { sheMtaMibControlGroup, sheMtaMibNotificationGroup }
			::= { sheMtaMibCompliances 1 }

		
		sheMtaMibGroups OBJECT IDENTIFIER ::= { sheMtaMibConformance 2 }

		
		sheMtaMibControlGroup OBJECT-GROUP
			OBJECTS { sheMtaCtrlControlReq, sheMtaCtrlControlStatus, sheMtaCtrlIfIndex, sheMtaCtrlIfIndexUnderTest, sheMtaAutoFreeTimer, 
				sheMtaCtrlControlReqResult, sheMtaCtrlControlTimeStamp }
			STATUS current
			DESCRIPTION 
				"Description."
			::= { sheMtaMibGroups 1 }

		
		sheMtaMibNotificationGroup NOTIFICATION-GROUP
			NOTIFICATIONS { sheMtaAutoFreeEvent }
			STATUS current
			DESCRIPTION 
				"Description."
			::= { sheMtaMibGroups 2 }

		
	
	END

--
-- she-mta-mib.mib
--
