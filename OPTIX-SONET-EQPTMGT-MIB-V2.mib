--
-- OPTIX-SONET-EQPTMGT-MIB-V2.mib
-- MIB generated by MG-SOFT Visual MIB Builder Version 3.0 Build 253
-- Wednesday, July 26, 2006 at 17:16:46
--

	OPTIX-SONET-EQPTMGT-MIB-V2 DEFINITIONS ::= BEGIN
 
		IMPORTS
			optixProvisionSonet			
				FROM OPTIX-OID-MIB			
			OBJECT-GROUP, MODULE-COMPLIANCE			
				FROM SNMPv2-CONF			
			Integer32, Gauge32, OBJECT-TYPE, MODULE-IDENTITY			
				FROM SNMPv2-SMI			
			TEXTUAL-CONVENTION			
				FROM SNMPv2-TC;
	
	
		optixsonetEqptMgt MODULE-IDENTITY 
			LAST-UPDATED "200605232006Z"		-- May 23, 2006 at 20:06 GMT
			ORGANIZATION 
				"Your organization"
			CONTACT-INFO 
				"Your contact info"
			DESCRIPTION 
				"Enter the description for this MIB module."
			::= { optixProvisionSonet 3 }
		
	
--
-- Textual conventions
--
	
		IntfType ::= TEXTUAL-CONVENTION
			STATUS current
			DESCRIPTION 
				"Enter the description for the IntfType TEXTUAL-CONVENTION converted from type assignment."
			SYNTAX INTEGER
				{
				ds1-asyn-vt1(1),
				ds3-asyn-sts1(10),
				ec(12),
				ds3-tmux-ds1(13),
				ds3-srv-ds1(17),
				uas(65),
				mix(100),
				invalid(254)
				}
			
	
--
-- Node definitions
--
	
		-- 1.3.6.1.4.1.2011.2.25.4.20.3.1
		optixsonetCardInfoTable OBJECT-TYPE
			SYNTAX SEQUENCE OF OptixsonetCardInfoEntry
			MAX-ACCESS not-accessible
			STATUS current
			DESCRIPTION
				"This table describes the equipment unit management interface of Huawei SONET transmit platform
				"
			::= { optixsonetEqptMgt 1 }
		
		-- 1.3.6.1.4.1.2011.2.25.4.20.3.1.1
		optixsonetCardInfoEntry OBJECT-TYPE
			SYNTAX OptixsonetCardInfoEntry
			MAX-ACCESS not-accessible
			STATUS current
			DESCRIPTION
				"The equipment unit management entry
				"
			INDEX { cardIndexSlotId, cardIndexSfpId }
			::= { optixsonetCardInfoTable 1 }
		
		OptixsonetCardInfoEntry ::=
			SEQUENCE { 
				cardIndexSlotId
					Gauge32,
				cardIndexSfpId
					Gauge32,
				cardProvisionType
					OCTET STRING,
				cardPhysicalType
					OCTET STRING,
				cardInterfaceType
					IntfType,
				cardBandwidth
					Integer32,
				cardSerialNum
					OCTET STRING,
				cardCLEICode
					OCTET STRING,
				cardPartNum
					OCTET STRING,
				cardDOM
					OCTET STRING,
				cardPCBVersion
					OCTET STRING,
				cardSWVersion
					OCTET STRING,
				cardFPGAVersion
					OCTET STRING,
				cardEPLDVersion
					OCTET STRING,
				cardBIOSVersion
					OCTET STRING,
				cardMAC
					OCTET STRING,
				cardPSTState
					OCTET STRING,
				cardSSTState
					OCTET STRING,
				cardTPSPriority
					Gauge32,
				cardSwitchState
					INTEGER,
				cardDescription
					OCTET STRING
			 }

		-- 1.3.6.1.4.1.2011.2.25.4.20.3.1.1.1
		cardIndexSlotId OBJECT-TYPE
			SYNTAX Gauge32
			MAX-ACCESS read-only
			STATUS current
			DESCRIPTION
				"Slot number.
				 	
				 	This will indicate what is the slot 
				 	of the object."
			::= { optixsonetCardInfoEntry 1 }
		
		-- 1.3.6.1.4.1.2011.2.25.4.20.3.1.1.2
		cardIndexSfpId OBJECT-TYPE
			SYNTAX Gauge32
			MAX-ACCESS read-only
			STATUS current
			DESCRIPTION
				"SFP identifier.
						 	
						 	This will indicate what is the SFP Slot
						 	of the object.For the card unit, I will be zero."
			::= { optixsonetCardInfoEntry 2 }
		
		-- 1.3.6.1.4.1.2011.2.25.4.20.3.1.1.3
		cardProvisionType OBJECT-TYPE
			SYNTAX OCTET STRING (SIZE (0..16))
			MAX-ACCESS read-only
			STATUS current
			DESCRIPTION
				"It means the logical unit type provisioned by user."
			::= { optixsonetCardInfoEntry 3 }
		
		-- 1.3.6.1.4.1.2011.2.25.4.20.3.1.1.4
		cardPhysicalType OBJECT-TYPE
			SYNTAX OCTET STRING (SIZE (0..64))
			MAX-ACCESS read-only
			STATUS current
			DESCRIPTION
				"It means the physical unit type inserted in the slot."
			::= { optixsonetCardInfoEntry 4 }
		
		-- 1.3.6.1.4.1.2011.2.25.4.20.3.1.1.5
		cardInterfaceType OBJECT-TYPE
			SYNTAX IntfType
			MAX-ACCESS read-only
			STATUS current
			DESCRIPTION
				"The AID unit interface type.This parameter is optional and can be used only for tributary units"
			::= { optixsonetCardInfoEntry 5 }
		
		-- 1.3.6.1.4.1.2011.2.25.4.20.3.1.1.6
		cardBandwidth OBJECT-TYPE
			SYNTAX Integer32
			MAX-ACCESS read-only
			STATUS current
			DESCRIPTION
				"The available bandwidth of the unit when it is provisioned in the slot. It is displayed when the Ethernet unit, the OC-N unit or the tributary unit is provisioned. It is the minimum value of the slot bus bandwidth and bandwidth of the unit."
			::= { optixsonetCardInfoEntry 6 }
		
		-- 1.3.6.1.4.1.2011.2.25.4.20.3.1.1.7
		cardSerialNum OBJECT-TYPE
			SYNTAX OCTET STRING (SIZE (0..32))
			MAX-ACCESS read-only
			STATUS current
			DESCRIPTION
				"The serial number for the equipment. Valid value is a string and is optional."
			::= { optixsonetCardInfoEntry 7 }
		
		-- 1.3.6.1.4.1.2011.2.25.4.20.3.1.1.8
		cardCLEICode OBJECT-TYPE
			SYNTAX OCTET STRING (SIZE (0..16))
			MAX-ACCESS read-only
			STATUS current
			DESCRIPTION
				"The CLEI code for the equipment. Valid value is a string and is optional."
			::= { optixsonetCardInfoEntry 8 }
		
		-- 1.3.6.1.4.1.2011.2.25.4.20.3.1.1.9
		cardPartNum OBJECT-TYPE
			SYNTAX OCTET STRING (SIZE (0..20))
			MAX-ACCESS read-only
			STATUS current
			DESCRIPTION
				"Part number of the unit. Valid value is a unique 8-digit number for the unit."
			::= { optixsonetCardInfoEntry 9 }
		
		-- 1.3.6.1.4.1.2011.2.25.4.20.3.1.1.10
		cardDOM OBJECT-TYPE
			SYNTAX OCTET STRING (SIZE (0..16))
			MAX-ACCESS read-only
			STATUS current
			DESCRIPTION
				"The date when the unit was manufactured and is optional."
			::= { optixsonetCardInfoEntry 10 }
		
		-- 1.3.6.1.4.1.2011.2.25.4.20.3.1.1.11
		cardPCBVersion OBJECT-TYPE
			SYNTAX OCTET STRING (SIZE (0..16))
			MAX-ACCESS read-only
			STATUS current
			DESCRIPTION
				"The PCB version for the equipment. Valid value is a string and is optional."
			::= { optixsonetCardInfoEntry 11 }
		
		-- 1.3.6.1.4.1.2011.2.25.4.20.3.1.1.12
		cardSWVersion OBJECT-TYPE
			SYNTAX OCTET STRING (SIZE (0..64))
			MAX-ACCESS read-only
			STATUS current
			DESCRIPTION
				"The software version for the equipment."
			::= { optixsonetCardInfoEntry 12 }
		
		-- 1.3.6.1.4.1.2011.2.25.4.20.3.1.1.13
		cardFPGAVersion OBJECT-TYPE
			SYNTAX OCTET STRING (SIZE (0..32))
			MAX-ACCESS read-only
			STATUS current
			DESCRIPTION
				"The FPGA version for the equipment. Valid value is a string and is optional."
			::= { optixsonetCardInfoEntry 13 }
		
		-- 1.3.6.1.4.1.2011.2.25.4.20.3.1.1.14
		cardEPLDVersion OBJECT-TYPE
			SYNTAX OCTET STRING (SIZE (0..8))
			MAX-ACCESS read-only
			STATUS current
			DESCRIPTION
				"The EPLD version for the equipment. Valid value is a string and is optional."
			::= { optixsonetCardInfoEntry 14 }
		
		-- 1.3.6.1.4.1.2011.2.25.4.20.3.1.1.15
		cardBIOSVersion OBJECT-TYPE
			SYNTAX OCTET STRING (SIZE (0..64))
			MAX-ACCESS read-only
			STATUS current
			DESCRIPTION
				"The BIOS version for the equipment. Valid value for <BIOSVER> is a string and is optional."
			::= { optixsonetCardInfoEntry 15 }
		
		-- 1.3.6.1.4.1.2011.2.25.4.20.3.1.1.16
		cardMAC OBJECT-TYPE
			SYNTAX OCTET STRING (SIZE (0..32))
			MAX-ACCESS read-only
			STATUS current
			DESCRIPTION
				"The MAC address of a common control unit. Valid value is a string like 00-B0-D0-E3-4C-DE and is optional."
			::= { optixsonetCardInfoEntry 16 }
		
		-- 1.3.6.1.4.1.2011.2.25.4.20.3.1.1.17
		cardPSTState OBJECT-TYPE
			SYNTAX OCTET STRING (SIZE (0..16))
			MAX-ACCESS read-only
			STATUS current
			DESCRIPTION
				"<PST> means the primary state of the entity."
			::= { optixsonetCardInfoEntry 17 }
		
		-- 1.3.6.1.4.1.2011.2.25.4.20.3.1.1.18
		cardSSTState OBJECT-TYPE
			SYNTAX OCTET STRING (SIZE (0..32))
			MAX-ACCESS read-only
			STATUS current
			DESCRIPTION
				"<SST> means the secondary state of the entity."
			::= { optixsonetCardInfoEntry 18 }
		
		-- 1.3.6.1.4.1.2011.2.25.4.20.3.1.1.19
		cardTPSPriority OBJECT-TYPE
			SYNTAX Gauge32
			MAX-ACCESS read-only
			STATUS current
			DESCRIPTION
				"The priority of the AID unit if the unit is a working unit of a DSn (TPS) protection group. 
				For any other units, this parameter is not available. This attribute will be used when multi-units 
				fault in a DSn (TPS) protection group.Valid values are list below
				Value	Description
				1	The highest priority for the unit in a TPS protection group
				2	The secondary priority for the unit in a TPS protection group
				3	The third priority for the unit in a TPS protection group
				4	The lowest priority for the unit in a TPS protection group
				"
			::= { optixsonetCardInfoEntry 19 }
		
		-- 1.3.6.1.4.1.2011.2.25.4.20.3.1.1.20
		cardSwitchState OBJECT-TYPE
			SYNTAX INTEGER
				{
				stateDNR(1),
				stateWTR(2),
				stateMAN(3),
				stateAUTOSW(4),
				stateFRCD(5),
				stateLOCK(6),
				stateINVALID(254),
				stateIDLE(255)
				}
			MAX-ACCESS read-only
			STATUS current
			DESCRIPTION
				"The switch state of the AID unit if the unit is a unit of a DSn (TPS) protection group.
				Switch state of SONET equipment protection 
				Value	Description
				AUTO_SW	Automatic switch
				DNR	Do not revert
				FRCD	Forced switch
				IDLE	Idle
				LOCKOUT	Lock to the working unit
				MAN	Manually switch
				WTR	Wait to restore
				"
			::= { optixsonetCardInfoEntry 20 }
		
		-- 1.3.6.1.4.1.2011.2.25.4.20.3.1.1.21
		cardDescription OBJECT-TYPE
			SYNTAX OCTET STRING (SIZE (0..64))
			MAX-ACCESS read-only
			STATUS current
			DESCRIPTION
				"Description."
			::= { optixsonetCardInfoEntry 21 }
		
		-- 1.3.6.1.4.1.2011.2.25.4.20.3.2
		optixsonetEqptMgtConformance OBJECT IDENTIFIER ::= { optixsonetEqptMgt 2 }
		
		-- 1.3.6.1.4.1.2011.2.25.4.20.3.2.1
		optixsonetEqptMgtGroups OBJECT IDENTIFIER ::= { optixsonetEqptMgtConformance 1 }
		
		-- 1.3.6.1.4.1.2011.2.25.4.20.3.2.1.1
		currentObjectGroup OBJECT-GROUP
			OBJECTS { cardIndexSlotId, cardIndexSfpId, cardProvisionType, cardPhysicalType, cardInterfaceType, 
				cardBandwidth, cardSerialNum, cardCLEICode, cardPartNum, cardDOM, 
				cardPCBVersion, cardSWVersion, cardFPGAVersion, cardEPLDVersion, cardBIOSVersion, 
				cardMAC, cardPSTState, cardSSTState, cardTPSPriority, cardSwitchState, 
				cardDescription }
			STATUS current
			DESCRIPTION 
				"Enter the description of the created OBJECT-GROUP."
			::= { optixsonetEqptMgtGroups 1 }
		
		-- 1.3.6.1.4.1.2011.2.25.4.20.3.2.2
		optixsonetEqptMgtCompliances OBJECT IDENTIFIER ::= { optixsonetEqptMgtConformance 2 }
		
		-- 1.3.6.1.4.1.2011.2.25.4.20.3.2.2.1
		basicCompliance MODULE-COMPLIANCE
			STATUS current
			DESCRIPTION 
				"Enter the description of the created MODULE-COMPLIANCE."
			MODULE -- this module
				MANDATORY-GROUPS { currentObjectGroup }
			::= { optixsonetEqptMgtCompliances 1 }
		
	
	END

--
-- OPTIX-SONET-EQPTMGT-MIB-V2.mib
--
