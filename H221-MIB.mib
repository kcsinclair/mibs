-- extracted from draft-kajos-hmultimediamib-00.txt
-- at Mon Nov 15 17:11:06 1999

        H221-MIB DEFINITIONS ::= BEGIN
             IMPORTS
                  MODULE-IDENTITY, OBJECT-TYPE, Counter32,
                  experimental, NOTIFICATION-TYPE
                       FROM SNMPv2-SMI

                  MODULE-COMPLIANCE, OBJECT-GROUP, NOTIFICATION-GROUP
                       FROM SNMPv2-CONF;
        
             h221MIB MODULE-IDENTITY
                  LAST-UPDATED "9805251400Z" -- May 25, 1998
                  ORGANIZATION "VTEL Corp. "
                  CONTACT-INFO
                       "Joon Maeng
                       VTEL Corp.
                        Postal: 108 Wild Basin Rd.
                                      Austin, TX 78746
                                      USA
                       TEL: (512)437-4567
                       Email: Joon_Maeng@vtel.com"
                  DESCRIPTION
                       "This MIB module supports the functions of the
                       IUT H.221 Protocol"
                  REVISION "9805251400Z" -- May 25, 1998
                  DESCRIPTION
                       " The initial version of the H221 mib"
                  ::= {experimental 221 2} -- temporary OID. TBD.
        
             h221Stats OBJECT IDENTIFIER ::= { h221MIB 1  }
             h221Events     OBJECT IDENTIFIER ::= { h221MIB 2  }
        
             -- TEXTUAL Conventions
        
             h221InFrames OBJECT-TYPE
                       SYNTAX Counter32
                       MAX-ACCESS read-only
                       STATUS current
                       DESCRIPTION
                                 "The number of H.221 frames received"
             ::= { h221Stats 1 }
        
             h221OutFrames OBJECT-TYPE
                       SYNTAX Counter32
                       MAX-ACCESS read-only
                  STATUS current
                       DESCRIPTION
                                 "The number of H.221 frames sent"
             ::= { h221Stats 2 }
        
             h221InFrameErrs OBJECT-TYPE
                       SYNTAX Counter32
                       MAX-ACCESS read-only
                       STATUS current
                       DESCRIPTION
                                 "The number of error frames received"
             ::= { h221Stats 3 }
        
             h221FrameAlignmentErrs OBJECT-TYPE
                       SYNTAX  Counter32
                       MAX-ACCESS read-only
                       STATUS current
                       DESCRIPTION
                                 "The number of frame alignment errors received"
             ::= { h221Stats 4 }
        
             h221MultiFrameAlignmentErrs OBJECT-TYPE
                       SYNTAX Counter32
                       MAX-ACCESS read-only
                       STATUS current
                       DESCRIPTION
                       "The number of multiple frame alignment errors received"
             ::= { h221Stats 5 }
        
             h221ErrorPerformance OBJECT-TYPE
                       SYNTAX Counter32
                       MAX-ACCESS read-only
                       STATUS current
                       DESCRIPTION
                       "The quality of the 64 Kbps connection can be monitored
                       by counting the number of  CRC blocks in error (E-bit = 1)
                       within a period of one second (50 blocks).
                       Percentage of CRC blocks in error  Error rate
                       70% CRC blocks in error            10E-4
                       12% CRC blocks in error            10E-5
                       1.2% CRC blocks in error           10E-6
                       0.12% CRC blocks in error          10E-7
                       0.012% CRC blocks in error         10E-8"
             ::= { h221Stats 6 }
        
             h221BASErrs OBJECT-TYPE
                       SYNTAX Counter32
                       MAX-ACCESS read-only
                       STATUS current
                       DESCRIPTION
                                 "The number of H.221 BAS errors received"
             ::= { h221Stats 7 }
        
             -- Notification group
             --
        
             h221TooManyErrors NOTIFICATION-TYPE
                  OBJECTS { h221ErrorPerformance }
                  STATUS    current
                  DESCRIPTION
                       "This message will be sent when there are
                       excessive line errors."
             ::= { h221Events 1 }
        
             -- CONFORMANCE
             --
        
             h221StatsMIBConfs   OBJECT IDENTIFIER ::= { h221MIB 3 }
             h221StatsMIBGroups  OBJECT IDENTIFIER ::= { h221StatsMIBConfs 1 }
             h221StatsMIBCompl   OBJECT IDENTIFIER ::= { h221StatsMIBConfs 2 }
        
             --
             -- Groups for conformance
             --
        
             h221StatsGroup OBJECT-GROUP
                  OBJECTS {
                       h221InFrames,
                       h221OutFrames,
                       h221InFrameErrs,
                       h221FrameAlignmentErrs,
                       h221MultiFrameAlignmentErrs,
                       h221ErrorPerformance,
                       h221BASErrs
                  }
                  STATUS current
                  DESCRIPTION
                       "A collection of objects providing the ability to invoke
                       terminal functions"
             ::= { h221StatsMIBGroups 1}
        
             h221EventsGroup     NOTIFICATION-GROUP
                  NOTIFICATIONS {
                       h221TooManyErrors
                  }
                  STATUS current
                  DESCRIPTION
                       "An object providing the ability to invoke
                       a notification function"
             ::= { h221StatsMIBGroups 2}
        
             h221StatsCompliance MODULE-COMPLIANCE
                  STATUS    current
                  DESCRIPTION
                       "The set of objects required for compliance"
             -- Unconditionally mandatory groups
                  MODULE
                  MANDATORY-GROUPS     { h221StatsGroup, h221EventsGroup }
        
             ::= { h221StatsMIBCompl 1 }
        
        END
