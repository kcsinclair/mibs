OMNI-gx2drr3x-MIB DEFINITIONS ::= BEGIN

    IMPORTS
	IpAddress, TimeTicks            
					      FROM RFC1155-SMI
	OBJECT-TYPE                     
					      FROM RFC-1212
	sysUpTime, DisplayString        
					      FROM RFC1213-MIB
	TRAP-TYPE                       
					      FROM RFC-1215
	gi, motproxies                   
					      FROM NLS-BBNIDENT-MIB
	gx2Drr3x
					      FROM GX2HFC-MIB

	trapIdentifier,trapNetworkElemModelNumber,
	trapNetworkElemSerialNum, trapPerceivedSeverity,
	trapNetworkElemOperState, trapNetworkElemAlarmStatus,
	trapNetworkElemAdminState, trapNetworkElemAvailStatus,
	trapText, trapNETrapLastTrapTimeStamp, trapChangedObjectId,
	trapChangedValueInteger, trapChangedValueDisplayString
					      FROM NLSBBN-TRAPS-MIB;



	       -- This MIB module uses the extended OBJECT-TYPE macro as
	       -- defined in RFC1212 and the TRAP-TYPE macro as defined
	       -- in RFC 1215.

		   --REVISION	"1" Jan 20, 2003
		   --DESCRIPTION
		   --			Added revision and description comment section


		--    OMNISTAR Digital Receiver Return 3X Module MIB MODULE

	-- This MIB module defines information for management of HFC networks
		-- 
		-- The MIB module assumes that all generic (static) network element
		-- information is defined in a different module such as the HFC module
		-- The MIB consists of two groups:
		-- the device type descriptor subgroup and 
		-- gx2drr3x Network Elements subgroup.
		-- The device type descriptor subgroup is used to define 
		-- parameters specific to gx2drr3x device type.
		-- These parameters are common across all network elements
		-- from gx2drr3x device type.
		--
		-- The gx2drr3x Network Elements subgroup is
		-- a list of gx2drr3x type elements in the
		-- current network topology with nominal
		-- and current parameter values for the
		-- individual network elements; the individual
		-- network elements are identified by  
		-- index from hfcCommonTable.
		-- That implies what hfcCommonTableIndex and
		-- gx2drr3xTableIndex are equal for each individual
		-- network element.
		-- This table is an extension of the hfcCommonTable
		-- for all elements of gx2Lmc type.
		--
		-- Both groups are mandatory for management of gx2Lmc devices.

-- ****************************************************************************
		--
		-- All floating point numbers will be represented by an IEEE 32 Bit number.
		-- Conversion of this number must be done on the user interface to view the 
		-- actual floating point number. 
		--

		Float ::= Counter  -- UNSIGNED (32 BITS) 

-- ****************************************************************************

		-- gx2drr3x Device Descriptor subgroup.

		-- The device type descriptor subgroup is used to define 
		-- parameters specific to gx2drr3x device type.
		-- These parameters are common across all network elements
		-- from gx2drr3x device type.


		 gx2drr3xDescriptor OBJECT IDENTIFIER ::= {gx2Drr3x 1}



--*****************************************************************************
		--              gx2drr3x Table
		
		-- Contains a list of all gx2drr3x type devices in
		-- the network. Each device is characterized with
		-- current network topology information, with nominal
		-- and current parameter values for the
		-- individual network elements;
		--
		-- The individual network elements indentified by  
		-- index from hfcCommonTable.
		-- That implies what hfcCommonTableIndex and
		-- gx2drr3xTableIndex are equal for each individual
		-- nettwork element.
		-- This table should be used as an extension of the hfcCommonTable
		-- for all elements of gx2drr3x type.


	       gx2drr3xAnalogTable                    OBJECT-TYPE
			 SYNTAX             SEQUENCE OF Gx2drr3xAnalogEntry
			 ACCESS             not-accessible
			 STATUS             mandatory
			 DESCRIPTION
			 "This table contains gx2drr3x specific analog parameters with
			  nominal,limits and current values."
			 ::= { gx2Drr3x 2 }


	       gx2drr3xAnalogEntry               OBJECT-TYPE
			 SYNTAX             Gx2drr3xAnalogEntry
			 ACCESS             not-accessible
			 STATUS             mandatory
			 DESCRIPTION
			 "This list contains the analog parameters and descriptions."
			 INDEX { gx2drr3xAnalogTableIndex }
			 ::= { gx2drr3xAnalogTable  1}

--*****************************************************************************
	       gx2drr3xDigitalTable                    OBJECT-TYPE
			 SYNTAX             SEQUENCE OF Gx2drr3xDigitalEntry
			 ACCESS             not-accessible
			 STATUS             mandatory
			 DESCRIPTION
			 "This table contains gx2drr3x specific digital parameters with
			  nominal and current values."
			 ::= { gx2Drr3x 3 }

	       gx2drr3xDigitalEntry               OBJECT-TYPE
			 SYNTAX             Gx2drr3xDigitalEntry
			 ACCESS             not-accessible
			 STATUS             mandatory
			 DESCRIPTION
			 "This list contains digital parameters and descriptions."
			 INDEX { gx2drr3xDigitalTableIndex }
			 ::= { gx2drr3xDigitalTable  2}

--*****************************************************************************
	       gx2drr3xStatusTable                    OBJECT-TYPE
			 SYNTAX             SEQUENCE OF Gx2drr3xStatusEntry
			 ACCESS             not-accessible
			 STATUS             mandatory
			 DESCRIPTION
			 "This table contains gx2drr3x specific status parameters with
			  nominal and current values."
			 ::= { gx2Drr3x 4 }

	       gx2drr3xStatusEntry               OBJECT-TYPE
			 SYNTAX             Gx2drr3xStatusEntry
			 ACCESS             not-accessible
			 STATUS             mandatory
			 DESCRIPTION
			 "This list contains Status parameters and descriptions."
			 INDEX { gx2drr3xStatusTableIndex }
			 ::= { gx2drr3xStatusTable  3}

--*****************************************************************************
	       gx2drr3xFactoryTable                    OBJECT-TYPE
			 SYNTAX             SEQUENCE OF Gx2drr3xFactoryEntry
			 ACCESS             not-accessible
			 STATUS             mandatory
			 DESCRIPTION
			 "This table contains gx2drr3x specific factory setting parameters with
			  nominal and current values."
			 ::= { gx2Drr3x 5 }

	       gx2drr3xFactoryEntry               OBJECT-TYPE
			 SYNTAX             Gx2drr3xFactoryEntry
			 ACCESS             not-accessible
			 STATUS             mandatory
			 DESCRIPTION
			 "This list contains Factory setting parameters and descriptions."
			 INDEX { gx2drr3xFactoryTableIndex }
			 ::= { gx2drr3xFactoryTable  4}

--*****************************************************************************
	      Gx2drr3xAnalogEntry    ::= SEQUENCE  
	       {
		gx2drr3xAnalogTableIndex      INTEGER,
		
		drrlabelRFAAttenuation			DisplayString (SIZE (0..80)),
		drruomRFAAttenuation			DisplayString (SIZE (0..80)),
		drrmajorHighRFAAttenuation		Float,
		drrmajorLowRFAAttenuation		Float, 
		drrminorHighRFAAttenuation		Float,
		drrminorLowRFAAttenuation		Float, 
		drrcurrentValueRFAAttenuation	Float, 
		drrstateFlagRFAAttenuation		INTEGER,
		drrminValueRFAAttenuation		Float,
		drrmaxValueRFAAttenuation 		Float,
		drralarmStateRFAAttenuation		INTEGER,
		
		drrlabelRFBAttenuation			DisplayString (SIZE (0..80)),
		drruomRFBAttenuation			DisplayString (SIZE (0..80)),
		drrmajorHighRFBAttenuation		Float, 
		drrmajorLowRFBAttenuation		Float, 
		drrminorHighRFBAttenuation		Float,
		drrminorLowRFBAttenuation		Float, 
		drrcurrentValueRFBAttenuation	Float, 
		drrstateFlagRFBAttenuation		INTEGER,
		drrminValueRFBAttenuation		Float,
		drrmaxValueRFBAttenuation 		Float,
		drralarmStateRFBAttenuation		INTEGER,
  
		drrlabelRFCAttenuation			DisplayString (SIZE (0..80)),
		drruomRFCAttenuation			DisplayString (SIZE (0..80)),
		drrmajorHighRFCAttenuation		Float, 
		drrmajorLowRFCAttenuation		Float, 
		drrminorHighRFCAttenuation		Float,
		drrminorLowRFCAttenuation		Float, 
		drrcurrentValueRFCAttenuation	Float, 
		drrstateFlagRFCAttenuation		INTEGER,
		drrminValueRFCAttenuation		Float,
		drrmaxValueRFCAttenuation 		Float,
		drralarmStateRFCAttenuation		INTEGER,
		
		drrlabelTrippointLevel			DisplayString (SIZE (0..80)),
		drruomTrippointLevel			DisplayString (SIZE (0..80)),
		drrmajorHighTrippointLevel		Float, 
		drrmajorLowTrippointLevel		Float, 
		drrminorHighTrippointLevel		Float,
		drrminorLowTrippointLevel		Float, 
		drrcurrentValueTrippointLevel	Float, 
		drrstateFlagTrippointLevel		INTEGER,
		drrminValueTrippointLevel		Float,
		drrmaxValueTrippointLevel 		Float,
		drralarmStateTrippointLevel  	INTEGER,	
		                   
        drrlabelOptCurrent				DisplayString (SIZE (0..80)),
		drruomOptCurrent				DisplayString (SIZE (0..80)),
		drrmajorHighOptCurrent			Float, 
		drrmajorLowOptCurrent			Float, 
		drrminorHighOptCurrent			Float,
		drrminorLowOptCurrent			Float, 
		drrcurrentValueOptCurrent		Float, 
		drrstateFlagOptCurrent			INTEGER,
		drrminValueOptCurrent			Float,
		drrmaxValueOptCurrent 			Float,
		drralarmStateOptCurrent			INTEGER,
                 
		drrlabel12VCurrent				DisplayString (SIZE (0..80)),
		drruom12VCurrent				DisplayString (SIZE (0..80)),
		drrmajorHigh12VCurrent			Float, 
		drrmajorLow12VCurrent			Float, 
		drrminorHigh12VCurrent			Float,
		drrminorLow12VCurrent			Float, 
		drrcurrentValue12VCurrent		Float, 
		drrstateFlag12VCurrent			INTEGER,
		drrminValue12VCurrent			Float,
		drrmaxValue12VCurrent 			Float,
		drralarmState12VCurrent			INTEGER, 
		
		drrlabelModTemp			    	DisplayString (SIZE (0..80)),
		drruomModTemp					DisplayString (SIZE (0..80)),
		drrmajorHighModTemp				Float, 
		drrmajorLowModTemp				Float, 
		drrminorHighModTemp				Float,
		drrminorLowModTemp				Float, 
		drrcurrentValueModTemp			Float, 
		drrstateFlagModTemp				INTEGER,
		drrminValueModTemp				Float,
		drrmaxValueModTemp				Float,
		drralarmStateModTemp			INTEGER,    
			
		drrlabelFanCurrent			DisplayString (SIZE (0..80)),
		drruomFanCurrent			DisplayString (SIZE (0..80)),
		drrmajorHighFanCurrent		Float, 
		drrmajorLowFanCurrent		Float, 
		drrminorHighFanCurrent		Float,
		drrminorLowFanCurrent		Float, 
		drrcurrentValueFanCurrent	Float, 
		drrstateFlagFanCurrent		INTEGER,
		drrminValueFanCurrent		Float,
		drrmaxValueFanCurrent 		Float,
		drralarmStateFanCurrent		INTEGER
				
		}

		-- ****************  Digital Parameters ***********************
	     Gx2drr3xDigitalEntry    ::= SEQUENCE  
	     {
		gx2drr3xDigitalTableIndex         INTEGER,    
		               
        drrlabelTrippointMode   	    DisplayString (SIZE (0..80)),
		drrenumTrippointMode		    DisplayString (SIZE (0..80)),
		drrvalueTrippointMode		    INTEGER,
		drrstateflagTrippointMode       INTEGER,
		    		
		drrlabelFrontPanelTest   	    DisplayString (SIZE (0..80)),
		drrenumFrontPanelTest		    DisplayString (SIZE (0..80)),
		drrvalueFrontPanelTest		    INTEGER,
		drrstateflagFrontPanelTest      INTEGER,
						         
		drrlabelFactoryDefaultReset	    DisplayString (SIZE (0..80)),
		drrenumFactoryDefaultReset		DisplayString (SIZE (0..80)),
		drrvalueFactoryDefaultReset		INTEGER,
		drrstateflagFactoryDefaultReset INTEGER                             
	    }

		-- ****************  Status Parameters ************************************
	     Gx2drr3xStatusEntry    ::= SEQUENCE  
	     {
		gx2drr3xStatusTableIndex      INTEGER,

		drrlabelBoot				DisplayString (SIZE (0..80)),
		drrvalueBoot				INTEGER,
		drrstateflagBoot			INTEGER,
		
		drrlabelFlash				DisplayString (SIZE (0..80)),
		drrvalueFlash				INTEGER,
		drrstateflagFlash			INTEGER,

		drrlabelFactoryDataCRC 		DisplayString (SIZE (0..80)),
		drrvalueFactoryDataCRC		INTEGER,
		drrstateflagFactoryDataCRC	INTEGER,

		drrlabelAlarmDataCrc		DisplayString (SIZE (0..80)),
		drrvalueAlarmDataCrc		INTEGER,
		drrstateflagAlarmDataCrc	INTEGER,

		drrlabelHardwareStatus		DisplayString (SIZE (0..80)),
		drrvalueHardwareStatus		INTEGER,
		drrstateflagHardwareStatus	INTEGER, 
	
		drrlabelOpticTripPointStatus		 DisplayString (SIZE (0..80)),
		drrvalueOpticTripPointStatus		 INTEGER,
		drrstateflagOpticTripPointStatus	 INTEGER,
			
		drrlabelLinkStatus	                 DisplayString (SIZE (0..80)),
		drrvalueLinkStatus		             INTEGER,
		drrstateflagLinkStatus	             INTEGER     
		}


		-- ****************  Factory Parameters *************************************
       Gx2drr3xFactoryEntry    ::= SEQUENCE  
       {
		gx2drr3xFactoryTableIndex       INTEGER,
		drrbootControlByte  			INTEGER,
		drrbootStatusByte   			INTEGER,
		drrbank1CRC    			        INTEGER,
		drrbank2CRC    			        INTEGER,
		drrprgEEPROMByte    			INTEGER,
		drrfactoryCRC    			    INTEGER,
		drrcalculateCRC    				INTEGER,
		drrhourMeter    				INTEGER,
		drrflashPrgCntA    				INTEGER,
		drrflashPrgCntB    				INTEGER,
		drrflashBankARev    			DisplayString (SIZE (0..80)),
		drrflashBankBRev    			DisplayString (SIZE (0..80))
--		drrSubAgentRev					DisplayString (SIZE (0..80))
		}
            -- ************** Analog Parameters ****************************
		gx2drr3xAnalogTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2drr3xAnalogEntry 1}
			   
 -- RFAAttenuation         
        drrlabelRFAAttenuation           OBJECT-TYPE
			   SYNTAX           DisplayString (SIZE (0..80))
			   ACCESS           read-only
			   STATUS           optional
			   DESCRIPTION
			   "The value of this object provides the label of the
			    RF Channel A Attenuation Analog parameter."
			   ::= { gx2drr3xAnalogEntry 2}

		drruomRFAAttenuation             OBJECT-TYPE
			   SYNTAX           DisplayString (SIZE (0..80))
			   ACCESS           read-only
			   STATUS           optional
			   DESCRIPTION
			   "The value of this object provides the Unit of Measure of the
			     RF Channel A Attenuation Analog parameter."
			   ::= { gx2drr3xAnalogEntry 3}

		drrmajorHighRFAAttenuation       OBJECT-TYPE
			   SYNTAX           Float 
			   ACCESS           read-only
			   STATUS           mandatory
			   DESCRIPTION
			   "The value of this object provides the Major High alarm value
			    of the  RF Channel A Attenuation Analog parameter. This parameter has not been used by the module 
			    and set as the invalid float value (0xFFFFFFFF)"
			   ::= { gx2drr3xAnalogEntry 4}

		drrmajorLowRFAAttenuation        OBJECT-TYPE
			   SYNTAX           Float 
			   ACCESS           read-only
			   STATUS           mandatory
			   DESCRIPTION
			   "The value of this object provides the Major Low alarm value
			    of the RF Channel A Attenuation  Analog parameter.
			   This parameter has not been used by the module 
                     and set as the invalid float value (0xFFFFFFFF) "
			   ::= { gx2drr3xAnalogEntry 5}

		drrminorHighRFAAttenuation       OBJECT-TYPE
			   SYNTAX           Float
			   ACCESS           read-only
			   STATUS           mandatory
			   DESCRIPTION
			   "The value of this object provides the Minor High alarm value
			    of the RF Channel A Attenuation  Analog parameter.
			   This parameter has not been used by the module 
                     and set as the invalid float value (0xFFFFFFFF) "
			   ::= { gx2drr3xAnalogEntry 6}

		drrminorLowRFAAttenuation        OBJECT-TYPE
			   SYNTAX           Float 
			   ACCESS           read-only
			   STATUS           mandatory
			   DESCRIPTION
			   "The value of this object provides the Minor Low alarm value
			    of the RF Channel A Attenuation Analog parameter.
			   This parameter has not been used by the module 
                     and set as the invalid float value (0xFFFFFFFF) "
			   ::= { gx2drr3xAnalogEntry 7}

		drrcurrentValueRFAAttenuation    OBJECT-TYPE
			   SYNTAX           Float 
			   ACCESS           read-write
			   STATUS           mandatory
			   DESCRIPTION
			   "The value of this object provides the Current value
			    of the RF Channel A Attenuation Analog parameter.
			   This value is a floating point number that is represented as an IEEE 32 bit number."
			   ::= { gx2drr3xAnalogEntry 8}

		drrstateFlagRFAAttenuation       OBJECT-TYPE
			   SYNTAX           INTEGER
								{
								hidden(1),
								read-only(2),
								updateable(3)
								}
			   ACCESS           read-only
			   STATUS           mandatory
			   DESCRIPTION
			   "The value of this object provides the state
			    of the RF Channel A Attenuation Analog parameter. (0-Hidden	
			          1-Read-Only, 2-Updateable)."
			   ::= { gx2drr3xAnalogEntry 9}

		drrminValueRFAAttenuation        OBJECT-TYPE
			   SYNTAX           Float
			   ACCESS           read-only
			   STATUS           mandatory
			   DESCRIPTION
			   "The value of this object provides the minimum value
			    the RF Channel A Attenuation Analog parameter can achive.
			   This value is a floating point number that is represented as an IEEE 32 bit number."
			   ::= { gx2drr3xAnalogEntry 10}

		drrmaxValueRFAAttenuation        OBJECT-TYPE
			   SYNTAX           Float
			   ACCESS           read-only
			   STATUS           mandatory
			   DESCRIPTION
			   "The value of this object provides the maximum value
			    the RF Channel A Attenuation Analog parameter can achive.
			   This value is a floating point number that is represented as an IEEE 32 bit number."
			   ::= { gx2drr3xAnalogEntry 11}

        drralarmStateRFAAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel A Attenuation Analog parameter."
			   ::= { gx2drr3xAnalogEntry 12}
			   
			   
-- 	RFBAttenuation		         
       
          		drrlabelRFBAttenuation           OBJECT-TYPE
			   SYNTAX           DisplayString (SIZE (0..80))
			   ACCESS           read-only
			   STATUS           optional
			   DESCRIPTION
			   "The value of this object provides the label of the
			    RF Channel B Attenuation Analog parameter."
			   ::= { gx2drr3xAnalogEntry 13}

		drruomRFBAttenuation             OBJECT-TYPE
			   SYNTAX           DisplayString (SIZE (0..80))
			   ACCESS           read-only
			   STATUS           optional
			   DESCRIPTION
			   "The value of this object provides the Unit of Measure of the
			     RF Channel B Attenuation Analog parameter."
			   ::= { gx2drr3xAnalogEntry 14}

		drrmajorHighRFBAttenuation       OBJECT-TYPE
			   SYNTAX           Float 
			   ACCESS           read-only
			   STATUS           mandatory
			   DESCRIPTION
			   "The value of this object provides the Major High alarm value
			    of the  RF Channel B Attenuation Analog parameter.
			   This parameter has not been used by the module 
                     and set as the invalid float value (0xFFFFFFFF) "
			   ::= { gx2drr3xAnalogEntry 15}

		drrmajorLowRFBAttenuation        OBJECT-TYPE
			   SYNTAX           Float 
			   ACCESS           read-only
			   STATUS           mandatory
			   DESCRIPTION
			   "The value of this object provides the Major Low alarm value
			    of the RF Channel B Attenuation  Analog parameter.
			   This parameter has not been used by the module 
                     and set as the invalid float value (0xFFFFFFFF) "
			   ::= { gx2drr3xAnalogEntry 16}

		drrminorHighRFBAttenuation       OBJECT-TYPE
			   SYNTAX           Float
			   ACCESS           read-only
			   STATUS           mandatory
			   DESCRIPTION
			   "The value of this object provides the Minor High alarm value
			    of the RF Channel B Attenuation  Analog parameter.
			   This parameter has not been used by the module 
                     and set as the invalid float value (0xFFFFFFFF) "
			   ::= { gx2drr3xAnalogEntry 17}

		drrminorLowRFBAttenuation        OBJECT-TYPE
			   SYNTAX           Float 
			   ACCESS           read-only
			   STATUS           mandatory
			   DESCRIPTION
			   "The value of this object provides the Minor Low alarm value
			    of the RF Channel B Attenuation Analog parameter.
			   This parameter has not been used by the module 
                     and set as the invalid float value (0xFFFFFFFF) "
			   ::= { gx2drr3xAnalogEntry 18}

		drrcurrentValueRFBAttenuation    OBJECT-TYPE
			   SYNTAX           Float 
			   ACCESS           read-write
			   STATUS           mandatory
			   DESCRIPTION
			   "The value of this object provides the Current value
			    of the RF Channel B Attenuation Analog parameter.                 
			   This value is a floating point number that is represented as an IEEE 32 bit number."
			   ::= { gx2drr3xAnalogEntry 19}

		drrstateFlagRFBAttenuation       OBJECT-TYPE
			   SYNTAX           INTEGER
								{
								hidden(1),
								read-only(2),
								updateable(3)
								}
			   ACCESS           read-only
			   STATUS           mandatory
			   DESCRIPTION
			   "The value of this object provides the state
			    of the RF Channel B Attenuation Analog parameter. (0-Hidden	
			          1-Read-Only, 2-Updateable)."
			   ::= { gx2drr3xAnalogEntry 20}

		drrminValueRFBAttenuation        OBJECT-TYPE
			   SYNTAX           Float
			   ACCESS           read-only
			   STATUS           mandatory
			   DESCRIPTION
			   "The value of this object provides the minimum value
			    the RF Channel B Attenuation Analog parameter can achive.
			   This value is a floating point number that is represented as an IEEE 32 bit number."
			   ::= { gx2drr3xAnalogEntry 21}

		drrmaxValueRFBAttenuation        OBJECT-TYPE
			   SYNTAX           Float
			   ACCESS           read-only
			   STATUS           mandatory
			   DESCRIPTION
			   "The value of this object provides the maximum value
			    the RF Channel B Attenuation Analog parameter can achive. 
			   This value is a floating point number that is represented as an IEEE 32 bit number."
			   ::= { gx2drr3xAnalogEntry 22}

        drralarmStateRFBAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel B Attenuation Analog parameter."
			   ::= { gx2drr3xAnalogEntry 23}
                 
                 
-- 	RFCAttenuation	          
          		drrlabelRFCAttenuation           OBJECT-TYPE
			   SYNTAX           DisplayString (SIZE (0..80))
			   ACCESS           read-only
			   STATUS           optional
			   DESCRIPTION
			   "The value of this object provides the label of the
			    RF Channel C Attenuation Analog parameter."
			   ::= { gx2drr3xAnalogEntry 24}

		drruomRFCAttenuation             OBJECT-TYPE
			   SYNTAX           DisplayString (SIZE (0..80))
			   ACCESS           read-only
			   STATUS           optional
			   DESCRIPTION
			   "The value of this object provides the Unit of Measure of the
			     RF Channel C Attenuation Analog parameter."
			   ::= { gx2drr3xAnalogEntry 25}

		drrmajorHighRFCAttenuation       OBJECT-TYPE
			   SYNTAX           Float 
			   ACCESS           read-only
			   STATUS           mandatory
			   DESCRIPTION
			   "The value of this object provides the Major High alarm value
			    of the  RF Channel C Attenuation Analog parameter.
			   This parameter has not been used by the module 
                     and set as the invalid float value (0xFFFFFFFF) "
			   ::= { gx2drr3xAnalogEntry 26}

		drrmajorLowRFCAttenuation        OBJECT-TYPE
			   SYNTAX           Float 
			   ACCESS           read-only
			   STATUS           mandatory
			   DESCRIPTION
			   "The value of this object provides the Major Low alarm value
			    of the RF Channel C Attenuation  Analog parameter.
			  This parameter has not been used by the module 
                     and set as the invalid float value (0xFFFFFFFF) "
			   ::= { gx2drr3xAnalogEntry 27}

		drrminorHighRFCAttenuation       OBJECT-TYPE
			   SYNTAX           Float
			   ACCESS           read-only
			   STATUS           mandatory
			   DESCRIPTION
			   "The value of this object provides the Minor High alarm value
			    of the RF Channel C Attenuation  Analog parameter.
			   This parameter has not been used by the module 
                     and set as the invalid float value (0xFFFFFFFF) "
			   ::= { gx2drr3xAnalogEntry 28}

		drrminorLowRFCAttenuation        OBJECT-TYPE
			   SYNTAX           Float 
			   ACCESS           read-only
			   STATUS           mandatory
			   DESCRIPTION
			   "The value of this object provides the Minor Low alarm value
			    of the RF Channel C Attenuation Analog parameter.
			   This parameter has not been used by the module 
                     and set as the invalid float value (0xFFFFFFFF) "
			   ::= { gx2drr3xAnalogEntry 29}

		drrcurrentValueRFCAttenuation    OBJECT-TYPE
			   SYNTAX           Float 
			   ACCESS           read-write
			   STATUS           mandatory
			   DESCRIPTION
			   "The value of this object provides the Current value
			    of the RF Channel C Attenuation Analog parameter.
			   This value is a floating point number that is represented as an IEEE 32 bit number."
			   ::= { gx2drr3xAnalogEntry 30}

		drrstateFlagRFCAttenuation       OBJECT-TYPE
			   SYNTAX           INTEGER
								{
								hidden(1),
								read-only(2),
								updateable(3)
								}
			   ACCESS           read-only
			   STATUS           mandatory
			   DESCRIPTION
			   "The value of this object provides the state
			    of the RF Channel C Attenuation Analog parameter. (0-Hidden	
			          1-Read-Only, 2-Updateable)."
			   ::= { gx2drr3xAnalogEntry 31}

		drrminValueRFCAttenuation        OBJECT-TYPE
			   SYNTAX           Float
			   ACCESS           read-only
			   STATUS           mandatory
			   DESCRIPTION
			   "The value of this object provides the minimum value
			    the RF Channel C Attenuation Analog parameter can achive.
			   This value is a floating point number that is represented as an IEEE 32 bit number."
			   ::= { gx2drr3xAnalogEntry 32}

		drrmaxValueRFCAttenuation        OBJECT-TYPE
			   SYNTAX           Float
			   ACCESS           read-only
			   STATUS           mandatory
			   DESCRIPTION
			   "The value of this object provides the maximum value
			    the RF Channel C Attenuation Analog parameter can achive. 
			   This value is a floating point number that is represented as an IEEE 32 bit number."
			   ::= { gx2drr3xAnalogEntry 33}

        drralarmStateRFCAttenuation      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the RF Channel C Attenuation Analog parameter."
			   ::= { gx2drr3xAnalogEntry 34}
			   
-- 	TrippointLevel	          
        drrlabelTrippointLevel           OBJECT-TYPE
			   SYNTAX           DisplayString (SIZE (0..80))
			   ACCESS           read-only
			   STATUS           optional
			   DESCRIPTION
			   "The value of this object provides the label of the
			    trip point level Analog parameter."
			   ::= { gx2drr3xAnalogEntry 35}

		drruomTrippointLevel             OBJECT-TYPE
			   SYNTAX           DisplayString (SIZE (0..80))
			   ACCESS           read-only
			   STATUS           optional
			   DESCRIPTION
			   "The value of this object provides the Unit of Measure of the
			     trip point level Analog parameter."
			   ::= { gx2drr3xAnalogEntry 36}

		drrmajorHighTrippointLevel       OBJECT-TYPE
			   SYNTAX           Float 
			   ACCESS           read-only
			   STATUS           mandatory
			   DESCRIPTION
			   "The value of this object provides the Major High alarm value
			    of the  trip point level Analog parameter.
			   This parameter has not been used by the module 
                     and set as the invalid float value (0xFFFFFFFF) "
			   ::= { gx2drr3xAnalogEntry 37}

		drrmajorLowTrippointLevel        OBJECT-TYPE
			   SYNTAX           Float 
			   ACCESS           read-only
			   STATUS           mandatory
			   DESCRIPTION
			   "The value of this object provides the Major Low alarm value
			    of the trip point level Analog parameter.
			   This parameter has not been used by the module 
                     and set as the invalid float value (0xFFFFFFFF) "

			   ::= { gx2drr3xAnalogEntry 38}

		drrminorHighTrippointLevel       OBJECT-TYPE
			   SYNTAX           Float
			   ACCESS           read-only
			   STATUS           mandatory
			   DESCRIPTION
			   "The value of this object provides the Minor High alarm value
			    of the trip point level Analog parameter.
			   This parameter has not been used by the module 
                     and set as the invalid float value (0xFFFFFFFF) "
			   ::= { gx2drr3xAnalogEntry 39}

		drrminorLowTrippointLevel        OBJECT-TYPE
			   SYNTAX           Float 
			   ACCESS           read-only
			   STATUS           mandatory
			   DESCRIPTION
			   "The value of this object provides the Minor Low alarm value
			    of the trip point level Analog parameter.
			   This parameter has not been used by the module 
                     and set as the invalid float value (0xFFFFFFFF) "
			   ::= { gx2drr3xAnalogEntry 40}

		drrcurrentValueTrippointLevel    OBJECT-TYPE
			   SYNTAX           Float 
			   ACCESS           read-write
			   STATUS           mandatory
			   DESCRIPTION
			  "The value of this object provides the Current value	of the trippoint level Analog parameter. The trip point level set the custumer preferred 
                      optical input level.
                This parameter combined with trippoint mode(inside digital table) decides the trippoint alarm and RF channel output impedance.
                      
                when optical power level is lower than trip point level(Set by this parameter)
                    1) When trip point mode is ALARM_SWITCH,  trip point alarm will be generated and RF output 
                      impedance will be changed to high impedance.
                    2) When trippoint mode is ALARM_ONLY, trippoint alarm will be generated but RF output inpedance 
                      remains to be low impedance.    
			   This trip point level value is a floating point number that is represented as an IEEE 32 bit number."
			   ::= { gx2drr3xAnalogEntry 41}

		drrstateFlagTrippointLevel       OBJECT-TYPE
			   SYNTAX           INTEGER
								{
								hidden(1),
								read-only(2),
								updateable(3)
								}
			   ACCESS           read-only
			   STATUS           mandatory
			   DESCRIPTION
			   "The value of this object provides the state
			    of the trip point level Analog parameter. (0-Hidden	
			          1-Read-Only, 2-Updateable)."
			   ::= { gx2drr3xAnalogEntry 42}

		drrminValueTrippointLevel        OBJECT-TYPE
			   SYNTAX           Float
			   ACCESS           read-only
			   STATUS           mandatory
			   DESCRIPTION
			   "The value of this object provides the minimum value
			    the trip point level Analog parameter can achive.
			   This value is a floating point number that is represented as an IEEE 32 bit number."
			   ::= { gx2drr3xAnalogEntry 43}

		drrmaxValueTrippointLevel        OBJECT-TYPE
			   SYNTAX           Float
			   ACCESS           read-only
			   STATUS           mandatory
			   DESCRIPTION
			   "The value of this object provides the maximum value
			    the trip point level Analog parameter can achive.
			   This value is a floating point number that is represented as an IEEE 32 bit number."
			   ::= { gx2drr3xAnalogEntry 44}

        drralarmStateTrippointLevel      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the trip point level Analog parameter."
			   ::= { gx2drr3xAnalogEntry 45}
			               
-- Optical power 
	    drrlabelOptCurrent           OBJECT-TYPE
			   SYNTAX           DisplayString (SIZE (0..80))
			   ACCESS           read-only
			   STATUS           optional
			   DESCRIPTION
			   "The value of this object provides the label of the
			    Optical Power Current Analog parameter."
			   ::= { gx2drr3xAnalogEntry 46}

		drruomOptCurrent             OBJECT-TYPE
			   SYNTAX           DisplayString (SIZE (0..80))
			   ACCESS           read-only
			   STATUS           optional
			   DESCRIPTION
			   "The value of this object provides the Unit of Measure of the
			    Optical Power Current Analog parameter."
			   ::= { gx2drr3xAnalogEntry 47}

		drrmajorHighOptCurrent       OBJECT-TYPE
			   SYNTAX           Float 
			   ACCESS           read-only
			   STATUS           mandatory
			   DESCRIPTION
			   "The value of this object provides the Major High alarm value
			    of the Optical Power Current Analog parameter.
			   This value is a floating point number that is represented as an IEEE 32 bit number."
			   ::= { gx2drr3xAnalogEntry 48}


		drrmajorLowOptCurrent        OBJECT-TYPE
			   SYNTAX           Float 
			   ACCESS           read-only
			   STATUS           mandatory
			   DESCRIPTION
			   "The value of this object provides the Major Low alarm value
			    of the Optical Power Current Analog parameter.
			   This value is a floating point number that is represented as an IEEE 32 bit number."
			   ::= { gx2drr3xAnalogEntry 49}

		drrminorHighOptCurrent       OBJECT-TYPE
			   SYNTAX           Float
			   ACCESS           read-only
			   STATUS           mandatory
			   DESCRIPTION
			   "The value of this object provides the Minor High alarm value
			   of the Optical Power Current Analog parameter.
			   This parameter has not been used by the module 
               and set as the invalid float value (0xFFFFFFFF) "
			   ::= { gx2drr3xAnalogEntry 50}

		drrminorLowOptCurrent        OBJECT-TYPE
			   SYNTAX           Float 
			   ACCESS           read-only
			   STATUS           mandatory
			   DESCRIPTION
			   "The value of this object provides the Minor Low alarm value
			    of the Optical Power Current Analog parameter.
			   This parameter has not been used by the module 
               and set as the invalid float value (0xFFFFFFFF) "
               ::= { gx2drr3xAnalogEntry 51}

		drrcurrentValueOptCurrent    OBJECT-TYPE
			   SYNTAX           Float 
			   ACCESS           read-only
			   STATUS           mandatory
			   DESCRIPTION
			   "The value of this object provides the Current value
			    of the Optical Power Current Analog parameter.
			   This value is a floating point number that is represented as an IEEE 32 bit number."
			   ::= { gx2drr3xAnalogEntry 52}

		drrstateFlagOptCurrent       OBJECT-TYPE
			   SYNTAX           INTEGER
								{
								hidden(1),
								read-only(2),
								updateable(3)
								}
			   ACCESS           read-only
			   STATUS           mandatory
			   DESCRIPTION
			   "The value of this object provides the state
			    of the Optical Power Current Analog parameter. (0-Hidden	
			          1-Read-Only, 2-Updateable)."
			   ::= { gx2drr3xAnalogEntry 53}

		drrminValueOptCurrent        OBJECT-TYPE
			   SYNTAX           Float
			   ACCESS           read-only
			   STATUS           mandatory
			   DESCRIPTION
			   "The value of this object provides the minimum value
			    the Optical Power Current Analog parameter can achive.
			   This value is a floating point number that is represented as an IEEE 32 bit number.
			   The input optical power in lower than this value, 
			   drrcurrentValueOptCurrent will report -99dBm"
               ::= { gx2drr3xAnalogEntry 54}

		drrmaxValueOptCurrent        OBJECT-TYPE
			   SYNTAX           Float
			   ACCESS           read-only
			   STATUS           mandatory
			   DESCRIPTION
			   "The value of this object provides the maximum value
			    the Optical Power Current  Analog parameter can achive.
			   This value is a floating point number that is represented as an IEEE 32 bit number.
			   The input optical power in higher than this value, 
			   drrcurrentValueOptCurrent will report 99dBm"
			   ::= { gx2drr3xAnalogEntry 55}

        drralarmStateOptCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Optical Power Current Analog parameter."
			   ::= { gx2drr3xAnalogEntry 56}
			   
-- 12V current 
    	drrlabel12VCurrent           OBJECT-TYPE
			   SYNTAX           DisplayString (SIZE (0..80))
			   ACCESS           read-only
			   STATUS           optional
			   DESCRIPTION
			   "The value of this object provides the label of the
			    12v power supply Current Analog parameter."
			   ::= { gx2drr3xAnalogEntry 57}

		drruom12VCurrent             OBJECT-TYPE
			   SYNTAX           DisplayString (SIZE (0..80))
			   ACCESS           read-only
			   STATUS           optional
			   DESCRIPTION
			   "The value of this object provides the Unit of Measure of the
			    12v power supply Current Analog parameter."
			   ::= { gx2drr3xAnalogEntry 58}

		drrmajorHigh12VCurrent       OBJECT-TYPE
			   SYNTAX           Float 
			   ACCESS           read-only
			   STATUS           mandatory
			   DESCRIPTION
			   "The value of this object provides the Major High alarm value
			    of the 12v power supply Current Analog parameter.
			   This value is a floating point number that is represented as an IEEE 32 bit number."
			   ::= { gx2drr3xAnalogEntry 59}


		drrmajorLow12VCurrent        OBJECT-TYPE
			   SYNTAX           Float 
			   ACCESS           read-only
			   STATUS           mandatory
			   DESCRIPTION
			   "The value of this object provides the Major Low alarm value
			    of the 12v power supply Current Analog parameter.
			   This value is a floating point number that is represented as an IEEE 32 bit number."
			   ::= { gx2drr3xAnalogEntry 60}

		drrminorHigh12VCurrent       OBJECT-TYPE
			   SYNTAX           Float
			   ACCESS           read-only
			   STATUS           mandatory
			   DESCRIPTION
			   "The value of this object provides the Minor High alarm value
			    of the 12v power supply Current Analog parameter.
			   This value is a floating point number that is represented as an IEEE 32 bit number."
			   ::= { gx2drr3xAnalogEntry 61}

		drrminorLow12VCurrent        OBJECT-TYPE
			   SYNTAX           Float 
			   ACCESS           read-only
			   STATUS           mandatory
			   DESCRIPTION
			   "The value of this object provides the Minor Low alarm value
			    of the 12v power supply Current Analog parameter.
			   This value is a floating point number that is represented as an IEEE 32 bit number."
			   ::= { gx2drr3xAnalogEntry 62}

		drrcurrentValue12VCurrent    OBJECT-TYPE
			   SYNTAX           Float 
			   ACCESS           read-only
			   STATUS           mandatory
			   DESCRIPTION
			   "The value of this object provides the Current value
			    of the 12v power supply Current parameter.
			   This value is a floating point number that is represented as an IEEE 32 bit number."
			   ::= { gx2drr3xAnalogEntry 63}

		drrstateFlag12VCurrent       OBJECT-TYPE
			   SYNTAX           INTEGER
								{
								hidden(1),
								read-only(2),
								updateable(3)
								}
			   ACCESS           read-only
			   STATUS           mandatory
			   DESCRIPTION
			   "The value of this object provides the state
			    of the 12v power supply Current Analog parameter. (0-Hidden	
			          1-Read-Only, 2-Updateable)."
			   ::= { gx2drr3xAnalogEntry 64}

		drrminValue12VCurrent        OBJECT-TYPE
			   SYNTAX           Float
			   ACCESS           read-only
			   STATUS           mandatory
			   DESCRIPTION
			   "The value of this object provides the minimum value
			    the 12v power supply Current Analog parameter can achive.
			   This value is a floating point number that is represented as an IEEE 32 bit number."
			   ::= { gx2drr3xAnalogEntry 65}

		drrmaxValue12VCurrent        OBJECT-TYPE
			   SYNTAX           Float
			   ACCESS           read-only
			   STATUS           mandatory
			   DESCRIPTION
			   "The value of this object provides the maximum value
			    the 12v power supply Current Analog parameter can achive.
			   This value is a floating point number that is represented as an IEEE 32 bit number."
			   ::= { gx2drr3xAnalogEntry 66}

        drralarmState12VCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the 12v power supply Current Analog parameter."
			   ::= { gx2drr3xAnalogEntry 67}
			   
-- Module Temperature 

		drrlabelModTemp              OBJECT-TYPE
			   SYNTAX           DisplayString (SIZE (0..80))
			   ACCESS           read-only
			   STATUS           optional
			   DESCRIPTION
			   "The value of this object provides the label of the
			    Module Temperature Analog parameter."
			   ::= { gx2drr3xAnalogEntry 68}

		drruomModTemp                OBJECT-TYPE
			   SYNTAX           DisplayString (SIZE (0..80))
			   ACCESS           read-only
			   STATUS           optional
			   DESCRIPTION
			   "The value of this object provides the Unit of Measure of the
			    Module Temperature Analog parameter."
			   ::= { gx2drr3xAnalogEntry 69}

		drrmajorHighModTemp          OBJECT-TYPE
			   SYNTAX           Float 
			   ACCESS           read-only
			   STATUS           mandatory
			   DESCRIPTION
			   "The value of this object provides the Major High alarm value
			    of the Module Temperature Analog parameter.
			   This value is a floating point number that is represented as an IEEE 32 bit number."
			   ::= { gx2drr3xAnalogEntry 70}


		drrmajorLowModTemp           OBJECT-TYPE
			   SYNTAX           Float 
			   ACCESS           read-only
			   STATUS           mandatory
			   DESCRIPTION
			   "The value of this object provides the Major Low alarm value
			    of the Module Temperature Analog parameter.
			   This value is a floating point number that is represented as an IEEE 32 bit number."
			   ::= { gx2drr3xAnalogEntry 71}

		drrminorHighModTemp          OBJECT-TYPE
			   SYNTAX           Float
			   ACCESS           read-only
			   STATUS           mandatory
			   DESCRIPTION
			   "The value of this object provides the Minor High alarm value
			    of the Module Temperature Analog parameter.
			   This value is a floating point number that is represented as an IEEE 32 bit number."
			   ::= { gx2drr3xAnalogEntry 72}

		drrminorLowModTemp           OBJECT-TYPE
			   SYNTAX           Float 
			   ACCESS           read-only
			   STATUS           mandatory
			   DESCRIPTION
			   "The value of this object provides the Minor Low alarm value
			    of the Module Temperature Analog parameter.
			   This value is a floating point number that is represented as an IEEE 32 bit number."
			   ::= { gx2drr3xAnalogEntry 73}

		drrcurrentValueModTemp       OBJECT-TYPE
			   SYNTAX           Float 
			   ACCESS           read-only
			   STATUS           mandatory
			   DESCRIPTION
			   "The value of this object provides the Current value
			    of the Module Temperature Analog parameter.
			   This value is a floating point number that is represented as an IEEE 32 bit number."
			   ::= { gx2drr3xAnalogEntry 74}

		drrstateFlagModTemp          OBJECT-TYPE
			   SYNTAX           INTEGER
								{
								hidden(1),
								read-only(2),
								updateable(3)
								}
			   ACCESS           read-only
			   STATUS           mandatory
			   DESCRIPTION
			   "The value of this object provides the state
			    of the Module Temperature Analog parameter. (0-Hidden	
			          1-Read-Only, 2-Updateable)."
			   ::= { gx2drr3xAnalogEntry 75}

		drrminValueModTemp           OBJECT-TYPE
			   SYNTAX           Float
			   ACCESS           read-only
			   STATUS           mandatory
			   DESCRIPTION
			   "The value of this object provides the minimum value
			    the Module Temperature Analog parameter can achive.
			   This value is a floating point number that is represented as an IEEE 32 bit number."
			   ::= { gx2drr3xAnalogEntry 76}

		drrmaxValueModTemp           OBJECT-TYPE
			   SYNTAX           Float
			   ACCESS           read-only
			   STATUS           mandatory
			   DESCRIPTION
			   "The value of this object provides the maximum value
			    the Module Temperature Analog parameter can achive.
			   This value is a floating point number that is represented as an IEEE 32 bit number."
			   ::= { gx2drr3xAnalogEntry 77}

		drralarmStateModTemp         OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Module Temperature Analog parameter."
			   ::= { gx2drr3xAnalogEntry 78}
			     
			   
-- Fan current 
		drrlabelFanCurrent           OBJECT-TYPE
			   SYNTAX           DisplayString (SIZE (0..80))
			   ACCESS           read-only
			   STATUS           optional
			   DESCRIPTION
			   "The value of this object provides the label of the
			    Fan Current Analog parameter."
			   ::= { gx2drr3xAnalogEntry 79}

		drruomFanCurrent             OBJECT-TYPE
			   SYNTAX           DisplayString (SIZE (0..80))
			   ACCESS           read-only
			   STATUS           optional
			   DESCRIPTION
			   "The value of this object provides the Unit of Measure of the
			    Fan Current Analog parameter."
			   ::= { gx2drr3xAnalogEntry 80}

		drrmajorHighFanCurrent       OBJECT-TYPE
			   SYNTAX           Float 
			   ACCESS           read-only
			   STATUS           mandatory
			   DESCRIPTION
			   "The value of this object provides the Major High alarm value
			    of the Fan Current Analog parameter.This value is a floating 
			    point number that is represented as an IEEE 32 bit number."
			   ::= { gx2drr3xAnalogEntry 81}


		drrmajorLowFanCurrent        OBJECT-TYPE
			   SYNTAX           Float 
			   ACCESS           read-only
			   STATUS           mandatory
			   DESCRIPTION
			   "The value of this object provides the Major Low alarm value
			    of the Fan Current Analog parameter.This value is a floating
			    point number that is represented as an IEEE 32 bit number."
			   ::= { gx2drr3xAnalogEntry 82}

		drrminorHighFanCurrent       OBJECT-TYPE
			   SYNTAX           Float
			   ACCESS           read-only
			   STATUS           mandatory
			   DESCRIPTION
			   "The value of this object provides the Minor High alarm value
			    of the Fan Current Analog parameter.
			    This parameter has not been used by the module 
               and set as the invalid float value (0xFFFFFFFF)"
			   ::= { gx2drr3xAnalogEntry 83}

		drrminorLowFanCurrent        OBJECT-TYPE
			   SYNTAX           Float 
			   ACCESS           read-only
			   STATUS           mandatory
			   DESCRIPTION
			   "The value of this object provides the Minor Low alarm value
			    of the Fan Current Analog parameter.
			    This parameter has not been used by the module 
               and set as the invalid float value (0xFFFFFFFF)"
               ::= { gx2drr3xAnalogEntry 84}

		drrcurrentValueFanCurrent    OBJECT-TYPE
			   SYNTAX           Float 
			   ACCESS           read-only
			   STATUS           mandatory
			   DESCRIPTION
			   "The value of this object provides the Current value
			    of the Fan Current Analog parameter.This value is a floating 
			    point number that is represented as an IEEE 32 bit number."
			   ::= { gx2drr3xAnalogEntry 85}

		drrstateFlagFanCurrent       OBJECT-TYPE
			   SYNTAX           INTEGER
								{
								hidden(1),
								read-only(2),
								updateable(3)
								}
			   ACCESS           read-only
			   STATUS           mandatory
			   DESCRIPTION
			   "The value of this object provides the state
			    of the Fan Current Analog parameter. (0-Hidden	
			          1-Read-Only, 2-Updateable)."
			   ::= { gx2drr3xAnalogEntry 86}

		drrminValueFanCurrent        OBJECT-TYPE
			   SYNTAX           Float
			   ACCESS           read-only
			   STATUS           mandatory
			   DESCRIPTION
			   "The value of this object provides the minimum value
			    the Fan Current Analog parameter can achive. This value is a 
			    floating point number that is represented as an IEEE 32 bit number."
			   ::= { gx2drr3xAnalogEntry 87}

		drrmaxValueFanCurrent        OBJECT-TYPE
			   SYNTAX           Float
			   ACCESS           read-only
			   STATUS           mandatory
			   DESCRIPTION
			   "The value of this object provides the maximum value
			    the Fan Current Analog parameter can achive. This value is a floating
			    point number that is represented as an IEEE 32 bit number."
			   ::= { gx2drr3xAnalogEntry 88}

        drralarmStateFanCurrent      OBJECT-TYPE
			   SYNTAX           INTEGER
									{
									noAlarm(1),
									majorLowAlarm(2),
									minorLowAlarm(3),
									minorHighAlarm(4),
									majorHighAlarm(5),
									informational(6)
									}
			   ACCESS           read-only
			   STATUS           mandatory
			   DESCRIPTION
			   "The value of this object provides the curent alarm state of
			    the Fan Current Analog parameter."
			   ::= { gx2drr3xAnalogEntry 89}  
			   
    			   
-- ************************ Digital parameters **********************************
		gx2drr3xDigitalTableIndex              OBJECT-TYPE
			   SYNTAX           INTEGER (1..4294967295)
			   ACCESS           read-only
			   STATUS           mandatory
			   DESCRIPTION
			   "The value of this object identifies the network
			    element. This index is equal to the
			    hfcCommonTableIndex for the same element."
               ::= { gx2drr3xDigitalEntry 1}
               
   -- Trip point mode   
         drrlabelTrippointMode          OBJECT-TYPE
			   SYNTAX       		DisplayString (SIZE (0..80))         
			   ACCESS           	read-only
			   STATUS           	optional
			   DESCRIPTION
			   "The value of this object provides the label of the
			    Trip point mode Digital parameter. The trip point mode defines the RF switch 
                      action based on the optical power input to the DRR3X"
			   ::= { gx2drr3xDigitalEntry 2}

		drrenumTrippointMode               	OBJECT-TYPE
			   SYNTAX       		DisplayString (SIZE (0..80))         
			   ACCESS           	read-only
			   STATUS           	optional
			   DESCRIPTION
			   "The value of this object represents the Enumeration values
			    possible for the Digital parameter. Each Enumerated values is
			    separated by a common. "
			   ::= { gx2drr3xDigitalEntry 3}


		drrvalueTrippointMode         	OBJECT-TYPE
			   SYNTAX					INTEGER{
			   							off(1),
			   							alarmOnly(2),
			   							alarm-and-Switch(3)
			   							}			   					    	
			   ACCESS           	read-write
			   STATUS           	mandatory
			   DESCRIPTION
			   "The value of this object is the current value of trip point mode.
			   There are three possible value: 1-off, 2-alarm_only, 3-alarm&switch.
			   			   
			   If module input optical power is higher than the preset trippoint value,
			        no operational difference for these three modes. 
			   
			   If module input optical power is less than the preset trippoint value, 
                     1) When trippoint mode is OFF, no trippoint alarm will be generated and RF output impedance 
                     will stay normal as low.
                     2) When tripoint mode is ALARM_ONLY, trip_point alarm will be generated when the input optical power 
                     lower than the preset trippoint level but RF output impedance will stay normal as low. 
                     3) When trippoint mode is ALARM_SWITCH, trip point alarm will be generated and RF output impedance 
                     will switch to abnorml as high impedance"
               ::= { gx2drr3xDigitalEntry 4}

		drrstateflagTrippointMode     	OBJECT-TYPE
			   SYNTAX       		INTEGER
								{
								hidden(1),
								readOnly(2),
								updateable(3)
								}
			   ACCESS           	read-only
			   STATUS           	mandatory
			   DESCRIPTION
			   "The value of this object provides the state
			    of the the parameter. (0-Hidden 1-Read-Only, 2-Updateable)."
			   ::= { gx2drr3xDigitalEntry 5}
			   		   
	-- Front panel test point control     
         drrlabelFrontPanelTest          OBJECT-TYPE
			   SYNTAX       		DisplayString (SIZE (0..80))         
			   ACCESS           	read-only
			   STATUS           	optional
			   DESCRIPTION
			   "The value of this object provides the label of the
			    Front panel test point Digital parameter."
			   ::= { gx2drr3xDigitalEntry 6}

		drrenumFrontPanelTest               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2drr3xDigitalEntry 7}

		drrvalueFrontPanelTest        	OBJECT-TYPE
				SYNTAX					INTEGER
										{
										chanA(1),
										chanB(2),
										chanC(3)
										}			   					    	
			   ACCESS           	read-write
			   STATUS           	mandatory
			   DESCRIPTION
			   "The value of this object is the current value of Front panel 
			   RF test point Channel number"
			   ::= { gx2drr3xDigitalEntry 8}

		drrstateflagFrontPanelTest    	OBJECT-TYPE
			   SYNTAX       		INTEGER
								{
								hidden(1),
								readOnly(2),
								updateable(3)
								}
			   ACCESS           	read-only
			   STATUS           	mandatory
			   DESCRIPTION
			   "The value of this object provides the state
			    of the the parameter. (0-Hidden 1-Read-Only, 2-Updateable)."
			   ::= { gx2drr3xDigitalEntry 9}  
			   		   
-- Factory default reset 
         drrlabelFactoryDefaultReset           OBJECT-TYPE
			   SYNTAX       		DisplayString (SIZE (0..80))         
			   ACCESS           	read-only
			   STATUS           	optional
			   DESCRIPTION
			   "The value of this object provides the label of the
			    Factory Default Reset  Digital parameter."
			   ::= { gx2drr3xDigitalEntry 10}

		drrenumFactoryDefaultReset               	OBJECT-TYPE
			   SYNTAX       		DisplayString (SIZE (0..80))         
			   ACCESS           	read-only
			   STATUS           	optional
			   DESCRIPTION
			   "The value of this object represents the Enumeration values
			    possible for the Digital parameter. Each Enumerated values is
			    separated by a common. The first value has a enumerated value of 1."
			   ::= { gx2drr3xDigitalEntry 11}


		drrvalueFactoryDefaultReset         	OBJECT-TYPE
			   SYNTAX       		INTEGER
					    		{
							off(1),
							on(2)
					    		}
			   ACCESS           	read-write
			   STATUS           	mandatory
			   DESCRIPTION
			   "The read of this value will return a invalid value.
			    The read will not reflect the actual setting value for this parameter
			   "
			   ::= { gx2drr3xDigitalEntry 12}

		drrstateflagFactoryDefaultReset     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drr3xDigitalEntry 13} 
			   
   
 	--*********** STATUS *****************
		gx2drr3xStatusTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2drr3xStatusEntry 1}

--Boot status 
		drrlabelBoot               	OBJECT-TYPE
			   SYNTAX       		DisplayString (SIZE (0..80))         
			   ACCESS           	read-only
			   STATUS           	optional
			   DESCRIPTION
			   "The value of this object provides the label of the
			    Boot Status  parameter."
			   ::= { gx2drr3xStatusEntry 2}

		drrvalueBoot              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drr3xStatusEntry 3}

		drrstateflagBoot     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drr3xStatusEntry  4}

--Flash program status 
		drrlabelFlash               	OBJECT-TYPE
			   SYNTAX       		DisplayString (SIZE (0..80))         
			   ACCESS           	read-only
			   STATUS           	optional
			   DESCRIPTION
			   "The value of this object provides the label of the
			    Flash Status  parameter."
			   ::= { gx2drr3xStatusEntry 5}

		drrvalueFlash              	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drr3xStatusEntry 6}

		drrstateflagFlash     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drr3xStatusEntry  7}

--Factory data crc 
		drrlabelFactoryDataCRC           OBJECT-TYPE
			   SYNTAX       		DisplayString (SIZE (0..80))         
			   ACCESS           	read-only
			   STATUS           	optional
			   DESCRIPTION
			   "The value of this object provides the label of the
			    Factory Data CRC Status parameter."
			   ::= { gx2drr3xStatusEntry 8}

		drrvalueFactoryDataCRC          	OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drr3xStatusEntry 9}

		drrstateflagFactoryDataCRC     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drr3xStatusEntry  10}

--Alarm data status CRC
		drrlabelAlarmDataCrc               	      OBJECT-TYPE
			   SYNTAX       		DisplayString (SIZE (0..80))         
			   ACCESS           	read-only
			   STATUS           	optional
			   DESCRIPTION
			   "The value of this object provides the label of the
			    Alarm Data Crc parameter."
			   ::= { gx2drr3xStatusEntry 11}

		drrvalueAlarmDataCrc              		OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drr3xStatusEntry 12}

		drrstateflagAlarmDataCrc     	OBJECT-TYPE
			   SYNTAX       		INTEGER
								{
								hidden(1),
								read-only(2),
								updateable(3)
								}
			   ACCESS           	read-only
			   STATUS           	mandatory
			   DESCRIPTION
			   "The value of this object provides the state
			    of the the parameter. (0-Hidden 1-Read-Only, 2-Updateable)."
			   ::= { gx2drr3xStatusEntry  13}

--Module hardware status
		drrlabelHardwareStatus              OBJECT-TYPE
			   SYNTAX       		DisplayString (SIZE (0..80))         
			   ACCESS           	read-only
			   STATUS           	optional
			   DESCRIPTION
			   "The value of this object provides the label of the
			   Module Hardware Status parameter."
			   ::= { gx2drr3xStatusEntry 14}

		drrvalueHardwareStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drr3xStatusEntry 15}

		drrstateflagHardwareStatus     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2drr3xStatusEntry  16}
                            
  --Optical signal trip point status 
		drrlabelOpticTripPointStatus              OBJECT-TYPE
			   SYNTAX       		DisplayString (SIZE (0..80))         
			   ACCESS           	read-only
			   STATUS           	optional
			   DESCRIPTION
			   "The value of this object provides the label of the
			    Optical Trip Point Status parameter.It indicates whether 
			    the optical power is above(0) or below(1) trip point value"
			   ::= { gx2drr3xStatusEntry 17}

		drrvalueOpticTripPointStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drr3xStatusEntry 18}

		drrstateflagOpticTripPointStatus     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2drr3xStatusEntry  19}
    
                                        
         --Link Status 
		drrlabelLinkStatus              OBJECT-TYPE
			   SYNTAX       		DisplayString (SIZE (0..80))         
			   ACCESS           	read-only
			   STATUS           	optional
			   DESCRIPTION
			   "The value of this object provides the label of the
			    Link Activity Status parameter. It represents receiver
			    out of SYN with transmitter or Demux can not detect 
			    the optical signal."
			   ::= { gx2drr3xStatusEntry 20}

		drrvalueLinkStatus              OBJECT-TYPE
			   SYNTAX       		INTEGER
									{
									ok(1),
									undetermined(2),
									warning(3),
									minor(4),
									major(5),
									critical(6)
									}
			   ACCESS           	read-only
			   STATUS           	mandatory
			   DESCRIPTION
			   "The value of this object provides the current state of
			    the parameter (0-Ok, 1-Undetermined
			    2-Warning, 3-Minor, 4-Major, 5-Critical)."
			   ::= { gx2drr3xStatusEntry 21}

		drrstateflagLinkStatus     	OBJECT-TYPE
			   SYNTAX       		INTEGER
								{
								hidden(1),
								read-only(2),
								updateable(3)
								}
			   ACCESS           	read-only
			   STATUS           	mandatory
			   DESCRIPTION
			   "The value of this object provides the state
			    of the parameter. (0-Hidden 1-Read-Only, 2-Updateable)."
			   ::= { gx2drr3xStatusEntry  22}
                          
                                       
-- ************ FACTORY DATA ****************
		gx2drr3xFactoryTableIndex              OBJECT-TYPE
			   SYNTAX           INTEGER (1..4294967295)
			   ACCESS           read-only
			   STATUS           mandatory
			   DESCRIPTION
			   "The value of this object identifies the network
			    element. This index is equal to the
			    hfcCommonTableIndex for the same element."
			   ::= { gx2drr3xFactoryEntry 1}

		drrbootControlByte          	OBJECT-TYPE
			   SYNTAX       		INTEGER
			   ACCESS           	read-only
			   STATUS           	mandatory
			   DESCRIPTION
			   "The value of this object indicates which bank the firmware
			    is currently being boot from."
			   ::= { gx2drr3xFactoryEntry 2}

		drrbootStatusByte          	OBJECT-TYPE
			   SYNTAX       		INTEGER
			   ACCESS           	read-only
			   STATUS           	mandatory
			   DESCRIPTION
			   "This object indicates the status of the last boot"
			   ::= { gx2drr3xFactoryEntry 3}

		drrbank1CRC          		OBJECT-TYPE
			   SYNTAX       		INTEGER
			   ACCESS           	read-only
			   STATUS           	mandatory
			   DESCRIPTION
			   "This object provides the CRC code of bank 0."
			   ::= { gx2drr3xFactoryEntry 4}

		drrbank2CRC          		OBJECT-TYPE
			   SYNTAX       		INTEGER
			   ACCESS           	read-only
			   STATUS           	mandatory
			   DESCRIPTION
			   "This object provides the CRC code of bank 1."
			   ::= { gx2drr3xFactoryEntry 5}

		drrprgEEPROMByte          		OBJECT-TYPE
			   SYNTAX       		INTEGER
			   ACCESS           	read-only
			   STATUS           	mandatory
			   DESCRIPTION
			   "This object indicates if the EEPROM has been programmed"
			   ::= { gx2drr3xFactoryEntry 6}

		drrfactoryCRC          		OBJECT-TYPE
			   SYNTAX       		INTEGER
			   ACCESS           	read-only
			   STATUS           	mandatory
			   DESCRIPTION
			   "This object provides the CRC code for the Factory data."
			   ::= { gx2drr3xFactoryEntry 7}

		drrcalculateCRC          		OBJECT-TYPE
			   SYNTAX       		INTEGER
					    		{
							factory(1),
							alarm(2)
					    		}
			   ACCESS           	read-only
			   STATUS           	mandatory
			   DESCRIPTION
			   "This object indicates which of the Emnums will have the CRC calculated."
			   ::= { gx2drr3xFactoryEntry 8}

		drrhourMeter          		OBJECT-TYPE
			   SYNTAX       		INTEGER
			   ACCESS           	read-only
			   STATUS           	mandatory
			   DESCRIPTION
			   "This object provides the hour meter reading of the module."
			   ::= { gx2drr3xFactoryEntry 9}

		drrflashPrgCntA          		OBJECT-TYPE
			   SYNTAX       		INTEGER
			   ACCESS           	read-only
			   STATUS           	mandatory
			   DESCRIPTION
			   "This object provides the number of times Bank 0 flash has been 
                      programmed."
			   ::= { gx2drr3xFactoryEntry 10}

		drrflashPrgCntB          		OBJECT-TYPE
			   SYNTAX       		INTEGER
			   ACCESS           	read-only
			   STATUS           	mandatory
			   DESCRIPTION
			   "This object provides the number of times Bank 1 flash has been 
                      programmed."
			   ::= { gx2drr3xFactoryEntry 11}

		drrflashBankARev          		OBJECT-TYPE
			   SYNTAX       		DisplayString (SIZE (0..80))
			   ACCESS           	read-only
			   STATUS           	mandatory
			   DESCRIPTION
			   "This object provides the revision of flash bank 0."
			   ::= { gx2drr3xFactoryEntry 12}

		drrflashBankBRev          		OBJECT-TYPE
			   SYNTAX       		DisplayString (SIZE (0..80))
			   ACCESS           	read-only
			   STATUS           	mandatory
			   DESCRIPTION
			   "This object provides the revision of flash bank 1."
			   ::= { gx2drr3xFactoryEntry 13}
                  
--		drrSubAgentRev          		OBJECT-TYPE
--			   SYNTAX       		DisplayString (SIZE (0..80))
--			   ACCESS           	read-only
--			   STATUS           	mandatory
--			   DESCRIPTION
--			   "This object provides the subagent revision of receiver module."
--			   ::= { gx2drr3xFactoryEntry 14}
--
-- ****************************************************************
--
-- TRAP DEFINITIONS
--
--
-- Every trap generated by an HFC agents will include first 9 identical
-- fields. If particular variable is not supported in
-- particular TRAP-TYPE then default value will be returned.
--
-- DESCRIPTION will include explanation of use of generic
-- variables (trapAdditionalInfo******.)  If no
-- DESCRIPTION is given then generic variables will contain
-- default values.
--
-- *****************************************************************

--***************************************************************************
-- ***********!!! THE TRAP SECTION HAS NOT BEEN COMPLETED YET !!! ***********
--***************************************************************************

-- **************************************************************************
--                              Digital Receiver Return Module traps
-- **************************************************************************
   trapdrrConfigChangeInteger TRAP-TYPE
       ENTERPRISE gx2Drr3x
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueInteger,
		trapNETrapLastTrapTimeStamp
	       }
       DESCRIPTION
	"This trap is issued if configuration of a single variable
	 with integer type was changed (via ANY interface).  
	 TrapChangedValueInteger variable may contain current reading
	 of that variable.
	 trapPerceivedSeverity - 'indeterminate'"
  ::= 1

   trapdrrConfigChangeDisplayString TRAP-TYPE
       ENTERPRISE gx2Drr3x
       VARIABLES
	       {       
		trapIdentifier,
		trapNetworkElemModelNumber,
		trapNetworkElemSerialNum,
		trapPerceivedSeverity,
		trapNetworkElemOperState,
		trapNetworkElemAlarmStatus,  
		trapNetworkElemAdminState,
		trapNetworkElemAvailStatus,
		trapText,
		trapChangedObjectId,
		trapChangedValueDisplayString,
		trapNETrapLastTrapTimeStamp
	       }
       DESCRIPTION
	"This trap is issued if configuration of a single variable
	 with DispalayString type was changed (via ANY interface).  
	 TrapChangedValueDisplayString variable may contain current reading
	 of that variable.
	 trapPerceivedSeverity - 'indeterminate'"
  ::= 2
        
   trapdrr12VCurrentAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the 12V power supply Current 
	 parameter goes out of range.
	 trapAdditionalInfoInteger variable contains current reading of 
	 the this parameter."
     ::= 3       
          
  trapdrrModuleTempAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Internal Module Temperature goes out of range.
	 trapAdditionalInfoInteger variable contains current reading of 
	 the this parameter."
    ::= 4
  
    trapdrrFanCurrentAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Fan Current 
	 parameter goes out of range.
	 trapAdditionalInfoInteger variable contains current reading of 
	 the this parameter."
  ::= 5

  trapdrrFlashAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the detects an error during
	Flash memory operations."
  ::= 6
  
  trapdrrBankBootAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the detects an error while booting
	from bank 0 or bank 1."
  ::= 7

	trapdrrAlarmDataCRCAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Alarm Data CRC is incorrect."
  ::= 8

	trapdrrHardwareErrAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when hardware is abnormal."
  ::= 9

 	trapdrrOpticalSignalAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the optical signal is beyond the reason range."  
  ::= 10
 
	trapdrrFactoryDataCRCAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Data CRC is incorrect."
  ::= 11

	trapdrrResetFactoryDefaultAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Factory Default Reset occurs."
  ::= 12

	trapdrrTripPointAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when the Input optical power is lower than the custumer set 
	trip point."
  ::= 13       
  
    trapdrrLinkAlarm TRAP-TYPE
	ENTERPRISE gx2Drr3x
	VARIABLES
		{       
		 trapIdentifier,
		 trapNetworkElemModelNumber,
		 trapNetworkElemSerialNum,
		 trapPerceivedSeverity,
		 trapNetworkElemOperState,
		 trapNetworkElemAlarmStatus,  
		 trapNetworkElemAdminState,
		 trapNetworkElemAvailStatus,
		 trapText,
		 trapChangedObjectId,
		 trapChangedValueInteger,
		 trapNETrapLastTrapTimeStamp
		}
	DESCRIPTION
	"This trap is issued when receiver is out of SYN with transmitter"
  ::= 14 

  END
