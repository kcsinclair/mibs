--
-- she-l2cp-mib.mib
-- MIB generated by MG-SOFT Visual MIB Builder Version 5.0  Build 250
-- Wednesday, June 06, 2007 at 08:58:42
--

	SHE-L2CP-MIB DEFINITIONS ::= BEGIN
 
		IMPORTS
			she			
				FROM AN-MIB			
			ifIndex			
				FROM IF-MIB			
			sheAlarmTimeAndDate, sheAlarmReportingSource, sheAlarmReportingSourceType, sheAlarmSeverity, SheAlarmSevProfileIndex			
				FROM SHE-ALARMING-MIB			
			SheControlStatusType			
				FROM SHE-TC-MIB			
			OBJECT-GROUP, MODULE-COMPLIANCE, NOTIFICATION-GROUP			
				FROM SNMPv2-CONF			
			Integer32, Unsigned32, OBJECT-TYPE, MODULE-IDENTITY, NOTIFICATION-TYPE			
				FROM SNMPv2-SMI;
	
	
		sheL2cpMib MODULE-IDENTITY 
			LAST-UPDATED "200706060955Z"		-- June 06, 2007 at 09:55 GMT
			ORGANIZATION 
				"Nokia Siemens Networks"
			CONTACT-INFO 
				"Gerd Barchmann
				COO BBA DSLAM RD SDE
				
				gerd.barchmann@nsn.com
				+49 3834 555654"
			DESCRIPTION 
				"She L2CP interface description."
			REVISION "200510111331Z"		-- October 11, 2005 at 13:31 GMT
			DESCRIPTION 
				"First release."
			REVISION "200511031526Z"		-- November 03, 2005 at 15:26 GMT
			DESCRIPTION 
				"Correct notification's object list's."
			REVISION "200512011555Z"		-- December 01, 2005 at 15:55 GMT
			DESCRIPTION 
				"Correct Range for Timer1 and set default value for Timers and
				PartitionId."
			REVISION "200512091105Z"		-- December 09, 2005 at 11:05 GMT
			DESCRIPTION 
				"Change access for table index to readonly."
			REVISION "200602271037Z"		-- February 27, 2006 at 10:37 GMT
			DESCRIPTION 
				"Add configuration of AlarmSeverity to L2cpIf-Table."
			REVISION "200604051012Z"		-- April 05, 2006 at 10:12 GMT
			DESCRIPTION 
				"Add new table and control group for configuration
				of the local l2cp host interface."
			REVISION "200605101606Z"		-- May 10, 2006 at 16:06 GMT
			DESCRIPTION 
				"Correct access for sheL2coHostIfVlanId.
				Delete Gateway entry from HostIf-Table."
			REVISION "200608101600Z"		-- August 10, 2006 at 16:00 GMT
			DESCRIPTION 
				"Merge from VSHE!!"
			REVISION "200704251033Z"		-- April 25, 2007 at 10:33 GMT
			DESCRIPTION 
				"HostIf configuration is now handled in sheSystemMib for the complete NE.
				The HostIfTable and Control-group is not longer supported with SHE R2.5.2."
			REVISION "200706061022Z"		-- June 06, 2007 at 10:22 GMT
			DESCRIPTION 
				"Set status for not longer supported elements obsolete (R2.6)."
			::= { she 16 }

		
	
--
-- Type definitions
--
	
		SheL2cpOperStateType ::= INTEGER
			{
			up(1),
			down(2)
			}

--   The states of the adjacency protocol.
		SheL2cpAdjacencyStateType ::= INTEGER
			{
			l2cpStateRESET(1),
			l2cpStateSYNSENT(2),
			l2cpStateSYNRCVD(3),
			l2cpStateESTAB(4)
			}

--  The ID of the partition managed by an L2CP protocol instance (see RFC 3292).
-- Or the partition to which a port is assigned.
-- 0...255: These are really partition IDs.
--     256: no partition (e.g. in case when DSLAM does not support partitions)
--     257: invalid partition (e.g. a port does not belong to any partition)
		SheL2cpPartitionIdType ::= INTEGER (0..255 | 256 | 257)

		SheL2cpControlRequestType ::= INTEGER
			{
			createL2cpIf(1),
			deleteL2cpIf(2),
			modifyL2cpIf(3),
			createL2cpHostIf(6),
			modifyL2cpHostIf(7),
			deleteL2cpHostIf(8),
			assignPortToPartition(10)
			}

		SheL2cpControlRequestResultType ::= INTEGER
			{
			commExecStarted(30),
			paramFaulty(31),
			requestBusy(32),
			setDataFailed(34),
			aswTimeout(35),
			commandFailed(36),
			commandSucceeded(37),
			wrongL2cpIfIndex(40),
			tooManyL2cpInterfaces(41),
			wrongL2cpPortPartitionIndex(50),
			wrongL2cpHostIfIndex(60),
			tooManyL2cpHostInterfaces(61)
			}

	
	
--
-- Node definitions
--
	
		sheL2cpObjects OBJECT IDENTIFIER ::= { sheL2cpMib 1 }

		
		sheL2cpIfTable OBJECT-TYPE
			SYNTAX SEQUENCE OF SheL2cpIfEntry
			MAX-ACCESS not-accessible
			STATUS current
			DESCRIPTION
				"The L2CP interface table."
			::= { sheL2cpObjects 2 }

		
		sheL2cpIfEntry OBJECT-TYPE
			SYNTAX SheL2cpIfEntry
			MAX-ACCESS not-accessible
			STATUS current
			DESCRIPTION
				"An entry of the L2CP interface table (sheL2cpIfTable)"
			INDEX { sheL2cpIfIndex }
			::= { sheL2cpIfTable 1 }

		
		SheL2cpIfEntry ::=
			SEQUENCE { 
				sheL2cpIfIndex
					INTEGER,
				sheL2cpOperState
					SheL2cpOperStateType,
				sheL2cpAdjacencyState
					SheL2cpAdjacencyStateType,
				sheL2cpTimer1
					INTEGER,
				sheL2cpTimer2
					INTEGER,
				sheL2cpTimer3
					INTEGER,
				sheL2cpControllerIpAddress
					OCTET STRING,
				sheL2cpAccessNodeIdentifier
					OCTET STRING,
				sheL2cpPartitionId
					SheL2cpPartitionIdType,
				sheL2cpAlarmSeverityIndex
					SheAlarmSevProfileIndex
			 }

		sheL2cpIfIndex OBJECT-TYPE
			SYNTAX INTEGER (1..8)
			MAX-ACCESS read-only
			STATUS current
			DESCRIPTION
				"The index of an L2CP protocol instance in the sheL2cpIfTable."
			::= { sheL2cpIfEntry 1 }

		
		sheL2cpOperState OBJECT-TYPE
			SYNTAX SheL2cpOperStateType
			MAX-ACCESS read-only
			STATUS current
			DESCRIPTION
				"The operational state of the L2CP interface."
			DEFVAL { 2 }
			::= { sheL2cpIfEntry 2 }

		
		sheL2cpAdjacencyState OBJECT-TYPE
			SYNTAX SheL2cpAdjacencyStateType
			MAX-ACCESS read-only
			STATUS current
			DESCRIPTION
				"The state of the adjacency protocol."
			DEFVAL { 1 }
			::= { sheL2cpIfEntry 3 }

		
		sheL2cpTimer1 OBJECT-TYPE
			SYNTAX INTEGER (1..255)
			UNITS "100ms"
			MAX-ACCESS read-only
			STATUS current
			DESCRIPTION
				"This timer defines the TIMER field is used to inform the receiver of the timer 
				value used in the adjacency protocol of the sender. 
				The timer specifies the nominal time between periodic 
				adjacency protocol messages. 
				It is a constant for the duration of a session."
			DEFVAL { 100 }
			::= { sheL2cpIfEntry 4 }

		
		sheL2cpTimer2 OBJECT-TYPE
			SYNTAX INTEGER (0..10)
			UNITS "second"
			MAX-ACCESS read-only
			STATUS current
			DESCRIPTION
				"This value defines the minimum time between two port state messages of 
				the same port. It is used to limit the port messages in case of
				toggeling ports. 
				The timer base is 1s.
				0 means: all port state changes are reported."
			DEFVAL { 0 }
			::= { sheL2cpIfEntry 5 }

		
		sheL2cpTimer3 OBJECT-TYPE
			SYNTAX INTEGER (0..60)
			UNITS "second"
			MAX-ACCESS read-only
			STATUS current
			DESCRIPTION
				"This timeout is used to handle L2CP message flooding after Controller recovery.
				The timer is started when the link to the controller was established, The first
				port state message is sent when this timer expires."
			DEFVAL { 0 }
			::= { sheL2cpIfEntry 6 }

		
--   
-- 
		sheL2cpControllerIpAddress OBJECT-TYPE
			SYNTAX OCTET STRING (SIZE (4))
			MAX-ACCESS read-only
			STATUS current
			DESCRIPTION
				"The IP address of the remote L2cp controller which should be contacted by this interface."
			::= { sheL2cpIfEntry 7 }

		
		sheL2cpAccessNodeIdentifier OBJECT-TYPE
			SYNTAX OCTET STRING (SIZE (0..64))
			MAX-ACCESS read-only
			STATUS current
			DESCRIPTION
				"The name of the access node. The DSLAM identifies itself with the
				controller by means of this name."
			::= { sheL2cpIfEntry 8 }

		
		sheL2cpPartitionId OBJECT-TYPE
			SYNTAX SheL2cpPartitionIdType
			MAX-ACCESS read-only
			STATUS current
			DESCRIPTION
				"The ID of the partition managed via this L2CP protocol instance.
				(see RFC 3292).
				The value 257 is not used here."
			DEFVAL { 256 }
			::= { sheL2cpIfEntry 10 }

		
		sheL2cpAlarmSeverityIndex OBJECT-TYPE
			SYNTAX SheAlarmSevProfileIndex
			MAX-ACCESS read-only
			STATUS current
			DESCRIPTION
				"The currently used alarm severity profile index for this l2cp interface."
			DEFVAL { 1 }
			::= { sheL2cpIfEntry 11 }

		
		sheL2cpPortPartitionTable OBJECT-TYPE
			SYNTAX SEQUENCE OF SheL2cpPortPartitionEntry
			MAX-ACCESS not-accessible
			STATUS current
			DESCRIPTION
				"The L2CP port table.
				The index in this table is the ifIndex. But only such interfaces are
				listed in this table which are of type xDSL."
			::= { sheL2cpObjects 3 }

		
		sheL2cpPortPartitionEntry OBJECT-TYPE
			SYNTAX SheL2cpPortPartitionEntry
			MAX-ACCESS not-accessible
			STATUS current
			DESCRIPTION
				"An entry in the L2CP port partition table (sheL2cpPortPartitionTable)."
			INDEX { ifIndex }
			::= { sheL2cpPortPartitionTable 1 }

		
		SheL2cpPortPartitionEntry ::=
			SEQUENCE { 
				sheL2cpPortPartitionId
					SheL2cpPartitionIdType
			 }

		sheL2cpPortPartitionId OBJECT-TYPE
			SYNTAX SheL2cpPartitionIdType
			MAX-ACCESS read-only
			STATUS current
			DESCRIPTION
				"The ID of the partition managed the port is assigned to.
				0...255: These are really partition IDs. 
				         The port is managed by such L2CP interface instances which 
				         have the same partition ID.
				    256: no partition. 
				         The port belongs to no partition. It is managed by such L2CP 
				         interface instances wich are assigned to 'no partition'.
				    257: invalid partition 
				         The port is not managed by any L2CP instance."
			DEFVAL { 256 }
			::= { sheL2cpPortPartitionEntry 2 }

		
		sheL2cpControl OBJECT IDENTIFIER ::= { sheL2cpObjects 4 }

		
		sheL2cpControlRequest OBJECT-TYPE
			SYNTAX SheL2cpControlRequestType
			MAX-ACCESS read-write
			STATUS current
			DESCRIPTION
				"The L2CP commands:
				
				createL2cpIf:
				  Create a new L2CP interface instance:
				  Parameter: sheL2cpControlTimer1,
				             sheL2cpControlTimer2,
				             sheL2cpControlTimer3,
				             sheL2cpControlControllerIpAddress,             
				             sheL2cpControlPartitionId,
				             sheL2cpControlAccessNodeIdentifier
				             sheL2cpControlAlarmSeverityIndex
				
				deleteL2cpIf:
				  Delete a L2CP interface instance.
				  Parameter: sheL2cpControlIndex
				
				modifyL2cpIf:
				  Change the parameter of an L2CP interface instance.
				  Parameter: sheL2cpControlL2cpIndex,
				             sheL2cpControlTimer1,
				             sheL2cpControlTimer2,
				             sheL2cpControlTimer3,
				             sheL2cpControlControllerIpAddress,             
				             sheL2cpControlPartitionId,
				             sheL2cpControlAccessNodeIdentifier
				             sheL2cpControlAlarmSeverityIndex
				
				assignPortToPartition:
				  A port is assigned to a partition.
				  Parameter: sheL2cpControlIndex,
				             sheL2cpControlPartitionId
				"
			::= { sheL2cpControl 1 }

		
		sheL2cpControlIndex OBJECT-TYPE
			SYNTAX Unsigned32
			MAX-ACCESS read-write
			STATUS current
			DESCRIPTION
				"The index of a port in the port partition table (vshL2cpPortPartitionTable) if the 
				PartionId should be set or the index of a valid L2cpIf in the sheL2cpIfTable for 
				modify or delete of these interface.
				"
			::= { sheL2cpControl 2 }

		
		sheL2cpControlStatus OBJECT-TYPE
			SYNTAX SheControlStatusType
			MAX-ACCESS read-only
			STATUS current
			DESCRIPTION
				"The status of a user command."
			::= { sheL2cpControl 3 }

		
		sheL2cpControlReqResult OBJECT-TYPE
			SYNTAX SheL2cpControlRequestResultType
			MAX-ACCESS read-only
			STATUS current
			DESCRIPTION
				"The result of the last ControlRequest"
			::= { sheL2cpControl 4 }

		
		sheL2cpControlTimer OBJECT-TYPE
			SYNTAX Integer32
			MAX-ACCESS read-only
			STATUS current
			DESCRIPTION
				"The maximum wait time for the manager for a long running
				user command."
			::= { sheL2cpControl 5 }

		
		sheL2cpControlTimeStamp OBJECT-TYPE
			SYNTAX Integer32
			MAX-ACCESS read-only
			STATUS current
			DESCRIPTION
				"The time stamp of the last command (end of command)."
			::= { sheL2cpControl 6 }

		
		sheL2cpControlTimer1 OBJECT-TYPE
			SYNTAX INTEGER (1..255)
			UNITS "100ms"
			MAX-ACCESS read-write
			STATUS current
			DESCRIPTION
				"This timer defines the timer value used by the adjacency protocol.
				It defines the time between perdiodic adjacency protocol messages.
				The time base are 100ms.
				(see RFC 3292)"
			::= { sheL2cpControl 7 }

		
		sheL2cpControlTimer2 OBJECT-TYPE
			SYNTAX INTEGER (0..10)
			UNITS "second"
			MAX-ACCESS read-write
			STATUS current
			DESCRIPTION
				"This value defines the minimum time between two port state messages of 
				the same port. It is used to limit the port messages in case of
				toggeling ports. 
				The timer base is 1s.
				0 means: all port state changes are reported."
			::= { sheL2cpControl 8 }

		
		sheL2cpControlTimer3 OBJECT-TYPE
			SYNTAX INTEGER (0..60)
			UNITS "second"
			MAX-ACCESS read-write
			STATUS current
			DESCRIPTION
				"This value defines the time before all port states are reported to
				controller after an L2CP connection was established. This timer can
				be used to avoid a message flooding of the controller.
				The timer base is 1s."
			::= { sheL2cpControl 9 }

		
		sheL2cpControlControllerIpAddress OBJECT-TYPE
			SYNTAX OCTET STRING (SIZE (4))
			MAX-ACCESS read-write
			STATUS current
			DESCRIPTION
				"The IP address of the controller."
			::= { sheL2cpControl 10 }

		
		sheL2cpControlAccessNodeIdentifier OBJECT-TYPE
			SYNTAX OCTET STRING (SIZE (0..64))
			MAX-ACCESS read-write
			STATUS current
			DESCRIPTION
				"The name of the access node. The DSLAM identifies itself with the
				controller by means of this name."
			::= { sheL2cpControl 11 }

		
		sheL2cpControlPartitionId OBJECT-TYPE
			SYNTAX SheL2cpPartitionIdType
			MAX-ACCESS read-write
			STATUS current
			DESCRIPTION
				"The ID of the partition managed by an L2CP protocol instance (see RFC 3292).
				The partition to which a port is assigned.
				"
			::= { sheL2cpControl 12 }

		
		sheL2cpControlAlarmSeverityIndex OBJECT-TYPE
			SYNTAX SheAlarmSevProfileIndex
			MAX-ACCESS read-write
			STATUS current
			DESCRIPTION
				"look at table."
			::= { sheL2cpControl 13 }

		
		sheL2cpNotification OBJECT IDENTIFIER ::= { sheL2cpObjects 5 }

		
		sheL2cpAlarmEvents OBJECT IDENTIFIER ::= { sheL2cpNotification 1 }

		
		sheL2cpLinkDown NOTIFICATION-TYPE
			OBJECTS { sheAlarmTimeAndDate, sheAlarmReportingSource, sheAlarmReportingSourceType, sheAlarmSeverity }
			STATUS current
			DESCRIPTION 
				"Description."
			::= { sheL2cpAlarmEvents 1 }

		
		sheL2cpConfigEvents OBJECT IDENTIFIER ::= { sheL2cpNotification 2 }

		
		sheL2cpIfCreated NOTIFICATION-TYPE
			OBJECTS { sheL2cpControlTimeStamp, sheL2cpOperState, sheL2cpTimer1, sheL2cpTimer2, sheL2cpTimer3, 
				sheL2cpControllerIpAddress, sheL2cpAccessNodeIdentifier, sheL2cpAdjacencyState, sheL2cpPartitionId, sheL2cpAlarmSeverityIndex
				 }
			STATUS current
			DESCRIPTION 
				"Configuration trap."
			::= { sheL2cpConfigEvents 1 }

		
		sheL2cpIfDeleted NOTIFICATION-TYPE
			OBJECTS { sheL2cpControlTimeStamp, sheL2cpControlIndex }
			STATUS current
			DESCRIPTION 
				"Configuration trap."
			::= { sheL2cpConfigEvents 2 }

		
		sheL2cpIfModified NOTIFICATION-TYPE
			OBJECTS { sheL2cpControlTimeStamp, sheL2cpOperState, sheL2cpTimer1, sheL2cpTimer2, sheL2cpTimer3, 
				sheL2cpControllerIpAddress, sheL2cpAccessNodeIdentifier, sheL2cpAdjacencyState, sheL2cpPartitionId, sheL2cpAlarmSeverityIndex
				 }
			STATUS current
			DESCRIPTION 
				"Configuration trap."
			::= { sheL2cpConfigEvents 3 }

		
		sheL2cpPartitionPortDataChanged NOTIFICATION-TYPE
			OBJECTS { sheL2cpControlTimeStamp, sheL2cpPortPartitionId }
			STATUS current
			DESCRIPTION 
				"Configuration trap."
			::= { sheL2cpConfigEvents 4 }

		
		sheL2cpHostIfCreated NOTIFICATION-TYPE
			OBJECTS { sheL2cpHostIfControlIndex, sheL2cpHostIfControlStatus, sheL2cpHostIfControlReqResult, sheL2cpHostIfControlTimeStamp, sheL2cpHostIfControlVlanId, 
				sheL2cpHostIfControlIpAddress, sheL2cpHostIfControlNetmask }
			STATUS obsolete
			DESCRIPTION 
				"Note: This parameter is not longer valid starting with release SHE R2.6 
				The IP interface configuration was moved to sheSystemIpHostTable."
			::= { sheL2cpConfigEvents 5 }

		
		sheL2cpHostIfModified NOTIFICATION-TYPE
			OBJECTS { sheL2cpHostIfControlIndex, sheL2cpHostIfControlStatus, sheL2cpHostIfControlReqResult, sheL2cpHostIfControlTimeStamp, sheL2cpHostIfControlVlanId, 
				sheL2cpHostIfControlIpAddress, sheL2cpHostIfControlNetmask }
			STATUS obsolete
			DESCRIPTION 
				"Note: This parameter is not longer valid starting with release SHE R2.6. 
				The IP interface configuration was moved to sheSystemIpHostTable."
			::= { sheL2cpConfigEvents 6 }

		
		sheL2cpHostIfDeleted NOTIFICATION-TYPE
			OBJECTS { sheL2cpHostIfControlIndex, sheL2cpHostIfControlStatus, sheL2cpHostIfControlReqResult, sheL2cpHostIfControlTimeStamp }
			STATUS obsolete
			DESCRIPTION 
				"Note: This parameter is not longer valid starting with release SHE R2.6 
				The IP interface configuration was moved to sheSystemIpHostTable."
			::= { sheL2cpConfigEvents 7 }

		
		sheL2cpHostIfTable OBJECT-TYPE
			SYNTAX SEQUENCE OF SheL2cpHostIfEntry
			MAX-ACCESS not-accessible
			STATUS obsolete
			DESCRIPTION
				"Note: This parameter is not longer valid starting with release SHE R2.6. 
				The IP interface configuration was moved to sheSystemIpHostTable."
			::= { sheL2cpObjects 6 }

		
		sheL2cpHostIfEntry OBJECT-TYPE
			SYNTAX SheL2cpHostIfEntry
			MAX-ACCESS not-accessible
			STATUS obsolete
			DESCRIPTION
				"The index of an L2CP host interface instance in this table.
				
				Note: This parameter is not longer valid starting with release SHE R2.6. 
				The IP interface configuration was moved to sheSystemIpHostTable."
			INDEX { sheL2cpHostIfIndex }
			::= { sheL2cpHostIfTable 1 }

		
		SheL2cpHostIfEntry ::=
			SEQUENCE { 
				sheL2cpHostIfIndex
					INTEGER,
				sheL2cpHostIfVlanId
					Unsigned32,
				sheL2cpHostIfIpAddress
					OCTET STRING,
				sheL2cpHostIfNetmask
					OCTET STRING
			 }

		sheL2cpHostIfIndex OBJECT-TYPE
			SYNTAX INTEGER (1..8)
			MAX-ACCESS read-only
			STATUS obsolete
			DESCRIPTION
				"Unique key for that table."
			::= { sheL2cpHostIfEntry 1 }

		
		sheL2cpHostIfVlanId OBJECT-TYPE
			SYNTAX Unsigned32 (1..4093)
			MAX-ACCESS read-only
			STATUS obsolete
			DESCRIPTION
				"The host vlan for the local L2cp interface which should be used as tag to 
				contact the remote L2cp controller."
			::= { sheL2cpHostIfEntry 2 }

		
		sheL2cpHostIfIpAddress OBJECT-TYPE
			SYNTAX OCTET STRING (SIZE (4))
			MAX-ACCESS read-only
			STATUS obsolete
			DESCRIPTION
				"The IP address of the local L2cp interface which should be used by the NE."
			::= { sheL2cpHostIfEntry 3 }

		
		sheL2cpHostIfNetmask OBJECT-TYPE
			SYNTAX OCTET STRING (SIZE (4))
			MAX-ACCESS read-only
			STATUS obsolete
			DESCRIPTION
				"The l2cp host interface Netmask."
			::= { sheL2cpHostIfEntry 5 }

		
-- Note: This parameter is not longer valid starting with release SHE R2.6. 
-- The IP interface configuration was moved to sheSystemIpHostTable.
		sheL2cpHostIfControl OBJECT IDENTIFIER ::= { sheL2cpObjects 7 }

		
		sheL2cpHostIfControlRequest OBJECT-TYPE
			SYNTAX SheL2cpControlRequestType
			MAX-ACCESS read-write
			STATUS obsolete
			DESCRIPTION
				"The L2CP commands:
				
				Note: This parameter is not longer valid starting with release SHE R2.6. 
				The IP interface configuration was moved to sheSystemIpHostTable.
				
				createL2cpHostIf:
				  Create a new L2CP host interface instance:
				  Parameter: 
				       sheL2cpHostIfControlVlanId
				       sheL2cpHostIfControlIpAddress
				       sheL2cpHostIfControlNetmask
				       
				deleteL2cpHostIf:
				  Delete a L2CP host interface instance.
				  Parameter:
				        sheL2cpHostIfControlIndex
				
				modifyL2cpHostIf:
				  Change the parameter of an L2CP host interface instance.
				  Parameter:
				       sheL2cpHostIfControlIndex
				       sheL2cpHostIfControlIpAddress
				       sheL2cpHostIfControlNetmask
				
				"
			::= { sheL2cpHostIfControl 1 }

		
		sheL2cpHostIfControlIndex OBJECT-TYPE
			SYNTAX Unsigned32 (1..8)
			MAX-ACCESS read-write
			STATUS obsolete
			DESCRIPTION
				"The index of a valid L2cpHostIf from sheL2cpHostIfTable for modifies or delete. "
			::= { sheL2cpHostIfControl 2 }

		
		sheL2cpHostIfControlStatus OBJECT-TYPE
			SYNTAX SheControlStatusType
			MAX-ACCESS read-only
			STATUS obsolete
			DESCRIPTION
				"The status of a user command."
			::= { sheL2cpHostIfControl 3 }

		
		sheL2cpHostIfControlReqResult OBJECT-TYPE
			SYNTAX SheL2cpControlRequestResultType
			MAX-ACCESS read-only
			STATUS obsolete
			DESCRIPTION
				"The result of the last ControlRequest"
			::= { sheL2cpHostIfControl 4 }

		
		sheL2cpHostIfControlTimer OBJECT-TYPE
			SYNTAX Integer32
			MAX-ACCESS read-only
			STATUS obsolete
			DESCRIPTION
				"The maximum wait time for the manager for a long running
				user command."
			::= { sheL2cpHostIfControl 5 }

		
		sheL2cpHostIfControlTimeStamp OBJECT-TYPE
			SYNTAX Integer32
			MAX-ACCESS read-only
			STATUS obsolete
			DESCRIPTION
				"The time stamp of the last command (end of command)."
			::= { sheL2cpHostIfControl 6 }

		
		sheL2cpHostIfControlVlanId OBJECT-TYPE
			SYNTAX Unsigned32 (1..4093)
			MAX-ACCESS read-write
			STATUS obsolete
			DESCRIPTION
				"The host vlan for the local L2cp interface which should be used as tag to 
				contact the remote L2cp controller.
				This value could only be used for create command. A modification is not allowed!"
			::= { sheL2cpHostIfControl 7 }

		
		sheL2cpHostIfControlIpAddress OBJECT-TYPE
			SYNTAX OCTET STRING (SIZE (4))
			MAX-ACCESS read-write
			STATUS obsolete
			DESCRIPTION
				"The IP address of the local L2cp host interface."
			::= { sheL2cpHostIfControl 8 }

		
		sheL2cpHostIfControlNetmask OBJECT-TYPE
			SYNTAX OCTET STRING (SIZE (4))
			MAX-ACCESS read-write
			STATUS obsolete
			DESCRIPTION
				"The l2cp host interface Netmask."
			::= { sheL2cpHostIfControl 10 }

		
--     conformance information
-- 
		sheL2cpConformance OBJECT IDENTIFIER ::= { sheL2cpObjects 8 }

		
		sheL2cpGroups OBJECT IDENTIFIER ::= { sheL2cpConformance 1 }

		
--     units of conformance
-- 
		sheL2cpGroup OBJECT-GROUP
			OBJECTS { sheL2cpIfIndex, sheL2cpOperState, sheL2cpTimer1, sheL2cpTimer2, sheL2cpTimer3, 
				sheL2cpControllerIpAddress, sheL2cpAccessNodeIdentifier, sheL2cpAlarmSeverityIndex, sheL2cpPortPartitionId, sheL2cpAdjacencyState, 
				sheL2cpPartitionId }
			STATUS current
			DESCRIPTION 
				"A collection of objects providing information about
				a VDSL Line."
			::= { sheL2cpGroups 1 }

		
		sheL2cpControlGroup OBJECT-GROUP
			OBJECTS { sheL2cpControlRequest, sheL2cpControlStatus, sheL2cpControlIndex, sheL2cpControlReqResult, sheL2cpControlTimer, 
				sheL2cpControlTimeStamp, sheL2cpControlControllerIpAddress, sheL2cpControlTimer1, sheL2cpControlTimer2, sheL2cpControlTimer3, 
				sheL2cpControlAlarmSeverityIndex, sheL2cpControlPartitionId, sheL2cpControlAccessNodeIdentifier }
			STATUS current
			DESCRIPTION 
				"Description."
			::= { sheL2cpGroups 2 }

		
		sheL2cpNotificationGroup NOTIFICATION-GROUP
			NOTIFICATIONS { sheL2cpLinkDown, sheL2cpIfModified, sheL2cpPartitionPortDataChanged, sheL2cpIfCreated, sheL2cpIfDeleted
				 }
			STATUS current
			DESCRIPTION 
				"This group supports notifications of significant 
				conditions associated with VDSL Lines."
			::= { sheL2cpGroups 3 }

		
		sheL2cpObsoleteGroup OBJECT-GROUP
			OBJECTS { sheL2cpHostIfIndex, sheL2cpHostIfVlanId, sheL2cpHostIfIpAddress, sheL2cpHostIfNetmask, sheL2cpHostIfControlRequest, 
				sheL2cpHostIfControlIndex, sheL2cpHostIfControlStatus, sheL2cpHostIfControlReqResult, sheL2cpHostIfControlTimer, sheL2cpHostIfControlTimeStamp, 
				sheL2cpHostIfControlVlanId, sheL2cpHostIfControlIpAddress, sheL2cpHostIfControlNetmask }
			STATUS obsolete
			DESCRIPTION 
				"Description."
			::= { sheL2cpGroups 4 }

		
		sheL2cpObsoleteNotificationGroup NOTIFICATION-GROUP
			NOTIFICATIONS { sheL2cpHostIfCreated, sheL2cpHostIfModified, sheL2cpHostIfDeleted }
			STATUS obsolete
			DESCRIPTION 
				"Description."
			::= { sheL2cpGroups 5 }

		
		sheL2cpCompliances OBJECT IDENTIFIER ::= { sheL2cpConformance 2 }

		
--   this module
-- this module
-- this module
		sheL2cpMibCompliance MODULE-COMPLIANCE
			STATUS current
			DESCRIPTION 
				"The compliance statement for SNMP entities which 
				manage VDSL interfaces in SHE."
			MODULE -- this module
				MANDATORY-GROUPS { sheL2cpGroup, sheL2cpControlGroup, sheL2cpNotificationGroup }
			::= { sheL2cpCompliances 1 }

		
	
	END

--
-- she-l2cp-mib.mib
--
