--  Title:    NGD_G42.MIB
--  Version:  v4.2
--
--  Copyright @ 1997-2004 DPS Inc. All Rights Reserved
--
--  This MIB defines supplemental objects for the DPS NetGuardian series.
--
--
-- JJV [3/7/11] - NG216F alternative format traps reuse existing variable bindings for different purposes

DPS-MIB-NGD-V10 DEFINITIONS ::= BEGIN

IMPORTS
	dpsRTU,
	dpsRTUDateTime,
	dpsRTUAPort,
	dpsRTUCAddress,
	dpsRTUADisplay,
	dpsRTUAPoint,
	dpsRTUAPntDesc,
	dpsRTUAState
		FROM DPS-MIB-V38
	sysDescr,
	sysLocation
		FROM RFC1213-MIB
	TRAP-TYPE
		FROM RFC-1215;

dpsRTUp8001Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 1 is set."
	::=  8001

dpsRTUp9001Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 1 clears."
	::=  9001

dpsRTUp8002Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 2 is set."
	::=  8002

dpsRTUp9002Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 2 clears."
	::=  9002

dpsRTUp8003Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 3 is set."
	::=  8003

dpsRTUp9003Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 3 clears."
	::=  9003

dpsRTUp8004Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 4 is set."
	::=  8004

dpsRTUp9004Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 4 clears."
	::=  9004

dpsRTUp8005Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 5 is set."
	::=  8005

dpsRTUp9005Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 5 clears."
	::=  9005

dpsRTUp8006Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 6 is set."
	::=  8006

dpsRTUp9006Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 6 clears."
	::=  9006

dpsRTUp8007Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 7 is set."
	::=  8007

dpsRTUp9007Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 7 clears."
	::=  9007

dpsRTUp8008Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 8 is set."
	::=  8008

dpsRTUp9008Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 8 clears."
	::=  9008

dpsRTUp8009Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 9 is set."
	::=  8009

dpsRTUp9009Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 9 clears."
	::=  9009

dpsRTUp8010Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 10 is set."
	::=  8010

dpsRTUp9010Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 10 clears."
	::=  9010

dpsRTUp8011Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 11 is set."
	::=  8011

dpsRTUp9011Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 11 clears."
	::=  9011

dpsRTUp8012Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 12 is set."
	::=  8012

dpsRTUp9012Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 12 clears."
	::=  9012

dpsRTUp8013Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 13 is set."
	::=  8013

dpsRTUp9013Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 13 clears."
	::=  9013

dpsRTUp8014Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 14 is set."
	::=  8014

dpsRTUp9014Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 14 clears."
	::=  9014

dpsRTUp8015Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 15 is set."
	::=  8015

dpsRTUp9015Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 15 clears."
	::=  9015

dpsRTUp8016Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 16 is set."
	::=  8016

dpsRTUp9016Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 16 clears."
	::=  9016

dpsRTUp8017Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 17 is set."
	::=  8017

dpsRTUp9017Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 17 clears."
	::=  9017

dpsRTUp8018Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 18 is set."
	::=  8018

dpsRTUp9018Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 18 clears."
	::=  9018

dpsRTUp8019Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 19 is set."
	::=  8019

dpsRTUp9019Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 19 clears."
	::=  9019

dpsRTUp8020Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 20 is set."
	::=  8020

dpsRTUp9020Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 20 clears."
	::=  9020

dpsRTUp8021Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 21 is set."
	::=  8021

dpsRTUp9021Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 21 clears."
	::=  9021

dpsRTUp8022Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 22 is set."
	::=  8022

dpsRTUp9022Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 22 clears."
	::=  9022

dpsRTUp8023Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 23 is set."
	::=  8023

dpsRTUp9023Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 23 clears."
	::=  9023

dpsRTUp8024Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 24 is set."
	::=  8024

dpsRTUp9024Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 24 clears."
	::=  9024

dpsRTUp8025Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 25 is set."
	::=  8025

dpsRTUp9025Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 25 clears."
	::=  9025

dpsRTUp8026Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 26 is set."
	::=  8026

dpsRTUp9026Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 26 clears."
	::=  9026

dpsRTUp8027Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 27 is set."
	::=  8027

dpsRTUp9027Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 27 clears."
	::=  9027

dpsRTUp8028Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 28 is set."
	::=  8028

dpsRTUp9028Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 28 clears."
	::=  9028

dpsRTUp8029Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 29 is set."
	::=  8029

dpsRTUp9029Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 29 clears."
	::=  9029

dpsRTUp8030Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 30 is set."
	::=  8030

dpsRTUp9030Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 30 clears."
	::=  9030

dpsRTUp8031Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 31 is set."
	::=  8031

dpsRTUp9031Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 31 clears."
	::=  9031

dpsRTUp8032Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 32 is set."
	::=  8032

dpsRTUp9032Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 32 clears."
	::=  9032
dpsRTUp8033Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 33 is set."
	::=  8033

dpsRTUp9033Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 33 clears."
	::=  9033
dpsRTUp8034Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 34 is set."
	::=  8034

dpsRTUp9034Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 34 clears."
	::=  9034
dpsRTUp8035Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 35 is set."
	::=  8035

dpsRTUp9035Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 35 clears."
	::=  9035
dpsRTUp8036Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 36 is set."
	::=  8036

dpsRTUp9036Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 36 clears."
	::=  9036

dpsRTUp8037Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 37 is set."
	::=  8037

dpsRTUp9037Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 37 clears."
	::=  9037

dpsRTUp8038Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 38 is set."
	::=  8038

dpsRTUp9038Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 38 clears."
	::=  9038

dpsRTUp8039Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 39 is set."
	::=  8039

dpsRTUp9039Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 39 clears."
	::=  9039

dpsRTUp8040Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 40 is set."
	::=  8040

dpsRTUp9040Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 40 clears."
	::=  9040
dpsRTUp8041Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 41 is set."
	::=  8041

dpsRTUp9041Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 41 clears."
	::=  9041

dpsRTUp8042Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 42 is set."
	::=  8042

dpsRTUp9042Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 42 clears."
	::=  9042

dpsRTUp8043Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 43 is set."
	::=  8043

dpsRTUp9043Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 43 clears."
	::=  9043

dpsRTUp8044Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 44 is set."
	::=  8044

dpsRTUp9044Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 44 clears."
	::=  9044

dpsRTUp8045Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 45 is set."
	::=  8045

dpsRTUp9045Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 45 clears."
	::=  9045

dpsRTUp8046Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 46 is set."
	::=  8046

dpsRTUp9046Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 46 clears."
	::=  9046

dpsRTUp8047Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 47 is set."
	::=  8047

dpsRTUp9047Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 47 clears."
	::=  9047

dpsRTUp8048Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 48 is set."
	::=  8048

dpsRTUp9048Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 48 clears."
	::=  9048

dpsRTUp8049Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 49 is set."
	::=  8049

dpsRTUp9049Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 49 clears."
	::=  9049

dpsRTUp8050Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 50 is set."
	::=  8050

dpsRTUp9050Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 50 clears."
	::=  9050


dpsRTUp8051Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 51 is set."
	::=  8051

dpsRTUp9051Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 51 clears."
	::=  9051

dpsRTUp8052Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 52 is set."
	::=  8052

dpsRTUp9052Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 52 clears."
	::=  9052

dpsRTUp8053Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 53 is set."
	::=  8053

dpsRTUp9053Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 53 clears."
	::=  9053

dpsRTUp8054Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 54 is set."
	::=  8054

dpsRTUp9054Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 54 clears."
	::=  9054

dpsRTUp8055Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 55 is set."
	::=  8055

dpsRTUp9055Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 55 clears."
	::=  9055

dpsRTUp8056Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 56 is set."
	::=  8056

dpsRTUp9056Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 56 clears."
	::=  9056

dpsRTUp8057Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 57 is set."
	::=  8057

dpsRTUp9057Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 57 clears."
	::=  9057

dpsRTUp8058Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 58 is set."
	::=  8058

dpsRTUp9058Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 58 clears."
	::=  9058

dpsRTUp8059Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 59 is set."
	::=  8059

dpsRTUp9059Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 59 clears."
	::=  9059

dpsRTUp8060Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 60 is set."
	::=  8060

dpsRTUp9060Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 60 clears."
	::=  9060
dpsRTUp8061Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 61 is set."
	::=  8061

dpsRTUp9061Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 61 clears."
	::=  9061

dpsRTUp8062Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 62 is set."
	::=  8062

dpsRTUp9062Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 62 clears."
	::=  9062

dpsRTUp8063Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 63 is set."
	::=  8063

dpsRTUp9063Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 63 clears."
	::=  9063

dpsRTUp8064Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 64 is set."
	::=  8064

dpsRTUp9064Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 64 clears."
	::=  9064


dpsRTUp8065Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 1 fails."
	::=  8065

dpsRTUp9065Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 1 reappears."
	::=  9065

dpsRTUp8066Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 2 fails."
	::=  8066

dpsRTUp9066Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 2 reappears."
	::=  9066

dpsRTUp8067Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 3 fails."
	::=  8067

dpsRTUp9067Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 3 reappears."
	::=  9067

dpsRTUp8068Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 4 fails."
	::=  8068

dpsRTUp9068Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 4 reappears."
	::=  9068

dpsRTUp8069Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 5 fails."
	::=  8069

dpsRTUp9069Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 5 reappears."
	::=  9069

dpsRTUp8070Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 6 fails."
	::=  8070

dpsRTUp9070Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 6 reappears."
	::=  9070

dpsRTUp8071Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 7 fails."
	::=  8071

dpsRTUp9071Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 7 reappears."
	::=  9071

dpsRTUp8072Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 8 fails."
	::=  8072

dpsRTUp9072Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 8 reappears."
	::=  9072

dpsRTUp8073Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 9 fails."
	::=  8073

dpsRTUp9073Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 9 reappears."
	::=  9073

dpsRTUp8074Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 10 fails."
	::=  8074

dpsRTUp9074Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 10 reappears."
	::=  9074

dpsRTUp8075Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 11 fails."
	::=  8075

dpsRTUp9075Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 11 reappears."
	::=  9075

dpsRTUp8076Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 12 fails."
	::=  8076

dpsRTUp9076Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 12 reappears."
	::=  9076

dpsRTUp8077Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 13 fails."
	::=  8077

dpsRTUp9077Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 13 reappears."
	::=  9077

dpsRTUp8078Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 14 fails."
	::=  8078

dpsRTUp9078Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 14 reappears."
	::=  9078

dpsRTUp8079Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 15 fails."
	::=  8079

dpsRTUp9079Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 15 reappears."
	::=  9079

dpsRTUp8080Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 16 fails."
	::=  8080

dpsRTUp9080Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 16 reappears."
	::=  9080

dpsRTUp8081Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 17 fails."
	::=  8081

dpsRTUp9081Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 17 reappears."
	::=  9081

dpsRTUp8082Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 18 fails."
	::=  8082

dpsRTUp9082Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 18 reappears."
	::=  9082

dpsRTUp8083Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 19 fails."
	::=  8083

dpsRTUp9083Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 19 reappears."
	::=  9083

dpsRTUp8084Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 20 fails."
	::=  8084

dpsRTUp9084Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 20 reappears."
	::=  9084

dpsRTUp8085Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 21 fails."
	::=  8085

dpsRTUp9085Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 21 reappears."
	::=  9085

dpsRTUp8086Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 22 fails."
	::=  8086

dpsRTUp9086Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 22 reappears."
	::=  9086

dpsRTUp8087Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 23 fails."
	::=  8087

dpsRTUp9087Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 23 reappears."
	::=  9087

dpsRTUp8088Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 24 fails."
	::=  8088

dpsRTUp9088Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 24 reappears."
	::=  9088

dpsRTUp8089Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 25 fails."
	::=  8089

dpsRTUp9089Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 25 reappears."
	::=  9089

dpsRTUp8090Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 26 fails."
	::=  8090

dpsRTUp9090Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 26 reappears."
	::=  9090

dpsRTUp8091Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 27 fails."
	::=  8091

dpsRTUp9091Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 27 reappears."
	::=  9091

dpsRTUp8092Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 28 fails."
	::=  8092

dpsRTUp9092Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 28 reappears."
	::=  9092

dpsRTUp8093Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 29 fails."
	::=  8093

dpsRTUp9093Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 29 reappears."
	::=  9093

dpsRTUp8094Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 30 fails."
	::=  8094

dpsRTUp9094Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 30 reappears."
	::=  9094

dpsRTUp8095Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 31 fails."
	::=  8095

dpsRTUp9095Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 31 reappears."
	::=  9095

dpsRTUp8096Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 32 fails."
	::=  8096

dpsRTUp9096Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when ping target 32 reappears."
	::=  9096
dpsRTUp8097Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 97 is set."
	::=  8097

dpsRTUp9097Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 97 clears."
	::=  9097

dpsRTUp8098Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 98 is set."
	::=  8098

dpsRTUp9098Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 98 clears."
	::=  9098

dpsRTUp8099Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 99 is set."
	::=  8099

dpsRTUp9099Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 99 clears."
	::=  9099

dpsRTUp8100Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 64 is set."
	::=  8100

dpsRTUp9100Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 64 clears."
	::=  9100

dpsRTUp8101Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 101 is set."
	::=  8101

dpsRTUp9101Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 101 clears."
	::=  9101

dpsRTUp8102Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 102 is set."
	::=  8102

dpsRTUp9102Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 102 clears."
	::=  9102

dpsRTUp8103Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 103 is set."
	::=  8103

dpsRTUp9103Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 103 clears."
	::=  9103

dpsRTUp8104Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 104 is set."
	::=  8104

dpsRTUp9104Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 104 clears."
	::=  9104

dpsRTUp8105Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 105 is set."
	::=  8105

dpsRTUp9105Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 105 clears."
	::=  9105

dpsRTUp8106Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 106 is set."
	::=  8106

dpsRTUp9106Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 106 clears."
	::=  9106

dpsRTUp8107Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 107 is set."
	::=  8107

dpsRTUp9107Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 107 clears."
	::=  9107

dpsRTUp8108Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 108 is set."
	::=  8108

dpsRTUp9108Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 108 clears."
	::=  9108

dpsRTUp8109Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 109 is set."
	::=  8109

dpsRTUp9109Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 109 clears."
	::=  9109

dpsRTUp8110Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 110 is set."
	::=  8110

dpsRTUp9110Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 110 clears."
	::=  9110


dpsRTUp8111Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 111 is set."
	::=  8111

dpsRTUp9111Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 111 clears."
	::=  9111

dpsRTUp8112Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 112 is set."
	::=  8112

dpsRTUp9112Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 112 clears."
	::=  9112

dpsRTUp8113Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 113 is set."
	::=  8113

dpsRTUp9113Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 113 clears."
	::=  9113

dpsRTUp8114Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 114 is set."
	::=  8114

dpsRTUp9114Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 114 clears."
	::=  9114

dpsRTUp8115Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 115 is set."
	::=  8115

dpsRTUp9115Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 115 clears."
	::=  9115

dpsRTUp8116Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 116 is set."
	::=  8116

dpsRTUp9116Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 116 clears."
	::=  9116

dpsRTUp8117Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 117 is set."
	::=  8117

dpsRTUp9117Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 117 clears."
	::=  9117

dpsRTUp8118Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 118 is set."
	::=  8118

dpsRTUp9118Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 118 clears."
	::=  9118

dpsRTUp8119Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 119 is set."
	::=  8119

dpsRTUp9119Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 119 clears."
	::=  9119

dpsRTUp8120Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 120 is set."
	::=  8120

dpsRTUp9120Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 120 clears."
	::=  9120
dpsRTUp8121Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 121 is set."
	::=  8121

dpsRTUp9121Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 121 clears."
	::=  9121

dpsRTUp8122Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 122 is set."
	::=  8122

dpsRTUp9122Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 122 clears."
	::=  9122

dpsRTUp8123Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 123 is set."
	::=  8123

dpsRTUp9123Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 123 clears."
	::=  9123

dpsRTUp8124Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 124 is set."
	::=  8124

dpsRTUp9124Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 124 clears."
	::=  9124

dpsRTUp8125Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 125 is set."
	::=  8125

dpsRTUp9125Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 125 clears."
	::=  9125

dpsRTUp8126Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 126 is set."
	::=  8126

dpsRTUp9126Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 126 clears."
	::=  9126

dpsRTUp8127Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 127 is set."
	::=  8127

dpsRTUp9127Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 127 clears."
	::=  9127

dpsRTUp8128Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 128 is set."
	::=  8128

dpsRTUp9128Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 128 clears."
	::=  9128

dpsRTUp8129Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 1 minor under threshold is violated"
	::=  8129

dpsRTUp9129Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 1 minor under threshold is restored"
	::=  9129

dpsRTUp8130Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 1 minor over threshold is violated"
	::=  8130

dpsRTUp9130Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 1 minor over threshold is restored"
	::=  9130

dpsRTUp8131Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 1 major under threshold is violated"
	::=  8131

dpsRTUp9131Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 1 major under threshold is restored"
	::=  9131

dpsRTUp8132Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 1 major over threshold is violated"
	::=  8132

dpsRTUp9132Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 1 major over threshold is restored"
	::=  9132

dpsRTUp8133Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 1 threshold is violated"
	::=  8133

dpsRTUp9133Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 1 threshold is cleared"
	::=  9133
	   
dpsRTUp8134Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 134 is set."
	::=  8134

dpsRTUp9134Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 134 clears."
	::=  9134
	   
dpsRTUp8135Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 135 is set."
	::=  8135

dpsRTUp9135Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 135 clears."
	::=  9135
	   
dpsRTUp8136Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 136 is set."
	::=  8136

dpsRTUp9136Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 136 clears."
	::=  9136
	   
dpsRTUp8137Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 137 is set."
	::=  8137

dpsRTUp9137Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 137 clears."
	::=  9137
	   
dpsRTUp8138Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 138 is set."
	::=  8138

dpsRTUp9138Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 138 clears."
	::=  9138
	   
dpsRTUp8139Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 139 is set."
	::=  8139

dpsRTUp9139Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 139 clears."
	::=  9139
	   
dpsRTUp8140Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 140 is set."
	::=  8140

dpsRTUp9140Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 140 clears."
	::=  9140
	   
dpsRTUp8141Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 141 is set."
	::=  8141

dpsRTUp9141Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 141 clears."
	::=  9141
	   
dpsRTUp8142Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 142 is set."
	::=  8142

dpsRTUp9142Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 142 clears."
	::=  9142
	   
dpsRTUp8143Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 143 is set."
	::=  8143

dpsRTUp9143Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 143 clears."
	::=  9143
	   
dpsRTUp8144Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 144 is set."
	::=  8144

dpsRTUp9144Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 144 clears."
	::=  9144
	   
dpsRTUp8145Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 145 is set."
	::=  8145

dpsRTUp9145Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 145 clears."
	::=  9145
	   
dpsRTUp8146Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 146 is set."
	::=  8146

dpsRTUp9146Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 146 clears."
	::=  9146
	   
dpsRTUp8147Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 147 is set."
	::=  8147

dpsRTUp9147Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 147 clears."
	::=  9147
	   
dpsRTUp8148Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 148 is set."
	::=  8148

dpsRTUp9148Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 148 clears."
	::=  9148
	   
dpsRTUp8149Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 149 is set."
	::=  8149

dpsRTUp9149Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 149 clears."
	::=  9149
	   
dpsRTUp8150Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 150 is set."
	::=  8150

dpsRTUp9150Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 150 clears."
	::=  9150
	   
dpsRTUp8151Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 151 is set."
	::=  8151

dpsRTUp9151Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 151 clears."
	::=  9151
	   
dpsRTUp8152Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 152 is set."
	::=  8152

dpsRTUp9152Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 152 clears."
	::=  9152
	   
dpsRTUp8153Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 153 is set."
	::=  8153

dpsRTUp9153Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 153 clears."
	::=  9153
	   
dpsRTUp8154Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 154 is set."
	::=  8154

dpsRTUp9154Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 154 clears."
	::=  9154
	   
dpsRTUp8155Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 155 is set."
	::=  8155

dpsRTUp9155Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 155 clears."
	::=  9155
	   
dpsRTUp8156Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 156 is set."
	::=  8156

dpsRTUp9156Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 156 clears."
	::=  9156
	   
dpsRTUp8157Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 157 is set."
	::=  8157

dpsRTUp9157Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 157 clears."
	::=  9157
	   
dpsRTUp8158Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 158 is set."
	::=  8158

dpsRTUp9158Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 158 clears."
	::=  9158
	   
dpsRTUp8159Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 159 is set."
	::=  8159

dpsRTUp9159Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 159 clears."
	::=  9159
	   
dpsRTUp8160Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 160 is set."
	::=  8160

dpsRTUp9160Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 160 clears."
	::=  9160
	   
dpsRTUp8161Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 161 is set."
	::=  8161

dpsRTUp9161Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 161 clears."
	::=  9161
	   
dpsRTUp8162Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 162 is set."
	::=  8162

dpsRTUp9162Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 162 clears."
	::=  9162
	   
dpsRTUp8163Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 163 is set."
	::=  8163

dpsRTUp9163Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 163 clears."
	::=  9163
	   
dpsRTUp8164Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 164 is set."
	::=  8164

dpsRTUp9164Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 164 clears."
	::=  9164
	   
dpsRTUp8165Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 165 is set."
	::=  8165

dpsRTUp9165Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 165 clears."
	::=  9165
	   
dpsRTUp8166Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 166 is set."
	::=  8166

dpsRTUp9166Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 166 clears."
	::=  9166
	   
dpsRTUp8167Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 167 is set."
	::=  8167

dpsRTUp9167Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 167 clears."
	::=  9167
	   
dpsRTUp8168Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 168 is set."
	::=  8168

dpsRTUp9168Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 168 clears."
	::=  9168
	   
dpsRTUp8169Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 169 is set."
	::=  8169

dpsRTUp9169Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 169 clears."
	::=  9169
	   
dpsRTUp8170Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 170 is set."
	::=  8170

dpsRTUp9170Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 170 clears."
	::=  9170
	   
dpsRTUp8171Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 171 is set."
	::=  8171

dpsRTUp9171Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 171 clears."
	::=  9171
	   
dpsRTUp8172Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 172 is set."
	::=  8172

dpsRTUp9172Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 172 clears."
	::=  9172
	   
dpsRTUp8173Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 173 is set."
	::=  8173

dpsRTUp9173Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 173 clears."
	::=  9173
	   
dpsRTUp8174Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 174 is set."
	::=  8174

dpsRTUp9174Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 174 clears."
	::=  9174
	   
dpsRTUp8175Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 175 is set."
	::=  8175

dpsRTUp9175Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 175 clears."
	::=  9175
	   
dpsRTUp8176Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 176 is set."
	::=  8176

dpsRTUp9176Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 176 clears."
	::=  9176

dpsRTUp8193Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 2 minor under threshold is violated"
	::=  8193

dpsRTUp9193Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 2 minor under threshold is restored"
	::=  9193

dpsRTUp8194Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 2 minor over threshold is violated"
	::=  8194

dpsRTUp9194Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 2 minor over threshold is restored"
	::=  9194

dpsRTUp8195Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 2 major under threshold is violated"
	::=  8195

dpsRTUp9195Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 2 major under threshold is restored"
	::=  9195

dpsRTUp8196Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 2 major over threshold is violated"
	::=  8196

dpsRTUp9196Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 2 major over threshold is restored"
	::=  9196

dpsRTUp8197Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 2 threshold is violated"
	::=  8197

dpsRTUp9197Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 2 threshold is cleared"
	::=  9197

dpsRTUp8198Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 198 is set."
	::=  8198

dpsRTUp9198Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 198 clears."
	::=  9198

dpsRTUp8199Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 199 is set."
	::=  8199

dpsRTUp9199Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 199 clears."
	::=  9199

dpsRTUp8200Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 200 is set."
	::=  8200

dpsRTUp9200Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 200 clears."
	::=  9200

dpsRTUp8201Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 201 is set."
	::=  8201

dpsRTUp9201Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 201 clears."
	::=  9201

dpsRTUp8202Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 202 is set."
	::=  8202

dpsRTUp9202Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 202 clears."
	::=  9202

dpsRTUp8203Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 203 is set."
	::=  8203

dpsRTUp9203Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 203 clears."
	::=  9203

dpsRTUp8204Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 204 is set."
	::=  8204

dpsRTUp9204Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 204 clears."
	::=  9204

dpsRTUp8205Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 205 is set."
	::=  8205

dpsRTUp9205Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 205 clears."
	::=  9205

dpsRTUp8206Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 206 is set."
	::=  8206

dpsRTUp9206Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 206 clears."
	::=  9206

dpsRTUp8207Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 207 is set."
	::=  8207

dpsRTUp9207Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 207 clears."
	::=  9207

dpsRTUp8208Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 208 is set."
	::=  8208

dpsRTUp9208Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 208 clears."
	::=  9208

dpsRTUp8209Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 209 is set."
	::=  8209

dpsRTUp9209Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 209 clears."
	::=  9209

dpsRTUp8210Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 210 is set."
	::=  8210

dpsRTUp9210Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 210 clears."
	::=  9210


dpsRTUp8211Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 211 is set."
	::=  8211

dpsRTUp9211Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 211 clears."
	::=  9211

dpsRTUp8212Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 212 is set."
	::=  8212

dpsRTUp9212Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 212 clears."
	::=  9212

dpsRTUp8213Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 213 is set."
	::=  8213

dpsRTUp9213Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 213 clears."
	::=  9213

dpsRTUp8214Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 214 is set."
	::=  8214

dpsRTUp9214Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 214 clears."
	::=  9214

dpsRTUp8215Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 215 is set."
	::=  8215

dpsRTUp9215Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 215 clears."
	::=  9215

dpsRTUp8216Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 216 is set."
	::=  8216

dpsRTUp9216Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 216 clears."
	::=  9216

dpsRTUp8217Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 217 is set."
	::=  8217

dpsRTUp9217Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 217 clears."
	::=  9217

dpsRTUp8218Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 218 is set."
	::=  8218

dpsRTUp9218Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 218 clears."
	::=  9218

dpsRTUp8219Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 219 is set."
	::=  8219

dpsRTUp9219Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 219 clears."
	::=  9219

dpsRTUp8220Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 220 is set."
	::=  8220

dpsRTUp9220Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 220 clears."
	::=  9220

dpsRTUp8221Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 221 is set."
	::=  8221

dpsRTUp9221Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 221 clears."
	::=  9221

dpsRTUp8222Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 222 is set."
	::=  8222

dpsRTUp9222Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 222 clears."
	::=  9222

dpsRTUp8223Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 223 is set."
	::=  8223

dpsRTUp9223Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 223 clears."
	::=  9223

dpsRTUp8224Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 224 is set."
	::=  8224

dpsRTUp9224Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 224 clears."
	::=  9224

dpsRTUp8225Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 225 is set."
	::=  8225

dpsRTUp9225Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 225 clears."
	::=  9225

dpsRTUp8226Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 226 is set."
	::=  8226

dpsRTUp9226Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 226 clears."
	::=  9226

dpsRTUp8227Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 227 is set."
	::=  8227

dpsRTUp9227Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 227 clears."
	::=  9227

dpsRTUp8228Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 228 is set."
	::=  8228

dpsRTUp9228Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 228 clears."
	::=  9228

dpsRTUp8229Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 229 is set."
	::=  8229

dpsRTUp9229Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 229 clears."
	::=  9229

dpsRTUp8230Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 230 is set."
	::=  8230

dpsRTUp9230Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 230 clears."
	::=  9230


dpsRTUp8231Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 231 is set."
	::=  8231

dpsRTUp9231Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 231 clears."
	::=  9231

dpsRTUp8232Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 232 is set."
	::=  8232

dpsRTUp9232Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 232 clears."
	::=  9232

dpsRTUp8233Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 233 is set."
	::=  8233

dpsRTUp9233Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 233 clears."
	::=  9233

dpsRTUp8234Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 234 is set."
	::=  8234

dpsRTUp9234Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 234 clears."
	::=  9234

dpsRTUp8235Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 235 is set."
	::=  8235

dpsRTUp9235Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 235 clears."
	::=  9235

dpsRTUp8236Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 236 is set."
	::=  8236

dpsRTUp9236Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 236 clears."
	::=  9236

dpsRTUp8237Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 237 is set."
	::=  8237

dpsRTUp9237Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 237 clears."
	::=  9237

dpsRTUp8238Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 238 is set."
	::=  8238

dpsRTUp9238Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 238 clears."
	::=  9238

dpsRTUp8239Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 239 is set."
	::=  8239

dpsRTUp9239Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 239 clears."
	::=  9239

dpsRTUp8240Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 240 is set."
	::=  8240

dpsRTUp9240Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 240 clears."
	::=  9240


dpsRTUp8241Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 241 is set."
	::=  8241

dpsRTUp9241Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 241 clears."
	::=  9241

dpsRTUp8242Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 242 is set."
	::=  8242

dpsRTUp9242Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 242 clears."
	::=  9242

dpsRTUp8243Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 243 is set."
	::=  8243

dpsRTUp9243Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 243 clears."
	::=  9243

dpsRTUp8244Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 244 is set."
	::=  8244

dpsRTUp9244Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 244 clears."
	::=  9244

dpsRTUp8245Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 245 is set."
	::=  8245

dpsRTUp9245Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 245 clears."
	::=  9245

dpsRTUp8246Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 246 is set."
	::=  8246

dpsRTUp9246Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 246 clears."
	::=  9246

dpsRTUp8247Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 247 is set."
	::=  8247

dpsRTUp9247Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 247 clears."
	::=  9247

dpsRTUp8248Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 248 is set."
	::=  8248

dpsRTUp9248Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 248 clears."
	::=  9248

dpsRTUp8249Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 249 is set."
	::=  8249

dpsRTUp9249Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 249 clears."
	::=  9249

dpsRTUp8250Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 250 is set."
	::=  8250

dpsRTUp9250Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 250 clears."
	::=  9250

dpsRTUp8251Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 251 is set."
	::=  8251

dpsRTUp9251Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 251 clears."
	::=  9251

dpsRTUp8252Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 252 is set."
	::=  8252

dpsRTUp9252Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 252 clears."
	::=  9252

dpsRTUp8253Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 253 is set."
	::=  8253

dpsRTUp9253Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 253 clears."
	::=  9253

dpsRTUp8254Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 254 is set."
	::=  8254

dpsRTUp9254Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 254 clears."
	::=  9254

dpsRTUp8255Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 255 is set."
	::=  8255

dpsRTUp9255Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 255 clears."
	::=  9255

dpsRTUp8256Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 256 is set."
	::=  8256

dpsRTUp9256Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when discrete point 256 clears."
	::=  9256


dpsRTUp8257Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 3 minor under threshold is violated"
	::=  8257

dpsRTUp9257Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 3 minor under threshold is restored"
	::=  9257

dpsRTUp8258Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 3 minor over threshold is violated"
	::=  8258

dpsRTUp9258Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 3 minor over threshold is restored"
	::=  9258

dpsRTUp8259Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 3 major under threshold is violated"
	::=  8259

dpsRTUp9259Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 3 major under threshold is restored"
	::=  9259

dpsRTUp8260Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 3 major over threshold is violated"
	::=  8260

dpsRTUp9260Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 3 major over threshold is restored"
	::=  9260
	
dpsRTUp8261Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 3 threshold is violated"
	::=  8261

dpsRTUp9261Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 3 threshold is cleared"
	::=  9261	

dpsRTUp8321Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 4 minor under threshold is violated"
	::=  8321

dpsRTUp9321Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 4 minor under threshold is restored"
	::=  9321

dpsRTUp8322Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 4 minor over threshold is violated"
	::=  8322

dpsRTUp9322Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 4 minor over threshold is restored"
	::=  9322

dpsRTUp8323Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 4 major under threshold is violated"
	::=  8323

dpsRTUp9323Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 4 major under threshold is restored"
	::=  9323

dpsRTUp8324Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 4 major over threshold is violated"
	::=  8324

dpsRTUp9324Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 4 major over threshold is restored"
	::=  9324

dpsRTUp8325Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 4 threshold is violated"
	::=  8325

dpsRTUp9325Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 4 threshold is cleared"
	::=  9325	
	
dpsRTUp8385Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 5 minor under threshold is violated"
	::=  8385

dpsRTUp9385Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 5 minor under threshold is restored"
	::=  9385

dpsRTUp8386Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 5 minor over threshold is violated"
	::=  8386

dpsRTUp9386Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 5 minor over threshold is restored"
	::=  9386

dpsRTUp8387Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 5 major under threshold is violated"
	::=  8387

dpsRTUp9387Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 5 major under threshold is restored"
	::=  9387

dpsRTUp8388Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 5 major over threshold is violated"
	::=  8388

dpsRTUp9388Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 5 major over threshold is restored"
	::=  9388
	
dpsRTUp8389Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 5 threshold is violated"
	::=  8389

dpsRTUp9389Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 5 threshold is cleared"
	::=  9389	

dpsRTUp8449Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 6 minor under threshold is violated"
	::=  8449

dpsRTUp9449Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 6 minor under threshold is restored"
	::=  9449

dpsRTUp8450Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 6 minor over threshold is violated"
	::=  8450

dpsRTUp9450Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 6 minor over threshold is restored"
	::=  9450

dpsRTUp8451Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 6 major under threshold is violated"
	::=  8451

dpsRTUp9451Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 6 major under threshold is restored"
	::=  9451

dpsRTUp8452Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 6 major over threshold is violated"
	::=  8452

dpsRTUp9452Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 6 major over threshold is restored"
	::=  9452
	
dpsRTUp8453Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 6 threshold is violated"
	::=  8453

dpsRTUp9453Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 6 threshold is cleared"
	::=  9453		

dpsRTUp8513Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 7 minor under threshold is violated"
	::=  8513

dpsRTUp9513Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 7 minor under threshold is restored"
	::=  9513

dpsRTUp8514Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 7 minor over threshold is violated"
	::=  8514

dpsRTUp9514Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 7 minor over threshold is restored"
	::=  9514

dpsRTUp8515Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 7 major under threshold is violated"
	::=  8515

dpsRTUp9515Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 7 major under threshold is restored"
	::=  9515

dpsRTUp8516Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 7 major over threshold is violated"
	::=  8516

dpsRTUp9516Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 7 major over threshold is restored"
	::=  9516

dpsRTUp8517Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 7 threshold is violated"
	::=  8517

dpsRTUp9517Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 7 threshold is cleared"
	::=  9517		
	
dpsRTUp8577Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 8 minor under threshold is violated"
	::=  8577

dpsRTUp9577Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 8 minor under threshold is restored"
	::=  9577

dpsRTUp8578Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 8 minor over threshold is violated"
	::=  8578

dpsRTUp9578Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 8 minor over threshold is restored"
	::=  9578

dpsRTUp8579Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 8 major under threshold is violated"
	::=  8579

dpsRTUp9579Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 8 major under threshold is restored"
	::=  9579

dpsRTUp8580Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 8 major over threshold is violated"
	::=  8580

dpsRTUp9580Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when channel 8 major over threshold is restored"
	::=  9580
	
dpsRTUp8581Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 8 threshold is violated"
	::=  8581

dpsRTUp9581Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Alternative Format: Generated periodically or when channel 8 threshold is cleared"
	::=  9581		

dpsRTUp8641Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 1 is latched."
	::=  8641

dpsRTUp9641Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 1 is released."
	::=  9641

dpsRTUp8642Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 2 is latched."
	::=  8642

dpsRTUp9642Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 2 is released."
	::=  9642

dpsRTUp8643Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 3 is latched."
	::=  8643

dpsRTUp9643Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 3 is released."
	::=  9643

dpsRTUp8644Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 4 is latched."
	::=  8644

dpsRTUp9644Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 4 is released."
	::=  9644

dpsRTUp8645Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 5 is latched."
	::=  8645

dpsRTUp9645Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 5 is released."
	::=  9645

dpsRTUp8646Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 6 is latched."
	::=  8646

dpsRTUp9646Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 6 is released."
	::=  9646

dpsRTUp8647Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 7 is latched."
	::=  8647

dpsRTUp9647Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 7 is released."
	::=  9647

dpsRTUp8648Set TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 8 is latched."
	::=  8648

dpsRTUp9648Clr TRAP-TYPE
	ENTERPRISE  dpsRTU
	VARIABLES {	sysDescr, sysLocation, dpsRTUDateTime,
					dpsRTUAPort, dpsRTUCAddress, dpsRTUADisplay, dpsRTUAPoint,
					dpsRTUAPntDesc, dpsRTUAState }
	DESCRIPTION "Generated when control 8 is released."
	::=  9648

dpsRTUp8657Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Timed Tick: set."
	::= 8657

dpsRTUp9657Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Timed Tick: cleared."
	::= 9657

dpsRTUp8658Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Exp.Module Callout: set."
	::= 8658

dpsRTUp9658Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Exp.Module Callout: cleared."
	::= 9658

dpsRTUp8659Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Network Time Server: set."
	::= 8659

dpsRTUp9659Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Network Time Server: cleared."
	::= 9659

dpsRTUp8660Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Accumulation Event: set."
	::= 8660

dpsRTUp9660Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Accumulation Event: cleared."
	::= 9660

dpsRTUp8661Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Duplicate IP Address: set."
	::= 8661

dpsRTUp9661Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Duplicate IP Address: cleared."
	::= 9661

dpsRTUp8673Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Power Up: set."
	::= 8673

dpsRTUp9673Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Power Up: cleared."
	::= 9673


dpsRTUp8676Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Lost Provisioning: set."
	::= 8676

dpsRTUp9676Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Lost Provisioning: cleared."
	::= 9676


dpsRTUp8677Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "DCP Poller Inactive: set."
	::= 8677

dpsRTUp9677Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "DCP Poller Inactive: cleared."
	::= 9677


dpsRTUp8678Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "LAN Not Active: set."
	::= 8678

dpsRTUp9678Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "LAN Not Active: cleared."
	::= 9678


dpsRTUp8681Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Modem Not Responding: set."
	::= 8681

dpsRTUp9681Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Modem Not Responding: cleared."
	::= 9681


dpsRTUp8682Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "No Dialtone: set."
	::= 8682

dpsRTUp9682Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "No Dialtone: cleared."
	::= 9682

dpsRTUp8683Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "SNMP Trap not Sent: set."
	::= 8683

dpsRTUp9683Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "SNMP Trap not Sent: cleared."
	::= 9683

dpsRTUp8684Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Pager Que Overflow: set."
	::= 8684

dpsRTUp9684Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Pager Que Overflow: cleared."
	::= 9684


dpsRTUp8685Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Notification Failed: set."
	::= 8685

dpsRTUp9685Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Notification Failed: cleared."
	::= 9685
	

dpsRTUp8686Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Craft RcvQ full: set."
	::= 8686

dpsRTUp9686Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Craft RcvQ full: cleared."
	::= 9686


dpsRTUp8687Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Modem RcvQ full: set."
	::= 8687

dpsRTUp9687Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Modem RcvQ full: cleared."
	::= 9687


dpsRTUp8688Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 1 RcvQ full: set."
	::= 8688

dpsRTUp9688Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 1 RcvQ full: cleared."
	::= 9688


dpsRTUp8689Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 2 RcvQ full: set."
	::= 8689

dpsRTUp9689Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 2 RcvQ full: cleared."
	::= 9689


dpsRTUp8690Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 3 RcvQ full: set."
	::= 8690

dpsRTUp9690Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 3 RcvQ full: cleared."
	::= 9690


dpsRTUp8691Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 4 RcvQ full: set."
	::= 8691

dpsRTUp9691Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 4 RcvQ full: cleared."
	::= 9691


dpsRTUp8692Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 5 RcvQ full: set."
	::= 8692

dpsRTUp9692Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 5 RcvQ full: cleared."
	::= 9692


dpsRTUp8693Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 6 RcvQ full: set."
	::= 8693

dpsRTUp9693Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 6 RcvQ full: cleared."
	::= 9693


dpsRTUp8694Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 7 RcvQ full: set."
	::= 8694

dpsRTUp9694Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 7 RcvQ full: cleared."
	::= 9694


dpsRTUp8695Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 8 RcvQ full: set."
	::= 8695

dpsRTUp9695Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Data 8 RcvQ full: cleared."
	::= 9695

dpsRTUp8696Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "NGDdx 1 Fail: set."
	::= 8696

dpsRTUp9696Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "NGDdx 1 Fail: cleared."
	::= 9696

dpsRTUp8697Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "NGDdx 2 Fail: set."
	::= 8697

dpsRTUp9697Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "NGDdx 2 Fail: cleared."
	::= 9697

dpsRTUp8698Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "NGDdx 3 Fail: set."
	::= 8698

dpsRTUp9698Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "NGDdx 3 Fail: cleared."
	::= 9698

dpsRTUp8699Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "GLD 1 Fail: set."
	::= 8699

dpsRTUp9699Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "GLD 1 Fail: cleared."
	::= 9699

dpsRTUp8700Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "GLD 2 Fail: set."
	::= 8700

dpsRTUp9700Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "GLD 2 Fail: cleared."
	::= 9700

dpsRTUp8701Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "GLD 3 Fail: set."
	::= 8701

dpsRTUp9701Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "GLD 3 Fail: cleared."
	::= 9701

dpsRTUp8702Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Chan. Port Timeout: set."
	::= 8702

dpsRTUp9702Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Chan. Port Timeout: cleared."
	::= 9702

dpsRTUp8703Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Craft Timeout: set."
	::= 8703

dpsRTUp9703Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Craft Timeout: cleared."
	::= 9703

dpsRTUp8704Set TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Event Que Full: set."
	::= 8704

dpsRTUp9704Clr TRAP-TYPE
	ENTERPRISE  dpsRTU
	VARIABLES {	sysDescr, sysLocation, dpsRTUDateTime,
			dpsRTUAPort, dpsRTUCAddress, dpsRTUADisplay, dpsRTUAPoint,
			dpsRTUAPntDesc, dpsRTUAState }
	DESCRIPTION "Event Que Full: cleared."
	::= 9704

-- Granular Traps for SNMPv2

dpsRTUp8001nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8001 is set."
	::= { dpsRTU 8001 }

dpsRTUp9001nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8001 clears."
	::= { dpsRTU 9001 }

dpsRTUp8002nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8002 is set."
	::= { dpsRTU 8002 }

dpsRTUp9002nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8002 clears."
	::= { dpsRTU 9002 }

dpsRTUp8003nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8003 is set."
	::= { dpsRTU 8003 }

dpsRTUp9003nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8003 clears."
	::= { dpsRTU 9003 }

dpsRTUp8004nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8004 is set."
	::= { dpsRTU 8004 }

dpsRTUp9004nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8004 clears."
	::= { dpsRTU 9004 }

dpsRTUp8005nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8005 is set."
	::= { dpsRTU 8005 }

dpsRTUp9005nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8005 clears."
	::= { dpsRTU 9005 }

dpsRTUp8006nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8006 is set."
	::= { dpsRTU 8006 }

dpsRTUp9006nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8006 clears."
	::= { dpsRTU 9006 }

dpsRTUp8007nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8007 is set."
	::= { dpsRTU 8007 }

dpsRTUp9007nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8007 clears."
	::= { dpsRTU 9007 }

dpsRTUp8008nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8008 is set."
	::= { dpsRTU 8008 }

dpsRTUp9008nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8008 clears."
	::= { dpsRTU 9008 }

dpsRTUp8009nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8009 is set."
	::= { dpsRTU 8009 }

dpsRTUp9009nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8009 clears."
	::= { dpsRTU 9009 }

dpsRTUp8010nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8010 is set."
	::= { dpsRTU 8010 }

dpsRTUp9010nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8010 clears."
	::= { dpsRTU 9010 }

dpsRTUp8011nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8011 is set."
	::= { dpsRTU 8011 }

dpsRTUp9011nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8011 clears."
	::= { dpsRTU 9011 }

dpsRTUp8012nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8012 is set."
	::= { dpsRTU 8012 }

dpsRTUp9012nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8012 clears."
	::= { dpsRTU 9012 }

dpsRTUp8013nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8013 is set."
	::= { dpsRTU 8013 }

dpsRTUp9013nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8013 clears."
	::= { dpsRTU 9013 }

dpsRTUp8014nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8014 is set."
	::= { dpsRTU 8014 }

dpsRTUp9014nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8014 clears."
	::= { dpsRTU 9014 }

dpsRTUp8015nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8015 is set."
	::= { dpsRTU 8015 }

dpsRTUp9015nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8015 clears."
	::= { dpsRTU 9015 }

dpsRTUp8016nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8016 is set."
	::= { dpsRTU 8016 }

dpsRTUp9016nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8016 clears."
	::= { dpsRTU 9016 }

dpsRTUp8017nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8017 is set."
	::= { dpsRTU 8017 }

dpsRTUp9017nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8017 clears."
	::= { dpsRTU 9017 }

dpsRTUp8018nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8018 is set."
	::= { dpsRTU 8018 }

dpsRTUp9018nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8018 clears."
	::= { dpsRTU 9018 }

dpsRTUp8019nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8019 is set."
	::= { dpsRTU 8019 }

dpsRTUp9019nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8019 clears."
	::= { dpsRTU 9019 }

dpsRTUp8020nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8020 is set."
	::= { dpsRTU 8020 }

dpsRTUp9020nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8020 clears."
	::= { dpsRTU 9020 }

dpsRTUp8021nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8021 is set."
	::= { dpsRTU 8021 }

dpsRTUp9021nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8021 clears."
	::= { dpsRTU 9021 }

dpsRTUp8022nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8022 is set."
	::= { dpsRTU 8022 }

dpsRTUp9022nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8022 clears."
	::= { dpsRTU 9022 }

dpsRTUp8023nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8023 is set."
	::= { dpsRTU 8023 }

dpsRTUp9023nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8023 clears."
	::= { dpsRTU 9023 }

dpsRTUp8024nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8024 is set."
	::= { dpsRTU 8024 }

dpsRTUp9024nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8024 clears."
	::= { dpsRTU 9024 }

dpsRTUp8025nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8025 is set."
	::= { dpsRTU 8025 }

dpsRTUp9025nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8025 clears."
	::= { dpsRTU 9025 }

dpsRTUp8026nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8026 is set."
	::= { dpsRTU 8026 }

dpsRTUp9026nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8026 clears."
	::= { dpsRTU 9026 }

dpsRTUp8027nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8027 is set."
	::= { dpsRTU 8027 }

dpsRTUp9027nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8027 clears."
	::= { dpsRTU 9027 }

dpsRTUp8028nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8028 is set."
	::= { dpsRTU 8028 }

dpsRTUp9028nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8028 clears."
	::= { dpsRTU 9028 }

dpsRTUp8029nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8029 is set."
	::= { dpsRTU 8029 }

dpsRTUp9029nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8029 clears."
	::= { dpsRTU 9029 }

dpsRTUp8030nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8030 is set."
	::= { dpsRTU 8030 }

dpsRTUp9030nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8030 clears."
	::= { dpsRTU 9030 }

dpsRTUp8031nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8031 is set."
	::= { dpsRTU 8031 }

dpsRTUp9031nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8031 clears."
	::= { dpsRTU 9031 }

dpsRTUp8032nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8032 is set."
	::= { dpsRTU 8032 }

dpsRTUp9032nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8032 clears."
	::= { dpsRTU 9032 }

dpsRTUp8033nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8033 is set."
	::= { dpsRTU 8033 }

dpsRTUp9033nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8033 clears."
	::= { dpsRTU 9033 }

dpsRTUp8034nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8034 is set."
	::= { dpsRTU 8034 }

dpsRTUp9034nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8034 clears."
	::= { dpsRTU 9034 }

dpsRTUp8035nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8035 is set."
	::= { dpsRTU 8035 }

dpsRTUp9035nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8035 clears."
	::= { dpsRTU 9035 }

dpsRTUp8036nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8036 is set."
	::= { dpsRTU 8036 }

dpsRTUp9036nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8036 clears."
	::= { dpsRTU 9036 }

dpsRTUp8037nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8037 is set."
	::= { dpsRTU 8037 }

dpsRTUp9037nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8037 clears."
	::= { dpsRTU 9037 }

dpsRTUp8038nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8038 is set."
	::= { dpsRTU 8038 }

dpsRTUp9038nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8038 clears."
	::= { dpsRTU 9038 }

dpsRTUp8039nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8039 is set."
	::= { dpsRTU 8039 }

dpsRTUp9039nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8039 clears."
	::= { dpsRTU 9039 }

dpsRTUp8040nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8040 is set."
	::= { dpsRTU 8040 }

dpsRTUp9040nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8040 clears."
	::= { dpsRTU 9040 }

dpsRTUp8041nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8041 is set."
	::= { dpsRTU 8041 }

dpsRTUp9041nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8041 clears."
	::= { dpsRTU 9041 }

dpsRTUp8042nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8042 is set."
	::= { dpsRTU 8042 }

dpsRTUp9042nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8042 clears."
	::= { dpsRTU 9042 }

dpsRTUp8043nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8043 is set."
	::= { dpsRTU 8043 }

dpsRTUp9043nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8043 clears."
	::= { dpsRTU 9043 }

dpsRTUp8044nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8044 is set."
	::= { dpsRTU 8044 }

dpsRTUp9044nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8044 clears."
	::= { dpsRTU 9044 }

dpsRTUp8045nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8045 is set."
	::= { dpsRTU 8045 }

dpsRTUp9045nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8045 clears."
	::= { dpsRTU 9045 }

dpsRTUp8046nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8046 is set."
	::= { dpsRTU 8046 }

dpsRTUp9046nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8046 clears."
	::= { dpsRTU 9046 }

dpsRTUp8047nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8047 is set."
	::= { dpsRTU 8047 }

dpsRTUp9047nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8047 clears."
	::= { dpsRTU 9047 }

dpsRTUp8048nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8048 is set."
	::= { dpsRTU 8048 }

dpsRTUp9048nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8048 clears."
	::= { dpsRTU 9048 }

dpsRTUp8049nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8049 is set."
	::= { dpsRTU 8049 }

dpsRTUp9049nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8049 clears."
	::= { dpsRTU 9049 }

dpsRTUp8050nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8050 is set."
	::= { dpsRTU 8050 }

dpsRTUp9050nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8050 clears."
	::= { dpsRTU 9050 }

dpsRTUp8051nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8051 is set."
	::= { dpsRTU 8051 }

dpsRTUp9051nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8051 clears."
	::= { dpsRTU 9051 }

dpsRTUp8052nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8052 is set."
	::= { dpsRTU 8052 }

dpsRTUp9052nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8052 clears."
	::= { dpsRTU 9052 }

dpsRTUp8053nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8053 is set."
	::= { dpsRTU 8053 }

dpsRTUp9053nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8053 clears."
	::= { dpsRTU 9053 }

dpsRTUp8054nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8054 is set."
	::= { dpsRTU 8054 }

dpsRTUp9054nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8054 clears."
	::= { dpsRTU 9054 }

dpsRTUp8055nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8055 is set."
	::= { dpsRTU 8055 }

dpsRTUp9055nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8055 clears."
	::= { dpsRTU 9055 }

dpsRTUp8056nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8056 is set."
	::= { dpsRTU 8056 }

dpsRTUp9056nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8056 clears."
	::= { dpsRTU 9056 }

dpsRTUp8057nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8057 is set."
	::= { dpsRTU 8057 }

dpsRTUp9057nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8057 clears."
	::= { dpsRTU 9057 }

dpsRTUp8058nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8058 is set."
	::= { dpsRTU 8058 }

dpsRTUp9058nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8058 clears."
	::= { dpsRTU 9058 }

dpsRTUp8059nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8059 is set."
	::= { dpsRTU 8059 }

dpsRTUp9059nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8059 clears."
	::= { dpsRTU 9059 }

dpsRTUp8060nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8060 is set."
	::= { dpsRTU 8060 }

dpsRTUp9060nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8060 clears."
	::= { dpsRTU 9060 }

dpsRTUp8061nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8061 is set."
	::= { dpsRTU 8061 }

dpsRTUp9061nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8061 clears."
	::= { dpsRTU 9061 }

dpsRTUp8062nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8062 is set."
	::= { dpsRTU 8062 }

dpsRTUp9062nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8062 clears."
	::= { dpsRTU 9062 }

dpsRTUp8063nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8063 is set."
	::= { dpsRTU 8063 }

dpsRTUp9063nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8063 clears."
	::= { dpsRTU 9063 }

dpsRTUp8064nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8064 is set."
	::= { dpsRTU 8064 }

dpsRTUp9064nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8064 clears."
	::= { dpsRTU 9064 }

dpsRTUp8065nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8065 is set."
	::= { dpsRTU 8065 }

dpsRTUp9065nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8065 clears."
	::= { dpsRTU 9065 }

dpsRTUp8066nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8066 is set."
	::= { dpsRTU 8066 }

dpsRTUp9066nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8066 clears."
	::= { dpsRTU 9066 }

dpsRTUp8067nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8067 is set."
	::= { dpsRTU 8067 }

dpsRTUp9067nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8067 clears."
	::= { dpsRTU 9067 }

dpsRTUp8068nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8068 is set."
	::= { dpsRTU 8068 }

dpsRTUp9068nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8068 clears."
	::= { dpsRTU 9068 }

dpsRTUp8069nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8069 is set."
	::= { dpsRTU 8069 }

dpsRTUp9069nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8069 clears."
	::= { dpsRTU 9069 }

dpsRTUp8070nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8070 is set."
	::= { dpsRTU 8070 }

dpsRTUp9070nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8070 clears."
	::= { dpsRTU 9070 }

dpsRTUp8071nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8071 is set."
	::= { dpsRTU 8071 }

dpsRTUp9071nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8071 clears."
	::= { dpsRTU 9071 }

dpsRTUp8072nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8072 is set."
	::= { dpsRTU 8072 }

dpsRTUp9072nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8072 clears."
	::= { dpsRTU 9072 }

dpsRTUp8073nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8073 is set."
	::= { dpsRTU 8073 }

dpsRTUp9073nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8073 clears."
	::= { dpsRTU 9073 }

dpsRTUp8074nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8074 is set."
	::= { dpsRTU 8074 }

dpsRTUp9074nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8074 clears."
	::= { dpsRTU 9074 }

dpsRTUp8075nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8075 is set."
	::= { dpsRTU 8075 }

dpsRTUp9075nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8075 clears."
	::= { dpsRTU 9075 }

dpsRTUp8076nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8076 is set."
	::= { dpsRTU 8076 }

dpsRTUp9076nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8076 clears."
	::= { dpsRTU 9076 }

dpsRTUp8077nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8077 is set."
	::= { dpsRTU 8077 }

dpsRTUp9077nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8077 clears."
	::= { dpsRTU 9077 }

dpsRTUp8078nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8078 is set."
	::= { dpsRTU 8078 }

dpsRTUp9078nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8078 clears."
	::= { dpsRTU 9078 }

dpsRTUp8079nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8079 is set."
	::= { dpsRTU 8079 }

dpsRTUp9079nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8079 clears."
	::= { dpsRTU 9079 }

dpsRTUp8080nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8080 is set."
	::= { dpsRTU 8080 }

dpsRTUp9080nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8080 clears."
	::= { dpsRTU 9080 }

dpsRTUp8081nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8081 is set."
	::= { dpsRTU 8081 }

dpsRTUp9081nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8081 clears."
	::= { dpsRTU 9081 }

dpsRTUp8082nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8082 is set."
	::= { dpsRTU 8082 }

dpsRTUp9082nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8082 clears."
	::= { dpsRTU 9082 }

dpsRTUp8083nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8083 is set."
	::= { dpsRTU 8083 }

dpsRTUp9083nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8083 clears."
	::= { dpsRTU 9083 }

dpsRTUp8084nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8084 is set."
	::= { dpsRTU 8084 }

dpsRTUp9084nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8084 clears."
	::= { dpsRTU 9084 }

dpsRTUp8085nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8085 is set."
	::= { dpsRTU 8085 }

dpsRTUp9085nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8085 clears."
	::= { dpsRTU 9085 }

dpsRTUp8086nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8086 is set."
	::= { dpsRTU 8086 }

dpsRTUp9086nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8086 clears."
	::= { dpsRTU 9086 }

dpsRTUp8087nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8087 is set."
	::= { dpsRTU 8087 }

dpsRTUp9087nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8087 clears."
	::= { dpsRTU 9087 }

dpsRTUp8088nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8088 is set."
	::= { dpsRTU 8088 }

dpsRTUp9088nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8088 clears."
	::= { dpsRTU 9088 }

dpsRTUp8089nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8089 is set."
	::= { dpsRTU 8089 }

dpsRTUp9089nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8089 clears."
	::= { dpsRTU 9089 }

dpsRTUp8090nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8090 is set."
	::= { dpsRTU 8090 }

dpsRTUp9090nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8090 clears."
	::= { dpsRTU 9090 }

dpsRTUp8091nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8091 is set."
	::= { dpsRTU 8091 }

dpsRTUp9091nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8091 clears."
	::= { dpsRTU 9091 }

dpsRTUp8092nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8092 is set."
	::= { dpsRTU 8092 }

dpsRTUp9092nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8092 clears."
	::= { dpsRTU 9092 }

dpsRTUp8093nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8093 is set."
	::= { dpsRTU 8093 }

dpsRTUp9093nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8093 clears."
	::= { dpsRTU 9093 }

dpsRTUp8094nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8094 is set."
	::= { dpsRTU 8094 }

dpsRTUp9094nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8094 clears."
	::= { dpsRTU 9094 }

dpsRTUp8095nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8095 is set."
	::= { dpsRTU 8095 }

dpsRTUp9095nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8095 clears."
	::= { dpsRTU 9095 }

dpsRTUp8096nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8096 is set."
	::= { dpsRTU 8096 }

dpsRTUp9096nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8096 clears."
	::= { dpsRTU 9096 }

dpsRTUp8097nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8097 is set."
	::= { dpsRTU 8097 }

dpsRTUp9097nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8097 clears."
	::= { dpsRTU 9097 }

dpsRTUp8098nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8098 is set."
	::= { dpsRTU 8098 }

dpsRTUp9098nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8098 clears."
	::= { dpsRTU 9098 }

dpsRTUp8099nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8099 is set."
	::= { dpsRTU 8099 }

dpsRTUp9099nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8099 clears."
	::= { dpsRTU 9099 }

dpsRTUp8100nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8100 is set."
	::= { dpsRTU 8100 }

dpsRTUp9100nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8100 clears."
	::= { dpsRTU 9100 }

dpsRTUp8101nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8101 is set."
	::= { dpsRTU 8101 }

dpsRTUp9101nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8101 clears."
	::= { dpsRTU 9101 }

dpsRTUp8102nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8102 is set."
	::= { dpsRTU 8102 }

dpsRTUp9102nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8102 clears."
	::= { dpsRTU 9102 }

dpsRTUp8103nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8103 is set."
	::= { dpsRTU 8103 }

dpsRTUp9103nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8103 clears."
	::= { dpsRTU 9103 }

dpsRTUp8104nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8104 is set."
	::= { dpsRTU 8104 }

dpsRTUp9104nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8104 clears."
	::= { dpsRTU 9104 }

dpsRTUp8105nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8105 is set."
	::= { dpsRTU 8105 }

dpsRTUp9105nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8105 clears."
	::= { dpsRTU 9105 }

dpsRTUp8106nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8106 is set."
	::= { dpsRTU 8106 }

dpsRTUp9106nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8106 clears."
	::= { dpsRTU 9106 }

dpsRTUp8107nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8107 is set."
	::= { dpsRTU 8107 }

dpsRTUp9107nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8107 clears."
	::= { dpsRTU 9107 }

dpsRTUp8108nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8108 is set."
	::= { dpsRTU 8108 }

dpsRTUp9108nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8108 clears."
	::= { dpsRTU 9108 }

dpsRTUp8109nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8109 is set."
	::= { dpsRTU 8109 }

dpsRTUp9109nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8109 clears."
	::= { dpsRTU 9109 }

dpsRTUp8110nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8110 is set."
	::= { dpsRTU 8110 }

dpsRTUp9110nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8110 clears."
	::= { dpsRTU 9110 }

dpsRTUp8111nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8111 is set."
	::= { dpsRTU 8111 }

dpsRTUp9111nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8111 clears."
	::= { dpsRTU 9111 }

dpsRTUp8112nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8112 is set."
	::= { dpsRTU 8112 }

dpsRTUp9112nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8112 clears."
	::= { dpsRTU 9112 }

dpsRTUp8113nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8113 is set."
	::= { dpsRTU 8113 }

dpsRTUp9113nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8113 clears."
	::= { dpsRTU 9113 }

dpsRTUp8114nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8114 is set."
	::= { dpsRTU 8114 }

dpsRTUp9114nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8114 clears."
	::= { dpsRTU 9114 }

dpsRTUp8115nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8115 is set."
	::= { dpsRTU 8115 }

dpsRTUp9115nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8115 clears."
	::= { dpsRTU 9115 }

dpsRTUp8116nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8116 is set."
	::= { dpsRTU 8116 }

dpsRTUp9116nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8116 clears."
	::= { dpsRTU 9116 }

dpsRTUp8117nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8117 is set."
	::= { dpsRTU 8117 }

dpsRTUp9117nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8117 clears."
	::= { dpsRTU 9117 }

dpsRTUp8118nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8118 is set."
	::= { dpsRTU 8118 }

dpsRTUp9118nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8118 clears."
	::= { dpsRTU 9118 }

dpsRTUp8119nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8119 is set."
	::= { dpsRTU 8119 }

dpsRTUp9119nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8119 clears."
	::= { dpsRTU 9119 }

dpsRTUp8120nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8120 is set."
	::= { dpsRTU 8120 }

dpsRTUp9120nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8120 clears."
	::= { dpsRTU 9120 }

dpsRTUp8121nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8121 is set."
	::= { dpsRTU 8121 }

dpsRTUp9121nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8121 clears."
	::= { dpsRTU 9121 }

dpsRTUp8122nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8122 is set."
	::= { dpsRTU 8122 }

dpsRTUp9122nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8122 clears."
	::= { dpsRTU 9122 }

dpsRTUp8123nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8123 is set."
	::= { dpsRTU 8123 }

dpsRTUp9123nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8123 clears."
	::= { dpsRTU 9123 }

dpsRTUp8124nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8124 is set."
	::= { dpsRTU 8124 }

dpsRTUp9124nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8124 clears."
	::= { dpsRTU 9124 }

dpsRTUp8125nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8125 is set."
	::= { dpsRTU 8125 }

dpsRTUp9125nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8125 clears."
	::= { dpsRTU 9125 }

dpsRTUp8126nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8126 is set."
	::= { dpsRTU 8126 }

dpsRTUp9126nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8126 clears."
	::= { dpsRTU 9126 }

dpsRTUp8127nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8127 is set."
	::= { dpsRTU 8127 }

dpsRTUp9127nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8127 clears."
	::= { dpsRTU 9127 }

dpsRTUp8128nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8128 is set."
	::= { dpsRTU 8128 }

dpsRTUp9128nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8128 clears."
	::= { dpsRTU 9128 }

dpsRTUp8129nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8129 is set."
	::= { dpsRTU 8129 }

dpsRTUp9129nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8129 clears."
	::= { dpsRTU 9129 }

dpsRTUp8130nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8130 is set."
	::= { dpsRTU 8130 }

dpsRTUp9130nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8130 clears."
	::= { dpsRTU 9130 }

dpsRTUp8131nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8131 is set."
	::= { dpsRTU 8131 }

dpsRTUp9131nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8131 clears."
	::= { dpsRTU 9131 }

dpsRTUp8132nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8132 is set."
	::= { dpsRTU 8132 }

dpsRTUp9132nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8132 clears."
	::= { dpsRTU 9132 }

dpsRTUp8133nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8133 is set."
	::= { dpsRTU 8133 }

dpsRTUp9133nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8133 clears."
	::= { dpsRTU 9133 }

dpsRTUp8134nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8134 is set."
	::= { dpsRTU 8134 }

dpsRTUp9134nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8134 clears."
	::= { dpsRTU 9134 }

dpsRTUp8135nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8135 is set."
	::= { dpsRTU 8135 }

dpsRTUp9135nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8135 clears."
	::= { dpsRTU 9135 }

dpsRTUp8136nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8136 is set."
	::= { dpsRTU 8136 }

dpsRTUp9136nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8136 clears."
	::= { dpsRTU 9136 }

dpsRTUp8137nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8137 is set."
	::= { dpsRTU 8137 }

dpsRTUp9137nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8137 clears."
	::= { dpsRTU 9137 }

dpsRTUp8138nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8138 is set."
	::= { dpsRTU 8138 }

dpsRTUp9138nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8138 clears."
	::= { dpsRTU 9138 }

dpsRTUp8139nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8139 is set."
	::= { dpsRTU 8139 }

dpsRTUp9139nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8139 clears."
	::= { dpsRTU 9139 }

dpsRTUp8140nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8140 is set."
	::= { dpsRTU 8140 }

dpsRTUp9140nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8140 clears."
	::= { dpsRTU 9140 }

dpsRTUp8141nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8141 is set."
	::= { dpsRTU 8141 }

dpsRTUp9141nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8141 clears."
	::= { dpsRTU 9141 }

dpsRTUp8142nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8142 is set."
	::= { dpsRTU 8142 }

dpsRTUp9142nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8142 clears."
	::= { dpsRTU 9142 }

dpsRTUp8143nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8143 is set."
	::= { dpsRTU 8143 }

dpsRTUp9143nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8143 clears."
	::= { dpsRTU 9143 }

dpsRTUp8144nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8144 is set."
	::= { dpsRTU 8144 }

dpsRTUp9144nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8144 clears."
	::= { dpsRTU 9144 }

dpsRTUp8145nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8145 is set."
	::= { dpsRTU 8145 }

dpsRTUp9145nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8145 clears."
	::= { dpsRTU 9145 }

dpsRTUp8146nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8146 is set."
	::= { dpsRTU 8146 }

dpsRTUp9146nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8146 clears."
	::= { dpsRTU 9146 }

dpsRTUp8147nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8147 is set."
	::= { dpsRTU 8147 }

dpsRTUp9147nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8147 clears."
	::= { dpsRTU 9147 }

dpsRTUp8148nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8148 is set."
	::= { dpsRTU 8148 }

dpsRTUp9148nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8148 clears."
	::= { dpsRTU 9148 }

dpsRTUp8149nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8149 is set."
	::= { dpsRTU 8149 }

dpsRTUp9149nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8149 clears."
	::= { dpsRTU 9149 }

dpsRTUp8150nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8150 is set."
	::= { dpsRTU 8150 }

dpsRTUp9150nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8150 clears."
	::= { dpsRTU 9150 }

dpsRTUp8151nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8151 is set."
	::= { dpsRTU 8151 }

dpsRTUp9151nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8151 clears."
	::= { dpsRTU 9151 }

dpsRTUp8152nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8152 is set."
	::= { dpsRTU 8152 }

dpsRTUp9152nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8152 clears."
	::= { dpsRTU 9152 }

dpsRTUp8153nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8153 is set."
	::= { dpsRTU 8153 }

dpsRTUp9153nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8153 clears."
	::= { dpsRTU 9153 }

dpsRTUp8154nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8154 is set."
	::= { dpsRTU 8154 }

dpsRTUp9154nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8154 clears."
	::= { dpsRTU 9154 }

dpsRTUp8155nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8155 is set."
	::= { dpsRTU 8155 }

dpsRTUp9155nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8155 clears."
	::= { dpsRTU 9155 }

dpsRTUp8156nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8156 is set."
	::= { dpsRTU 8156 }

dpsRTUp9156nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8156 clears."
	::= { dpsRTU 9156 }

dpsRTUp8157nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8157 is set."
	::= { dpsRTU 8157 }

dpsRTUp9157nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8157 clears."
	::= { dpsRTU 9157 }

dpsRTUp8158nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8158 is set."
	::= { dpsRTU 8158 }

dpsRTUp9158nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8158 clears."
	::= { dpsRTU 9158 }

dpsRTUp8159nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8159 is set."
	::= { dpsRTU 8159 }

dpsRTUp9159nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8159 clears."
	::= { dpsRTU 9159 }

dpsRTUp8160nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8160 is set."
	::= { dpsRTU 8160 }

dpsRTUp9160nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8160 clears."
	::= { dpsRTU 9160 }

dpsRTUp8161nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8161 is set."
	::= { dpsRTU 8161 }

dpsRTUp9161nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8161 clears."
	::= { dpsRTU 9161 }

dpsRTUp8162nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8162 is set."
	::= { dpsRTU 8162 }

dpsRTUp9162nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8162 clears."
	::= { dpsRTU 9162 }

dpsRTUp8163nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8163 is set."
	::= { dpsRTU 8163 }

dpsRTUp9163nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8163 clears."
	::= { dpsRTU 9163 }

dpsRTUp8164nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8164 is set."
	::= { dpsRTU 8164 }

dpsRTUp9164nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8164 clears."
	::= { dpsRTU 9164 }

dpsRTUp8165nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8165 is set."
	::= { dpsRTU 8165 }

dpsRTUp9165nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8165 clears."
	::= { dpsRTU 9165 }

dpsRTUp8166nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8166 is set."
	::= { dpsRTU 8166 }

dpsRTUp9166nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8166 clears."
	::= { dpsRTU 9166 }

dpsRTUp8167nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8167 is set."
	::= { dpsRTU 8167 }

dpsRTUp9167nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8167 clears."
	::= { dpsRTU 9167 }

dpsRTUp8168nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8168 is set."
	::= { dpsRTU 8168 }

dpsRTUp9168nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8168 clears."
	::= { dpsRTU 9168 }

dpsRTUp8169nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8169 is set."
	::= { dpsRTU 8169 }

dpsRTUp9169nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8169 clears."
	::= { dpsRTU 9169 }

dpsRTUp8170nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8170 is set."
	::= { dpsRTU 8170 }

dpsRTUp9170nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8170 clears."
	::= { dpsRTU 9170 }

dpsRTUp8171nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8171 is set."
	::= { dpsRTU 8171 }

dpsRTUp9171nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8171 clears."
	::= { dpsRTU 9171 }

dpsRTUp8172nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8172 is set."
	::= { dpsRTU 8172 }

dpsRTUp9172nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8172 clears."
	::= { dpsRTU 9172 }

dpsRTUp8173nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8173 is set."
	::= { dpsRTU 8173 }

dpsRTUp9173nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8173 clears."
	::= { dpsRTU 9173 }

dpsRTUp8174nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8174 is set."
	::= { dpsRTU 8174 }

dpsRTUp9174nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8174 clears."
	::= { dpsRTU 9174 }

dpsRTUp8175nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8175 is set."
	::= { dpsRTU 8175 }

dpsRTUp9175nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8175 clears."
	::= { dpsRTU 9175 }

dpsRTUp8176nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8176 is set."
	::= { dpsRTU 8176 }

dpsRTUp9176nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8176 clears."
	::= { dpsRTU 9176 }

dpsRTUp8177nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8177 is set."
	::= { dpsRTU 8177 }

dpsRTUp9177nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8177 clears."
	::= { dpsRTU 9177 }

dpsRTUp8178nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8178 is set."
	::= { dpsRTU 8178 }

dpsRTUp9178nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8178 clears."
	::= { dpsRTU 9178 }

dpsRTUp8179nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8179 is set."
	::= { dpsRTU 8179 }

dpsRTUp9179nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8179 clears."
	::= { dpsRTU 9179 }

dpsRTUp8180nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8180 is set."
	::= { dpsRTU 8180 }

dpsRTUp9180nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8180 clears."
	::= { dpsRTU 9180 }

dpsRTUp8181nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8181 is set."
	::= { dpsRTU 8181 }

dpsRTUp9181nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8181 clears."
	::= { dpsRTU 9181 }

dpsRTUp8182nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8182 is set."
	::= { dpsRTU 8182 }

dpsRTUp9182nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8182 clears."
	::= { dpsRTU 9182 }

dpsRTUp8183nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8183 is set."
	::= { dpsRTU 8183 }

dpsRTUp9183nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8183 clears."
	::= { dpsRTU 9183 }

dpsRTUp8184nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8184 is set."
	::= { dpsRTU 8184 }

dpsRTUp9184nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8184 clears."
	::= { dpsRTU 9184 }

dpsRTUp8185nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8185 is set."
	::= { dpsRTU 8185 }

dpsRTUp9185nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8185 clears."
	::= { dpsRTU 9185 }

dpsRTUp8186nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8186 is set."
	::= { dpsRTU 8186 }

dpsRTUp9186nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8186 clears."
	::= { dpsRTU 9186 }

dpsRTUp8187nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8187 is set."
	::= { dpsRTU 8187 }

dpsRTUp9187nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8187 clears."
	::= { dpsRTU 9187 }

dpsRTUp8188nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8188 is set."
	::= { dpsRTU 8188 }

dpsRTUp9188nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8188 clears."
	::= { dpsRTU 9188 }

dpsRTUp8189nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8189 is set."
	::= { dpsRTU 8189 }

dpsRTUp9189nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8189 clears."
	::= { dpsRTU 9189 }

dpsRTUp8190nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8190 is set."
	::= { dpsRTU 8190 }

dpsRTUp9190nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8190 clears."
	::= { dpsRTU 9190 }

dpsRTUp8191nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8191 is set."
	::= { dpsRTU 8191 }

dpsRTUp9191nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8191 clears."
	::= { dpsRTU 9191 }

dpsRTUp8192nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8192 is set."
	::= { dpsRTU 8192 }

dpsRTUp9192nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8192 clears."
	::= { dpsRTU 9192 }

dpsRTUp8193nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8193 is set."
	::= { dpsRTU 8193 }

dpsRTUp9193nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8193 clears."
	::= { dpsRTU 9193 }

dpsRTUp8194nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8194 is set."
	::= { dpsRTU 8194 }

dpsRTUp9194nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8194 clears."
	::= { dpsRTU 9194 }

dpsRTUp8195nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8195 is set."
	::= { dpsRTU 8195 }

dpsRTUp9195nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8195 clears."
	::= { dpsRTU 9195 }

dpsRTUp8196nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8196 is set."
	::= { dpsRTU 8196 }

dpsRTUp9196nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8196 clears."
	::= { dpsRTU 9196 }

dpsRTUp8197nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8197 is set."
	::= { dpsRTU 8197 }

dpsRTUp9197nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8197 clears."
	::= { dpsRTU 9197 }

dpsRTUp8198nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8198 is set."
	::= { dpsRTU 8198 }

dpsRTUp9198nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8198 clears."
	::= { dpsRTU 9198 }

dpsRTUp8199nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8199 is set."
	::= { dpsRTU 8199 }

dpsRTUp9199nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8199 clears."
	::= { dpsRTU 9199 }

dpsRTUp8200nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8200 is set."
	::= { dpsRTU 8200 }

dpsRTUp9200nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8200 clears."
	::= { dpsRTU 9200 }

dpsRTUp8201nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8201 is set."
	::= { dpsRTU 8201 }

dpsRTUp9201nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8201 clears."
	::= { dpsRTU 9201 }

dpsRTUp8202nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8202 is set."
	::= { dpsRTU 8202 }

dpsRTUp9202nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8202 clears."
	::= { dpsRTU 9202 }

dpsRTUp8203nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8203 is set."
	::= { dpsRTU 8203 }

dpsRTUp9203nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8203 clears."
	::= { dpsRTU 9203 }

dpsRTUp8204nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8204 is set."
	::= { dpsRTU 8204 }

dpsRTUp9204nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8204 clears."
	::= { dpsRTU 9204 }

dpsRTUp8205nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8205 is set."
	::= { dpsRTU 8205 }

dpsRTUp9205nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8205 clears."
	::= { dpsRTU 9205 }

dpsRTUp8206nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8206 is set."
	::= { dpsRTU 8206 }

dpsRTUp9206nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8206 clears."
	::= { dpsRTU 9206 }

dpsRTUp8207nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8207 is set."
	::= { dpsRTU 8207 }

dpsRTUp9207nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8207 clears."
	::= { dpsRTU 9207 }

dpsRTUp8208nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8208 is set."
	::= { dpsRTU 8208 }

dpsRTUp9208nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8208 clears."
	::= { dpsRTU 9208 }

dpsRTUp8209nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8209 is set."
	::= { dpsRTU 8209 }

dpsRTUp9209nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8209 clears."
	::= { dpsRTU 9209 }

dpsRTUp8210nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8210 is set."
	::= { dpsRTU 8210 }

dpsRTUp9210nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8210 clears."
	::= { dpsRTU 9210 }

dpsRTUp8211nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8211 is set."
	::= { dpsRTU 8211 }

dpsRTUp9211nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8211 clears."
	::= { dpsRTU 9211 }

dpsRTUp8212nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8212 is set."
	::= { dpsRTU 8212 }

dpsRTUp9212nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8212 clears."
	::= { dpsRTU 9212 }

dpsRTUp8213nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8213 is set."
	::= { dpsRTU 8213 }

dpsRTUp9213nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8213 clears."
	::= { dpsRTU 9213 }

dpsRTUp8214nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8214 is set."
	::= { dpsRTU 8214 }

dpsRTUp9214nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8214 clears."
	::= { dpsRTU 9214 }

dpsRTUp8215nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8215 is set."
	::= { dpsRTU 8215 }

dpsRTUp9215nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8215 clears."
	::= { dpsRTU 9215 }

dpsRTUp8216nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8216 is set."
	::= { dpsRTU 8216 }

dpsRTUp9216nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8216 clears."
	::= { dpsRTU 9216 }

dpsRTUp8217nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8217 is set."
	::= { dpsRTU 8217 }

dpsRTUp9217nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8217 clears."
	::= { dpsRTU 9217 }

dpsRTUp8218nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8218 is set."
	::= { dpsRTU 8218 }

dpsRTUp9218nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8218 clears."
	::= { dpsRTU 9218 }

dpsRTUp8219nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8219 is set."
	::= { dpsRTU 8219 }

dpsRTUp9219nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8219 clears."
	::= { dpsRTU 9219 }

dpsRTUp8220nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8220 is set."
	::= { dpsRTU 8220 }

dpsRTUp9220nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8220 clears."
	::= { dpsRTU 9220 }

dpsRTUp8221nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8221 is set."
	::= { dpsRTU 8221 }

dpsRTUp9221nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8221 clears."
	::= { dpsRTU 9221 }

dpsRTUp8222nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8222 is set."
	::= { dpsRTU 8222 }

dpsRTUp9222nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8222 clears."
	::= { dpsRTU 9222 }

dpsRTUp8223nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8223 is set."
	::= { dpsRTU 8223 }

dpsRTUp9223nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8223 clears."
	::= { dpsRTU 9223 }

dpsRTUp8224nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8224 is set."
	::= { dpsRTU 8224 }

dpsRTUp9224nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8224 clears."
	::= { dpsRTU 9224 }

dpsRTUp8225nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8225 is set."
	::= { dpsRTU 8225 }

dpsRTUp9225nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8225 clears."
	::= { dpsRTU 9225 }

dpsRTUp8226nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8226 is set."
	::= { dpsRTU 8226 }

dpsRTUp9226nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8226 clears."
	::= { dpsRTU 9226 }

dpsRTUp8227nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8227 is set."
	::= { dpsRTU 8227 }

dpsRTUp9227nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8227 clears."
	::= { dpsRTU 9227 }

dpsRTUp8228nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8228 is set."
	::= { dpsRTU 8228 }

dpsRTUp9228nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8228 clears."
	::= { dpsRTU 9228 }

dpsRTUp8229nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8229 is set."
	::= { dpsRTU 8229 }

dpsRTUp9229nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8229 clears."
	::= { dpsRTU 9229 }

dpsRTUp8230nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8230 is set."
	::= { dpsRTU 8230 }

dpsRTUp9230nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8230 clears."
	::= { dpsRTU 9230 }

dpsRTUp8231nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8231 is set."
	::= { dpsRTU 8231 }

dpsRTUp9231nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8231 clears."
	::= { dpsRTU 9231 }

dpsRTUp8232nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8232 is set."
	::= { dpsRTU 8232 }

dpsRTUp9232nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8232 clears."
	::= { dpsRTU 9232 }

dpsRTUp8233nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8233 is set."
	::= { dpsRTU 8233 }

dpsRTUp9233nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8233 clears."
	::= { dpsRTU 9233 }

dpsRTUp8234nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8234 is set."
	::= { dpsRTU 8234 }

dpsRTUp9234nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8234 clears."
	::= { dpsRTU 9234 }

dpsRTUp8235nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8235 is set."
	::= { dpsRTU 8235 }

dpsRTUp9235nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8235 clears."
	::= { dpsRTU 9235 }

dpsRTUp8236nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8236 is set."
	::= { dpsRTU 8236 }

dpsRTUp9236nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8236 clears."
	::= { dpsRTU 9236 }

dpsRTUp8237nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8237 is set."
	::= { dpsRTU 8237 }

dpsRTUp9237nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8237 clears."
	::= { dpsRTU 9237 }

dpsRTUp8238nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8238 is set."
	::= { dpsRTU 8238 }

dpsRTUp9238nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8238 clears."
	::= { dpsRTU 9238 }

dpsRTUp8239nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8239 is set."
	::= { dpsRTU 8239 }

dpsRTUp9239nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8239 clears."
	::= { dpsRTU 9239 }

dpsRTUp8240nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8240 is set."
	::= { dpsRTU 8240 }

dpsRTUp9240nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8240 clears."
	::= { dpsRTU 9240 }

dpsRTUp8241nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8241 is set."
	::= { dpsRTU 8241 }

dpsRTUp9241nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8241 clears."
	::= { dpsRTU 9241 }

dpsRTUp8242nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8242 is set."
	::= { dpsRTU 8242 }

dpsRTUp9242nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8242 clears."
	::= { dpsRTU 9242 }

dpsRTUp8243nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8243 is set."
	::= { dpsRTU 8243 }

dpsRTUp9243nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8243 clears."
	::= { dpsRTU 9243 }

dpsRTUp8244nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8244 is set."
	::= { dpsRTU 8244 }

dpsRTUp9244nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8244 clears."
	::= { dpsRTU 9244 }

dpsRTUp8245nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8245 is set."
	::= { dpsRTU 8245 }

dpsRTUp9245nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8245 clears."
	::= { dpsRTU 9245 }

dpsRTUp8246nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8246 is set."
	::= { dpsRTU 8246 }

dpsRTUp9246nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8246 clears."
	::= { dpsRTU 9246 }

dpsRTUp8247nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8247 is set."
	::= { dpsRTU 8247 }

dpsRTUp9247nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8247 clears."
	::= { dpsRTU 9247 }

dpsRTUp8248nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8248 is set."
	::= { dpsRTU 8248 }

dpsRTUp9248nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8248 clears."
	::= { dpsRTU 9248 }

dpsRTUp8249nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8249 is set."
	::= { dpsRTU 8249 }

dpsRTUp9249nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8249 clears."
	::= { dpsRTU 9249 }

dpsRTUp8250nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8250 is set."
	::= { dpsRTU 8250 }

dpsRTUp9250nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8250 clears."
	::= { dpsRTU 9250 }

dpsRTUp8251nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8251 is set."
	::= { dpsRTU 8251 }

dpsRTUp9251nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8251 clears."
	::= { dpsRTU 9251 }

dpsRTUp8252nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8252 is set."
	::= { dpsRTU 8252 }

dpsRTUp9252nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8252 clears."
	::= { dpsRTU 9252 }

dpsRTUp8253nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8253 is set."
	::= { dpsRTU 8253 }

dpsRTUp9253nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8253 clears."
	::= { dpsRTU 9253 }

dpsRTUp8254nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8254 is set."
	::= { dpsRTU 8254 }

dpsRTUp9254nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8254 clears."
	::= { dpsRTU 9254 }

dpsRTUp8255nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8255 is set."
	::= { dpsRTU 8255 }

dpsRTUp9255nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8255 clears."
	::= { dpsRTU 9255 }

dpsRTUp8256nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8256 is set."
	::= { dpsRTU 8256 }

dpsRTUp9256nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8256 clears."
	::= { dpsRTU 9256 }

dpsRTUp8257nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8257 is set."
	::= { dpsRTU 8257 }

dpsRTUp9257nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8257 clears."
	::= { dpsRTU 9257 }

dpsRTUp8258nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8258 is set."
	::= { dpsRTU 8258 }

dpsRTUp9258nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8258 clears."
	::= { dpsRTU 9258 }

dpsRTUp8259nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8259 is set."
	::= { dpsRTU 8259 }

dpsRTUp9259nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8259 clears."
	::= { dpsRTU 9259 }

dpsRTUp8260nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8260 is set."
	::= { dpsRTU 8260 }

dpsRTUp9260nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8260 clears."
	::= { dpsRTU 9260 }

dpsRTUp8261nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8261 is set."
	::= { dpsRTU 8261 }

dpsRTUp9261nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8261 clears."
	::= { dpsRTU 9261 }

dpsRTUp8262nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8262 is set."
	::= { dpsRTU 8262 }

dpsRTUp9262nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8262 clears."
	::= { dpsRTU 9262 }

dpsRTUp8263nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8263 is set."
	::= { dpsRTU 8263 }

dpsRTUp9263nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8263 clears."
	::= { dpsRTU 9263 }

dpsRTUp8264nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8264 is set."
	::= { dpsRTU 8264 }

dpsRTUp9264nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8264 clears."
	::= { dpsRTU 9264 }

dpsRTUp8265nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8265 is set."
	::= { dpsRTU 8265 }

dpsRTUp9265nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8265 clears."
	::= { dpsRTU 9265 }

dpsRTUp8266nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8266 is set."
	::= { dpsRTU 8266 }

dpsRTUp9266nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8266 clears."
	::= { dpsRTU 9266 }

dpsRTUp8267nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8267 is set."
	::= { dpsRTU 8267 }

dpsRTUp9267nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8267 clears."
	::= { dpsRTU 9267 }

dpsRTUp8268nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8268 is set."
	::= { dpsRTU 8268 }

dpsRTUp9268nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8268 clears."
	::= { dpsRTU 9268 }

dpsRTUp8269nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8269 is set."
	::= { dpsRTU 8269 }

dpsRTUp9269nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8269 clears."
	::= { dpsRTU 9269 }

dpsRTUp8270nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8270 is set."
	::= { dpsRTU 8270 }

dpsRTUp9270nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8270 clears."
	::= { dpsRTU 9270 }

dpsRTUp8271nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8271 is set."
	::= { dpsRTU 8271 }

dpsRTUp9271nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8271 clears."
	::= { dpsRTU 9271 }

dpsRTUp8272nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8272 is set."
	::= { dpsRTU 8272 }

dpsRTUp9272nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8272 clears."
	::= { dpsRTU 9272 }

dpsRTUp8273nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8273 is set."
	::= { dpsRTU 8273 }

dpsRTUp9273nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8273 clears."
	::= { dpsRTU 9273 }

dpsRTUp8274nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8274 is set."
	::= { dpsRTU 8274 }

dpsRTUp9274nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8274 clears."
	::= { dpsRTU 9274 }

dpsRTUp8275nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8275 is set."
	::= { dpsRTU 8275 }

dpsRTUp9275nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8275 clears."
	::= { dpsRTU 9275 }

dpsRTUp8276nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8276 is set."
	::= { dpsRTU 8276 }

dpsRTUp9276nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8276 clears."
	::= { dpsRTU 9276 }

dpsRTUp8277nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8277 is set."
	::= { dpsRTU 8277 }

dpsRTUp9277nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8277 clears."
	::= { dpsRTU 9277 }

dpsRTUp8278nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8278 is set."
	::= { dpsRTU 8278 }

dpsRTUp9278nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8278 clears."
	::= { dpsRTU 9278 }

dpsRTUp8279nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8279 is set."
	::= { dpsRTU 8279 }

dpsRTUp9279nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8279 clears."
	::= { dpsRTU 9279 }

dpsRTUp8280nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8280 is set."
	::= { dpsRTU 8280 }

dpsRTUp9280nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8280 clears."
	::= { dpsRTU 9280 }

dpsRTUp8281nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8281 is set."
	::= { dpsRTU 8281 }

dpsRTUp9281nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8281 clears."
	::= { dpsRTU 9281 }

dpsRTUp8282nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8282 is set."
	::= { dpsRTU 8282 }

dpsRTUp9282nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8282 clears."
	::= { dpsRTU 9282 }

dpsRTUp8283nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8283 is set."
	::= { dpsRTU 8283 }

dpsRTUp9283nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8283 clears."
	::= { dpsRTU 9283 }

dpsRTUp8284nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8284 is set."
	::= { dpsRTU 8284 }

dpsRTUp9284nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8284 clears."
	::= { dpsRTU 9284 }

dpsRTUp8285nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8285 is set."
	::= { dpsRTU 8285 }

dpsRTUp9285nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8285 clears."
	::= { dpsRTU 9285 }

dpsRTUp8286nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8286 is set."
	::= { dpsRTU 8286 }

dpsRTUp9286nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8286 clears."
	::= { dpsRTU 9286 }

dpsRTUp8287nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8287 is set."
	::= { dpsRTU 8287 }

dpsRTUp9287nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8287 clears."
	::= { dpsRTU 9287 }

dpsRTUp8288nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8288 is set."
	::= { dpsRTU 8288 }

dpsRTUp9288nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8288 clears."
	::= { dpsRTU 9288 }

dpsRTUp8289nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8289 is set."
	::= { dpsRTU 8289 }

dpsRTUp9289nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8289 clears."
	::= { dpsRTU 9289 }

dpsRTUp8290nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8290 is set."
	::= { dpsRTU 8290 }

dpsRTUp9290nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8290 clears."
	::= { dpsRTU 9290 }

dpsRTUp8291nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8291 is set."
	::= { dpsRTU 8291 }

dpsRTUp9291nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8291 clears."
	::= { dpsRTU 9291 }

dpsRTUp8292nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8292 is set."
	::= { dpsRTU 8292 }

dpsRTUp9292nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8292 clears."
	::= { dpsRTU 9292 }

dpsRTUp8293nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8293 is set."
	::= { dpsRTU 8293 }

dpsRTUp9293nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8293 clears."
	::= { dpsRTU 9293 }

dpsRTUp8294nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8294 is set."
	::= { dpsRTU 8294 }

dpsRTUp9294nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8294 clears."
	::= { dpsRTU 9294 }

dpsRTUp8295nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8295 is set."
	::= { dpsRTU 8295 }

dpsRTUp9295nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8295 clears."
	::= { dpsRTU 9295 }

dpsRTUp8296nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8296 is set."
	::= { dpsRTU 8296 }

dpsRTUp9296nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8296 clears."
	::= { dpsRTU 9296 }

dpsRTUp8297nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8297 is set."
	::= { dpsRTU 8297 }

dpsRTUp9297nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8297 clears."
	::= { dpsRTU 9297 }

dpsRTUp8298nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8298 is set."
	::= { dpsRTU 8298 }

dpsRTUp9298nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8298 clears."
	::= { dpsRTU 9298 }

dpsRTUp8299nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8299 is set."
	::= { dpsRTU 8299 }

dpsRTUp9299nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8299 clears."
	::= { dpsRTU 9299 }

dpsRTUp8300nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8300 is set."
	::= { dpsRTU 8300 }

dpsRTUp9300nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8300 clears."
	::= { dpsRTU 9300 }

dpsRTUp8301nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8301 is set."
	::= { dpsRTU 8301 }

dpsRTUp9301nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8301 clears."
	::= { dpsRTU 9301 }

dpsRTUp8302nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8302 is set."
	::= { dpsRTU 8302 }

dpsRTUp9302nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8302 clears."
	::= { dpsRTU 9302 }

dpsRTUp8303nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8303 is set."
	::= { dpsRTU 8303 }

dpsRTUp9303nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8303 clears."
	::= { dpsRTU 9303 }

dpsRTUp8304nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8304 is set."
	::= { dpsRTU 8304 }

dpsRTUp9304nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8304 clears."
	::= { dpsRTU 9304 }

dpsRTUp8305nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8305 is set."
	::= { dpsRTU 8305 }

dpsRTUp9305nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8305 clears."
	::= { dpsRTU 9305 }

dpsRTUp8306nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8306 is set."
	::= { dpsRTU 8306 }

dpsRTUp9306nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8306 clears."
	::= { dpsRTU 9306 }

dpsRTUp8307nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8307 is set."
	::= { dpsRTU 8307 }

dpsRTUp9307nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8307 clears."
	::= { dpsRTU 9307 }

dpsRTUp8308nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8308 is set."
	::= { dpsRTU 8308 }

dpsRTUp9308nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8308 clears."
	::= { dpsRTU 9308 }

dpsRTUp8309nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8309 is set."
	::= { dpsRTU 8309 }

dpsRTUp9309nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8309 clears."
	::= { dpsRTU 9309 }

dpsRTUp8310nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8310 is set."
	::= { dpsRTU 8310 }

dpsRTUp9310nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8310 clears."
	::= { dpsRTU 9310 }

dpsRTUp8311nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8311 is set."
	::= { dpsRTU 8311 }

dpsRTUp9311nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8311 clears."
	::= { dpsRTU 9311 }

dpsRTUp8312nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8312 is set."
	::= { dpsRTU 8312 }

dpsRTUp9312nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8312 clears."
	::= { dpsRTU 9312 }

dpsRTUp8313nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8313 is set."
	::= { dpsRTU 8313 }

dpsRTUp9313nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8313 clears."
	::= { dpsRTU 9313 }

dpsRTUp8314nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8314 is set."
	::= { dpsRTU 8314 }

dpsRTUp9314nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8314 clears."
	::= { dpsRTU 9314 }

dpsRTUp8315nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8315 is set."
	::= { dpsRTU 8315 }

dpsRTUp9315nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8315 clears."
	::= { dpsRTU 9315 }

dpsRTUp8316nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8316 is set."
	::= { dpsRTU 8316 }

dpsRTUp9316nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8316 clears."
	::= { dpsRTU 9316 }

dpsRTUp8317nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8317 is set."
	::= { dpsRTU 8317 }

dpsRTUp9317nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8317 clears."
	::= { dpsRTU 9317 }

dpsRTUp8318nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8318 is set."
	::= { dpsRTU 8318 }

dpsRTUp9318nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8318 clears."
	::= { dpsRTU 9318 }

dpsRTUp8319nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8319 is set."
	::= { dpsRTU 8319 }

dpsRTUp9319nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8319 clears."
	::= { dpsRTU 9319 }

dpsRTUp8320nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8320 is set."
	::= { dpsRTU 8320 }

dpsRTUp9320nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8320 clears."
	::= { dpsRTU 9320 }

dpsRTUp8321nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8321 is set."
	::= { dpsRTU 8321 }

dpsRTUp9321nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8321 clears."
	::= { dpsRTU 9321 }

dpsRTUp8322nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8322 is set."
	::= { dpsRTU 8322 }

dpsRTUp9322nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8322 clears."
	::= { dpsRTU 9322 }

dpsRTUp8323nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8323 is set."
	::= { dpsRTU 8323 }

dpsRTUp9323nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8323 clears."
	::= { dpsRTU 9323 }

dpsRTUp8324nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8324 is set."
	::= { dpsRTU 8324 }

dpsRTUp9324nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8324 clears."
	::= { dpsRTU 9324 }

dpsRTUp8325nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8325 is set."
	::= { dpsRTU 8325 }

dpsRTUp9325nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8325 clears."
	::= { dpsRTU 9325 }

dpsRTUp8326nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8326 is set."
	::= { dpsRTU 8326 }

dpsRTUp9326nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8326 clears."
	::= { dpsRTU 9326 }

dpsRTUp8327nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8327 is set."
	::= { dpsRTU 8327 }

dpsRTUp9327nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8327 clears."
	::= { dpsRTU 9327 }

dpsRTUp8328nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8328 is set."
	::= { dpsRTU 8328 }

dpsRTUp9328nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8328 clears."
	::= { dpsRTU 9328 }

dpsRTUp8329nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8329 is set."
	::= { dpsRTU 8329 }

dpsRTUp9329nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8329 clears."
	::= { dpsRTU 9329 }

dpsRTUp8330nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8330 is set."
	::= { dpsRTU 8330 }

dpsRTUp9330nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8330 clears."
	::= { dpsRTU 9330 }

dpsRTUp8331nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8331 is set."
	::= { dpsRTU 8331 }

dpsRTUp9331nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8331 clears."
	::= { dpsRTU 9331 }

dpsRTUp8332nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8332 is set."
	::= { dpsRTU 8332 }

dpsRTUp9332nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8332 clears."
	::= { dpsRTU 9332 }

dpsRTUp8333nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8333 is set."
	::= { dpsRTU 8333 }

dpsRTUp9333nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8333 clears."
	::= { dpsRTU 9333 }

dpsRTUp8334nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8334 is set."
	::= { dpsRTU 8334 }

dpsRTUp9334nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8334 clears."
	::= { dpsRTU 9334 }

dpsRTUp8335nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8335 is set."
	::= { dpsRTU 8335 }

dpsRTUp9335nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8335 clears."
	::= { dpsRTU 9335 }

dpsRTUp8336nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8336 is set."
	::= { dpsRTU 8336 }

dpsRTUp9336nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8336 clears."
	::= { dpsRTU 9336 }

dpsRTUp8337nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8337 is set."
	::= { dpsRTU 8337 }

dpsRTUp9337nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8337 clears."
	::= { dpsRTU 9337 }

dpsRTUp8338nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8338 is set."
	::= { dpsRTU 8338 }

dpsRTUp9338nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8338 clears."
	::= { dpsRTU 9338 }

dpsRTUp8339nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8339 is set."
	::= { dpsRTU 8339 }

dpsRTUp9339nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8339 clears."
	::= { dpsRTU 9339 }

dpsRTUp8340nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8340 is set."
	::= { dpsRTU 8340 }

dpsRTUp9340nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8340 clears."
	::= { dpsRTU 9340 }

dpsRTUp8341nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8341 is set."
	::= { dpsRTU 8341 }

dpsRTUp9341nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8341 clears."
	::= { dpsRTU 9341 }

dpsRTUp8342nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8342 is set."
	::= { dpsRTU 8342 }

dpsRTUp9342nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8342 clears."
	::= { dpsRTU 9342 }

dpsRTUp8343nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8343 is set."
	::= { dpsRTU 8343 }

dpsRTUp9343nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8343 clears."
	::= { dpsRTU 9343 }

dpsRTUp8344nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8344 is set."
	::= { dpsRTU 8344 }

dpsRTUp9344nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8344 clears."
	::= { dpsRTU 9344 }

dpsRTUp8345nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8345 is set."
	::= { dpsRTU 8345 }

dpsRTUp9345nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8345 clears."
	::= { dpsRTU 9345 }

dpsRTUp8346nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8346 is set."
	::= { dpsRTU 8346 }

dpsRTUp9346nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8346 clears."
	::= { dpsRTU 9346 }

dpsRTUp8347nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8347 is set."
	::= { dpsRTU 8347 }

dpsRTUp9347nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8347 clears."
	::= { dpsRTU 9347 }

dpsRTUp8348nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8348 is set."
	::= { dpsRTU 8348 }

dpsRTUp9348nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8348 clears."
	::= { dpsRTU 9348 }

dpsRTUp8349nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8349 is set."
	::= { dpsRTU 8349 }

dpsRTUp9349nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8349 clears."
	::= { dpsRTU 9349 }

dpsRTUp8350nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8350 is set."
	::= { dpsRTU 8350 }

dpsRTUp9350nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8350 clears."
	::= { dpsRTU 9350 }

dpsRTUp8351nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8351 is set."
	::= { dpsRTU 8351 }

dpsRTUp9351nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8351 clears."
	::= { dpsRTU 9351 }

dpsRTUp8352nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8352 is set."
	::= { dpsRTU 8352 }

dpsRTUp9352nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8352 clears."
	::= { dpsRTU 9352 }

dpsRTUp8353nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8353 is set."
	::= { dpsRTU 8353 }

dpsRTUp9353nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8353 clears."
	::= { dpsRTU 9353 }

dpsRTUp8354nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8354 is set."
	::= { dpsRTU 8354 }

dpsRTUp9354nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8354 clears."
	::= { dpsRTU 9354 }

dpsRTUp8355nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8355 is set."
	::= { dpsRTU 8355 }

dpsRTUp9355nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8355 clears."
	::= { dpsRTU 9355 }

dpsRTUp8356nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8356 is set."
	::= { dpsRTU 8356 }

dpsRTUp9356nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8356 clears."
	::= { dpsRTU 9356 }

dpsRTUp8357nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8357 is set."
	::= { dpsRTU 8357 }

dpsRTUp9357nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8357 clears."
	::= { dpsRTU 9357 }

dpsRTUp8358nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8358 is set."
	::= { dpsRTU 8358 }

dpsRTUp9358nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8358 clears."
	::= { dpsRTU 9358 }

dpsRTUp8359nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8359 is set."
	::= { dpsRTU 8359 }

dpsRTUp9359nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8359 clears."
	::= { dpsRTU 9359 }

dpsRTUp8360nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8360 is set."
	::= { dpsRTU 8360 }

dpsRTUp9360nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8360 clears."
	::= { dpsRTU 9360 }

dpsRTUp8361nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8361 is set."
	::= { dpsRTU 8361 }

dpsRTUp9361nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8361 clears."
	::= { dpsRTU 9361 }

dpsRTUp8362nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8362 is set."
	::= { dpsRTU 8362 }

dpsRTUp9362nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8362 clears."
	::= { dpsRTU 9362 }

dpsRTUp8363nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8363 is set."
	::= { dpsRTU 8363 }

dpsRTUp9363nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8363 clears."
	::= { dpsRTU 9363 }

dpsRTUp8364nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8364 is set."
	::= { dpsRTU 8364 }

dpsRTUp9364nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8364 clears."
	::= { dpsRTU 9364 }

dpsRTUp8365nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8365 is set."
	::= { dpsRTU 8365 }

dpsRTUp9365nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8365 clears."
	::= { dpsRTU 9365 }

dpsRTUp8366nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8366 is set."
	::= { dpsRTU 8366 }

dpsRTUp9366nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8366 clears."
	::= { dpsRTU 9366 }

dpsRTUp8367nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8367 is set."
	::= { dpsRTU 8367 }

dpsRTUp9367nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8367 clears."
	::= { dpsRTU 9367 }

dpsRTUp8368nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8368 is set."
	::= { dpsRTU 8368 }

dpsRTUp9368nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8368 clears."
	::= { dpsRTU 9368 }

dpsRTUp8369nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8369 is set."
	::= { dpsRTU 8369 }

dpsRTUp9369nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8369 clears."
	::= { dpsRTU 9369 }

dpsRTUp8370nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8370 is set."
	::= { dpsRTU 8370 }

dpsRTUp9370nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8370 clears."
	::= { dpsRTU 9370 }

dpsRTUp8371nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8371 is set."
	::= { dpsRTU 8371 }

dpsRTUp9371nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8371 clears."
	::= { dpsRTU 9371 }

dpsRTUp8372nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8372 is set."
	::= { dpsRTU 8372 }

dpsRTUp9372nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8372 clears."
	::= { dpsRTU 9372 }

dpsRTUp8373nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8373 is set."
	::= { dpsRTU 8373 }

dpsRTUp9373nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8373 clears."
	::= { dpsRTU 9373 }

dpsRTUp8374nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8374 is set."
	::= { dpsRTU 8374 }

dpsRTUp9374nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8374 clears."
	::= { dpsRTU 9374 }

dpsRTUp8375nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8375 is set."
	::= { dpsRTU 8375 }

dpsRTUp9375nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8375 clears."
	::= { dpsRTU 9375 }

dpsRTUp8376nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8376 is set."
	::= { dpsRTU 8376 }

dpsRTUp9376nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8376 clears."
	::= { dpsRTU 9376 }

dpsRTUp8377nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8377 is set."
	::= { dpsRTU 8377 }

dpsRTUp9377nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8377 clears."
	::= { dpsRTU 9377 }

dpsRTUp8378nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8378 is set."
	::= { dpsRTU 8378 }

dpsRTUp9378nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8378 clears."
	::= { dpsRTU 9378 }

dpsRTUp8379nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8379 is set."
	::= { dpsRTU 8379 }

dpsRTUp9379nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8379 clears."
	::= { dpsRTU 9379 }

dpsRTUp8380nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8380 is set."
	::= { dpsRTU 8380 }

dpsRTUp9380nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8380 clears."
	::= { dpsRTU 9380 }

dpsRTUp8381nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8381 is set."
	::= { dpsRTU 8381 }

dpsRTUp9381nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8381 clears."
	::= { dpsRTU 9381 }

dpsRTUp8382nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8382 is set."
	::= { dpsRTU 8382 }

dpsRTUp9382nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8382 clears."
	::= { dpsRTU 9382 }

dpsRTUp8383nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8383 is set."
	::= { dpsRTU 8383 }

dpsRTUp9383nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8383 clears."
	::= { dpsRTU 9383 }

dpsRTUp8384nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8384 is set."
	::= { dpsRTU 8384 }

dpsRTUp9384nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8384 clears."
	::= { dpsRTU 9384 }

dpsRTUp8385nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8385 is set."
	::= { dpsRTU 8385 }

dpsRTUp9385nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8385 clears."
	::= { dpsRTU 9385 }

dpsRTUp8386nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8386 is set."
	::= { dpsRTU 8386 }

dpsRTUp9386nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8386 clears."
	::= { dpsRTU 9386 }

dpsRTUp8387nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8387 is set."
	::= { dpsRTU 8387 }

dpsRTUp9387nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8387 clears."
	::= { dpsRTU 9387 }

dpsRTUp8388nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8388 is set."
	::= { dpsRTU 8388 }

dpsRTUp9388nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8388 clears."
	::= { dpsRTU 9388 }

dpsRTUp8389nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8389 is set."
	::= { dpsRTU 8389 }

dpsRTUp9389nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8389 clears."
	::= { dpsRTU 9389 }

dpsRTUp8390nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8390 is set."
	::= { dpsRTU 8390 }

dpsRTUp9390nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8390 clears."
	::= { dpsRTU 9390 }

dpsRTUp8391nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8391 is set."
	::= { dpsRTU 8391 }

dpsRTUp9391nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8391 clears."
	::= { dpsRTU 9391 }

dpsRTUp8392nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8392 is set."
	::= { dpsRTU 8392 }

dpsRTUp9392nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8392 clears."
	::= { dpsRTU 9392 }

dpsRTUp8393nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8393 is set."
	::= { dpsRTU 8393 }

dpsRTUp9393nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8393 clears."
	::= { dpsRTU 9393 }

dpsRTUp8394nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8394 is set."
	::= { dpsRTU 8394 }

dpsRTUp9394nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8394 clears."
	::= { dpsRTU 9394 }

dpsRTUp8395nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8395 is set."
	::= { dpsRTU 8395 }

dpsRTUp9395nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8395 clears."
	::= { dpsRTU 9395 }

dpsRTUp8396nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8396 is set."
	::= { dpsRTU 8396 }

dpsRTUp9396nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8396 clears."
	::= { dpsRTU 9396 }

dpsRTUp8397nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8397 is set."
	::= { dpsRTU 8397 }

dpsRTUp9397nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8397 clears."
	::= { dpsRTU 9397 }

dpsRTUp8398nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8398 is set."
	::= { dpsRTU 8398 }

dpsRTUp9398nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8398 clears."
	::= { dpsRTU 9398 }

dpsRTUp8399nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8399 is set."
	::= { dpsRTU 8399 }

dpsRTUp9399nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8399 clears."
	::= { dpsRTU 9399 }

dpsRTUp8400nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8400 is set."
	::= { dpsRTU 8400 }

dpsRTUp9400nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8400 clears."
	::= { dpsRTU 9400 }

dpsRTUp8401nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8401 is set."
	::= { dpsRTU 8401 }

dpsRTUp9401nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8401 clears."
	::= { dpsRTU 9401 }

dpsRTUp8402nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8402 is set."
	::= { dpsRTU 8402 }

dpsRTUp9402nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8402 clears."
	::= { dpsRTU 9402 }

dpsRTUp8403nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8403 is set."
	::= { dpsRTU 8403 }

dpsRTUp9403nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8403 clears."
	::= { dpsRTU 9403 }

dpsRTUp8404nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8404 is set."
	::= { dpsRTU 8404 }

dpsRTUp9404nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8404 clears."
	::= { dpsRTU 9404 }

dpsRTUp8405nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8405 is set."
	::= { dpsRTU 8405 }

dpsRTUp9405nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8405 clears."
	::= { dpsRTU 9405 }

dpsRTUp8406nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8406 is set."
	::= { dpsRTU 8406 }

dpsRTUp9406nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8406 clears."
	::= { dpsRTU 9406 }

dpsRTUp8407nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8407 is set."
	::= { dpsRTU 8407 }

dpsRTUp9407nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8407 clears."
	::= { dpsRTU 9407 }

dpsRTUp8408nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8408 is set."
	::= { dpsRTU 8408 }

dpsRTUp9408nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8408 clears."
	::= { dpsRTU 9408 }

dpsRTUp8409nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8409 is set."
	::= { dpsRTU 8409 }

dpsRTUp9409nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8409 clears."
	::= { dpsRTU 9409 }

dpsRTUp8410nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8410 is set."
	::= { dpsRTU 8410 }

dpsRTUp9410nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8410 clears."
	::= { dpsRTU 9410 }

dpsRTUp8411nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8411 is set."
	::= { dpsRTU 8411 }

dpsRTUp9411nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8411 clears."
	::= { dpsRTU 9411 }

dpsRTUp8412nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8412 is set."
	::= { dpsRTU 8412 }

dpsRTUp9412nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8412 clears."
	::= { dpsRTU 9412 }

dpsRTUp8413nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8413 is set."
	::= { dpsRTU 8413 }

dpsRTUp9413nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8413 clears."
	::= { dpsRTU 9413 }

dpsRTUp8414nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8414 is set."
	::= { dpsRTU 8414 }

dpsRTUp9414nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8414 clears."
	::= { dpsRTU 9414 }

dpsRTUp8415nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8415 is set."
	::= { dpsRTU 8415 }

dpsRTUp9415nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8415 clears."
	::= { dpsRTU 9415 }

dpsRTUp8416nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8416 is set."
	::= { dpsRTU 8416 }

dpsRTUp9416nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8416 clears."
	::= { dpsRTU 9416 }

dpsRTUp8417nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8417 is set."
	::= { dpsRTU 8417 }

dpsRTUp9417nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8417 clears."
	::= { dpsRTU 9417 }

dpsRTUp8418nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8418 is set."
	::= { dpsRTU 8418 }

dpsRTUp9418nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8418 clears."
	::= { dpsRTU 9418 }

dpsRTUp8419nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8419 is set."
	::= { dpsRTU 8419 }

dpsRTUp9419nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8419 clears."
	::= { dpsRTU 9419 }

dpsRTUp8420nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8420 is set."
	::= { dpsRTU 8420 }

dpsRTUp9420nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8420 clears."
	::= { dpsRTU 9420 }

dpsRTUp8421nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8421 is set."
	::= { dpsRTU 8421 }

dpsRTUp9421nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8421 clears."
	::= { dpsRTU 9421 }

dpsRTUp8422nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8422 is set."
	::= { dpsRTU 8422 }

dpsRTUp9422nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8422 clears."
	::= { dpsRTU 9422 }

dpsRTUp8423nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8423 is set."
	::= { dpsRTU 8423 }

dpsRTUp9423nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8423 clears."
	::= { dpsRTU 9423 }

dpsRTUp8424nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8424 is set."
	::= { dpsRTU 8424 }

dpsRTUp9424nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8424 clears."
	::= { dpsRTU 9424 }

dpsRTUp8425nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8425 is set."
	::= { dpsRTU 8425 }

dpsRTUp9425nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8425 clears."
	::= { dpsRTU 9425 }

dpsRTUp8426nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8426 is set."
	::= { dpsRTU 8426 }

dpsRTUp9426nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8426 clears."
	::= { dpsRTU 9426 }

dpsRTUp8427nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8427 is set."
	::= { dpsRTU 8427 }

dpsRTUp9427nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8427 clears."
	::= { dpsRTU 9427 }

dpsRTUp8428nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8428 is set."
	::= { dpsRTU 8428 }

dpsRTUp9428nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8428 clears."
	::= { dpsRTU 9428 }

dpsRTUp8429nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8429 is set."
	::= { dpsRTU 8429 }

dpsRTUp9429nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8429 clears."
	::= { dpsRTU 9429 }

dpsRTUp8430nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8430 is set."
	::= { dpsRTU 8430 }

dpsRTUp9430nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8430 clears."
	::= { dpsRTU 9430 }

dpsRTUp8431nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8431 is set."
	::= { dpsRTU 8431 }

dpsRTUp9431nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8431 clears."
	::= { dpsRTU 9431 }

dpsRTUp8432nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8432 is set."
	::= { dpsRTU 8432 }

dpsRTUp9432nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8432 clears."
	::= { dpsRTU 9432 }

dpsRTUp8433nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8433 is set."
	::= { dpsRTU 8433 }

dpsRTUp9433nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8433 clears."
	::= { dpsRTU 9433 }

dpsRTUp8434nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8434 is set."
	::= { dpsRTU 8434 }

dpsRTUp9434nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8434 clears."
	::= { dpsRTU 9434 }

dpsRTUp8435nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8435 is set."
	::= { dpsRTU 8435 }

dpsRTUp9435nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8435 clears."
	::= { dpsRTU 9435 }

dpsRTUp8436nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8436 is set."
	::= { dpsRTU 8436 }

dpsRTUp9436nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8436 clears."
	::= { dpsRTU 9436 }

dpsRTUp8437nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8437 is set."
	::= { dpsRTU 8437 }

dpsRTUp9437nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8437 clears."
	::= { dpsRTU 9437 }

dpsRTUp8438nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8438 is set."
	::= { dpsRTU 8438 }

dpsRTUp9438nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8438 clears."
	::= { dpsRTU 9438 }

dpsRTUp8439nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8439 is set."
	::= { dpsRTU 8439 }

dpsRTUp9439nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8439 clears."
	::= { dpsRTU 9439 }

dpsRTUp8440nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8440 is set."
	::= { dpsRTU 8440 }

dpsRTUp9440nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8440 clears."
	::= { dpsRTU 9440 }

dpsRTUp8441nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8441 is set."
	::= { dpsRTU 8441 }

dpsRTUp9441nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8441 clears."
	::= { dpsRTU 9441 }

dpsRTUp8442nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8442 is set."
	::= { dpsRTU 8442 }

dpsRTUp9442nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8442 clears."
	::= { dpsRTU 9442 }

dpsRTUp8443nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8443 is set."
	::= { dpsRTU 8443 }

dpsRTUp9443nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8443 clears."
	::= { dpsRTU 9443 }

dpsRTUp8444nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8444 is set."
	::= { dpsRTU 8444 }

dpsRTUp9444nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8444 clears."
	::= { dpsRTU 9444 }

dpsRTUp8445nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8445 is set."
	::= { dpsRTU 8445 }

dpsRTUp9445nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8445 clears."
	::= { dpsRTU 9445 }

dpsRTUp8446nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8446 is set."
	::= { dpsRTU 8446 }

dpsRTUp9446nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8446 clears."
	::= { dpsRTU 9446 }

dpsRTUp8447nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8447 is set."
	::= { dpsRTU 8447 }

dpsRTUp9447nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8447 clears."
	::= { dpsRTU 9447 }

dpsRTUp8448nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8448 is set."
	::= { dpsRTU 8448 }

dpsRTUp9448nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8448 clears."
	::= { dpsRTU 9448 }

dpsRTUp8449nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8449 is set."
	::= { dpsRTU 8449 }

dpsRTUp9449nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8449 clears."
	::= { dpsRTU 9449 }

dpsRTUp8450nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8450 is set."
	::= { dpsRTU 8450 }

dpsRTUp9450nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8450 clears."
	::= { dpsRTU 9450 }

dpsRTUp8451nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8451 is set."
	::= { dpsRTU 8451 }

dpsRTUp9451nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8451 clears."
	::= { dpsRTU 9451 }

dpsRTUp8452nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8452 is set."
	::= { dpsRTU 8452 }

dpsRTUp9452nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8452 clears."
	::= { dpsRTU 9452 }

dpsRTUp8453nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8453 is set."
	::= { dpsRTU 8453 }

dpsRTUp9453nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8453 clears."
	::= { dpsRTU 9453 }

dpsRTUp8454nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8454 is set."
	::= { dpsRTU 8454 }

dpsRTUp9454nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8454 clears."
	::= { dpsRTU 9454 }

dpsRTUp8455nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8455 is set."
	::= { dpsRTU 8455 }

dpsRTUp9455nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8455 clears."
	::= { dpsRTU 9455 }

dpsRTUp8456nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8456 is set."
	::= { dpsRTU 8456 }

dpsRTUp9456nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8456 clears."
	::= { dpsRTU 9456 }

dpsRTUp8457nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8457 is set."
	::= { dpsRTU 8457 }

dpsRTUp9457nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8457 clears."
	::= { dpsRTU 9457 }

dpsRTUp8458nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8458 is set."
	::= { dpsRTU 8458 }

dpsRTUp9458nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8458 clears."
	::= { dpsRTU 9458 }

dpsRTUp8459nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8459 is set."
	::= { dpsRTU 8459 }

dpsRTUp9459nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8459 clears."
	::= { dpsRTU 9459 }

dpsRTUp8460nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8460 is set."
	::= { dpsRTU 8460 }

dpsRTUp9460nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8460 clears."
	::= { dpsRTU 9460 }

dpsRTUp8461nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8461 is set."
	::= { dpsRTU 8461 }

dpsRTUp9461nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8461 clears."
	::= { dpsRTU 9461 }

dpsRTUp8462nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8462 is set."
	::= { dpsRTU 8462 }

dpsRTUp9462nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8462 clears."
	::= { dpsRTU 9462 }

dpsRTUp8463nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8463 is set."
	::= { dpsRTU 8463 }

dpsRTUp9463nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8463 clears."
	::= { dpsRTU 9463 }

dpsRTUp8464nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8464 is set."
	::= { dpsRTU 8464 }

dpsRTUp9464nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8464 clears."
	::= { dpsRTU 9464 }

dpsRTUp8465nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8465 is set."
	::= { dpsRTU 8465 }

dpsRTUp9465nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8465 clears."
	::= { dpsRTU 9465 }

dpsRTUp8466nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8466 is set."
	::= { dpsRTU 8466 }

dpsRTUp9466nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8466 clears."
	::= { dpsRTU 9466 }

dpsRTUp8467nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8467 is set."
	::= { dpsRTU 8467 }

dpsRTUp9467nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8467 clears."
	::= { dpsRTU 9467 }

dpsRTUp8468nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8468 is set."
	::= { dpsRTU 8468 }

dpsRTUp9468nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8468 clears."
	::= { dpsRTU 9468 }

dpsRTUp8469nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8469 is set."
	::= { dpsRTU 8469 }

dpsRTUp9469nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8469 clears."
	::= { dpsRTU 9469 }

dpsRTUp8470nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8470 is set."
	::= { dpsRTU 8470 }

dpsRTUp9470nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8470 clears."
	::= { dpsRTU 9470 }

dpsRTUp8471nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8471 is set."
	::= { dpsRTU 8471 }

dpsRTUp9471nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8471 clears."
	::= { dpsRTU 9471 }

dpsRTUp8472nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8472 is set."
	::= { dpsRTU 8472 }

dpsRTUp9472nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8472 clears."
	::= { dpsRTU 9472 }

dpsRTUp8473nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8473 is set."
	::= { dpsRTU 8473 }

dpsRTUp9473nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8473 clears."
	::= { dpsRTU 9473 }

dpsRTUp8474nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8474 is set."
	::= { dpsRTU 8474 }

dpsRTUp9474nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8474 clears."
	::= { dpsRTU 9474 }

dpsRTUp8475nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8475 is set."
	::= { dpsRTU 8475 }

dpsRTUp9475nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8475 clears."
	::= { dpsRTU 9475 }

dpsRTUp8476nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8476 is set."
	::= { dpsRTU 8476 }

dpsRTUp9476nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8476 clears."
	::= { dpsRTU 9476 }

dpsRTUp8477nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8477 is set."
	::= { dpsRTU 8477 }

dpsRTUp9477nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8477 clears."
	::= { dpsRTU 9477 }

dpsRTUp8478nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8478 is set."
	::= { dpsRTU 8478 }

dpsRTUp9478nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8478 clears."
	::= { dpsRTU 9478 }

dpsRTUp8479nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8479 is set."
	::= { dpsRTU 8479 }

dpsRTUp9479nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8479 clears."
	::= { dpsRTU 9479 }

dpsRTUp8480nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8480 is set."
	::= { dpsRTU 8480 }

dpsRTUp9480nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8480 clears."
	::= { dpsRTU 9480 }

dpsRTUp8481nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8481 is set."
	::= { dpsRTU 8481 }

dpsRTUp9481nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8481 clears."
	::= { dpsRTU 9481 }

dpsRTUp8482nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8482 is set."
	::= { dpsRTU 8482 }

dpsRTUp9482nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8482 clears."
	::= { dpsRTU 9482 }

dpsRTUp8483nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8483 is set."
	::= { dpsRTU 8483 }

dpsRTUp9483nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8483 clears."
	::= { dpsRTU 9483 }

dpsRTUp8484nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8484 is set."
	::= { dpsRTU 8484 }

dpsRTUp9484nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8484 clears."
	::= { dpsRTU 9484 }

dpsRTUp8485nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8485 is set."
	::= { dpsRTU 8485 }

dpsRTUp9485nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8485 clears."
	::= { dpsRTU 9485 }

dpsRTUp8486nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8486 is set."
	::= { dpsRTU 8486 }

dpsRTUp9486nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8486 clears."
	::= { dpsRTU 9486 }

dpsRTUp8487nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8487 is set."
	::= { dpsRTU 8487 }

dpsRTUp9487nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8487 clears."
	::= { dpsRTU 9487 }

dpsRTUp8488nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8488 is set."
	::= { dpsRTU 8488 }

dpsRTUp9488nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8488 clears."
	::= { dpsRTU 9488 }

dpsRTUp8489nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8489 is set."
	::= { dpsRTU 8489 }

dpsRTUp9489nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8489 clears."
	::= { dpsRTU 9489 }

dpsRTUp8490nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8490 is set."
	::= { dpsRTU 8490 }

dpsRTUp9490nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8490 clears."
	::= { dpsRTU 9490 }

dpsRTUp8491nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8491 is set."
	::= { dpsRTU 8491 }

dpsRTUp9491nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8491 clears."
	::= { dpsRTU 9491 }

dpsRTUp8492nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8492 is set."
	::= { dpsRTU 8492 }

dpsRTUp9492nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8492 clears."
	::= { dpsRTU 9492 }

dpsRTUp8493nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8493 is set."
	::= { dpsRTU 8493 }

dpsRTUp9493nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8493 clears."
	::= { dpsRTU 9493 }

dpsRTUp8494nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8494 is set."
	::= { dpsRTU 8494 }

dpsRTUp9494nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8494 clears."
	::= { dpsRTU 9494 }

dpsRTUp8495nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8495 is set."
	::= { dpsRTU 8495 }

dpsRTUp9495nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8495 clears."
	::= { dpsRTU 9495 }

dpsRTUp8496nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8496 is set."
	::= { dpsRTU 8496 }

dpsRTUp9496nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8496 clears."
	::= { dpsRTU 9496 }

dpsRTUp8497nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8497 is set."
	::= { dpsRTU 8497 }

dpsRTUp9497nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8497 clears."
	::= { dpsRTU 9497 }

dpsRTUp8498nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8498 is set."
	::= { dpsRTU 8498 }

dpsRTUp9498nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8498 clears."
	::= { dpsRTU 9498 }

dpsRTUp8499nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8499 is set."
	::= { dpsRTU 8499 }

dpsRTUp9499nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8499 clears."
	::= { dpsRTU 9499 }

dpsRTUp8500nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8500 is set."
	::= { dpsRTU 8500 }

dpsRTUp9500nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8500 clears."
	::= { dpsRTU 9500 }

dpsRTUp8501nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8501 is set."
	::= { dpsRTU 8501 }

dpsRTUp9501nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8501 clears."
	::= { dpsRTU 9501 }

dpsRTUp8502nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8502 is set."
	::= { dpsRTU 8502 }

dpsRTUp9502nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8502 clears."
	::= { dpsRTU 9502 }

dpsRTUp8503nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8503 is set."
	::= { dpsRTU 8503 }

dpsRTUp9503nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8503 clears."
	::= { dpsRTU 9503 }

dpsRTUp8504nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8504 is set."
	::= { dpsRTU 8504 }

dpsRTUp9504nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8504 clears."
	::= { dpsRTU 9504 }

dpsRTUp8505nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8505 is set."
	::= { dpsRTU 8505 }

dpsRTUp9505nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8505 clears."
	::= { dpsRTU 9505 }

dpsRTUp8506nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8506 is set."
	::= { dpsRTU 8506 }

dpsRTUp9506nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8506 clears."
	::= { dpsRTU 9506 }

dpsRTUp8507nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8507 is set."
	::= { dpsRTU 8507 }

dpsRTUp9507nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8507 clears."
	::= { dpsRTU 9507 }

dpsRTUp8508nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8508 is set."
	::= { dpsRTU 8508 }

dpsRTUp9508nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8508 clears."
	::= { dpsRTU 9508 }

dpsRTUp8509nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8509 is set."
	::= { dpsRTU 8509 }

dpsRTUp9509nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8509 clears."
	::= { dpsRTU 9509 }

dpsRTUp8510nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8510 is set."
	::= { dpsRTU 8510 }

dpsRTUp9510nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8510 clears."
	::= { dpsRTU 9510 }

dpsRTUp8511nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8511 is set."
	::= { dpsRTU 8511 }

dpsRTUp9511nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8511 clears."
	::= { dpsRTU 9511 }

dpsRTUp8512nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8512 is set."
	::= { dpsRTU 8512 }

dpsRTUp9512nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8512 clears."
	::= { dpsRTU 9512 }

dpsRTUp8513nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8513 is set."
	::= { dpsRTU 8513 }

dpsRTUp9513nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8513 clears."
	::= { dpsRTU 9513 }

dpsRTUp8514nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8514 is set."
	::= { dpsRTU 8514 }

dpsRTUp9514nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8514 clears."
	::= { dpsRTU 9514 }

dpsRTUp8515nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8515 is set."
	::= { dpsRTU 8515 }

dpsRTUp9515nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8515 clears."
	::= { dpsRTU 9515 }

dpsRTUp8516nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8516 is set."
	::= { dpsRTU 8516 }

dpsRTUp9516nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8516 clears."
	::= { dpsRTU 9516 }

dpsRTUp8517nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8517 is set."
	::= { dpsRTU 8517 }

dpsRTUp9517nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8517 clears."
	::= { dpsRTU 9517 }

dpsRTUp8518nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8518 is set."
	::= { dpsRTU 8518 }

dpsRTUp9518nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8518 clears."
	::= { dpsRTU 9518 }

dpsRTUp8519nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8519 is set."
	::= { dpsRTU 8519 }

dpsRTUp9519nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8519 clears."
	::= { dpsRTU 9519 }

dpsRTUp8520nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8520 is set."
	::= { dpsRTU 8520 }

dpsRTUp9520nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8520 clears."
	::= { dpsRTU 9520 }

dpsRTUp8521nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8521 is set."
	::= { dpsRTU 8521 }

dpsRTUp9521nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8521 clears."
	::= { dpsRTU 9521 }

dpsRTUp8522nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8522 is set."
	::= { dpsRTU 8522 }

dpsRTUp9522nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8522 clears."
	::= { dpsRTU 9522 }

dpsRTUp8523nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8523 is set."
	::= { dpsRTU 8523 }

dpsRTUp9523nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8523 clears."
	::= { dpsRTU 9523 }

dpsRTUp8524nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8524 is set."
	::= { dpsRTU 8524 }

dpsRTUp9524nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8524 clears."
	::= { dpsRTU 9524 }

dpsRTUp8525nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8525 is set."
	::= { dpsRTU 8525 }

dpsRTUp9525nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8525 clears."
	::= { dpsRTU 9525 }

dpsRTUp8526nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8526 is set."
	::= { dpsRTU 8526 }

dpsRTUp9526nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8526 clears."
	::= { dpsRTU 9526 }

dpsRTUp8527nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8527 is set."
	::= { dpsRTU 8527 }

dpsRTUp9527nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8527 clears."
	::= { dpsRTU 9527 }

dpsRTUp8528nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8528 is set."
	::= { dpsRTU 8528 }

dpsRTUp9528nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8528 clears."
	::= { dpsRTU 9528 }

dpsRTUp8529nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8529 is set."
	::= { dpsRTU 8529 }

dpsRTUp9529nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8529 clears."
	::= { dpsRTU 9529 }

dpsRTUp8530nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8530 is set."
	::= { dpsRTU 8530 }

dpsRTUp9530nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8530 clears."
	::= { dpsRTU 9530 }

dpsRTUp8531nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8531 is set."
	::= { dpsRTU 8531 }

dpsRTUp9531nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8531 clears."
	::= { dpsRTU 9531 }

dpsRTUp8532nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8532 is set."
	::= { dpsRTU 8532 }

dpsRTUp9532nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8532 clears."
	::= { dpsRTU 9532 }

dpsRTUp8533nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8533 is set."
	::= { dpsRTU 8533 }

dpsRTUp9533nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8533 clears."
	::= { dpsRTU 9533 }

dpsRTUp8534nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8534 is set."
	::= { dpsRTU 8534 }

dpsRTUp9534nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8534 clears."
	::= { dpsRTU 9534 }

dpsRTUp8535nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8535 is set."
	::= { dpsRTU 8535 }

dpsRTUp9535nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8535 clears."
	::= { dpsRTU 9535 }

dpsRTUp8536nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8536 is set."
	::= { dpsRTU 8536 }

dpsRTUp9536nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8536 clears."
	::= { dpsRTU 9536 }

dpsRTUp8537nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8537 is set."
	::= { dpsRTU 8537 }

dpsRTUp9537nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8537 clears."
	::= { dpsRTU 9537 }

dpsRTUp8538nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8538 is set."
	::= { dpsRTU 8538 }

dpsRTUp9538nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8538 clears."
	::= { dpsRTU 9538 }

dpsRTUp8539nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8539 is set."
	::= { dpsRTU 8539 }

dpsRTUp9539nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8539 clears."
	::= { dpsRTU 9539 }

dpsRTUp8540nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8540 is set."
	::= { dpsRTU 8540 }

dpsRTUp9540nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8540 clears."
	::= { dpsRTU 9540 }

dpsRTUp8541nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8541 is set."
	::= { dpsRTU 8541 }

dpsRTUp9541nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8541 clears."
	::= { dpsRTU 9541 }

dpsRTUp8542nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8542 is set."
	::= { dpsRTU 8542 }

dpsRTUp9542nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8542 clears."
	::= { dpsRTU 9542 }

dpsRTUp8543nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8543 is set."
	::= { dpsRTU 8543 }

dpsRTUp9543nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8543 clears."
	::= { dpsRTU 9543 }

dpsRTUp8544nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8544 is set."
	::= { dpsRTU 8544 }

dpsRTUp9544nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8544 clears."
	::= { dpsRTU 9544 }

dpsRTUp8545nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8545 is set."
	::= { dpsRTU 8545 }

dpsRTUp9545nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8545 clears."
	::= { dpsRTU 9545 }

dpsRTUp8546nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8546 is set."
	::= { dpsRTU 8546 }

dpsRTUp9546nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8546 clears."
	::= { dpsRTU 9546 }

dpsRTUp8547nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8547 is set."
	::= { dpsRTU 8547 }

dpsRTUp9547nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8547 clears."
	::= { dpsRTU 9547 }

dpsRTUp8548nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8548 is set."
	::= { dpsRTU 8548 }

dpsRTUp9548nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8548 clears."
	::= { dpsRTU 9548 }

dpsRTUp8549nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8549 is set."
	::= { dpsRTU 8549 }

dpsRTUp9549nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8549 clears."
	::= { dpsRTU 9549 }

dpsRTUp8550nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8550 is set."
	::= { dpsRTU 8550 }

dpsRTUp9550nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8550 clears."
	::= { dpsRTU 9550 }

dpsRTUp8551nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8551 is set."
	::= { dpsRTU 8551 }

dpsRTUp9551nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8551 clears."
	::= { dpsRTU 9551 }

dpsRTUp8552nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8552 is set."
	::= { dpsRTU 8552 }

dpsRTUp9552nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8552 clears."
	::= { dpsRTU 9552 }

dpsRTUp8553nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8553 is set."
	::= { dpsRTU 8553 }

dpsRTUp9553nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8553 clears."
	::= { dpsRTU 9553 }

dpsRTUp8554nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8554 is set."
	::= { dpsRTU 8554 }

dpsRTUp9554nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8554 clears."
	::= { dpsRTU 9554 }

dpsRTUp8555nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8555 is set."
	::= { dpsRTU 8555 }

dpsRTUp9555nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8555 clears."
	::= { dpsRTU 9555 }

dpsRTUp8556nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8556 is set."
	::= { dpsRTU 8556 }

dpsRTUp9556nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8556 clears."
	::= { dpsRTU 9556 }

dpsRTUp8557nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8557 is set."
	::= { dpsRTU 8557 }

dpsRTUp9557nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8557 clears."
	::= { dpsRTU 9557 }

dpsRTUp8558nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8558 is set."
	::= { dpsRTU 8558 }

dpsRTUp9558nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8558 clears."
	::= { dpsRTU 9558 }

dpsRTUp8559nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8559 is set."
	::= { dpsRTU 8559 }

dpsRTUp9559nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8559 clears."
	::= { dpsRTU 9559 }

dpsRTUp8560nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8560 is set."
	::= { dpsRTU 8560 }

dpsRTUp9560nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8560 clears."
	::= { dpsRTU 9560 }

dpsRTUp8561nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8561 is set."
	::= { dpsRTU 8561 }

dpsRTUp9561nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8561 clears."
	::= { dpsRTU 9561 }

dpsRTUp8562nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8562 is set."
	::= { dpsRTU 8562 }

dpsRTUp9562nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8562 clears."
	::= { dpsRTU 9562 }

dpsRTUp8563nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8563 is set."
	::= { dpsRTU 8563 }

dpsRTUp9563nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8563 clears."
	::= { dpsRTU 9563 }

dpsRTUp8564nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8564 is set."
	::= { dpsRTU 8564 }

dpsRTUp9564nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8564 clears."
	::= { dpsRTU 9564 }

dpsRTUp8565nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8565 is set."
	::= { dpsRTU 8565 }

dpsRTUp9565nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8565 clears."
	::= { dpsRTU 9565 }

dpsRTUp8566nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8566 is set."
	::= { dpsRTU 8566 }

dpsRTUp9566nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8566 clears."
	::= { dpsRTU 9566 }

dpsRTUp8567nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8567 is set."
	::= { dpsRTU 8567 }

dpsRTUp9567nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8567 clears."
	::= { dpsRTU 9567 }

dpsRTUp8568nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8568 is set."
	::= { dpsRTU 8568 }

dpsRTUp9568nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8568 clears."
	::= { dpsRTU 9568 }

dpsRTUp8569nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8569 is set."
	::= { dpsRTU 8569 }

dpsRTUp9569nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8569 clears."
	::= { dpsRTU 9569 }

dpsRTUp8570nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8570 is set."
	::= { dpsRTU 8570 }

dpsRTUp9570nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8570 clears."
	::= { dpsRTU 9570 }

dpsRTUp8571nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8571 is set."
	::= { dpsRTU 8571 }

dpsRTUp9571nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8571 clears."
	::= { dpsRTU 9571 }

dpsRTUp8572nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8572 is set."
	::= { dpsRTU 8572 }

dpsRTUp9572nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8572 clears."
	::= { dpsRTU 9572 }

dpsRTUp8573nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8573 is set."
	::= { dpsRTU 8573 }

dpsRTUp9573nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8573 clears."
	::= { dpsRTU 9573 }

dpsRTUp8574nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8574 is set."
	::= { dpsRTU 8574 }

dpsRTUp9574nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8574 clears."
	::= { dpsRTU 9574 }

dpsRTUp8575nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8575 is set."
	::= { dpsRTU 8575 }

dpsRTUp9575nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8575 clears."
	::= { dpsRTU 9575 }

dpsRTUp8576nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8576 is set."
	::= { dpsRTU 8576 }

dpsRTUp9576nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8576 clears."
	::= { dpsRTU 9576 }

dpsRTUp8577nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8577 is set."
	::= { dpsRTU 8577 }

dpsRTUp9577nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8577 clears."
	::= { dpsRTU 9577 }

dpsRTUp8578nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8578 is set."
	::= { dpsRTU 8578 }

dpsRTUp9578nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8578 clears."
	::= { dpsRTU 9578 }

dpsRTUp8579nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8579 is set."
	::= { dpsRTU 8579 }

dpsRTUp9579nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8579 clears."
	::= { dpsRTU 9579 }

dpsRTUp8580nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8580 is set."
	::= { dpsRTU 8580 }

dpsRTUp9580nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8580 clears."
	::= { dpsRTU 9580 }

dpsRTUp8581nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8581 is set."
	::= { dpsRTU 8581 }

dpsRTUp9581nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8581 clears."
	::= { dpsRTU 9581 }

dpsRTUp8582nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8582 is set."
	::= { dpsRTU 8582 }

dpsRTUp9582nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8582 clears."
	::= { dpsRTU 9582 }

dpsRTUp8583nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8583 is set."
	::= { dpsRTU 8583 }

dpsRTUp9583nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8583 clears."
	::= { dpsRTU 9583 }

dpsRTUp8584nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8584 is set."
	::= { dpsRTU 8584 }

dpsRTUp9584nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8584 clears."
	::= { dpsRTU 9584 }

dpsRTUp8585nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8585 is set."
	::= { dpsRTU 8585 }

dpsRTUp9585nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8585 clears."
	::= { dpsRTU 9585 }

dpsRTUp8586nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8586 is set."
	::= { dpsRTU 8586 }

dpsRTUp9586nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8586 clears."
	::= { dpsRTU 9586 }

dpsRTUp8587nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8587 is set."
	::= { dpsRTU 8587 }

dpsRTUp9587nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8587 clears."
	::= { dpsRTU 9587 }

dpsRTUp8588nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8588 is set."
	::= { dpsRTU 8588 }

dpsRTUp9588nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8588 clears."
	::= { dpsRTU 9588 }

dpsRTUp8589nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8589 is set."
	::= { dpsRTU 8589 }

dpsRTUp9589nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8589 clears."
	::= { dpsRTU 9589 }

dpsRTUp8590nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8590 is set."
	::= { dpsRTU 8590 }

dpsRTUp9590nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8590 clears."
	::= { dpsRTU 9590 }

dpsRTUp8591nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8591 is set."
	::= { dpsRTU 8591 }

dpsRTUp9591nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8591 clears."
	::= { dpsRTU 9591 }

dpsRTUp8592nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8592 is set."
	::= { dpsRTU 8592 }

dpsRTUp9592nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8592 clears."
	::= { dpsRTU 9592 }

dpsRTUp8593nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8593 is set."
	::= { dpsRTU 8593 }

dpsRTUp9593nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8593 clears."
	::= { dpsRTU 9593 }

dpsRTUp8594nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8594 is set."
	::= { dpsRTU 8594 }

dpsRTUp9594nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8594 clears."
	::= { dpsRTU 9594 }

dpsRTUp8595nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8595 is set."
	::= { dpsRTU 8595 }

dpsRTUp9595nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8595 clears."
	::= { dpsRTU 9595 }

dpsRTUp8596nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8596 is set."
	::= { dpsRTU 8596 }

dpsRTUp9596nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8596 clears."
	::= { dpsRTU 9596 }

dpsRTUp8597nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8597 is set."
	::= { dpsRTU 8597 }

dpsRTUp9597nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8597 clears."
	::= { dpsRTU 9597 }

dpsRTUp8598nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8598 is set."
	::= { dpsRTU 8598 }

dpsRTUp9598nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8598 clears."
	::= { dpsRTU 9598 }

dpsRTUp8599nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8599 is set."
	::= { dpsRTU 8599 }

dpsRTUp9599nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8599 clears."
	::= { dpsRTU 9599 }

dpsRTUp8600nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8600 is set."
	::= { dpsRTU 8600 }

dpsRTUp9600nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8600 clears."
	::= { dpsRTU 9600 }

dpsRTUp8601nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8601 is set."
	::= { dpsRTU 8601 }

dpsRTUp9601nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8601 clears."
	::= { dpsRTU 9601 }

dpsRTUp8602nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8602 is set."
	::= { dpsRTU 8602 }

dpsRTUp9602nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8602 clears."
	::= { dpsRTU 9602 }

dpsRTUp8603nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8603 is set."
	::= { dpsRTU 8603 }

dpsRTUp9603nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8603 clears."
	::= { dpsRTU 9603 }

dpsRTUp8604nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8604 is set."
	::= { dpsRTU 8604 }

dpsRTUp9604nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8604 clears."
	::= { dpsRTU 9604 }

dpsRTUp8605nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8605 is set."
	::= { dpsRTU 8605 }

dpsRTUp9605nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8605 clears."
	::= { dpsRTU 9605 }

dpsRTUp8606nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8606 is set."
	::= { dpsRTU 8606 }

dpsRTUp9606nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8606 clears."
	::= { dpsRTU 9606 }

dpsRTUp8607nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8607 is set."
	::= { dpsRTU 8607 }

dpsRTUp9607nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8607 clears."
	::= { dpsRTU 9607 }

dpsRTUp8608nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8608 is set."
	::= { dpsRTU 8608 }

dpsRTUp9608nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8608 clears."
	::= { dpsRTU 9608 }

dpsRTUp8609nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8609 is set."
	::= { dpsRTU 8609 }

dpsRTUp9609nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8609 clears."
	::= { dpsRTU 9609 }

dpsRTUp8610nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8610 is set."
	::= { dpsRTU 8610 }

dpsRTUp9610nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8610 clears."
	::= { dpsRTU 9610 }

dpsRTUp8611nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8611 is set."
	::= { dpsRTU 8611 }

dpsRTUp9611nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8611 clears."
	::= { dpsRTU 9611 }

dpsRTUp8612nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8612 is set."
	::= { dpsRTU 8612 }

dpsRTUp9612nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8612 clears."
	::= { dpsRTU 9612 }

dpsRTUp8613nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8613 is set."
	::= { dpsRTU 8613 }

dpsRTUp9613nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8613 clears."
	::= { dpsRTU 9613 }

dpsRTUp8614nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8614 is set."
	::= { dpsRTU 8614 }

dpsRTUp9614nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8614 clears."
	::= { dpsRTU 9614 }

dpsRTUp8615nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8615 is set."
	::= { dpsRTU 8615 }

dpsRTUp9615nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8615 clears."
	::= { dpsRTU 9615 }

dpsRTUp8616nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8616 is set."
	::= { dpsRTU 8616 }

dpsRTUp9616nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8616 clears."
	::= { dpsRTU 9616 }

dpsRTUp8617nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8617 is set."
	::= { dpsRTU 8617 }

dpsRTUp9617nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8617 clears."
	::= { dpsRTU 9617 }

dpsRTUp8618nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8618 is set."
	::= { dpsRTU 8618 }

dpsRTUp9618nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8618 clears."
	::= { dpsRTU 9618 }

dpsRTUp8619nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8619 is set."
	::= { dpsRTU 8619 }

dpsRTUp9619nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8619 clears."
	::= { dpsRTU 9619 }

dpsRTUp8620nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8620 is set."
	::= { dpsRTU 8620 }

dpsRTUp9620nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8620 clears."
	::= { dpsRTU 9620 }

dpsRTUp8621nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8621 is set."
	::= { dpsRTU 8621 }

dpsRTUp9621nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8621 clears."
	::= { dpsRTU 9621 }

dpsRTUp8622nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8622 is set."
	::= { dpsRTU 8622 }

dpsRTUp9622nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8622 clears."
	::= { dpsRTU 9622 }

dpsRTUp8623nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8623 is set."
	::= { dpsRTU 8623 }

dpsRTUp9623nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8623 clears."
	::= { dpsRTU 9623 }

dpsRTUp8624nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8624 is set."
	::= { dpsRTU 8624 }

dpsRTUp9624nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8624 clears."
	::= { dpsRTU 9624 }

dpsRTUp8625nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8625 is set."
	::= { dpsRTU 8625 }

dpsRTUp9625nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8625 clears."
	::= { dpsRTU 9625 }

dpsRTUp8626nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8626 is set."
	::= { dpsRTU 8626 }

dpsRTUp9626nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8626 clears."
	::= { dpsRTU 9626 }

dpsRTUp8627nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8627 is set."
	::= { dpsRTU 8627 }

dpsRTUp9627nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8627 clears."
	::= { dpsRTU 9627 }

dpsRTUp8628nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8628 is set."
	::= { dpsRTU 8628 }

dpsRTUp9628nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8628 clears."
	::= { dpsRTU 9628 }

dpsRTUp8629nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8629 is set."
	::= { dpsRTU 8629 }

dpsRTUp9629nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8629 clears."
	::= { dpsRTU 9629 }

dpsRTUp8630nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8630 is set."
	::= { dpsRTU 8630 }

dpsRTUp9630nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8630 clears."
	::= { dpsRTU 9630 }

dpsRTUp8631nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8631 is set."
	::= { dpsRTU 8631 }

dpsRTUp9631nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8631 clears."
	::= { dpsRTU 9631 }

dpsRTUp8632nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8632 is set."
	::= { dpsRTU 8632 }

dpsRTUp9632nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8632 clears."
	::= { dpsRTU 9632 }

dpsRTUp8633nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8633 is set."
	::= { dpsRTU 8633 }

dpsRTUp9633nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8633 clears."
	::= { dpsRTU 9633 }

dpsRTUp8634nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8634 is set."
	::= { dpsRTU 8634 }

dpsRTUp9634nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8634 clears."
	::= { dpsRTU 9634 }

dpsRTUp8635nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8635 is set."
	::= { dpsRTU 8635 }

dpsRTUp9635nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8635 clears."
	::= { dpsRTU 9635 }

dpsRTUp8636nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8636 is set."
	::= { dpsRTU 8636 }

dpsRTUp9636nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8636 clears."
	::= { dpsRTU 9636 }

dpsRTUp8637nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8637 is set."
	::= { dpsRTU 8637 }

dpsRTUp9637nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8637 clears."
	::= { dpsRTU 9637 }

dpsRTUp8638nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8638 is set."
	::= { dpsRTU 8638 }

dpsRTUp9638nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8638 clears."
	::= { dpsRTU 9638 }

dpsRTUp8639nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8639 is set."
	::= { dpsRTU 8639 }

dpsRTUp9639nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8639 clears."
	::= { dpsRTU 9639 }

dpsRTUp8640nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8640 is set."
	::= { dpsRTU 8640 }

dpsRTUp9640nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8640 clears."
	::= { dpsRTU 9640 }

dpsRTUp8641nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8641 is set."
	::= { dpsRTU 8641 }

dpsRTUp9641nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8641 clears."
	::= { dpsRTU 9641 }

dpsRTUp8642nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8642 is set."
	::= { dpsRTU 8642 }

dpsRTUp9642nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8642 clears."
	::= { dpsRTU 9642 }

dpsRTUp8643nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8643 is set."
	::= { dpsRTU 8643 }

dpsRTUp9643nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8643 clears."
	::= { dpsRTU 9643 }

dpsRTUp8644nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8644 is set."
	::= { dpsRTU 8644 }

dpsRTUp9644nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8644 clears."
	::= { dpsRTU 9644 }

dpsRTUp8645nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8645 is set."
	::= { dpsRTU 8645 }

dpsRTUp9645nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8645 clears."
	::= { dpsRTU 9645 }

dpsRTUp8646nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8646 is set."
	::= { dpsRTU 8646 }

dpsRTUp9646nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8646 clears."
	::= { dpsRTU 9646 }

dpsRTUp8647nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8647 is set."
	::= { dpsRTU 8647 }

dpsRTUp9647nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8647 clears."
	::= { dpsRTU 9647 }

dpsRTUp8648nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8648 is set."
	::= { dpsRTU 8648 }

dpsRTUp9648nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8648 clears."
	::= { dpsRTU 9648 }

dpsRTUp8649nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8649 is set."
	::= { dpsRTU 8649 }

dpsRTUp9649nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8649 clears."
	::= { dpsRTU 9649 }

dpsRTUp8650nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8650 is set."
	::= { dpsRTU 8650 }

dpsRTUp9650nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8650 clears."
	::= { dpsRTU 9650 }

dpsRTUp8651nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8651 is set."
	::= { dpsRTU 8651 }

dpsRTUp9651nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8651 clears."
	::= { dpsRTU 9651 }

dpsRTUp8652nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8652 is set."
	::= { dpsRTU 8652 }

dpsRTUp9652nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8652 clears."
	::= { dpsRTU 9652 }

dpsRTUp8653nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8653 is set."
	::= { dpsRTU 8653 }

dpsRTUp9653nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8653 clears."
	::= { dpsRTU 9653 }

dpsRTUp8654nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8654 is set."
	::= { dpsRTU 8654 }

dpsRTUp9654nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8654 clears."
	::= { dpsRTU 9654 }

dpsRTUp8655nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8655 is set."
	::= { dpsRTU 8655 }

dpsRTUp9655nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8655 clears."
	::= { dpsRTU 9655 }

dpsRTUp8656nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8656 is set."
	::= { dpsRTU 8656 }

dpsRTUp9656nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8656 clears."
	::= { dpsRTU 9656 }

dpsRTUp8657nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8657 is set."
	::= { dpsRTU 8657 }

dpsRTUp9657nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8657 clears."
	::= { dpsRTU 9657 }

dpsRTUp8658nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8658 is set."
	::= { dpsRTU 8658 }

dpsRTUp9658nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8658 clears."
	::= { dpsRTU 9658 }

dpsRTUp8659nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8659 is set."
	::= { dpsRTU 8659 }

dpsRTUp9659nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8659 clears."
	::= { dpsRTU 9659 }

dpsRTUp8660nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8660 is set."
	::= { dpsRTU 8660 }

dpsRTUp9660nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8660 clears."
	::= { dpsRTU 9660 }

dpsRTUp8661nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8661 is set."
	::= { dpsRTU 8661 }

dpsRTUp9661nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8661 clears."
	::= { dpsRTU 9661 }

dpsRTUp8662nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8662 is set."
	::= { dpsRTU 8662 }

dpsRTUp9662nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8662 clears."
	::= { dpsRTU 9662 }

dpsRTUp8663nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8663 is set."
	::= { dpsRTU 8663 }

dpsRTUp9663nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8663 clears."
	::= { dpsRTU 9663 }

dpsRTUp8664nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8664 is set."
	::= { dpsRTU 8664 }

dpsRTUp9664nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8664 clears."
	::= { dpsRTU 9664 }

dpsRTUp8665nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8665 is set."
	::= { dpsRTU 8665 }

dpsRTUp9665nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8665 clears."
	::= { dpsRTU 9665 }

dpsRTUp8666nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8666 is set."
	::= { dpsRTU 8666 }

dpsRTUp9666nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8666 clears."
	::= { dpsRTU 9666 }

dpsRTUp8667nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8667 is set."
	::= { dpsRTU 8667 }

dpsRTUp9667nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8667 clears."
	::= { dpsRTU 9667 }

dpsRTUp8668nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8668 is set."
	::= { dpsRTU 8668 }

dpsRTUp9668nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8668 clears."
	::= { dpsRTU 9668 }

dpsRTUp8669nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8669 is set."
	::= { dpsRTU 8669 }

dpsRTUp9669nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8669 clears."
	::= { dpsRTU 9669 }

dpsRTUp8670nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8670 is set."
	::= { dpsRTU 8670 }

dpsRTUp9670nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8670 clears."
	::= { dpsRTU 9670 }

dpsRTUp8671nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8671 is set."
	::= { dpsRTU 8671 }

dpsRTUp9671nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8671 clears."
	::= { dpsRTU 9671 }

dpsRTUp8672nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8672 is set."
	::= { dpsRTU 8672 }

dpsRTUp9672nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8672 clears."
	::= { dpsRTU 9672 }

dpsRTUp8673nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8673 is set."
	::= { dpsRTU 8673 }

dpsRTUp9673nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8673 clears."
	::= { dpsRTU 9673 }

dpsRTUp8674nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8674 is set."
	::= { dpsRTU 8674 }

dpsRTUp9674nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8674 clears."
	::= { dpsRTU 9674 }

dpsRTUp8675nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8675 is set."
	::= { dpsRTU 8675 }

dpsRTUp9675nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8675 clears."
	::= { dpsRTU 9675 }

dpsRTUp8676nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8676 is set."
	::= { dpsRTU 8676 }

dpsRTUp9676nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8676 clears."
	::= { dpsRTU 9676 }

dpsRTUp8677nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8677 is set."
	::= { dpsRTU 8677 }

dpsRTUp9677nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8677 clears."
	::= { dpsRTU 9677 }

dpsRTUp8678nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8678 is set."
	::= { dpsRTU 8678 }

dpsRTUp9678nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8678 clears."
	::= { dpsRTU 9678 }

dpsRTUp8679nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8679 is set."
	::= { dpsRTU 8679 }

dpsRTUp9679nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8679 clears."
	::= { dpsRTU 9679 }

dpsRTUp8680nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8680 is set."
	::= { dpsRTU 8680 }

dpsRTUp9680nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8680 clears."
	::= { dpsRTU 9680 }

dpsRTUp8681nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8681 is set."
	::= { dpsRTU 8681 }

dpsRTUp9681nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8681 clears."
	::= { dpsRTU 9681 }

dpsRTUp8682nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8682 is set."
	::= { dpsRTU 8682 }

dpsRTUp9682nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8682 clears."
	::= { dpsRTU 9682 }

dpsRTUp8683nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8683 is set."
	::= { dpsRTU 8683 }

dpsRTUp9683nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8683 clears."
	::= { dpsRTU 9683 }

dpsRTUp8684nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8684 is set."
	::= { dpsRTU 8684 }

dpsRTUp9684nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8684 clears."
	::= { dpsRTU 9684 }

dpsRTUp8685nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8685 is set."
	::= { dpsRTU 8685 }

dpsRTUp9685nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8685 clears."
	::= { dpsRTU 9685 }

dpsRTUp8686nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8686 is set."
	::= { dpsRTU 8686 }

dpsRTUp9686nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8686 clears."
	::= { dpsRTU 9686 }

dpsRTUp8687nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8687 is set."
	::= { dpsRTU 8687 }

dpsRTUp9687nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8687 clears."
	::= { dpsRTU 9687 }

dpsRTUp8688nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8688 is set."
	::= { dpsRTU 8688 }

dpsRTUp9688nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8688 clears."
	::= { dpsRTU 9688 }

dpsRTUp8689nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8689 is set."
	::= { dpsRTU 8689 }

dpsRTUp9689nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8689 clears."
	::= { dpsRTU 9689 }

dpsRTUp8690nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8690 is set."
	::= { dpsRTU 8690 }

dpsRTUp9690nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8690 clears."
	::= { dpsRTU 9690 }

dpsRTUp8691nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8691 is set."
	::= { dpsRTU 8691 }

dpsRTUp9691nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8691 clears."
	::= { dpsRTU 9691 }

dpsRTUp8692nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8692 is set."
	::= { dpsRTU 8692 }

dpsRTUp9692nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8692 clears."
	::= { dpsRTU 9692 }

dpsRTUp8693nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8693 is set."
	::= { dpsRTU 8693 }

dpsRTUp9693nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8693 clears."
	::= { dpsRTU 9693 }

dpsRTUp8694nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8694 is set."
	::= { dpsRTU 8694 }

dpsRTUp9694nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8694 clears."
	::= { dpsRTU 9694 }

dpsRTUp8695nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8695 is set."
	::= { dpsRTU 8695 }

dpsRTUp9695nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8695 clears."
	::= { dpsRTU 9695 }

dpsRTUp8696nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8696 is set."
	::= { dpsRTU 8696 }

dpsRTUp9696nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8696 clears."
	::= { dpsRTU 9696 }

dpsRTUp8697nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8697 is set."
	::= { dpsRTU 8697 }

dpsRTUp9697nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8697 clears."
	::= { dpsRTU 9697 }

dpsRTUp8698nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8698 is set."
	::= { dpsRTU 8698 }

dpsRTUp9698nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8698 clears."
	::= { dpsRTU 9698 }

dpsRTUp8699nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8699 is set."
	::= { dpsRTU 8699 }

dpsRTUp9699nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8699 clears."
	::= { dpsRTU 9699 }

dpsRTUp8700nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8700 is set."
	::= { dpsRTU 8700 }

dpsRTUp9700nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8700 clears."
	::= { dpsRTU 9700 }

dpsRTUp8701nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8701 is set."
	::= { dpsRTU 8701 }

dpsRTUp9701nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8701 clears."
	::= { dpsRTU 9701 }

dpsRTUp8702nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8702 is set."
	::= { dpsRTU 8702 }

dpsRTUp9702nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8702 clears."
	::= { dpsRTU 9702 }

dpsRTUp8703nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8703 is set."
	::= { dpsRTU 8703 }

dpsRTUp9703nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8703 clears."
	::= { dpsRTU 9703 }

dpsRTUp8704nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8704 is set."
	::= { dpsRTU 8704 }

dpsRTUp9704nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8704 clears."
	::= { dpsRTU 9704 }

dpsRTUp8705nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8705 is set."
	::= { dpsRTU 8705 }

dpsRTUp9705nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8705 clears."
	::= { dpsRTU 9705 }

dpsRTUp8706nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8706 is set."
	::= { dpsRTU 8706 }

dpsRTUp9706nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8706 clears."
	::= { dpsRTU 9706 }

dpsRTUp8707nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8707 is set."
	::= { dpsRTU 8707 }

dpsRTUp9707nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8707 clears."
	::= { dpsRTU 9707 }

dpsRTUp8708nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8708 is set."
	::= { dpsRTU 8708 }

dpsRTUp9708nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8708 clears."
	::= { dpsRTU 9708 }

dpsRTUp8709nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8709 is set."
	::= { dpsRTU 8709 }

dpsRTUp9709nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8709 clears."
	::= { dpsRTU 9709 }

dpsRTUp8710nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8710 is set."
	::= { dpsRTU 8710 }

dpsRTUp9710nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8710 clears."
	::= { dpsRTU 9710 }

dpsRTUp8711nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8711 is set."
	::= { dpsRTU 8711 }

dpsRTUp9711nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8711 clears."
	::= { dpsRTU 9711 }

dpsRTUp8712nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8712 is set."
	::= { dpsRTU 8712 }

dpsRTUp9712nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8712 clears."
	::= { dpsRTU 9712 }

dpsRTUp8713nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8713 is set."
	::= { dpsRTU 8713 }

dpsRTUp9713nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8713 clears."
	::= { dpsRTU 9713 }

dpsRTUp8714nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8714 is set."
	::= { dpsRTU 8714 }

dpsRTUp9714nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8714 clears."
	::= { dpsRTU 9714 }

dpsRTUp8715nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8715 is set."
	::= { dpsRTU 8715 }

dpsRTUp9715nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8715 clears."
	::= { dpsRTU 9715 }

dpsRTUp8716nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8716 is set."
	::= { dpsRTU 8716 }

dpsRTUp9716nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8716 clears."
	::= { dpsRTU 9716 }

dpsRTUp8717nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8717 is set."
	::= { dpsRTU 8717 }

dpsRTUp9717nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8717 clears."
	::= { dpsRTU 9717 }

dpsRTUp8718nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8718 is set."
	::= { dpsRTU 8718 }

dpsRTUp9718nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8718 clears."
	::= { dpsRTU 9718 }

dpsRTUp8719nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8719 is set."
	::= { dpsRTU 8719 }

dpsRTUp9719nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8719 clears."
	::= { dpsRTU 9719 }

dpsRTUp8720nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8720 is set."
	::= { dpsRTU 8720 }

dpsRTUp9720nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8720 clears."
	::= { dpsRTU 9720 }

dpsRTUp8721nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8721 is set."
	::= { dpsRTU 8721 }

dpsRTUp9721nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8721 clears."
	::= { dpsRTU 9721 }

dpsRTUp8722nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8722 is set."
	::= { dpsRTU 8722 }

dpsRTUp9722nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8722 clears."
	::= { dpsRTU 9722 }

dpsRTUp8723nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8723 is set."
	::= { dpsRTU 8723 }

dpsRTUp9723nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8723 clears."
	::= { dpsRTU 9723 }

dpsRTUp8724nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8724 is set."
	::= { dpsRTU 8724 }

dpsRTUp9724nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8724 clears."
	::= { dpsRTU 9724 }

dpsRTUp8725nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8725 is set."
	::= { dpsRTU 8725 }

dpsRTUp9725nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8725 clears."
	::= { dpsRTU 9725 }

dpsRTUp8726nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8726 is set."
	::= { dpsRTU 8726 }

dpsRTUp9726nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8726 clears."
	::= { dpsRTU 9726 }

dpsRTUp8727nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8727 is set."
	::= { dpsRTU 8727 }

dpsRTUp9727nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8727 clears."
	::= { dpsRTU 9727 }

dpsRTUp8728nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8728 is set."
	::= { dpsRTU 8728 }

dpsRTUp9728nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8728 clears."
	::= { dpsRTU 9728 }

dpsRTUp8729nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8729 is set."
	::= { dpsRTU 8729 }

dpsRTUp9729nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8729 clears."
	::= { dpsRTU 9729 }

dpsRTUp8730nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8730 is set."
	::= { dpsRTU 8730 }

dpsRTUp9730nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8730 clears."
	::= { dpsRTU 9730 }

dpsRTUp8731nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8731 is set."
	::= { dpsRTU 8731 }

dpsRTUp9731nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8731 clears."
	::= { dpsRTU 9731 }

dpsRTUp8732nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8732 is set."
	::= { dpsRTU 8732 }

dpsRTUp9732nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8732 clears."
	::= { dpsRTU 9732 }

dpsRTUp8733nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8733 is set."
	::= { dpsRTU 8733 }

dpsRTUp9733nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8733 clears."
	::= { dpsRTU 9733 }

dpsRTUp8734nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8734 is set."
	::= { dpsRTU 8734 }

dpsRTUp9734nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8734 clears."
	::= { dpsRTU 9734 }

dpsRTUp8735nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8735 is set."
	::= { dpsRTU 8735 }

dpsRTUp9735nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8735 clears."
	::= { dpsRTU 9735 }

dpsRTUp8736nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8736 is set."
	::= { dpsRTU 8736 }

dpsRTUp9736nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8736 clears."
	::= { dpsRTU 9736 }

dpsRTUp8737nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8737 is set."
	::= { dpsRTU 8737 }

dpsRTUp9737nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8737 clears."
	::= { dpsRTU 9737 }

dpsRTUp8738nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8738 is set."
	::= { dpsRTU 8738 }

dpsRTUp9738nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8738 clears."
	::= { dpsRTU 9738 }

dpsRTUp8739nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8739 is set."
	::= { dpsRTU 8739 }

dpsRTUp9739nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8739 clears."
	::= { dpsRTU 9739 }

dpsRTUp8740nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8740 is set."
	::= { dpsRTU 8740 }

dpsRTUp9740nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8740 clears."
	::= { dpsRTU 9740 }

dpsRTUp8741nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8741 is set."
	::= { dpsRTU 8741 }

dpsRTUp9741nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8741 clears."
	::= { dpsRTU 9741 }

dpsRTUp8742nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8742 is set."
	::= { dpsRTU 8742 }

dpsRTUp9742nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8742 clears."
	::= { dpsRTU 9742 }

dpsRTUp8743nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8743 is set."
	::= { dpsRTU 8743 }

dpsRTUp9743nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8743 clears."
	::= { dpsRTU 9743 }

dpsRTUp8744nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8744 is set."
	::= { dpsRTU 8744 }

dpsRTUp9744nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8744 clears."
	::= { dpsRTU 9744 }

dpsRTUp8745nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8745 is set."
	::= { dpsRTU 8745 }

dpsRTUp9745nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8745 clears."
	::= { dpsRTU 9745 }

dpsRTUp8746nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8746 is set."
	::= { dpsRTU 8746 }

dpsRTUp9746nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8746 clears."
	::= { dpsRTU 9746 }

dpsRTUp8747nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8747 is set."
	::= { dpsRTU 8747 }

dpsRTUp9747nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8747 clears."
	::= { dpsRTU 9747 }

dpsRTUp8748nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8748 is set."
	::= { dpsRTU 8748 }

dpsRTUp9748nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8748 clears."
	::= { dpsRTU 9748 }

dpsRTUp8749nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8749 is set."
	::= { dpsRTU 8749 }

dpsRTUp9749nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8749 clears."
	::= { dpsRTU 9749 }

dpsRTUp8750nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8750 is set."
	::= { dpsRTU 8750 }

dpsRTUp9750nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8750 clears."
	::= { dpsRTU 9750 }

dpsRTUp8751nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8751 is set."
	::= { dpsRTU 8751 }

dpsRTUp9751nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8751 clears."
	::= { dpsRTU 9751 }

dpsRTUp8752nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8752 is set."
	::= { dpsRTU 8752 }

dpsRTUp9752nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8752 clears."
	::= { dpsRTU 9752 }

dpsRTUp8753nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8753 is set."
	::= { dpsRTU 8753 }

dpsRTUp9753nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8753 clears."
	::= { dpsRTU 9753 }

dpsRTUp8754nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8754 is set."
	::= { dpsRTU 8754 }

dpsRTUp9754nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8754 clears."
	::= { dpsRTU 9754 }

dpsRTUp8755nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8755 is set."
	::= { dpsRTU 8755 }

dpsRTUp9755nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8755 clears."
	::= { dpsRTU 9755 }

dpsRTUp8756nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8756 is set."
	::= { dpsRTU 8756 }

dpsRTUp9756nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8756 clears."
	::= { dpsRTU 9756 }

dpsRTUp8757nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8757 is set."
	::= { dpsRTU 8757 }

dpsRTUp9757nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8757 clears."
	::= { dpsRTU 9757 }

dpsRTUp8758nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8758 is set."
	::= { dpsRTU 8758 }

dpsRTUp9758nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8758 clears."
	::= { dpsRTU 9758 }

dpsRTUp8759nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8759 is set."
	::= { dpsRTU 8759 }

dpsRTUp9759nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8759 clears."
	::= { dpsRTU 9759 }

dpsRTUp8760nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8760 is set."
	::= { dpsRTU 8760 }

dpsRTUp9760nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8760 clears."
	::= { dpsRTU 9760 }

dpsRTUp8761nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8761 is set."
	::= { dpsRTU 8761 }

dpsRTUp9761nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8761 clears."
	::= { dpsRTU 9761 }

dpsRTUp8762nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8762 is set."
	::= { dpsRTU 8762 }

dpsRTUp9762nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8762 clears."
	::= { dpsRTU 9762 }

dpsRTUp8763nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8763 is set."
	::= { dpsRTU 8763 }

dpsRTUp9763nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8763 clears."
	::= { dpsRTU 9763 }

dpsRTUp8764nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8764 is set."
	::= { dpsRTU 8764 }

dpsRTUp9764nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8764 clears."
	::= { dpsRTU 9764 }

dpsRTUp8765nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8765 is set."
	::= { dpsRTU 8765 }

dpsRTUp9765nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8765 clears."
	::= { dpsRTU 9765 }

dpsRTUp8766nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8766 is set."
	::= { dpsRTU 8766 }

dpsRTUp9766nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8766 clears."
	::= { dpsRTU 9766 }

dpsRTUp8767nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8767 is set."
	::= { dpsRTU 8767 }

dpsRTUp9767nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8767 clears."
	::= { dpsRTU 9767 }

dpsRTUp8768nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8768 is set."
	::= { dpsRTU 8768 }

dpsRTUp9768nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8768 clears."
	::= { dpsRTU 9768 }

dpsRTUp8769nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8769 is set."
	::= { dpsRTU 8769 }

dpsRTUp9769nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8769 clears."
	::= { dpsRTU 9769 }

dpsRTUp8770nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8770 is set."
	::= { dpsRTU 8770 }

dpsRTUp9770nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8770 clears."
	::= { dpsRTU 9770 }

dpsRTUp8771nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8771 is set."
	::= { dpsRTU 8771 }

dpsRTUp9771nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8771 clears."
	::= { dpsRTU 9771 }

dpsRTUp8772nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8772 is set."
	::= { dpsRTU 8772 }

dpsRTUp9772nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8772 clears."
	::= { dpsRTU 9772 }

dpsRTUp8773nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8773 is set."
	::= { dpsRTU 8773 }

dpsRTUp9773nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8773 clears."
	::= { dpsRTU 9773 }

dpsRTUp8774nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8774 is set."
	::= { dpsRTU 8774 }

dpsRTUp9774nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8774 clears."
	::= { dpsRTU 9774 }

dpsRTUp8775nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8775 is set."
	::= { dpsRTU 8775 }

dpsRTUp9775nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8775 clears."
	::= { dpsRTU 9775 }

dpsRTUp8776nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8776 is set."
	::= { dpsRTU 8776 }

dpsRTUp9776nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8776 clears."
	::= { dpsRTU 9776 }

dpsRTUp8777nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8777 is set."
	::= { dpsRTU 8777 }

dpsRTUp9777nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8777 clears."
	::= { dpsRTU 9777 }

dpsRTUp8778nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8778 is set."
	::= { dpsRTU 8778 }

dpsRTUp9778nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8778 clears."
	::= { dpsRTU 9778 }

dpsRTUp8779nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8779 is set."
	::= { dpsRTU 8779 }

dpsRTUp9779nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8779 clears."
	::= { dpsRTU 9779 }

dpsRTUp8780nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8780 is set."
	::= { dpsRTU 8780 }

dpsRTUp9780nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8780 clears."
	::= { dpsRTU 9780 }

dpsRTUp8781nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8781 is set."
	::= { dpsRTU 8781 }

dpsRTUp9781nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8781 clears."
	::= { dpsRTU 9781 }

dpsRTUp8782nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8782 is set."
	::= { dpsRTU 8782 }

dpsRTUp9782nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8782 clears."
	::= { dpsRTU 9782 }

dpsRTUp8783nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8783 is set."
	::= { dpsRTU 8783 }

dpsRTUp9783nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8783 clears."
	::= { dpsRTU 9783 }

dpsRTUp8784nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8784 is set."
	::= { dpsRTU 8784 }

dpsRTUp9784nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8784 clears."
	::= { dpsRTU 9784 }

dpsRTUp8785nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8785 is set."
	::= { dpsRTU 8785 }

dpsRTUp9785nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8785 clears."
	::= { dpsRTU 9785 }

dpsRTUp8786nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8786 is set."
	::= { dpsRTU 8786 }

dpsRTUp9786nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8786 clears."
	::= { dpsRTU 9786 }

dpsRTUp8787nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8787 is set."
	::= { dpsRTU 8787 }

dpsRTUp9787nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8787 clears."
	::= { dpsRTU 9787 }

dpsRTUp8788nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8788 is set."
	::= { dpsRTU 8788 }

dpsRTUp9788nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8788 clears."
	::= { dpsRTU 9788 }

dpsRTUp8789nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8789 is set."
	::= { dpsRTU 8789 }

dpsRTUp9789nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8789 clears."
	::= { dpsRTU 9789 }

dpsRTUp8790nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8790 is set."
	::= { dpsRTU 8790 }

dpsRTUp9790nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8790 clears."
	::= { dpsRTU 9790 }

dpsRTUp8791nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8791 is set."
	::= { dpsRTU 8791 }

dpsRTUp9791nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8791 clears."
	::= { dpsRTU 9791 }

dpsRTUp8792nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8792 is set."
	::= { dpsRTU 8792 }

dpsRTUp9792nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8792 clears."
	::= { dpsRTU 9792 }

dpsRTUp8793nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8793 is set."
	::= { dpsRTU 8793 }

dpsRTUp9793nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8793 clears."
	::= { dpsRTU 9793 }

dpsRTUp8794nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8794 is set."
	::= { dpsRTU 8794 }

dpsRTUp9794nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8794 clears."
	::= { dpsRTU 9794 }

dpsRTUp8795nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8795 is set."
	::= { dpsRTU 8795 }

dpsRTUp9795nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8795 clears."
	::= { dpsRTU 9795 }

dpsRTUp8796nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8796 is set."
	::= { dpsRTU 8796 }

dpsRTUp9796nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8796 clears."
	::= { dpsRTU 9796 }

dpsRTUp8797nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8797 is set."
	::= { dpsRTU 8797 }

dpsRTUp9797nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8797 clears."
	::= { dpsRTU 9797 }

dpsRTUp8798nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8798 is set."
	::= { dpsRTU 8798 }

dpsRTUp9798nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8798 clears."
	::= { dpsRTU 9798 }

dpsRTUp8799nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8799 is set."
	::= { dpsRTU 8799 }

dpsRTUp9799nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8799 clears."
	::= { dpsRTU 9799 }

dpsRTUp8800nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8800 is set."
	::= { dpsRTU 8800 }

dpsRTUp9800nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8800 clears."
	::= { dpsRTU 9800 }

dpsRTUp8801nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8801 is set."
	::= { dpsRTU 8801 }

dpsRTUp9801nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8801 clears."
	::= { dpsRTU 9801 }

dpsRTUp8802nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8802 is set."
	::= { dpsRTU 8802 }

dpsRTUp9802nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8802 clears."
	::= { dpsRTU 9802 }

dpsRTUp8803nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8803 is set."
	::= { dpsRTU 8803 }

dpsRTUp9803nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8803 clears."
	::= { dpsRTU 9803 }

dpsRTUp8804nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8804 is set."
	::= { dpsRTU 8804 }

dpsRTUp9804nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8804 clears."
	::= { dpsRTU 9804 }

dpsRTUp8805nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8805 is set."
	::= { dpsRTU 8805 }

dpsRTUp9805nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8805 clears."
	::= { dpsRTU 9805 }

dpsRTUp8806nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8806 is set."
	::= { dpsRTU 8806 }

dpsRTUp9806nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8806 clears."
	::= { dpsRTU 9806 }

dpsRTUp8807nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8807 is set."
	::= { dpsRTU 8807 }

dpsRTUp9807nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8807 clears."
	::= { dpsRTU 9807 }

dpsRTUp8808nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8808 is set."
	::= { dpsRTU 8808 }

dpsRTUp9808nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8808 clears."
	::= { dpsRTU 9808 }

dpsRTUp8809nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8809 is set."
	::= { dpsRTU 8809 }

dpsRTUp9809nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8809 clears."
	::= { dpsRTU 9809 }

dpsRTUp8810nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8810 is set."
	::= { dpsRTU 8810 }

dpsRTUp9810nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8810 clears."
	::= { dpsRTU 9810 }

dpsRTUp8811nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8811 is set."
	::= { dpsRTU 8811 }

dpsRTUp9811nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8811 clears."
	::= { dpsRTU 9811 }

dpsRTUp8812nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8812 is set."
	::= { dpsRTU 8812 }

dpsRTUp9812nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8812 clears."
	::= { dpsRTU 9812 }

dpsRTUp8813nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8813 is set."
	::= { dpsRTU 8813 }

dpsRTUp9813nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8813 clears."
	::= { dpsRTU 9813 }

dpsRTUp8814nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8814 is set."
	::= { dpsRTU 8814 }

dpsRTUp9814nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8814 clears."
	::= { dpsRTU 9814 }

dpsRTUp8815nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8815 is set."
	::= { dpsRTU 8815 }

dpsRTUp9815nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8815 clears."
	::= { dpsRTU 9815 }

dpsRTUp8816nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8816 is set."
	::= { dpsRTU 8816 }

dpsRTUp9816nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8816 clears."
	::= { dpsRTU 9816 }

dpsRTUp8817nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8817 is set."
	::= { dpsRTU 8817 }

dpsRTUp9817nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8817 clears."
	::= { dpsRTU 9817 }

dpsRTUp8818nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8818 is set."
	::= { dpsRTU 8818 }

dpsRTUp9818nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8818 clears."
	::= { dpsRTU 9818 }

dpsRTUp8819nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8819 is set."
	::= { dpsRTU 8819 }

dpsRTUp9819nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8819 clears."
	::= { dpsRTU 9819 }

dpsRTUp8820nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8820 is set."
	::= { dpsRTU 8820 }

dpsRTUp9820nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8820 clears."
	::= { dpsRTU 9820 }

dpsRTUp8821nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8821 is set."
	::= { dpsRTU 8821 }

dpsRTUp9821nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8821 clears."
	::= { dpsRTU 9821 }

dpsRTUp8822nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8822 is set."
	::= { dpsRTU 8822 }

dpsRTUp9822nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8822 clears."
	::= { dpsRTU 9822 }

dpsRTUp8823nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8823 is set."
	::= { dpsRTU 8823 }

dpsRTUp9823nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8823 clears."
	::= { dpsRTU 9823 }

dpsRTUp8824nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8824 is set."
	::= { dpsRTU 8824 }

dpsRTUp9824nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8824 clears."
	::= { dpsRTU 9824 }

dpsRTUp8825nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8825 is set."
	::= { dpsRTU 8825 }

dpsRTUp9825nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8825 clears."
	::= { dpsRTU 9825 }

dpsRTUp8826nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8826 is set."
	::= { dpsRTU 8826 }

dpsRTUp9826nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8826 clears."
	::= { dpsRTU 9826 }

dpsRTUp8827nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8827 is set."
	::= { dpsRTU 8827 }

dpsRTUp9827nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8827 clears."
	::= { dpsRTU 9827 }

dpsRTUp8828nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8828 is set."
	::= { dpsRTU 8828 }

dpsRTUp9828nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8828 clears."
	::= { dpsRTU 9828 }

dpsRTUp8829nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8829 is set."
	::= { dpsRTU 8829 }

dpsRTUp9829nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8829 clears."
	::= { dpsRTU 9829 }

dpsRTUp8830nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8830 is set."
	::= { dpsRTU 8830 }

dpsRTUp9830nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8830 clears."
	::= { dpsRTU 9830 }

dpsRTUp8831nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8831 is set."
	::= { dpsRTU 8831 }

dpsRTUp9831nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8831 clears."
	::= { dpsRTU 9831 }

dpsRTUp8832nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8832 is set."
	::= { dpsRTU 8832 }

dpsRTUp9832nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8832 clears."
	::= { dpsRTU 9832 }

dpsRTUp8833nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8833 is set."
	::= { dpsRTU 8833 }

dpsRTUp9833nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8833 clears."
	::= { dpsRTU 9833 }

dpsRTUp8834nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8834 is set."
	::= { dpsRTU 8834 }

dpsRTUp9834nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8834 clears."
	::= { dpsRTU 9834 }

dpsRTUp8835nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8835 is set."
	::= { dpsRTU 8835 }

dpsRTUp9835nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8835 clears."
	::= { dpsRTU 9835 }

dpsRTUp8836nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8836 is set."
	::= { dpsRTU 8836 }

dpsRTUp9836nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8836 clears."
	::= { dpsRTU 9836 }

dpsRTUp8837nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8837 is set."
	::= { dpsRTU 8837 }

dpsRTUp9837nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8837 clears."
	::= { dpsRTU 9837 }

dpsRTUp8838nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8838 is set."
	::= { dpsRTU 8838 }

dpsRTUp9838nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8838 clears."
	::= { dpsRTU 9838 }

dpsRTUp8839nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8839 is set."
	::= { dpsRTU 8839 }

dpsRTUp9839nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8839 clears."
	::= { dpsRTU 9839 }

dpsRTUp8840nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8840 is set."
	::= { dpsRTU 8840 }

dpsRTUp9840nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8840 clears."
	::= { dpsRTU 9840 }

dpsRTUp8841nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8841 is set."
	::= { dpsRTU 8841 }

dpsRTUp9841nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8841 clears."
	::= { dpsRTU 9841 }

dpsRTUp8842nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8842 is set."
	::= { dpsRTU 8842 }

dpsRTUp9842nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8842 clears."
	::= { dpsRTU 9842 }

dpsRTUp8843nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8843 is set."
	::= { dpsRTU 8843 }

dpsRTUp9843nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8843 clears."
	::= { dpsRTU 9843 }

dpsRTUp8844nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8844 is set."
	::= { dpsRTU 8844 }

dpsRTUp9844nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8844 clears."
	::= { dpsRTU 9844 }

dpsRTUp8845nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8845 is set."
	::= { dpsRTU 8845 }

dpsRTUp9845nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8845 clears."
	::= { dpsRTU 9845 }

dpsRTUp8846nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8846 is set."
	::= { dpsRTU 8846 }

dpsRTUp9846nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8846 clears."
	::= { dpsRTU 9846 }

dpsRTUp8847nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8847 is set."
	::= { dpsRTU 8847 }

dpsRTUp9847nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8847 clears."
	::= { dpsRTU 9847 }

dpsRTUp8848nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8848 is set."
	::= { dpsRTU 8848 }

dpsRTUp9848nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8848 clears."
	::= { dpsRTU 9848 }

dpsRTUp8849nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8849 is set."
	::= { dpsRTU 8849 }

dpsRTUp9849nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8849 clears."
	::= { dpsRTU 9849 }

dpsRTUp8850nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8850 is set."
	::= { dpsRTU 8850 }

dpsRTUp9850nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8850 clears."
	::= { dpsRTU 9850 }

dpsRTUp8851nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8851 is set."
	::= { dpsRTU 8851 }

dpsRTUp9851nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8851 clears."
	::= { dpsRTU 9851 }

dpsRTUp8852nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8852 is set."
	::= { dpsRTU 8852 }

dpsRTUp9852nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8852 clears."
	::= { dpsRTU 9852 }

dpsRTUp8853nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8853 is set."
	::= { dpsRTU 8853 }

dpsRTUp9853nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8853 clears."
	::= { dpsRTU 9853 }

dpsRTUp8854nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8854 is set."
	::= { dpsRTU 8854 }

dpsRTUp9854nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8854 clears."
	::= { dpsRTU 9854 }

dpsRTUp8855nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8855 is set."
	::= { dpsRTU 8855 }

dpsRTUp9855nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8855 clears."
	::= { dpsRTU 9855 }

dpsRTUp8856nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8856 is set."
	::= { dpsRTU 8856 }

dpsRTUp9856nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8856 clears."
	::= { dpsRTU 9856 }

dpsRTUp8857nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8857 is set."
	::= { dpsRTU 8857 }

dpsRTUp9857nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8857 clears."
	::= { dpsRTU 9857 }

dpsRTUp8858nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8858 is set."
	::= { dpsRTU 8858 }

dpsRTUp9858nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8858 clears."
	::= { dpsRTU 9858 }

dpsRTUp8859nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8859 is set."
	::= { dpsRTU 8859 }

dpsRTUp9859nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8859 clears."
	::= { dpsRTU 9859 }

dpsRTUp8860nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8860 is set."
	::= { dpsRTU 8860 }

dpsRTUp9860nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8860 clears."
	::= { dpsRTU 9860 }

dpsRTUp8861nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8861 is set."
	::= { dpsRTU 8861 }

dpsRTUp9861nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8861 clears."
	::= { dpsRTU 9861 }

dpsRTUp8862nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8862 is set."
	::= { dpsRTU 8862 }

dpsRTUp9862nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8862 clears."
	::= { dpsRTU 9862 }

dpsRTUp8863nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8863 is set."
	::= { dpsRTU 8863 }

dpsRTUp9863nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8863 clears."
	::= { dpsRTU 9863 }

dpsRTUp8864nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8864 is set."
	::= { dpsRTU 8864 }

dpsRTUp9864nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8864 clears."
	::= { dpsRTU 9864 }

dpsRTUp8865nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8865 is set."
	::= { dpsRTU 8865 }

dpsRTUp9865nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8865 clears."
	::= { dpsRTU 9865 }

dpsRTUp8866nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8866 is set."
	::= { dpsRTU 8866 }

dpsRTUp9866nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8866 clears."
	::= { dpsRTU 9866 }

dpsRTUp8867nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8867 is set."
	::= { dpsRTU 8867 }

dpsRTUp9867nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8867 clears."
	::= { dpsRTU 9867 }

dpsRTUp8868nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8868 is set."
	::= { dpsRTU 8868 }

dpsRTUp9868nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8868 clears."
	::= { dpsRTU 9868 }

dpsRTUp8869nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8869 is set."
	::= { dpsRTU 8869 }

dpsRTUp9869nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8869 clears."
	::= { dpsRTU 9869 }

dpsRTUp8870nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8870 is set."
	::= { dpsRTU 8870 }

dpsRTUp9870nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8870 clears."
	::= { dpsRTU 9870 }

dpsRTUp8871nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8871 is set."
	::= { dpsRTU 8871 }

dpsRTUp9871nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8871 clears."
	::= { dpsRTU 9871 }

dpsRTUp8872nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8872 is set."
	::= { dpsRTU 8872 }

dpsRTUp9872nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8872 clears."
	::= { dpsRTU 9872 }

dpsRTUp8873nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8873 is set."
	::= { dpsRTU 8873 }

dpsRTUp9873nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8873 clears."
	::= { dpsRTU 9873 }

dpsRTUp8874nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8874 is set."
	::= { dpsRTU 8874 }

dpsRTUp9874nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8874 clears."
	::= { dpsRTU 9874 }

dpsRTUp8875nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8875 is set."
	::= { dpsRTU 8875 }

dpsRTUp9875nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8875 clears."
	::= { dpsRTU 9875 }

dpsRTUp8876nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8876 is set."
	::= { dpsRTU 8876 }

dpsRTUp9876nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8876 clears."
	::= { dpsRTU 9876 }

dpsRTUp8877nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8877 is set."
	::= { dpsRTU 8877 }

dpsRTUp9877nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8877 clears."
	::= { dpsRTU 9877 }

dpsRTUp8878nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8878 is set."
	::= { dpsRTU 8878 }

dpsRTUp9878nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8878 clears."
	::= { dpsRTU 9878 }

dpsRTUp8879nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8879 is set."
	::= { dpsRTU 8879 }

dpsRTUp9879nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8879 clears."
	::= { dpsRTU 9879 }

dpsRTUp8880nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8880 is set."
	::= { dpsRTU 8880 }

dpsRTUp9880nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8880 clears."
	::= { dpsRTU 9880 }

dpsRTUp8881nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8881 is set."
	::= { dpsRTU 8881 }

dpsRTUp9881nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8881 clears."
	::= { dpsRTU 9881 }

dpsRTUp8882nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8882 is set."
	::= { dpsRTU 8882 }

dpsRTUp9882nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8882 clears."
	::= { dpsRTU 9882 }

dpsRTUp8883nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8883 is set."
	::= { dpsRTU 8883 }

dpsRTUp9883nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8883 clears."
	::= { dpsRTU 9883 }

dpsRTUp8884nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8884 is set."
	::= { dpsRTU 8884 }

dpsRTUp9884nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8884 clears."
	::= { dpsRTU 9884 }

dpsRTUp8885nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8885 is set."
	::= { dpsRTU 8885 }

dpsRTUp9885nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8885 clears."
	::= { dpsRTU 9885 }

dpsRTUp8886nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8886 is set."
	::= { dpsRTU 8886 }

dpsRTUp9886nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8886 clears."
	::= { dpsRTU 9886 }

dpsRTUp8887nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8887 is set."
	::= { dpsRTU 8887 }

dpsRTUp9887nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8887 clears."
	::= { dpsRTU 9887 }

dpsRTUp8888nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8888 is set."
	::= { dpsRTU 8888 }

dpsRTUp9888nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8888 clears."
	::= { dpsRTU 9888 }

dpsRTUp8889nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8889 is set."
	::= { dpsRTU 8889 }

dpsRTUp9889nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8889 clears."
	::= { dpsRTU 9889 }

dpsRTUp8890nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8890 is set."
	::= { dpsRTU 8890 }

dpsRTUp9890nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8890 clears."
	::= { dpsRTU 9890 }

dpsRTUp8891nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8891 is set."
	::= { dpsRTU 8891 }

dpsRTUp9891nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8891 clears."
	::= { dpsRTU 9891 }

dpsRTUp8892nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8892 is set."
	::= { dpsRTU 8892 }

dpsRTUp9892nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8892 clears."
	::= { dpsRTU 9892 }

dpsRTUp8893nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8893 is set."
	::= { dpsRTU 8893 }

dpsRTUp9893nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8893 clears."
	::= { dpsRTU 9893 }

dpsRTUp8894nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8894 is set."
	::= { dpsRTU 8894 }

dpsRTUp9894nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8894 clears."
	::= { dpsRTU 9894 }

dpsRTUp8895nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8895 is set."
	::= { dpsRTU 8895 }

dpsRTUp9895nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8895 clears."
	::= { dpsRTU 9895 }

dpsRTUp8896nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8896 is set."
	::= { dpsRTU 8896 }

dpsRTUp9896nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8896 clears."
	::= { dpsRTU 9896 }

dpsRTUp8897nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8897 is set."
	::= { dpsRTU 8897 }

dpsRTUp9897nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8897 clears."
	::= { dpsRTU 9897 }

dpsRTUp8898nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8898 is set."
	::= { dpsRTU 8898 }

dpsRTUp9898nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8898 clears."
	::= { dpsRTU 9898 }

dpsRTUp8899nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8899 is set."
	::= { dpsRTU 8899 }

dpsRTUp9899nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8899 clears."
	::= { dpsRTU 9899 }

dpsRTUp8900nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8900 is set."
	::= { dpsRTU 8900 }

dpsRTUp9900nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8900 clears."
	::= { dpsRTU 9900 }

dpsRTUp8901nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8901 is set."
	::= { dpsRTU 8901 }

dpsRTUp9901nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8901 clears."
	::= { dpsRTU 9901 }

dpsRTUp8902nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8902 is set."
	::= { dpsRTU 8902 }

dpsRTUp9902nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8902 clears."
	::= { dpsRTU 9902 }

dpsRTUp8903nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8903 is set."
	::= { dpsRTU 8903 }

dpsRTUp9903nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8903 clears."
	::= { dpsRTU 9903 }

dpsRTUp8904nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8904 is set."
	::= { dpsRTU 8904 }

dpsRTUp9904nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8904 clears."
	::= { dpsRTU 9904 }

dpsRTUp8905nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8905 is set."
	::= { dpsRTU 8905 }

dpsRTUp9905nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8905 clears."
	::= { dpsRTU 9905 }

dpsRTUp8906nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8906 is set."
	::= { dpsRTU 8906 }

dpsRTUp9906nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8906 clears."
	::= { dpsRTU 9906 }

dpsRTUp8907nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8907 is set."
	::= { dpsRTU 8907 }

dpsRTUp9907nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8907 clears."
	::= { dpsRTU 9907 }

dpsRTUp8908nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8908 is set."
	::= { dpsRTU 8908 }

dpsRTUp9908nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8908 clears."
	::= { dpsRTU 9908 }

dpsRTUp8909nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8909 is set."
	::= { dpsRTU 8909 }

dpsRTUp9909nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8909 clears."
	::= { dpsRTU 9909 }

dpsRTUp8910nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8910 is set."
	::= { dpsRTU 8910 }

dpsRTUp9910nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8910 clears."
	::= { dpsRTU 9910 }

dpsRTUp8911nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8911 is set."
	::= { dpsRTU 8911 }

dpsRTUp9911nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8911 clears."
	::= { dpsRTU 9911 }

dpsRTUp8912nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8912 is set."
	::= { dpsRTU 8912 }

dpsRTUp9912nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8912 clears."
	::= { dpsRTU 9912 }

dpsRTUp8913nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8913 is set."
	::= { dpsRTU 8913 }

dpsRTUp9913nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8913 clears."
	::= { dpsRTU 9913 }

dpsRTUp8914nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8914 is set."
	::= { dpsRTU 8914 }

dpsRTUp9914nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8914 clears."
	::= { dpsRTU 9914 }

dpsRTUp8915nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8915 is set."
	::= { dpsRTU 8915 }

dpsRTUp9915nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8915 clears."
	::= { dpsRTU 9915 }

dpsRTUp8916nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8916 is set."
	::= { dpsRTU 8916 }

dpsRTUp9916nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8916 clears."
	::= { dpsRTU 9916 }

dpsRTUp8917nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8917 is set."
	::= { dpsRTU 8917 }

dpsRTUp9917nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8917 clears."
	::= { dpsRTU 9917 }

dpsRTUp8918nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8918 is set."
	::= { dpsRTU 8918 }

dpsRTUp9918nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8918 clears."
	::= { dpsRTU 9918 }

dpsRTUp8919nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8919 is set."
	::= { dpsRTU 8919 }

dpsRTUp9919nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8919 clears."
	::= { dpsRTU 9919 }

dpsRTUp8920nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8920 is set."
	::= { dpsRTU 8920 }

dpsRTUp9920nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8920 clears."
	::= { dpsRTU 9920 }

dpsRTUp8921nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8921 is set."
	::= { dpsRTU 8921 }

dpsRTUp9921nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8921 clears."
	::= { dpsRTU 9921 }

dpsRTUp8922nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8922 is set."
	::= { dpsRTU 8922 }

dpsRTUp9922nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8922 clears."
	::= { dpsRTU 9922 }

dpsRTUp8923nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8923 is set."
	::= { dpsRTU 8923 }

dpsRTUp9923nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8923 clears."
	::= { dpsRTU 9923 }

dpsRTUp8924nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8924 is set."
	::= { dpsRTU 8924 }

dpsRTUp9924nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8924 clears."
	::= { dpsRTU 9924 }

dpsRTUp8925nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8925 is set."
	::= { dpsRTU 8925 }

dpsRTUp9925nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8925 clears."
	::= { dpsRTU 9925 }

dpsRTUp8926nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8926 is set."
	::= { dpsRTU 8926 }

dpsRTUp9926nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8926 clears."
	::= { dpsRTU 9926 }

dpsRTUp8927nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8927 is set."
	::= { dpsRTU 8927 }

dpsRTUp9927nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8927 clears."
	::= { dpsRTU 9927 }

dpsRTUp8928nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8928 is set."
	::= { dpsRTU 8928 }

dpsRTUp9928nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8928 clears."
	::= { dpsRTU 9928 }

dpsRTUp8929nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8929 is set."
	::= { dpsRTU 8929 }

dpsRTUp9929nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8929 clears."
	::= { dpsRTU 9929 }

dpsRTUp8930nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8930 is set."
	::= { dpsRTU 8930 }

dpsRTUp9930nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8930 clears."
	::= { dpsRTU 9930 }

dpsRTUp8931nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8931 is set."
	::= { dpsRTU 8931 }

dpsRTUp9931nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8931 clears."
	::= { dpsRTU 9931 }

dpsRTUp8932nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8932 is set."
	::= { dpsRTU 8932 }

dpsRTUp9932nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8932 clears."
	::= { dpsRTU 9932 }

dpsRTUp8933nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8933 is set."
	::= { dpsRTU 8933 }

dpsRTUp9933nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8933 clears."
	::= { dpsRTU 9933 }

dpsRTUp8934nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8934 is set."
	::= { dpsRTU 8934 }

dpsRTUp9934nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8934 clears."
	::= { dpsRTU 9934 }

dpsRTUp8935nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8935 is set."
	::= { dpsRTU 8935 }

dpsRTUp9935nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8935 clears."
	::= { dpsRTU 9935 }

dpsRTUp8936nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8936 is set."
	::= { dpsRTU 8936 }

dpsRTUp9936nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8936 clears."
	::= { dpsRTU 9936 }

dpsRTUp8937nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8937 is set."
	::= { dpsRTU 8937 }

dpsRTUp9937nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8937 clears."
	::= { dpsRTU 9937 }

dpsRTUp8938nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8938 is set."
	::= { dpsRTU 8938 }

dpsRTUp9938nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8938 clears."
	::= { dpsRTU 9938 }

dpsRTUp8939nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8939 is set."
	::= { dpsRTU 8939 }

dpsRTUp9939nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8939 clears."
	::= { dpsRTU 9939 }

dpsRTUp8940nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8940 is set."
	::= { dpsRTU 8940 }

dpsRTUp9940nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8940 clears."
	::= { dpsRTU 9940 }

dpsRTUp8941nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8941 is set."
	::= { dpsRTU 8941 }

dpsRTUp9941nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8941 clears."
	::= { dpsRTU 9941 }

dpsRTUp8942nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8942 is set."
	::= { dpsRTU 8942 }

dpsRTUp9942nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8942 clears."
	::= { dpsRTU 9942 }

dpsRTUp8943nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8943 is set."
	::= { dpsRTU 8943 }

dpsRTUp9943nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8943 clears."
	::= { dpsRTU 9943 }

dpsRTUp8944nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8944 is set."
	::= { dpsRTU 8944 }

dpsRTUp9944nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8944 clears."
	::= { dpsRTU 9944 }

dpsRTUp8945nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8945 is set."
	::= { dpsRTU 8945 }

dpsRTUp9945nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8945 clears."
	::= { dpsRTU 9945 }

dpsRTUp8946nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8946 is set."
	::= { dpsRTU 8946 }

dpsRTUp9946nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8946 clears."
	::= { dpsRTU 9946 }

dpsRTUp8947nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8947 is set."
	::= { dpsRTU 8947 }

dpsRTUp9947nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8947 clears."
	::= { dpsRTU 9947 }

dpsRTUp8948nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8948 is set."
	::= { dpsRTU 8948 }

dpsRTUp9948nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8948 clears."
	::= { dpsRTU 9948 }

dpsRTUp8949nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8949 is set."
	::= { dpsRTU 8949 }

dpsRTUp9949nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8949 clears."
	::= { dpsRTU 9949 }

dpsRTUp8950nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8950 is set."
	::= { dpsRTU 8950 }

dpsRTUp9950nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8950 clears."
	::= { dpsRTU 9950 }

dpsRTUp8951nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8951 is set."
	::= { dpsRTU 8951 }

dpsRTUp9951nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8951 clears."
	::= { dpsRTU 9951 }

dpsRTUp8952nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8952 is set."
	::= { dpsRTU 8952 }

dpsRTUp9952nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8952 clears."
	::= { dpsRTU 9952 }

dpsRTUp8953nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8953 is set."
	::= { dpsRTU 8953 }

dpsRTUp9953nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8953 clears."
	::= { dpsRTU 9953 }

dpsRTUp8954nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8954 is set."
	::= { dpsRTU 8954 }

dpsRTUp9954nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8954 clears."
	::= { dpsRTU 9954 }

dpsRTUp8955nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8955 is set."
	::= { dpsRTU 8955 }

dpsRTUp9955nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8955 clears."
	::= { dpsRTU 9955 }

dpsRTUp8956nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8956 is set."
	::= { dpsRTU 8956 }

dpsRTUp9956nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8956 clears."
	::= { dpsRTU 9956 }

dpsRTUp8957nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8957 is set."
	::= { dpsRTU 8957 }

dpsRTUp9957nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8957 clears."
	::= { dpsRTU 9957 }

dpsRTUp8958nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8958 is set."
	::= { dpsRTU 8958 }

dpsRTUp9958nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8958 clears."
	::= { dpsRTU 9958 }

dpsRTUp8959nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8959 is set."
	::= { dpsRTU 8959 }

dpsRTUp9959nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8959 clears."
	::= { dpsRTU 9959 }

dpsRTUp8960nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8960 is set."
	::= { dpsRTU 8960 }

dpsRTUp9960nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8960 clears."
	::= { dpsRTU 9960 }

dpsRTUp8961nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8961 is set."
	::= { dpsRTU 8961 }

dpsRTUp9961nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8961 clears."
	::= { dpsRTU 9961 }

dpsRTUp8962nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8962 is set."
	::= { dpsRTU 8962 }

dpsRTUp9962nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8962 clears."
	::= { dpsRTU 9962 }

dpsRTUp8963nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8963 is set."
	::= { dpsRTU 8963 }

dpsRTUp9963nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8963 clears."
	::= { dpsRTU 9963 }

dpsRTUp8964nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8964 is set."
	::= { dpsRTU 8964 }

dpsRTUp9964nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8964 clears."
	::= { dpsRTU 9964 }

dpsRTUp8965nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8965 is set."
	::= { dpsRTU 8965 }

dpsRTUp9965nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8965 clears."
	::= { dpsRTU 9965 }

dpsRTUp8966nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8966 is set."
	::= { dpsRTU 8966 }

dpsRTUp9966nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8966 clears."
	::= { dpsRTU 9966 }

dpsRTUp8967nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8967 is set."
	::= { dpsRTU 8967 }

dpsRTUp9967nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8967 clears."
	::= { dpsRTU 9967 }

dpsRTUp8968nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8968 is set."
	::= { dpsRTU 8968 }

dpsRTUp9968nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8968 clears."
	::= { dpsRTU 9968 }

dpsRTUp8969nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8969 is set."
	::= { dpsRTU 8969 }

dpsRTUp9969nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8969 clears."
	::= { dpsRTU 9969 }

dpsRTUp8970nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8970 is set."
	::= { dpsRTU 8970 }

dpsRTUp9970nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8970 clears."
	::= { dpsRTU 9970 }

dpsRTUp8971nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8971 is set."
	::= { dpsRTU 8971 }

dpsRTUp9971nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8971 clears."
	::= { dpsRTU 9971 }

dpsRTUp8972nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8972 is set."
	::= { dpsRTU 8972 }

dpsRTUp9972nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8972 clears."
	::= { dpsRTU 9972 }

dpsRTUp8973nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8973 is set."
	::= { dpsRTU 8973 }

dpsRTUp9973nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8973 clears."
	::= { dpsRTU 9973 }

dpsRTUp8974nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8974 is set."
	::= { dpsRTU 8974 }

dpsRTUp9974nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8974 clears."
	::= { dpsRTU 9974 }

dpsRTUp8975nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8975 is set."
	::= { dpsRTU 8975 }

dpsRTUp9975nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8975 clears."
	::= { dpsRTU 9975 }

dpsRTUp8976nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8976 is set."
	::= { dpsRTU 8976 }

dpsRTUp9976nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8976 clears."
	::= { dpsRTU 9976 }

dpsRTUp8977nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8977 is set."
	::= { dpsRTU 8977 }

dpsRTUp9977nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8977 clears."
	::= { dpsRTU 9977 }

dpsRTUp8978nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8978 is set."
	::= { dpsRTU 8978 }

dpsRTUp9978nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8978 clears."
	::= { dpsRTU 9978 }

dpsRTUp8979nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8979 is set."
	::= { dpsRTU 8979 }

dpsRTUp9979nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8979 clears."
	::= { dpsRTU 9979 }

dpsRTUp8980nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8980 is set."
	::= { dpsRTU 8980 }

dpsRTUp9980nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8980 clears."
	::= { dpsRTU 9980 }

dpsRTUp8981nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8981 is set."
	::= { dpsRTU 8981 }

dpsRTUp9981nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8981 clears."
	::= { dpsRTU 9981 }

dpsRTUp8982nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8982 is set."
	::= { dpsRTU 8982 }

dpsRTUp9982nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8982 clears."
	::= { dpsRTU 9982 }

dpsRTUp8983nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8983 is set."
	::= { dpsRTU 8983 }

dpsRTUp9983nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8983 clears."
	::= { dpsRTU 9983 }

dpsRTUp8984nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8984 is set."
	::= { dpsRTU 8984 }

dpsRTUp9984nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8984 clears."
	::= { dpsRTU 9984 }

dpsRTUp8985nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8985 is set."
	::= { dpsRTU 8985 }

dpsRTUp9985nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8985 clears."
	::= { dpsRTU 9985 }

dpsRTUp8986nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8986 is set."
	::= { dpsRTU 8986 }

dpsRTUp9986nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8986 clears."
	::= { dpsRTU 9986 }

dpsRTUp8987nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8987 is set."
	::= { dpsRTU 8987 }

dpsRTUp9987nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8987 clears."
	::= { dpsRTU 9987 }

dpsRTUp8988nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8988 is set."
	::= { dpsRTU 8988 }

dpsRTUp9988nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8988 clears."
	::= { dpsRTU 9988 }

dpsRTUp8989nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8989 is set."
	::= { dpsRTU 8989 }

dpsRTUp9989nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8989 clears."
	::= { dpsRTU 9989 }

dpsRTUp8990nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8990 is set."
	::= { dpsRTU 8990 }

dpsRTUp9990nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8990 clears."
	::= { dpsRTU 9990 }

dpsRTUp8991nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8991 is set."
	::= { dpsRTU 8991 }

dpsRTUp9991nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8991 clears."
	::= { dpsRTU 9991 }

dpsRTUp8992nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8992 is set."
	::= { dpsRTU 8992 }

dpsRTUp9992nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8992 clears."
	::= { dpsRTU 9992 }

dpsRTUp8993nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8993 is set."
	::= { dpsRTU 8993 }

dpsRTUp9993nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8993 clears."
	::= { dpsRTU 9993 }

dpsRTUp8994nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8994 is set."
	::= { dpsRTU 8994 }

dpsRTUp9994nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8994 clears."
	::= { dpsRTU 9994 }

dpsRTUp8995nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8995 is set."
	::= { dpsRTU 8995 }

dpsRTUp9995nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8995 clears."
	::= { dpsRTU 9995 }

dpsRTUp8996nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8996 is set."
	::= { dpsRTU 8996 }

dpsRTUp9996nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8996 clears."
	::= { dpsRTU 9996 }

dpsRTUp8997nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8997 is set."
	::= { dpsRTU 8997 }

dpsRTUp9997nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8997 clears."
	::= { dpsRTU 9997 }

dpsRTUp8998nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8998 is set."
	::= { dpsRTU 8998 }

dpsRTUp9998nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8998 clears."
	::= { dpsRTU 9998 }

dpsRTUp8999nSet NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8999 is set."
	::= { dpsRTU 8999 }

dpsRTUp9999nClr NOTIFICATION-TYPE
	OBJECTS { sysDescr, sysLocation, dpsRTUDateTime,
				dpsRTUAPort, dpsRTUCAddress, dpsRTUADisplay, dpsRTUAPoint,
				dpsRTUAPntDesc, dpsRTUAState }
	STATUS current
	DESCRIPTION "Granular point 8999 clears."
	::= { dpsRTU 9999 }

END
