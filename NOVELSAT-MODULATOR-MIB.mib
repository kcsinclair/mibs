----------------------------------------------
-- NOVELSAT-MODULATOR.mib               --
-- MIB generated by naamab, Novelsat        --
-- Sunday, September 12, 2010 at 15:46:00   --
----------------------------------------------


NOVELSAT-MODULATOR-MIB DEFINITIONS ::= BEGIN

IMPORTS
        OBJECT-TYPE, Integer32, Unsigned32, Counter32, IpAddress, OBJECT-IDENTITY, MODULE-IDENTITY
                FROM SNMPv2-SMI
        DisplayString
                FROM SNMPv2-TC
        ifIndex
                FROM IF-MIB
        nsRoot
                FROM NOVELSAT-ROOT-MIB;

-- ===================================================

nsModulator MODULE-IDENTITY
        LAST-UPDATED "201009121500Z"
        ORGANIZATION
                "Novelsat"
        CONTACT-INFO
                "21 Ha'taasiya St.,
                Ra'anana 43654,Israel
                --------------------------
                Tel: +972-9-7889730
                Fax: +972-9-
                e-mail: info@novelsat.com, support@novelsat.com
                http://www.novelsat.com
                --------------------------
                "
        DESCRIPTION
                "novelsat MIB branch for Modulator products"

        REVISION "201009121500Z"
        DESCRIPTION
                "Version 1.0.0.X"
::= { nsRoot 3 }

-- ===================================================
nsModConfig  OBJECT-IDENTITY
        STATUS current
        DESCRIPTION
              "Modulator MIB branch that holds all Modulator parameters."
        ::= { nsModulator 1 }

-- ===================================================
nsModConfigLine  OBJECT-IDENTITY
        STATUS current
        DESCRIPTION
              "Modulator MIB branch that holds all Modulator line parameters."
        ::= { nsModConfig 1 }

nsModConfigLineTXStatus  OBJECT-TYPE
        SYNTAX  INTEGER {
        	disabled (0),
            enabled (1),
            notApplicable (255)
        }
        MAX-ACCESS  read-write
        STATUS  current
        DESCRIPTION
                "This parameter determine the TX status: enabled/disabled."
        ::= { nsModConfigLine  1 }

nsModConfigLineMode  OBJECT-TYPE
        SYNTAX  INTEGER {
            dvbs (0),
            dsng (1),
			dvbs2 (2),
			ns3 (3),
            notApplicable (255)
		}
        MAX-ACCESS  read-write
        STATUS  current
        DESCRIPTION
                "This parameter holds Line mode."
        ::= { nsModConfigLine  2 }

nsModConfigLineChPriority  OBJECT-TYPE
        SYNTAX  INTEGER {
            equal (0),
            ch1   (1),
			ch2   (2),
            notApplicable (255)
        }
        MAX-ACCESS  read-write
        STATUS  current
        DESCRIPTION
                "This parameter is no longer supported"
        ::= { nsModConfigLine  4 }

nsModConfigLineRollOff  OBJECT-TYPE
        SYNTAX  INTEGER {
			rollOff005 (0),
			rollOff010 (1),
			rollOff015 (2),
			rollOff020 (3),
			rollOff025 (4),
			rollOff035 (5),
            notApplicable (255)
        }
        MAX-ACCESS  read-write
        STATUS  current
        DESCRIPTION
                "This parameter holds Line roll off.
                rollOff005 = 0.05
				rollOff010 = 0.10
				rollOff015 = 0.15
				rollOff020 = 0.20
				rollOff025 = 0.25
				rollOff035 = 0.35
                "
        ::= { nsModConfigLine  5 }

nsModConfigLineSineStatus  OBJECT-TYPE
        SYNTAX  INTEGER {
			off (0),
			on (1),
            notApplicable (255)
        }
        MAX-ACCESS  read-write
        STATUS  current
        DESCRIPTION
                "This parameter holds Line sine status: on/off."
        ::= { nsModConfigLine  6 }

nsModConfigLineRFFreq  OBJECT-TYPE
        SYNTAX  Unsigned32
        MAX-ACCESS  read-write
        STATUS  current
        DESCRIPTION
                "This parameter holds Line RF frequency in 10Hrz."
        ::= { nsModConfigLine  7 }

nsModConfigLineSymbolRate  OBJECT-TYPE
        SYNTAX  Integer32 (50000..72000000)
        MAX-ACCESS  read-write
        STATUS  current
        DESCRIPTION
                "This parameter holds Line symbol rate in SPS."
        ::= { nsModConfigLine  8 }

nsModConfigLinePower  OBJECT-TYPE
        SYNTAX  Integer32 (-3000..0)
        MAX-ACCESS  read-write
        STATUS  current
        DESCRIPTION
                "This parameter holds Line power in hundreds of dBm."
        ::= { nsModConfigLine  9 } 

nsModConfigLineGoldSeq  OBJECT-TYPE
        SYNTAX  Integer32 (0..262141)
        MAX-ACCESS  read-write
        STATUS  current
        DESCRIPTION
                "This parameter holds Line golden sequence."
        ::= { nsModConfigLine  10 } 

nsModConfigLineDualChState  OBJECT-TYPE
        SYNTAX  INTEGER {
			dual (0),
			single (1),
            notApplicable (255)
        }
        MAX-ACCESS  read-write
        STATUS  current
        DESCRIPTION
                "This parameter holds Line dual channel status: dual/single channel."
        ::= { nsModConfigLine  11 }
 
nsModConfigLineBitRate  OBJECT-TYPE
        SYNTAX  Integer32 
        MAX-ACCESS  read-write
        STATUS  current
        DESCRIPTION
                "This parameter holds Line bit rate in bPS."
        ::= { nsModConfigLine  12 } 

nsModConfigLinePowerUpTXState  OBJECT-TYPE
        SYNTAX  INTEGER {
			disable (0),
			enable (1),
            notApplicable (255)
        }
        MAX-ACCESS  read-write
        STATUS  current
        DESCRIPTION
                "This parameter holds Line Power-Up TX State: disable/enable."
        ::= { nsModConfigLine  13 }
 
nsModConfigLineAcmMode  OBJECT-TYPE
        SYNTAX  INTEGER {
			disable (0),
			enableCh1 (1),
			enableCh2 (2),
			enableCh1Ch2 (3),
            notApplicable (255)
        }
        MAX-ACCESS  read-write
        STATUS  current
        DESCRIPTION
                "This parameter holds Line ACM mode: enable/disable."
        ::= { nsModConfigLine  14 } 

nsModConfigLineOutputLevelMode  OBJECT-TYPE
        SYNTAX  INTEGER {
            constantPower (0),
            constantEnvelope (1),
            notApplicable (255)
        }
        MAX-ACCESS  read-write
        STATUS  current
        DESCRIPTION
                "This parameter holds Line output level mode."
        ::= { nsModConfigLine  15 } 
        
nsModConfigLineChannel1Bandwidth  OBJECT-TYPE
        SYNTAX  INTEGER (0..100)
        MAX-ACCESS  read-write
        STATUS  current
        DESCRIPTION
                "This parameter holds Channel-1 allocated bandwidth percentage."
        ::= { nsModConfigLine  16 }

nsModConfigLineChannel2Bandwidth  OBJECT-TYPE
        SYNTAX  INTEGER (0..100)
        MAX-ACCESS  read-write
        STATUS  current
        DESCRIPTION
                "This parameter holds Channel-2 allocated bandwidth percentage."
        ::= { nsModConfigLine  17 }        

nsModConfigLineSpectrumInvert  OBJECT-TYPE
        SYNTAX  INTEGER {
            off (0),
            on (1),
            notApplicable (255)
        }
        MAX-ACCESS  read-write
        STATUS  current
        DESCRIPTION
                "This parameter holds Line spectrum invert status: on/off."
        ::= { nsModConfigLine  18 }

nsModConfigLineRecommendedBitRate  OBJECT-TYPE
        SYNTAX  Integer32 
        MAX-ACCESS  read-only
        STATUS  current
        DESCRIPTION
                "This parameter holds Line recommended bit rate in bPS."
        ::= { nsModConfigLine  19 } 

nsModConfigLineLOFreq  OBJECT-TYPE
        SYNTAX  Unsigned32 (0..4000000000)
        MAX-ACCESS  read-write
        STATUS  current
        DESCRIPTION
                "This parameter holds Line LO frequency in 10Hrz."
        ::= { nsModConfigLine  20 }

nsModConfigLineAcmUseManagementIp  OBJECT-TYPE 
        SYNTAX  INTEGER {
            disable (0),
            enable (1),
            notApplicable (255)
        }
        MAX-ACCESS  read-write
        STATUS  current
        DESCRIPTION
                "This parameter is no longer supported"
        ::= { nsModConfigLine  21 } 
                
nsModConfigLineAcmIpAddress  OBJECT-TYPE 
        SYNTAX  IpAddress
        MAX-ACCESS  read-write
        STATUS  current
        DESCRIPTION
                "This parameter is no longer supported"
        ::= { nsModConfigLine  22 } 
        
nsModConfigLineAcmIpNetmask  OBJECT-TYPE 
        SYNTAX  IpAddress
        MAX-ACCESS  read-write
        STATUS  current
        DESCRIPTION
                "This parameter is no longer supported"
        ::= { nsModConfigLine  23 } 
        
nsModConfigLineAupcMode  OBJECT-TYPE
        SYNTAX  INTEGER {
			disable (0),
			enable (1),
            notApplicable (255)
        }
        MAX-ACCESS  read-write
        STATUS  current
        DESCRIPTION
                "This parameter holds Line AUPC mode: enable/disable."
        ::= { nsModConfigLine  24 } 

nsModConfigLineAupcSatRxFreq  OBJECT-TYPE
        SYNTAX  Integer32 (100..40000)
        MAX-ACCESS  read-write
        STATUS  current
        DESCRIPTION
                "This parameter holds AUPC satellite RX Frequency in hundreds of GHz."
        ::= { nsModConfigLine  25 } 

nsModConfigLineAupcSatRxPolarity  OBJECT-TYPE
        SYNTAX  INTEGER {
			vertical (0),
			horizontal (1),
			circular-left (2),
			circular-right (3),
            notApplicable (255)
        }
        MAX-ACCESS  read-write
        STATUS  current
        DESCRIPTION
                "This parameter holds AUPC satellite RX Polarity: vertical/horizontal/circular."
        ::= { nsModConfigLine  26 } 

nsModConfigLineAupcSatTxFreq  OBJECT-TYPE
        SYNTAX  Integer32 (100..40000)
        MAX-ACCESS  read-write
        STATUS  current
        DESCRIPTION
                "This parameter holds AUPC satellite TX Frequency in hundreds of GHz."
        ::= { nsModConfigLine  27 } 

nsModConfigLineAupcSatTxPolarity  OBJECT-TYPE
        SYNTAX  INTEGER {
			vertical (0),
			horizontal (1),
			circular-left (2),
			circular-right (3),
            notApplicable (255)
        }
        MAX-ACCESS  read-write
        STATUS  current
        DESCRIPTION
                "This parameter holds AUPC satellite TX Polarity: vertical/horizontal/circular."
        ::= { nsModConfigLine  28 } 

nsModConfigLineAupcMaxGain  OBJECT-TYPE
        SYNTAX  Integer32 (0..4000)
        MAX-ACCESS  read-write
        STATUS  current
        DESCRIPTION
                "This parameter holds AUPC maximal gain in hundreds of dBm."
        ::= { nsModConfigLine  29 } 

nsModConfigLineAupcMaxAttn  OBJECT-TYPE
 	 	SYNTAX  Integer32 (0..4000)
 	 	MAX-ACCESS  read-write
 	 	STATUS  current
 	 	DESCRIPTION
 	 	        "This parameter holds AUPC maximal Attenuation in hundreds of dBm."
 	 	::= { nsModConfigLine  30 } 

-- ===================================================
nsModConfigChannel  OBJECT-IDENTITY
        STATUS current
        DESCRIPTION
              "Modulator MIB branch that holds all Modulator channel parameters."
        ::= { nsModConfig 2 }

nsModConfigChannelTable OBJECT-TYPE
	SYNTAX SEQUENCE OF ModChannelEntry
	MAX-ACCESS not-accessible
	STATUS current
	DESCRIPTION
		"A list of Channel parameters"
	::= { nsModConfigChannel 1 } 

nsModConfigChannelEntry OBJECT-TYPE
    SYNTAX      ModChannelEntry
    MAX-ACCESS  not-accessible
    STATUS      current
    DESCRIPTION "Conceptual row in table for each channel."
    INDEX   { ifIndex }
    ::= { nsModConfigChannelTable 1 }
        
ModChannelEntry ::=
	SEQUENCE {
		nsModConfigChStatus 		     INTEGER,
		nsModConfigChSource 		     INTEGER,
		nsModConfigChNPD 			     INTEGER,
		nsModConfigChFrameSize 	  	     INTEGER,
		nsModConfigChModulation 	     INTEGER,
		nsModConfigChFECRate 		     INTEGER,
		nsModConfigChPilot 			     INTEGER,
		nsModConfigChISSY 			     INTEGER,
		nsModConfigChStreamFormat 	     INTEGER,
		nsModConfigChPacketSize 	     Integer32,
		nsModConfigChSyncByte 		     Integer32,
		nsModConfigChIsi	 		     Integer32,
		nsModConfigChPCRRestamping	     INTEGER,
		nsModConfigChMpegProcessingMode  INTEGER,
		nsModConfigChBitRate             INTEGER,
		nsModConfigChBitRatePercent      INTEGER,
        nsModConfigChTSProtect           INTEGER
	} 
    
nsModConfigChStatus  OBJECT-TYPE
        SYNTAX  INTEGER {
            disabled (0),
			enabled (1),
            notApplicable (255)
        }
        MAX-ACCESS  read-write
        STATUS  current
        DESCRIPTION
                "This parameter holds channel status."
        ::= { nsModConfigChannelEntry  1 }

nsModConfigChSource  OBJECT-TYPE
        SYNTAX  INTEGER {
			gbeA    (0),
			gbeB    (1),
			asi1    (2),
			asi2    (3),
			gigE    (4),
			disable (5),
			g703    (6),
           	test1   (7),
		    test2   (8),
            notApplicable (255)
        }
        MAX-ACCESS  read-write
        STATUS  current
        DESCRIPTION
                "This parameter holds channel source."
        ::= { nsModConfigChannelEntry  2 }

nsModConfigChNPD  OBJECT-TYPE
        SYNTAX  INTEGER {
			none (0),
			addition (1),
			deletion (2),
            notApplicable (255)
        }
        MAX-ACCESS  read-write
        STATUS  current
        DESCRIPTION
                "This parameter is no longer supported"
        ::= { nsModConfigChannelEntry  3 }

nsModConfigChFrameSize  OBJECT-TYPE
        SYNTAX  INTEGER {
			normal (0),
			short (1),
            notApplicable (255)
        }
        MAX-ACCESS  read-write
        STATUS  current
        DESCRIPTION
                "This parameter holds channel frame size."
        ::= { nsModConfigChannelEntry  4 }

nsModConfigChModulation  OBJECT-TYPE
        SYNTAX  INTEGER {
            modulationBpsk   (0),
            modulationQpsk   (1),
            modulation8Psk   (2),
            modulation16Qam  (3),
            modulation16Apsk (4),
			modulation32Apsk (5),
			modulation64Apsk (6),
            notApplicable (255)
        }
        MAX-ACCESS  read-write
        STATUS  current
        DESCRIPTION
                "This parameter holds channel modulation."
        ::= { nsModConfigChannelEntry  5 }

nsModConfigChFECRate  OBJECT-TYPE
        SYNTAX  INTEGER {
        	fec1Div5   (0),
		  	fec1Div4   (1),
	  		fec1Div3   (2),
		  	fec2Div5   (3),
	  		fec13Div30 (4),
		  	fec4Div9   (5),
	  		fec7Div15  (6),
		  	fec22Div45 (7),
	  		fec1Div2   (8),
			fec8Div15  (9),
		  	fec5Div9   (10),
	  		fec17Div30 (11),
		  	fec3Div5   (12),
	  		fec28Div45 (13),
		  	fec19Div30 (14),
	  		fec2Div3   (15),
		  	fec32Div45 (16),
	  		fec11Div15 (17),
		  	fec3Div4   (18),
	  		fec7Div9   (19),
		  	fec4Div5   (20),
	  		fec37Div45 (21),
		  	fec5Div6   (22),
	  		fec7Div8   (23),
		  	fec8Div9   (24),
	  		fec9Div10  (25),
            notApplicable (255)
       	}
        MAX-ACCESS  read-write
        STATUS  current
        DESCRIPTION
                "This parameter holds channel FEC rate.
                    fec1Div5   = 1/5
                    fec1Div4   = 1/4
                    fec1Div3   = 1/3
                    fec2Div5   = 2/5
                    fec13Div30 = 13/30
                    fec4Div9   = 4/9
                    fec7Div15  = 7/15
                    fec22Div45 = 22/45
                    fec1Div2   = 1/2
                    fec8Div15  = 8/15
                    fec5Div9   = 5/9
                    fec17Div30 = 17/30
                    fec3Div5   = 3/5
                    fec28Div45 = 28/45
                    fec19Div30 = 19/30
                    fec2Div3   = 2/3
                    fec32Div45 = 32/45
                    fec11Div15 = 11/15
                    fec3Div4   = 3/4
                    fec7Div9   = 7/9
                    fec4Div5   = 4/5
                    fec37Div45 = 37/45
                    fec5Div6   = 5/6
                    fec7Div8   = 7/8
                    fec8Div9   = 8/9
                    fec9Div10  = 9/10                
                "
        ::= { nsModConfigChannelEntry  6 }

nsModConfigChPilot  OBJECT-TYPE
        SYNTAX  INTEGER {
            pilotNo       (0),
	    pilot8Slots   (1),
            pilot16Slots  (2),
            notApplicable (255)
        }
        MAX-ACCESS  read-write
        STATUS  current
        DESCRIPTION
                "This parameter holds channel pilot."
        ::= { nsModConfigChannelEntry  7 }

nsModConfigChISSY  OBJECT-TYPE
        SYNTAX  INTEGER {
			issyDisabled (0),
            issy2Bytes  (1),
            issy3Bytes  (2),
            notApplicable (255)
        }
        MAX-ACCESS  read-write
        STATUS  current
        DESCRIPTION
                "This parameter holds channel ISSY."
        ::= { nsModConfigChannelEntry  8 }

nsModConfigChStreamFormat  OBJECT-TYPE
        SYNTAX  INTEGER {
            transport188 (0),
            transport204 (1),
            genericPacketsized (2),
            genericContinuous  (3),
            notApplicable (255)
        }
        MAX-ACCESS  read-write
        STATUS  current
        DESCRIPTION
                "This parameter holds channel stream format."
        ::= { nsModConfigChannelEntry  9 }

nsModConfigChPacketSize  OBJECT-TYPE
        SYNTAX  Integer32 (0..65535)
        MAX-ACCESS  read-write
        STATUS  current
        DESCRIPTION
                "This parameter holds channel packet size."
        ::= { nsModConfigChannelEntry  10 }
        
nsModConfigChSyncByte  OBJECT-TYPE
        SYNTAX  Integer32 (0..255)
        MAX-ACCESS  read-write
        STATUS  current
        DESCRIPTION
                "This parameter holds channel sync byte."
        ::= { nsModConfigChannelEntry  11 }     

nsModConfigChIsi  OBJECT-TYPE
        SYNTAX  Integer32 (0..255)
        MAX-ACCESS  read-write
        STATUS  current
        DESCRIPTION
                "This parameter holds channel ISI value."
        ::= { nsModConfigChannelEntry  12 }
        
nsModConfigChPCRRestamping  OBJECT-TYPE
        SYNTAX  INTEGER {
            disabled (0),
			enabled (1),
            notApplicable (255)
        }
        MAX-ACCESS  read-write
        STATUS  current
        DESCRIPTION
                "This parameter is no longer supported"
        ::= { nsModConfigChannelEntry  13 }
        
nsModConfigChMpegProcessingMode  OBJECT-TYPE
        SYNTAX  INTEGER {
            off (0),
            dataAdjust (1),
            symbolAdjust (2),	
            partialDataAdjust (3),	                   
            notApplicable (255)
        }
        MAX-ACCESS  read-write
        STATUS  current
        DESCRIPTION
                "This parameter holds channel MPEG processing mode."
        ::= { nsModConfigChannelEntry  14 }
        
nsModConfigChBitRate  OBJECT-TYPE
        SYNTAX  Integer32 
        MAX-ACCESS  read-write
        STATUS  current
        DESCRIPTION
                "This parameter holds channel bit rate in bPS."
        ::= { nsModConfigChannelEntry  15 }

nsModConfigChBitRatePercent  OBJECT-TYPE
        SYNTAX  Integer32 
        MAX-ACCESS  read-only
        STATUS  current
        DESCRIPTION
                "This parameter holds calculated channel bit rate as percent from maximal theoretical channel bitrate."
        ::= { nsModConfigChannelEntry  16 }

nsModConfigChTSProtect  OBJECT-TYPE
        SYNTAX  INTEGER {
            disable (0),
            enable (1),
            notApplicable (255)
        }
        MAX-ACCESS  read-write
        STATUS  current
        DESCRIPTION
                "Protect transport stream data, enabling constant bit-rate at the receiver, replacing RF link error frames by Null-packets."
        ::= { nsModConfigChannelEntry  17 }
                
-- ===================================================
nsModConfigInterface  OBJECT-IDENTITY
        STATUS current
        DESCRIPTION
              "Modulator MIB branch that holds all Modulator Interface parameters."
        ::= { nsModConfig 3 }


nsModConfigInterfaceTestTable  OBJECT-TYPE
	SYNTAX SEQUENCE OF ModConfigInterfaceTestEntry
	MAX-ACCESS not-accessible
	STATUS current
	DESCRIPTION
		"A list of Test interfaces"
	::= { nsModConfigInterface 1 } 

nsModConfigInterfaceTestEntry OBJECT-TYPE
    SYNTAX      ModConfigInterfaceTestEntry
    MAX-ACCESS  not-accessible
    STATUS      current
    DESCRIPTION "Conceptual row in table for each test interface."
    INDEX   { ifIndex }
    ::= { nsModConfigInterfaceTestTable 1 }
            
ModConfigInterfaceTestEntry ::=
	SEQUENCE {
		nsModConfigInterfaceTestPattern 		INTEGER,
		nsModConfigInterfaceTestInvert   		INTEGER
	} 
                
nsModConfigInterfaceTestPattern  OBJECT-TYPE
        SYNTAX  INTEGER {
            pattern2Pwr7Neg1 (0),
            pattern2Pwr9Neg1 (1),
            pattern2Pwr11Neg1 (2),
            pattern2Pwr15Neg1 (3),
            pattern2Pwr20Neg1 (4),
            pattern2Pwr23Neg1 (5),
            pattern2Pwr29Neg1 (6),
            pattern2Pwr31Neg1 (7),
            patternAllZeros (8),
            patternAllOnes (9),
            patternBitAlternate (10),
            pattern2BitAlternate (11),
            pattern7Ones (12),
            pattern7Zeros (13),
            pattern6Ones (14),
            pattern6Zeros (15),
            pattern55AA (16),
            pattern6699 (17),
            patternC33C (18),
            pattern00FF (19),
            patternSAWTOOTH (20),
            notApplicable (255)
        }
        MAX-ACCESS  read-write
        STATUS  current
        DESCRIPTION
                "This parameter holds Test interface pattern.
                    pattern2Pwr07Neg1 = 2^07-1
                    pattern2Pwr09Neg1 = 2^09-1
		            pattern2Pwr11Neg1 = 2^11-1
		            pattern2Pwr15Neg1 = 2^15-1
		            pattern2Pwr20Neg1 = 2^20-1
		            pattern2Pwr23Neg1 = 2^23-1
		            pattern2Pwr29Neg1 = 2^29-1
		            pattern2Pwr31Neg1 = 2^31-1
		            patternAllZeros   = all zeros
		            patternAllOnes    = all ones
		            patternBitAlternate = bit alternate
		            pattern2BitAlternate= 2 bit alternate
		            pattern7Ones      = 1111111 (7 ones)
		            pattern7Zeros     = 0000000 (7 zeros)
		            pattern6Ones      = 111111 (6 ones)
		            pattern6Zeros     = 000000 (6 zeros)
		            pattern55AA       = 0x55AA
		            pattern6699       = 0x6699
		            patternC33C       = 0xC33C
		            pattern00FF       = 0x00FF
		            patternSAWTOOTH   = SAWTOOTH
                "
        ::= { nsModConfigInterfaceTestEntry  1 }                

nsModConfigInterfaceTestInvert  OBJECT-TYPE
        SYNTAX  INTEGER {
            no (0),
            yes (1),
            notApplicable (255)
        }
        MAX-ACCESS  read-write
        STATUS  current
        DESCRIPTION
                "This parameter holds Test interface invert."
        ::= { nsModConfigInterfaceTestEntry  2 }   
                
                
                
                
nsModConfigInterfaceASITable  OBJECT-TYPE
	SYNTAX SEQUENCE OF ModConfigInterfaceASIEntry
	MAX-ACCESS not-accessible
	STATUS current
	DESCRIPTION
		"A list of ASI interfaces"
    ::= { nsModConfigInterface  2 }
          
nsModConfigInterfaceASIEntry OBJECT-TYPE
    SYNTAX      ModConfigInterfaceASIEntry
    MAX-ACCESS  not-accessible
    STATUS      current
    DESCRIPTION "Conceptual row in table for each ASI interface."
    INDEX   { ifIndex }
    ::= { nsModConfigInterfaceASITable 1 }
            
ModConfigInterfaceASIEntry ::=
    SEQUENCE {
        nsModConfigInterfaceASIDataOrder         INTEGER
    } 
                

nsModConfigInterfaceASIDataOrder  OBJECT-TYPE
        SYNTAX  INTEGER {
            lsb (0),
            msb (1),
            notApplicable (255)
        }
        MAX-ACCESS  read-write
        STATUS  current
        DESCRIPTION
                "This parameter holds ASI interface data order."
        ::= { nsModConfigInterfaceASIEntry  1 }   
                        
                        
nsModConfigInterfaceEthernetTable  OBJECT-TYPE
	SYNTAX SEQUENCE OF ModConfigInterfaceEthernetEntry
	MAX-ACCESS not-accessible
	STATUS current
	DESCRIPTION
		"A list of Ethernet interfaces"
    ::= { nsModConfigInterface  3 }
          
nsModConfigInterfaceEthernetEntry OBJECT-TYPE
    SYNTAX      ModConfigInterfaceEthernetEntry
    MAX-ACCESS  not-accessible
    STATUS      current
    DESCRIPTION "Conceptual row in table for each Ethernet interface."
    INDEX   { ifIndex }
    ::= { nsModConfigInterfaceEthernetTable 1 }
            
ModConfigInterfaceEthernetEntry ::=
    SEQUENCE {
        nsModConfigInterfaceEthernetAutoNegotiation    INTEGER,
        nsModConfigInterfaceEthernetSpeed              INTEGER,
        nsModConfigInterfaceEthernetDuplex             INTEGER,
        nsModConfigInterfaceEthernetEncapsulation      INTEGER,
        nsModConfigInterfaceEthernetPid                Integer32
    } 
                

nsModConfigInterfaceEthernetAutoNegotiation  OBJECT-TYPE
        SYNTAX  INTEGER {
            disable (0),
            enable (1),
            notApplicable (255)
        }
        MAX-ACCESS  read-write
        STATUS  current
        DESCRIPTION
                "This parameter holds Ethernet interface auto-negotiation status"
        ::= { nsModConfigInterfaceEthernetEntry  1 }
        
nsModConfigInterfaceEthernetSpeed  OBJECT-TYPE
        SYNTAX  INTEGER {
            speed10 (0),
            speed100 (1),
            notApplicable (255)
        }
        MAX-ACCESS  read-write
        STATUS  current
        DESCRIPTION
                "This parameter holds Ethernet interface speed"
        ::= { nsModConfigInterfaceEthernetEntry  2 }          
        
nsModConfigInterfaceEthernetDuplex  OBJECT-TYPE
        SYNTAX  INTEGER {
            half (0),
            full (1),
            notApplicable (255)
        }
        MAX-ACCESS  read-write
        STATUS  current
        DESCRIPTION
                "This parameter holds Ethernet interface Duplex"
        ::= { nsModConfigInterfaceEthernetEntry  3 }     

nsModConfigInterfaceEthernetEncapsulation  OBJECT-TYPE
        SYNTAX  INTEGER {
            raw (0),
            nspe (1),
            gse  (2),
            ule  (3),
            notApplicable (255)
        }
        MAX-ACCESS  read-write
        STATUS  current
        DESCRIPTION
                "This parameter holds Ethernet interface Encapsulation"
        ::= { nsModConfigInterfaceEthernetEntry  4 }                           

nsModConfigInterfaceEthernetPid  OBJECT-TYPE
        SYNTAX  Integer32 (32..8191)
        MAX-ACCESS  read-write
        STATUS  current
        DESCRIPTION
                "This parameter holds Ethernet interface PID value"
        ::= { nsModConfigInterfaceEthernetEntry  5 }    
        
        
nsModConfigInterfaceGigETable  OBJECT-TYPE
    SYNTAX SEQUENCE OF ModConfigInterfaceGigEEntry
    MAX-ACCESS not-accessible
    STATUS current
    DESCRIPTION
        "A list of GigE interfaces"
    ::= { nsModConfigInterface  4 }
          
nsModConfigInterfaceGigEEntry OBJECT-TYPE
    SYNTAX      ModConfigInterfaceGigEEntry
    MAX-ACCESS  not-accessible
    STATUS      current
    DESCRIPTION "Conceptual row in table for each gigE interface."
    INDEX   { ifIndex }
    ::= { nsModConfigInterfaceGigETable 1 }
            
ModConfigInterfaceGigEEntry ::=
    SEQUENCE {
        nsModConfigInterfaceGigEAutoNegotiation    INTEGER,
        nsModConfigInterfaceGigESpeed              INTEGER,
        nsModConfigInterfaceGigEDuplex             INTEGER,
        nsModConfigInterfaceGigEPortType           INTEGER
    } 
                

nsModConfigInterfaceGigEAutoNegotiation  OBJECT-TYPE
        SYNTAX  INTEGER {
            disable (0),
            enable (1),
            notApplicable (255)
        }
        MAX-ACCESS  read-write
        STATUS  current
        DESCRIPTION
                "This parameter holds GigE interface auto-negotiation status"
        ::= { nsModConfigInterfaceGigEEntry  1 }
        
nsModConfigInterfaceGigESpeed  OBJECT-TYPE
        SYNTAX  INTEGER {
            speed10 (0),
            speed100 (1),
            notApplicable (255)
        }
        MAX-ACCESS  read-write
        STATUS  current
        DESCRIPTION
                "This parameter holds GigE interface speed"
        ::= { nsModConfigInterfaceGigEEntry  2 }          
        
nsModConfigInterfaceGigEDuplex  OBJECT-TYPE
        SYNTAX  INTEGER {
            half (0),
            full (1),
            notApplicable (255)
        }
        MAX-ACCESS  read-write
        STATUS  current
        DESCRIPTION
                "This parameter holds GigE interface Duplex"
        ::= { nsModConfigInterfaceGigEEntry  3 }     

nsModConfigInterfaceGigEPortType  OBJECT-TYPE
        SYNTAX  INTEGER {
            rj45 (0),
            sfp (1),
            notApplicable (255)
        }
        MAX-ACCESS  read-write
        STATUS  current
        DESCRIPTION
                "This parameter holds GigE interface port type value"
        ::= { nsModConfigInterfaceGigEEntry  5 }                        
                        
                        
-- ===================================================
nsModConfigCid  OBJECT-IDENTITY
        STATUS current
        DESCRIPTION
              "Modulator MIB branch that holds all Modulator CID parameters."
        ::= { nsModConfig 4 }

nsModConfigCidState  OBJECT-TYPE
        SYNTAX  INTEGER {
        	disabled (0),
            enabled (1),
            notApplicable (255)
        }
        MAX-ACCESS  read-write
        STATUS  current
        DESCRIPTION
                "This parameter determine the CID state: enabled/disabled."
        ::= { nsModConfigCid  1 }

nsModConfigCidLatitude  OBJECT-TYPE
        SYNTAX  DisplayString (SIZE(0..255))
        MAX-ACCESS  read-write
        STATUS  current
        DESCRIPTION
                "This parameter determine the CID latitude to transmit."
        ::= { nsModConfigCid  2 }  

nsModConfigCidLongitude  OBJECT-TYPE
        SYNTAX  DisplayString (SIZE(0..255))
        MAX-ACCESS  read-write
        STATUS  current
        DESCRIPTION
                "This parameter determine the CID longitude to transmit."
        ::= { nsModConfigCid  3 }  

nsModConfigCidPhone  OBJECT-TYPE
        SYNTAX  DisplayString (SIZE(0..255))
        MAX-ACCESS  read-write
        STATUS  current
        DESCRIPTION
                "This parameter determine the CID phone number to transmit."
        ::= { nsModConfigCid  4 }  

nsModConfigCidExtension  OBJECT-TYPE
        SYNTAX  DisplayString (SIZE(0..255))
        MAX-ACCESS  read-write
        STATUS  current
        DESCRIPTION
                "This parameter determine the CID phone extension to transmit."
        ::= { nsModConfigCid  5 }  

nsModConfigCidUsertext  OBJECT-TYPE
        SYNTAX  DisplayString (SIZE(0..255))
        MAX-ACCESS  read-write
        STATUS  current
        DESCRIPTION
                "This parameter determine the CID user text to transmit."
        ::= { nsModConfigCid  6 }  
                                   
-- ===================================================
nsModMonitor  OBJECT-IDENTITY
        STATUS current
        DESCRIPTION
              "Modulator MIB branch that holds all Demodulator status and alarms."
        ::= { nsModulator 2 }


nsModMonitorInterface  OBJECT-IDENTITY
        STATUS current
        DESCRIPTION
              "Modulator MIB branch that holds all Modulator interface statuses."
        ::= { nsModMonitor 1 }

nsModMonitorInterfaceTable OBJECT-TYPE
    SYNTAX SEQUENCE OF ModMonitorInterfaceEntry
    MAX-ACCESS not-accessible
    STATUS current
    DESCRIPTION
        "A list of interface statuses"
    ::= { nsModMonitorInterface 1 } 
    
nsModMonitorInterfaceEntry OBJECT-TYPE
    SYNTAX      ModMonitorInterfaceEntry
    MAX-ACCESS  not-accessible
    STATUS      current
    DESCRIPTION "Conceptual row in table for each interface."
    INDEX   { ifIndex }
    ::= { nsModMonitorInterfaceTable 1 }   
        
ModMonitorInterfaceEntry ::=
    SEQUENCE {
        nsModMonitorInterfaceDataRate         Counter32,
        nsModMonitorInterfaceStatus           INTEGER,
        nsModMonitorInterfaceChannel          INTEGER,
        nsModMonitorInterfaceName             DisplayString
    }   
    
nsModMonitorInterfaceDataRate  OBJECT-TYPE
        SYNTAX  Counter32
        MAX-ACCESS  read-only
        STATUS  current
        DESCRIPTION
                "This parameter holds Interface data rate status (bps)."
        ::= { nsModMonitorInterfaceEntry  1 }

nsModMonitorInterfaceStatus  OBJECT-TYPE
        SYNTAX  INTEGER {
            notLocked (0),
            locked    (1),
            inactive  (2),
            notApplicable (255)
        }
        MAX-ACCESS  read-only
        STATUS  current
        DESCRIPTION
                "This parameter holds Interface status."
        ::= { nsModMonitorInterfaceEntry  2 }
        
nsModMonitorInterfaceChannel  OBJECT-TYPE
        SYNTAX  INTEGER {
            none (0),
            channel-1 (1),
            channel-2 (2),
            notApplicable (255)
        }
        MAX-ACCESS  read-only
        STATUS  current
        DESCRIPTION
                "This parameter holds Interface channel."
        ::= { nsModMonitorInterfaceEntry  3 }        

nsModMonitorInterfaceName  OBJECT-TYPE
        SYNTAX  DisplayString (SIZE(0..255))
        MAX-ACCESS  read-only
        STATUS  current
        DESCRIPTION
                "This parameter holds Interface name."
        ::= { nsModMonitorInterfaceEntry  4 }  

-- ===================================================

nsModMonitorSystem  OBJECT-IDENTITY
        STATUS current
        DESCRIPTION
              "Modulator MIB branch that holds all Modulator system statuses."
        ::= { nsModMonitor 2 }

nsModMonitorSystemBoardTmp  OBJECT-TYPE
        SYNTAX  Integer32 
        MAX-ACCESS  read-only
        STATUS  current
        DESCRIPTION
                "This parameter holds system board temperature status in hundreds of Celsius degrees."
        ::= { nsModMonitorSystem  1 }

nsModMonitorSystem10MHrzClkSource  OBJECT-TYPE
        SYNTAX  INTEGER {
            internal (0),
            external (1),
            notApplicable (255)
        }
        MAX-ACCESS  read-only
        STATUS  current
        DESCRIPTION
                "This parameter holds system 10MHrz clock source."
        ::= { nsModMonitorSystem  2 }

nsModMonitorSystemRefClkOut  OBJECT-TYPE
        SYNTAX  INTEGER {
            off (0),
            on (1),
            notApplicable (255)
        }
        MAX-ACCESS  read-only
        STATUS  current
        DESCRIPTION
                "This parameter holds system ref clock out."
        ::= { nsModMonitorSystem  3 }

nsModMonitorSystemTxPortClk  OBJECT-TYPE
        SYNTAX  INTEGER {
            off (0),
            lband (1),
            buc (2),
            notApplicable (255)
        }
        MAX-ACCESS  read-only
        STATUS  current
        DESCRIPTION
                "This parameter holds system TX port clock."
        ::= { nsModMonitorSystem  4 }

-- ===================================================


nsModMonitorEthernet  OBJECT-IDENTITY
         STATUS current
        DESCRIPTION
              "Common MIB branch that holds all Ethernet statistics."
        ::= { nsModMonitor 3 }
 
nsModMonitorEthernetTable OBJECT-TYPE
	SYNTAX SEQUENCE OF DemodEthernetStatisticsEntry
	MAX-ACCESS not-accessible
	STATUS current
	DESCRIPTION
		"List of Ethernet Statistics"
	::= { nsModMonitorEthernet 1 } 

nsModMonitorEthernetEntry OBJECT-TYPE
    SYNTAX      DemodEthernetStatisticsEntry
    MAX-ACCESS  not-accessible
    STATUS      current
    DESCRIPTION "Conceptual row in table for each event."
    INDEX   { nsModMonitorEthernetStatisticsNumber }
    ::= { nsModMonitorEthernetTable 1 }
        
DemodEthernetStatisticsEntry ::=
	SEQUENCE {
		nsModMonitorEthernetStatisticsNumber	Counter32,
		nsModMonitorEthernetStatisticsName		DisplayString,
		nsModMonitorEthernetStatisticsValueA	Integer32,
		nsModMonitorEthernetStatisticsValueB	Integer32
	} 
    
nsModMonitorEthernetStatisticsNumber  OBJECT-TYPE
        SYNTAX  Counter32
        MAX-ACCESS  not-accessible
        STATUS  current
        DESCRIPTION
                "Ethernet Statistics Number"
        ::= { nsModMonitorEthernetEntry  1 }        
 
nsModMonitorEthernetStatisticsName  OBJECT-TYPE
        SYNTAX  DisplayString (SIZE(0..255))
        MAX-ACCESS  read-only
        STATUS  current
        DESCRIPTION
                "Name of Ethernet Statistics"
        ::= { nsModMonitorEthernetEntry  2 }  
 
nsModMonitorEthernetStatisticsValueA  OBJECT-TYPE
        SYNTAX  Integer32
        MAX-ACCESS  read-only
        STATUS  current
        DESCRIPTION
                "Value of Ethernet Statistics"
        ::= { nsModMonitorEthernetEntry  3 }   
        
nsModMonitorEthernetStatisticsValueB  OBJECT-TYPE
        SYNTAX  Integer32
        MAX-ACCESS  read-only
        STATUS  current
        DESCRIPTION
                "Value of Ethernet Statistics"
        ::= { nsModMonitorEthernetEntry  4 }          


-- ===================================================

nsModMonitorAcm  OBJECT-IDENTITY
         STATUS current
        DESCRIPTION
              "Common MIB branch that holds all ACM statistics."
        ::= { nsModMonitor 4 }
 
nsModMonitorAcmTable OBJECT-TYPE
	SYNTAX SEQUENCE OF ModAcmStatisticsEntry
	MAX-ACCESS not-accessible
	STATUS current
	DESCRIPTION
		"List of ACM Statistics"
	::= { nsModMonitorAcm 1 } 

nsModMonitorAcmEntry OBJECT-TYPE
    SYNTAX      ModAcmStatisticsEntry
    MAX-ACCESS  not-accessible
    STATUS      current
    DESCRIPTION "Conceptual row in table for each event."
    INDEX   { nsModMonitorAcmStatisticsNumber }
    ::= { nsModMonitorAcmTable 1 }
        
ModAcmStatisticsEntry ::=
	SEQUENCE {
		nsModMonitorAcmStatisticsNumber			        Unsigned32,
		nsModMonitorAcmStatisticsClientIp		        IpAddress,
        nsModMonitorAcmStatisticsClientName             DisplayString,
		nsModMonitorAcmStatisticsClientSnr		        Integer32,
		nsModMonitorAcmStatisticsClientMargin	        Integer32,
		nsModMonitorAcmStatisticsChannelNum		        INTEGER,
		nsModMonitorAcmStatisticsLineMode		        INTEGER,
		nsModMonitorAcmStatisticsModulation           	INTEGER,
		nsModMonitorAcmStatisticsFecRate          		INTEGER,
        nsModMonitorAcmStatisticsFrameSize              INTEGER,
		nsModMonitorAcmStatisticsPilot            		INTEGER,
		nsModMonitorAcmStatisticsIsLocked               INTEGER,
		nsModMonitorAcmStatisticsIsWorstCase            INTEGER,
		nsModMonitorAcmStatisticsState                  INTEGER,
		nsModMonitorAcmStatisticsGroup                  Unsigned32
	} 
    
nsModMonitorAcmStatisticsNumber  OBJECT-TYPE
        SYNTAX  Unsigned32
        MAX-ACCESS  not-accessible
        STATUS  current
        DESCRIPTION
                "ACM Statistics Number"
        ::= { nsModMonitorAcmEntry  1 }        
    
nsModMonitorAcmStatisticsClientIp  OBJECT-TYPE
        SYNTAX  IpAddress
        MAX-ACCESS  read-only
        STATUS  current
        DESCRIPTION
                "ACM Statistics- Client IP"
        ::= { nsModMonitorAcmEntry  2 }        

nsModMonitorAcmStatisticsClientName  OBJECT-TYPE
        SYNTAX  DisplayString (SIZE(0..255))
        MAX-ACCESS  read-only
        STATUS  current
        DESCRIPTION
                "ACM client's name"
        ::= { nsModMonitorAcmEntry  3 }  
 
nsModMonitorAcmStatisticsClientSnr  OBJECT-TYPE
        SYNTAX  Integer32
        MAX-ACCESS  read-only
        STATUS  current
        DESCRIPTION
                "ACM Statistics- Received SNR from client hundreds of dB"
        ::= { nsModMonitorAcmEntry  4 }  
 
nsModMonitorAcmStatisticsClientMargin  OBJECT-TYPE
        SYNTAX  Integer32
        MAX-ACCESS  read-only
        STATUS  current
        DESCRIPTION
                "ACM Statistics- Received margin from client"
        ::= { nsModMonitorAcmEntry  5 }   
        
nsModMonitorAcmStatisticsChannelNum  OBJECT-TYPE
        SYNTAX  INTEGER {
            channel-1 (0),
            channel-2 (1),
            notApplicable (255)
        }        MAX-ACCESS  read-only
        STATUS  current
        DESCRIPTION
                "ACM Statistics- Channel number"
        ::= { nsModMonitorAcmEntry  6 }     
        
nsModMonitorAcmStatisticsLineMode  OBJECT-TYPE
        SYNTAX  INTEGER {
            dvbs (0),
            dsng (1),
			dvbs2 (2),
			ns3 (3),
            notApplicable (255)
        }        
        MAX-ACCESS  read-only
        STATUS  current
        DESCRIPTION
                "ACM Statistics- Modulator line mode value"
        ::= { nsModMonitorAcmEntry  7 }      
        
nsModMonitorAcmStatisticsModulation  OBJECT-TYPE
        SYNTAX  INTEGER {
            modulationBpsk   (0),
            modulationQpsk   (1),
            modulation8Psk   (2),
            modulation16Qam  (3),
            modulation16Apsk (4),
            modulation32Apsk (5),
            modulation64Apsk (6),
            notApplicable (255)
        }        
        MAX-ACCESS  read-only
        STATUS  current
        DESCRIPTION
                "ACM Statistics- Matching MCT modulation value"
        ::= { nsModMonitorAcmEntry  8 }      
        
nsModMonitorAcmStatisticsFecRate  OBJECT-TYPE
        SYNTAX  INTEGER {
            fec1Div5   (0),
            fec1Div4   (1),
            fec1Div3   (2),
            fec2Div5   (3),
            fec13Div30 (4),
            fec4Div9   (5),
            fec7Div15  (6),
            fec22Div45 (7),
            fec1Div2   (8),
            fec8Div15  (9),
            fec5Div9   (10),
            fec17Div30 (11),
            fec3Div5   (12),
            fec28Div45 (13),
            fec19Div30 (14),
            fec2Div3   (15),
            fec32Div45 (16),
            fec11Div15 (17),
            fec3Div4   (18),
            fec7Div9   (19),
            fec4Div5   (20),
            fec37Div45 (21),
            fec5Div6   (22),
            fec7Div8   (23),
            fec8Div9   (24),
            fec9Div10  (25),
            notApplicable (255)
        }        
        MAX-ACCESS  read-only
        STATUS  current
        DESCRIPTION
                "ACM Statistics- Matching MCT FEC rate value
                    fec1Div5   = 1/5
                    fec1Div4   = 1/4
                    fec1Div3   = 1/3
                    fec2Div5   = 2/5
                    fec13Div30 = 13/30
                    fec4Div9   = 4/9
                    fec7Div15  = 7/15
                    fec22Div45 = 22/45
                    fec1Div2   = 1/2
                    fec8Div15  = 8/15
                    fec5Div9   = 5/9
                    fec17Div30 = 17/30
                    fec3Div5   = 3/5
                    fec28Div45 = 28/45
                    fec19Div30 = 19/30
                    fec2Div3   = 2/3
                    fec32Div45 = 32/45
                    fec11Div15 = 11/15
                    fec3Div4   = 3/4
                    fec7Div9   = 7/9
                    fec4Div5   = 4/5
                    fec37Div45 = 37/45
                    fec5Div6   = 5/6
                    fec7Div8   = 7/8
                    fec8Div9   = 8/9
                    fec9Div10  = 9/10                  
                "
        ::= { nsModMonitorAcmEntry  9 }         
                                        
nsModMonitorAcmStatisticsFrameSize  OBJECT-TYPE
        SYNTAX  INTEGER {
			normal (0),
			short (1),
            notApplicable (255)
        }        
        MAX-ACCESS  read-only
        STATUS  current
        DESCRIPTION
                "ACM Statistics- Matching MCT frame size value"
        ::= { nsModMonitorAcmEntry  10 }
        
nsModMonitorAcmStatisticsPilot  OBJECT-TYPE
        SYNTAX  INTEGER {
            pilotNo       (0),
            pilot16Slots (1),
			pilot8Slots  (2),
            notApplicable (255)
        }      
        MAX-ACCESS  read-only
        STATUS  current
        DESCRIPTION
                "ACM Statistics- Matching MCT pilot value"
        ::= { nsModMonitorAcmEntry  11 }           
               
nsModMonitorAcmStatisticsIsLocked  OBJECT-TYPE
        SYNTAX  INTEGER {
            no            (0),
            yes           (1),
            notApplicable (255)
        }      
        MAX-ACCESS  read-only
        STATUS  current
        DESCRIPTION
                "ACM Statistics- Is client locked"
        ::= { nsModMonitorAcmEntry  12 }   

nsModMonitorAcmStatisticsIsWorstCase  OBJECT-TYPE
        SYNTAX  INTEGER {
            no            (0),
            yes           (1),
            notApplicable (255)
        }      
        MAX-ACCESS  read-only
        STATUS  current
        DESCRIPTION
                "ACM Statistics- no longer supported"
        ::= { nsModMonitorAcmEntry  13 } 
        
nsModMonitorAcmStatisticsState  OBJECT-TYPE
        SYNTAX  INTEGER {
            active        (0),
            progress      (1),
            lost          (2),
            idle		  (3),
            notApplicable (255)
        }      
        MAX-ACCESS  read-only
        STATUS  current
        DESCRIPTION
                "ACM Statistics- Client's state"
        ::= { nsModMonitorAcmEntry  14 }            

nsModMonitorAcmStatisticsGroup  OBJECT-TYPE
        SYNTAX  Unsigned32
        MAX-ACCESS  read-only
        STATUS  current
        DESCRIPTION
                "ACM Statistics- group"
        ::= { nsModMonitorAcmEntry  15 }   

-- ===================================================
nsModMonitorAcmStatisticsClrCmd  OBJECT-TYPE
        SYNTAX  INTEGER {
            none (0),
            execute (1),
            notApplicable (255)
        }
        MAX-ACCESS  read-write
        STATUS  current
        DESCRIPTION
                "Clear ACM statistics command" 
        ::= { nsModMonitorAcm  2 }


-- ===================================================



nsModMonitorAupc  OBJECT-IDENTITY
        STATUS current
        DESCRIPTION
              "Modulator MIB branch that holds all AUPC statistics."
        ::= { nsModMonitor 5 }
 
nsModMonitorAupcCurrentPower  OBJECT-TYPE
        SYNTAX  Integer32
        MAX-ACCESS  read-only
        STATUS  current
        DESCRIPTION
                "AUPC monitor - Current output power in hundreds of dBm"
        ::= { nsModMonitorAupc  1 }        

nsModMonitorAupcMinimalPower  OBJECT-TYPE
        SYNTAX  Integer32
        MAX-ACCESS  read-only
        STATUS  current
        DESCRIPTION
                "AUPC monitor - Minimal output power in hundreds of dBm"
        ::= { nsModMonitorAupc  2 }        

nsModMonitorAupcMaximalPower  OBJECT-TYPE
        SYNTAX  Integer32
        MAX-ACCESS  read-only
        STATUS  current
        DESCRIPTION
                "AUPC monitor - Maximal output power in hundreds of dBm"
        ::= { nsModMonitorAupc  3 }        

nsModMonitorAupcAveragePower  OBJECT-TYPE
        SYNTAX  Integer32
        MAX-ACCESS  read-only
        STATUS  current
        DESCRIPTION
                "AUPC monitor - Average output power in hundreds of dBm"
        ::= { nsModMonitorAupc  4 }        

nsModMonitorAupcEstimatedUplinkAttn  OBJECT-TYPE
        SYNTAX  Integer32
        MAX-ACCESS  read-only
        STATUS  current
        DESCRIPTION
                "AUPC monitor - Estimated uplink attenuation in hundreds of dBm"
        ::= { nsModMonitorAupc  5 }        

nsModMonitorAupcEstimatedDownlinkAttn  OBJECT-TYPE
        SYNTAX  Integer32
        MAX-ACCESS  read-only
        STATUS  current
        DESCRIPTION
                "AUPC monitor - Estimated downlink attenuation in hundreds of dBm"
        ::= { nsModMonitorAupc  6 }        

nsModMonitorAupcResetAvgCmd  OBJECT-TYPE
        SYNTAX  INTEGER {
            none (0),
            execute (1),
            notApplicable (255)
        }
        MAX-ACCESS  read-write
        STATUS  current
        DESCRIPTION
                "Restart AUPC monitor power averaging" 
        ::= { nsModMonitorAupc  7 }        

-- removed until further notice, still got a handler function though:
-- nsModMonitorAupcClearSkyCalibCmd  OBJECT-TYPE
--         SYNTAX  INTEGER {
--             none (0),
--             execute (1),
--             notApplicable (255)
--         }
--         MAX-ACCESS  read-write
--         STATUS  current
--         DESCRIPTION
--                 "Run AUPC clear sky calibration command" 
--         ::= { nsModMonitorAupc  8 }        
-- 

-- ===================================================

END

----------------------------------------------
-- NOVELSAT-MODULATOR.mib               --
----------------------------------------------
