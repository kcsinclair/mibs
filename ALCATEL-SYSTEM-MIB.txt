-- orig SYSTEM_MIB

SYSTEM-MIB DEFINITIONS ::= BEGIN

    IMPORTS enterprises
        FROM RFC1155-SMI
    ;

    alcatel OBJECT IDENTIFIER ::= { enterprises 637 }
    asd     OBJECT IDENTIFIER ::= { alcatel 61 }
    asam    OBJECT IDENTIFIER ::= { asd 1 }
    ant     OBJECT IDENTIFIER ::= { asd 2 }

END
