SL-SECU-MIB DEFINITIONS ::= BEGIN

IMPORTS
    MODULE-IDENTITY, OBJECT-TYPE,
    Integer32, transmission, IpAddress
          FROM SNMPv2-SMI
	InterfaceIndex		               	FROM IF-MIB
    DisplayString, TruthValue, RowStatus, DateAndTime
          FROM SNMPv2-TC
    MODULE-COMPLIANCE, OBJECT-GROUP
          FROM SNMPv2-CONF
    slMain				      		   	FROM SL-MAIN-MIB;

--  This is the MIB module for PL security.


slSecuMib MODULE-IDENTITY
	LAST-UPDATED "201105170000Z"
	ORGANIZATION "PacketLight Networks Ltd."
	CONTACT-INFO
		"Omri_Viner@PacketLight.com"
	DESCRIPTION
		"This security module. This mib is used to configure the firewall."
	::= { slMain 24 }


SlSecuInterface ::= TEXTUAL-CONVENTION
       STATUS       current
       DESCRIPTION
       "The security protocol types:
        	oamp 	- Remote management port (eth0)
        	cit  	- Craft Interface for device management with Web GUI or CLI (eth1)"
       SYNTAX       INTEGER {
            oamp(1),
            cit(2),
            bothInifs(3)
       }

SlSecuAction ::= TEXTUAL-CONVENTION
       STATUS       current
       DESCRIPTION
       "The rule action:
        	drop 	- block the packet
        	pass  	- pass the packet"
       SYNTAX       INTEGER {
            drop(1),
            pass(2)
       }

SlSecuEstablished ::= TEXTUAL-CONVENTION
       STATUS       current
       DESCRIPTION
       "The rule action:
        	clear 	- established bit is (0)
        	set  	- established bit is (1)"
       SYNTAX       INTEGER {
            clear(1),
            set(2)
       }


SlSecuType ::= TEXTUAL-CONVENTION
       STATUS       current
       DESCRIPTION
       "The security protocol types:
        	Telnet 	- Teslnet Server
        	SSH  	- Secured Telnet Server
        	HTTP 	- Hyper Text Server
        	HTTPS	- Secured HTTP Server
        	ICMP	- Ping
        	SNMP	- Simple Network Management (only 161 is supported)
        	FTP		- File Server
        	TFTP	- Trivial FTP Client
        	TL1		- TL1 over Telnet
        	TL1SSH  - TL1 over SSH
        	WL		- White list (port number is 0)
        	SNMPOVERTCP - SNMP over TCP
        	SFTP	- Secure FTP Client 
        	NTP		- NTP server
        	RADIUS	- RADIUS client
        	FTPC	- FTP client
        	DHCPC	- DHCP Client
        	DHCPS	- DHCP Server
        	Telnetc	- Telnet Client"
       SYNTAX       INTEGER {
            telnet(1),
            ssh(2),
            http(3),
            https(4),
            icmp(5),
            snmp(6),
            ftp(7),
            tftp(8),
            tl1(9),
            tl1ssh(10),
            wl(11),
            snmpovertcp(12),  
            sftp(13),  
            ntp(14),  
            radius(15),  
            ftpc(16),  
            dhcpc(17),  
            dhcps(18),  
            telnetc(19)  
       }


slSecuGen	            OBJECT IDENTIFIER ::= { slSecuMib 1 }
slSecuSelect            OBJECT IDENTIFIER ::= { slSecuMib 2 }
slSecuWl		        OBJECT IDENTIFIER ::= { slSecuMib 3 }  
slSecuEncryption	    OBJECT IDENTIFIER ::= { slSecuMib 4 }  


-- The Security general part 

slSecuFirewallEnable OBJECT-TYPE
    SYNTAX TruthValue
    MAX-ACCESS read-write
    STATUS current
    DESCRIPTION
       "General Enable/Disable of the firewall operation."
       ::= { slSecuGen 1 }

-- The Security Selection Table 

slSecuSelectTable OBJECT-TYPE
    SYNTAX  SEQUENCE OF SlSecuSelectEntry
    MAX-ACCESS  not-accessible
    STATUS  current
    DESCRIPTION
       "The security protocol selection table."
     ::= { slSecuSelect 1 }

slSecuSelectEntry OBJECT-TYPE
    SYNTAX  SlSecuSelectEntry
    MAX-ACCESS  not-accessible
    STATUS  current
    DESCRIPTION
       "An entry in the security selection table."
    INDEX   { slSecuSelectType }            
     ::= { slSecuSelectTable 1 }

SlSecuSelectEntry ::=
    SEQUENCE {
         slSecuSelectType			  	SlSecuType,
         slSecuSelectPort				INTEGER,
         slSecuSelectEnable	  			TruthValue
    }

slSecuSelectType OBJECT-TYPE
    SYNTAX  SlSecuType
    MAX-ACCESS  not-accessible
    STATUS  current
    DESCRIPTION
      "The secutity protocol type"
     ::= { slSecuSelectEntry 1 }

slSecuSelectPort OBJECT-TYPE
    SYNTAX  INTEGER
    MAX-ACCESS  read-only
    STATUS  current
    DESCRIPTION
      "The corresponding port number of the protocol.
       Port number 0 is used when not applicable/available."
     ::= { slSecuSelectEntry 2 }

slSecuSelectEnable OBJECT-TYPE
    SYNTAX  TruthValue
    MAX-ACCESS  read-write
    STATUS  current
    DESCRIPTION
      "True - Enables the firewall for the corresponding protocol.
       False - Dsables the firewall for the corresponding protocol.
       When enabled the firewall blocks the protocol."
     ::= { slSecuSelectEntry 3 }



--  IP White List Table

--  The IP white list Table odefine which IP addresses are allowed.

slSecuWlTable OBJECT-TYPE
    SYNTAX   SEQUENCE OF SlSecuWlEntry
    MAX-ACCESS not-accessible
    STATUS   current
    DESCRIPTION
       "This white list table."
    ::= { slSecuWl 1 }

slSecuWlEntry OBJECT-TYPE
    SYNTAX   SlSecuWlEntry
    MAX-ACCESS not-accessible
    STATUS   current
    DESCRIPTION
       "A particular IP address."
    INDEX { slSecuWlIp }
    ::= { slSecuWlTable 1 }

SlSecuWlEntry ::=
    SEQUENCE {
        slSecuWlIp
            IpAddress,
        slSecuWlMask
            IpAddress,
        slSecuWlStatus
            RowStatus
    }

slSecuWlIp OBJECT-TYPE
    SYNTAX   IpAddress
    MAX-ACCESS read-only
    STATUS   current
    DESCRIPTION
       "The IP address to allow"
    ::= { slSecuWlEntry 1 }

slSecuWlMask OBJECT-TYPE
    SYNTAX   IpAddress
    MAX-ACCESS read-only
    STATUS   current
    DESCRIPTION
       "Indicate the mask to be logical-ANDed with the
       destination  address  before  being compared to
       the value  in  the  slSecuWlIp field."
    ::= { slSecuWlEntry 2 }

slSecuWlStatus OBJECT-TYPE
    SYNTAX   RowStatus
    MAX-ACCESS read-create
    STATUS   current
    DESCRIPTION
       "The row status variable, used according to
       row installation and removal conventions."
    ::= { slSecuWlEntry 3 }


--
-- The IPACL Table 
--

slSecuAclTable OBJECT-TYPE
    SYNTAX  SEQUENCE OF SlSecuAclEntry
    MAX-ACCESS  not-accessible
    STATUS  current
    DESCRIPTION
       "The security protocol ACL table."
     ::= { slSecuSelect 2 }

slSecuAclEntry OBJECT-TYPE
    SYNTAX  SlSecuAclEntry
    MAX-ACCESS  not-accessible
    STATUS  current
    DESCRIPTION
       "An entry in the security ACL table."
    INDEX   { slSecuAclType, slSecuAclIndex }            
     ::= { slSecuAclTable 1 }

SlSecuAclEntry ::=
    SEQUENCE {
        slSecuAclType			  	SlSecuType,		-- AccessID
		slSecuAclIndex				INTEGER,		-- 1..32		
		slSecuAclInterface			SlSecuInterface,-- 1..32		
		slSecuAclSourceIp			IpAddress,		-- Source IP		
		slSecuAclSourceIpMask		INTEGER,		-- 0..32		
		slSecuAclDestIp				IpAddress,		-- Destination IP		
		slSecuAclDestIpMask			INTEGER,		-- 0..32		
        slSecuAclSourcePortStart	INTEGER,        -- 0-65535
        slSecuAclSourcePortEnd		INTEGER,        -- 0-65535
        slSecuAclDestPortStart		INTEGER,        -- 0-65535
        slSecuAclDestPortEnd		INTEGER,        -- 0-65535
        slSecuAclIcmpType			INTEGER,        -- 0-255
        slSecuAclIcmpCode			INTEGER,        -- 0-255
		slSecuAclRowStatus			RowStatus,  	
        slSecuAclAction	  			SlSecuAction,
        slSecuAclEstablished		SlSecuEstablished
    }

slSecuAclType OBJECT-TYPE
    SYNTAX  SlSecuType
    MAX-ACCESS  not-accessible
    STATUS  current
    DESCRIPTION
      "The AccessID"
     ::= { slSecuAclEntry 1 }

slSecuAclIndex OBJECT-TYPE
    SYNTAX  INTEGER (1..32)
    MAX-ACCESS  not-accessible
    STATUS  current
    DESCRIPTION
      "All index values should be continuous number with ascending order. 
      The new index could be [1, largest index+1] and could not select the larger number > index+1.
      When specifying index, the new rule is inserted before the existing rule indicated by the value of index. 
      When inserting a rule into a chain, index values of all existing rules (of the same chain) 
      with the same or a higher index value are incremented by one.
      For Add Row operation: If index is not entered, the new empty rule will be appended as last rule.
      For Delete Row operation: If the last rule is removed from a filter chain, leaving the chain empty, 
      all packets will be dropped, which are processed by that filter chain"
     ::= { slSecuAclEntry 2 }

slSecuAclInterface OBJECT-TYPE
    SYNTAX  SlSecuInterface
    MAX-ACCESS  read-write
    STATUS  current
    DESCRIPTION
      "The input interface.
       oamp - Remote management and daisy chain ports, share the same MAC and IP address (Etsec0)
       cit - Craft Interface for device management with Web GUI or CLI (Etsec1).
       bothInifs - both interfaces"
     ::= { slSecuAclEntry 3 }

slSecuAclSourceIp OBJECT-TYPE
    SYNTAX  IpAddress
    MAX-ACCESS  read-write
    STATUS  current
    DESCRIPTION
      "The source ip address of an access control rule."
     ::= { slSecuAclEntry 4 }

slSecuAclSourceIpMask OBJECT-TYPE
    SYNTAX  INTEGER (0..32)
    MAX-ACCESS  read-write
    STATUS  current
    DESCRIPTION
      "The mask of the source ip address."
     ::= { slSecuAclEntry 5 }

slSecuAclDestIp OBJECT-TYPE
    SYNTAX  IpAddress
    MAX-ACCESS  read-write
    STATUS  current
    DESCRIPTION
      "The destination ip address of an access control rule."
     ::= { slSecuAclEntry 6 }

slSecuAclDestIpMask OBJECT-TYPE
    SYNTAX  INTEGER (0..32)
    MAX-ACCESS  read-write
    STATUS  current
    DESCRIPTION
      "The mask of the destination ip address."
     ::= { slSecuAclEntry 7 }

slSecuAclSourcePortStart OBJECT-TYPE
    SYNTAX  INTEGER (0..65535)
    MAX-ACCESS  read-write
    STATUS  current
    DESCRIPTION
      "The start of the range of source port."
     ::= { slSecuAclEntry 8 }

slSecuAclSourcePortEnd OBJECT-TYPE
    SYNTAX  INTEGER (0..65535)
    MAX-ACCESS  read-write
    STATUS  current
    DESCRIPTION
      "The end of the range of source port."
     ::= { slSecuAclEntry 9 }

slSecuAclDestPortStart OBJECT-TYPE
    SYNTAX  INTEGER (0..65535)
    MAX-ACCESS  read-write
    STATUS  current
    DESCRIPTION
      "The start of the range of destination port."
     ::= { slSecuAclEntry 10 }

slSecuAclDestPortEnd OBJECT-TYPE
    SYNTAX  INTEGER (0..65535)
    MAX-ACCESS  read-write
    STATUS  current
    DESCRIPTION
      "The end of the range of destination port."
     ::= { slSecuAclEntry 11 }

slSecuAclIcmpType OBJECT-TYPE
    SYNTAX  INTEGER (0..255)
    MAX-ACCESS  read-write
    STATUS  current
    DESCRIPTION
      "The ICMP type."
     ::= { slSecuAclEntry 12 }

slSecuAclIcmpCode OBJECT-TYPE
    SYNTAX  INTEGER (0..255)
    MAX-ACCESS  read-write
    STATUS  current
    DESCRIPTION
      "The ICMP code."
     ::= { slSecuAclEntry 13 }

slSecuAclRowStatus 	OBJECT-TYPE
    SYNTAX      	RowStatus
    MAX-ACCESS  	read-create
    STATUS      	current
    DESCRIPTION
        "This object is used to create and delete rows in the
        slSecuAclTable."
       ::= { slSecuAclEntry 14 }

slSecuAclAction OBJECT-TYPE
    SYNTAX  SlSecuAction
    MAX-ACCESS  read-write
    STATUS  current
    DESCRIPTION
      "drop - drop the packet.
       pass - pass the packet."
     ::= { slSecuAclEntry 15 }

slSecuAclEstablished OBJECT-TYPE
    SYNTAX  SlSecuEstablished
    MAX-ACCESS  read-write
    STATUS  current
    DESCRIPTION
      "The Acknowledge bit in the TCP header - 
      when 0, it indicates that the packet is an initial call to the destination. 
      The host sending the message will clear the bit (0). 
      The host that responds to the message will set the bit(1) indicating this message is a response. 
      Effectively the call is now Established."
     ::= { slSecuAclEntry 16 }



-- *******************************************
--
-- The Encryption Table
--
-- *******************************************
	
slSecuEncryptionTable OBJECT-TYPE
	SYNTAX  SEQUENCE OF SlSecuEncryptionEntry
	MAX-ACCESS  		not-accessible
	STATUS  			current
	DESCRIPTION
		"The encryption table. This table has an entry per transponder."
	::= { slSecuEncryption 1 }

slSecuEncryptionEntry OBJECT-TYPE
	SYNTAX  SlSecuEncryptionEntry
	MAX-ACCESS  not-accessible
	STATUS  current
	DESCRIPTION
		"This entry is used to control the necryption per transponder."
	INDEX   { slSecuEncryptionIfIndex }
	::= { slSecuEncryptionTable 1 }

SlSecuEncryptionEntry ::=
	SEQUENCE {
		slSecuEncryptionIfIndex				InterfaceIndex,
		slSecuEncryptionEnable				TruthValue,
		slSecuEncryptionStatus				INTEGER,
		slSecuEncryptionForceInit			INTEGER,
		slSecuEncryptionPreShared			DisplayString,
		slSecuEncryptionKeyExchangePeriod	INTEGER,
		slSecuEncryptionLock				TruthValue,
		slSecuEncryptionProtectedStatus		INTEGER
	}	

slSecuEncryptionIfIndex OBJECT-TYPE
    SYNTAX      InterfaceIndex
    MAX-ACCESS  read-only
    STATUS      current
    DESCRIPTION
        "The Interface Index of the uplink port."
    ::= { slSecuEncryptionEntry 1 }

slSecuEncryptionEnable OBJECT-TYPE
	SYNTAX        TruthValue
	MAX-ACCESS    read-write
	STATUS        current
	DESCRIPTION
		"Enable/Disable the encryption on this uplink."
	::= { slSecuEncryptionEntry 2 }

slSecuEncryptionStatus OBJECT-TYPE
	SYNTAX        INTEGER {
		init(1),      --- init/link-failure state
		exchange(2),  --- public key exchange state
		kdf(3),       --- key derivation function state
		active(4)     --- active state
	}
	MAX-ACCESS    read-only
	STATUS        current
	DESCRIPTION
		"The state of the encryption finite state machine."
	::= { slSecuEncryptionEntry 3 }

slSecuEncryptionForceInit OBJECT-TYPE
	SYNTAX        INTEGER
	MAX-ACCESS    read-write
	STATUS        current
	DESCRIPTION
		"Writing this valiable forces init to the encryption state machine."
	::= { slSecuEncryptionEntry 4 }

slSecuEncryptionPreShared OBJECT-TYPE
	SYNTAX        DisplayString 
	MAX-ACCESS    read-write
	STATUS        current
	DESCRIPTION
		"The pre-shared secret. 
		Either the pre-shared key, or the shared secret to avoid Mitm when using DH public key exchange."
	::= { slSecuEncryptionEntry 5 }

slSecuEncryptionKeyExchangePeriod OBJECT-TYPE
	SYNTAX        INTEGER 
	MAX-ACCESS    read-write
	STATUS        current
	DESCRIPTION
		"The Key Exchage Period, specified in minutes.
		The value 0 means to perform the key exchange only once at link establishment."
	::= { slSecuEncryptionEntry 6 }

slSecuEncryptionLock OBJECT-TYPE
	SYNTAX        TruthValue
	MAX-ACCESS    read-write
	STATUS        current
	DESCRIPTION
		"Lock/Unlock the encrypted service for this uplink."
	::= { slSecuEncryptionEntry 7 }

slSecuEncryptionProtectedStatus OBJECT-TYPE
	SYNTAX        INTEGER {
		init(1),      --- init/link-failure state
		exchange(2),  --- public key exchange state
		kdf(3),       --- key derivation function state
		active(4)     --- active state
	}
	MAX-ACCESS    read-only
	STATUS        current
	DESCRIPTION
		"The protected port state of the encryption finite state machine."
	::= { slSecuEncryptionEntry 8 }


END
