-- *****************************************************************
-- Trap Forward MIB
-- *****************************************************************

SL-TRAP-FORWARD-MIB DEFINITIONS ::= BEGIN

IMPORTS
    MODULE-IDENTITY, OBJECT-TYPE, NOTIFICATION-TYPE,
    IpAddress, TimeTicks, Counter32, snmpModules, mib-2
        FROM SNMPv2-SMI
	TEXTUAL-CONVENTION, DisplayString, 
	TruthValue, TimeStamp				FROM SNMPv2-TC
	MODULE-COMPLIANCE, OBJECT-GROUP,
	NOTIFICATION-GROUP                  FROM SNMPv2-CONF
	InterfaceIndex		               	FROM IF-MIB
	PerfCurrentCount, PerfIntervalCount,
	PerfTotalCount                      FROM PerfHist-TC-MIB
    slMain				      		   	FROM SL-MAIN-MIB;

slTrapForwardMib MODULE-IDENTITY
	LAST-UPDATED "200708280000Z"
	ORGANIZATION "PacketLight Networks Ltd."
	CONTACT-INFO
		"Omri_Viner@PacketLight.com"
	DESCRIPTION
		"This MIB module describes the configuration change and inventory events."
	::= { slMain 31 }



slTrapForwardObjects	OBJECT IDENTIFIER ::= { slTrapForwardMib 1 }
slTrapForwardTraps		OBJECT IDENTIFIER ::= { slTrapForwardMib 2 }
slTrapForwardTraps0		OBJECT IDENTIFIER ::= { slTrapForwardTraps 0 }

--
-- SL Trap Forward Objects 
--

slTrapFowardIpAddr	OBJECT-TYPE
    SYNTAX     		IpAddress
    MAX-ACCESS 		read-only
    STATUS     		current
    DESCRIPTION
        "The IP of the device that sent the trap."
    ::= { slTrapForwardObjects 1 }

slTrapForwardLogId		OBJECT-TYPE
    SYNTAX     		Gauge32
    MAX-ACCESS 		read-only
    STATUS     		current
    DESCRIPTION
        "The trap log id. The id increments each time a new log
        entry arrives."
    ::= { slTrapForwardObjects 2 }

slTrapFowardIfIndex	OBJECT-TYPE
    SYNTAX     		InterfaceIndex
    MAX-ACCESS 		read-only
    STATUS     		current
    DESCRIPTION
        "The object id of the trap."
    ::= { slTrapForwardObjects 3 }

slTrapForwardTimeStamp		OBJECT-TYPE
    SYNTAX     		TimeTicks
    MAX-ACCESS 		read-only
    STATUS     		current
    DESCRIPTION
        "The trap time stamp."
    ::= { slTrapForwardObjects 4 }

slTrapFowardObjId		OBJECT-TYPE
    SYNTAX     		OBJECT IDENTIFIER
    MAX-ACCESS 		read-only
    STATUS     		current
    DESCRIPTION
        "The Object ID of the trap."
    ::= { slTrapForwardObjects 5 }

slTrapForwardParam1	OBJECT-TYPE
    SYNTAX     		OCTET STRING (SIZE (0..80))
    MAX-ACCESS 		read-only
    STATUS     		current
    DESCRIPTION
        "The first parameter of the trap."
    ::= { slTrapForwardObjects 6 }

slTrapForwardParam2	OBJECT-TYPE
    SYNTAX     		OCTET STRING (SIZE (0..80))
    MAX-ACCESS 		read-only
    STATUS     		current
    DESCRIPTION
        "The second parameter of the trap."
    ::= { slTrapForwardObjects 7 }

slTrapFowardParam3	OBJECT-TYPE
    SYNTAX     		OCTET STRING (SIZE (0..80))
    MAX-ACCESS 		read-only
    STATUS     		current
    DESCRIPTION
        "The third parameter of the trap."
    ::= { slTrapForwardObjects 8 }

slTrapForwardParam4	OBJECT-TYPE
    SYNTAX     		OCTET STRING (SIZE (0..80))
    MAX-ACCESS 		read-only
    STATUS     		current
    DESCRIPTION
        "The forth parameter of the trap."
    ::= { slTrapForwardObjects 9 }

slTrapForwardParam5	OBJECT-TYPE
    SYNTAX     		OCTET STRING (SIZE (0..80))
    MAX-ACCESS 		read-only
    STATUS     		current
    DESCRIPTION
        "The fifth parameter of the trap."
    ::= { slTrapForwardObjects 10 }


--
-- SL Trap Forwarding Traps
--

slTrapForwardTrap NOTIFICATION-TYPE
	OBJECTS { 
		slTrapFowardIpAddr, 
		slTrapFowardLogId, 
		slTrapFowardIfIndex, 
		slTrapFowardTimeStamp, 
		slTrapFowardObjId, 
		slTrapFowardParam1, 
		slTrapFowardParam2, 
		slTrapFowardParam3, 
		slTrapFowardParam4, 
		slTrapFowardParam5 
       }
       STATUS  current
       DESCRIPTION
		"A slTrapForwardTrap is to be forward by the NMS to a North-Bound management systems."
       ::= { slTrapForwardTraps 1 }

slTrapForwardTrap0 NOTIFICATION-TYPE
	OBJECTS { 
		slTrapFowardIpAddr, 
		slTrapFowardLogId, 
		slTrapFowardIfIndex, 
		slTrapFowardTimeStamp, 
		slTrapFowardObjId, 
		slTrapFowardParam1, 
		slTrapFowardParam2, 
		slTrapFowardParam3, 
		slTrapFowardParam4, 
		slTrapFowardParam5 
       }
       STATUS  current
       DESCRIPTION     
		"A slTrapForwardTrap0 is to be forward by the NMS to a North-Bound management systems.
		It is defined to support browsers that don't recognize RFC 2576."
       ::= { slTrapForwardTraps0 1 }


END
