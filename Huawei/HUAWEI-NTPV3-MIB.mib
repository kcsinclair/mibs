-- ==================================================================
-- Copyright (C) 2010 by  HUAWEI TECHNOLOGIES. All rights reserved.
--
-- Description: HUAWEI NTPV3 MIB
-- Reference:
-- Version: V1.0
-- History:
-- <author>,  <date>,  <contents>
-- caibenrui   2010-9-9
-- ==================================================================
-- ==================================================================
--
-- Variables and types are imported
--
-- ==================================================================

    HUAWEI-NTPV3-MIB DEFINITIONS ::= BEGIN

         IMPORTS
            hwDatacomm
                FROM HUAWEI-MIB
            DisplayString
                FROM SNMPv2-TC
            OBJECT-GROUP, MODULE-COMPLIANCE, NOTIFICATION-GROUP
                FROM SNMPv2-CONF
            Integer32, IpAddress, OBJECT-TYPE, MODULE-IDENTITY, NOTIFICATION-TYPE
                FROM SNMPv2-SMI;


        hwNtpV3 MODULE-IDENTITY
            LAST-UPDATED "201009092100Z"        -- Sep 9, 2010 at 21:00 GMT
            ORGANIZATION
                "Huawei Technologies Co.,Ltd."
            CONTACT-INFO
                "VRP Team Huawei Technologies Co.,Ltd.
                Huawei Bld.,NO.3 Xinxi Rd.,
                Shang-Di Information Industry Base,
                Hai-Dian District Beijing P.R. China
                http://www.huawei.com
                Zip:100085
                "
            DESCRIPTION
                "The private mib file includes the general extent
                information of the device.hwDatacomm(25).hwNtpV3(234)"
            ::= { hwDatacomm 234 }




--
-- Node definitions
--

-- ==================================================================
--
-- ======================= definition begin =========================
--
-- ==================================================================
     hwNtpV3MibObjects OBJECT IDENTIFIER ::= { hwNtpV3 1 }


     hwNtpV3ServerIPAdd        OBJECT-TYPE
        SYNTAX              IpAddress
        MAX-ACCESS          read-write
        STATUS              current
        DESCRIPTION         "IP address or domain name of the NTP server"
        ::= { hwNtpV3MibObjects 1 }

     hwNtpV3TimeSyncPeriod OBJECT-TYPE
            SYNTAX Integer32
            MAX-ACCESS read-write
            STATUS current
            DESCRIPTION
                "NTP poll interval."
            ::= { hwNtpV3MibObjects 2 }

     hwNtpV3TimeAfterNTPCal OBJECT-TYPE
        SYNTAX DisplayString
        MAX-ACCESS read-only
        STATUS current
        DESCRIPTION
            "This node gives the current local time of the system.
            The unit of it is DateAndTime."
        ::= { hwNtpV3MibObjects 3 }

--    Conformance information
        hwNtpV3Conformance OBJECT IDENTIFIER ::= { hwNtpV3 2 }


        hwNtpV3Compliances OBJECT IDENTIFIER ::= { hwNtpV3Conformance 1 }


        hwNtpV3Compliance MODULE-COMPLIANCE
            STATUS current
            DESCRIPTION
                "The compliance statement for systems supporting
                the HUAWEI-NtpV3-MIB."
            MODULE -- this module
                MANDATORY-GROUPS { hwNtpV3ObjectGroup }
            ::= { hwNtpV3Compliances 1 }


        hwNtpV3Groups OBJECT IDENTIFIER ::= { hwNtpV3Conformance 2 }


        hwNtpV3ObjectGroup OBJECT-GROUP
            OBJECTS { hwNtpV3ServerIPAdd, hwNtpV3TimeSyncPeriod, hwNtpV3TimeAfterNTPCal }
            STATUS current
            DESCRIPTION
                "The NTPV3 attribute group."
            ::= { hwNtpV3Groups 1 }

    END
