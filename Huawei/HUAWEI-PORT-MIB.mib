--
-- HUAWEI-PORT-MIB.mib

-- Monday, November 28, 2011 at 15:24:55
--

    HUAWEI-PORT-MIB DEFINITIONS ::= BEGIN
 
        IMPORTS
            ImaFrameLength, ImaGroupState            
                FROM HUAWEI-IMA-MIB            
            hwDatacomm            
                FROM HUAWEI-MIB            
            InterfaceIndex            
                FROM IF-MIB            
            EnabledStatus            
                FROM P-BRIDGE-MIB            
            OBJECT-GROUP, MODULE-COMPLIANCE, NOTIFICATION-GROUP            
                FROM SNMPv2-CONF            
            IpAddress, Integer32, Unsigned32, Counter64, OBJECT-TYPE, 
            MODULE-IDENTITY, NOTIFICATION-TYPE            
                FROM SNMPv2-SMI            
            TruthValue, RowStatus            
                FROM SNMPv2-TC;
    
    
        -- 1.3.6.1.4.1.2011.5.25.157
        hwPortMIB MODULE-IDENTITY 
            LAST-UPDATED "201105180930Z"        -- May 18, 2011 at 09:30 GMT
            ORGANIZATION 
                "Huawei Technologies Co.,Ltd."
            CONTACT-INFO 
                "VRP Team Huawei Technologies Co.,Ltd.
                Huawei Bld.,NO.3 Xinxi Rd.,
                Shang-Di Information Industry Base,
                Hai-Dian District Beijing P.R. China
                http://www.huawei.com
                Zip:100085
                "
            DESCRIPTION 
                "The private mib file includes the general extent
                information of the device.hwDatacomm(157).hwPortMIB"
            ::= { hwDatacomm 157 }

        
    
    
--
-- Node definitions
--
    
        -- 1.3.6.1.4.1.2011.5.25.157.1
        hwPortMIBObjects OBJECT IDENTIFIER ::= { hwPortMIB 1 }

        
        -- 1.3.6.1.4.1.2011.5.25.157.1.1
        hwEthernet OBJECT IDENTIFIER ::= { hwPortMIBObjects 1 }

        
        -- 1.3.6.1.4.1.2011.5.25.157.1.1.1
        hwEthernetTable OBJECT-TYPE
            SYNTAX SEQUENCE OF HwEthernetEntry
            MAX-ACCESS not-accessible
            STATUS current
            DESCRIPTION
                "Indicates the physical attributes of the Ethernet interface.
                This table lists the physical attributes of various Ethernet interfaces."
            ::= { hwEthernet 1 }

        
        -- 1.3.6.1.4.1.2011.5.25.157.1.1.1.1
        hwEthernetEntry OBJECT-TYPE
            SYNTAX HwEthernetEntry
            MAX-ACCESS not-accessible
            STATUS current
            DESCRIPTION
                "Indicates the physical attributes of the Ethernet interface.
                This table lists the physical attributes of various Ethernet interfaces."
            INDEX { hwEthernetIfIndex }
            ::= { hwEthernetTable 1 }

        
        HwEthernetEntry ::=
            SEQUENCE { 
                hwEthernetIfIndex
                    InterfaceIndex,
                hwEthernetLoopback
                    INTEGER,
                hwEthernetPortType
                    INTEGER,
                hwEthernetSpeedSet
                    INTEGER,
                hwEthernetDuplex
                    INTEGER,
                hwEthernetNegotiation
                    EnabledStatus,
                hwEthernetPortTypeOperate
                    INTEGER,
                hwEthernetClock
                    INTEGER,
                hwEthernetFlagJ0Mode
                    INTEGER,
                hwEthernetFlagJ0Value
                    Integer32,
                hwEthernetFlagJ0Trace
                    OCTET STRING,
                hwEthernetFlagJ1Mode
                    INTEGER,
                hwEthernetFlagJ1Value
                    Integer32,
                hwEthernetFlagJ1Trace
                    OCTET STRING,
                hwEthernetFlagC2Value
                    Integer32,
                hwEthernetUpHoldTime
                    Integer32,
                hwEthernetDownHoldTime
                    Integer32,
                hwEthernetSubinterfaceStatisticEnable
                    EnabledStatus,
                hwEthernetFlowControl
                    INTEGER,
        hwEthernetOffline
            INTEGER,
        hwEthernetSetTransferMode
            INTEGER,
                hwEthernetJumboframeMaxLength
                    Integer32,
                hwEthernetComboType
                    INTEGER,
                hwEthernetPortMode
                       INTEGER,
                hwEthernetNegotiationMode
                       INTEGER
             }

        -- 1.3.6.1.4.1.2011.5.25.157.1.1.1.1.1
        hwEthernetIfIndex OBJECT-TYPE
            SYNTAX InterfaceIndex
            MAX-ACCESS not-accessible
            STATUS current
            DESCRIPTION
                "Interface index(es) of port(s) present on the device ."
            ::= { hwEthernetEntry 1 }

        
        -- 1.3.6.1.4.1.2011.5.25.157.1.1.1.1.11
        hwEthernetLoopback OBJECT-TYPE
            SYNTAX INTEGER
                {
                otherLoop(1),
                stopLoopback(2),
                local(3),
                remote(4)
                }
            MAX-ACCESS read-write
            STATUS current
            DESCRIPTION
                "The local loopback of an Ethernet interface is used to test the interface itself.
                If an interface works in a normal situation, disable the local loopback.
                By default, stopLoopback is used."
            ::= { hwEthernetEntry 11 }

        
        -- 1.3.6.1.4.1.2011.5.25.157.1.1.1.1.12
        hwEthernetPortType OBJECT-TYPE
            SYNTAX INTEGER
                {
                other(1),
                copper(2),
                fiber(3)
                }
            MAX-ACCESS read-write
            STATUS current
            DESCRIPTION
                "Indicates the type of the Ethernet interface: an optical interface or an electrical interface."
            ::= { hwEthernetEntry 12 }

        
        -- 1.3.6.1.4.1.2011.5.25.157.1.1.1.1.13
        hwEthernetSpeedSet OBJECT-TYPE
            SYNTAX INTEGER
                {
                other(1),
                speed10(2),
                speed100(3),
                speed1000(4),
                speed10000(5)
                }
            MAX-ACCESS read-write
            STATUS current
            DESCRIPTION
                "Indicates the speed of the Ethernet interface. This parameter takes effect only on some Ethernet
                electrical interfaces rather than optical interfaces. The parameter can be 10 M, 100 M, 1000 M,
                10000 M."
            ::= { hwEthernetEntry 13 }

        
        -- 1.3.6.1.4.1.2011.5.25.157.1.1.1.1.14
        hwEthernetDuplex OBJECT-TYPE
            SYNTAX INTEGER
                {
                full(1),
                half(2)
                }
            MAX-ACCESS read-write
            STATUS current
            DESCRIPTION
                "Indicates the duplex mode of the Ethernet interface. An electrical Ethernet interface can
                work in half-duplex mode or full-duplex mode. An optical Ethernet can work only in full-duplex mode."
            ::= { hwEthernetEntry 14 }

        
        -- 1.3.6.1.4.1.2011.5.25.157.1.1.1.1.15
        hwEthernetNegotiation OBJECT-TYPE
            SYNTAX EnabledStatus
            MAX-ACCESS read-write
            STATUS current
            DESCRIPTION
                "Indicates the auto-negotiation mode of the Ethernet electrical interface. By default, auto-negotiation is enabled.
                The three objects, hwEthernetSpeedSet, hwEthernetDuplex, and hwEthernetNegotiation are associated with each other.
                If the auto-negotiation of hwEthernetNegotiation is enabled, the values of hwEthernetSpeedSet and hwEthernetDuplex are auto-negotiated.
                If hwEthernetSpeedSet is set to a certain value, hwEthernetDuplex is modified to the default value full,
                and hwEthernetNegotiation is automatically changed to disable. If the auto-negotiation of hwEthernetNegotiation is
                enabled, hwEthernetDuplex cannot be set."
            ::= { hwEthernetEntry 15 }

        
        -- 1.3.6.1.4.1.2011.5.25.157.1.1.1.1.16
        hwEthernetPortTypeOperate OBJECT-TYPE
            SYNTAX INTEGER
                {
                other(1),
                copper(2),
                fiber100(3),
                fiber1000(4)
                }
            MAX-ACCESS read-write
            STATUS current
            DESCRIPTION
                "Indicates the link type of the Ethernet interface. The type can be optical link or electrical link.
                This parameter takes effect only on specific Ethernet interfaces."
            ::= { hwEthernetEntry 16 }

        
        -- 1.3.6.1.4.1.2011.5.25.157.1.1.1.1.20
        hwEthernetClock OBJECT-TYPE
            SYNTAX INTEGER
                {
                master(1),
                slave(2)
                }
            MAX-ACCESS read-write
            STATUS current
            DESCRIPTION
                "Indicates the mode of the clock. The mode can be master or slave.
                By default, the mode of a clock is slave. This parameter takes effect only on the WAN board."
            ::= { hwEthernetEntry 20 }

        
        -- 1.3.6.1.4.1.2011.5.25.157.1.1.1.1.21
        hwEthernetFlagJ0Mode OBJECT-TYPE
            SYNTAX INTEGER
                {
                j01ByteMode(1),
                j016ByteMode(2),
                j064ByteOrNullMode(3),
                peer(4)
                }
            MAX-ACCESS read-write
            STATUS current
            DESCRIPTION
                "Before the 10 GE WAN board processes packets, the overhead byte must be configured on the interface.
                The overhead byte for the SDH frame, j0: Set section trace byte
                The default value is j016ByteMode(2):hwEthernetFlagJ0Trace:NetEngine"
            ::= { hwEthernetEntry 21 }

        
        -- 1.3.6.1.4.1.2011.5.25.157.1.1.1.1.22
        hwEthernetFlagJ0Value OBJECT-TYPE
            SYNTAX Integer32 (0..255)
            MAX-ACCESS read-write
            STATUS current
            DESCRIPTION
                "j01ByteMode Value. When hwEthernetFlagJ0Mode is set to j01ByteMode, this parameter takes effect."
            ::= { hwEthernetEntry 22 }

        
        -- 1.3.6.1.4.1.2011.5.25.157.1.1.1.1.23
        hwEthernetFlagJ0Trace OBJECT-TYPE
            SYNTAX OCTET STRING (SIZE (0..64))
            MAX-ACCESS read-write
            STATUS current
            DESCRIPTION
                "Set section trace byte.
                When hwEthernetFlagJ0Mode is set to j016ByteMode or j064ByteOrNullMode, this variable takes effect.
                When hwEthernetFlagJ0Mode is set to j016ByteMode, this variable is up to 15 characters trace byte.
                When hwEthernetFlagJ0Mode is set to j064ByteOrNullMode, this variable is up to 64 characters trace byte."
            ::= { hwEthernetEntry 23 }

        
        -- 1.3.6.1.4.1.2011.5.25.157.1.1.1.1.24
        hwEthernetFlagJ1Mode OBJECT-TYPE
            SYNTAX INTEGER
                {
                j11ByteMode(1),
                j116ByteMode(2),
                j164ByteOrNullMode(3),
                peer(4)
                }
            MAX-ACCESS read-write
            STATUS current
            DESCRIPTION
                "Indicates the overhead byte of the SDH frame. j1:sets path trace byte.
                The default value is j116ByteMode(2) hwEthernetFlagJ1Trace NetEngine."
            ::= { hwEthernetEntry 24 }

        
        -- 1.3.6.1.4.1.2011.5.25.157.1.1.1.1.25
        hwEthernetFlagJ1Value OBJECT-TYPE
            SYNTAX Integer32 (0..255)
            MAX-ACCESS read-write
            STATUS current
            DESCRIPTION
                "j11ByteMode Value. When hwEthernetFlagJ1Mode is set to j11ByteMode, this parameter takes effect."
            ::= { hwEthernetEntry 25 }

        
        -- 1.3.6.1.4.1.2011.5.25.157.1.1.1.1.26
        hwEthernetFlagJ1Trace OBJECT-TYPE
            SYNTAX OCTET STRING (SIZE (0..64))
            MAX-ACCESS read-write
            STATUS current
            DESCRIPTION
                "Set path trace byte.
                When hwEthernetFlagJ1Mode is set to j116ByteMode or j164ByteOrNullMode, this variable takes effect.
                When hwEthernetFlagJ1Mode is set to j116ByteMode, this variable is up to 15 characters trace byte.
                When hwEthernetFlagJ1Mode is set to j164ByteOrNullMode, this variable is up to 64 characters trace byte."
            ::= { hwEthernetEntry 26 }

        
        -- 1.3.6.1.4.1.2011.5.25.157.1.1.1.1.27
        hwEthernetFlagC2Value OBJECT-TYPE
            SYNTAX Integer32 (0..255)
            MAX-ACCESS read-write
            STATUS current
            DESCRIPTION
                "Indicates the overhead byte of the SDH frame.
                c2: indicates the signal label byte. It is a hexdecimal value ranging from 00 to FF.
                The default value is 0x02."
            ::= { hwEthernetEntry 27 }

        
        -- 1.3.6.1.4.1.2011.5.25.157.1.1.1.1.31
        hwEthernetUpHoldTime OBJECT-TYPE
            SYNTAX Integer32 (0..86400000)
            MAX-ACCESS read-write
            STATUS current
            DESCRIPTION
                "Indicates the response time to the event that the port turns Up. The units of hwEthernetUpHoldTime is millisecond."
            ::= { hwEthernetEntry 31 }

        
        -- 1.3.6.1.4.1.2011.5.25.157.1.1.1.1.32
        hwEthernetDownHoldTime OBJECT-TYPE
            SYNTAX Integer32 (0..86400000)
            MAX-ACCESS read-write
            STATUS current
            DESCRIPTION
                "Indicates the response time to the event that the port turns Down. The units of hwEthernetDownHoldTime is millisecond."
            ::= { hwEthernetEntry 32 }

        
        -- 1.3.6.1.4.1.2011.5.25.157.1.1.1.1.33
        hwEthernetSubinterfaceStatisticEnable OBJECT-TYPE
            SYNTAX EnabledStatus
            MAX-ACCESS read-write
            STATUS current
            DESCRIPTION
                "Enable the statistical function of the sub-interface."
            ::= { hwEthernetEntry 33 }

            
    -- 1.3.6.1.4.1.2011.5.25.157.1.1.1.1.34
    hwEthernetFlowControl OBJECT-TYPE
        SYNTAX INTEGER
            {
            receive(1),
            send(2),
            both(3),
            none(4)
            }
        MAX-ACCESS read-write
        STATUS current
        DESCRIPTION
            "Set flow control of this port."
        ::= { hwEthernetEntry 34 }

    
    -- 1.3.6.1.4.1.2011.5.25.157.1.1.1.1.35
    hwEthernetOffline OBJECT-TYPE
        SYNTAX INTEGER
            {
            true(1),
            false(2)
            }
        MAX-ACCESS read-write
        STATUS current
        DESCRIPTION
            "Set Line protocol state to down of this port."
        ::= { hwEthernetEntry 35 }

    
    -- 1.3.6.1.4.1.2011.5.25.157.1.1.1.1.36
    hwEthernetSetTransferMode OBJECT-TYPE
        SYNTAX INTEGER
            {
            lan(1),
            wan(2),
            none(3)
            }
        MAX-ACCESS read-write
        STATUS current
        DESCRIPTION
            "Set transfer mode of this port."
        ::= { hwEthernetEntry 36 }

        
        -- 1.3.6.1.4.1.2011.5.25.157.1.1.1.1.37
        hwEthernetJumboframeMaxLength OBJECT-TYPE
            SYNTAX Integer32 (1536..13296)
            MAX-ACCESS read-write
            STATUS current
            DESCRIPTION
                "Set the jumboframe max length of this port."
            ::= { hwEthernetEntry 37 }

        
        -- 1.3.6.1.4.1.2011.5.25.157.1.1.1.1.38
        hwEthernetComboType OBJECT-TYPE
            SYNTAX INTEGER
                {
                auto(1),
                copper(2),
                fiber(3),
                other(4)
                }
            MAX-ACCESS read-write
            STATUS current
            DESCRIPTION
                "combo mode of this port."
            ::= { hwEthernetEntry 38 }

        
        -- 1.3.6.1.4.1.2011.5.25.157.1.1.1.1.39
        hwEthernetPortMode OBJECT-TYPE
            SYNTAX INTEGER
                {
                copper(1),
                fiber(2),
                other(3)
                }
            MAX-ACCESS read-only
            STATUS current
            DESCRIPTION
                "Indicates combo mode of this port."
            ::= { hwEthernetEntry 39 }
            
            
        -- 1.3.6.1.4.1.2011.5.25.157.1.1.1.1.40
        hwEthernetNegotiationMode OBJECT-TYPE
            SYNTAX INTEGER
                {
                notsupport(1),
                auto(2),
                master(3),
                slave(4)
                }
            MAX-ACCESS read-write
            STATUS current
            DESCRIPTION
                "Set negotiation-mode for phy of electronic GE port.The mode is uesed for synchronizing clock. "
            ::= { hwEthernetEntry 40 }

        
        -- 1.3.6.1.4.1.2011.5.25.157.1.2
        hwPos OBJECT IDENTIFIER ::= { hwPortMIBObjects 2 }

        
        -- 1.3.6.1.4.1.2011.5.25.157.1.2.1
        hwPosTable OBJECT-TYPE
            SYNTAX SEQUENCE OF HwPosEntry
            MAX-ACCESS not-accessible
            STATUS current
            DESCRIPTION
                "Indicates the physical attributes of the POS interface.
                This table lists the physical attributes of the POS interface."
            ::= { hwPos 1 }

        
        -- 1.3.6.1.4.1.2011.5.25.157.1.2.1.1
        hwPosEntry OBJECT-TYPE
            SYNTAX HwPosEntry
            MAX-ACCESS not-accessible
            STATUS current
            DESCRIPTION
                "Indicates the physical attributes of the POS interface.
                This table lists the physical attributes of the POS interface."
            INDEX { hwPosIfIndex }
            ::= { hwPosTable 1 }

        
        HwPosEntry ::=
            SEQUENCE { 
                hwPosIfIndex
                    InterfaceIndex,
                hwPosLinkProtocol
                    INTEGER,
                hwPosFrameFormat
                    INTEGER,
                hwPosLoopback
                    INTEGER,
                hwPosScramble
                    EnabledStatus,
                hwPosClock
                    INTEGER,
                hwPosCrcVerifyCode
                    INTEGER,
                hwPosFlagJ0Mode
                    INTEGER,
                hwPosFlagJ0Value
                    Integer32,
                hwPosFlagJ0Trace
                    OCTET STRING,
                hwPosFlagJ1Mode
                    INTEGER,
                hwPosFlagJ1Value
                    Integer32,
                hwPosFlagJ1Trace
                    OCTET STRING,
                hwPosFlagC2Value
                    Integer32
             }

        -- 1.3.6.1.4.1.2011.5.25.157.1.2.1.1.1
        hwPosIfIndex OBJECT-TYPE
            SYNTAX InterfaceIndex
            MAX-ACCESS not-accessible
            STATUS current
            DESCRIPTION
                "Interface index(es) of port(s) present on the device ."
            ::= { hwPosEntry 1 }

        
        -- 1.3.6.1.4.1.2011.5.25.157.1.2.1.1.11
        hwPosLinkProtocol OBJECT-TYPE
            SYNTAX INTEGER
                {
                ietf(1),
                nonstandard(2),
                hdlc(3),
                ppp(4)
                }
            MAX-ACCESS read-write
            STATUS current
            DESCRIPTION
                "Indicates the link layer protocol of the POS interface.
                By default, on a POS interface, PPP serves as the link layer protocol."
            ::= { hwPosEntry 11 }

        
        -- 1.3.6.1.4.1.2011.5.25.157.1.2.1.1.12
        hwPosFrameFormat OBJECT-TYPE
            SYNTAX INTEGER
                {
                sonet(1),
                sdh(2)
                }
            MAX-ACCESS read-write
            STATUS current
            DESCRIPTION
                "Indicates the frame type of the POS interface.
                By default, the frame type of the POS interface is SDH.
                This variable identifies whether a SONET or a SDH signal is used across this interface."
            ::= { hwPosEntry 12 }

        
        -- 1.3.6.1.4.1.2011.5.25.157.1.2.1.1.13
        hwPosLoopback OBJECT-TYPE
            SYNTAX INTEGER
                {
                otherLoop(1),
                stopLoopback(2),
                local(3),
                remote(4)
                }
            MAX-ACCESS read-write
            STATUS current
            DESCRIPTION
                "The local loopback of a POS interface is used to test the interface itself.
                If an interface works in a normal situation, disable the local loopback.
                By default, stopLoopback is used."
            ::= { hwPosEntry 13 }

        
        -- 1.3.6.1.4.1.2011.5.25.157.1.2.1.1.14
        hwPosScramble OBJECT-TYPE
            SYNTAX EnabledStatus
            MAX-ACCESS read-write
            STATUS current
            DESCRIPTION
                "Indicates the scramble function of payload. By default, the scramble function of payload is enabled."
            ::= { hwPosEntry 14 }

        
        -- 1.3.6.1.4.1.2011.5.25.157.1.2.1.1.15
        hwPosClock OBJECT-TYPE
            SYNTAX INTEGER
                {
                master(1),
                slave(2)
                }
            MAX-ACCESS read-write
            STATUS current
            DESCRIPTION
                "Indicates whether the clock is in master mode or slave mode.
                By default, the clock is in slave mode."
            ::= { hwPosEntry 15 }

        
        -- 1.3.6.1.4.1.2011.5.25.157.1.2.1.1.16
        hwPosCrcVerifyCode OBJECT-TYPE
            SYNTAX INTEGER
                {
                crc16(1),
                crc32(2)
                }
            MAX-ACCESS read-write
            STATUS current
            DESCRIPTION
                "Indicates the length of the CRC verity code. The default value is 32."
            ::= { hwPosEntry 16 }

        
        -- 1.3.6.1.4.1.2011.5.25.157.1.2.1.1.21
        hwPosFlagJ0Mode OBJECT-TYPE
            SYNTAX INTEGER
                {
                j01ByteMode(1),
                j016ByteMode(2),
                j064ByteOrNullMode(3),
                peer(4)
                }
            MAX-ACCESS read-write
            STATUS current
            DESCRIPTION
                "Indicates the overhead byte of the SDH frame. j0: sets section trace byte.
                The default value is j016ByteMode(2);hwPosFlagJ0Trace:NetEngine."
            ::= { hwPosEntry 21 }

        
        -- 1.3.6.1.4.1.2011.5.25.157.1.2.1.1.22
        hwPosFlagJ0Value OBJECT-TYPE
            SYNTAX Integer32 (0..127)
            MAX-ACCESS read-write
            STATUS current
            DESCRIPTION
                "Indicates the value of j01ByteMode. When hwPosFlagJ0Mode is set to j01ByteMode, hwPosFlagJ0Value takes effect."
            ::= { hwPosEntry 22 }

        
        -- 1.3.6.1.4.1.2011.5.25.157.1.2.1.1.23
        hwPosFlagJ0Trace OBJECT-TYPE
            SYNTAX OCTET STRING (SIZE (0..64))
            MAX-ACCESS read-write
            STATUS current
            DESCRIPTION
                "Set section trace byte.
                When hwPosFlagJ0Mode is set to j016ByteMode or j064ByteOrNullMode, this variable takes effect.
                When hwPosFlagJ0Mode is set to j016ByteMode, the value of this variable is up to 15 characters trace byte.
                When hwPosFlagJ0Mode is set to j064ByteOrNullMode, the value of this variable is up to 64 characters trace byte."
            ::= { hwPosEntry 23 }

        
        -- 1.3.6.1.4.1.2011.5.25.157.1.2.1.1.24
        hwPosFlagJ1Mode OBJECT-TYPE
            SYNTAX INTEGER
                {
                j11ByteMode(1),
                j116ByteMode(2),
                j164ByteOrNullMode(3),
                peer(4)
                }
            MAX-ACCESS read-write
            STATUS current
            DESCRIPTION
                "Indicates the overhead byte of the SDH frame. j1: sets path trace byte.
                The default value is j116ByteMode(2);hwPosFlagJ1Trace:NetEngine."
            ::= { hwPosEntry 24 }

        
        -- 1.3.6.1.4.1.2011.5.25.157.1.2.1.1.25
        hwPosFlagJ1Value OBJECT-TYPE
            SYNTAX Integer32 (0..127)
            MAX-ACCESS read-write
            STATUS current
            DESCRIPTION
                "Indicates the value of j11ByteMode. When hwPosFlagJ1Mode is set to j11ByteMode, hwPosFlagJ1Value takes effect."
            ::= { hwPosEntry 25 }

        
        -- 1.3.6.1.4.1.2011.5.25.157.1.2.1.1.26
        hwPosFlagJ1Trace OBJECT-TYPE
            SYNTAX OCTET STRING (SIZE (0..64))
            MAX-ACCESS read-write
            STATUS current
            DESCRIPTION
                "Set path trace byte.
                When hwPosFlagJ1Mode is set to j116ByteMode or j164ByteOrNullMode, this variable takes effect.
                When hwPosFlagJ1Mode is set to j116ByteMode, this variable is up to 15 characters trace byte.
                When hwPosFlagJ1Mode is set to j164ByteOrNullMode, this variable is up to 64 characters trace byte."
            ::= { hwPosEntry 26 }

        
        -- 1.3.6.1.4.1.2011.5.25.157.1.2.1.1.27
        hwPosFlagC2Value OBJECT-TYPE
            SYNTAX Integer32 (0..255)
            MAX-ACCESS read-write
            STATUS current
            DESCRIPTION
                "Indicates the overhead byte of the SDH frame.
                c2: indicates the signal label byte. It is a hexdecimal value ranging from 00 to FF.
                The default value is 0x02."
            ::= { hwPosEntry 27 }

        
        -- 1.3.6.1.4.1.2011.5.25.157.1.3
        hwCpos OBJECT IDENTIFIER ::= { hwPortMIBObjects 3 }

        
        -- 1.3.6.1.4.1.2011.5.25.157.1.3.1
        hwCposTable OBJECT-TYPE
            SYNTAX SEQUENCE OF HwCposEntry
            MAX-ACCESS not-accessible
            STATUS current
            DESCRIPTION
                "Indicates the physical attributes of the CPOS interface.
                This table lists the physical attributes of the CPOS interface."
            ::= { hwCpos 1 }

        
        -- 1.3.6.1.4.1.2011.5.25.157.1.3.1.1
        hwCposEntry OBJECT-TYPE
            SYNTAX HwCposEntry
            MAX-ACCESS not-accessible
            STATUS current
            DESCRIPTION
                "Indicates the physical attributes of the CPOS interface.
                This table lists the physical attributes of the CPOS interface."
            INDEX { hwCposIfIndex }
            ::= { hwCposTable 1 }

        
        HwCposEntry ::=
            SEQUENCE { 
                hwCposIfIndex
                    InterfaceIndex,
                hwCposClock
                    INTEGER,
                hwCposIfType
                    INTEGER,
                hwCposFrameFormat
                    INTEGER,
                hwCposMultiplex
                    INTEGER,
                hwCposLoopback
                    INTEGER,
                hwCposFlagJ0Mode
                    INTEGER,
                hwCposFlagJ0Value
                    Integer32,
                hwCposFlagJ0Trace
                    OCTET STRING,
                hwCposFlagJ1Mode
                    INTEGER,
                hwCposFlagJ1Value
                    Integer32,
                hwCposFlagJ1Trace
                    OCTET STRING,
                hwCposFlagC2Value
                    Integer32,
                hwCposB1SdAlarmThreshold
                    Integer32,
                hwCposB1ExcAlarmThreshold
                    Integer32,
                hwCposB2SdAlarmThreshold
                    Integer32,
                hwCposB2ExcAlarmThreshold
                    Integer32,
                hwCposB3SdAlarmThreshold
                    Integer32,
                hwCposB3ExcAlarmThreshold
                    Integer32,
                hwCposLpBipSdAlarmThreshold
                    Integer32,
                hwCposLpBipExcAlarmThreshold
                    Integer32,
                hwCposHighPathNumber
                    Integer32,
                hwCposLowPathNumber
                    Integer32,
                hwCposMappingMode
                    INTEGER
             }

        -- 1.3.6.1.4.1.2011.5.25.157.1.3.1.1.1
        hwCposIfIndex OBJECT-TYPE
            SYNTAX InterfaceIndex
            MAX-ACCESS not-accessible
            STATUS current
            DESCRIPTION
                "Interface index(es) of port(s) present on the device ."
            ::= { hwCposEntry 1 }

        
        -- 1.3.6.1.4.1.2011.5.25.157.1.3.1.1.11
        hwCposClock OBJECT-TYPE
            SYNTAX INTEGER
                {
                master(1),
                slave(2)
                }
            MAX-ACCESS read-write
            STATUS current
            DESCRIPTION
                "Indicates whether the clock is in master mode or slave mode.
                By default, the clock is in slave mode."
            ::= { hwCposEntry 11 }

        
        -- 1.3.6.1.4.1.2011.5.25.157.1.3.1.1.12
        hwCposIfType OBJECT-TYPE
            SYNTAX INTEGER
                {
                stm1(1),
                stm16(2)
                }
            MAX-ACCESS read-write
            STATUS current
            DESCRIPTION
                "Indicates the interface type."
            ::= { hwCposEntry 12 }

        
        -- 1.3.6.1.4.1.2011.5.25.157.1.3.1.1.13
        hwCposFrameFormat OBJECT-TYPE
            SYNTAX INTEGER
                {
                sonet(1),
                sdh(2)
                }
            MAX-ACCESS read-write
            STATUS current
            DESCRIPTION
                "Indicates the frame type of the CPOS interface. By default, the frame type of the CPOS interface is SDH."
            ::= { hwCposEntry 13 }

        
        -- 1.3.6.1.4.1.2011.5.25.157.1.3.1.1.14
        hwCposMultiplex OBJECT-TYPE
            SYNTAX INTEGER
                {
                au3(1),
                au4(2)
                }
            MAX-ACCESS read-write
            STATUS current
            DESCRIPTION
                "Indicates the multiplex mode of the AUG. By default, the multiplex mode of the AUG is au-4."
            ::= { hwCposEntry 14 }

        
        -- 1.3.6.1.4.1.2011.5.25.157.1.3.1.1.15
        hwCposLoopback OBJECT-TYPE
            SYNTAX INTEGER
                {
                otherloop(1),
                stopLoopback(2),
                local(3),
                remote(4)
                }
            MAX-ACCESS read-write
            STATUS current
            DESCRIPTION
                "Indicates the loopback function of the CPOS interface. By default, the loopback function is disabled."
            ::= { hwCposEntry 15 }

        
        -- 1.3.6.1.4.1.2011.5.25.157.1.3.1.1.21
        hwCposFlagJ0Mode OBJECT-TYPE
            SYNTAX INTEGER
                {
                j01ByteMode(1),
                j016ByteMode(2),
                j064ByteOrNullMode(3),
                peer(4)
                }
            MAX-ACCESS read-write
            STATUS current
            DESCRIPTION
                "Indicates the overhead byte of the SDH frame. j0: sets section trace byte.
                The default value is j016ByteMode(2);hwCposFlagJ0Trace NetEngine."
            ::= { hwCposEntry 21 }

        
        -- 1.3.6.1.4.1.2011.5.25.157.1.3.1.1.22
        hwCposFlagJ0Value OBJECT-TYPE
            SYNTAX Integer32 (0..127)
            MAX-ACCESS read-write
            STATUS current
            DESCRIPTION
                "j01ByteMode Value . When hwCposFlagJ0Mode is set to j01ByteMode, hwCposFlagJ0Value takes effect."
            ::= { hwCposEntry 22 }

        
        -- 1.3.6.1.4.1.2011.5.25.157.1.3.1.1.23
        hwCposFlagJ0Trace OBJECT-TYPE
            SYNTAX OCTET STRING (SIZE (0..64))
            MAX-ACCESS read-write
            STATUS current
            DESCRIPTION
                "Set section trace byte.
                When hwCposFlagJ0Mode is set to j016ByteMode or j064ByteOrNullMode, this variable takes effect.
                When hwCposFlagJ0Mode is set to j016ByteMode, this variable is up to 15 characters trace byte.
                When hwCposFlagJ0Mode is set to j064ByteOrNullMode, this variable is up to 64 characters trace byte."
            ::= { hwCposEntry 23 }

        
        -- 1.3.6.1.4.1.2011.5.25.157.1.3.1.1.24
        hwCposFlagJ1Mode OBJECT-TYPE
            SYNTAX INTEGER
                {
                j11ByteMode(1),
                j116ByteMode(2),
                j164ByteOrNullMode(3),
                peer(4)
                }
            MAX-ACCESS read-write
            STATUS current
            DESCRIPTION
                "Indicates the overhead byte of the SDH frame. j1: sets path trace byte.
                The default value is j116ByteMode(2);hwCposFlagJ1Trace NetEngine."
            ::= { hwCposEntry 24 }

        
        -- 1.3.6.1.4.1.2011.5.25.157.1.3.1.1.25
        hwCposFlagJ1Value OBJECT-TYPE
            SYNTAX Integer32 (0..127)
            MAX-ACCESS read-write
            STATUS current
            DESCRIPTION
                "Indicates the value of j11ByteMode. When hwCposFlagJ1Mode is set to j11ByteMode, hwCposFlagJ1Value takes effect."
            ::= { hwCposEntry 25 }

        
        -- 1.3.6.1.4.1.2011.5.25.157.1.3.1.1.26
        hwCposFlagJ1Trace OBJECT-TYPE
            SYNTAX OCTET STRING (SIZE (0..64))
            MAX-ACCESS read-write
            STATUS current
            DESCRIPTION
                "Set path trace byte.
                When hwCposFlagJ1Mode is set to j116ByteMode or j164ByteOrNullMode, this variable takes effect.
                When hwCposFlagJ1Mode is set to j116ByteMode, this variable is a string up to 15 characters trace byte.
                When hwCposFlagJ1Mode is set to j164ByteOrNullMode, this variable is a string up to 64 characters trace byte."
            ::= { hwCposEntry 26 }

        
        -- 1.3.6.1.4.1.2011.5.25.157.1.3.1.1.27
        hwCposFlagC2Value OBJECT-TYPE
            SYNTAX Integer32 (0..255)
            MAX-ACCESS read-write
            STATUS current
            DESCRIPTION
                "Indicates the overhead byte of the SDH frame.
                c2: indicates the signal label byte. It is a hexdecimal value ranging from 00 to FF.
                The default value is 22(0x16)."
            ::= { hwCposEntry 27 }

        
        -- 1.3.6.1.4.1.2011.5.25.157.1.3.1.1.28
        hwCposB1SdAlarmThreshold OBJECT-TYPE
            SYNTAX Integer32 (1..9)
            MAX-ACCESS read-write
            STATUS current
            DESCRIPTION
                "The threshold of B1 threshold crossing alarm."
            DEFVAL { 6 }
            ::= { hwCposEntry 28 }

        
        -- 1.3.6.1.4.1.2011.5.25.157.1.3.1.1.29
        hwCposB1ExcAlarmThreshold OBJECT-TYPE
            SYNTAX Integer32 (1..9)
            MAX-ACCESS read-write
            STATUS current
            DESCRIPTION
                "The threshold of B1 threshold crossing alarm."
            DEFVAL { 3 }
            ::= { hwCposEntry 29 }

        
        -- 1.3.6.1.4.1.2011.5.25.157.1.3.1.1.30
        hwCposB2SdAlarmThreshold OBJECT-TYPE
            SYNTAX Integer32 (1..9)
            MAX-ACCESS read-write
            STATUS current
            DESCRIPTION
                "The threshold of B2 threshold crossing alarm."
            DEFVAL { 6 }
            ::= { hwCposEntry 30 }

        
        -- 1.3.6.1.4.1.2011.5.25.157.1.3.1.1.31
        hwCposB2ExcAlarmThreshold OBJECT-TYPE
            SYNTAX Integer32 (1..9)
            MAX-ACCESS read-write
            STATUS current
            DESCRIPTION
                "The threshold of B2 threshold crossing alarm."
            DEFVAL { 3 }
            ::= { hwCposEntry 31 }

        
        -- 1.3.6.1.4.1.2011.5.25.157.1.3.1.1.32
        hwCposB3SdAlarmThreshold OBJECT-TYPE
            SYNTAX Integer32 (1..9)
            MAX-ACCESS read-write
            STATUS current
            DESCRIPTION
                "The threshold of B3 threshold crossing alarm."
            DEFVAL { 6 }
            ::= { hwCposEntry 32 }

        
        -- 1.3.6.1.4.1.2011.5.25.157.1.3.1.1.33
        hwCposB3ExcAlarmThreshold OBJECT-TYPE
            SYNTAX Integer32 (1..9)
            MAX-ACCESS read-write
            STATUS current
            DESCRIPTION
                "The threshold of B3 threshold crossing alarm."
            DEFVAL { 3 }
            ::= { hwCposEntry 33 }

        
        -- 1.3.6.1.4.1.2011.5.25.157.1.3.1.1.34
        hwCposLpBipSdAlarmThreshold OBJECT-TYPE
            SYNTAX Integer32 (1..9)
            MAX-ACCESS read-write
            STATUS current
            DESCRIPTION
                "The threshold of BIP2 threshold crossing alarm."
            DEFVAL { 6 }
            ::= { hwCposEntry 34 }

        
        -- 1.3.6.1.4.1.2011.5.25.157.1.3.1.1.35
        hwCposLpBipExcAlarmThreshold OBJECT-TYPE
            SYNTAX Integer32 (1..9)
            MAX-ACCESS read-write
            STATUS current
            DESCRIPTION
                "The threshold of BIP2 threshold crossing alarm."
            DEFVAL { 3 }
            ::= { hwCposEntry 35 }

        
        -- 1.3.6.1.4.1.2011.5.25.157.1.3.1.1.36
        hwCposHighPathNumber OBJECT-TYPE
            SYNTAX Integer32 (0..255)
            MAX-ACCESS read-only
            STATUS current
            DESCRIPTION
                "Indicates the overhead byte of the SDH frame.
                c2: indicates the signal label byte. It is a hexdecimal value ranging from 00 to FF.
                The default value is 22(0x16)."
            ::= { hwCposEntry 36 }

        
        -- 1.3.6.1.4.1.2011.5.25.157.1.3.1.1.37
        hwCposLowPathNumber OBJECT-TYPE
            SYNTAX Integer32 (0..255)
            MAX-ACCESS read-only
            STATUS current
            DESCRIPTION
                "Indicates the overhead byte of the SDH frame.
                c2: indicates the signal label byte. It is a hexdecimal value ranging from 00 to FF.
                The default value is 22(0x16)."
            ::= { hwCposEntry 37 }

        
        -- 1.3.6.1.4.1.2011.5.25.157.1.3.1.1.38
        hwCposMappingMode OBJECT-TYPE
            SYNTAX INTEGER
                {
                h-mode(1),
                l-mode(2),
                a-mode(3)
                }
            MAX-ACCESS read-write
            STATUS current
            DESCRIPTION
                "Indicates the mapping mode of cpos port, default if h-mode(1)."
            ::= { hwCposEntry 38 }

        
        -- 1.3.6.1.4.1.2011.5.25.157.1.3.2
        hwPortPhysicalHpIndex OBJECT-TYPE
            SYNTAX Integer32
            MAX-ACCESS accessible-for-notify
            STATUS current
            DESCRIPTION
                "Indicates the higher order path number."
            ::= { hwCpos 2 }

        
        -- 1.3.6.1.4.1.2011.5.25.157.1.3.3
        hwPortPhysicalLpIndex OBJECT-TYPE
            SYNTAX Integer32
            MAX-ACCESS accessible-for-notify
            STATUS current
            DESCRIPTION
                "Indicates the low order path number."
            ::= { hwCpos 3 }

        -- 1.3.6.1.4.1.2011.5.25.157.1.3.4
        hwCposLpTable OBJECT-TYPE
            SYNTAX SEQUENCE OF HwCposLpEntry
	    MAX-ACCESS not-accessible
	    STATUS current
	    DESCRIPTION
                "Description."
            ::= { hwCpos 4 }

		
        -- 1.3.6.1.4.1.2011.5.25.157.1.3.4.1
        hwCposLpEntry OBJECT-TYPE
            SYNTAX HwCposLpEntry
            MAX-ACCESS not-accessible
            STATUS current
            DESCRIPTION
                "Description."
            INDEX { hwCposLpIfIndex, hwCposLpId }
            ::= { hwCposLpTable 1 }

		
	HwCposLpEntry ::=
            SEQUENCE { 
                hwCposLpIfIndex
                    InterfaceIndex,
                hwCposLpId
                    Integer32,
                hwCposFlagJ2Mode
                    INTEGER,
                hwCposFlagJ2Value
                    Integer32,
                hwCposFlagJ2Trace
                    OCTET STRING
             }


        -- 1.3.6.1.4.1.2011.5.25.157.1.3.4.1.1
        hwCposLpIfIndex OBJECT-TYPE
            SYNTAX InterfaceIndex
            MAX-ACCESS not-accessible
            STATUS current
            DESCRIPTION
                "Description."
            ::= { hwCposLpEntry 1 }

		

        -- 1.3.6.1.4.1.2011.5.25.157.1.3.4.1.2
        hwCposLpId OBJECT-TYPE
            SYNTAX Integer32
            MAX-ACCESS not-accessible
            STATUS current
            DESCRIPTION
                "Description."
            ::= { hwCposLpEntry 2 }

		

        -- 1.3.6.1.4.1.2011.5.25.157.1.3.4.1.3
        hwCposFlagJ2Mode OBJECT-TYPE
            SYNTAX INTEGER
            {
            j21ByteMode(1),
            j216ByteMode(2)
            }
            MAX-ACCESS read-write
            STATUS current
            DESCRIPTION
                "Description."
            ::= { hwCposLpEntry 3 }

		

        -- 1.3.6.1.4.1.2011.5.25.157.1.3.4.1.4
        hwCposFlagJ2Value OBJECT-TYPE
            SYNTAX Integer32 (0..127)
            MAX-ACCESS read-write
            STATUS current
            DESCRIPTION
                "Description."
            ::= { hwCposLpEntry 4 }

		

        -- 1.3.6.1.4.1.2011.5.25.157.1.3.4.1.5
        hwCposFlagJ2Trace OBJECT-TYPE
            SYNTAX OCTET STRING (SIZE (0..16))
            MAX-ACCESS read-write
            STATUS current
            DESCRIPTION
                "Description."
            ::= { hwCposLpEntry 5 }

        -- 1.3.6.1.4.1.2011.5.25.157.1.4
        hwDs0ChannelBundle OBJECT IDENTIFIER ::= { hwPortMIBObjects 4 }

        
        -- 1.3.6.1.4.1.2011.5.25.157.1.4.1
        hwDs0ChannelBundleTable OBJECT-TYPE
            SYNTAX SEQUENCE OF HwDs0ChannelBundleEntry
            MAX-ACCESS not-accessible
            STATUS current
            DESCRIPTION
                "This table is used to bundle timeslots of CE1/CT1 interfaces."
            ::= { hwDs0ChannelBundle 1 }

        
        -- 1.3.6.1.4.1.2011.5.25.157.1.4.1.1
        hwDs0ChannelBundleEntry OBJECT-TYPE
            SYNTAX HwDs0ChannelBundleEntry
            MAX-ACCESS not-accessible
            STATUS current
            DESCRIPTION
                "This table is used to bundle timeslots of CE1/CT1 interfaces."
            INDEX { hwDs0ChannelBundleParentIfIndex, hwDs0ChannelBundleDs1ChannelId, hwDs0ChannelBundleId }
            ::= { hwDs0ChannelBundleTable 1 }

        
        HwDs0ChannelBundleEntry ::=
            SEQUENCE { 
                hwDs0ChannelBundleParentIfIndex
                    InterfaceIndex,
                hwDs0ChannelBundleDs1ChannelId
                    Integer32,
                hwDs0ChannelBundleId
                    Integer32,
                hwDs0ChannelBundleIfIndex
                    InterfaceIndex,
                hwDs0ChannelBundleTimeSlots
                    OCTET STRING,
                hwDs0ChannelBundleSpeed
                    INTEGER,
                hwDs0ChannelBundleTimeSlot0
                    TruthValue,
                hwDs0ChannelBundleIsMasterPW
                    INTEGER,
                hwDs0ChannelBundleMasterPWStatus
                    INTEGER,
                hwDs0ChannelBundlePortName
                    OCTET STRING,
                hwDs0ChannelBundleRowStatus
                    RowStatus
             }

        -- 1.3.6.1.4.1.2011.5.25.157.1.4.1.1.1
        hwDs0ChannelBundleParentIfIndex OBJECT-TYPE
            SYNTAX InterfaceIndex
            MAX-ACCESS not-accessible
            STATUS current
            DESCRIPTION
                "Indicates the index of the parent interface."
            ::= { hwDs0ChannelBundleEntry 1 }

        
        -- 1.3.6.1.4.1.2011.5.25.157.1.4.1.1.2
        hwDs0ChannelBundleDs1ChannelId OBJECT-TYPE
            SYNTAX Integer32
            MAX-ACCESS not-accessible
            STATUS current
            DESCRIPTION
                "Indicates the channel ID."
            ::= { hwDs0ChannelBundleEntry 2 }

        
        -- 1.3.6.1.4.1.2011.5.25.157.1.4.1.1.3
        hwDs0ChannelBundleId OBJECT-TYPE
            SYNTAX Integer32 (0..30)
            MAX-ACCESS not-accessible
            STATUS current
            DESCRIPTION
                "Indicates the index number of the channel set."
            ::= { hwDs0ChannelBundleEntry 3 }

        
        -- 1.3.6.1.4.1.2011.5.25.157.1.4.1.1.11
        hwDs0ChannelBundleIfIndex OBJECT-TYPE
            SYNTAX InterfaceIndex
            MAX-ACCESS read-create
            STATUS current
            DESCRIPTION
                "Indicates the index of the serial interface formed by the timeslot binding."
            ::= { hwDs0ChannelBundleEntry 11 }

        
        -- 1.3.6.1.4.1.2011.5.25.157.1.4.1.1.12
        hwDs0ChannelBundleTimeSlots OBJECT-TYPE
            SYNTAX OCTET STRING (SIZE (0..61))
            MAX-ACCESS read-create
            STATUS current
            DESCRIPTION
                "Indicates the number of the range of the timeslot to be bound.
                The value is an integer ranging from 0 to 31. Multiple timeslots are
                separated by ','. The range of timeslot is expressed by using '-'.
                For E1 card mode:
                If the timeslots are '0-31', it means unframed format,
                If the timeslots are '0-30', it means framed format,
                For T1 card mode:
                If the timeslots are '0-23', it means unframed format,
                If the timeslots are '0-22', it means framed format,
                and hwDs0ChannelBundleDs1ChannelId and hwDs0ChannelBundleId should be zero."
            ::= { hwDs0ChannelBundleEntry 12 }

        
        -- 1.3.6.1.4.1.2011.5.25.157.1.4.1.1.13
        hwDs0ChannelBundleSpeed OBJECT-TYPE
            SYNTAX INTEGER
                {
                s56(1),
                s64(2)
                }
            UNITS "kilo bytes"
            MAX-ACCESS read-create
            STATUS current
            DESCRIPTION
                "Configures the mode to configure the timeslots.
                If the parameter 56 k is selected, the timeslots are bound in the mode of N x 56 kbit/s.
                If the parameter 64 k is selected, the timeslots are bound in the mode of N x 64 kbit/s.
                The default value is 64kbit/s."
            DEFVAL { 64 }
            ::= { hwDs0ChannelBundleEntry 13 }

        
        -- 1.3.6.1.4.1.2011.5.25.157.1.4.1.1.14
        hwDs0ChannelBundleTimeSlot0 OBJECT-TYPE
            SYNTAX TruthValue
            MAX-ACCESS read-create
            STATUS current
            DESCRIPTION
                "Indicates the timeslot0 to be bound or a single channel.
                The ture value indicates it will be create TDM channel."
            ::= { hwDs0ChannelBundleEntry 14 }

        
        -- 1.3.6.1.4.1.2011.5.25.157.1.4.1.1.15
        hwDs0ChannelBundleIsMasterPW OBJECT-TYPE
            SYNTAX INTEGER
                {
                notacrpw(0),
                masterpw(1),
                notmasterpw(2)
                }
            MAX-ACCESS read-only
            STATUS current
            DESCRIPTION
                "Indicates if the pw configed on this port is master pw."
            ::= { hwDs0ChannelBundleEntry 15 }

        
        -- 1.3.6.1.4.1.2011.5.25.157.1.4.1.1.16
        hwDs0ChannelBundleMasterPWStatus OBJECT-TYPE
            SYNTAX INTEGER
                {
                unlock(0),
                lock(1)
                }
            MAX-ACCESS read-only
            STATUS current
            DESCRIPTION
                "Indicates the status of master pw."
            ::= { hwDs0ChannelBundleEntry 16 }

        
        -- 1.3.6.1.4.1.2011.5.25.157.1.4.1.1.17
        hwDs0ChannelBundlePortName OBJECT-TYPE
            SYNTAX OCTET STRING
            MAX-ACCESS read-only
            STATUS current
            DESCRIPTION
                "Port name."
            ::= { hwDs0ChannelBundleEntry 17 }

        
        -- 1.3.6.1.4.1.2011.5.25.157.1.4.1.1.51
        hwDs0ChannelBundleRowStatus OBJECT-TYPE
            SYNTAX RowStatus
            MAX-ACCESS read-create
            STATUS current
            DESCRIPTION
                "This variable is used to create or delete an object."
            ::= { hwDs0ChannelBundleEntry 51 }

        
        -- 1.3.6.1.4.1.2011.5.25.157.1.5
        hwDs1 OBJECT IDENTIFIER ::= { hwPortMIBObjects 5 }

        
        -- 1.3.6.1.4.1.2011.5.25.157.1.5.1
        hwDs1Table OBJECT-TYPE
            SYNTAX SEQUENCE OF HwDs1Entry
            MAX-ACCESS not-accessible
            STATUS current
            DESCRIPTION
                "This table lists all E1/CE1 interfaces or T1/CT1 interfaces.
                After the mode of E3/CE3 interfaces or T3/CT3 interfaces is set to channelized, this table can be used
                to create E1/CE1, or T1/CT1, or E3/CE3, or T3/CT3 interfaces."
            ::= { hwDs1 1 }

        
        -- 1.3.6.1.4.1.2011.5.25.157.1.5.1.1
        hwDs1Entry OBJECT-TYPE
            SYNTAX HwDs1Entry
            MAX-ACCESS not-accessible
            STATUS current
            DESCRIPTION
                "This table lists all E1/CE1 interfaces or T1/CT1 interfaces.
                After the mode of E3/CE3 interfaces or T3/CT3 interfaces is set to channelized, this table can be used
                to create E1/CE1, or T1/CT1, or E3/CE3, or T3/CT3 interfaces."
            INDEX { hwDs1ParentIfIndex, hwDs1ChannelId, hwDs1IfIndex }
            ::= { hwDs1Table 1 }

        
        HwDs1Entry ::=
            SEQUENCE { 
                hwDs1ParentIfIndex
                    InterfaceIndex,
                hwDs1ChannelId
                    Integer32,
                hwDs1IfIndex
                    InterfaceIndex,
                hwDs1ChannelType
                    INTEGER,
                hwDs1IfType
                    INTEGER,
                hwDs1Channelized
                    TruthValue,
                hwDs1CodeType
                    INTEGER,
                hwDs1Clock
                    INTEGER,
                hwDs1FrameFormat
                    INTEGER,
                hwDs1Cable
                    INTEGER,
                hwDs1Loopback
                    INTEGER,
                hwDs1ClockRecoveryDomain
                    Integer32,
                hwDs1PWClockDomain
                    Integer32,
                hwDs1WorkMode
                    Integer32,
                hwDs1EsAlarmTriggerThreshold
                    Integer32,
                hwDs1EsAlarmResumeThreshold
                    Integer32,
                hwDs1RowStatus
                    RowStatus,
                   hwDs1Lbo
                    INTEGER,
                hwDs1CableLength
                    INTEGER
             }

        -- 1.3.6.1.4.1.2011.5.25.157.1.5.1.1.1
        hwDs1ParentIfIndex OBJECT-TYPE
            SYNTAX InterfaceIndex
            MAX-ACCESS not-accessible
            STATUS current
            DESCRIPTION
                "Indicates the index of the parent interface."
            ::= { hwDs1Entry 1 }

        
        -- 1.3.6.1.4.1.2011.5.25.157.1.5.1.1.2
        hwDs1ChannelId OBJECT-TYPE
            SYNTAX Integer32 (0..63)
            MAX-ACCESS not-accessible
            STATUS current
            DESCRIPTION
                "Indicates the channel ID."
            ::= { hwDs1Entry 2 }

        
        -- 1.3.6.1.4.1.2011.5.25.157.1.5.1.1.3
        hwDs1IfIndex OBJECT-TYPE
            SYNTAX InterfaceIndex
            MAX-ACCESS not-accessible
            STATUS current
            DESCRIPTION
                "Indicates the interface index."
            ::= { hwDs1Entry 3 }

        
        -- 1.3.6.1.4.1.2011.5.25.157.1.5.1.1.11
        hwDs1ChannelType OBJECT-TYPE
            SYNTAX INTEGER
                {
                t1(1),
                e1(2)
                }
            MAX-ACCESS read-create
            STATUS current
            DESCRIPTION
                "Indicates the interface type. The type can be E1/CE1 or T1/CT1."
            ::= { hwDs1Entry 11 }

        
        -- 1.3.6.1.4.1.2011.5.25.157.1.5.1.1.12
        hwDs1IfType OBJECT-TYPE
            SYNTAX INTEGER
                {
                e3(1),
                t3(2),
                cpos(3),
                atm(4),
                none(255)
                }
            MAX-ACCESS read-create
            STATUS current
            DESCRIPTION
                "Indicates the interface tyep.
                e3: is multiplexed by CE3 interfaces.
                t3: is multiplexed by CT3 interfaces.
                cpos: is multiplexed by CPOS interfaces.
                atm: is multiplexed by ATM interfaces.
                none: indicates the physical interface.
                
                default:none"
            DEFVAL { none }
            ::= { hwDs1Entry 12 }

        
        -- 1.3.6.1.4.1.2011.5.25.157.1.5.1.1.13
        hwDs1Channelized OBJECT-TYPE
            SYNTAX TruthValue
            MAX-ACCESS read-create
            STATUS current
            DESCRIPTION
                "Indicates the working mode of the interface.
                true: indicates the channelized mode.
                false: indicates the clear channel mode.
                The default is true."
            DEFVAL { true }
            ::= { hwDs1Entry 13 }

        
        -- 1.3.6.1.4.1.2011.5.25.157.1.5.1.1.14
        hwDs1CodeType OBJECT-TYPE
            SYNTAX INTEGER
                {
                ami(1),
                hdb3(2),
                b8zs(3),
                none(255)
                }
            MAX-ACCESS read-create
            STATUS current
            DESCRIPTION
                "Indicates the code type of the interface.
                ami: is short for Alternate Mark Inversion.
                hdb3: is short for High Density Bipolar of Order 3.
                b8zs: is short for Bipolar with 8-Zero Substitution.
                none: is not supported"
            DEFVAL { hdb3 }
            ::= { hwDs1Entry 14 }

        
        -- 1.3.6.1.4.1.2011.5.25.157.1.5.1.1.15
        hwDs1Clock OBJECT-TYPE
            SYNTAX INTEGER
                {
                master(1),
                slave(2)
                }
            MAX-ACCESS read-create
            STATUS current
            DESCRIPTION
                "Indicates the clock mode of the interface.
                master: indicates that the clock works in master mode and uses the internal clock signal.
                slave: indicates that the clock works in slave mode and uses the line clock signal."
            ::= { hwDs1Entry 15 }

        
        -- 1.3.6.1.4.1.2011.5.25.157.1.5.1.1.16
        hwDs1FrameFormat OBJECT-TYPE
            SYNTAX INTEGER
                {
                esf(1),
                sf(2),
                noCrc4(3),
                crc(4)
                }
            MAX-ACCESS read-create
            STATUS current
            DESCRIPTION
                "Indicates the frame format of the interface.
                crc4: indicates that the frame format is CRC4.
                no-crc4: indicates that the frame format is no-CRC4.
                sf: indicates that the frame format is Super Frame.
                esf: indicates that the frame format is Extended Super Frame.
                By default, the frame format of an E1 interface is no-crc4.
                By default, the frame format of a T1 interface is esf."
            ::= { hwDs1Entry 16 }

        
        -- 1.3.6.1.4.1.2011.5.25.157.1.5.1.1.17
        hwDs1Cable OBJECT-TYPE
            SYNTAX INTEGER
                {
                long(1),
                short(2),
                none(255)
                }
            MAX-ACCESS read-create
            STATUS current
            DESCRIPTION
                "The cable command takes effect only if the E1 interface card uses 75-ohm coaxial cable.
                The default is short. If no cable is connected, this parameter is displayed as null."
            DEFVAL { short }
            ::= { hwDs1Entry 17 }

        
        -- 1.3.6.1.4.1.2011.5.25.157.1.5.1.1.18
        hwDs1Loopback OBJECT-TYPE
            SYNTAX INTEGER
                {
                local(1),
                remote(2),
                payload(3),
                cell(4),
                none(255)
                }
            MAX-ACCESS read-create
            STATUS current
            DESCRIPTION
                "Enable the loopback function of the interface.
                local: enables the local loopback on the interface.
                remote: enables the remote loopback on the interface.
                payload: enables the remote payload loopback on the interface.
                cell: enables the local cell loopback. The local cell loopback is used to test the local physical chip."
            DEFVAL { none }
            ::= { hwDs1Entry 18 }

        
        -- 1.3.6.1.4.1.2011.5.25.157.1.5.1.1.19
        hwDs1ClockRecoveryDomain OBJECT-TYPE
            SYNTAX Integer32 (0..8)
            MAX-ACCESS read-create
            STATUS current
            DESCRIPTION
                "Indicates the clock recovery domain of the interface."
            DEFVAL { 0 }
            ::= { hwDs1Entry 19 }

        
        -- 1.3.6.1.4.1.2011.5.25.157.1.5.1.1.20
        hwDs1PWClockDomain OBJECT-TYPE
            SYNTAX Integer32 (0..8)
            MAX-ACCESS read-create
            STATUS current
            DESCRIPTION
                "Indicates the clock recovery domain of the interface."
            DEFVAL { 0 }
            ::= { hwDs1Entry 20 }

        
        -- 1.3.6.1.4.1.2011.5.25.157.1.5.1.1.21
        hwDs1WorkMode OBJECT-TYPE
            SYNTAX Integer32 (0..8)
            MAX-ACCESS read-only
            STATUS current
            DESCRIPTION
                "Indicates the clock recovery domain of the interface."
            ::= { hwDs1Entry 21 }

        
        -- 1.3.6.1.4.1.2011.5.25.157.1.5.1.1.22
        hwDs1EsAlarmTriggerThreshold OBJECT-TYPE
            SYNTAX Integer32 (1..900)
            MAX-ACCESS read-write
            STATUS current
            DESCRIPTION
                "The trigger threshold of code violation count threshold crossing alarm of E1 line side ."
            DEFVAL { 65 }
            ::= { hwDs1Entry 22 }

        
        -- 1.3.6.1.4.1.2011.5.25.157.1.5.1.1.23
        hwDs1EsAlarmResumeThreshold OBJECT-TYPE
            SYNTAX Integer32 (1..900)
            MAX-ACCESS read-write
            STATUS current
            DESCRIPTION
                "The resume threshold of code violation count threshold crossing alarm of E1 line side ."
            DEFVAL { 30 }
            ::= { hwDs1Entry 23 }

        
        -- 1.3.6.1.4.1.2011.5.25.157.1.5.1.1.51
        hwDs1RowStatus OBJECT-TYPE
            SYNTAX RowStatus
            MAX-ACCESS read-create
            STATUS current
            DESCRIPTION
                "This variable is used to create or delete an object."
            ::= { hwDs1Entry 51 }


            -- 1.3.6.1.4.1.2011.5.25.157.1.5.1.1.52
            hwDs1Lbo OBJECT-TYPE
                SYNTAX INTEGER
                    {
                    db75(1),
                    db155(2),
                    db225(3),
                    none(4),
                    notsupport(5)
                    }
            MAX-ACCESS read-create
            STATUS current
            DESCRIPTION
                "The lbo of T1 port. Unit: db. the value is expanded 10 times,so the real value should be reduced 10 times"
            ::= { hwDs1Entry 52 }

        
        -- 1.3.6.1.4.1.2011.5.25.157.1.5.1.1.53
        hwDs1CableLength OBJECT-TYPE
            SYNTAX INTEGER
                {
                length133(1),
                length266(2),
                length399(3),
                length533(4),
                length655(5),
                notsupport(6),
                none(255)
                }
            MAX-ACCESS read-create
            STATUS current
            DESCRIPTION
                "The cableLength of T1 port. Unit: feet."
            ::= { hwDs1Entry 53 }

        
        -- 1.3.6.1.4.1.2011.5.25.157.1.6
        hwDs3 OBJECT IDENTIFIER ::= { hwPortMIBObjects 6 }

        
        -- 1.3.6.1.4.1.2011.5.25.157.1.6.1
        hwDs3Table OBJECT-TYPE
            SYNTAX SEQUENCE OF HwDs3Entry
            MAX-ACCESS not-accessible
            STATUS current
            DESCRIPTION
                "This table lists all E3/CE3 interfaces or all T3/CT3 interfaces."
            ::= { hwDs3 1 }

        
        -- 1.3.6.1.4.1.2011.5.25.157.1.6.1.1
        hwDs3Entry OBJECT-TYPE
            SYNTAX HwDs3Entry
            MAX-ACCESS not-accessible
            STATUS current
            DESCRIPTION
                "This table lists all E3/CE3 interfaces or all T3/CT3 interfaces."
            INDEX { hwDs3ParentIfIndex, hwDs3ChannelId, hwDs3IfIndex }
            ::= { hwDs3Table 1 }

        
        HwDs3Entry ::=
            SEQUENCE { 
                hwDs3ParentIfIndex
                    InterfaceIndex,
                hwDs3ChannelId
                    Integer32,
                hwDs3IfIndex
                    InterfaceIndex,
                hwDs3ChannelType
                    INTEGER,
                hwDs3IfType
                    INTEGER,
                hwDs3Channelized
                    TruthValue,
                hwDs3Clock
                    INTEGER,
                hwDs3FrameFormat
                    INTEGER,
                hwDs3Scramble
                    TruthValue,
                hwDs3Cable
                    INTEGER,
                hwDs3NationalBit
                    INTEGER,
                hwDs3Loopback
                    INTEGER,
                hwDs3CreateSerial
                    TruthValue,
                hwDs3RowStatus
                    RowStatus
             }

        -- 1.3.6.1.4.1.2011.5.25.157.1.6.1.1.1
        hwDs3ParentIfIndex OBJECT-TYPE
            SYNTAX InterfaceIndex
            MAX-ACCESS not-accessible
            STATUS current
            DESCRIPTION
                "Indicates the index of the parent interface."
            ::= { hwDs3Entry 1 }

        
        -- 1.3.6.1.4.1.2011.5.25.157.1.6.1.1.2
        hwDs3ChannelId OBJECT-TYPE
            SYNTAX Integer32 (0..3)
            MAX-ACCESS not-accessible
            STATUS current
            DESCRIPTION
                "Indicates the index of the parent interface."
            ::= { hwDs3Entry 2 }

        
        -- 1.3.6.1.4.1.2011.5.25.157.1.6.1.1.3
        hwDs3IfIndex OBJECT-TYPE
            SYNTAX InterfaceIndex
            MAX-ACCESS not-accessible
            STATUS current
            DESCRIPTION
                "Indicates the interface index."
            ::= { hwDs3Entry 3 }

        
        -- 1.3.6.1.4.1.2011.5.25.157.1.6.1.1.11
        hwDs3ChannelType OBJECT-TYPE
            SYNTAX INTEGER
                {
                t3(1),
                e3(2)
                }
            MAX-ACCESS read-create
            STATUS current
            DESCRIPTION
                "Indicates the interface type. The type can be E3/CE3 or T3/CT3."
            ::= { hwDs3Entry 11 }

        
        -- 1.3.6.1.4.1.2011.5.25.157.1.6.1.1.12
        hwDs3IfType OBJECT-TYPE
            SYNTAX INTEGER
                {
                cpos(1),
                none(255)
                }
            MAX-ACCESS read-create
            STATUS current
            DESCRIPTION
                "Indicates the parent interface type of the interface.
                cpos: is multiplexed by CPOS interfaces.
                none: indicates the interface is a physical interface.
                The default is none."
            DEFVAL { none }
            ::= { hwDs3Entry 12 }

        
        -- 1.3.6.1.4.1.2011.5.25.157.1.6.1.1.13
        hwDs3Channelized OBJECT-TYPE
            SYNTAX TruthValue
            MAX-ACCESS read-create
            STATUS current
            DESCRIPTION
                "Indicates the working mode of the interface.
                true: indicates the channelized mode.
                false: indicates the clear channel mode.
                The default is true."
            DEFVAL { true }
            ::= { hwDs3Entry 13 }

        
        -- 1.3.6.1.4.1.2011.5.25.157.1.6.1.1.14
        hwDs3Clock OBJECT-TYPE
            SYNTAX INTEGER
                {
                master(1),
                slave(2)
                }
            MAX-ACCESS read-create
            STATUS current
            DESCRIPTION
                "Indicates the clock mode of the interface.
                master: indicates that the clock works in master mode and uses the internal clock signal.
                slave: indicates that the clock works in slave mode and uses the line clock signal."
            ::= { hwDs3Entry 14 }

        
        -- 1.3.6.1.4.1.2011.5.25.157.1.6.1.1.15
        hwDs3FrameFormat OBJECT-TYPE
            SYNTAX INTEGER
                {
                g832Adm(1),
                g751Adm(2),
                g751Plcp(3),
                cbitAdm(4),
                cbitPlcp(5),
                m23Adm(6),
                m23Plcp(7)
                }
            MAX-ACCESS read-create
            STATUS current
            DESCRIPTION
                "Indicates the frame format of the interface."
            ::= { hwDs3Entry 15 }

        
        -- 1.3.6.1.4.1.2011.5.25.157.1.6.1.1.16
        hwDs3Scramble OBJECT-TYPE
            SYNTAX TruthValue
            MAX-ACCESS read-create
            STATUS current
            DESCRIPTION
                "Indicates the scramble function of the interface.
                true: enables the scramble function.
                false: disables the scramble function.
                The default is false."
            DEFVAL { false }
            ::= { hwDs3Entry 16 }

        
        -- 1.3.6.1.4.1.2011.5.25.157.1.6.1.1.17
        hwDs3Cable OBJECT-TYPE
            SYNTAX INTEGER
                {
                long(1),
                short(2)
                }
            MAX-ACCESS read-create
            STATUS current
            DESCRIPTION
                "The cable command takes effect only if the E3 interface card uses 75-ohm coaxial cable.
                The default is short. If no cable is connected, this parameter is displayed as null."
            DEFVAL { short }
            ::= { hwDs3Entry 17 }

        
        -- 1.3.6.1.4.1.2011.5.25.157.1.6.1.1.18
        hwDs3NationalBit OBJECT-TYPE
            SYNTAX INTEGER
                {
                n0(1),
                n1(2)
                }
            MAX-ACCESS read-create
            STATUS current
            DESCRIPTION
                "Indicates the national bit of the E3/CE3 interface.
                n0: indicates the national bit is 0 and the interface supports only the communication within a country.
                n1: indicates the national bit is 1 and the interface supports the international communication.  "
            DEFVAL { n0 }
            ::= { hwDs3Entry 18 }

        
        -- 1.3.6.1.4.1.2011.5.25.157.1.6.1.1.19
        hwDs3Loopback OBJECT-TYPE
            SYNTAX INTEGER
                {
                local(1),
                remote(2),
                payload(3),
                cell(4),
                none(255)
                }
            MAX-ACCESS read-create
            STATUS current
            DESCRIPTION
                "Enable the loopback function of the interface.
                local: enables the local loopback on the interface.
                remote: enables the remote loopback on the interface.
                payload: enables the remote payload loopback on the interface.
                cell: enables the local cell loopback. The local cell loopback is used to test the local physical chip."
            DEFVAL { none }
            ::= { hwDs3Entry 19 }

        
        -- 1.3.6.1.4.1.2011.5.25.157.1.6.1.1.20
        hwDs3CreateSerial OBJECT-TYPE
            SYNTAX TruthValue
            MAX-ACCESS read-create
            STATUS current
            DESCRIPTION
                "Create serial interface from Ds3 interface.
                True create serial interface.
                False  destroy serial interface.
                 "
            DEFVAL { false }
            ::= { hwDs3Entry 20 }

        
        -- 1.3.6.1.4.1.2011.5.25.157.1.6.1.1.51
        hwDs3RowStatus OBJECT-TYPE
            SYNTAX RowStatus
            MAX-ACCESS read-create
            STATUS current
            DESCRIPTION
                "This variable is used to create or delete an object."
            ::= { hwDs3Entry 51 }

        
        -- 1.3.6.1.4.1.2011.5.25.157.1.7
        hwBundleSerial OBJECT IDENTIFIER ::= { hwPortMIBObjects 7 }

        
        -- 1.3.6.1.4.1.2011.5.25.157.1.7.1
        hwBundleSerialTable OBJECT-TYPE
            SYNTAX SEQUENCE OF HwBundleSerialEntry
            MAX-ACCESS not-accessible
            STATUS current
            DESCRIPTION
                "Indicates the attribute of the serial interface formed by timeslots.
                This table lists the physical attributes of the serial interface."
            ::= { hwBundleSerial 1 }

        
        -- 1.3.6.1.4.1.2011.5.25.157.1.7.1.1
        hwBundleSerialEntry OBJECT-TYPE
            SYNTAX HwBundleSerialEntry
            MAX-ACCESS not-accessible
            STATUS current
            DESCRIPTION
                "Indicates the attribute of the serial interface formed by timeslots.
                This table lists the physical attributes of the serial interface."
            INDEX { hwBundleSerialIfIndex }
            ::= { hwBundleSerialTable 1 }

        
        HwBundleSerialEntry ::=
            SEQUENCE { 
                hwBundleSerialIfIndex
                    InterfaceIndex,
                hwBundleSerialLinkProtocol
                    INTEGER,
                hwBundleSerialTimerHold
                    Integer32,
                hwBundleSerialLoopback
                    TruthValue,
                hwBundleSerialCrcVerifyCode
                    INTEGER
             }

        -- 1.3.6.1.4.1.2011.5.25.157.1.7.1.1.1
        hwBundleSerialIfIndex OBJECT-TYPE
            SYNTAX InterfaceIndex
            MAX-ACCESS not-accessible
            STATUS current
            DESCRIPTION
                "Interface index(es) of serial(s) present on the device ."
            ::= { hwBundleSerialEntry 1 }

        
        -- 1.3.6.1.4.1.2011.5.25.157.1.7.1.1.11
        hwBundleSerialLinkProtocol OBJECT-TYPE
            SYNTAX INTEGER
                {
                ietf(1),
                nonstandard(2),
                hdlc(3),
                ppp(4),
                lapb(5),
                atm(6),
                tdm(7),
                none(255)
                }
            MAX-ACCESS read-write
            STATUS current
            DESCRIPTION
                "The link-protocol of interface. The serial(s) always use PPP as its link-protocol for default."
            ::= { hwBundleSerialEntry 11 }

        
        -- 1.3.6.1.4.1.2011.5.25.157.1.7.1.1.12
        hwBundleSerialTimerHold OBJECT-TYPE
            SYNTAX Integer32 (0..32767)
            MAX-ACCESS read-write
            STATUS current
            DESCRIPTION
                "Indicates the interval for sending Keepalive packets from the serial interface to the peer.
                The default is 10 seconds."
            ::= { hwBundleSerialEntry 12 }

        
        -- 1.3.6.1.4.1.2011.5.25.157.1.7.1.1.13
        hwBundleSerialLoopback OBJECT-TYPE
            SYNTAX TruthValue
            MAX-ACCESS read-write
            STATUS current
            DESCRIPTION
                "true: enables the loopback on the serial interface.
                false: disables the loopback on the serial interface.
                By default, the loopback on the serial interface is disabled."
            DEFVAL { false }
            ::= { hwBundleSerialEntry 13 }

        
        -- 1.3.6.1.4.1.2011.5.25.157.1.7.1.1.14
        hwBundleSerialCrcVerifyCode OBJECT-TYPE
            SYNTAX INTEGER
                {
                crc16(1),
                crc32(2)
                }
            MAX-ACCESS read-write
            STATUS current
            DESCRIPTION
                "Indicates the length of the CRC verify code. The default is 32."
            ::= { hwBundleSerialEntry 14 }

        
        -- 1.3.6.1.4.1.2011.5.25.157.1.8
        hwPhysicalPort OBJECT IDENTIFIER ::= { hwPortMIBObjects 8 }

        
        -- 1.3.6.1.4.1.2011.5.25.157.1.8.1
        hwPhysicalPortTable OBJECT-TYPE
            SYNTAX SEQUENCE OF HwPhysicalPortEntry
            MAX-ACCESS not-accessible
            STATUS current
            DESCRIPTION
                "Indicates the attribute of the physical port."
            ::= { hwPhysicalPort 1 }

        
        -- 1.3.6.1.4.1.2011.5.25.157.1.8.1.1
        hwPhysicalPortEntry OBJECT-TYPE
            SYNTAX HwPhysicalPortEntry
            MAX-ACCESS not-accessible
            STATUS current
            DESCRIPTION
                "Indicates the attribute of the physical port."
            INDEX { hwPhysicalPortIfIndex }
            ::= { hwPhysicalPortTable 1 }

        
        HwPhysicalPortEntry ::=
            SEQUENCE { 
                hwPhysicalPortIfIndex
                    InterfaceIndex,
                hwPhysicalPortDelayTime
                    Unsigned32,
                hwPhysicalPortDelayRemainTime
                    Unsigned32,
                hwPhysicalPortName
                    OCTET STRING,
                hwPhysicalPortInChassis
                    Integer32,
                hwPhysicalPortInSlot
                    Integer32,
                hwPhysicalPortInCard
                    Integer32,
                hwPhysicalPortInPort
                    Integer32,
                hwPhysicalAutoShutLaserEnable
                    INTEGER,
                hwPhysicalAutoShutLaserOpenInterval
                    Integer32,
                hwPhysicalAutoShutLaserCloseInterval
                    Integer32,
                hwPhysicalAutoShutLaserLongOpenInterval
                    Integer32,
                hwPhysicalLoopbackType
                    INTEGER,
                hwPhysicalShutLaser
                    INTEGER,
                hwPhysicalLaserStatus
                    INTEGER,
                hwPhysicalPortHoldUp
                    INTEGER,
                hwPhysicalPortAlarmInverseEnable
                    INTEGER
             }

        -- 1.3.6.1.4.1.2011.5.25.157.1.8.1.1.1
        hwPhysicalPortIfIndex OBJECT-TYPE
            SYNTAX InterfaceIndex
            MAX-ACCESS not-accessible
            STATUS current
            DESCRIPTION
                "Interface index(es) of physical port(s) present on the device ."
            ::= { hwPhysicalPortEntry 1 }

        
        -- 1.3.6.1.4.1.2011.5.25.157.1.8.1.1.2
        hwPhysicalPortDelayTime OBJECT-TYPE
            SYNTAX Unsigned32 (0..86400000)
            MAX-ACCESS read-write
            STATUS current
            DESCRIPTION
                "Indicates the port tx enabling delay time. The units of hwPhysicalPortDelayTime is millisecond. The default value is 0 ms. "
            DEFVAL { 0 }
            ::= { hwPhysicalPortEntry 2 }

        
        -- 1.3.6.1.4.1.2011.5.25.157.1.8.1.1.3
        hwPhysicalPortDelayRemainTime OBJECT-TYPE
            SYNTAX Unsigned32 (0..86400000)
            MAX-ACCESS read-only
            STATUS current
            DESCRIPTION
                "Indicates the remnant time of enabling port-tx. The units of hwPhysicalPortDelayTime is millisecond."
            ::= { hwPhysicalPortEntry 3 }

        
        -- 1.3.6.1.4.1.2011.5.25.157.1.8.1.1.4
        hwPhysicalPortName OBJECT-TYPE
            SYNTAX OCTET STRING
            MAX-ACCESS read-only
            STATUS current
            DESCRIPTION
                "Indicates the physical port name."
            ::= { hwPhysicalPortEntry 4 }

        
        -- 1.3.6.1.4.1.2011.5.25.157.1.8.1.1.5
        hwPhysicalPortInChassis OBJECT-TYPE
            SYNTAX Integer32
            MAX-ACCESS read-only
            STATUS current
            DESCRIPTION
                "Indicates the physical port in chassis."
            ::= { hwPhysicalPortEntry 5 }

        
        -- 1.3.6.1.4.1.2011.5.25.157.1.8.1.1.6
        hwPhysicalPortInSlot OBJECT-TYPE
            SYNTAX Integer32
            MAX-ACCESS read-only
            STATUS current
            DESCRIPTION
                "Indicates the SlotID."
            ::= { hwPhysicalPortEntry 6 }

        
        -- 1.3.6.1.4.1.2011.5.25.157.1.8.1.1.7
        hwPhysicalPortInCard OBJECT-TYPE
            SYNTAX Integer32
            MAX-ACCESS read-only
            STATUS current
            DESCRIPTION
                "Indicates the CardID."
            ::= { hwPhysicalPortEntry 7 }

        
        -- 1.3.6.1.4.1.2011.5.25.157.1.8.1.1.8
        hwPhysicalPortInPort OBJECT-TYPE
            SYNTAX Integer32
            MAX-ACCESS read-only
            STATUS current
            DESCRIPTION
                "Indicates the PortID."
            ::= { hwPhysicalPortEntry 8 }

        
        -- 1.3.6.1.4.1.2011.5.25.157.1.8.1.1.9
        hwPhysicalAutoShutLaserEnable OBJECT-TYPE
            SYNTAX INTEGER
                {
                enable(1),
                disable(2),
                not-support(255)
                }
            MAX-ACCESS read-write
            STATUS current
            DESCRIPTION
                " Indicates enable or disable the laser auto shut . Default is disable."
            ::= { hwPhysicalPortEntry 9 }

        
        -- 1.3.6.1.4.1.2011.5.25.157.1.8.1.1.10
        hwPhysicalAutoShutLaserOpenInterval OBJECT-TYPE
            SYNTAX Integer32 (100..300 | 2147483647)
            MAX-ACCESS read-write
            STATUS current
            DESCRIPTION
                " Indicates the open interval of laser auto shut . The default value is 200 (unit: 10 ms). The value 2147483647 means that the interface doesn't support laser auto shut."
            ::= { hwPhysicalPortEntry 10 }

        
        -- 1.3.6.1.4.1.2011.5.25.157.1.8.1.1.11
        hwPhysicalAutoShutLaserCloseInterval OBJECT-TYPE
            SYNTAX Integer32 (200..30000 | 2147483647)
            MAX-ACCESS read-write
            STATUS current
            DESCRIPTION
                " Indicates the close interval of laser auto shut . The default value is 6000 (unit: 10 ms). The value 2147483647 means that the interface doesn't support laser auto shut."
            ::= { hwPhysicalPortEntry 11 }

        
        -- 1.3.6.1.4.1.2011.5.25.157.1.8.1.1.12
        hwPhysicalAutoShutLaserLongOpenInterval OBJECT-TYPE
            SYNTAX Integer32 (200..30000 | 2147483647)
            MAX-ACCESS read-write
            STATUS current
            DESCRIPTION
                " Indicates the long open interval of laser auto shut . The default value is 9000 (unit: 10 ms). The value 2147483647 means that the interface doesn't support laser auto shut."
            ::= { hwPhysicalPortEntry 12 }

        
        -- 1.3.6.1.4.1.2011.5.25.157.1.8.1.1.13
        hwPhysicalLoopbackType OBJECT-TYPE
            SYNTAX INTEGER
                {
                otherLoop(1),
                stopLoopback(2),
                local(3),
                remote(4)
                }
            MAX-ACCESS read-only
            STATUS current
            DESCRIPTION
                " The current state of loopbackType in port."
            ::= { hwPhysicalPortEntry 13 }

        
        -- 1.3.6.1.4.1.2011.5.25.157.1.8.1.1.14
        hwPhysicalShutLaser OBJECT-TYPE
            SYNTAX INTEGER
                {
                off(1),
                on(2),
                not-support(255)
                }
            MAX-ACCESS read-write
            STATUS current
            DESCRIPTION
                " Turn on or turn off the laser."
            ::= { hwPhysicalPortEntry 14 }

        
        -- 1.3.6.1.4.1.2011.5.25.157.1.8.1.1.15
        hwPhysicalLaserStatus OBJECT-TYPE
            SYNTAX INTEGER
                {
                off(1),
                on(2),
                offline(3),
                not-support(255)
                }
            MAX-ACCESS read-only
            STATUS current
            DESCRIPTION
                " The current status of the laser."
            ::= { hwPhysicalPortEntry 15 }

        
        -- 1.3.6.1.4.1.2011.5.25.157.1.8.1.1.16
        hwPhysicalPortHoldUp OBJECT-TYPE
            SYNTAX INTEGER
                {
                disable(0),
                enable(1)
                }
            MAX-ACCESS read-write
            STATUS current
            DESCRIPTION
                " Indicates enable or disable the interface to remain Up , the default value is disable."
            ::= { hwPhysicalPortEntry 16 }

        -- 1.3.6.1.4.1.2011.5.25.157.1.8.1.1.17
        hwPhysicalPortAlarmInverseEnable OBJECT-TYPE
            SYNTAX INTEGER
                {
                enable(1),
                disable(2)
                }
            MAX-ACCESS read-write
            STATUS current
            DESCRIPTION
                "Config port alarm inverse enable."
            ::= { hwPhysicalPortEntry 17 }
        
        -- 1.3.6.1.4.1.2011.5.25.157.1.8.2
        hwSDHRsMsPerfCurrentTable OBJECT-TYPE
            SYNTAX SEQUENCE OF HwSDHRsMsPerfCurrentEntry
            MAX-ACCESS not-accessible
            STATUS current
            DESCRIPTION
                "Indicates the performance stat of the Regenerator Section."
            ::= { hwPhysicalPort 2 }

        
        -- 1.3.6.1.4.1.2011.5.25.157.1.8.2.1
        hwSDHRsMsPerfCurrentEntry OBJECT-TYPE
            SYNTAX HwSDHRsMsPerfCurrentEntry
            MAX-ACCESS not-accessible
            STATUS current
            DESCRIPTION
                "Indicates the performance stat of the Regenerator Section."
            INDEX { hwSDHRsMsPerfCurrentIfIndex, hwSDHRsMsPerfCurrentDataIndex }
            ::= { hwSDHRsMsPerfCurrentTable 1 }

        
        HwSDHRsMsPerfCurrentEntry ::=
            SEQUENCE { 
                hwSDHRsMsPerfCurrentIfIndex
                    InterfaceIndex,
                hwSDHRsMsPerfCurrentDataIndex
                    Integer32,
                hwSDHRsPerfCurrentBBE
                    Integer32,
                hwSDHRsPerfCurrentES
                    Integer32,
                hwSDHRsPerfCurrentSES
                    Integer32,
                hwSDHRsPerfCurrentUAS
                    Integer32,
                hwSDHMsPerfCurrentBBE
                    Integer32,
                hwSDHMsPerfCurrentES
                    Integer32,
                hwSDHMsPerfCurrentSES
                    Integer32,
                hwSDHMsPerfCurrentUAS
                    Integer32,
                hwSDHMsPerfCurrentFEBBE
                    Integer32,
                hwSDHMsPerfCurrentFEES
                    Integer32,
                hwSDHMsPerfCurrentFESES
                    Integer32,
                hwSDHMsPerfCurrentFEUAS
                    Integer32
             }

        -- 1.3.6.1.4.1.2011.5.25.157.1.8.2.1.1
        hwSDHRsMsPerfCurrentIfIndex OBJECT-TYPE
            SYNTAX InterfaceIndex
            MAX-ACCESS not-accessible
            STATUS current
            DESCRIPTION
                "Interface index(es) of port(s) present on the device ."
            ::= { hwSDHRsMsPerfCurrentEntry 1 }

        
        -- 1.3.6.1.4.1.2011.5.25.157.1.8.2.1.2
        hwSDHRsMsPerfCurrentDataIndex OBJECT-TYPE
            SYNTAX Integer32 (0..1)
            MAX-ACCESS not-accessible
            STATUS current
            DESCRIPTION
                "Data index(es) of port(s) present on the device ."
            ::= { hwSDHRsMsPerfCurrentEntry 2 }

        
        -- 1.3.6.1.4.1.2011.5.25.157.1.8.2.1.3
        hwSDHRsPerfCurrentBBE OBJECT-TYPE
            SYNTAX Integer32
            MAX-ACCESS read-only
            STATUS current
            DESCRIPTION
                "Regenerator Section Background Block Error."
            ::= { hwSDHRsMsPerfCurrentEntry 3 }

        
        -- 1.3.6.1.4.1.2011.5.25.157.1.8.2.1.4
        hwSDHRsPerfCurrentES OBJECT-TYPE
            SYNTAX Integer32
            MAX-ACCESS read-only
            STATUS current
            DESCRIPTION
                "Regenerator Section Errored Second."
            ::= { hwSDHRsMsPerfCurrentEntry 4 }

        
        -- 1.3.6.1.4.1.2011.5.25.157.1.8.2.1.5
        hwSDHRsPerfCurrentSES OBJECT-TYPE
            SYNTAX Integer32
            MAX-ACCESS read-only
            STATUS current
            DESCRIPTION
                "Regenerator Section Severely Errored Second."
            ::= { hwSDHRsMsPerfCurrentEntry 5 }

        
        -- 1.3.6.1.4.1.2011.5.25.157.1.8.2.1.6
        hwSDHRsPerfCurrentUAS OBJECT-TYPE
            SYNTAX Integer32
            MAX-ACCESS read-only
            STATUS current
            DESCRIPTION
                "Regenerator section unavailable second."
            ::= { hwSDHRsMsPerfCurrentEntry 6 }

        
        -- 1.3.6.1.4.1.2011.5.25.157.1.8.2.1.7
        hwSDHMsPerfCurrentBBE OBJECT-TYPE
            SYNTAX Integer32
            MAX-ACCESS read-only
            STATUS current
            DESCRIPTION
                "Multiplex Section Background Block Error."
            ::= { hwSDHRsMsPerfCurrentEntry 7 }

        
        -- 1.3.6.1.4.1.2011.5.25.157.1.8.2.1.8
        hwSDHMsPerfCurrentES OBJECT-TYPE
            SYNTAX Integer32
            MAX-ACCESS read-only
            STATUS current
            DESCRIPTION
                "Multiplex Section Errored Second."
            ::= { hwSDHRsMsPerfCurrentEntry 8 }

        
        -- 1.3.6.1.4.1.2011.5.25.157.1.8.2.1.9
        hwSDHMsPerfCurrentSES OBJECT-TYPE
            SYNTAX Integer32
            MAX-ACCESS read-only
            STATUS current
            DESCRIPTION
                "Multiplex Section Severely Errored Second."
            ::= { hwSDHRsMsPerfCurrentEntry 9 }

        
        -- 1.3.6.1.4.1.2011.5.25.157.1.8.2.1.10
        hwSDHMsPerfCurrentUAS OBJECT-TYPE
            SYNTAX Integer32
            MAX-ACCESS read-only
            STATUS current
            DESCRIPTION
                "Multiplex Section Unavaliable Seconds."
            ::= { hwSDHRsMsPerfCurrentEntry 10 }

        
        -- 1.3.6.1.4.1.2011.5.25.157.1.8.2.1.11
        hwSDHMsPerfCurrentFEBBE OBJECT-TYPE
            SYNTAX Integer32
            MAX-ACCESS read-only
            STATUS current
            DESCRIPTION
                "Multiplex Section Far end Background Block Error."
            ::= { hwSDHRsMsPerfCurrentEntry 11 }

        
        -- 1.3.6.1.4.1.2011.5.25.157.1.8.2.1.12
        hwSDHMsPerfCurrentFEES OBJECT-TYPE
            SYNTAX Integer32
            MAX-ACCESS read-only
            STATUS current
            DESCRIPTION
                "Multiplex Section Far end Errored Second."
            ::= { hwSDHRsMsPerfCurrentEntry 12 }

        
        -- 1.3.6.1.4.1.2011.5.25.157.1.8.2.1.13
        hwSDHMsPerfCurrentFESES OBJECT-TYPE
            SYNTAX Integer32
            MAX-ACCESS read-only
            STATUS current
            DESCRIPTION
                "Multiplex Section Far end Severely Errored Second."
            ::= { hwSDHRsMsPerfCurrentEntry 13 }

        
        -- 1.3.6.1.4.1.2011.5.25.157.1.8.2.1.14
        hwSDHMsPerfCurrentFEUAS OBJECT-TYPE
            SYNTAX Integer32
            MAX-ACCESS read-only
            STATUS current
            DESCRIPTION
                "Multiplex Section Far end Unavaliable Seconds."
            ::= { hwSDHRsMsPerfCurrentEntry 14 }

        
        -- 1.3.6.1.4.1.2011.5.25.157.1.8.3
        hwSDHHpPerfCurrentTable OBJECT-TYPE
            SYNTAX SEQUENCE OF HwSDHHpPerfCurrentEntry
            MAX-ACCESS not-accessible
            STATUS current
            DESCRIPTION
                "Indicates the performance stat of the Higher order Path."
            ::= { hwPhysicalPort 3 }

        
        -- 1.3.6.1.4.1.2011.5.25.157.1.8.3.1
        hwSDHHpPerfCurrentEntry OBJECT-TYPE
            SYNTAX HwSDHHpPerfCurrentEntry
            MAX-ACCESS not-accessible
            STATUS current
            DESCRIPTION
                "Indicates the performance stat of the Higher order Path."
            INDEX { hwSDHHpPerfCurrentIfIndex, hwSDHHpPerfCurrentHpIndex, hwSDHHpPerfCurrentDataIndex }
            ::= { hwSDHHpPerfCurrentTable 1 }

        
        HwSDHHpPerfCurrentEntry ::=
            SEQUENCE { 
                hwSDHHpPerfCurrentIfIndex
                    InterfaceIndex,
                hwSDHHpPerfCurrentHpIndex
                    Integer32,
                hwSDHHpPerfCurrentDataIndex
                    Integer32,
                hwSDHHpPerfCurrentBBE
                    Integer32,
                hwSDHHpPerfCurrentES
                    Integer32,
                hwSDHHpPerfCurrentSES
                    Integer32,
                hwSDHHpPerfCurrentUAS
                    Integer32,
                hwSDHHpPerfCurrentFEBBE
                    Integer32,
                hwSDHHpPerfCurrentFEES
                    Integer32,
                hwSDHHpPerfCurrentFESES
                    Integer32,
                hwSDHHpPerfCurrentFEUAS
                    Integer32
             }

        -- 1.3.6.1.4.1.2011.5.25.157.1.8.3.1.1
        hwSDHHpPerfCurrentIfIndex OBJECT-TYPE
            SYNTAX InterfaceIndex
            MAX-ACCESS not-accessible
            STATUS current
            DESCRIPTION
                "Interface index(es) of port(s) present on the device ."
            ::= { hwSDHHpPerfCurrentEntry 1 }

        
        -- 1.3.6.1.4.1.2011.5.25.157.1.8.3.1.2
        hwSDHHpPerfCurrentHpIndex OBJECT-TYPE
            SYNTAX Integer32
            MAX-ACCESS not-accessible
            STATUS current
            DESCRIPTION
                "Higher order Path index(es) of port(s) present on the device ."
            ::= { hwSDHHpPerfCurrentEntry 2 }

        
        -- 1.3.6.1.4.1.2011.5.25.157.1.8.3.1.3
        hwSDHHpPerfCurrentDataIndex OBJECT-TYPE
            SYNTAX Integer32 (0..1)
            MAX-ACCESS not-accessible
            STATUS current
            DESCRIPTION
                "Data index(es) of port(s) present on the device ."
            ::= { hwSDHHpPerfCurrentEntry 3 }

        
        -- 1.3.6.1.4.1.2011.5.25.157.1.8.3.1.4
        hwSDHHpPerfCurrentBBE OBJECT-TYPE
            SYNTAX Integer32
            MAX-ACCESS read-only
            STATUS current
            DESCRIPTION
                "Multiplex Section Far end Unavaliable Seconds."
            ::= { hwSDHHpPerfCurrentEntry 4 }

        
        -- 1.3.6.1.4.1.2011.5.25.157.1.8.3.1.5
        hwSDHHpPerfCurrentES OBJECT-TYPE
            SYNTAX Integer32
            MAX-ACCESS read-only
            STATUS current
            DESCRIPTION
                "Higher order Path Errored Second."
            ::= { hwSDHHpPerfCurrentEntry 5 }

        
        -- 1.3.6.1.4.1.2011.5.25.157.1.8.3.1.6
        hwSDHHpPerfCurrentSES OBJECT-TYPE
            SYNTAX Integer32
            MAX-ACCESS read-only
            STATUS current
            DESCRIPTION
                "Higher order Path Severely Errored Second."
            ::= { hwSDHHpPerfCurrentEntry 6 }

        
        -- 1.3.6.1.4.1.2011.5.25.157.1.8.3.1.7
        hwSDHHpPerfCurrentUAS OBJECT-TYPE
            SYNTAX Integer32
            MAX-ACCESS read-only
            STATUS current
            DESCRIPTION
                "Higher order Path Unavaliable Seconds."
            ::= { hwSDHHpPerfCurrentEntry 7 }

        
        -- 1.3.6.1.4.1.2011.5.25.157.1.8.3.1.8
        hwSDHHpPerfCurrentFEBBE OBJECT-TYPE
            SYNTAX Integer32
            MAX-ACCESS read-only
            STATUS current
            DESCRIPTION
                "Higher order Path Far end Background Block Error."
            ::= { hwSDHHpPerfCurrentEntry 8 }

        
        -- 1.3.6.1.4.1.2011.5.25.157.1.8.3.1.9
        hwSDHHpPerfCurrentFEES OBJECT-TYPE
            SYNTAX Integer32
            MAX-ACCESS read-only
            STATUS current
            DESCRIPTION
                "Higher order Path Far end Errored Second."
            ::= { hwSDHHpPerfCurrentEntry 9 }

        
        -- 1.3.6.1.4.1.2011.5.25.157.1.8.3.1.10
        hwSDHHpPerfCurrentFESES OBJECT-TYPE
            SYNTAX Integer32
            MAX-ACCESS read-only
            STATUS current
            DESCRIPTION
                "Higher order Path Far end Severely Errored Second."
            ::= { hwSDHHpPerfCurrentEntry 10 }

        
        -- 1.3.6.1.4.1.2011.5.25.157.1.8.3.1.11
        hwSDHHpPerfCurrentFEUAS OBJECT-TYPE
            SYNTAX Integer32
            MAX-ACCESS read-only
            STATUS current
            DESCRIPTION
                "Higher order Path Far end Unavaliable Seconds."
            ::= { hwSDHHpPerfCurrentEntry 11 }

        
        -- 1.3.6.1.4.1.2011.5.25.157.1.8.4
        hwSDHLpPerfCurrentTable OBJECT-TYPE
            SYNTAX SEQUENCE OF HwSDHLpPerfCurrentEntry
            MAX-ACCESS not-accessible
            STATUS current
            DESCRIPTION
                "Indicates the performance stat of the Low order Path."
            ::= { hwPhysicalPort 4 }

        
        -- 1.3.6.1.4.1.2011.5.25.157.1.8.4.1
        hwSDHLpPerfCurrentEntry OBJECT-TYPE
            SYNTAX HwSDHLpPerfCurrentEntry
            MAX-ACCESS not-accessible
            STATUS current
            DESCRIPTION
                "Indicates the performance stat of the Low order Path."
            INDEX { hwSDHLpPerfCurrentIfIndex, hwSDHLpPerfCurrentHpIndex, hwSDHLpPerfCurrentLpIndex, hwSDHLpPerfCurrentDataIndex }
            ::= { hwSDHLpPerfCurrentTable 1 }

        
        HwSDHLpPerfCurrentEntry ::=
            SEQUENCE { 
                hwSDHLpPerfCurrentIfIndex
                    InterfaceIndex,
                hwSDHLpPerfCurrentHpIndex
                    Integer32,
                hwSDHLpPerfCurrentLpIndex
                    Integer32,
                hwSDHLpPerfCurrentDataIndex
                    Integer32,
                hwSDHLpPerfCurrentBBE
                    Integer32,
                hwSDHLpPerfCurrentES
                    Integer32,
                hwSDHLpPerfCurrentSES
                    Integer32,
                hwSDHLpPerfCurrentUAS
                    Integer32,
                hwSDHLpPerfCurrentFEBBE
                    Integer32,
                hwSDHLpPerfCurrentFEES
                    Integer32,
                hwSDHLpPerfCurrentFESES
                    Integer32,
                hwSDHLpPerfCurrentFEUAS
                    Integer32
             }

        -- 1.3.6.1.4.1.2011.5.25.157.1.8.4.1.1
        hwSDHLpPerfCurrentIfIndex OBJECT-TYPE
            SYNTAX InterfaceIndex
            MAX-ACCESS not-accessible
            STATUS current
            DESCRIPTION
                "Interface index(es) of port(s) present on the device ."
            ::= { hwSDHLpPerfCurrentEntry 1 }

        
        -- 1.3.6.1.4.1.2011.5.25.157.1.8.4.1.2
        hwSDHLpPerfCurrentHpIndex OBJECT-TYPE
            SYNTAX Integer32
            MAX-ACCESS not-accessible
            STATUS current
            DESCRIPTION
                "Higher order Path index(es) of port(s) present on the device ."
            ::= { hwSDHLpPerfCurrentEntry 2 }

        
        -- 1.3.6.1.4.1.2011.5.25.157.1.8.4.1.3
        hwSDHLpPerfCurrentLpIndex OBJECT-TYPE
            SYNTAX Integer32
            MAX-ACCESS not-accessible
            STATUS current
            DESCRIPTION
                "Low order Path index(es) of port(s) present on the device ."
            ::= { hwSDHLpPerfCurrentEntry 3 }

        
        -- 1.3.6.1.4.1.2011.5.25.157.1.8.4.1.4
        hwSDHLpPerfCurrentDataIndex OBJECT-TYPE
            SYNTAX Integer32 (0..1)
            MAX-ACCESS not-accessible
            STATUS current
            DESCRIPTION
                "Data index(es) of port(s) present on the device ."
            ::= { hwSDHLpPerfCurrentEntry 4 }

        
        -- 1.3.6.1.4.1.2011.5.25.157.1.8.4.1.5
        hwSDHLpPerfCurrentBBE OBJECT-TYPE
            SYNTAX Integer32
            MAX-ACCESS read-only
            STATUS current
            DESCRIPTION
                "Low order Path Background Block Error."
            ::= { hwSDHLpPerfCurrentEntry 5 }

        
        -- 1.3.6.1.4.1.2011.5.25.157.1.8.4.1.6
        hwSDHLpPerfCurrentES OBJECT-TYPE
            SYNTAX Integer32
            MAX-ACCESS read-only
            STATUS current
            DESCRIPTION
                "Low order Path errored seconds."
            ::= { hwSDHLpPerfCurrentEntry 6 }

        
        -- 1.3.6.1.4.1.2011.5.25.157.1.8.4.1.7
        hwSDHLpPerfCurrentSES OBJECT-TYPE
            SYNTAX Integer32
            MAX-ACCESS read-only
            STATUS current
            DESCRIPTION
                "Low order Path severely errored seconds."
            ::= { hwSDHLpPerfCurrentEntry 7 }

        
        -- 1.3.6.1.4.1.2011.5.25.157.1.8.4.1.8
        hwSDHLpPerfCurrentUAS OBJECT-TYPE
            SYNTAX Integer32
            MAX-ACCESS read-only
            STATUS current
            DESCRIPTION
                "Low order Path Unavailable second."
            ::= { hwSDHLpPerfCurrentEntry 8 }

        
        -- 1.3.6.1.4.1.2011.5.25.157.1.8.4.1.9
        hwSDHLpPerfCurrentFEBBE OBJECT-TYPE
            SYNTAX Integer32
            MAX-ACCESS read-only
            STATUS current
            DESCRIPTION
                "Low order Path Far-end Background Block Error."
            ::= { hwSDHLpPerfCurrentEntry 9 }

        
        -- 1.3.6.1.4.1.2011.5.25.157.1.8.4.1.10
        hwSDHLpPerfCurrentFEES OBJECT-TYPE
            SYNTAX Integer32
            MAX-ACCESS read-only
            STATUS current
            DESCRIPTION
                "Low order Path Far-end errored seconds."
            ::= { hwSDHLpPerfCurrentEntry 10 }

        
        -- 1.3.6.1.4.1.2011.5.25.157.1.8.4.1.11
        hwSDHLpPerfCurrentFESES OBJECT-TYPE
            SYNTAX Integer32
            MAX-ACCESS read-only
            STATUS current
            DESCRIPTION
                "Low order Path Far-end severely errored seconds."
            ::= { hwSDHLpPerfCurrentEntry 11 }

        
        -- 1.3.6.1.4.1.2011.5.25.157.1.8.4.1.12
        hwSDHLpPerfCurrentFEUAS OBJECT-TYPE
            SYNTAX Integer32
            MAX-ACCESS read-only
            STATUS current
            DESCRIPTION
                "Low order Path Far-end Unavailable second."
            ::= { hwSDHLpPerfCurrentEntry 12 }

        
        -- 1.3.6.1.4.1.2011.5.25.157.1.8.5
        hwPDHPerfCurrentTable OBJECT-TYPE
            SYNTAX SEQUENCE OF HwPDHPerfCurrentEntry
            MAX-ACCESS not-accessible
            STATUS current
            DESCRIPTION
                "Indicates the performance stat of the E1 line side."
            ::= { hwPhysicalPort 5 }

        
        -- 1.3.6.1.4.1.2011.5.25.157.1.8.5.1
        hwPDHPerfCurrentEntry OBJECT-TYPE
            SYNTAX HwPDHPerfCurrentEntry
            MAX-ACCESS not-accessible
            STATUS current
            DESCRIPTION
                "Indicates the performance stat of the E1 line side."
            INDEX { hwPDHPerfCurrentIfIndex, hwPDHPerfCurrentDataIndex }
            ::= { hwPDHPerfCurrentTable 1 }

        
        HwPDHPerfCurrentEntry ::=
            SEQUENCE { 
                hwPDHPerfCurrentIfIndex
                    InterfaceIndex,
                hwPDHPerfCurrentDataIndex
                    Integer32,
                hwPDHPerfCurrentBBE
                    Integer32,
                hwPDHPerfCurrentES
                    Integer32,
                hwPDHPerfCurrentSES
                    Integer32,
                hwPDHPerfCurrentUAS
                    Integer32
             }

        -- 1.3.6.1.4.1.2011.5.25.157.1.8.5.1.1
        hwPDHPerfCurrentIfIndex OBJECT-TYPE
            SYNTAX InterfaceIndex
            MAX-ACCESS not-accessible
            STATUS current
            DESCRIPTION
                "Interface index(es) of port(s) present on the device."
            ::= { hwPDHPerfCurrentEntry 1 }

        
        -- 1.3.6.1.4.1.2011.5.25.157.1.8.5.1.2
        hwPDHPerfCurrentDataIndex OBJECT-TYPE
            SYNTAX Integer32 (0..1)
            MAX-ACCESS not-accessible
            STATUS current
            DESCRIPTION
                "Data index(es) of port(s) present on the device."
            ::= { hwPDHPerfCurrentEntry 2 }

        
        -- 1.3.6.1.4.1.2011.5.25.157.1.8.5.1.3
        hwPDHPerfCurrentBBE OBJECT-TYPE
            SYNTAX Integer32
            MAX-ACCESS read-only
            STATUS current
            DESCRIPTION
                "E1 line side code violation count."
            ::= { hwPDHPerfCurrentEntry 3 }

        
        -- 1.3.6.1.4.1.2011.5.25.157.1.8.5.1.4
        hwPDHPerfCurrentES OBJECT-TYPE
            SYNTAX Integer32
            MAX-ACCESS read-only
            STATUS current
            DESCRIPTION
                "E1 line side code violation errored second."
            ::= { hwPDHPerfCurrentEntry 4 }

        
        -- 1.3.6.1.4.1.2011.5.25.157.1.8.5.1.5
        hwPDHPerfCurrentSES OBJECT-TYPE
            SYNTAX Integer32
            MAX-ACCESS read-only
            STATUS current
            DESCRIPTION
                "E1 line side code violation severely errored second."
            ::= { hwPDHPerfCurrentEntry 5 }

        
        -- 1.3.6.1.4.1.2011.5.25.157.1.8.5.1.6
        hwPDHPerfCurrentUAS OBJECT-TYPE
            SYNTAX Integer32
            MAX-ACCESS read-only
            STATUS current
            DESCRIPTION
                "E1 line side code violation loss-of-signal second."
            ::= { hwPDHPerfCurrentEntry 6 }

        
        -- 1.3.6.1.4.1.2011.5.25.157.1.8.6
        hwEthPortStatTable OBJECT-TYPE
            SYNTAX SEQUENCE OF HwEthPortStatEntry
            MAX-ACCESS not-accessible
            STATUS current
            DESCRIPTION
                "Indicates the stat of the ethernet interface."
            ::= { hwPhysicalPort 6 }

        
        -- 1.3.6.1.4.1.2011.5.25.157.1.8.6.1
        hwEthPortStatEntry OBJECT-TYPE
            SYNTAX HwEthPortStatEntry
            MAX-ACCESS not-accessible
            STATUS current
            DESCRIPTION
                "Indicates the stat of the ethernet interface."
            INDEX { hwEthPortStatIfIndex }
            ::= { hwEthPortStatTable 1 }

        
        HwEthPortStatEntry ::=
            SEQUENCE { 
                hwEthPortStatIfIndex
                    InterfaceIndex,
                hwEthPortStatBadBytes
                    Counter64
             }

        -- 1.3.6.1.4.1.2011.5.25.157.1.8.6.1.1
        hwEthPortStatIfIndex OBJECT-TYPE
            SYNTAX InterfaceIndex
            MAX-ACCESS not-accessible
            STATUS current
            DESCRIPTION
                "Interface index(es) of port(s) present on the device."
            ::= { hwEthPortStatEntry 1 }

        
        -- 1.3.6.1.4.1.2011.5.25.157.1.8.6.1.2
        hwEthPortStatBadBytes OBJECT-TYPE
            SYNTAX Counter64
            MAX-ACCESS read-only
            STATUS current
            DESCRIPTION
                "Indicates the stat of badbytes."
            ::= { hwEthPortStatEntry 2 }

    -- 1.3.6.1.4.1.2011.5.25.157.1.8.7
    hwPhysicalPortGlobleCfg OBJECT IDENTIFIER ::= { hwPhysicalPort 7 }

        
    -- 1.3.6.1.4.1.2011.5.25.157.1.8.7.1
    hwLoopBackAutoClearEnable OBJECT-TYPE
        SYNTAX INTEGER
        {
            enable(1),
        disable(2)
        }
        MAX-ACCESS read-write
        STATUS current
        DESCRIPTION
            "set loopback autoclear status enable(1) disable(2)."
        ::= { hwPhysicalPortGlobleCfg 1 }

        
    -- 1.3.6.1.4.1.2011.5.25.157.1.8.7.2
    hwLoopBackAutoClearPeriod OBJECT-TYPE
        SYNTAX Integer32 (1..2880)
        UNITS "minute"
        MAX-ACCESS read-write
        STATUS current
        DESCRIPTION
            "set loopback autoclear period, unit minute,value range<1-2880> default<5 minute>."
        ::= { hwPhysicalPortGlobleCfg 2 }


    -- 1.3.6.1.4.1.2011.5.25.157.1.8.7.3
    hwPortAlarmInverseEnable OBJECT-TYPE
        SYNTAX INTEGER
		{
		enable(1),
		disable(2)
		}
        MAX-ACCESS read-write
        STATUS current
        DESCRIPTION
            "Config globle alarm inverse enable."
        ::= { hwPhysicalPortGlobleCfg 3 }


        -- 1.3.6.1.4.1.2011.5.25.157.1.9
        hwDslGroup OBJECT IDENTIFIER ::= { hwPortMIBObjects 9 }

        
        -- 1.3.6.1.4.1.2011.5.25.157.1.9.1
        hwDslGroupTable OBJECT-TYPE
            SYNTAX SEQUENCE OF HwDslGroupEntry
            MAX-ACCESS not-accessible
            STATUS current
            DESCRIPTION
                "Indicates the attributes of the dsl group."
            ::= { hwDslGroup 1 }

        
        -- 1.3.6.1.4.1.2011.5.25.157.1.9.1.1
        hwDslGroupEntry OBJECT-TYPE
            SYNTAX HwDslGroupEntry
            MAX-ACCESS not-accessible
            STATUS current
            DESCRIPTION
                "An entry in the dsl group table."
            INDEX { hwDslGroupIfIndex }
            ::= { hwDslGroupTable 1 }

        
        HwDslGroupEntry ::=
            SEQUENCE { 
                hwDslGroupIfIndex
                    InterfaceIndex,
                hwDslGroupWorkMode
                    INTEGER,
                hwDslGroupBisState
                    INTEGER,
                hwDslGroupEncapeMode
                    INTEGER,
                hwDslGroupEnable
                    INTEGER,
                hwDslGroupRowStatus
                    RowStatus
             }

        -- 1.3.6.1.4.1.2011.5.25.157.1.9.1.1.1
        hwDslGroupIfIndex OBJECT-TYPE
            SYNTAX InterfaceIndex
            MAX-ACCESS read-only
            STATUS current
            DESCRIPTION
                "Interface index(es) of dsl group present on the device."
            ::= { hwDslGroupEntry 1 }

        
        -- 1.3.6.1.4.1.2011.5.25.157.1.9.1.1.2
        hwDslGroupWorkMode OBJECT-TYPE
            SYNTAX INTEGER
                {
                atm(1),
                efm(2)
                }
            MAX-ACCESS read-write
            STATUS current
            DESCRIPTION
                "The dsl group of SHD4 card can work in efm or atm mode. Default is efm.
                "
            ::= { hwDslGroupEntry 2 }

        
        -- 1.3.6.1.4.1.2011.5.25.157.1.9.1.1.3
        hwDslGroupBisState OBJECT-TYPE
            SYNTAX INTEGER
                {
        disable(1),
        enable(2),
        notSupport(3)
                }
            MAX-ACCESS read-write
            STATUS current
            DESCRIPTION
                "Bis can be enabled or disabled in ATM mode of SHD4 card."
            ::= { hwDslGroupEntry 3 }

        
        -- 1.3.6.1.4.1.2011.5.25.157.1.9.1.1.4
        hwDslGroupEncapeMode OBJECT-TYPE
            SYNTAX INTEGER
                {
                eoaLlc(1),
        eoaVcmux(2),
        notSupport(3)
                }
            MAX-ACCESS read-write
            STATUS current
            DESCRIPTION
                "The dsl group of AVD8 card can work in ETHoA-LLC mode or ETHoA-VCMUX mode. Default is ETHoA-LLC."
            ::= { hwDslGroupEntry 4 }

        
        -- 1.3.6.1.4.1.2011.5.25.157.1.9.1.1.5
    hwDslGroupEnable OBJECT-TYPE
            SYNTAX INTEGER
                {
        disable(1),
        enable(2),
        notSupport(3)
                }
            MAX-ACCESS read-write
            STATUS current
            DESCRIPTION
                "Trigger the operation of binding dsl link(s) to the dsl group."
            ::= { hwDslGroupEntry 5 }

        
        --  1.3.6.1.4.1.2011.5.25.157.1.9.1.1.60
        hwDslGroupRowStatus OBJECT-TYPE
            SYNTAX RowStatus
            MAX-ACCESS read-write
            STATUS current
            DESCRIPTION
                "An object that allows entries in this table to
                be created, modified and deleted using the RowStatus
                convention.
                A SET operation to any other attribute in this row, when
                this object is set to 'active' (1), MUST be rejected with
                an SNMP error (e.g., inconsistentValue).
                In order to perform a SET operation to any other attribute
                in this table the manager MUST set this object to
                notInService (2).  After setting the object back to
                'active' the implementation MAY tear down all the sessions
                that belong to this partition and recreate them, depending
                on what session attributes have been modified."
        ::= { hwDslGroupEntry 60 }

        
        -- 1.3.6.1.4.1.2011.5.25.157.1.9.2
        hwDslGroupBoundVeTable OBJECT-TYPE
            SYNTAX SEQUENCE OF HwDslGroupBoundVeEntry
            MAX-ACCESS not-accessible
            STATUS current
            DESCRIPTION
                "Indicates the attributes of the dsl group bound virtual-ethernet."
            ::= { hwDslGroup 2 }

        
        -- 1.3.6.1.4.1.2011.5.25.157.1.9.2.1
        hwDslGroupBoundVeEntry OBJECT-TYPE
            SYNTAX HwDslGroupBoundVeEntry
            MAX-ACCESS not-accessible
            STATUS current
            DESCRIPTION
                "An entry in the dsl group bound vitrual-ethernet table."
        INDEX { hwDslGroupIfIndexOfBound, hwDslGroupPvcId }
            ::= { hwDslGroupBoundVeTable 1 }

        
        HwDslGroupBoundVeEntry ::=
            SEQUENCE { 
                hwDslGroupIfIndexOfBound
                    InterfaceIndex,
                hwVirtualEthernetIfIndex
                    InterfaceIndex,
                hwDslGroupVpi
                    Integer32,
                hwDslGroupVci
                    Integer32,
        hwDslGroupPvcId
            Integer32,
                hwBoundVeRowStatus
            RowStatus
             }

        -- 1.3.6.1.4.1.2011.5.25.157.1.9.2.1.1
        hwDslGroupIfIndexOfBound OBJECT-TYPE
            SYNTAX InterfaceIndex
            MAX-ACCESS read-only
            STATUS current
            DESCRIPTION
                "Interface index(es) of dsl group present on the device."
            ::= { hwDslGroupBoundVeEntry 1 }

        
        -- 1.3.6.1.4.1.2011.5.25.157.1.9.2.1.2
        hwVirtualEthernetIfIndex OBJECT-TYPE
            SYNTAX InterfaceIndex
            MAX-ACCESS read-only
            STATUS current
            DESCRIPTION
                "The first virtual ethernet interface which the dsl group is bound to."
            ::= { hwDslGroupBoundVeEntry 2 }

        
        -- 1.3.6.1.4.1.2011.5.25.157.1.9.2.1.3
        hwDslGroupVpi OBJECT-TYPE
            SYNTAX Integer32 (0..4095)
            MAX-ACCESS read-write
            STATUS current
            DESCRIPTION
                "VPI value of the 1st PVC pair."
            ::= { hwDslGroupBoundVeEntry 3 }

        
        -- 1.3.6.1.4.1.2011.5.25.157.1.9.2.1.4
        hwDslGroupVci OBJECT-TYPE
            SYNTAX Integer32 (0..65535)
            MAX-ACCESS read-write
            STATUS current
            DESCRIPTION
                "VCI value of the 1st PVC pair."
            ::= { hwDslGroupBoundVeEntry 4 }

        
--  1.3.6.1.4.1.2011.5.25.157.1.9.2.1.5
        -- 1.3.6.1.4.1.2011.5.25.157.1.9.2.1.5
        hwDslGroupPvcId OBJECT-TYPE
            SYNTAX Integer32 (1..2)
            MAX-ACCESS read-only
            STATUS current
            DESCRIPTION
                "Identifier for VPI/VCI Pair."
            ::= { hwDslGroupBoundVeEntry 5 }

        
--  1.3.6.1.4.1.2011.5.25.157.1.9.2.1.50
        -- 1.3.6.1.4.1.2011.5.25.157.1.9.2.1.50
        hwBoundVeRowStatus OBJECT-TYPE
            SYNTAX RowStatus
            MAX-ACCESS read-write
            STATUS obsolete
            DESCRIPTION
                "An object that allows entries in this table to
                be created, modified and deleted using the RowStatus
                convention.
                A SET operation to any other attribute in this row, when
                this object is set to 'active' (1), MUST be rejected with
                an SNMP error (e.g., inconsistentValue).
                In order to perform a SET operation to any other attribute
                in this table the manager MUST set this object to
                notInService (2).  After setting the object back to
                'active' the implementation MAY tear down all the sessions
                that belong to this partition and recreate them, depending
                on what session attributes have been modified."
            ::= { hwDslGroupBoundVeEntry 50 }

        
--  1.3.6.1.4.1.2011.5.25.157.1.9.3
        -- 1.3.6.1.4.1.2011.5.25.157.1.9.3
        hwDslGroupBindVeTable OBJECT-TYPE
            SYNTAX SEQUENCE OF HwDslGroupBindVeEntry
            MAX-ACCESS not-accessible
            STATUS current
            DESCRIPTION
                "Indicates the relation of the dsl group binding virtual-ethernet."
            ::= { hwDslGroup 3 }

        
--  1.3.6.1.4.1.2011.5.25.157.1.9.3.1
        -- 1.3.6.1.4.1.2011.5.25.157.1.9.3.1
        hwDslGroupBindVeEntry OBJECT-TYPE
            SYNTAX HwDslGroupBindVeEntry
            MAX-ACCESS not-accessible
            STATUS current
            DESCRIPTION
                "An entry in the dsl group binding vitrual-ethernet table."
            INDEX { hwDslGroupInterfaceIndex, hwVirtualEthernetInterfaceIndex }
            ::= { hwDslGroupBindVeTable 1 }

        
        HwDslGroupBindVeEntry ::=
            SEQUENCE { 
                hwDslGroupInterfaceIndex
                    InterfaceIndex,
                hwVirtualEthernetInterfaceIndex
                    InterfaceIndex,
                hwBindVeRowStatus
                    RowStatus
             }

--  1.3.6.1.4.1.2011.5.25.157.1.9.3.1.1
        -- 1.3.6.1.4.1.2011.5.25.157.1.9.3.1.1
        hwDslGroupInterfaceIndex OBJECT-TYPE
            SYNTAX InterfaceIndex
            MAX-ACCESS read-only
            STATUS current
            DESCRIPTION
                "Interface index(es) of the dsl group present on the device."
            ::= { hwDslGroupBindVeEntry 1 }

        
--  1.3.6.1.4.1.2011.5.25.157.1.9.3.1.2
        -- 1.3.6.1.4.1.2011.5.25.157.1.9.3.1.2
        hwVirtualEthernetInterfaceIndex OBJECT-TYPE
            SYNTAX InterfaceIndex
            MAX-ACCESS read-only
            STATUS current
            DESCRIPTION
                "The virtual ethernet interface index which the dsl group is bound to."
            ::= { hwDslGroupBindVeEntry 2 }

        
--  1.3.6.1.4.1.2011.5.25.157.1.9.3.1.50
        -- 1.3.6.1.4.1.2011.5.25.157.1.9.3.1.50
        hwBindVeRowStatus OBJECT-TYPE
            SYNTAX RowStatus
            MAX-ACCESS read-write
            STATUS current
            DESCRIPTION
                "An object that allows entries in this table to
                be created, modified and deleted using the RowStatus
                convention.
                A SET operation to any other attribute in this row, when
                this object is set to 'active' (1), MUST be rejected with
                an SNMP error (e.g., inconsistentValue).
                In order to perform a SET operation to any other attribute
                in this table the manager MUST set this object to
                notInService (2).  After setting the object back to
                'active' the implementation MAY tear down all the sessions
                that belong to this partition and recreate them, depending
                on what session attributes have been modified."
            ::= { hwDslGroupBindVeEntry 50 }

        
        -- 1.3.6.1.4.1.2011.5.25.157.1.10
        hwDslGroupIma OBJECT IDENTIFIER ::= { hwPortMIBObjects 10 }

        
        -- 1.3.6.1.4.1.2011.5.25.157.1.10.1
        hwDslGroupImaTable OBJECT-TYPE
            SYNTAX SEQUENCE OF HwDslGroupImaEntry
            MAX-ACCESS not-accessible
            STATUS current
            DESCRIPTION
                "Indicates the attributes of the dsl ima group."
            ::= { hwDslGroupIma 1 }

        
        -- 1.3.6.1.4.1.2011.5.25.157.1.10.1.1
        hwDslGroupImaEntry OBJECT-TYPE
            SYNTAX HwDslGroupImaEntry
            MAX-ACCESS not-accessible
            STATUS current
            DESCRIPTION
                "An entry of the dsl ima group table."
            INDEX { hwDslGroupImaIfIndex }
            ::= { hwDslGroupImaTable 1 }

        
        HwDslGroupImaEntry ::=
            SEQUENCE { 
                hwDslGroupImaIfIndex
                    InterfaceIndex,
                hwDslGroupImaVersion
                    INTEGER,
                hwDslGroupImaFrameLen
                    ImaFrameLength,
        hwDslGroupImaReset
                    INTEGER,
                hwDslGroupImaTxMinLinkNum
                    Integer32,
                hwDslGroupImaRxMinLinkNum
                    Integer32,
                hwDslGroupImaNeState
                    ImaGroupState,
                hwDslGroupImaFeState
                    ImaGroupState,
                hwDslGroupImaTxCellRate
                    Integer32,
                hwDslGroupImaRxCellRate
                    Integer32,
                hwDslGroupImaTxActLinkNum
                    Integer32,
                hwDslGroupImaRxActLinkNum
                Integer32,
        hwDslGroupImaIfName
                OCTET STRING
             }

        -- 1.3.6.1.4.1.2011.5.25.157.1.10.1.1.1
        hwDslGroupImaIfIndex OBJECT-TYPE
            SYNTAX InterfaceIndex
            MAX-ACCESS read-only
            STATUS current
            DESCRIPTION
                "Interface index(es) of dsl group present on the device."
            ::= { hwDslGroupImaEntry 1 }

        
        -- 1.3.6.1.4.1.2011.5.25.157.1.10.1.1.2
        hwDslGroupImaVersion OBJECT-TYPE
            SYNTAX INTEGER
                {
                v0(1),
                v1(2)
                }
            MAX-ACCESS read-write
            STATUS current
            DESCRIPTION
                "Version of the ima group of SHD4I card.
                v0: ima protocol version 1.0;
                v1: ima protocol version 1.1. "
            ::= { hwDslGroupImaEntry 2 }

        
        -- 1.3.6.1.4.1.2011.5.25.157.1.10.1.1.3
        hwDslGroupImaFrameLen OBJECT-TYPE
            SYNTAX ImaFrameLength
            MAX-ACCESS read-write
            STATUS current
            DESCRIPTION
                "Frame length of the ima group of SHD4I card. If ima protocol version is 1.0, the frame length is only 128."
            ::= { hwDslGroupImaEntry 3 }

        
        -- 1.3.6.1.4.1.2011.5.25.157.1.10.1.1.4
    hwDslGroupImaReset OBJECT-TYPE
            SYNTAX INTEGER
                {
        disable(1),
            enable(2)
                }
            MAX-ACCESS read-write
            STATUS current
            DESCRIPTION
        "ima group reset for SHD4I card."
            ::= { hwDslGroupImaEntry 4 }

        
        -- 1.3.6.1.4.1.2011.5.25.157.1.10.1.1.5
        hwDslGroupImaTxMinLinkNum OBJECT-TYPE
            SYNTAX Integer32 (1..4)
            MAX-ACCESS read-write
            STATUS current
            DESCRIPTION
                "Minimum active links number by TX direction."
            ::= { hwDslGroupImaEntry 5 }

        
        -- 1.3.6.1.4.1.2011.5.25.157.1.10.1.1.6
        hwDslGroupImaRxMinLinkNum OBJECT-TYPE
            SYNTAX Integer32 (1..4)
            MAX-ACCESS read-write
            STATUS current
            DESCRIPTION
                "Minimum active links number by RX direction.
                "
            ::= { hwDslGroupImaEntry 6 }

        
        -- 1.3.6.1.4.1.2011.5.25.157.1.10.1.1.7
        hwDslGroupImaNeState OBJECT-TYPE
            SYNTAX ImaGroupState
            MAX-ACCESS read-only
            STATUS current
            DESCRIPTION
                "The current state of the near-end ima group."
            ::= { hwDslGroupImaEntry 7 }

        
        -- 1.3.6.1.4.1.2011.5.25.157.1.10.1.1.8
        hwDslGroupImaFeState OBJECT-TYPE
            SYNTAX ImaGroupState
            MAX-ACCESS read-only
            STATUS current
            DESCRIPTION
                "The current state of the far-end ima group."
            ::= { hwDslGroupImaEntry 8 }

        
        -- 1.3.6.1.4.1.2011.5.25.157.1.10.1.1.9
        hwDslGroupImaTxCellRate OBJECT-TYPE
            SYNTAX Integer32
            MAX-ACCESS read-only
            STATUS current
            DESCRIPTION
                "The current cell rate of ima group by TX direction."
            ::= { hwDslGroupImaEntry 9 }

        
        -- 1.3.6.1.4.1.2011.5.25.157.1.10.1.1.10
        hwDslGroupImaRxCellRate OBJECT-TYPE
            SYNTAX Integer32
            MAX-ACCESS read-only
            STATUS current
            DESCRIPTION
                "The current cell rate of ima group by RX direction."
            ::= { hwDslGroupImaEntry 10 }

        
        -- 1.3.6.1.4.1.2011.5.25.157.1.10.1.1.11
        hwDslGroupImaTxActLinkNum OBJECT-TYPE
            SYNTAX Integer32 (0..4)
            MAX-ACCESS read-only
            STATUS current
            DESCRIPTION
                "Number of active links by TX direction."
            ::= { hwDslGroupImaEntry 11 }

        
        -- 1.3.6.1.4.1.2011.5.25.157.1.10.1.1.12
        hwDslGroupImaRxActLinkNum OBJECT-TYPE
            SYNTAX Integer32 (0..4)
            MAX-ACCESS read-only
            STATUS current
            DESCRIPTION
                "Number of active links by RX direction."
            ::= { hwDslGroupImaEntry 12 }

        

    -- 1.3.6.1.4.1.2011.5.25.157.1.10.1.1.13
    hwDslGroupImaIfName OBJECT-TYPE
            SYNTAX OCTET STRING
            MAX-ACCESS read-only
            STATUS current
            DESCRIPTION
                "The interface name of ima group."
            ::= { hwDslGroupImaEntry 13 }

        

    -- 1.3.6.1.4.1.2011.5.25.157.1.11
    hwDslLink OBJECT IDENTIFIER ::= { hwPortMIBObjects 11 }

        
        -- 1.3.6.1.4.1.2011.5.25.157.1.11.1
        hwDslLinkTable OBJECT-TYPE
            SYNTAX SEQUENCE OF HwDslLinkEntry
            MAX-ACCESS not-accessible
            STATUS current
            DESCRIPTION
                "Indicates the dsl link bound relation."
            ::= { hwDslLink 1 }

        
        -- 1.3.6.1.4.1.2011.5.25.157.1.11.1.1
        hwDslLinkEntry OBJECT-TYPE
            SYNTAX HwDslLinkEntry
            MAX-ACCESS not-accessible
            STATUS current
            DESCRIPTION
                "An entry of the dsl link bound relation."
            INDEX { hwBoundDslGroupIfIndex, hwDslLinkIfIndex }
            ::= { hwDslLinkTable 1 }

        
        HwDslLinkEntry ::=
            SEQUENCE { 
                hwBoundDslGroupIfIndex
                    InterfaceIndex,
                hwDslLinkIfIndex
                    InterfaceIndex,
        hwDslLinkIfName
                OCTET STRING,
        hwBoundDslGroupIfName
            OCTET STRING,
                hwDslLinkBoundRowStatus
                RowStatus
             }

        -- 1.3.6.1.4.1.2011.5.25.157.1.11.1.1.1
        hwBoundDslGroupIfIndex OBJECT-TYPE
            SYNTAX InterfaceIndex
            MAX-ACCESS read-only
            STATUS current
            DESCRIPTION
                "Interface index of dsl group which the dsl link bound to."
            ::= { hwDslLinkEntry 1 }

        
        -- 1.3.6.1.4.1.2011.5.25.157.1.11.1.1.2
        hwDslLinkIfIndex OBJECT-TYPE
            SYNTAX InterfaceIndex
            MAX-ACCESS read-write
            STATUS current
            DESCRIPTION
                "Interface index of the dsl link device."
            ::= { hwDslLinkEntry 2 }

        
        
    -- 1.3.6.1.4.1.2011.5.25.157.1.11.1.1.4
    hwDslLinkIfName OBJECT-TYPE
        SYNTAX OCTET STRING
        MAX-ACCESS read-only
        STATUS current
            DESCRIPTION
        "The interface name of the dsl link."
        ::= { hwDslLinkEntry 4 }

        
        
    -- 1.3.6.1.4.1.2011.5.25.157.1.11.1.1.5
    hwBoundDslGroupIfName OBJECT-TYPE
            SYNTAX OCTET STRING
        MAX-ACCESS read-only
        STATUS current
        DESCRIPTION
        "Interface index of dsl group which the dsl link bound to."
            ::= { hwDslLinkEntry 5 }

        

    -- 1.3.6.1.4.1.2011.5.25.157.1.11.1.1.50
    hwDslLinkBoundRowStatus OBJECT-TYPE
        SYNTAX RowStatus
        MAX-ACCESS read-write
        STATUS current
        DESCRIPTION
        "An object that allows entries in this table to
        be created, modified and deleted using the RowStatus
        convention.
        A SET operation to any other attribute in this row, when
        this object is set to 'active' (1), MUST be rejected with
        an SNMP error (e.g., inconsistentValue).
        In order to perform a SET operation to any other attribute
        in this table the manager MUST set this object to
        notInService (2).  After setting the object back to
        'active' the implementation MAY tear down all the sessions
        that belong to this partition and recreate them, depending
        on what session attributes have been modified."
    ::= { hwDslLinkEntry 50 }

        
        -- 1.3.6.1.4.1.2011.5.25.157.1.12
        hwPWAlarm OBJECT IDENTIFIER ::= { hwPortMIBObjects 12 }

        
        -- 1.3.6.1.4.1.2011.5.25.157.1.12.1
        hwPWAlarmTable OBJECT-TYPE
            SYNTAX SEQUENCE OF HwPWAlarmEntry
            MAX-ACCESS not-accessible
            STATUS current
            DESCRIPTION
                "Indicates the attributes of the PW alarm."
            ::= { hwPWAlarm 1 }

        
        -- 1.3.6.1.4.1.2011.5.25.157.1.12.1.1
        hwPWAlarmEntry OBJECT-TYPE
            SYNTAX HwPWAlarmEntry
            MAX-ACCESS not-accessible
            STATUS current
            DESCRIPTION
                "An entry of the PW alarm relation."
            INDEX { hwPWAlarmIfIndex }
            ::= { hwPWAlarmTable 1 }

        
        HwPWAlarmEntry ::=
            SEQUENCE { 
                hwPWAlarmIfIndex
                    InterfaceIndex,
                hwPWCesVcID
                    Integer32,
                hwPWCesVcType
                    Integer32,
                hwPeerIpAddr
                    IpAddress,
                hwAlarmStatus
                    Integer32,
                hwPWAlarmRMLEnableStatus
                    EnabledStatus,
                hwLosAlarmTriggerThreshold
                    Integer32,
                hwLosAlarmResumeThreshold
                    Integer32,
                hwPWPortName
                    OCTET STRING,
                hwLosPktExcTriggerThreshold
                    Integer32,
                hwLosPktExcResumeThreshold
                    Integer32,
                hwMisorderPktExcTriggerThreshold
                    Integer32,
                hwMisorderPktExcResumeThreshold
                    Integer32,
                hwStrayPktExcTriggerThreshold
                    Integer32,
                hwStrayPktExcResumeThreshold
                    Integer32,
                hwMalPktExcTriggerThreshold
                    Integer32,
                hwMalPktExcResumeThreshold
                    Integer32,
                hwJtrUdrExcTriggerThreshold
                    Integer32,
                hwJtrUdrExcResumeThreshold
                    Integer32,
                hwJtrOvrExcTriggerThreshold
                    Integer32,
                hwJtrOvrExcResumeThreshold
                    Integer32
             }

        -- 1.3.6.1.4.1.2011.5.25.157.1.12.1.1.1
        hwPWAlarmIfIndex OBJECT-TYPE
            SYNTAX InterfaceIndex
            MAX-ACCESS not-accessible
            STATUS current
            DESCRIPTION
                "Interface index of PW alarm group."
            ::= { hwPWAlarmEntry 1 }

        
        -- 1.3.6.1.4.1.2011.5.25.157.1.12.1.1.2
        hwPWCesVcID OBJECT-TYPE
            SYNTAX Integer32
            MAX-ACCESS read-only
            STATUS current
            DESCRIPTION
                "Vc ID of PW alarm group."
            ::= { hwPWAlarmEntry 2 }

        
        -- 1.3.6.1.4.1.2011.5.25.157.1.12.1.1.3
        hwPWCesVcType OBJECT-TYPE
            SYNTAX Integer32
            MAX-ACCESS read-only
            STATUS current
            DESCRIPTION
                "Vc Type of PW alarm group."
            ::= { hwPWAlarmEntry 3 }

        
        -- 1.3.6.1.4.1.2011.5.25.157.1.12.1.1.4
        hwPeerIpAddr OBJECT-TYPE
            SYNTAX IpAddress
            MAX-ACCESS read-only
            STATUS current
            DESCRIPTION
                "Peer IP Address of PW alarm group."
            ::= { hwPWAlarmEntry 4 }

        
        -- 1.3.6.1.4.1.2011.5.25.157.1.12.1.1.5
        hwAlarmStatus OBJECT-TYPE
            SYNTAX Integer32
            MAX-ACCESS read-only
            STATUS obsolete
            DESCRIPTION
                "Alarm status of PW alarm group."
            ::= { hwPWAlarmEntry 5 }

        
        -- 1.3.6.1.4.1.2011.5.25.157.1.12.1.1.6
        hwPWAlarmRMLEnableStatus OBJECT-TYPE
            SYNTAX EnabledStatus
            MAX-ACCESS read-write
            STATUS current
            DESCRIPTION
                "PW control word RML of PW alarm group."
            ::= { hwPWAlarmEntry 6 }

        
        -- 1.3.6.1.4.1.2011.5.25.157.1.12.1.1.7
        hwLosAlarmTriggerThreshold OBJECT-TYPE
            SYNTAX Integer32 (2..65535)
            MAX-ACCESS read-write
            STATUS current
            DESCRIPTION
                "Trigger Threshold of continuous loss packets of PW alarm group."
            DEFVAL { 100 }
            ::= { hwPWAlarmEntry 7 }

        
        -- 1.3.6.1.4.1.2011.5.25.157.1.12.1.1.8
        hwLosAlarmResumeThreshold OBJECT-TYPE
            SYNTAX Integer32 (32..65535)
            MAX-ACCESS read-write
            STATUS current
            DESCRIPTION
                "Resume Threshold of continuous loss packets of PW alarm group."
            DEFVAL { 5 }
            ::= { hwPWAlarmEntry 8 }

        
        -- 1.3.6.1.4.1.2011.5.25.157.1.12.1.1.9
        hwPWPortName OBJECT-TYPE
            SYNTAX OCTET STRING
            MAX-ACCESS read-only
            STATUS current
            DESCRIPTION
                "PW port name of PW alarm group."
            ::= { hwPWAlarmEntry 9 }

        
        -- 1.3.6.1.4.1.2011.5.25.157.1.12.1.1.10
        hwLosPktExcTriggerThreshold OBJECT-TYPE
            SYNTAX Integer32
            MAX-ACCESS read-write
            STATUS current
            DESCRIPTION
                "Trigger threshold of lost packets of PW alarm group."
            ::= { hwPWAlarmEntry 10 }

        
        -- 1.3.6.1.4.1.2011.5.25.157.1.12.1.1.11
        hwLosPktExcResumeThreshold OBJECT-TYPE
            SYNTAX Integer32
            MAX-ACCESS read-write
            STATUS current
            DESCRIPTION
                "Resume threshold of lost packets of PW alarm group."
            ::= { hwPWAlarmEntry 11 }

        
        -- 1.3.6.1.4.1.2011.5.25.157.1.12.1.1.12
        hwMisorderPktExcTriggerThreshold OBJECT-TYPE
            SYNTAX Integer32
            MAX-ACCESS read-write
            STATUS current
            DESCRIPTION
                "Trigger threshold of packets lost due to the out-of-order condition of PW alarm group."
            ::= { hwPWAlarmEntry 12 }

        
        -- 1.3.6.1.4.1.2011.5.25.157.1.12.1.1.13
        hwMisorderPktExcResumeThreshold OBJECT-TYPE
            SYNTAX Integer32
            MAX-ACCESS read-write
            STATUS current
            DESCRIPTION
                "Resume threshold of packets lost due to the out-of-order condition of PW alarm group."
            ::= { hwPWAlarmEntry 13 }

        
        -- 1.3.6.1.4.1.2011.5.25.157.1.12.1.1.14
        hwStrayPktExcTriggerThreshold OBJECT-TYPE
            SYNTAX Integer32
            MAX-ACCESS read-write
            STATUS current
            DESCRIPTION
                "Trigger threshold of misconnected packets of PW alarm group."
            ::= { hwPWAlarmEntry 14 }

        
        -- 1.3.6.1.4.1.2011.5.25.157.1.12.1.1.15
        hwStrayPktExcResumeThreshold OBJECT-TYPE
            SYNTAX Integer32
            MAX-ACCESS read-write
            STATUS current
            DESCRIPTION
                "Resume threshold of misconnected packets of PW alarm group."
            ::= { hwPWAlarmEntry 15 }

        
        -- 1.3.6.1.4.1.2011.5.25.157.1.12.1.1.16
        hwMalPktExcTriggerThreshold OBJECT-TYPE
            SYNTAX Integer32
            MAX-ACCESS read-write
            STATUS current
            DESCRIPTION
                "Trigger threshold of malformed packets of PW alarm group."
            ::= { hwPWAlarmEntry 16 }

        
        -- 1.3.6.1.4.1.2011.5.25.157.1.12.1.1.17
        hwMalPktExcResumeThreshold OBJECT-TYPE
            SYNTAX Integer32
            MAX-ACCESS read-write
            STATUS current
            DESCRIPTION
                "Resume threshold of malformed packets of PW alarm group."
            ::= { hwPWAlarmEntry 17 }

        
        -- 1.3.6.1.4.1.2011.5.25.157.1.12.1.1.18
        hwJtrUdrExcTriggerThreshold OBJECT-TYPE
            SYNTAX Integer32
            MAX-ACCESS read-write
            STATUS current
            DESCRIPTION
                "Trigger threshold of jitter buffer underflows of PW alarm group."
            ::= { hwPWAlarmEntry 18 }

        
        -- 1.3.6.1.4.1.2011.5.25.157.1.12.1.1.19
        hwJtrUdrExcResumeThreshold OBJECT-TYPE
            SYNTAX Integer32
            MAX-ACCESS read-write
            STATUS current
            DESCRIPTION
                "Resume threshold of jitter buffer underflows of PW alarm group."
            ::= { hwPWAlarmEntry 19 }

        
        -- 1.3.6.1.4.1.2011.5.25.157.1.12.1.1.20
        hwJtrOvrExcTriggerThreshold OBJECT-TYPE
            SYNTAX Integer32
            MAX-ACCESS read-write
            STATUS current
            DESCRIPTION
                "Trigger threshold of jitter buffer overflows of PW alarm group."
            ::= { hwPWAlarmEntry 20 }

        
        -- 1.3.6.1.4.1.2011.5.25.157.1.12.1.1.21
        hwJtrOvrExcResumeThreshold OBJECT-TYPE
            SYNTAX Integer32
            MAX-ACCESS read-write
            STATUS current
            DESCRIPTION
                "Resume threshold of jitter buffer overflows of PW alarm group."
            ::= { hwPWAlarmEntry 21 }

        
        -- 1.3.6.1.4.1.2011.5.25.157.1.12.2
        hwAtmPWAlarmTable OBJECT-TYPE
            SYNTAX SEQUENCE OF HwAtmPWAlarmEntry
            MAX-ACCESS not-accessible
            STATUS current
            DESCRIPTION
                "Indicates the attributes of the ATM PW alarm."
            ::= { hwPWAlarm 2 }

        
        -- 1.3.6.1.4.1.2011.5.25.157.1.12.2.1
        hwAtmPWAlarmEntry OBJECT-TYPE
            SYNTAX HwAtmPWAlarmEntry
            MAX-ACCESS not-accessible
            STATUS current
            DESCRIPTION
                "An entry of the ATM PW alarm relation."
            INDEX { hwAtmPWAlarmIfIndex }
            ::= { hwAtmPWAlarmTable 1 }

        
        HwAtmPWAlarmEntry ::=
            SEQUENCE { 
                hwAtmPWAlarmIfIndex
                    InterfaceIndex,
                hwAtmVcID
                    Integer32,
                hwAtmVcType
                    Integer32,
                hwAtmPeerIpAddr
                    IpAddress,
                hwAtmPWPortName
                    OCTET STRING,
                hwAtmLosPktExcTriggerThreshold
                    Integer32,
                hwAtmLosPktExcResumeThreshold
                    Integer32,
                hwAtmMisorderPktExcTriggerThreshold
                    Integer32,
                hwAtmMisorderPktExcResumeThreshold
                    Integer32,
                hwAtmUnknownCellExcTriggerThreshold
                    Integer32,
                hwAtmUnknownCellExcResumeThreshold
                    Integer32
             }

        -- 1.3.6.1.4.1.2011.5.25.157.1.12.2.1.1
        hwAtmPWAlarmIfIndex OBJECT-TYPE
            SYNTAX InterfaceIndex
            MAX-ACCESS read-only
            STATUS current
            DESCRIPTION
                "Interface index of ATM PW alarm group."
            ::= { hwAtmPWAlarmEntry 1 }

        
        -- 1.3.6.1.4.1.2011.5.25.157.1.12.2.1.2
        hwAtmVcID OBJECT-TYPE
            SYNTAX Integer32
            MAX-ACCESS read-only
            STATUS current
            DESCRIPTION
                "Vc ID of ATM PW alarm group."
            ::= { hwAtmPWAlarmEntry 2 }

        
        -- 1.3.6.1.4.1.2011.5.25.157.1.12.2.1.3
        hwAtmVcType OBJECT-TYPE
            SYNTAX Integer32
            MAX-ACCESS read-only
            STATUS current
            DESCRIPTION
                "Vc Type of ATM PW alarm group."
            ::= { hwAtmPWAlarmEntry 3 }

        
        -- 1.3.6.1.4.1.2011.5.25.157.1.12.2.1.4
        hwAtmPeerIpAddr OBJECT-TYPE
            SYNTAX IpAddress
            MAX-ACCESS read-only
            STATUS current
            DESCRIPTION
                "Peer IP Address of ATM PW alarm group."
            ::= { hwAtmPWAlarmEntry 4 }

        
        -- 1.3.6.1.4.1.2011.5.25.157.1.12.2.1.5
        hwAtmPWPortName OBJECT-TYPE
            SYNTAX OCTET STRING
            MAX-ACCESS read-only
            STATUS current
            DESCRIPTION
                "ATM PW port name of PW alarm group."
            ::= { hwAtmPWAlarmEntry 5 }

        
        -- 1.3.6.1.4.1.2011.5.25.157.1.12.2.1.6
        hwAtmLosPktExcTriggerThreshold OBJECT-TYPE
            SYNTAX Integer32 (1..1000)
            MAX-ACCESS read-write
            STATUS current
            DESCRIPTION
                "Trigger threshold of lost packets of ATM PW alarm group."
            DEFVAL { 100 }
            ::= { hwAtmPWAlarmEntry 6 }

        
        -- 1.3.6.1.4.1.2011.5.25.157.1.12.2.1.7
        hwAtmLosPktExcResumeThreshold OBJECT-TYPE
            SYNTAX Integer32 (1..1000)
            MAX-ACCESS read-write
            STATUS current
            DESCRIPTION
                "Resume threshold of lost packets of ATM PW alarm group."
            DEFVAL { 1 }
            ::= { hwAtmPWAlarmEntry 7 }

        
        -- 1.3.6.1.4.1.2011.5.25.157.1.12.2.1.8
        hwAtmMisorderPktExcTriggerThreshold OBJECT-TYPE
            SYNTAX Integer32 (1..1000)
            MAX-ACCESS read-write
            STATUS current
            DESCRIPTION
                "Trigger threshold of packets lost due to the out-of-order condition of ATM PW alarm group."
            DEFVAL { 100 }
            ::= { hwAtmPWAlarmEntry 8 }

        
        -- 1.3.6.1.4.1.2011.5.25.157.1.12.2.1.9
        hwAtmMisorderPktExcResumeThreshold OBJECT-TYPE
            SYNTAX Integer32 (1..1000)
            MAX-ACCESS read-write
            STATUS current
            DESCRIPTION
                "Resume threshold of packets lost due to the out-of-order condition of ATM PW alarm group."
            DEFVAL { 1 }
            ::= { hwAtmPWAlarmEntry 9 }

        
        -- 1.3.6.1.4.1.2011.5.25.157.1.12.2.1.10
        hwAtmUnknownCellExcTriggerThreshold OBJECT-TYPE
            SYNTAX Integer32 (1..1000)
            MAX-ACCESS read-write
            STATUS current
            DESCRIPTION
                "Trigger threshold of unknown cell of ATM PW alarm group."
            DEFVAL { 100 }
            ::= { hwAtmPWAlarmEntry 10 }

        
        -- 1.3.6.1.4.1.2011.5.25.157.1.12.2.1.11
        hwAtmUnknownCellExcResumeThreshold OBJECT-TYPE
            SYNTAX Integer32 (1..1000)
            MAX-ACCESS read-write
            STATUS current
            DESCRIPTION
                "Resume threshold of unknown cell of ATM PW alarm group."
            DEFVAL { 1 }
            ::= { hwAtmPWAlarmEntry 11 }

        
        -- 1.3.6.1.4.1.2011.5.25.157.1.13
        hwSNMPTrapEn OBJECT IDENTIFIER ::= { hwPortMIBObjects 13 }

        
        -- 1.3.6.1.4.1.2011.5.25.157.1.13.1
        hwSNMPTrapEnTable OBJECT-TYPE
            SYNTAX SEQUENCE OF HwSNMPTrapEnEntry
            MAX-ACCESS not-accessible
            STATUS current
            DESCRIPTION
                "Reserved nodes do not support this function temporarily."
            ::= { hwSNMPTrapEn 1 }

        
        -- 1.3.6.1.4.1.2011.5.25.157.1.13.1.1
        hwSNMPTrapEnEntry OBJECT-TYPE
            SYNTAX HwSNMPTrapEnEntry
            MAX-ACCESS not-accessible
            STATUS current
            DESCRIPTION
                "Reserved nodes do not support this function temporarily."
            INDEX { hwSNMPTrapEnIfIndex }
            ::= { hwSNMPTrapEnTable 1 }

        
        HwSNMPTrapEnEntry ::=
            SEQUENCE { 
                hwSNMPTrapEnIfIndex
                    InterfaceIndex,
                hwCesPWLopsEn
                    Integer32,
                hwCesPWRemoteLosPktEn
                    Integer32,
                hwCesPWOppositeRAIEn
                    Integer32,
                hwCesPWOppositeAcfaultEn
                    Integer32,
                hwCesPWLosPktEn
                    Integer32,
                hwCesPWMisorderPktEn
                    Integer32,
                hwCesPWStrayPktEn
                    Integer32,
                hwCesPWMalPktEn
                    Integer32,
                hwCesPWJtrUnrEn
                    Integer32,
                hwCesPWJtrOvrEn
                    Integer32,
                hwCesPWAllEn
                    Integer32,
                hwPhysicalPortLosAlarmEn
                    Integer32,
                hwPhysicalPortLofAlarmEn
                    Integer32,
                hwRsOofAlarmEn
                    Integer32,
                hwRsB1ExcAlarmEn
                    Integer32,
                hwRsB1SdAlarmEn
                    Integer32,
                hwRsJ0TimAlarmEn
                    Integer32,
                hwMsRdiAlarmEn
                    Integer32,
                hwMsB2ExcAlarmEn
                    Integer32,
                hwMsAuLopAlarmEn
                    Integer32,
                hwMsAisAlarmEn
                    Integer32,
                hwMsB2SdAlarmEn
                    Integer32,
                hwHpJ1TimAlarmEn
                    Integer32,
                hwHpUneqAlarmEn
                    Integer32,
                hwHpRdiAlarmEn
                    Integer32,
                hwHpB3ExcAlarmEn
                    Integer32,
                hwHpPlmAlarmEn
                    Integer32,
                hwHpB3SdAlarmEn
                    Integer32,
                hwHpAuAisAlarmEn
                    Integer32,
                hwLpTuLopAlarmEn
                    Integer32,
                hwHpTuLomAlarmEn
                    Integer32,
                hwLpTimAlarmEn
                    Integer32,
                hwLpUneqAlarmEn
                    Integer32,
                hwLpRdiAlarmEn
                    Integer32,
                hwLpBipExcAlarmEn
                    Integer32,
                hwLpBipSdAlarmEn
                    Integer32,
                hwLpPlmAlarmEn
                    Integer32,
                hwLpTuAisAlarmEn
                    Integer32,
                hwDs1EsExcAlarmEn
                    Integer32,
                hwDs1RmfaAlarmEn
                    Integer32,
                hwDs1LmfaAlarmEn
                    Integer32,
                hwDs1AisAlarmEn
                    Integer32,
                hwDs1RdiAlarmEn
                    Integer32,
                hwRsLocAlarmEn
                    Integer32,
                hwLpRfiAlarmEn
                    Integer32,
                hwLpV5VcaisAlarmEn
                    Integer32,
                hwVc12oofAlarmEn
                    Integer32,
                hwVc12AlmE1RaiAlarmEn
                    Integer32,
                hwVc12LfaAlarmEn
                    Integer32,
                hwVc12UpE1AisAlarmEn
                    Integer32,
                hwVc12DownE1AisAlarmEn
                    Integer32,
                hwDs1DownE1AisAlarmEn
                    Integer32,
                hwMsLpsUniBiMAlarmEn
                    Integer32,
                hwMsK1K2MAlarmEn
                    Integer32,
                hwMsK2MAlarmEn
                    Integer32,
                hwVc12LmfaAlarmEn
                    Integer32,
                hwSDHAllEn
                    Integer32,
                hwLaserShutAlarmEn
                    Integer32,
                hwLaserAutoShutAlarmEn
                    Integer32,
                hwLaserAllEn
                    Integer32,
                hwLoopbackAlarmEn
                    Integer32,
                hwChannelLoopbackAlarmEn
                    Integer32,
                hwLoopbackAllEn
                    Integer32,
                hwAtmOcdAlarmEn
                    Integer32,
                hwAtmLcdAlarmEn
                    Integer32,
                hwAtmUhcsAlarmEn
                    Integer32,
                hwAtmChcsAlarmEn
                    Integer32,
                hwAtmPWLosPktEn
                    Integer32,
                hwAtmPWMisorderPktEn
                    Integer32,
                hwAtmPWUnknownCellEn
                    Integer32,
                hwAtmAllEn
                    Integer32
             }

        -- 1.3.6.1.4.1.2011.5.25.157.1.13.1.1.1
        hwSNMPTrapEnIfIndex OBJECT-TYPE
            SYNTAX InterfaceIndex
            MAX-ACCESS not-accessible
            STATUS current
            DESCRIPTION
                "Reserved nodes do not support this function temporarily."
            ::= { hwSNMPTrapEnEntry 1 }

        
        -- 1.3.6.1.4.1.2011.5.25.157.1.13.1.1.2
        hwCesPWLopsEn OBJECT-TYPE
            SYNTAX Integer32
            MAX-ACCESS read-write
            STATUS current
            DESCRIPTION
                "Reserved nodes do not support this function temporarily."
            ::= { hwSNMPTrapEnEntry 2 }

        
        -- 1.3.6.1.4.1.2011.5.25.157.1.13.1.1.3
        hwCesPWRemoteLosPktEn OBJECT-TYPE
            SYNTAX Integer32
            MAX-ACCESS read-write
            STATUS current
            DESCRIPTION
                "Reserved nodes do not support this function temporarily."
            ::= { hwSNMPTrapEnEntry 3 }

        
        -- 1.3.6.1.4.1.2011.5.25.157.1.13.1.1.4
        hwCesPWOppositeRAIEn OBJECT-TYPE
            SYNTAX Integer32
            MAX-ACCESS read-write
            STATUS current
            DESCRIPTION
                "Reserved nodes do not support this function temporarily."
            ::= { hwSNMPTrapEnEntry 4 }

        
        -- 1.3.6.1.4.1.2011.5.25.157.1.13.1.1.5
        hwCesPWOppositeAcfaultEn OBJECT-TYPE
            SYNTAX Integer32
            MAX-ACCESS read-write
            STATUS current
            DESCRIPTION
                "Reserved nodes do not support this function temporarily."
            ::= { hwSNMPTrapEnEntry 5 }

        
        -- 1.3.6.1.4.1.2011.5.25.157.1.13.1.1.6
        hwCesPWLosPktEn OBJECT-TYPE
            SYNTAX Integer32
            MAX-ACCESS read-write
            STATUS current
            DESCRIPTION
                "Reserved nodes do not support this function temporarily."
            ::= { hwSNMPTrapEnEntry 6 }

        
        -- 1.3.6.1.4.1.2011.5.25.157.1.13.1.1.7
        hwCesPWMisorderPktEn OBJECT-TYPE
            SYNTAX Integer32
            MAX-ACCESS read-write
            STATUS current
            DESCRIPTION
                "Reserved nodes do not support this function temporarily."
            ::= { hwSNMPTrapEnEntry 7 }

        
        -- 1.3.6.1.4.1.2011.5.25.157.1.13.1.1.8
        hwCesPWStrayPktEn OBJECT-TYPE
            SYNTAX Integer32
            MAX-ACCESS read-write
            STATUS current
            DESCRIPTION
                "Reserved nodes do not support this function temporarily."
            ::= { hwSNMPTrapEnEntry 8 }

        
        -- 1.3.6.1.4.1.2011.5.25.157.1.13.1.1.9
        hwCesPWMalPktEn OBJECT-TYPE
            SYNTAX Integer32
            MAX-ACCESS read-write
            STATUS current
            DESCRIPTION
                "Reserved nodes do not support this function temporarily."
            ::= { hwSNMPTrapEnEntry 9 }

        
        -- 1.3.6.1.4.1.2011.5.25.157.1.13.1.1.10
        hwCesPWJtrUnrEn OBJECT-TYPE
            SYNTAX Integer32
            MAX-ACCESS read-write
            STATUS current
            DESCRIPTION
                "Reserved nodes do not support this function temporarily."
            ::= { hwSNMPTrapEnEntry 10 }

        
        -- 1.3.6.1.4.1.2011.5.25.157.1.13.1.1.11
        hwCesPWJtrOvrEn OBJECT-TYPE
            SYNTAX Integer32
            MAX-ACCESS read-write
            STATUS current
            DESCRIPTION
                "Reserved nodes do not support this function temporarily."
            ::= { hwSNMPTrapEnEntry 11 }

        
        -- 1.3.6.1.4.1.2011.5.25.157.1.13.1.1.12
        hwCesPWAllEn OBJECT-TYPE
            SYNTAX Integer32
            MAX-ACCESS read-write
            STATUS current
            DESCRIPTION
                "Reserved nodes do not support this function temporarily."
            ::= { hwSNMPTrapEnEntry 12 }

        
        -- 1.3.6.1.4.1.2011.5.25.157.1.13.1.1.13
        hwPhysicalPortLosAlarmEn OBJECT-TYPE
            SYNTAX Integer32
            MAX-ACCESS read-write
            STATUS current
            DESCRIPTION
                "Reserved nodes do not support this function temporarily."
            ::= { hwSNMPTrapEnEntry 13 }

        
        -- 1.3.6.1.4.1.2011.5.25.157.1.13.1.1.14
        hwPhysicalPortLofAlarmEn OBJECT-TYPE
            SYNTAX Integer32
            MAX-ACCESS read-write
            STATUS current
            DESCRIPTION
                "Reserved nodes do not support this function temporarily."
            ::= { hwSNMPTrapEnEntry 14 }

        
        -- 1.3.6.1.4.1.2011.5.25.157.1.13.1.1.15
        hwRsOofAlarmEn OBJECT-TYPE
            SYNTAX Integer32
            MAX-ACCESS read-write
            STATUS current
            DESCRIPTION
                "Reserved nodes do not support this function temporarily."
            ::= { hwSNMPTrapEnEntry 15 }

        
        -- 1.3.6.1.4.1.2011.5.25.157.1.13.1.1.16
        hwRsB1ExcAlarmEn OBJECT-TYPE
            SYNTAX Integer32
            MAX-ACCESS read-write
            STATUS current
            DESCRIPTION
                "Reserved nodes do not support this function temporarily."
            ::= { hwSNMPTrapEnEntry 16 }

        
        -- 1.3.6.1.4.1.2011.5.25.157.1.13.1.1.17
        hwRsB1SdAlarmEn OBJECT-TYPE
            SYNTAX Integer32
            MAX-ACCESS read-write
            STATUS current
            DESCRIPTION
                "Reserved nodes do not support this function temporarily."
            ::= { hwSNMPTrapEnEntry 17 }

        
        -- 1.3.6.1.4.1.2011.5.25.157.1.13.1.1.18
        hwRsJ0TimAlarmEn OBJECT-TYPE
            SYNTAX Integer32
            MAX-ACCESS read-write
            STATUS current
            DESCRIPTION
                "Reserved nodes do not support this function temporarily."
            ::= { hwSNMPTrapEnEntry 18 }

        
        -- 1.3.6.1.4.1.2011.5.25.157.1.13.1.1.19
        hwMsRdiAlarmEn OBJECT-TYPE
            SYNTAX Integer32
            MAX-ACCESS read-write
            STATUS current
            DESCRIPTION
                "Reserved nodes do not support this function temporarily."
            ::= { hwSNMPTrapEnEntry 19 }

        
        -- 1.3.6.1.4.1.2011.5.25.157.1.13.1.1.20
        hwMsB2ExcAlarmEn OBJECT-TYPE
            SYNTAX Integer32
            MAX-ACCESS read-write
            STATUS current
            DESCRIPTION
                "Reserved nodes do not support this function temporarily."
            ::= { hwSNMPTrapEnEntry 20 }

        
        -- 1.3.6.1.4.1.2011.5.25.157.1.13.1.1.21
        hwMsAuLopAlarmEn OBJECT-TYPE
            SYNTAX Integer32
            MAX-ACCESS read-write
            STATUS current
            DESCRIPTION
                "Reserved nodes do not support this function temporarily."
            ::= { hwSNMPTrapEnEntry 21 }

        
        -- 1.3.6.1.4.1.2011.5.25.157.1.13.1.1.22
        hwMsAisAlarmEn OBJECT-TYPE
            SYNTAX Integer32
            MAX-ACCESS read-write
            STATUS current
            DESCRIPTION
                "Reserved nodes do not support this function temporarily."
            ::= { hwSNMPTrapEnEntry 22 }

        
        -- 1.3.6.1.4.1.2011.5.25.157.1.13.1.1.23
        hwMsB2SdAlarmEn OBJECT-TYPE
            SYNTAX Integer32
            MAX-ACCESS read-write
            STATUS current
            DESCRIPTION
                "Reserved nodes do not support this function temporarily."
            ::= { hwSNMPTrapEnEntry 23 }

        
        -- 1.3.6.1.4.1.2011.5.25.157.1.13.1.1.24
        hwHpJ1TimAlarmEn OBJECT-TYPE
            SYNTAX Integer32
            MAX-ACCESS read-write
            STATUS current
            DESCRIPTION
                "Reserved nodes do not support this function temporarily."
            ::= { hwSNMPTrapEnEntry 24 }

        
        -- 1.3.6.1.4.1.2011.5.25.157.1.13.1.1.25
        hwHpUneqAlarmEn OBJECT-TYPE
            SYNTAX Integer32
            MAX-ACCESS read-write
            STATUS current
            DESCRIPTION
                "Reserved nodes do not support this function temporarily."
            ::= { hwSNMPTrapEnEntry 25 }

        
        -- 1.3.6.1.4.1.2011.5.25.157.1.13.1.1.26
        hwHpRdiAlarmEn OBJECT-TYPE
            SYNTAX Integer32
            MAX-ACCESS read-write
            STATUS current
            DESCRIPTION
                "Reserved nodes do not support this function temporarily."
            ::= { hwSNMPTrapEnEntry 26 }

        
        -- 1.3.6.1.4.1.2011.5.25.157.1.13.1.1.27
        hwHpB3ExcAlarmEn OBJECT-TYPE
            SYNTAX Integer32
            MAX-ACCESS read-write
            STATUS current
            DESCRIPTION
                "Reserved nodes do not support this function temporarily."
            ::= { hwSNMPTrapEnEntry 27 }

        
        -- 1.3.6.1.4.1.2011.5.25.157.1.13.1.1.28
        hwHpPlmAlarmEn OBJECT-TYPE
            SYNTAX Integer32
            MAX-ACCESS read-write
            STATUS current
            DESCRIPTION
                "Reserved nodes do not support this function temporarily."
            ::= { hwSNMPTrapEnEntry 28 }

        
        -- 1.3.6.1.4.1.2011.5.25.157.1.13.1.1.29
        hwHpB3SdAlarmEn OBJECT-TYPE
            SYNTAX Integer32
            MAX-ACCESS read-write
            STATUS current
            DESCRIPTION
                "Reserved nodes do not support this function temporarily."
            ::= { hwSNMPTrapEnEntry 29 }

        
        -- 1.3.6.1.4.1.2011.5.25.157.1.13.1.1.30
        hwHpAuAisAlarmEn OBJECT-TYPE
            SYNTAX Integer32
            MAX-ACCESS read-write
            STATUS current
            DESCRIPTION
                "Reserved nodes do not support this function temporarily."
            ::= { hwSNMPTrapEnEntry 30 }

        
        -- 1.3.6.1.4.1.2011.5.25.157.1.13.1.1.31
        hwLpTuLopAlarmEn OBJECT-TYPE
            SYNTAX Integer32
            MAX-ACCESS read-write
            STATUS current
            DESCRIPTION
                "Reserved nodes do not support this function temporarily."
            ::= { hwSNMPTrapEnEntry 31 }

        
        -- 1.3.6.1.4.1.2011.5.25.157.1.13.1.1.32
        hwHpTuLomAlarmEn OBJECT-TYPE
            SYNTAX Integer32
            MAX-ACCESS read-write
            STATUS current
            DESCRIPTION
                "Reserved nodes do not support this function temporarily."
            ::= { hwSNMPTrapEnEntry 32 }

        
        -- 1.3.6.1.4.1.2011.5.25.157.1.13.1.1.33
        hwLpTimAlarmEn OBJECT-TYPE
            SYNTAX Integer32
            MAX-ACCESS read-write
            STATUS current
            DESCRIPTION
                "Reserved nodes do not support this function temporarily."
            ::= { hwSNMPTrapEnEntry 33 }

        
        -- 1.3.6.1.4.1.2011.5.25.157.1.13.1.1.34
        hwLpUneqAlarmEn OBJECT-TYPE
            SYNTAX Integer32
            MAX-ACCESS read-write
            STATUS current
            DESCRIPTION
                "Reserved nodes do not support this function temporarily."
            ::= { hwSNMPTrapEnEntry 34 }

        
        -- 1.3.6.1.4.1.2011.5.25.157.1.13.1.1.35
        hwLpRdiAlarmEn OBJECT-TYPE
            SYNTAX Integer32
            MAX-ACCESS read-write
            STATUS current
            DESCRIPTION
                "Reserved nodes do not support this function temporarily."
            ::= { hwSNMPTrapEnEntry 35 }

        
        -- 1.3.6.1.4.1.2011.5.25.157.1.13.1.1.36
        hwLpBipExcAlarmEn OBJECT-TYPE
            SYNTAX Integer32
            MAX-ACCESS read-write
            STATUS current
            DESCRIPTION
                "Reserved nodes do not support this function temporarily."
            ::= { hwSNMPTrapEnEntry 36 }

        
        -- 1.3.6.1.4.1.2011.5.25.157.1.13.1.1.37
        hwLpBipSdAlarmEn OBJECT-TYPE
            SYNTAX Integer32
            MAX-ACCESS read-write
            STATUS current
            DESCRIPTION
                "Reserved nodes do not support this function temporarily."
            ::= { hwSNMPTrapEnEntry 37 }

        
        -- 1.3.6.1.4.1.2011.5.25.157.1.13.1.1.38
        hwLpPlmAlarmEn OBJECT-TYPE
            SYNTAX Integer32
            MAX-ACCESS read-write
            STATUS current
            DESCRIPTION
                "Reserved nodes do not support this function temporarily."
            ::= { hwSNMPTrapEnEntry 38 }

        
        -- 1.3.6.1.4.1.2011.5.25.157.1.13.1.1.39
        hwLpTuAisAlarmEn OBJECT-TYPE
            SYNTAX Integer32
            MAX-ACCESS read-write
            STATUS current
            DESCRIPTION
                "Reserved nodes do not support this function temporarily."
            ::= { hwSNMPTrapEnEntry 39 }

        
        -- 1.3.6.1.4.1.2011.5.25.157.1.13.1.1.40
        hwDs1EsExcAlarmEn OBJECT-TYPE
            SYNTAX Integer32
            MAX-ACCESS read-write
            STATUS current
            DESCRIPTION
                "Reserved nodes do not support this function temporarily."
            ::= { hwSNMPTrapEnEntry 40 }

        
        -- 1.3.6.1.4.1.2011.5.25.157.1.13.1.1.41
        hwDs1RmfaAlarmEn OBJECT-TYPE
            SYNTAX Integer32
            MAX-ACCESS read-write
            STATUS current
            DESCRIPTION
                "Reserved nodes do not support this function temporarily."
            ::= { hwSNMPTrapEnEntry 41 }

        
        -- 1.3.6.1.4.1.2011.5.25.157.1.13.1.1.42
        hwDs1LmfaAlarmEn OBJECT-TYPE
            SYNTAX Integer32
            MAX-ACCESS read-write
            STATUS current
            DESCRIPTION
                "Reserved nodes do not support this function temporarily."
            ::= { hwSNMPTrapEnEntry 42 }

        
        -- 1.3.6.1.4.1.2011.5.25.157.1.13.1.1.43
        hwDs1AisAlarmEn OBJECT-TYPE
            SYNTAX Integer32
            MAX-ACCESS read-write
            STATUS current
            DESCRIPTION
                "Reserved nodes do not support this function temporarily."
            ::= { hwSNMPTrapEnEntry 43 }

        
        -- 1.3.6.1.4.1.2011.5.25.157.1.13.1.1.44
        hwDs1RdiAlarmEn OBJECT-TYPE
            SYNTAX Integer32
            MAX-ACCESS read-write
            STATUS current
            DESCRIPTION
                "Reserved nodes do not support this function temporarily."
            ::= { hwSNMPTrapEnEntry 44 }

        
        -- 1.3.6.1.4.1.2011.5.25.157.1.13.1.1.45
        hwRsLocAlarmEn OBJECT-TYPE
            SYNTAX Integer32
            MAX-ACCESS read-write
            STATUS current
            DESCRIPTION
                "Reserved nodes do not support this function temporarily."
            ::= { hwSNMPTrapEnEntry 45 }

        
        -- 1.3.6.1.4.1.2011.5.25.157.1.13.1.1.46
        hwLpRfiAlarmEn OBJECT-TYPE
            SYNTAX Integer32
            MAX-ACCESS read-write
            STATUS current
            DESCRIPTION
                "Reserved nodes do not support this function temporarily."
            ::= { hwSNMPTrapEnEntry 46 }

        
        -- 1.3.6.1.4.1.2011.5.25.157.1.13.1.1.47
        hwLpV5VcaisAlarmEn OBJECT-TYPE
            SYNTAX Integer32
            MAX-ACCESS read-write
            STATUS current
            DESCRIPTION
                "Reserved nodes do not support this function temporarily."
            ::= { hwSNMPTrapEnEntry 47 }

        
        -- 1.3.6.1.4.1.2011.5.25.157.1.13.1.1.48
        hwVc12oofAlarmEn OBJECT-TYPE
            SYNTAX Integer32
            MAX-ACCESS read-write
            STATUS current
            DESCRIPTION
                "Reserved nodes do not support this function temporarily."
            ::= { hwSNMPTrapEnEntry 48 }

        
        -- 1.3.6.1.4.1.2011.5.25.157.1.13.1.1.49
        hwVc12AlmE1RaiAlarmEn OBJECT-TYPE
            SYNTAX Integer32
            MAX-ACCESS read-write
            STATUS current
            DESCRIPTION
                "Reserved nodes do not support this function temporarily."
            ::= { hwSNMPTrapEnEntry 49 }

        
        -- 1.3.6.1.4.1.2011.5.25.157.1.13.1.1.50
        hwVc12LfaAlarmEn OBJECT-TYPE
            SYNTAX Integer32
            MAX-ACCESS read-write
            STATUS current
            DESCRIPTION
                "Reserved nodes do not support this function temporarily."
            ::= { hwSNMPTrapEnEntry 50 }

        
        -- 1.3.6.1.4.1.2011.5.25.157.1.13.1.1.51
        hwVc12UpE1AisAlarmEn OBJECT-TYPE
            SYNTAX Integer32
            MAX-ACCESS read-write
            STATUS current
            DESCRIPTION
                "Reserved nodes do not support this function temporarily."
            ::= { hwSNMPTrapEnEntry 51 }

        
        -- 1.3.6.1.4.1.2011.5.25.157.1.13.1.1.52
        hwVc12DownE1AisAlarmEn OBJECT-TYPE
            SYNTAX Integer32
            MAX-ACCESS read-write
            STATUS current
            DESCRIPTION
                "Reserved nodes do not support this function temporarily."
            ::= { hwSNMPTrapEnEntry 52 }

        
        -- 1.3.6.1.4.1.2011.5.25.157.1.13.1.1.53
        hwDs1DownE1AisAlarmEn OBJECT-TYPE
            SYNTAX Integer32
            MAX-ACCESS read-write
            STATUS current
            DESCRIPTION
                "Reserved nodes do not support this function temporarily."
            ::= { hwSNMPTrapEnEntry 53 }

        
        -- 1.3.6.1.4.1.2011.5.25.157.1.13.1.1.54
        hwMsLpsUniBiMAlarmEn OBJECT-TYPE
            SYNTAX Integer32
            MAX-ACCESS read-write
            STATUS current
            DESCRIPTION
                "Reserved nodes do not support this function temporarily."
            ::= { hwSNMPTrapEnEntry 54 }

        
        -- 1.3.6.1.4.1.2011.5.25.157.1.13.1.1.55
        hwMsK1K2MAlarmEn OBJECT-TYPE
            SYNTAX Integer32
            MAX-ACCESS read-write
            STATUS current
            DESCRIPTION
                "Reserved nodes do not support this function temporarily."
            ::= { hwSNMPTrapEnEntry 55 }

        
        -- 1.3.6.1.4.1.2011.5.25.157.1.13.1.1.56
        hwMsK2MAlarmEn OBJECT-TYPE
            SYNTAX Integer32
            MAX-ACCESS read-write
            STATUS current
            DESCRIPTION
                "Reserved nodes do not support this function temporarily."
            ::= { hwSNMPTrapEnEntry 56 }

        
        -- 1.3.6.1.4.1.2011.5.25.157.1.13.1.1.57
        hwVc12LmfaAlarmEn OBJECT-TYPE
            SYNTAX Integer32
            MAX-ACCESS read-write
            STATUS current
            DESCRIPTION
                "Reserved nodes do not support this function temporarily."
            ::= { hwSNMPTrapEnEntry 57 }

        
        -- 1.3.6.1.4.1.2011.5.25.157.1.13.1.1.58
        hwSDHAllEn OBJECT-TYPE
            SYNTAX Integer32
            MAX-ACCESS read-write
            STATUS current
            DESCRIPTION
                "Reserved nodes do not support this function temporarily."
            ::= { hwSNMPTrapEnEntry 58 }

        
        -- 1.3.6.1.4.1.2011.5.25.157.1.13.1.1.59
        hwLaserShutAlarmEn OBJECT-TYPE
            SYNTAX Integer32
            MAX-ACCESS read-write
            STATUS current
            DESCRIPTION
                "Reserved nodes do not support this function temporarily."
            ::= { hwSNMPTrapEnEntry 59 }

        
        -- 1.3.6.1.4.1.2011.5.25.157.1.13.1.1.60
        hwLaserAutoShutAlarmEn OBJECT-TYPE
            SYNTAX Integer32
            MAX-ACCESS read-write
            STATUS current
            DESCRIPTION
                "Reserved nodes do not support this function temporarily."
            ::= { hwSNMPTrapEnEntry 60 }

        
        -- 1.3.6.1.4.1.2011.5.25.157.1.13.1.1.61
        hwLaserAllEn OBJECT-TYPE
            SYNTAX Integer32
            MAX-ACCESS read-write
            STATUS current
            DESCRIPTION
                "Reserved nodes do not support this function temporarily."
            ::= { hwSNMPTrapEnEntry 61 }

        
        -- 1.3.6.1.4.1.2011.5.25.157.1.13.1.1.62
        hwLoopbackAlarmEn OBJECT-TYPE
            SYNTAX Integer32
            MAX-ACCESS read-write
            STATUS current
            DESCRIPTION
                "Reserved nodes do not support this function temporarily."
            ::= { hwSNMPTrapEnEntry 62 }

        
        -- 1.3.6.1.4.1.2011.5.25.157.1.13.1.1.63
        hwChannelLoopbackAlarmEn OBJECT-TYPE
            SYNTAX Integer32
            MAX-ACCESS read-write
            STATUS current
            DESCRIPTION
                "Reserved nodes do not support this function temporarily."
            ::= { hwSNMPTrapEnEntry 63 }

        
        -- 1.3.6.1.4.1.2011.5.25.157.1.13.1.1.64
        hwLoopbackAllEn OBJECT-TYPE
            SYNTAX Integer32
            MAX-ACCESS read-write
            STATUS current
            DESCRIPTION
                "Reserved nodes do not support this function temporarily."
            ::= { hwSNMPTrapEnEntry 64 }

        
        -- 1.3.6.1.4.1.2011.5.25.157.1.13.1.1.65
        hwAtmOcdAlarmEn OBJECT-TYPE
            SYNTAX Integer32
            MAX-ACCESS read-write
            STATUS current
            DESCRIPTION
                "Reserved nodes do not support this function temporarily."
            ::= { hwSNMPTrapEnEntry 65 }

        
        -- 1.3.6.1.4.1.2011.5.25.157.1.13.1.1.66
        hwAtmLcdAlarmEn OBJECT-TYPE
            SYNTAX Integer32
            MAX-ACCESS read-write
            STATUS current
            DESCRIPTION
                "Reserved nodes do not support this function temporarily."
            ::= { hwSNMPTrapEnEntry 66 }

        
        -- 1.3.6.1.4.1.2011.5.25.157.1.13.1.1.67
        hwAtmUhcsAlarmEn OBJECT-TYPE
            SYNTAX Integer32
            MAX-ACCESS read-write
            STATUS current
            DESCRIPTION
                "Reserved nodes do not support this function temporarily."
            ::= { hwSNMPTrapEnEntry 67 }

        
        -- 1.3.6.1.4.1.2011.5.25.157.1.13.1.1.68
        hwAtmChcsAlarmEn OBJECT-TYPE
            SYNTAX Integer32
            MAX-ACCESS read-write
            STATUS current
            DESCRIPTION
                "Reserved nodes do not support this function temporarily."
            ::= { hwSNMPTrapEnEntry 68 }

        
        -- 1.3.6.1.4.1.2011.5.25.157.1.13.1.1.69
        hwAtmPWLosPktEn OBJECT-TYPE
            SYNTAX Integer32
            MAX-ACCESS read-write
            STATUS current
            DESCRIPTION
                "Reserved nodes do not support this function temporarily."
            ::= { hwSNMPTrapEnEntry 69 }

        
        -- 1.3.6.1.4.1.2011.5.25.157.1.13.1.1.70
        hwAtmPWMisorderPktEn OBJECT-TYPE
            SYNTAX Integer32
            MAX-ACCESS read-write
            STATUS current
            DESCRIPTION
                "Reserved nodes do not support this function temporarily."
            ::= { hwSNMPTrapEnEntry 70 }

        
        -- 1.3.6.1.4.1.2011.5.25.157.1.13.1.1.71
        hwAtmPWUnknownCellEn OBJECT-TYPE
            SYNTAX Integer32
            MAX-ACCESS read-write
            STATUS current
            DESCRIPTION
                "Reserved nodes do not support this function temporarily."
            ::= { hwSNMPTrapEnEntry 71 }

        
        -- 1.3.6.1.4.1.2011.5.25.157.1.13.1.1.72
        hwAtmAllEn OBJECT-TYPE
            SYNTAX Integer32
            MAX-ACCESS read-write
            STATUS current
            DESCRIPTION
                "Reserved nodes do not support this function temporarily."
            ::= { hwSNMPTrapEnEntry 72 }

        -- 1.3.6.1.4.1.2011.5.25.157.1.14
        hwPortAlarmThreshold OBJECT IDENTIFIER ::= { hwPortMIBObjects 14 }
        
        -- 1.3.6.1.4.1.2011.5.25.157.1.14.1
        hwPortAlarmThresholdTable OBJECT-TYPE
            SYNTAX      SEQUENCE OF HwPortAlarmThresholdEntry
            MAX-ACCESS  not-accessible
            STATUS      current
            DESCRIPTION
                "Indicates the port alarm threshold.
                This table lists the port alarm threshold of various interfaces."
            ::= { hwPortAlarmThreshold 1 }
        
        -- 1.3.6.1.4.1.2011.5.25.157.1.14.1.1
        hwPortAlarmThresholdEntry OBJECT-TYPE
            SYNTAX HwPortAlarmThresholdEntry
            MAX-ACCESS not-accessible
            STATUS current
            DESCRIPTION
                "Indicates the port alarm threshold.
                This table lists the threshold of various port alarm."
            INDEX  { hwPhysicalPortThrIfIndex }    
            ::= { hwPortAlarmThresholdTable 1 }           
        
        HwPortAlarmThresholdEntry  ::= 
            SEQUENCE{
                hwPhysicalPortThrIfIndex                          InterfaceIndex,   
                hwPhysicalPortThrName                             OCTET STRING,
                hwPhysicalPortCrcErrorStatistics                  Counter64,
                hwPhysicalPortCrcErrorHighThreshold               Unsigned32,               
                hwPhysicalPortCrcErrorLowThreshold                Unsigned32,
                hwPhysicalPortCrcErrorInterval                    Unsigned32,
                hwPhysicalPortSymbolErrorStatistics               Counter64,
                hwPhysicalPortSymbolErrorHighThreshold            Unsigned32,                  
                hwPhysicalPortSymbolErrorLowThreshold             Unsigned32,
                hwPhysicalPortSymbolErrorInterval                 Unsigned32,
                hwPhysicalPortInputErrorStatistics                Counter64,
                hwPhysicalPortInputErrorHighThreshold             Unsigned32,
                hwPhysicalPortInputErrorLowThreshold              Unsigned32,
                hwPhysicalPortInputErrorInterval                  Unsigned32,
                hwPhysicalPortOutputErrorStatistics               Counter64,
                hwPhysicalPortOutputErrorHighThreshold            Unsigned32,
                hwPhysicalPortOutputErrorLowThreshold             Unsigned32,
                hwPhysicalPortOutputErrorInterval                 Unsigned32,
                hwPhysicalPortSdhErrorStatistics                  Counter64,
                hwPhysicalPortSdhErrorHighThreshold               Unsigned32,               
                hwPhysicalPortSdhErrorLowThreshold                Unsigned32,
                hwPhysicalPortSdhErrorInterval                    Unsigned32,
                hwPhysicalPortBIP8SDErrorThreshold                Unsigned32,
                hwPhysicalPortCrcPerAlarmThresholdCoefficient     Unsigned32,
                hwPhysicalPortCrcPerAlarmThresholdPower           Unsigned32,
                hwPhysicalPortCrcPerResumeThresholdCoefficient    Unsigned32,
                hwPhysicalPortCrcPerResumeThresholdPower          Unsigned32,
                hwPhysicalPortCrcPerTriggerLsp                    Unsigned32,
                hwPhysicalPortCrcPerCurrentValueString            OCTET STRING,
                hwPhysicalPortCrcPerAlarmThresholdString          OCTET STRING,
                hwPhysicalPortCrcPerResumeThresholdString         OCTET STRING
                    }                  
        
        -- 1.3.6.1.4.1.2011.5.25.157.1.14.1.1.1
        hwPhysicalPortThrIfIndex OBJECT-TYPE
            SYNTAX InterfaceIndex
            MAX-ACCESS not-accessible
            STATUS current
            DESCRIPTION
                "Interface index(es) of physical port(s) present on the device."
            ::= { hwPortAlarmThresholdEntry 1 }
            
        -- 1.3.6.1.4.1.2011.5.25.157.1.14.1.1.2
        hwPhysicalPortThrName OBJECT-TYPE
            SYNTAX OCTET STRING(SIZE (0..64))
            MAX-ACCESS read-only
            STATUS current
            DESCRIPTION
                "Interface name of physical port(s) present on the device."
            ::= { hwPortAlarmThresholdEntry 2 }
        
        -- 1.3.6.1.4.1.2011.5.25.157.1.14.1.1.3
        hwPhysicalPortCrcErrorStatistics OBJECT-TYPE
            SYNTAX Counter64
            MAX-ACCESS read-only
            STATUS current
            DESCRIPTION
              "Crc error statistics value."
            ::= { hwPortAlarmThresholdEntry 3 }
            
        -- 1.3.6.1.4.1.2011.5.25.157.1.14.1.1.4
        hwPhysicalPortCrcErrorHighThreshold OBJECT-TYPE
            SYNTAX Unsigned32(1..4294967295)
            MAX-ACCESS read-write
            STATUS current
            DESCRIPTION
               "Crc error alarm high threshold,default value is 3."
            ::= { hwPortAlarmThresholdEntry 4 }
        
        -- 1.3.6.1.4.1.2011.5.25.157.1.14.1.1.5
        hwPhysicalPortCrcErrorLowThreshold OBJECT-TYPE
            SYNTAX Unsigned32(1..4294967295)
            MAX-ACCESS read-write
            STATUS current
            DESCRIPTION
               "Crc error alarm low threshold,default value is 3."
            ::= { hwPortAlarmThresholdEntry 5 }
        
        -- 1.3.6.1.4.1.2011.5.25.157.1.14.1.1.6
        hwPhysicalPortCrcErrorInterval OBJECT-TYPE
            SYNTAX Unsigned32(1..65535)
            MAX-ACCESS read-write
            STATUS current
            DESCRIPTION
               "Crc error alarm interval time(unit is second),default value is 10s."
            ::= { hwPortAlarmThresholdEntry 6 }
              
        -- 1.3.6.1.4.1.2011.5.25.157.1.14.1.1.7
        hwPhysicalPortSymbolErrorStatistics OBJECT-TYPE
            SYNTAX Counter64
            MAX-ACCESS read-only
            STATUS current
            DESCRIPTION
              "Symbol error statistics value."
            ::= { hwPortAlarmThresholdEntry 7 }
            
        -- 1.3.6.1.4.1.2011.5.25.157.1.14.1.1.8
        hwPhysicalPortSymbolErrorHighThreshold OBJECT-TYPE
            SYNTAX Unsigned32(1..4294967295)
            MAX-ACCESS read-write
            STATUS current
            DESCRIPTION
               "Symbol error alarm high threshold,default value is 3."
            ::= { hwPortAlarmThresholdEntry 8 }
        
        -- 1.3.6.1.4.1.2011.5.25.157.1.14.1.1.9
        hwPhysicalPortSymbolErrorLowThreshold OBJECT-TYPE
            SYNTAX Unsigned32(1..4294967295)
            MAX-ACCESS read-write
            STATUS current
            DESCRIPTION
               "Symbol error alarm low threshold,default value is 3."
            ::= { hwPortAlarmThresholdEntry 9 }
        
        -- 1.3.6.1.4.1.2011.5.25.157.1.14.1.1.10
        hwPhysicalPortSymbolErrorInterval OBJECT-TYPE
            SYNTAX Unsigned32(1..65535)
            MAX-ACCESS read-write
            STATUS current
            DESCRIPTION
               "Symbol error alarm interval time(unit is second),default value is 10s."
            ::= { hwPortAlarmThresholdEntry 10 }
        
        -- 1.3.6.1.4.1.2011.5.25.157.1.14.1.1.11
        hwPhysicalPortInputErrorStatistics OBJECT-TYPE
            SYNTAX Counter64
            MAX-ACCESS read-only
            STATUS current
            DESCRIPTION
              "Input error statistics value."
            ::= { hwPortAlarmThresholdEntry 11 }
            
        -- 1.3.6.1.4.1.2011.5.25.157.1.14.1.1.12
        hwPhysicalPortInputErrorHighThreshold OBJECT-TYPE
            SYNTAX Unsigned32(1..4294967295)
            MAX-ACCESS read-write
            STATUS current
            DESCRIPTION
               "Input error alarm high threshold,default value is 3."
            ::= { hwPortAlarmThresholdEntry 12 }
        
        -- 1.3.6.1.4.1.2011.5.25.157.1.14.1.1.13
        hwPhysicalPortInputErrorLowThreshold OBJECT-TYPE
            SYNTAX Unsigned32(1..4294967295)
            MAX-ACCESS read-write
            STATUS current
            DESCRIPTION
               "Input error alarm low threshold,default value is 3."
            ::= { hwPortAlarmThresholdEntry 13 }
            
        -- 1.3.6.1.4.1.2011.5.25.157.1.14.1.1.14
        hwPhysicalPortInputErrorInterval OBJECT-TYPE
            SYNTAX Unsigned32(1..65535)
            MAX-ACCESS read-write
            STATUS current
            DESCRIPTION
               "Input error alarm interval time(unit is second),default value is 10s."
            ::= { hwPortAlarmThresholdEntry 14 }
        
        -- 1.3.6.1.4.1.2011.5.25.157.1.14.1.1.15
        hwPhysicalPortOutputErrorStatistics OBJECT-TYPE
            SYNTAX Counter64
            MAX-ACCESS read-only
            STATUS current
            DESCRIPTION
              "Output error statistics value."
            ::= { hwPortAlarmThresholdEntry 15 }
            
        -- 1.3.6.1.4.1.2011.5.25.157.1.14.1.1.16
        hwPhysicalPortOutputErrorHighThreshold OBJECT-TYPE
            SYNTAX Unsigned32(1..4294967295)
            MAX-ACCESS read-write
            STATUS current
            DESCRIPTION
               "Output error alarm high threshold,default value is 3."
            ::= { hwPortAlarmThresholdEntry 16 }
        
        -- 1.3.6.1.4.1.2011.5.25.157.1.14.1.1.17
        hwPhysicalPortOutputErrorLowThreshold OBJECT-TYPE
            SYNTAX Unsigned32(1..4294967295)
            MAX-ACCESS read-write
            STATUS current
            DESCRIPTION
               "Output error alarm low threshold,default value is 3."
            ::= { hwPortAlarmThresholdEntry 17 }
        
        -- 1.3.6.1.4.1.2011.5.25.157.1.14.1.1.18
        hwPhysicalPortOutputErrorInterval OBJECT-TYPE
            SYNTAX Unsigned32(1..65535)
            MAX-ACCESS read-write
            STATUS current
            DESCRIPTION
               "Output error alarm interval time(unit is second),default value is 10s."
            ::= { hwPortAlarmThresholdEntry 18 }
        
        -- 1.3.6.1.4.1.2011.5.25.157.1.14.1.1.19
        hwPhysicalPortSdhErrorStatistics OBJECT-TYPE
            SYNTAX Counter64
            MAX-ACCESS read-only
            STATUS current
            DESCRIPTION
              "Sdh error statistics value."
            ::= { hwPortAlarmThresholdEntry 19 }
            
        -- 1.3.6.1.4.1.2011.5.25.157.1.14.1.1.20
        hwPhysicalPortSdhErrorHighThreshold OBJECT-TYPE
            SYNTAX Unsigned32(1..4294967295)
            MAX-ACCESS read-write
            STATUS current
            DESCRIPTION
               "Sdh error alarm high threshold,default value is 3."
            ::= { hwPortAlarmThresholdEntry 20 }
        
        -- 1.3.6.1.4.1.2011.5.25.157.1.14.1.1.21
        hwPhysicalPortSdhErrorLowThreshold OBJECT-TYPE
            SYNTAX Unsigned32(1..4294967295)
            MAX-ACCESS read-write
            STATUS current
            DESCRIPTION
               "Sdh error alarm low threshold,default value is 3."
            ::= { hwPortAlarmThresholdEntry 21 }
        
        -- 1.3.6.1.4.1.2011.5.25.157.1.14.1.1.22
        hwPhysicalPortSdhErrorInterval OBJECT-TYPE
            SYNTAX Unsigned32(1..65535)
            MAX-ACCESS read-write
            STATUS current
            DESCRIPTION
               "Sdh error alarm interval time(unit is second),default value is 10s."
            ::= { hwPortAlarmThresholdEntry 22 }
        
        -- 1.3.6.1.4.1.2011.5.25.157.1.14.1.1.23
        hwPhysicalPortBIP8SDErrorThreshold OBJECT-TYPE
            SYNTAX Unsigned32(6..9)
            MAX-ACCESS read-write
            STATUS current
            DESCRIPTION
               "BIP8-SD error alarm threshold,default value is 6."
            ::= { hwPortAlarmThresholdEntry 23 }
        
        -- 1.3.6.1.4.1.2011.5.25.157.1.14.1.1.24
        hwPhysicalPortCrcPerAlarmThresholdCoefficient OBJECT-TYPE
            SYNTAX Unsigned32
            MAX-ACCESS read-write
            STATUS current
            DESCRIPTION
                "The coefficient value of CRC-PER(Packet Error Ratio) alarm threshold. The range is 1 to 9."
            ::= { hwPortAlarmThresholdEntry 24 }

        
        -- 1.3.6.1.4.1.2011.5.25.157.1.14.1.1.25
        hwPhysicalPortCrcPerAlarmThresholdPower OBJECT-TYPE
            SYNTAX Unsigned32
            MAX-ACCESS read-write
            STATUS current
            DESCRIPTION
                "The power value of CRC-PER(Packet Error Ratio) alarm threshold. The range is 1 to 5."
            ::= { hwPortAlarmThresholdEntry 25 }

        
        -- 1.3.6.1.4.1.2011.5.25.157.1.14.1.1.26
        hwPhysicalPortCrcPerResumeThresholdCoefficient OBJECT-TYPE
            SYNTAX Unsigned32
            MAX-ACCESS read-write
            STATUS current
            DESCRIPTION
                "The coefficient value of CRC-PER(Packet Error Ratio) resume threshold. The range is 1 to 9."
            ::= { hwPortAlarmThresholdEntry 26 }

        
        -- 1.3.6.1.4.1.2011.5.25.157.1.14.1.1.27
        hwPhysicalPortCrcPerResumeThresholdPower OBJECT-TYPE
            SYNTAX Unsigned32
            MAX-ACCESS read-write
            STATUS current
            DESCRIPTION
                "The power value of CRC-PER(Packet Error Ratio) resume threshold. The range is 1 to 6."
            ::= { hwPortAlarmThresholdEntry 27 }

        
        -- 1.3.6.1.4.1.2011.5.25.157.1.14.1.1.28
        hwPhysicalPortCrcPerTriggerLsp OBJECT-TYPE
            SYNTAX Unsigned32
            MAX-ACCESS read-write
            STATUS current
            DESCRIPTION
                "Enalbe or disable the CRC-PER(Packet Error Ratio) result in lsp switchover. The range is 0 to 1."
            ::= { hwPortAlarmThresholdEntry 28 }

        
        -- 1.3.6.1.4.1.2011.5.25.157.1.14.1.1.29
        hwPhysicalPortCrcPerCurrentValueString OBJECT-TYPE
            SYNTAX OCTET STRING
            MAX-ACCESS accessible-for-notify
            STATUS current
            DESCRIPTION
                "The current value of CRC-PER(Packet Error Ratio)."
            ::= { hwPortAlarmThresholdEntry 29 }

        
        -- 1.3.6.1.4.1.2011.5.25.157.1.14.1.1.30
        hwPhysicalPortCrcPerAlarmThresholdString OBJECT-TYPE
            SYNTAX OCTET STRING
            MAX-ACCESS accessible-for-notify
            STATUS current
            DESCRIPTION
                "The alarm threshold of CRC-PER(Packet Error Ratio)."
            ::= { hwPortAlarmThresholdEntry 30 }

        
        -- 1.3.6.1.4.1.2011.5.25.157.1.14.1.1.31
        hwPhysicalPortCrcPerResumeThresholdString OBJECT-TYPE
            SYNTAX OCTET STRING
            MAX-ACCESS accessible-for-notify
            STATUS current
            DESCRIPTION
                "The resume threshold of CRC-PER(Packet Error Ratio)."
            ::= { hwPortAlarmThresholdEntry 31 }

        
        -- 1.3.6.1.4.1.2011.5.25.157.1.15
        hwPortAlarmDownEnable OBJECT IDENTIFIER ::= { hwPortMIBObjects 15 }
              
        -- 1.3.6.1.4.1.2011.5.25.157.1.15.1
        hwPortAlarmDownEnableTable OBJECT-TYPE
            SYNTAX      SEQUENCE OF HwPortAlarmDownEnableEntry
            MAX-ACCESS  not-accessible
            STATUS      current
            DESCRIPTION
                "Enalbe or disable the port alarm result in physics down.
                This table lists the enable status of various port alarm."
            ::= { hwPortAlarmDownEnable 1 }
        
        -- 1.3.6.1.4.1.2011.5.25.157.1.15.1.1
        hwPortAlarmDownEnableEntry OBJECT-TYPE
            SYNTAX HwPortAlarmDownEnableEntry
            MAX-ACCESS not-accessible
            STATUS current
            DESCRIPTION
                "Enalbe or disable the port alarm result in physics down.
                This table lists the enable status of various port alarm."
            INDEX  { hwPhysicalPortDownIfIndex }    
            ::= { hwPortAlarmDownEnableTable 1 }           
        
        HwPortAlarmDownEnableEntry  ::= 
            SEQUENCE{
                hwPhysicalPortDownIfIndex                         InterfaceIndex,   
                hwPhysicalPortDownName                            OCTET STRING,
                hwPhysicalPortCrcEnabledDown                      INTEGER,
                hwPhysicalPortSymbolEnabledDown                   INTEGER,               
                hwPhysicalPortInputEnabledDown                    INTEGER,
                hwPhysicalPortOutputEnabledDown                   INTEGER,
                hwPhysicalPortSdhEnabledDown                      INTEGER,
                hwPhysicalPortBip8SdEnabledDown                   INTEGER
                    }                  
        
        -- 1.3.6.1.4.1.2011.5.25.157.1.15.1.1.1
        hwPhysicalPortDownIfIndex OBJECT-TYPE
            SYNTAX InterfaceIndex
            MAX-ACCESS not-accessible
            STATUS current
            DESCRIPTION
                "Interface index(es) of physical port(s) present on the device."
            ::= { hwPortAlarmDownEnableEntry 1 }
        
        -- 1.3.6.1.4.1.2011.5.25.157.1.15.1.1.2
        hwPhysicalPortDownName OBJECT-TYPE
            SYNTAX OCTET STRING(SIZE (0..64))
            MAX-ACCESS read-only
            STATUS current
            DESCRIPTION
                "Interface name of physical port(s) present on the device."
            ::= { hwPortAlarmDownEnableEntry 2 }
        
        -- 1.3.6.1.4.1.2011.5.25.157.1.15.1.1.3
        hwPhysicalPortCrcEnabledDown OBJECT-TYPE
            SYNTAX INTEGER{ disable(0), enable(1) }
            MAX-ACCESS read-write
            STATUS current
            DESCRIPTION
              "Enalbe or disable the crc error alarm result in physics down, and the default value is disable."
            ::= { hwPortAlarmDownEnableEntry 3 }
        
        -- 1.3.6.1.4.1.2011.5.25.157.1.15.1.1.4
        hwPhysicalPortSymbolEnabledDown OBJECT-TYPE
            SYNTAX INTEGER{ disable(0), enable(1) }
            MAX-ACCESS read-write
            STATUS current
            DESCRIPTION
              "Enalbe or disable the symbol error alarm result in physics down, and the default value is disable."
            ::= { hwPortAlarmDownEnableEntry 4 }
        
        -- 1.3.6.1.4.1.2011.5.25.157.1.15.1.1.5
        hwPhysicalPortInputEnabledDown OBJECT-TYPE
            SYNTAX INTEGER{ disable(0), enable(1) }
            MAX-ACCESS read-write
            STATUS current
            DESCRIPTION
              "Enalbe or disable the input error alarm result in physics down, and the default value is disable."
            ::= { hwPortAlarmDownEnableEntry 5 }
        
        -- 1.3.6.1.4.1.2011.5.25.157.1.15.1.1.6
        hwPhysicalPortOutputEnabledDown OBJECT-TYPE
            SYNTAX INTEGER{ disable(0), enable(1) }
            MAX-ACCESS read-write
            STATUS current
            DESCRIPTION
              "Enalbe or disable the output error alarm result in physics down, and the default value is disable."
            ::= { hwPortAlarmDownEnableEntry 6 }
        
        -- 1.3.6.1.4.1.2011.5.25.157.1.15.1.1.7
        hwPhysicalPortSdhEnabledDown OBJECT-TYPE
            SYNTAX INTEGER{ disable(0), enable(1) }
            MAX-ACCESS read-write
            STATUS current
            DESCRIPTION
              "Enalbe or disable the sdh error alarm result in physics down, and the default value is disable."
            ::= { hwPortAlarmDownEnableEntry 7 }
        
        -- 1.3.6.1.4.1.2011.5.25.157.1.15.1.1.8
        hwPhysicalPortBip8SdEnabledDown OBJECT-TYPE
            SYNTAX INTEGER{ disable(0), enable(1) }
            MAX-ACCESS read-write
            STATUS current
            DESCRIPTION
              "Enalbe or disable the BIP8-SD error alarm result in physics down, and the default value is disable."
            ::= { hwPortAlarmDownEnableEntry 8 }

            
        -- 1.3.6.1.4.1.2011.5.25.157.2
        hwPortNotifications OBJECT IDENTIFIER ::= { hwPortMIB 2 }

        
        -- 1.3.6.1.4.1.2011.5.25.157.2.1
        hwPortACRMasterPWChange NOTIFICATION-TYPE
            OBJECTS { hwDs0ChannelBundleParentIfIndex, hwDs0ChannelBundleDs1ChannelId, hwDs0ChannelBundleId, hwDs0ChannelBundlePortName, hwDs0ChannelBundleIsMasterPW, 
                hwDs0ChannelBundleMasterPWStatus }
            STATUS current
            DESCRIPTION 
                "CES-ACR master PW change notification,indicates master pw change or master pw status change,this may happen when a
                pw is deleted or the pw status change."
            ::= { hwPortNotifications 1 }

        
        -- 1.3.6.1.4.1.2011.5.25.157.2.2
        hwDslImaGroupTraps OBJECT IDENTIFIER ::= { hwPortNotifications 2 }

        
        -- 1.3.6.1.4.1.2011.5.25.157.2.2.1
        hwDslImaGroupLEDown NOTIFICATION-TYPE
            OBJECTS { hwDslGroupImaIfIndex, hwDslGroupImaIfName }
            STATUS current
            DESCRIPTION 
                "The ima group local edge down notification."
            ::= { hwDslImaGroupTraps 1 }

        
        -- 1.3.6.1.4.1.2011.5.25.157.2.2.2
        hwDslImaGroupLEUp NOTIFICATION-TYPE
            OBJECTS { hwDslGroupImaIfIndex, hwDslGroupImaIfName }
            STATUS current
            DESCRIPTION 
                "The ima group local edge up notification."
            ::= { hwDslImaGroupTraps 2 }

        
        -- 1.3.6.1.4.1.2011.5.25.157.2.2.3
        hwDslImaGroupREDown NOTIFICATION-TYPE
        OBJECTS { hwDslGroupImaIfIndex, hwDslGroupImaIfName }
            STATUS current
            DESCRIPTION 
                "The ima group remote edge down notification."
            ::= { hwDslImaGroupTraps 3 }

        
        -- 1.3.6.1.4.1.2011.5.25.157.2.2.4
        hwDslImaGroupREUp NOTIFICATION-TYPE
            OBJECTS { hwDslGroupImaIfIndex, hwDslGroupImaIfName }
            STATUS current
            DESCRIPTION 
                "The ima group remote edge up notification."
            ::= { hwDslImaGroupTraps 4 }

        
        -- 1.3.6.1.4.1.2011.5.25.157.2.3
        hwDslImaLinkTraps OBJECT IDENTIFIER ::= { hwPortNotifications 3 }

        
        -- 1.3.6.1.4.1.2011.5.25.157.2.3.1
        hwDslImaLinkLif NOTIFICATION-TYPE
            OBJECTS { hwDslGroupImaIfIndex, hwDslLinkIfIndex, hwDslGroupImaIfName, hwDslLinkIfName }
            STATUS current
            DESCRIPTION 
                "The ima link lif notification."
            ::= { hwDslImaLinkTraps 1 }

        
        -- 1.3.6.1.4.1.2011.5.25.157.2.3.2
        hwDslImaLinkLifResume NOTIFICATION-TYPE
            OBJECTS { hwDslGroupImaIfIndex, hwDslLinkIfIndex, hwDslGroupImaIfName, hwDslLinkIfName }
            STATUS current
            DESCRIPTION 
                "The ima link lif resume notification."
            ::= { hwDslImaLinkTraps 2 }

        
        -- 1.3.6.1.4.1.2011.5.25.157.2.3.3
        hwDslImaLinkLods NOTIFICATION-TYPE
            OBJECTS { hwDslGroupImaIfIndex, hwDslLinkIfIndex, hwDslGroupImaIfName, hwDslLinkIfName }
            STATUS current
            DESCRIPTION 
                "The ima link lods notification."
            ::= { hwDslImaLinkTraps 3 }

        
        -- 1.3.6.1.4.1.2011.5.25.157.2.3.4
        hwDslImaLinkLodsResume NOTIFICATION-TYPE
        OBJECTS { hwDslGroupImaIfIndex, hwDslLinkIfIndex, hwDslGroupImaIfName, hwDslLinkIfName }
            STATUS current
            DESCRIPTION 
                "The ima link lods resume notification."
            ::= { hwDslImaLinkTraps 4 }

        
        -- 1.3.6.1.4.1.2011.5.25.157.2.3.5
        hwDslImaLinkRfi NOTIFICATION-TYPE
        OBJECTS { hwDslGroupImaIfIndex, hwDslLinkIfIndex, hwDslGroupImaIfName, hwDslLinkIfName }
            STATUS current
            DESCRIPTION 
                "The ima link rfi notification."
            ::= { hwDslImaLinkTraps 5 }

        
        -- 1.3.6.1.4.1.2011.5.25.157.2.3.6
        hwDslImaLinkRfiResume NOTIFICATION-TYPE
        OBJECTS { hwDslGroupImaIfIndex, hwDslLinkIfIndex, hwDslGroupImaIfName, hwDslLinkIfName }
            STATUS current
            DESCRIPTION 
                "The ima link rfi resume notification."
            ::= { hwDslImaLinkTraps 6 }

        
        -- 1.3.6.1.4.1.2011.5.25.157.2.3.7
        hwDslImaLinkReTxUnusable NOTIFICATION-TYPE
            OBJECTS { hwDslGroupImaIfIndex, hwDslLinkIfIndex, hwDslGroupImaIfName, hwDslLinkIfName }
            STATUS current
            DESCRIPTION 
                "The ima link remote tx unusable notification."
            ::= { hwDslImaLinkTraps 7 }

        
        -- 1.3.6.1.4.1.2011.5.25.157.2.3.8
        hwDslImaLinkReTxUsable NOTIFICATION-TYPE
            OBJECTS { hwDslGroupImaIfIndex, hwDslLinkIfIndex, hwDslGroupImaIfName, hwDslLinkIfName }
            STATUS current
            DESCRIPTION 
                "The ima link remote tx usable notification."
            ::= { hwDslImaLinkTraps 8 }

        
        -- 1.3.6.1.4.1.2011.5.25.157.2.3.9
        hwDslImaLinkReRxUnusable NOTIFICATION-TYPE
        OBJECTS { hwDslGroupImaIfIndex, hwDslLinkIfIndex, hwDslGroupImaIfName, hwDslLinkIfName }
            STATUS current
            DESCRIPTION 
                "The ima link remote rx unusable notification."
            ::= { hwDslImaLinkTraps 9 }

        
        -- 1.3.6.1.4.1.2011.5.25.157.2.3.10
        hwDslImaLinkReRxUsable NOTIFICATION-TYPE
        OBJECTS { hwDslGroupImaIfIndex, hwDslLinkIfIndex, hwDslGroupImaIfName, hwDslLinkIfName }
            STATUS current
            DESCRIPTION 
                "The ima link remote tx usable notification."
            ::= { hwDslImaLinkTraps 10 }

        
        -- 1.3.6.1.4.1.2011.5.25.157.2.4
        hwDslLinkTraps OBJECT IDENTIFIER ::= { hwPortNotifications 4 }

        
        -- 1.3.6.1.4.1.2011.5.25.157.2.4.1
        hwDslLinkFrameLost NOTIFICATION-TYPE
        OBJECTS { hwBoundDslGroupIfIndex, hwDslLinkIfIndex, hwBoundDslGroupIfName, hwDslLinkIfName }
            STATUS current
            DESCRIPTION 
                "The dsl link frame lost notification."
            ::= { hwDslLinkTraps 1 }

        
        -- 1.3.6.1.4.1.2011.5.25.157.2.4.2
        hwDslLinkFrameResume NOTIFICATION-TYPE
        OBJECTS { hwBoundDslGroupIfIndex, hwDslLinkIfIndex, hwBoundDslGroupIfName, hwDslLinkIfName }
            STATUS current
            DESCRIPTION 
                "The dsl link frame resume notification."
            ::= { hwDslLinkTraps 2 }

        
        -- 1.3.6.1.4.1.2011.5.25.157.2.4.3
        hwDslLinkSignalLost NOTIFICATION-TYPE
        OBJECTS { hwBoundDslGroupIfIndex, hwDslLinkIfIndex, hwBoundDslGroupIfName, hwDslLinkIfName }
            STATUS current
            DESCRIPTION 
                "The dsl link signal lost notification."
            ::= { hwDslLinkTraps 3 }

        
        -- 1.3.6.1.4.1.2011.5.25.157.2.4.4
        hwDslLinkSignalResume NOTIFICATION-TYPE
        OBJECTS { hwBoundDslGroupIfIndex, hwDslLinkIfIndex, hwBoundDslGroupIfName, hwDslLinkIfName }
            STATUS current
            DESCRIPTION 
                "The dsl link signal resume notification."
            ::= { hwDslLinkTraps 4 }

        
        -- 1.3.6.1.4.1.2011.5.25.157.2.5
        hwCesPwRemoteLosPktAlarm NOTIFICATION-TYPE
            OBJECTS { hwPWCesVcID, hwPWCesVcType, hwPeerIpAddr, hwPWPortName }
            STATUS current
            DESCRIPTION 
                "Indicates the alarm is detected."
            ::= { hwPortNotifications 5 }

        
        -- 1.3.6.1.4.1.2011.5.25.157.2.6
        hwCesPwRemoteLosPktAlarmResume NOTIFICATION-TYPE
            OBJECTS { hwPWCesVcID, hwPWCesVcType, hwPeerIpAddr, hwPWPortName }
            STATUS current
            DESCRIPTION 
                "Indicates the alarm is cleared."
            ::= { hwPortNotifications 6 }

        
        -- 1.3.6.1.4.1.2011.5.25.157.2.7
        hwCesPwOppositeRai NOTIFICATION-TYPE
            OBJECTS { hwPWCesVcID, hwPWCesVcType, hwPeerIpAddr, hwPWPortName }
            STATUS current
            DESCRIPTION 
                "Indicates the alarm is detected."
            ::= { hwPortNotifications 7 }

        
        -- 1.3.6.1.4.1.2011.5.25.157.2.8
        hwCesPwOppositeRaiResume NOTIFICATION-TYPE
            OBJECTS { hwPWCesVcID, hwPWCesVcType, hwPeerIpAddr, hwPWPortName }
            STATUS current
            DESCRIPTION 
                "Indicates the alarm is cleared."
            ::= { hwPortNotifications 8 }

        
        -- 1.3.6.1.4.1.2011.5.25.157.2.9
        hwLosAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 9 }

        
        -- 1.3.6.1.4.1.2011.5.25.157.2.10
        hwLosAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 10 }

        
        -- 1.3.6.1.4.1.2011.5.25.157.2.11
        hwLofAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 11 }

        
        -- 1.3.6.1.4.1.2011.5.25.157.2.12
        hwLofAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 12 }

        
        -- 1.3.6.1.4.1.2011.5.25.157.2.13
        hwOofAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 13 }

        
        -- 1.3.6.1.4.1.2011.5.25.157.2.14
        hwOofAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 14 }

        
        -- 1.3.6.1.4.1.2011.5.25.157.2.15
        hwB1TcaAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 15 }

        
        -- 1.3.6.1.4.1.2011.5.25.157.2.16
        hwB1TcaAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 16 }

        
        -- 1.3.6.1.4.1.2011.5.25.157.2.17
        hwB2TcaAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 17 }

        
        -- 1.3.6.1.4.1.2011.5.25.157.2.18
        hwB2TcaAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 18 }

        
        -- 1.3.6.1.4.1.2011.5.25.157.2.19
        hwJ0TimAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 19 }

        
        -- 1.3.6.1.4.1.2011.5.25.157.2.20
        hwJ0TimAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 20 }

        
        -- 1.3.6.1.4.1.2011.5.25.157.2.21
        hwLrdiAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 21 }

        
        -- 1.3.6.1.4.1.2011.5.25.157.2.22
        hwLrdiAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 22 }

        
        -- 1.3.6.1.4.1.2011.5.25.157.2.23
        hwSfbereAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 23 }

        
        -- 1.3.6.1.4.1.2011.5.25.157.2.24
        hwSfbereAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 24 }

        
        -- 1.3.6.1.4.1.2011.5.25.157.2.25
        hwAuLopAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 25 }

        
        -- 1.3.6.1.4.1.2011.5.25.157.2.26
        hwAuLopAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 26 }

        
        -- 1.3.6.1.4.1.2011.5.25.157.2.27
        hwLaisAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 27 }

        
        -- 1.3.6.1.4.1.2011.5.25.157.2.28
        hwLaisAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 28 }

        
        -- 1.3.6.1.4.1.2011.5.25.157.2.29
        hwSdbereAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 29 }

        
        -- 1.3.6.1.4.1.2011.5.25.157.2.30
        hwSdbereAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 30 }

        
        -- 1.3.6.1.4.1.2011.5.25.157.2.31
        hwPtimAlarm NOTIFICATION-TYPE
            OBJECTS { hwPhysicalPortInSlot, hwPhysicalPortInCard, hwPhysicalPortInPort, hwPortPhysicalHpIndex }
            STATUS current
            DESCRIPTION 
                "Indicates the alarm is detected."
            ::= { hwPortNotifications 31 }

        
        -- 1.3.6.1.4.1.2011.5.25.157.2.32
        hwPtimAlarmResume NOTIFICATION-TYPE
            OBJECTS { hwPhysicalPortInSlot, hwPhysicalPortInCard, hwPhysicalPortInPort, hwPortPhysicalHpIndex }
            STATUS current
            DESCRIPTION 
                "Indicates the alarm is cleared."
            ::= { hwPortNotifications 32 }

        
        -- 1.3.6.1.4.1.2011.5.25.157.2.33
        hwPuneqAlarm NOTIFICATION-TYPE
            OBJECTS { hwPhysicalPortInSlot, hwPhysicalPortInCard, hwPhysicalPortInPort, hwPortPhysicalHpIndex }
            STATUS current
            DESCRIPTION 
                "Indicates the alarm is detected."
            ::= { hwPortNotifications 33 }

        
        -- 1.3.6.1.4.1.2011.5.25.157.2.34
        hwPuneqAlarmResume NOTIFICATION-TYPE
            OBJECTS { hwPhysicalPortInSlot, hwPhysicalPortInCard, hwPhysicalPortInPort, hwPortPhysicalHpIndex }
            STATUS current
            DESCRIPTION 
                "Indicates the alarm is cleared."
            ::= { hwPortNotifications 34 }

        
        -- 1.3.6.1.4.1.2011.5.25.157.2.35
        hwPrdiAlarm NOTIFICATION-TYPE
            OBJECTS { hwPhysicalPortInSlot, hwPhysicalPortInCard, hwPhysicalPortInPort, hwPortPhysicalHpIndex }
            STATUS current
            DESCRIPTION 
                "Indicates the alarm is detected."
            ::= { hwPortNotifications 35 }

        
        -- 1.3.6.1.4.1.2011.5.25.157.2.36
        hwPrdiAlarmResume NOTIFICATION-TYPE
            OBJECTS { hwPhysicalPortInSlot, hwPhysicalPortInCard, hwPhysicalPortInPort, hwPortPhysicalHpIndex }
            STATUS current
            DESCRIPTION 
                "Indicates the alarm is cleared."
            ::= { hwPortNotifications 36 }

        
        -- 1.3.6.1.4.1.2011.5.25.157.2.37
        hwB3TcaAlarm NOTIFICATION-TYPE
            OBJECTS { hwPhysicalPortInSlot, hwPhysicalPortInCard, hwPhysicalPortInPort, hwPortPhysicalHpIndex }
            STATUS current
            DESCRIPTION 
                "Indicates the alarm is detected."
            ::= { hwPortNotifications 37 }

        
        -- 1.3.6.1.4.1.2011.5.25.157.2.38
        hwB3TcaAlarmResume NOTIFICATION-TYPE
            OBJECTS { hwPhysicalPortInSlot, hwPhysicalPortInCard, hwPhysicalPortInPort, hwPortPhysicalHpIndex }
            STATUS current
            DESCRIPTION 
                "Indicates the alarm is cleared."
            ::= { hwPortNotifications 38 }

        
        -- 1.3.6.1.4.1.2011.5.25.157.2.39
        hwPplmAlarm NOTIFICATION-TYPE
            OBJECTS { hwPhysicalPortInSlot, hwPhysicalPortInCard, hwPhysicalPortInPort, hwPortPhysicalHpIndex }
            STATUS current
            DESCRIPTION 
                "Indicates the alarm is detected."
            ::= { hwPortNotifications 39 }

        
        -- 1.3.6.1.4.1.2011.5.25.157.2.40
        hwPplmAlarmResume NOTIFICATION-TYPE
            OBJECTS { hwPhysicalPortInSlot, hwPhysicalPortInCard, hwPhysicalPortInPort, hwPortPhysicalHpIndex }
            STATUS current
            DESCRIPTION 
                "Indicates the alarm is cleared."
            ::= { hwPortNotifications 40 }

        
        -- 1.3.6.1.4.1.2011.5.25.157.2.41
        hwPaisAlarm NOTIFICATION-TYPE
            OBJECTS { hwPhysicalPortInSlot, hwPhysicalPortInCard, hwPhysicalPortInPort, hwPortPhysicalHpIndex }
            STATUS current
            DESCRIPTION 
                "Indicates the alarm is detected."
            ::= { hwPortNotifications 41 }

        
        -- 1.3.6.1.4.1.2011.5.25.157.2.42
        hwPaisAlarmResume NOTIFICATION-TYPE
            OBJECTS { hwPhysicalPortInSlot, hwPhysicalPortInCard, hwPhysicalPortInPort, hwPortPhysicalHpIndex }
            STATUS current
            DESCRIPTION 
                "Indicates the alarm is cleared."
            ::= { hwPortNotifications 42 }

        
        -- 1.3.6.1.4.1.2011.5.25.157.2.43
        hwAuAisAlarm NOTIFICATION-TYPE
            OBJECTS { hwPhysicalPortInSlot, hwPhysicalPortInCard, hwPhysicalPortInPort, hwPortPhysicalHpIndex }
            STATUS current
            DESCRIPTION 
                "Indicates the alarm is detected."
            ::= { hwPortNotifications 43 }

        
        -- 1.3.6.1.4.1.2011.5.25.157.2.44
        hwAuAisAlarmResume NOTIFICATION-TYPE
            OBJECTS { hwPhysicalPortInSlot, hwPhysicalPortInCard, hwPhysicalPortInPort, hwPortPhysicalHpIndex }
            STATUS current
            DESCRIPTION 
                "Indicates the alarm is cleared."
            ::= { hwPortNotifications 44 }

        
        -- 1.3.6.1.4.1.2011.5.25.157.2.45
        hwVlopAlarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 45 }

        
        -- 1.3.6.1.4.1.2011.5.25.157.2.46
        hwVlopAlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 46 }

        
        -- 1.3.6.1.4.1.2011.5.25.157.2.47
        hwLomAlarm NOTIFICATION-TYPE
            OBJECTS { hwPhysicalPortInSlot, hwPhysicalPortInCard, hwPhysicalPortInPort, hwPortPhysicalHpIndex }
            STATUS current
            DESCRIPTION 
                "Indicates the alarm is detected."
            ::= { hwPortNotifications 47 }

        
        -- 1.3.6.1.4.1.2011.5.25.157.2.48
        hwLomAlarmResume NOTIFICATION-TYPE
            OBJECTS { hwPhysicalPortInSlot, hwPhysicalPortInCard, hwPhysicalPortInPort, hwPortPhysicalHpIndex }
            STATUS current
            DESCRIPTION 
                "Indicates the alarm is cleared."
            ::= { hwPortNotifications 48 }

        
        -- 1.3.6.1.4.1.2011.5.25.157.2.49
        hwLpTimVc12Alarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 49 }

        
        -- 1.3.6.1.4.1.2011.5.25.157.2.50
        hwLpTimVc12AlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 50 }

        
        -- 1.3.6.1.4.1.2011.5.25.157.2.51
        hwLpUneqVc12Alarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 51 }

        
        -- 1.3.6.1.4.1.2011.5.25.157.2.52
        hwLpUneqVc12AlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 52 }

        
        -- 1.3.6.1.4.1.2011.5.25.157.2.53
        hwVrdiAlarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 53 }

        
        -- 1.3.6.1.4.1.2011.5.25.157.2.54
        hwVrdiAlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 54 }

        
        -- 1.3.6.1.4.1.2011.5.25.157.2.57
        hwBip2TcaAlarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 57 }

        
        -- 1.3.6.1.4.1.2011.5.25.157.2.58
        hwBip2TcaAlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 58 }

        
        -- 1.3.6.1.4.1.2011.5.25.157.2.59
        hwLpSlmVc12Alarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 59 }

        
        -- 1.3.6.1.4.1.2011.5.25.157.2.60
        hwLpSlmVc12AlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 60 }

        
        -- 1.3.6.1.4.1.2011.5.25.157.2.61
        hwTuAisVc12Alarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 61 }

        
        -- 1.3.6.1.4.1.2011.5.25.157.2.62
        hwTuAisVc12AlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 62 }

        
        -- 1.3.6.1.4.1.2011.5.25.157.2.63
        hwE1EsTcaAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 63 }

        
        -- 1.3.6.1.4.1.2011.5.25.157.2.64
        hwE1EsTcaAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 64 }

        
        -- 1.3.6.1.4.1.2011.5.25.157.2.67
        hwE1LmfaAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 67 }

        
        -- 1.3.6.1.4.1.2011.5.25.157.2.68
        hwE1LmfaAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 68 }

        
        -- 1.3.6.1.4.1.2011.5.25.157.2.69
        hwE1UpE1AisAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 69 }

        
        -- 1.3.6.1.4.1.2011.5.25.157.2.70
        hwE1UpE1AisAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 70 }

        
        -- 1.3.6.1.4.1.2011.5.25.157.2.71
        hwE1AlmE1RaiAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 71 }

        
        -- 1.3.6.1.4.1.2011.5.25.157.2.72
        hwE1AlmE1RaiAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 72 }

        
        -- 1.3.6.1.4.1.2011.5.25.157.2.73
        hwCesPwOppositeAcFault NOTIFICATION-TYPE
            OBJECTS { hwPWCesVcID, hwPWCesVcType, hwPeerIpAddr, hwPWPortName }
            STATUS current
            DESCRIPTION 
                "Indicates the alarm is detected."
            ::= { hwPortNotifications 73 }

        
        -- 1.3.6.1.4.1.2011.5.25.157.2.74
        hwCesPwOppositeAcFaultResume NOTIFICATION-TYPE
            OBJECTS { hwPWCesVcID, hwPWCesVcType, hwPeerIpAddr, hwPWPortName }
            STATUS current
            DESCRIPTION 
                "Indicates the alarm is cleared."
            ::= { hwPortNotifications 74 }

        
        -- 1.3.6.1.4.1.2011.5.25.157.2.75
        hwCesLosPktExcAlarm NOTIFICATION-TYPE
            OBJECTS { hwPWCesVcID, hwPWCesVcType, hwPeerIpAddr, hwPWPortName }
            STATUS current
            DESCRIPTION 
                "Indicates the alarm is detected."
            ::= { hwPortNotifications 75 }

        
        -- 1.3.6.1.4.1.2011.5.25.157.2.76
        hwCesLosPktExcAlarmResume NOTIFICATION-TYPE
            OBJECTS { hwPWCesVcID, hwPWCesVcType, hwPeerIpAddr, hwPWPortName }
            STATUS current
            DESCRIPTION 
                "Indicates the alarm is cleared."
            ::= { hwPortNotifications 76 }

        
        -- 1.3.6.1.4.1.2011.5.25.157.2.77
        hwCesMisorderPktExcAlarm NOTIFICATION-TYPE
            OBJECTS { hwPWCesVcID, hwPWCesVcType, hwPeerIpAddr, hwPWPortName }
            STATUS current
            DESCRIPTION 
                "Indicates the alarm is detected."
            ::= { hwPortNotifications 77 }

        
        -- 1.3.6.1.4.1.2011.5.25.157.2.78
        hwCesMisorderPktExcAlarmResume NOTIFICATION-TYPE
            OBJECTS { hwPWCesVcID, hwPWCesVcType, hwPeerIpAddr, hwPWPortName }
            STATUS current
            DESCRIPTION 
                "Indicates the alarm is cleared."
            ::= { hwPortNotifications 78 }

        
        -- 1.3.6.1.4.1.2011.5.25.157.2.79
        hwCesStrayPktExcAlarm NOTIFICATION-TYPE
            OBJECTS { hwPWCesVcID, hwPWCesVcType, hwPeerIpAddr, hwPWPortName }
            STATUS current
            DESCRIPTION 
                "Indicates the alarm is detected."
            ::= { hwPortNotifications 79 }

        
        -- 1.3.6.1.4.1.2011.5.25.157.2.80
        hwCesStrayPktExcAlarmResume NOTIFICATION-TYPE
            OBJECTS { hwPWCesVcID, hwPWCesVcType, hwPeerIpAddr, hwPWPortName }
            STATUS current
            DESCRIPTION 
                "Indicates the alarm is cleared."
            ::= { hwPortNotifications 80 }

        
        -- 1.3.6.1.4.1.2011.5.25.157.2.81
        hwCesMalPktExcAlarm NOTIFICATION-TYPE
            OBJECTS { hwPWCesVcID, hwPWCesVcType, hwPeerIpAddr, hwPWPortName }
            STATUS current
            DESCRIPTION 
                "Indicates the alarm is detected."
            ::= { hwPortNotifications 81 }

        
        -- 1.3.6.1.4.1.2011.5.25.157.2.82
        hwCesMalPktExcAlarmResume NOTIFICATION-TYPE
            OBJECTS { hwPWCesVcID, hwPWCesVcType, hwPeerIpAddr, hwPWPortName }
            STATUS current
            DESCRIPTION 
                "Indicates the alarm is cleared."
            ::= { hwPortNotifications 82 }

        
        -- 1.3.6.1.4.1.2011.5.25.157.2.83
        hwCesJtrUdrExcAlarm NOTIFICATION-TYPE
            OBJECTS { hwPWCesVcID, hwPWCesVcType, hwPeerIpAddr, hwPWPortName }
            STATUS current
            DESCRIPTION 
                "Indicates the alarm is detected."
            ::= { hwPortNotifications 83 }

        
        -- 1.3.6.1.4.1.2011.5.25.157.2.84
        hwCesJtrUdrExcAlarmResume NOTIFICATION-TYPE
            OBJECTS { hwPWCesVcID, hwPWCesVcType, hwPeerIpAddr, hwPWPortName }
            STATUS current
            DESCRIPTION 
                "Indicates the alarm is cleared."
            ::= { hwPortNotifications 84 }

        
        -- 1.3.6.1.4.1.2011.5.25.157.2.85
        hwCesJtrOvrExcAlarm NOTIFICATION-TYPE
            OBJECTS { hwPWCesVcID, hwPWCesVcType, hwPeerIpAddr, hwPWPortName }
            STATUS current
            DESCRIPTION 
                "Indicates the alarm is detected."
            ::= { hwPortNotifications 85 }

        
        -- 1.3.6.1.4.1.2011.5.25.157.2.86
        hwCesJtrOvrExcAlarmResume NOTIFICATION-TYPE
            OBJECTS { hwPWCesVcID, hwPWCesVcType, hwPeerIpAddr, hwPWPortName }
            STATUS current
            DESCRIPTION 
                "Indicates the alarm is cleared."
            ::= { hwPortNotifications 86 }

        
        -- 1.3.6.1.4.1.2011.5.25.157.2.87
        hwRroolAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 87 }

        
        -- 1.3.6.1.4.1.2011.5.25.157.2.88
        hwRroolAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 88 }

        
        -- 1.3.6.1.4.1.2011.5.25.157.2.89
        hwVrfiAlarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 89 }

        
        -- 1.3.6.1.4.1.2011.5.25.157.2.90
        hwVrfiAlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 90 }

        
        -- 1.3.6.1.4.1.2011.5.25.157.2.91
        hwV5VcaisAlarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 91 }

        
        -- 1.3.6.1.4.1.2011.5.25.157.2.92
        hwV5VcaisAlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 92 }

        
        -- 1.3.6.1.4.1.2011.5.25.157.2.95
        hwCposE1AlmE1RaiAlarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 95 }

        
        -- 1.3.6.1.4.1.2011.5.25.157.2.96
        hwCposE1AlmE1RaiAlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 96 }

        
        -- 1.3.6.1.4.1.2011.5.25.157.2.97
        hwCposE1LfaAlarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 97 }

        
        -- 1.3.6.1.4.1.2011.5.25.157.2.98
        hwCposE1LfaAlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 98 }

        
        -- 1.3.6.1.4.1.2011.5.25.157.2.99
        hwCposE1UpE1AisAlarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 99 }

        
        -- 1.3.6.1.4.1.2011.5.25.157.2.100
        hwCposE1UpE1AisAlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 100 }

        
        -- 1.3.6.1.4.1.2011.5.25.157.2.101
        hwCposE1DownE1AisAlarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 101 }

        
        -- 1.3.6.1.4.1.2011.5.25.157.2.102
        hwCposE1DownE1AisAlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 102 }

        
        -- 1.3.6.1.4.1.2011.5.25.157.2.103
        hwE1DownE1AisAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 103 }

        
        -- 1.3.6.1.4.1.2011.5.25.157.2.104
        hwE1DownE1AisAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 104 }

        
        -- 1.3.6.1.4.1.2011.5.25.157.2.111
        hwCposE1LmfaAlarm NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is detected."
            ::= { hwPortNotifications 111 }

        
        -- 1.3.6.1.4.1.2011.5.25.157.2.112
        hwCposE1LmfaAlarmResume NOTIFICATION-TYPE
            OBJECTS { hwPhysicalPortInSlot, hwPhysicalPortInCard, hwPhysicalPortInPort, hwPortPhysicalHpIndex, hwPortPhysicalLpIndex
                 }
            STATUS current
            DESCRIPTION 
                "Indicates the alarm is cleared."
            ::= { hwPortNotifications 112 }

        
        -- 1.3.6.1.4.1.2011.5.25.157.2.113
        hwLaserShutAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 113 }

        
        -- 1.3.6.1.4.1.2011.5.25.157.2.114
        hwLaserShutAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 114 }

        
        -- 1.3.6.1.4.1.2011.5.25.157.2.115
        hwLaserAutoShutAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 115 }

        
        -- 1.3.6.1.4.1.2011.5.25.157.2.116
        hwLaserAutoShutAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 116 }

        
        -- 1.3.6.1.4.1.2011.5.25.157.2.117
        hwLoopbackAlarm NOTIFICATION-TYPE
            OBJECTS { hwPhysicalPortIfIndex, hwPhysicalPortName, hwPhysicalLoopbackType }
            STATUS current
            DESCRIPTION 
                "Indicates the alarm is detected."
            ::= { hwPortNotifications 117 }

        
        -- 1.3.6.1.4.1.2011.5.25.157.2.118
        hwLoopbackAlarmResume NOTIFICATION-TYPE
            OBJECTS { hwPhysicalPortIfIndex, hwPhysicalPortName, hwPhysicalLoopbackType }
            STATUS current
            DESCRIPTION 
                "Indicates the alarm is cleared."
            ::= { hwPortNotifications 118 }

        
        -- 1.3.6.1.4.1.2011.5.25.157.2.119
        hwOcdAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 119 }

        
        -- 1.3.6.1.4.1.2011.5.25.157.2.120
        hwOcdAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 120 }

        
        -- 1.3.6.1.4.1.2011.5.25.157.2.121
        hwLcdAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 121 }

        
        -- 1.3.6.1.4.1.2011.5.25.157.2.122
        hwLcdAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 122 }

        
        -- 1.3.6.1.4.1.2011.5.25.157.2.123
        hwUhcsAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 123 }

        
        -- 1.3.6.1.4.1.2011.5.25.157.2.124
        hwUhcsAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 124 }

        
        -- 1.3.6.1.4.1.2011.5.25.157.2.125
        hwChcsAlarm NOTIFICATION-TYPE
            OBJECTS { hwPhysicalPortInSlot, hwPhysicalPortInCard, hwPhysicalPortInPort, hwPhysicalPortName }
            STATUS current
            DESCRIPTION 
                "Indicates the alarm is detected."
            ::= { hwPortNotifications 125 }

        
        -- 1.3.6.1.4.1.2011.5.25.157.2.126
        hwChcsAlarmResume NOTIFICATION-TYPE
            OBJECTS { hwPhysicalPortInSlot, hwPhysicalPortInCard, hwPhysicalPortInPort, hwPhysicalPortName }
            STATUS current
            DESCRIPTION 
                "Indicates the alarm is cleared."
            ::= { hwPortNotifications 126 }

        
        -- 1.3.6.1.4.1.2011.5.25.157.2.127
        hwChannelLoopbackAlarm NOTIFICATION-TYPE
            OBJECTS { hwSDHHpPerfCurrentIfIndex, hwSDHLpPerfCurrentIfIndex, hwPhysicalLoopbackType, hwPhysicalPortIfIndex, hwPhysicalPortName
                 }
            STATUS current
            DESCRIPTION 
                "Indicates the alarm is detected."
            ::= { hwPortNotifications 127 }

        
        -- 1.3.6.1.4.1.2011.5.25.157.2.128
        hwChannelLoopbackAlarmResume NOTIFICATION-TYPE
            OBJECTS { hwSDHHpPerfCurrentIfIndex, hwSDHLpPerfCurrentIfIndex, hwPhysicalLoopbackType, hwPhysicalPortIfIndex, hwPhysicalPortName
                 }
            STATUS current
            DESCRIPTION 
                "Indicates the alarm is cleared."
            ::= { hwPortNotifications 128 }

        
        -- 1.3.6.1.4.1.2011.5.25.157.2.129
        hwCesLopsAlarm NOTIFICATION-TYPE
            OBJECTS { hwPWCesVcID, hwPWCesVcType, hwPeerIpAddr, hwPWPortName }
            STATUS current
            DESCRIPTION 
                "Indicates the alarm is detected."
            ::= { hwPortNotifications 129 }

        
        -- 1.3.6.1.4.1.2011.5.25.157.2.130
        hwCesLopsAlarmResume NOTIFICATION-TYPE
            OBJECTS { hwPWCesVcID, hwPWCesVcType, hwPeerIpAddr, hwPWPortName }
            STATUS current
            DESCRIPTION 
                "Indicates the alarm is cleared."
            ::= { hwPortNotifications 130 }

        
        -- 1.3.6.1.4.1.2011.5.25.157.2.131
        hwAtmPwLosPktExcAlarm NOTIFICATION-TYPE
            OBJECTS { hwAtmVcID, hwAtmVcType, hwAtmPeerIpAddr, hwAtmPWPortName }
            STATUS current
            DESCRIPTION 
                "Indicates the alarm is detected."
            ::= { hwPortNotifications 131 }

        
        -- 1.3.6.1.4.1.2011.5.25.157.2.132
        hwAtmPwLosPktExcAlarmResume NOTIFICATION-TYPE
            OBJECTS { hwAtmVcID, hwAtmVcType, hwAtmPeerIpAddr, hwAtmPWPortName }
            STATUS current
            DESCRIPTION 
                "Indicates the alarm is cleared."
            ::= { hwPortNotifications 132 }

        
        -- 1.3.6.1.4.1.2011.5.25.157.2.133
        hwAtmPwMisorderPktExcAlarm NOTIFICATION-TYPE
            OBJECTS { hwAtmVcID, hwAtmVcType, hwAtmPeerIpAddr, hwAtmPWPortName }
            STATUS current
            DESCRIPTION 
                "Indicates the alarm is detected."
            ::= { hwPortNotifications 133 }

        
        -- 1.3.6.1.4.1.2011.5.25.157.2.134
        hwAtmPwMisorderPktExcAlarmResume NOTIFICATION-TYPE
            OBJECTS { hwAtmVcID, hwAtmVcType, hwAtmPeerIpAddr, hwAtmPWPortName }
            STATUS current
            DESCRIPTION 
                "Indicates the alarm is cleared."
            ::= { hwPortNotifications 134 }

        
        -- 1.3.6.1.4.1.2011.5.25.157.2.135
        hwAtmPwUnknownCellExcAlarm NOTIFICATION-TYPE
            OBJECTS { hwAtmVcID, hwAtmVcType, hwAtmPeerIpAddr, hwAtmPWPortName }
            STATUS current
            DESCRIPTION 
                "Indicates the alarm is detected."
            ::= { hwPortNotifications 135 }

        
        -- 1.3.6.1.4.1.2011.5.25.157.2.136
        hwAtmPwUnknownCellExcAlarmResume NOTIFICATION-TYPE
            OBJECTS { hwAtmVcID, hwAtmVcType, hwAtmPeerIpAddr, hwAtmPWPortName }
            STATUS current
            DESCRIPTION 
                "Indicates the alarm is cleared."
            ::= { hwPortNotifications 136 }

        
        -- 1.3.6.1.4.1.2011.5.25.157.2.153
        hwInputErrorAlarm NOTIFICATION-TYPE
            OBJECTS { hwPhysicalPortInSlot, hwPhysicalPortInCard, hwPhysicalPortInPort, hwPhysicalPortName}
            STATUS current
            DESCRIPTION 
                "The port input errors notification."
            ::= { hwPortNotifications 153 }

        
        -- 1.3.6.1.4.1.2011.5.25.157.2.154
        hwInputErrorAlarmResume NOTIFICATION-TYPE
            OBJECTS { hwPhysicalPortInSlot, hwPhysicalPortInCard, hwPhysicalPortInPort, hwPhysicalPortName}
            STATUS current
            DESCRIPTION 
                "The port input errors resume notification."
            ::= { hwPortNotifications 154 }

        
        -- 1.3.6.1.4.1.2011.5.25.157.2.155
        hwOutputErrorAlarm NOTIFICATION-TYPE
            OBJECTS { hwPhysicalPortInSlot, hwPhysicalPortInCard, hwPhysicalPortInPort, hwPhysicalPortName}
            STATUS current
            DESCRIPTION 
                "The port output errors notification."
            ::= { hwPortNotifications 155 }

        
        -- 1.3.6.1.4.1.2011.5.25.157.2.156
        hwOutputErrorAlarmResume NOTIFICATION-TYPE
            OBJECTS { hwPhysicalPortInSlot, hwPhysicalPortInCard, hwPhysicalPortInPort, hwPhysicalPortName}
            STATUS current
            DESCRIPTION 
                "The port output errors resume notification."
            ::= { hwPortNotifications 156 }

        -- 1.3.6.1.4.1.2011.5.25.157.2.157
        hwPortAlarmTraps OBJECT IDENTIFIER ::= { hwPortNotifications 157 }

        -- 1.3.6.1.4.1.2011.5.25.157.2.157.1
        hwPhysicalPortCrcError NOTIFICATION-TYPE
            OBJECTS { hwPhysicalPortThrIfIndex, hwPhysicalPortThrName, hwPhysicalPortCrcErrorStatistics, hwPhysicalPortCrcErrorHighThreshold, hwPhysicalPortCrcErrorLowThreshold, hwPhysicalPortCrcErrorInterval }
            STATUS current
            DESCRIPTION 
                "Port Crc error alarm notification."
            ::= { hwPortAlarmTraps 1 }

        -- 1.3.6.1.4.1.2011.5.25.157.2.157.2
        hwPhysicalPortCrcErrorResume NOTIFICATION-TYPE
            OBJECTS { hwPhysicalPortThrIfIndex, hwPhysicalPortThrName, hwPhysicalPortCrcErrorStatistics, hwPhysicalPortCrcErrorHighThreshold, hwPhysicalPortCrcErrorLowThreshold, hwPhysicalPortCrcErrorInterval }
            STATUS current
            DESCRIPTION 
                "Port Crc error alarm resume."
            ::= { hwPortAlarmTraps 2 }

        -- 1.3.6.1.4.1.2011.5.25.157.2.157.3
        hwPhysicalPortSymbolError NOTIFICATION-TYPE
            OBJECTS { hwPhysicalPortThrIfIndex, hwPhysicalPortThrName, hwPhysicalPortSymbolErrorStatistics, hwPhysicalPortSymbolErrorHighThreshold, hwPhysicalPortSymbolErrorLowThreshold, hwPhysicalPortSymbolErrorInterval }
            STATUS current
            DESCRIPTION 
                "Port Symbol error alarm notification."
            ::= { hwPortAlarmTraps 3 }

        -- 1.3.6.1.4.1.2011.5.25.157.2.157.4
        hwPhysicalPortSymbolErrorResume NOTIFICATION-TYPE
            OBJECTS { hwPhysicalPortThrIfIndex, hwPhysicalPortThrName, hwPhysicalPortSymbolErrorStatistics, hwPhysicalPortSymbolErrorHighThreshold, hwPhysicalPortSymbolErrorLowThreshold, hwPhysicalPortSymbolErrorInterval }
            STATUS current
            DESCRIPTION 
                "Port Symbol error alarm resume."
            ::= { hwPortAlarmTraps 4 }
            
        -- 1.3.6.1.4.1.2011.5.25.157.2.157.5
        hwPhysicalPortSdhError NOTIFICATION-TYPE
            OBJECTS { hwPhysicalPortThrIfIndex, hwPhysicalPortThrName, hwPhysicalPortSdhErrorStatistics, hwPhysicalPortSdhErrorHighThreshold, hwPhysicalPortSdhErrorLowThreshold, hwPhysicalPortSdhErrorInterval }
            STATUS current
            DESCRIPTION 
                "Port Sdh error alarm notification."
            ::= { hwPortAlarmTraps 5 }

        -- 1.3.6.1.4.1.2011.5.25.157.2.157.6
        hwPhysicalPortSdhErrorResume NOTIFICATION-TYPE
            OBJECTS { hwPhysicalPortThrIfIndex, hwPhysicalPortThrName, hwPhysicalPortSdhErrorStatistics, hwPhysicalPortSdhErrorHighThreshold, hwPhysicalPortSdhErrorLowThreshold, hwPhysicalPortSdhErrorInterval }
            STATUS current
            DESCRIPTION 
                "Port Sdh error alarm resume."
            ::= { hwPortAlarmTraps 6 }
            
        -- 1.3.6.1.4.1.2011.5.25.157.2.157.7
        hwPhysicalPortBip8SdError NOTIFICATION-TYPE
            OBJECTS { hwPhysicalPortThrIfIndex, hwPhysicalPortThrName, hwPhysicalPortBIP8SDErrorThreshold }
            STATUS current
            DESCRIPTION 
                "Port BIP8 Signal Degrade alarm notification."
            ::= { hwPortAlarmTraps 7 }

        -- 1.3.6.1.4.1.2011.5.25.157.2.157.8
        hwPhysicalPortBip8SdErrorResume NOTIFICATION-TYPE
            OBJECTS { hwPhysicalPortThrIfIndex, hwPhysicalPortThrName, hwPhysicalPortBIP8SDErrorThreshold }
            STATUS current
            DESCRIPTION 
                "Port BIP8 Signal Degrade alarm resume."
            ::= { hwPortAlarmTraps 8 }

        
        -- 1.3.6.1.4.1.2011.5.25.157.2.157.9
        hwPhysicalPortCrcPacketErrorRatio NOTIFICATION-TYPE
            OBJECTS { hwPhysicalPortThrIfIndex, hwPhysicalPortThrName, hwPhysicalPortCrcPerCurrentValueString, hwPhysicalPortCrcPerAlarmThresholdString, hwPhysicalPortCrcPerResumeThresholdString
                 }
            STATUS current
            DESCRIPTION 
                "Port CRC-PER(Packet Error Ratio) alarm notification."
            ::= { hwPortAlarmTraps 9 }

        
        -- 1.3.6.1.4.1.2011.5.25.157.2.157.10
        hwPhysicalPortCrcPacketErrorRatioResume NOTIFICATION-TYPE
            OBJECTS { hwPhysicalPortThrIfIndex, hwPhysicalPortThrName, hwPhysicalPortCrcPerCurrentValueString, hwPhysicalPortCrcPerAlarmThresholdString, hwPhysicalPortCrcPerResumeThresholdString
                 }
            STATUS current
            DESCRIPTION 
                "Port CRC-PER(Packet Error Ratio) alarm resume notification."
            ::= { hwPortAlarmTraps 10 }

        
    -- 1.3.6.1.4.1.2011.5.25.157.2.160
    hwLoopBackAutoClearNotice NOTIFICATION-TYPE
        OBJECTS { hwPhysicalPortIfIndex, hwPhysicalPortName }
        STATUS current
        DESCRIPTION 
            "set port undo loopback while set loopback autoclear enable when time out."
        ::= { hwPortNotifications 160 }

        
    -- 1.3.6.1.4.1.2011.5.25.157.2.161
    hwChannelLoopBackAutoClearNotice NOTIFICATION-TYPE
        OBJECTS { hwPhysicalPortIfIndex, hwPhysicalPortName, hwDs1ChannelId }
        STATUS current
        DESCRIPTION 
            "set channel undo loopback while set loopback autoclear enable when time out."
        ::= { hwPortNotifications 161 }
    
    
    -- 1.3.6.1.4.1.2011.5.25.157.2.162   
    hwHpJ1TiuAlarm NOTIFICATION-TYPE
        OBJECTS { hwPhysicalPortInSlot, hwPhysicalPortInCard, hwPhysicalPortInPort, hwPortPhysicalHpIndex, hwPhysicalPortName }
        STATUS current
        DESCRIPTION 
            "Trace Identifier Unstable in the Higher order Path."
        ::= { hwPortNotifications 162 }

        
     -- 1.3.6.1.4.1.2011.5.25.157.2.163
     hwHpJ1TiuAlarmResume NOTIFICATION-TYPE
        OBJECTS { hwPhysicalPortInSlot, hwPhysicalPortInCard, hwPhysicalPortInPort, hwPortPhysicalHpIndex, hwPhysicalPortName }
        STATUS current
        DESCRIPTION 
             "Trace Identifier Unstable in the Higher order Path alarm resume."
        ::= { hwPortNotifications 163 }         


     -- 1.3.6.1.4.1.2011.5.25.157.2.164
     hwPortAlarmInverseAutoRecover NOTIFICATION-TYPE
        OBJECTS { hwPhysicalPortName }
        STATUS current
        DESCRIPTION 
             "Port alarm inverse auto recover."
        ::= { hwPortNotifications 164 }

                        
        -- 1.3.6.1.4.1.2011.5.25.157.11
        hwPortConformance OBJECT IDENTIFIER ::= { hwPortMIB 11 }

        
        -- 1.3.6.1.4.1.2011.5.25.157.11.1
        hwPortCompliances OBJECT IDENTIFIER ::= { hwPortConformance 1 }

        
        -- 1.3.6.1.4.1.2011.5.25.157.11.1.1
        hwPortCompliance MODULE-COMPLIANCE
            STATUS current
            DESCRIPTION 
                "The compliance statement for systems supporting
                the HUAWEI-PORT-MIB."
            MODULE -- this module
                MANDATORY-GROUPS { hwEthernetObjectGroup, hwPosObjectGroup, hwCposObjectGroup, hwBundleSerialObjectGroup, hwDs0ChannelBundleObjectGroup, 
                    hwDs1ObjectGroup, hwDs3ObjectGroup, hwPortNotificationsGroup, hwPortAlarmThresholdObjectGroup, hwPortAlarmDownEnableObjectGroup }
            ::= { hwPortCompliances 1 }

        
        -- 1.3.6.1.4.1.2011.5.25.157.11.2
        hwPortGroups OBJECT IDENTIFIER ::= { hwPortConformance 2 }

        
        -- 1.3.6.1.4.1.2011.5.25.157.11.2.1
        hwEthernetObjectGroup OBJECT-GROUP
            OBJECTS { hwEthernetLoopback, hwEthernetPortType, hwEthernetSpeedSet, hwEthernetDuplex, hwEthernetNegotiation, 
                hwEthernetPortTypeOperate, hwEthernetClock, hwEthernetFlagJ0Mode, hwEthernetFlagJ0Value, hwEthernetFlagJ0Trace, 
                hwEthernetFlagJ1Mode, hwEthernetFlagJ1Value, hwEthernetFlagJ1Trace, hwEthernetFlagC2Value, hwEthernetUpHoldTime, 
                hwEthernetDownHoldTime, hwEthernetSubinterfaceStatisticEnable, hwEthernetJumboframeMaxLength, hwEthernetComboType, hwEthernetPortMode
                 }
            STATUS current
            DESCRIPTION 
                "The Port attribute group."
            ::= { hwPortGroups 1 }

        
        -- 1.3.6.1.4.1.2011.5.25.157.11.2.2
        hwPosObjectGroup OBJECT-GROUP
            OBJECTS { hwPosLinkProtocol, hwPosFrameFormat, hwPosLoopback, hwPosScramble, hwPosClock, 
                hwPosCrcVerifyCode, hwPosFlagJ0Mode, hwPosFlagJ0Value, hwPosFlagJ0Trace, hwPosFlagJ1Mode, 
                hwPosFlagJ1Value, hwPosFlagJ1Trace, hwPosFlagC2Value }
            STATUS current
            DESCRIPTION 
                "The Port attribute group."
            ::= { hwPortGroups 2 }

        
        -- 1.3.6.1.4.1.2011.5.25.157.11.2.3
        hwCposObjectGroup OBJECT-GROUP
            OBJECTS { hwCposFrameFormat, hwCposMultiplex, hwCposClock, hwCposIfType, hwCposLoopback, 
                hwCposFlagJ0Mode, hwCposFlagJ0Value, hwCposFlagJ0Trace, hwCposFlagJ1Mode, hwCposFlagJ1Value, 
                hwCposFlagJ1Trace, hwCposFlagC2Value, hwCposB1SdAlarmThreshold, hwCposB1ExcAlarmThreshold, hwCposB2SdAlarmThreshold, 
                hwCposB2ExcAlarmThreshold, hwCposB3SdAlarmThreshold, hwCposB3ExcAlarmThreshold, hwCposLpBipSdAlarmThreshold, hwCposLpBipExcAlarmThreshold, 
                hwCposHighPathNumber, hwCposLowPathNumber, hwCposMappingMode }
            STATUS current
            DESCRIPTION 
                "The Port attribute group."
            ::= { hwPortGroups 3 }

        
        -- 1.3.6.1.4.1.2011.5.25.157.11.2.4
        hwDs0ChannelBundleObjectGroup OBJECT-GROUP
            OBJECTS { hwDs0ChannelBundleIfIndex, hwDs0ChannelBundleTimeSlots, hwDs0ChannelBundleSpeed, hwDs0ChannelBundleIsMasterPW, hwDs0ChannelBundleMasterPWStatus, 
                hwDs0ChannelBundlePortName, hwDs0ChannelBundleRowStatus }
            STATUS current
            DESCRIPTION 
                "The Port attribute group."
            ::= { hwPortGroups 4 }

        
        -- 1.3.6.1.4.1.2011.5.25.157.11.2.5
        hwDs1ObjectGroup OBJECT-GROUP
            OBJECTS { hwDs1ChannelType, hwDs1IfType, hwDs1Channelized, hwDs1CodeType, hwDs1Clock, 
                hwDs1FrameFormat, hwDs1Cable, hwDs1Loopback, hwDs1ClockRecoveryDomain, hwDs1PWClockDomain, 
                hwDs1WorkMode, hwDs1RowStatus }
            STATUS current
            DESCRIPTION 
                "The Port attribute group."
            ::= { hwPortGroups 5 }

        
        -- 1.3.6.1.4.1.2011.5.25.157.11.2.6
        hwDs3ObjectGroup OBJECT-GROUP
            OBJECTS { hwDs3ChannelType, hwDs3IfType, hwDs3Channelized, hwDs3Clock, hwDs3FrameFormat, 
                hwDs3Scramble, hwDs3Cable, hwDs3NationalBit, hwDs3Loopback, hwDs3CreateSerial, 
                hwDs3RowStatus }
            STATUS current
            DESCRIPTION 
                "The Port attribute group."
            ::= { hwPortGroups 6 }

        
        -- 1.3.6.1.4.1.2011.5.25.157.11.2.7
        hwBundleSerialObjectGroup OBJECT-GROUP
            OBJECTS { hwBundleSerialLinkProtocol, hwBundleSerialTimerHold, hwBundleSerialCrcVerifyCode, hwBundleSerialLoopback }
            STATUS current
            DESCRIPTION 
                "The Port attribute group."
            ::= { hwPortGroups 7 }

        
        -- 1.3.6.1.4.1.2011.5.25.157.11.2.8
        hwPortNotificationsGroup NOTIFICATION-GROUP
			NOTIFICATIONS { hwPortACRMasterPWChange, hwHpJ1TiuAlarm, hwHpJ1TiuAlarmResume, 
				hwCesPwOppositeAcFault, hwCesPwOppositeAcFaultResume, hwCesLosPktExcAlarm, hwCesLosPktExcAlarmResume, hwCesMisorderPktExcAlarm, 
				hwCesMisorderPktExcAlarmResume, hwCesStrayPktExcAlarm, hwCesStrayPktExcAlarmResume, hwCesMalPktExcAlarm, hwCesMalPktExcAlarmResume, 
				hwCesJtrUdrExcAlarm, hwCesJtrUdrExcAlarmResume, hwCesJtrOvrExcAlarm, hwCesJtrOvrExcAlarmResume, hwLaserShutAlarm, 
				hwLaserShutAlarmResume, hwLaserAutoShutAlarm, hwLaserAutoShutAlarmResume, hwLoopbackAlarm, hwLoopbackAlarmResume, 
				hwChannelLoopbackAlarm, hwChannelLoopbackAlarmResume, hwCesPwOppositeRaiResume, hwCesPwOppositeRai, hwB1TcaAlarm, 
				hwB1TcaAlarmResume, hwB2TcaAlarm, hwB2TcaAlarmResume, hwOofAlarm, hwOofAlarmResume, 
				hwLosAlarm, hwLosAlarmResume, hwJ0TimAlarm, hwJ0TimAlarmResume, hwLrdiAlarm, 
				hwLrdiAlarmResume, hwSfbereAlarm, hwSfbereAlarmResume, hwAuLopAlarm, hwAuLopAlarmResume, 
				hwLaisAlarm, hwLaisAlarmResume, hwSdbereAlarm, hwSdbereAlarmResume, hwPtimAlarm, 
				hwPtimAlarmResume, hwPuneqAlarm, hwPuneqAlarmResume, hwPrdiAlarm, hwPrdiAlarmResume, 
				hwB3TcaAlarm, hwB3TcaAlarmResume, hwPplmAlarm, hwPplmAlarmResume, hwPaisAlarm, 
				hwPaisAlarmResume, hwAuAisAlarm, hwAuAisAlarmResume, hwVlopAlarm, hwVlopAlarmResume, 
				hwLomAlarm, hwLomAlarmResume, hwLpTimVc12Alarm, hwLpTimVc12AlarmResume, hwLofAlarm, 
				hwLofAlarmResume, hwCesPwRemoteLosPktAlarm, hwCesPwRemoteLosPktAlarmResume, hwLpUneqVc12Alarm, hwLpUneqVc12AlarmResume, 
				hwVrdiAlarm, hwVrdiAlarmResume, hwBip2TcaAlarm, hwBip2TcaAlarmResume, hwLpSlmVc12Alarm, 
				hwLpSlmVc12AlarmResume, hwTuAisVc12Alarm, hwTuAisVc12AlarmResume, hwE1EsTcaAlarm, hwE1EsTcaAlarmResume, 
				hwE1LmfaAlarm, hwE1LmfaAlarmResume, hwE1UpE1AisAlarm, hwE1UpE1AisAlarmResume, hwE1AlmE1RaiAlarm, 
				hwE1AlmE1RaiAlarmResume, hwRroolAlarm, hwRroolAlarmResume, hwVrfiAlarm, hwVrfiAlarmResume, 
				hwV5VcaisAlarm, hwV5VcaisAlarmResume, hwCposE1AlmE1RaiAlarm, hwCposE1AlmE1RaiAlarmResume, hwCposE1LfaAlarm, 
				hwCposE1LfaAlarmResume, hwCposE1UpE1AisAlarm, hwCposE1UpE1AisAlarmResume, hwCposE1DownE1AisAlarm, hwCposE1DownE1AisAlarmResume, 
				hwE1DownE1AisAlarm, hwE1DownE1AisAlarmResume, hwCposE1LmfaAlarm, hwCposE1LmfaAlarmResume, hwOcdAlarm, 
				hwOcdAlarmResume, hwLcdAlarm, hwLcdAlarmResume, hwUhcsAlarm, hwUhcsAlarmResume, 
				hwChcsAlarm, hwChcsAlarmResume, hwCesLopsAlarm, hwCesLopsAlarmResume, hwAtmPwLosPktExcAlarm, 
				hwAtmPwLosPktExcAlarmResume, hwAtmPwMisorderPktExcAlarm, hwAtmPwMisorderPktExcAlarmResume, hwAtmPwUnknownCellExcAlarm, hwAtmPwUnknownCellExcAlarmResume,
				hwPortAlarmInverseAutoRecover
				 }
            STATUS current
            DESCRIPTION 
                "This is the group of port notifiction."
            ::= { hwPortGroups 8 }

        
        -- 1.3.6.1.4.1.2011.5.25.157.11.2.9
        hwDslGroupObjectGroup OBJECT-GROUP
            OBJECTS { hwDslGroupIfIndex, hwDslGroupWorkMode, hwDslGroupBisState, hwDslGroupEncapeMode, hwDslGroupEnable, 
                hwDslGroupRowStatus, hwDslGroupIfIndexOfBound, hwVirtualEthernetIfIndex, hwBoundVeRowStatus, hwDslGroupVci, 
        hwDslGroupVpi, hwDslGroupPvcId }
            STATUS current
            DESCRIPTION 
                "The dsl group attribute group."
            ::= { hwPortGroups 9 }

        
        -- 1.3.6.1.4.1.2011.5.25.157.11.2.10
        hwDslGroupImaObjectGroup OBJECT-GROUP
        OBJECTS { hwDslGroupImaVersion, hwDslGroupImaFrameLen, hwDslGroupImaReset, hwDslGroupImaRxMinLinkNum, hwDslGroupImaNeState, 
                hwDslGroupImaRxActLinkNum, hwDslGroupImaRxCellRate, hwDslGroupImaTxActLinkNum, hwDslGroupImaTxCellRate, hwDslGroupImaFeState, 
        hwDslGroupImaIfIndex, hwDslGroupImaTxMinLinkNum, hwDslGroupImaIfName }
            STATUS current
            DESCRIPTION 
                "The dsl group ima attribute group."
            ::= { hwPortGroups 10 }

        
        -- 1.3.6.1.4.1.2011.5.25.157.11.2.11
        hwDslLinkObjectGroup OBJECT-GROUP
        OBJECTS { hwBoundDslGroupIfIndex, hwDslLinkIfIndex, hwDslLinkBoundRowStatus, hwDslLinkIfName, hwBoundDslGroupIfName
                }
            STATUS current
            DESCRIPTION 
                "The dsl link attribute group."
            ::= { hwPortGroups 11 }

        
        -- 1.3.6.1.4.1.2011.5.25.157.11.2.20
        hwDslImaTrapGroup NOTIFICATION-GROUP
            NOTIFICATIONS { hwDslImaGroupLEDown, hwDslImaGroupLEUp, hwDslImaGroupREDown, hwDslImaGroupREUp, hwDslImaLinkLif, 
                hwDslImaLinkLifResume, hwDslImaLinkLods, hwDslImaLinkLodsResume, hwDslImaLinkRfi, hwDslImaLinkRfiResume, 
                hwDslImaLinkReTxUnusable, hwDslImaLinkReTxUsable, hwDslImaLinkReRxUnusable, hwDslImaLinkReRxUsable }
            STATUS current
            DESCRIPTION 
                "The dsl Ima Trap group."
            ::= { hwPortGroups 20 }

        
        -- 1.3.6.1.4.1.2011.5.25.157.11.2.21
        hwDslLinkTrapGroup NOTIFICATION-GROUP
            NOTIFICATIONS { hwDslLinkFrameLost, hwDslLinkFrameResume, hwDslLinkSignalLost, hwDslLinkSignalResume }
            STATUS current
            DESCRIPTION 
                "The dsl Link Trap group."
            ::= { hwPortGroups 21 }

        -- 1.3.6.1.4.1.2011.5.25.157.11.2.22
      hwPortAlarmThresholdObjectGroup OBJECT-GROUP
          OBJECTS{ hwPhysicalPortCrcErrorStatistics, hwPhysicalPortCrcErrorHighThreshold, hwPhysicalPortCrcErrorLowThreshold, hwPhysicalPortCrcErrorInterval,
                   hwPhysicalPortSymbolErrorStatistics, hwPhysicalPortSymbolErrorHighThreshold, hwPhysicalPortSymbolErrorLowThreshold, hwPhysicalPortSymbolErrorInterval,
                   hwPhysicalPortInputErrorStatistics, hwPhysicalPortInputErrorHighThreshold, hwPhysicalPortInputErrorLowThreshold, hwPhysicalPortInputErrorInterval,
                   hwPhysicalPortOutputErrorStatistics, hwPhysicalPortOutputErrorHighThreshold, hwPhysicalPortOutputErrorLowThreshold, hwPhysicalPortOutputErrorInterval,
                   hwPhysicalPortSdhErrorStatistics, hwPhysicalPortSdhErrorHighThreshold, hwPhysicalPortSdhErrorLowThreshold, hwPhysicalPortSdhErrorInterval,
                   hwPhysicalPortBIP8SDErrorThreshold }
          STATUS current       
          DESCRIPTION 
              "The port alarm threshold group."
          ::= { hwPortGroups 22 }

        -- 1.3.6.1.4.1.2011.5.25.157.11.2.23
      hwPortAlarmDownEnableObjectGroup OBJECT-GROUP
          OBJECTS{ hwPhysicalPortCrcEnabledDown, hwPhysicalPortSymbolEnabledDown, hwPhysicalPortInputEnabledDown, hwPhysicalPortOutputEnabledDown,
                   hwPhysicalPortSdhEnabledDown, hwPhysicalPortBip8SdEnabledDown }
          STATUS current       
          DESCRIPTION 
              "The port alarm down enable group."
          ::= { hwPortGroups 23 }

        -- 1.3.6.1.4.1.2011.5.25.157.11.2.25
      hwPortAlarmTrapGroup OBJECT-GROUP
          OBJECTS{ hwPhysicalPortCrcError, hwPhysicalPortCrcErrorResume,
                   hwPhysicalPortSymbolError, hwPhysicalPortSymbolErrorResume,
                   hwPhysicalPortInputError, hwPhysicalPortInputErrorResume,
                   hwPhysicalPortOutputError, hwPhysicalPortOutputErrorResume,
                   hwPhysicalPortSdhError, hwPhysicalPortSdhErrorResume,
                   hwPhysicalPortBip8SdError, hwPhysicalPortBip8SdErrorResume }
          STATUS current       
          DESCRIPTION 
              "The port alarm trap group."
          ::= { hwPortGroups 25 }

    
    END

--
-- HUAWEI-PORT-MIB.mib
--
