-- =================================================================
-- Copyright (C) 2011 by HUAWEI TECHNOLOGIES. All rights reserved
-- 
-- Description: ITU-T G.8032 huawei mib define
-- Reference: ITU-T G.8032/Y.1344
-- Version: V1.00
-- History:
--    <fenghaisheng 61958>,<2011.07.05>,<create>
-- =================================================================
         
HUAWEI-ERPS-MIB DEFINITIONS ::= BEGIN

    IMPORTS
        hwDatacomm            
            FROM HUAWEI-MIB            
        EnabledStatus            
            FROM P-BRIDGE-MIB            
        VlanId            
            FROM Q-BRIDGE-MIB            
        OBJECT-GROUP, NOTIFICATION-GROUP            
            FROM SNMPv2-CONF            
        InterfaceIndex
            FROM IF-MIB  
        Integer32, Unsigned32, OBJECT-TYPE, MODULE-IDENTITY, OBJECT-IDENTITY,
        NOTIFICATION-TYPE,TimeTicks,Counter32        
            FROM SNMPv2-SMI                
        RowStatus,DisplayString            
            FROM SNMPv2-TC;


    -- 1.3.6.1.4.1.2011.5.25.256
    hwErpsMIB MODULE-IDENTITY 
        LAST-UPDATED "201107051557Z"
        ORGANIZATION 
            "Huawei Technologies Co.,Ltd."
        CONTACT-INFO 
            "8090 Team Huawei Technologies Co.,Ltd.
            Huawei Bld.,NO.3 Xinxi Rd., 
            Shang-Di Information Industry Base,
            Hai-Dian District Beijing P.R. China
            http://www.huawei.com
            Zip:100085
            "
        DESCRIPTION 
            "The private mib file includes the general extent 
            information of the device.hwDatacomm(25).hwErpsMIB.
            "
        ::= { hwDatacomm 256 }

    
--  Node definitions
-- 
    -- 1.3.6.1.4.1.2011.5.25.256.1
    hwErpsObjects OBJECT IDENTIFIER ::= { hwErpsMIB 1 }

    
    -- 1.3.6.1.4.1.2011.5.25.256.1.1
    hwErpsGlobalResetRapsPktCnt OBJECT-TYPE
        SYNTAX INTEGER {
                        clear(1),
                        unused(65535)
                       }
        MAX-ACCESS read-write
        STATUS current
        DESCRIPTION
            "Reset the RAPS packets counter of all running ERPS ports.
            The value is unused(65535) when it is read. And it must be clear(1) when it is set."
        ::= { hwErpsObjects 1 }

    -- ring config table
    -- 1.3.6.1.4.1.2011.5.25.256.1.2
    hwErpsRingConfigTable OBJECT-TYPE
        SYNTAX SEQUENCE OF HwErpsRingConfigEntry
        MAX-ACCESS not-accessible
        STATUS current
        DESCRIPTION
            "The table includes the configurtion of ERPS rings."
        ::= { hwErpsObjects 2 }

    
    -- 1.3.6.1.4.1.2011.5.25.256.1.2.1
    hwErpsRingConfigEntry OBJECT-TYPE
        SYNTAX HwErpsRingConfigEntry
        MAX-ACCESS not-accessible
        STATUS current
        DESCRIPTION
            "The table includes the configurtion of ERPS rings.
            The index of the table is ERPS ring id."
        INDEX { hwConfigRingId }
        ::= { hwErpsRingConfigTable 1 }

    
    HwErpsRingConfigEntry ::=
        SEQUENCE { 
            hwConfigRingId
                Integer32, 
            hwConfigRingRowStatus
                RowStatus,     
            hwConfigDescription
                DisplayString,                
            hwConfigControlVlanId
                Integer32,
            hwConfigProtectedInstanceList
                OCTET STRING,           
            hwConfigWtrTimerSettingValue
                Integer32, 
            hwConfigGuardTimerSettingValue
                Integer32,
               hwConfigHoldoffTimerSettingValue
                Integer32,
            hwConfigResetRapsPktCnt 
                INTEGER,
               hwConfigRapsMel
                   Integer32
               }

    -- 1.3.6.1.4.1.2011.5.25.256.1.2.1.1
    hwConfigRingId OBJECT-TYPE
        SYNTAX Integer32 (1..255)
        MAX-ACCESS not-accessible
        STATUS current
        DESCRIPTION
            "ERPS ring Identifier."
        ::= { hwErpsRingConfigEntry 1 }

    -- 1.3.6.1.4.1.2011.5.25.256.1.2.1.2
    hwConfigRingRowStatus OBJECT-TYPE
        SYNTAX RowStatus
        MAX-ACCESS read-create
        STATUS current
        DESCRIPTION
            "Operation of CreateAndGo can be used to create a new ERPS ring, 
            and operation of Destroy be used to destroy an existent ERPS ring."
        ::= { hwErpsRingConfigEntry 2 }

    -- 1.3.6.1.4.1.2011.5.25.256.1.2.1.3
    hwConfigDescription OBJECT-TYPE
        SYNTAX DisplayString (SIZE (0..80))
        MAX-ACCESS read-create
        STATUS current
        DESCRIPTION
            "A textual description of the ERPS ring.  
            It is mandatory that this only contain no more than 80 printable ASCII characters."
        ::= { hwErpsRingConfigEntry 3 }


    -- 1.3.6.1.4.1.2011.5.25.256.1.2.1.4
    hwConfigControlVlanId OBJECT-TYPE
        SYNTAX Integer32 (0 | 1..4094)
        MAX-ACCESS read-create
        STATUS current
        DESCRIPTION
            "The control VLAN identifier of the ERPS ring.
             If the value of the object is set 0, the operation is to delete configuration."
        DEFVAL { 0 }
        ::= { hwErpsRingConfigEntry 4 }

    -- 1.3.6.1.4.1.2011.5.25.256.1.2.1.5
    hwConfigProtectedInstanceList OBJECT-TYPE
        SYNTAX OCTET STRING (SIZE (0..512))
        MAX-ACCESS read-create
        STATUS current
        DESCRIPTION
            " The protected instance list of the ERPS ring."
        ::= { hwErpsRingConfigEntry 5 }          
        
    -- 1.3.6.1.4.1.2011.5.25.256.1.2.1.6
    hwConfigWtrTimerSettingValue OBJECT-TYPE
        SYNTAX Integer32 (1..12)
        UNITS "minutes"
        MAX-ACCESS read-create
        STATUS current
        DESCRIPTION
            "The setting value of  the ring's wait to restore timer."
        DEFVAL { 5 }
        ::= { hwErpsRingConfigEntry 6 } 
        
    -- 1.3.6.1.4.1.2011.5.25.256.1.2.1.7
    hwConfigGuardTimerSettingValue OBJECT-TYPE
        SYNTAX Integer32 (1..200)
        UNITS "centiseconds"
        MAX-ACCESS read-create
        STATUS current
        DESCRIPTION
            "The setting value of the ring's guard timer." 
        ::= { hwErpsRingConfigEntry 7 }  
         
    -- 1.3.6.1.4.1.2011.5.25.256.1.2.1.8
    hwConfigHoldoffTimerSettingValue OBJECT-TYPE
        SYNTAX Integer32 (0..100)
        UNITS "deciseconds"
        MAX-ACCESS read-create
        STATUS current
        DESCRIPTION
            "The setting value of the ring's hold-off timer."
        DEFVAL { 0 }
        ::= { hwErpsRingConfigEntry 8 } 

    -- 1.3.6.1.4.1.2011.5.25.256.1.2.1.9
    hwConfigResetRapsPktCnt OBJECT-TYPE
        SYNTAX INTEGER
                {
                clear(1),
                unused(65535)
                }
            MAX-ACCESS read-create
            STATUS current
            DESCRIPTION
            "Reset the RAPS packets counter of the ERPS ring's ports.
             The value is unused(65535) when it is read. And it must be clear(1) when it is set."
            ::= { hwErpsRingConfigEntry 9 }

    -- 1.3.6.1.4.1.2011.5.25.256.1.2.1.10
    hwConfigRapsMel OBJECT-TYPE
        SYNTAX Integer32 (0..7)
        MAX-ACCESS read-create
        STATUS current
        DESCRIPTION
            "The MEL is the maintenance entity group(MEG) level providing a communication channel for the ring RAPS information."
        DEFVAL { 7 }
        ::= { hwErpsRingConfigEntry 10 }
                  
    --ring status table 
    -- 1.3.6.1.4.1.2011.5.25.256.1.3
    hwErpsRingStatusTable OBJECT-TYPE
        SYNTAX SEQUENCE OF HwErpsRingStatusEntry
        MAX-ACCESS not-accessible
        STATUS current
        DESCRIPTION
            "The table includes the status of ERPS rings."
        ::= { hwErpsObjects 3 }

    
    -- 1.3.6.1.4.1.2011.5.25.256.1.3.1
    hwErpsRingStatusEntry OBJECT-TYPE
        SYNTAX HwErpsRingStatusEntry
        MAX-ACCESS not-accessible
        STATUS current
        DESCRIPTION
            "The table includes the status of ERPS rings.
            The index of the table is ERPS ring id."
        INDEX { hwConfigRingId }
        ::= { hwErpsRingStatusTable 1 }

    
    HwErpsRingStatusEntry ::=
        SEQUENCE { 
            hwStatusWtrTimerRunningValue
                Integer32,
               hwStatusGuardTimerRunningValue
                Integer32,
               hwStatusHoldoffTimerRunningValue
                Integer32,
               hwStatusMachineState
                   INTEGER, 
               hwStatusTopoLastChangeTime
                   TimeTicks
                   }

       
    -- 1.3.6.1.4.1.2011.5.25.256.1.2.1.1
    hwStatusWtrTimerRunningValue OBJECT-TYPE
        SYNTAX Integer32 (0..720)
        UNITS "seconds"
        MAX-ACCESS read-only
        STATUS current
        DESCRIPTION
            "The running value of the ring's wait to restore timer."
        ::= { hwErpsRingStatusEntry 1 }
     
    -- 1.3.6.1.4.1.2011.5.25.256.1.2.1.2
    hwStatusGuardTimerRunningValue OBJECT-TYPE
        SYNTAX Integer32 (0..200)
        UNITS "centiseconds"
        MAX-ACCESS read-only
        STATUS current
        DESCRIPTION
            "The running value of the ring's guard timer."
        ::= { hwErpsRingStatusEntry 2 }
              
    -- 1.3.6.1.4.1.2011.5.25.256.1.2.1.3
    hwStatusHoldoffTimerRunningValue OBJECT-TYPE
        SYNTAX Integer32 (0..100)
        UNITS "deciseconds"
        MAX-ACCESS read-only
        STATUS current
        DESCRIPTION
            "The running value of the ring's hold-off timer."
        ::= { hwErpsRingStatusEntry 3 }
     
    -- 1.3.6.1.4.1.2011.5.25.256.1.2.1.4
    hwStatusMachineState OBJECT-TYPE
        SYNTAX INTEGER
                {
                idle(1),
                protection(2),
                manualSwitch(3),
                forcedSwitch(4),
                pending(5)
                }
            MAX-ACCESS read-only
            STATUS current
            DESCRIPTION
            "The Finite-state machine's state of the ERPS ring.
                state               value
                idle                1
                protection          2
                manualSwitch        3
                forcedSwitch        4
                pending             5
                "
            ::= { hwErpsRingStatusEntry 4 }
     
     
    -- 1.3.6.1.4.1.2011.5.25.256.1.2.1.6
    hwStatusTopoLastChangeTime OBJECT-TYPE
        SYNTAX TimeTicks
            MAX-ACCESS read-only
            STATUS current
            DESCRIPTION
            "The time since last topology change of the ring."
            ::= { hwErpsRingStatusEntry 5 }
           
           
    --port config table     
    --1.3.6.1.4.1.2011.5.25.256.1.3
    hwErpsPortConfigTable OBJECT-TYPE
        SYNTAX SEQUENCE OF HwErpsPortConfigEntry
        MAX-ACCESS not-accessible
        STATUS current
        DESCRIPTION
            "The table includes the configuration of ERPS ports."
        ::= { hwErpsObjects 4 }

    
    -- 1.3.6.1.4.1.2011.5.25.256.1.4.1
    hwErpsPortConfigEntry OBJECT-TYPE
        SYNTAX HwErpsPortConfigEntry
        MAX-ACCESS not-accessible
        STATUS current
        DESCRIPTION
            "The table includes the configuration of ERPS ports.
            The index of the table is ERPS ring identifier, port type, port identifier1, port identifier2, port identifier3, port identifier4.
            If it is an ethernet port including fast ethernet/gigabit ethernet/eth-trunk, the port type is 1, the port identifier1 is the IfIndex of the ethernet port.
            the other port identifier is for extension and not used currently, should be set 0."
        INDEX { hwConfigRingId, hwConfigPortType, hwConfigPortId1, hwConfigPortId2, hwConfigPortId3, 
            hwConfigPortId4 }
        ::= { hwErpsPortConfigTable 1 }

    
    HwErpsPortConfigEntry ::=
        SEQUENCE {    
            hwConfigPortType
                Unsigned32,
            hwConfigPortId1
                Unsigned32,
            hwConfigPortId2
                Unsigned32,
            hwConfigPortId3
                Unsigned32,
            hwConfigPortId4
                Unsigned32,
            hwConfigPortRowStatus
                RowStatus,
            hwConfigPortConfigRole
                Integer32
                  }

    -- 1.3.6.1.4.1.2011.5.25.256.1.4.1.1
    hwConfigPortType OBJECT-TYPE
        SYNTAX Unsigned32 (1)
        MAX-ACCESS not-accessible
        STATUS current
        DESCRIPTION
            "The port type.Currently ERPS just supports ethernet port and the value is 1."
        ::= { hwErpsPortConfigEntry 1 }

    
    -- 1.3.6.1.4.1.2011.5.25.256.1.4.1.2
    hwConfigPortId1 OBJECT-TYPE
        SYNTAX Unsigned32 (0..2147483647)
        MAX-ACCESS not-accessible
        STATUS current
        DESCRIPTION
            "The port identifier1, when the hwConfigPortType is 1, the value of the object is the IfIndex of the port."
        ::= { hwErpsPortConfigEntry 2 }

    
    -- 1.3.6.1.4.1.2011.5.25.256.1.4.1.3
    hwConfigPortId2 OBJECT-TYPE
        SYNTAX Unsigned32 (0..2147483647)
        MAX-ACCESS not-accessible
        STATUS current
        DESCRIPTION
            "The port identifier2, Currently it is not used and only for extension, should be set 0."
        ::= { hwErpsPortConfigEntry 3 }

    
    -- 1.3.6.1.4.1.2011.5.25.256.1.4.1.4
    hwConfigPortId3 OBJECT-TYPE
        SYNTAX Unsigned32 (0..2147483647)
        MAX-ACCESS not-accessible
        STATUS current
        DESCRIPTION
            "The port identifier3, Currently it is not used and only for extension, should be set 0."
        ::= { hwErpsPortConfigEntry 4 }

    
    -- 1.3.6.1.4.1.2011.5.25.256.1.4.1.5
    hwConfigPortId4 OBJECT-TYPE
        SYNTAX Unsigned32 (0..2147483647)
        MAX-ACCESS not-accessible
        STATUS current
        DESCRIPTION
            "The port identifier4, Currently it is not used and only for extension, should be set 0."
        ::= { hwErpsPortConfigEntry 5 } 
        
    -- 1.3.6.1.4.1.2011.5.25.256.1.4.1.6
    hwConfigPortRowStatus OBJECT-TYPE
        SYNTAX RowStatus
        MAX-ACCESS read-create
        STATUS current
        DESCRIPTION
            "Operation of CreateAndGo can be used to have a port join the ERPS ring.
            and operation of Destroy be used to have a port leave the ERPS ring."
        ::= { hwErpsPortConfigEntry 6 }

    -- 1.3.6.1.4.1.2011.5.25.256.1.4.1.7
    hwConfigPortConfigRole OBJECT-TYPE
        SYNTAX Integer32
        MAX-ACCESS read-create
        STATUS current
        DESCRIPTION
            "The configued port role:
            role                       value
            common                      0x10
            rplOwner                    0x21"
        ::= { hwErpsPortConfigEntry 7 }
       
       
    --port status table     
    --1.3.6.1.4.1.2011.5.25.256.1.5
    hwErpsPortStatusTable OBJECT-TYPE
        SYNTAX SEQUENCE OF HwErpsPortStatusEntry
        MAX-ACCESS not-accessible
        STATUS current
        DESCRIPTION
            "The table includes the status of ERPS ports."
        ::= { hwErpsObjects 5 }

    
    -- 1.3.6.1.4.1.2011.5.25.256.1.5.1
    hwErpsPortStatusEntry OBJECT-TYPE
        SYNTAX HwErpsPortStatusEntry
        MAX-ACCESS not-accessible
        STATUS current
        DESCRIPTION
            "The table includes the status of ERPS ports.
            The index of the table is ERPS ring identifier, port type, port identifier1, port identifier2, port identifier3, port identifier4.
            If it is an ethernet port including fast ethernet/gigabit ethernet/eth-trunk, the port type is 1, the port identifier1 is the IfIndex of the ethernet port.
            the other port identifier is for extension and not used currently, should be set 0."
        INDEX { hwConfigRingId, hwConfigPortType, hwConfigPortId1, hwConfigPortId2, hwConfigPortId3, 
        hwConfigPortId4 }
        ::= { hwErpsPortStatusTable 1 }

    
    HwErpsPortStatusEntry ::=
        SEQUENCE { 
            hwPortStatusActiveRole
                Integer32,
            hwPortStatusSignalStatus
                INTEGER,
            hwPortStatusFwdStatus
                INTEGER
                }

    -- 1.3.6.1.4.1.2011.5.25.256.1.5.1.1
    hwPortStatusActiveRole OBJECT-TYPE
        SYNTAX Integer32
        MAX-ACCESS read-only
        STATUS current
        DESCRIPTION
            "The active port role:
            role                       value
            common                      0x10
            rplOwner                    0x21"
        ::= { hwErpsPortStatusEntry 1 }     
        
    -- 1.3.6.1.4.1.2011.5.25.256.1.5.1.7
    hwPortStatusSignalStatus OBJECT-TYPE
        SYNTAX INTEGER
                {
                failed(1),
                nonFailed(2)
                }
        MAX-ACCESS read-only
        STATUS current
        DESCRIPTION
                "The signal status of the port:
                state         value
                failed        1
                nonFailed     2"
            ::= { hwErpsPortStatusEntry 2 }


    -- 1.3.6.1.4.1.2011.5.25.256.1.5.1.8
    hwPortStatusFwdStatus OBJECT-TYPE
            SYNTAX INTEGER
                {
                discarding(1),
                forwarding(2)
                }
            MAX-ACCESS read-only
            STATUS current
            DESCRIPTION
                "The forwarding status of the port:
                state         value
                discarding     1
                forwarding     2"
            ::= { hwErpsPortStatusEntry 3 }

    
    --port Statistics table     
    --1.3.6.1.4.1.2011.5.25.256.1.6
    hwErpsPortStatisticsTable OBJECT-TYPE
        SYNTAX SEQUENCE OF HwErpsPortStatisticsEntry
        MAX-ACCESS not-accessible
        STATUS current
        DESCRIPTION
            "The table includes the statistics of ERPS ports."
        ::= { hwErpsObjects 6 }

    
    -- 1.3.6.1.4.1.2011.5.25.256.1.6.1
    hwErpsPortStatisticsEntry OBJECT-TYPE
        SYNTAX HwErpsPortStatisticsEntry
        MAX-ACCESS not-accessible
        STATUS current
        DESCRIPTION
            "The table includes the Statistics of ERPS ports.
            The index of the table is ERPS ring identifier, port type, port identifier1, port identifier2, port identifier3, port identifier4.
            If it is an ethernet port including fast ethernet/gigabit ethernet/eth-trunk, the port type is 1, the port identifier1 is the IfIndex of the ethernet port.
            the other port identifier is for extension and not used currently, should be set 0."
        INDEX { hwConfigRingId, hwConfigPortType, hwConfigPortId1, hwConfigPortId2, hwConfigPortId3, hwConfigPortId4}
        ::= { hwErpsPortStatisticsTable 1 }

    
    HwErpsPortStatisticsEntry ::=
        SEQUENCE { 
            hwRxRapsSfPktCnt
                Counter32,
            hwTxRapsSfPktCnt
                Counter32,
            hwRxRapsNrPktCnt
                Counter32,
            hwTxRapsNrPktCnt
                Counter32,
            hwRxRapsNrRbPktCnt
                Counter32,
            hwTxRapsNrRbPktCnt
                Counter32        
             }

    
    -- 1.3.6.1.4.1.2011.5.25.256.1.6.1.1
    hwRxRapsSfPktCnt OBJECT-TYPE
        SYNTAX Counter32
        MAX-ACCESS read-only
        STATUS current
        DESCRIPTION
            "The number of received RAPS SF packets."
        ::= { hwErpsPortStatisticsEntry 1 }

    
    -- 1.3.6.1.4.1.2011.5.25.256.1.3.1.2
    hwTxRapsSfPktCnt OBJECT-TYPE
        SYNTAX Counter32
        MAX-ACCESS read-only
        STATUS current
        DESCRIPTION
            "The number of transmitted RAPS SF packets."
        ::= { hwErpsPortStatisticsEntry 2 }

    
    -- 1.3.6.1.4.1.2011.5.25.256.1.3.1.3
    hwRxRapsNrPktCnt OBJECT-TYPE
        SYNTAX Counter32
        MAX-ACCESS read-only
        STATUS current
        DESCRIPTION
                "The number of received RAPS NR packets."
        ::= { hwErpsPortStatisticsEntry 3 }

    
    -- 1.3.6.1.4.1.2011.5.25.256.1.3.1.4
    hwTxRapsNrPktCnt OBJECT-TYPE
        SYNTAX Counter32
        MAX-ACCESS read-only
        STATUS current
        DESCRIPTION
                "The number of transmitted RAPS NR packets."
        ::= { hwErpsPortStatisticsEntry 4 }

    
    -- 1.3.6.1.4.1.2011.5.25.256.1.3.1.5
    hwRxRapsNrRbPktCnt OBJECT-TYPE
        SYNTAX Counter32
        MAX-ACCESS read-only
        STATUS current
        DESCRIPTION
                "The number of received RAPS NRRB packets."
        ::= { hwErpsPortStatisticsEntry 5 }

    
    -- 1.3.6.1.4.1.2011.5.25.256.1.3.1.6
    hwTxRapsNrRbPktCnt OBJECT-TYPE
        SYNTAX Counter32
        MAX-ACCESS read-only
        STATUS current
        DESCRIPTION
                "The number of transmitted RAPS NRRB packets."
        ::= { hwErpsPortStatisticsEntry 6 }      
        

    -- 1.3.6.1.4.1.2011.5.25.256.2
    hwErpsGroups OBJECT IDENTIFIER ::= { hwErpsMIB 2 }

    
    -- 1.3.6.1.4.1.2011.5.25.256.2.1
    hwErpsGlobalInfoGroup OBJECT-GROUP
        OBJECTS { hwErpsGlobalResetRapsPktCnt }
        STATUS current
        DESCRIPTION 
            "The group of global information."
        ::= { hwErpsGroups 1 }

    
    -- 1.3.6.1.4.1.2011.5.25.256.2.2
    hwErpsRingConfigInfoGroup OBJECT-GROUP
        OBJECTS { hwConfigRingRowStatus, hwConfigDescription, hwConfigControlVlanId, hwConfigProtectedInstanceList,  
            hwConfigWtrTimerSettingValue, hwConfigGuardTimerSettingValue, hwConfigHoldoffTimerSettingValue,
            hwConfigResetRapsPktCnt, hwConfigRapsMel}
        STATUS current
        DESCRIPTION 
            "The group of ring configuration."
        ::= { hwErpsGroups 2 } 
        
    -- 1.3.6.1.4.1.2011.5.25.256.2.3
    hwErpsRingStatusInfoGroup OBJECT-GROUP
        OBJECTS { hwStatusWtrTimerRunningValue, hwStatusGuardTimerRunningValue, hwStatusHoldoffTimerRunningValue,
            hwStatusMachineState, hwStatusTopoLastChangeTime }
        STATUS current
        DESCRIPTION 
            "The group of ring status."
        ::= { hwErpsGroups 3 }
    
    -- 1.3.6.1.4.1.2011.5.25.256.2.4
    hwErpsPortConfigInfoGroup OBJECT-GROUP
        OBJECTS { hwConfigPortRowStatus, hwConfigPortConfigRole }
        STATUS current
        DESCRIPTION 
            "The group of port configuration."
        ::= { hwErpsGroups 4 }
    
    
    -- 1.3.6.1.4.1.2011.5.25.256.2.5
    hwErpsPortStatusInfoGroup OBJECT-GROUP
        OBJECTS { hwPortStatusActiveRole, hwPortStatusSignalStatus, hwPortStatusFwdStatus }
        STATUS current
        DESCRIPTION 
            "The group of port status."
        ::= { hwErpsGroups 5 }


    -- 1.3.6.1.4.1.2011.5.25.256.2.6
    hwErpsPortStatisticsInfoGroup OBJECT-GROUP
        OBJECTS { hwRxRapsSfPktCnt, hwTxRapsSfPktCnt, hwRxRapsNrPktCnt, hwTxRapsNrPktCnt,
            hwRxRapsNrRbPktCnt, hwTxRapsNrRbPktCnt }
        STATUS current
        DESCRIPTION 
            "The group of port information."
        ::= { hwErpsGroups 6 }

    END

--
-- HUAWEI-ERPS-MIBv2.my
--
