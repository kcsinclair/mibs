-- *****************************************************************
-- RDN-CHASSIS-TYPE-MIB.mib:
-- Motorola BSR's Chassis Types MIB
--
-- Copyright (C) 2001, 2008 by Motorola, Inc.
-- All rights reserved.
-- *****************************************************************
RDN-CHASSIS-TYPE-MIB DEFINITIONS ::= BEGIN

    IMPORTS
        MODULE-IDENTITY
            FROM SNMPv2-SMI
        rdnDefinitions
            FROM RDN-DEFINITIONS-MIB;

    -- riverdelta chassis-type definitions mib module

    rdnChassisTypes MODULE-IDENTITY
        LAST-UPDATED "200808080000Z"  -- 08 August 2008
        ORGANIZATION "Motorola"
        CONTACT-INFO "Motorola
                      Customer Service
                      101 Tournament Drive
                      Horsham, PA 19044
                      US Tel: +1 888 944 4357
                      Int Tel: +1 215 323 0044
	              Fax: +1 215 323 1502
                      Email: CPSSupport@Motorola.com"
        DESCRIPTION
                "MIB module for Motorola Chassis-Type
                definitions.

		Copyright (C) 2001, 2008 by Motorola, Inc.
		All rights reserved."

	REVISION     "200808080000Z"  -- 08 August 2008
	DESCRIPTION
	       "Added Copyright Statement into MIB modules's
	       descritption."	

        REVISION     "200311050000Z"
        DESCRIPTION
                "+ Updated the CONTACT-INFO.
	         + Reorder REVISION/DESCRIPTION in required 
                   reverse chronological order."
        REVISION     "200304290000Z"
        DESCRIPTION
                "Clean up of CONTACT-INFO."
        REVISION     "200104180000Z"
        DESCRIPTION
                "Initial creation."
        ::= { rdnDefinitions 2 }


      --
      -- chassis-type definitions for all riverdelta products
      --

      rdnChassisTypesUnknown     OBJECT IDENTIFIER ::= { rdnChassisTypes 0 }
      rdnChassisTypesBSR64000    OBJECT IDENTIFIER ::= { rdnChassisTypes 1 }
      rdnChassisTypesBSR1000     OBJECT IDENTIFIER ::= { rdnChassisTypes 2 }
      rdnChassisTypesOSR2000     OBJECT IDENTIFIER ::= { rdnChassisTypes 3 }

END
