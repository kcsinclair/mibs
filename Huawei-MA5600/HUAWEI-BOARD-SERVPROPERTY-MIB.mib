-- ================================================================================
-- Copyright (C) 2013 by  HUAWEI TECHNOLOGIES. All rights reserved.
-- Description:  This MIB is used for defining huawei's board service property,
--               it includes traffic controling...
-- Reference:  
-- Version:      V1.13
-- ================================================================================
    HUAWEI-BOARD-SERVPROPERTY-MIB DEFINITIONS ::= BEGIN

        IMPORTS 
            huaweiUtility            
                FROM HUAWEI-MIB      
            hwFrameIndex,hwSlotIndex
                FROM HUAWEI-DEVICE-MIB                    
            OBJECT-TYPE, MODULE-IDENTITY, Integer32, Counter32
                FROM SNMPv2-SMI;

        hwBoardServProperty MODULE-IDENTITY
            LAST-UPDATED "201202100000Z"
            ORGANIZATION "Huawei Technologies Co., Ltd."
            CONTACT-INFO 
                   "Huawei Industrial Base
                    Bantian, Longgang
                    Shenzhen 518129
                    People's Republic of China
                    Website: http://www.huawei.com
                    Email: support@huawei.com
                   "
            DESCRIPTION 
                "This MIB is used for defining huawei's board service property,
                it includes traffic controling..."        
        
            --  Revision history 
            REVISION     "201303100000Z"
            DESCRIPTION  "V1.13, added hwBoardGlobalOutboundTrafficSuppressTable"

            REVISION     "201202100000Z"
            DESCRIPTION  "V1.12, modified the description of hwBoardServPropertyTable."
                      
            REVISION     "201011200000Z"
            DESCRIPTION  "V1.11, modified the description of hwBoardStatTable, hwBoardWorkModeTable, 
                          hwBoardModemLearningTable and hwBoardModemLearningEnable."
            
            REVISION     "201007220000Z"
            DESCRIPTION  "V1.10, modified the description of leaves."
            
            REVISION     "201006260000Z"                                        
            DESCRIPTION  "V1.09, modified the description of hwBoardStatTable." 

            REVISION     "201006260000Z"
            DESCRIPTION  "V1.08, added hwBoardTrafficSuppressUnicast."   
            
            REVISION     "201003160000Z"                                       
            DESCRIPTION  "V1.07, modified description of hwBoardServPropertyTable."   
            
            REVISION     "200912240000Z"        
            DESCRIPTION  "V1.06, changed SMI to SMIv2 standard."
            
            REVISION     "200904070000Z"          
            DESCRIPTION  "V1.05, added service board unicast traffic-suppress."        
            
            REVISION     "200707310000Z"          
            DESCRIPTION  "V1.04, added R068 Modem auto configure VPI/VCI function switch list."
    
            REVISION     "200510190000Z"          
            DESCRIPTION  "V1.00, created for service board upload broadcast traffic-suppress. "

            ::= { huaweiUtility 48 }

        -- Node Definitions                
        hwBoardServPropertyTable OBJECT-TYPE
            SYNTAX SEQUENCE OF HwBoardServPropertyEntry
            MAX-ACCESS not-accessible
            STATUS current
            DESCRIPTION
                "Indicates the traffic suppression feature table for upstream broadcast, unknown multicast traffic and unknown 
                 unicast traffic on the board. 
                 The indexes of this table are hwFrameIndex and hwSlotIndex.
                "
            ::= { hwBoardServProperty 1 }
            
        hwBoardServPropertyEntry OBJECT-TYPE
            SYNTAX HwBoardServPropertyEntry
            MAX-ACCESS not-accessible
            STATUS current
            DESCRIPTION            
                "Indicates the traffic suppression feature table for upstream broadcast, unknown multicast traffic and unknown 
                 unicast traffic on the board. 
                 The indexes of this entry are hwFrameIndex and hwSlotIndex.
                "
            INDEX { hwFrameIndex,hwSlotIndex }
            ::= { hwBoardServPropertyTable 1 }
            
        HwBoardServPropertyEntry ::=
            SEQUENCE {
                hwBoardTrafficSuppressBroadcast    
                    Integer32,
                hwBoardTrafficSuppressMulticast
                    Integer32,
                hwBoardTrafficSuppressUnicast
                    Integer32
            }
            
        hwBoardTrafficSuppressBroadcast OBJECT-TYPE        
            SYNTAX Integer32 (-1..13)                      
            MAX-ACCESS read-write                              
            STATUS current                                    
            DESCRIPTION                                       
                "Indicates the upstream broadcast traffic suppression on a board. 
                 Range: -1,0-13
                 Default: 7                                         
                 13 indicates full-suppression of traffic, and 0 indicates no traffic suppression. 
                 -1 indicates invalid value. 
                 The suppression levels and corresponding bandwidth ranges are listed as follows: 
                 ---------------------------------------------------------------
                 NO. Min bandwidth(kbps) Max bandwidth(kbps) Package number(pps)
                 ---------------------------------------------------------------
                   0      Not suppressed      Not suppressed      Not suppressed
                   1                   6                 145                  12
                   2                  12                 291                  24
                   3                  24                 582                  48
                   4                  48                1153                  95
                   5                  97                2319                 191
                   6                 195                4639                 382
                   7                 390                9265                 763
                   8                 781               18531                1526
                   9                1562               37063                3052
                  10                3125               74126                6104
                  11                6249              148241               12207
                  12               12499              296483               24414
                  13                   0                   0                   0
                 ---------------------------------------------------------------
                "  
            ::= { hwBoardServPropertyEntry 1 }
            
        hwBoardTrafficSuppressMulticast OBJECT-TYPE        
            SYNTAX Integer32 (-1..13)                      
            MAX-ACCESS read-write                              
            STATUS current                                    
            DESCRIPTION                                       
                "Indicates the unknown multicast traffic suppression on a board. 
                 Range: -1,0-13
                 Default: 0                         
                 13 indicates full-suppression of traffic, and 0 indicates no traffic suppression. 
                 -1 indicates invalid value.
                 The suppression levels and corresponding bandwidth ranges are listed as follows: 
                 ---------------------------------------------------------------
                 NO. Min bandwidth(kbps) Max bandwidth(kbps) Package number(pps)
                 ---------------------------------------------------------------
                   0      Not suppressed      Not suppressed      Not suppressed
                   1                   6                 145                  12
                   2                  12                 291                  24
                   3                  24                 582                  48
                   4                  48                1153                  95
                   5                  97                2319                 191
                   6                 195                4639                 382
                   7                 390                9265                 763
                   8                 781               18531                1526
                   9                1562               37063                3052
                  10                3125               74126                6104
                  11                6249              148241               12207
                  12               12499              296483               24414
                  13                   0                   0                   0
                 ---------------------------------------------------------------
                " 
            ::= { hwBoardServPropertyEntry 2 }
            
        hwBoardTrafficSuppressUnicast OBJECT-TYPE        
            SYNTAX Integer32 (-1..13)                      
            MAX-ACCESS read-write                              
            STATUS current                                    
            DESCRIPTION                                       
                "Indicates the unknown unicast traffic suppression on a board. 
                 Range: -1,0-13
                 Default: 7                         
                 13 indicates full-suppression of traffic, and 0 indicates no traffic suppression. 
                 -1 indicates invalid value.
                 The suppression levels and corresponding bandwidth ranges are listed as follows: 
                 ---------------------------------------------------------------
                 NO. Min bandwidth(kbps) Max bandwidth(kbps) Package number(pps)
                 ---------------------------------------------------------------
                   0      Not suppressed      Not suppressed      Not suppressed
                   1                   6                 145                  12
                   2                  12                 291                  24
                   3                  24                 582                  48
                   4                  48                1153                  95
                   5                  97                2319                 191
                   6                 195                4639                 382
                   7                 390                9265                 763
                   8                 781               18531                1526
                   9                1562               37063                3052
                  10                3125               74126                6104
                  11                6249              148241               12207
                  12               12499              296483               24414
                  13                   0                   0                   0
                 ---------------------------------------------------------------
                " 
            ::= { hwBoardServPropertyEntry 3 }

        hwBoardStatTable OBJECT-TYPE
            SYNTAX SEQUENCE OF HwBoardStatEntry
            MAX-ACCESS not-accessible
            STATUS current
            DESCRIPTION
                "Indicates the board traffic statistics feature.
                 The indexes of this table are hwFrameIndex and hwSlotIndex.
                "
            ::= { hwBoardServProperty 2 }
            
        hwBoardStatEntry OBJECT-TYPE
            SYNTAX HwBoardStatEntry
            MAX-ACCESS not-accessible
            STATUS current
            DESCRIPTION
                "Indicates the board traffic statistics feature.
                 The indexes of this entry are hwFrameIndex and hwSlotIndex.
                "
            INDEX { hwFrameIndex,hwSlotIndex }
            ::= { hwBoardStatTable 1 }
        
        HwBoardStatEntry ::=
            SEQUENCE {
                hwBoardInOcts    
                    Counter32,
                hwBoardOutOcts
                    Counter32
             }
                 
        hwBoardInOcts OBJECT-TYPE
            SYNTAX Counter32
            MAX-ACCESS read-only
            STATUS current
            DESCRIPTION
                "The total count of Octets which were received by the specified board."     
            ::= { hwBoardStatEntry 1 }
            
        hwBoardOutOcts OBJECT-TYPE        
            SYNTAX Counter32
            MAX-ACCESS read-only
            STATUS current
            DESCRIPTION
                "The total count of Octets which were sent from the specified board."
            ::= { hwBoardStatEntry 2 }
            
        --Eth Board work mode table 
        hwBoardWorkModeTable OBJECT-TYPE
            SYNTAX SEQUENCE OF HwBoardWorkModeEntry
            MAX-ACCESS not-accessible
            STATUS current
            DESCRIPTION
                "Indicates the board work mode feature.
                 The indexes of this table are hwFrameIndex and hwSlotIndex.
                "
            ::= { hwBoardServProperty 3 }
            
        hwBoardWorkModeEntry OBJECT-TYPE
            SYNTAX HwBoardWorkModeEntry
            MAX-ACCESS not-accessible
            STATUS current
            DESCRIPTION
                "Indicates the board work mode feature.
                 The indexes of this entry are hwFrameIndex and hwSlotIndex.
                "
            INDEX { hwFrameIndex,hwSlotIndex }
            ::= { hwBoardWorkModeTable 1 }
    
        HwBoardWorkModeEntry ::=
            SEQUENCE {
                hwEthBoardWorkMode    
                    INTEGER
             }
                 
        hwEthBoardWorkMode OBJECT-TYPE
            SYNTAX INTEGER
                {    
                qinq(1),  
                normal(2)
                }
            MAX-ACCESS read-write
            STATUS current
            DESCRIPTION
                "Options: 
                 1. qinq(1)   -qinq mode
                 2. normal(2) -normal mode
                "     
            ::= { hwBoardWorkModeEntry 1 }
            
        -- TR068 Modem learning VPI/VCI Table (ADSL board support)         
        hwBoardModemLearningTable OBJECT-TYPE
            SYNTAX SEQUENCE OF HwBoardModemLearningEntry
            MAX-ACCESS not-accessible
            STATUS current
            DESCRIPTION
                "Indicates TR068 modem learning VPI/VCI feature.
                 The indexes of this table are hwFrameIndex and hwSlotIndex.
                "
            ::= { hwBoardServProperty 4 }
            
        hwBoardModemLearningEntry OBJECT-TYPE
            SYNTAX HwBoardModemLearningEntry
            MAX-ACCESS not-accessible
            STATUS current
            DESCRIPTION
                "Indicates TR068 modem learning VPI/VCI feature.
                 The indexes of this entry are hwFrameIndex and hwSlotIndex.
                "
            INDEX { hwFrameIndex,hwSlotIndex }
            ::= { hwBoardModemLearningTable 1 }
    
        HwBoardModemLearningEntry ::=
            SEQUENCE {
                hwBoardModemLearningEnable    
                    INTEGER
             }
                   
        hwBoardModemLearningEnable OBJECT-TYPE
            SYNTAX INTEGER
                {    
                true(1),  
                false(2)
                }
            MAX-ACCESS read-write
            STATUS current
            DESCRIPTION
                "TR068 Modem learning VPI/VCI (ADSL board support)
                 Options: 
                 1. true(1)  -indicates TR068 Modem can learn VPI/VCI 
                 2. false(2) -indicates TR068 Modem can not learn VPI/VCI
                "
            ::= { hwBoardModemLearningEntry 1 }
 
        -- The unicast traffic-suppress of board (XDSL board support) 
        hwBoardTrafficUnicast OBJECT-TYPE
            SYNTAX Integer32 ( 0..4905 )
            MAX-ACCESS read-write
            STATUS current
            DESCRIPTION
                "The unicast traffic-suppress of board.
                 Set 65535 to close. The default value of unicast traffic-suppress is 65535.
                "
            ::= { hwBoardServProperty 5 }    

        hwBoardGlobalOutboundTrafficSuppressTable OBJECT-TYPE
            SYNTAX SEQUENCE OF HwBoardGlobalOutboundTrafficSuppressEntry
            MAX-ACCESS not-accessible
            STATUS current
            DESCRIPTION
                "Indicates the traffic suppression feature table for outbound broadcast, unknown multicast traffic and unknown 
                 unicast traffic on the board. 
                 The indexes of this table are hwFrameIndex and hwSlotIndex."
            ::= { hwBoardServProperty 6 }
        
        hwBoardGlobalOutboundTrafficSuppressEntry OBJECT-TYPE
            SYNTAX HwBoardGlobalOutboundTrafficSuppressEntry
            MAX-ACCESS not-accessible
            STATUS current
            DESCRIPTION
                "Indicates the traffic suppression feature table for outbound broadcast, unknown multicast traffic and unknown 
                 unicast traffic on the board. 
                 The indexes of this entry are hwFrameIndex and hwSlotIndex."
            INDEX { hwFrameIndex,hwSlotIndex }
            ::= { hwBoardGlobalOutboundTrafficSuppressTable 1 }
        
        HwBoardGlobalOutboundTrafficSuppressEntry ::=
            SEQUENCE { 
                hwBoardGlobalOutboundTrafficSuppressBroadcast
                    Integer32,
                hwBoardGlobalOutboundTrafficSuppressMulticast
                    Integer32,
                hwBoardGlobalOutboundTrafficSuppressUnicast
                    Integer32
             }

        hwBoardGlobalOutboundTrafficSuppressBroadcast OBJECT-TYPE
            SYNTAX Integer32 (-1..13)
            MAX-ACCESS read-write
            STATUS current
            DESCRIPTION
                "Indicates the outbound broadcast traffic suppression on a board. 
                 Range: -1,0-13
                 Default: 0
                 13 indicates full-suppression of traffic, and 0 indicates no traffic suppression. 
                 -1 indicates invalid value. 
                 The suppression levels and corresponding bandwidth ranges are listed as follows: 
                 ---------------------------------------------------------------
                 NO. Min bandwidth(kbps) Max bandwidth(kbps) Package number(pps)
                 ---------------------------------------------------------------
                   0      Not suppressed      Not suppressed      Not suppressed
                   1                   6                 145                  12
                   2                  12                 291                  24
                   3                  24                 582                  48
                   4                  48                1153                  95
                   5                  97                2319                 191
                   6                 195                4639                 382
                   7                 390                9265                 763
                   8                 781               18531                1526
                   9                1562               37063                3052
                  10                3125               74126                6104
                  11                6249              148241               12207
                  12               12499              296483               24414
                  13                   0                   0                   0
                 ---------------------------------------------------------------
                "  
            ::= { hwBoardGlobalOutboundTrafficSuppressEntry 1 }
        
        hwBoardGlobalOutboundTrafficSuppressMulticast OBJECT-TYPE
            SYNTAX Integer32 (-1..13)
            MAX-ACCESS read-write
            STATUS current
            DESCRIPTION
                "Indicates the outbound unknown multicast traffic suppression on a board. 
                 Range: -1,0-13
                 Default: 0
                 13 indicates full-suppression of traffic, and 0 indicates no traffic suppression. 
                 -1 indicates invalid value.
                 The suppression levels and corresponding bandwidth ranges are listed as follows: 
                 ---------------------------------------------------------------
                 NO. Min bandwidth(kbps) Max bandwidth(kbps) Package number(pps)
                 ---------------------------------------------------------------
                   0      Not suppressed      Not suppressed      Not suppressed
                   1                   6                 145                  12
                   2                  12                 291                  24
                   3                  24                 582                  48
                   4                  48                1153                  95
                   5                  97                2319                 191
                   6                 195                4639                 382
                   7                 390                9265                 763
                   8                 781               18531                1526
                   9                1562               37063                3052
                  10                3125               74126                6104
                  11                6249              148241               12207
                  12               12499              296483               24414
                  13                   0                   0                   0
                 ---------------------------------------------------------------
                " 
            ::= { hwBoardGlobalOutboundTrafficSuppressEntry 2 }
        
        hwBoardGlobalOutboundTrafficSuppressUnicast OBJECT-TYPE
            SYNTAX Integer32 (-1..13)
            MAX-ACCESS read-write
            STATUS current
            DESCRIPTION
                "Indicates the outbound unknown unicast traffic suppression on a board. 
                 Range: -1,0-13
                 Default: 8
                 13 indicates full-suppression of traffic, and 0 indicates no traffic suppression. 
                 -1 indicates invalid value.
                 The suppression levels and corresponding bandwidth ranges are listed as follows: 
                 ---------------------------------------------------------------
                 NO. Min bandwidth(kbps) Max bandwidth(kbps) Package number(pps)
                 ---------------------------------------------------------------
                   0      Not suppressed      Not suppressed      Not suppressed
                   1                   6                 145                  12
                   2                  12                 291                  24
                   3                  24                 582                  48
                   4                  48                1153                  95
                   5                  97                2319                 191
                   6                 195                4639                 382
                   7                 390                9265                 763
                   8                 781               18531                1526
                   9                1562               37063                3052
                  10                3125               74126                6104
                  11                6249              148241               12207
                  12               12499              296483               24414
                  13                   0                   0                   0
                 ---------------------------------------------------------------
                " 
            ::= { hwBoardGlobalOutboundTrafficSuppressEntry 3 }
        
END
