-- =================================================================
-- Copyright (C) 2010 by HUAWEI TECHNOLOGIES. All rights reserved.
-- Description: Huawei entity extent MIB file for environment.  
--              This MIB is used for managing the running state of
--              the access devices that are in use. The content 
--              contains the administrative state, the operational
--              state, the usage of the device CPU and memory, and the
--              temperature of the device.
-- Reference:   
-- Version: V1.10
-- =================================================================

    HUAWEI-ENTITY-EXTENT-MIB DEFINITIONS ::= BEGIN
 
			IMPORTS
			 entPhysicalIndex            
			     FROM ENTITY-MIB            
			 hwDatacomm            
			     FROM HUAWEI-MIB            
			 SnmpAdminString            
			     FROM SNMP-FRAMEWORK-MIB            
			 OBJECT-GROUP, MODULE-COMPLIANCE, NOTIFICATION-GROUP            
			     FROM SNMPv2-CONF            
			 Integer32, BITS, OBJECT-TYPE, MODULE-IDENTITY, NOTIFICATION-TYPE            
			     FROM SNMPv2-SMI            
			 DateAndTime, TEXTUAL-CONVENTION            
			     FROM SNMPv2-TC;
 
 
			hwEntityExtentMIB MODULE-IDENTITY 
				LAST-UPDATED "201207120000Z"
				ORGANIZATION "Huawei Technologies co.,Ltd."
				CONTACT-INFO                                 
				             "Huawei Industrial Base         
				              Bantian, Longgang              
				              Shenzhen 518129                
				              People's Republic of China     
				              Website: http://www.huawei.com 
				              Email: support@huawei.com      
				             "                               
				DESCRIPTION 
					"Huawei entity extent MIB file for environment.  
					This MIB is used for managing the running state of
					the access devices that are in use. The content
					contains the administrative state, the operational
					state, the usage of the device CPU and memory, and the
					temperature of the device.
					"   
                
-- Revision history
			REVISION 	"201207120000Z"
			DESCRIPTION "V1.10, added leaves of the hwEntityPhysicalSpecTable:
			                hwEntityPhysicalSpecEmu,
			                hwEntityPhysicalSpecPowerframe,
			                hwEntityPhysicalSpecPowermodule,
			                hwEntityPhysicalSpecBattery
			             modified the description of leaves:
			                hwEntityPhysicalSpecRack,
			                hwEntityPhysicalSpecFrame,
			                hwEntityPhysicalSpecSlot,
			                hwEntityPhysicalSpecBoard,
			                hwEntityPhysicalSpecSubSlot,
			                hwEntityPhysicalSpecSubBoard,
			                hwEntityPhysicalSpecPort"
			
			REVISION 	"201011100000Z"
			DESCRIPTION "V1.09, modified the description of the hwEntityExtentMIB,hwEntityStateEntry and hwRUModuleInfoEntry."
			
			REVISION 	"201010080000Z"
			DESCRIPTION "V1.08, modified the description of the hwEntityTemperature."
			
			REVISION 	"201008300000Z"
			DESCRIPTION "V1.07, modified the description of the leaves in MIB files for DT MIB standardization."
                
			REVISION 	"201006170000Z"
			DESCRIPTION "V1.06, modified the Chinese characters in MIB files."

			REVISION 	"201003240000Z"
			DESCRIPTION "V1.05, cleared testing errors and warnings."

			REVISION	"200601040000Z"
			DESCRIPTION "V1.00, initial version"

        	::= { hwDatacomm 31 }

--
-- Textual conventions
--
    HwAdminState ::= TEXTUAL-CONVENTION
        STATUS current
        DESCRIPTION 
            "Represents the various possible administrative states.
             Locked means that the resource is administratively
             prohibited from use. ShuttingDown means that the
             usage is administratively limited to current instances of
             use. Unlocked means that the resource is not
             administratively prohibited from use."
        REFERENCE 
            "ITU Recommendation X.731, 'Information Technology - Open
             Systems Interconnection - System Management: State
             Management Function', 1992"
        SYNTAX INTEGER
            {
            notSupported(1),
            locked(2),
            shuttingDown(3),
            unlocked(4)
            }
        
    HwOperState ::= TEXTUAL-CONVENTION
        STATUS current
        DESCRIPTION 
            "Represents the possible values of operation states.
             Disabled means that the resource cannot be operated.
            Enabled means that the resource is partially or fully operable. The values up(11), down(12), and
             connect(13) are used only for NE5000E BTB or its extended systems."
        REFERENCE 
            "ITU Recommendation X.731, 'Information Technology - Open
             Systems Interconnection - System Management: State
             Management Function', 1992"
        SYNTAX INTEGER
            {
            notSupported(1),
            disabled(2),
            enabled(3),
            offline(4),
            up(11),
            down(12),
            connect(13)
            }
            
    HwStandbyStatus ::= TEXTUAL-CONVENTION
        STATUS current
        DESCRIPTION 
            "Represents the possible values of standby status.
             hotStandby means that the resource is not providing with 
             services, but will immediately be able to take over the
             role of the resource to be backed up without
             initialization activity. In addition, the resource will contain the same
             information as the resource to be backed up. 
             coldStandy means that the resource is to back up another
             resource, but will not be immediately able to take over
             the role of a resource to be backed up. In addition,
             some initialization activities are required. 
             providingService means that the resource is providing services."
        REFERENCE 
            "ITU Recommendation X.731, 'Information Technology - Open
             Systems Interconnection - System Management: State
             Management Function', 1992"
        SYNTAX INTEGER
            {
            notSupported(1),
            hotStandby(2),
            coldStandby(3),
            providingService(4)
            }
            
-- Not defined in X.731
    HwAlarmStatus ::= TEXTUAL-CONVENTION
        STATUS current
        DESCRIPTION 
            "Represents the possible values of alarm status.
             If this attribute is not set, none of the
             status conditions described below is displayed. If 
             underRepair(1) is set, the resource is currently
             being repaired.
            
             If critical(2) is set, one or more critical
             alarms are active. If major(3)is set, one or more major alarms are active. If minor(4) is set, one or more
             minor alarms are active. If warning(6) is set, one or more warning alarms are
             active. If indeterminate(7) is set, one or more  alarms at the indeterminate
             level are active.
            
             If alarmOutstanding(5) is set, one or more
             alarms are active. The fault may or may
             not be disabled. "
        REFERENCE 
            "ITU Recommendation X.731, 'Information Technology - Open
             Systems Interconnection - System Management: State
             Management Function', 1992"
        SYNTAX BITS
            {
            notSupported(0),
            underRepair(1),
            critical(2),
            major(3),
            minor(4),
            alarmOutstanding(5),
            warning(6),
            indeterminate(7)
            }
            
    
--
-- Node definitions
--
    
        hwEntityExtObjects OBJECT IDENTIFIER ::= { hwEntityExtentMIB 1 }
        
-- MIB contains four groups      
-- 
        hwEntityState OBJECT IDENTIFIER ::= { hwEntityExtObjects 1 }
        
        hwEntityStateTable OBJECT-TYPE
            SYNTAX SEQUENCE OF HwEntityStateEntry
            MAX-ACCESS not-accessible
            STATUS current
            DESCRIPTION
                "This table contains one row data for each physical entity. There is
                 always at least one row for an overall physical entity.
                 The index of this table is entPhysicalIndex. 
                 The information in each row may not include all the objects.
                " 
		   ::= { hwEntityState 1 }
        
        hwEntityStateEntry OBJECT-TYPE
            SYNTAX HwEntityStateEntry
            MAX-ACCESS not-accessible
            STATUS current
            DESCRIPTION
                "This table contains one row data for each physical entity. There is
                 always at least one row for an overall physical entity.
                 The index of this entry is entPhysicalIndex. 
                 The information in each row may not include all the objects.
                " 
        	INDEX { entPhysicalIndex }  
		   ::= { hwEntityStateTable 1 }
    
    	HwEntityStateEntry ::=
	        SEQUENCE 
	        	{ 
	            hwEntityAdminStatus
	                HwAdminState,
	            hwEntityOperStatus
	                HwOperState,
	            hwEntityStandbyStatus
	                HwStandbyStatus,
	            hwEntityAlarmLight
	                HwAlarmStatus,
	            hwEntityCpuUsage
	                Integer32,
	            hwEntityCpuUsageThreshold
	                Integer32,
	            hwEntityMemUsage
	                Integer32,
	            hwEntityMemUsageThreshold
	                Integer32,
	            hwEntityMemSize
	                Integer32,
	            hwEntityUpTime
	                Integer32,
	            hwEntityTemperature
	              	Integer32,
	            hwEntityTemperatureThreshold
	                Integer32,
	            hwEntityVoltage
	                Integer32,
	            hwEntityVoltageLowThreshold
	                Integer32,
	            hwEntityVoltageHighThreshold
	                Integer32,        
	            hwEntityTemperatureLowThreshold
	                Integer32,                    
	            hwEntityOpticalPower    
	                Integer32
	            }

        hwEntityAdminStatus OBJECT-TYPE
            SYNTAX HwAdminState
            MAX-ACCESS read-write
            STATUS current
            DESCRIPTION
                "The administrative status for this object. The state can be set when required.
                "
            ::= { hwEntityStateEntry 1 }
        
        hwEntityOperStatus OBJECT-TYPE
            SYNTAX HwOperState
            MAX-ACCESS read-only
            STATUS current
            DESCRIPTION
                "The operational state for this object. "
            ::= { hwEntityStateEntry 2 }
        
        hwEntityStandbyStatus OBJECT-TYPE
            SYNTAX HwStandbyStatus
            MAX-ACCESS read-only
            STATUS current
            DESCRIPTION
                "Some entities of a device support the standby mode.
                 This object is used for monitoring the standby status. "
            ::= { hwEntityStateEntry 3 }
        
        hwEntityAlarmLight OBJECT-TYPE
            SYNTAX HwAlarmStatus
            MAX-ACCESS read-only
            STATUS current
            DESCRIPTION
                "The alarm status for this entity. It does not include
                 the severity of alarms generated on sub components. There is an alarm LED on the entity. 
                 The object must be in the same state with it."
            ::= { hwEntityStateEntry 4 }
        
        hwEntityCpuUsage OBJECT-TYPE
            SYNTAX Integer32 (0..100)
            MAX-ACCESS read-only
            STATUS current
            DESCRIPTION
                "The CPU usage for this entity. Generally, the CPU usage 
                is the overall CPU usage of the entity and it 
                is not sensible with the number of CPUs of the entity.
                Range: 0-100
                "
            ::= { hwEntityStateEntry 5 }
        
        hwEntityCpuUsageThreshold OBJECT-TYPE
            SYNTAX Integer32 (0..100)
            MAX-ACCESS read-write
            STATUS current
            DESCRIPTION
                "The threshold for the CPU usage. When the CPU usage exceeds
                 the threshold, a notification will be sent. 
                 Range: 0-100
                "
            ::= { hwEntityStateEntry 6 }
        
        hwEntityMemUsage OBJECT-TYPE
            SYNTAX Integer32 (0..100)
            MAX-ACCESS read-only
            STATUS current
            DESCRIPTION
                "The memory usage of the entity. This object indicates
                the memory usage. 
                Range: 0-100
                "
            ::= { hwEntityStateEntry 7 }
        
        hwEntityMemUsageThreshold OBJECT-TYPE
            SYNTAX Integer32 (0..100)
            MAX-ACCESS read-write
            STATUS current
            DESCRIPTION
                "The threshold for the memory usage. When the memory usage 
                exceeds the threshold, a notification will be sent. 
                Range: 0-100
                "
            ::= { hwEntityStateEntry 8 }
        
        hwEntityMemSize OBJECT-TYPE
            SYNTAX Integer32
            UNITS "bytes"
            MAX-ACCESS read-only
            STATUS current
            DESCRIPTION
                "The size of memory of the entity. 
                 Unit: bytes
                "
            ::= { hwEntityStateEntry 9 }
        
        hwEntityUpTime OBJECT-TYPE
            SYNTAX Integer32
            UNITS "seconds"
            MAX-ACCESS read-only
            STATUS current
            DESCRIPTION
                "The up time of the entity. When the entity is up, the value of the object 
                 is added one per second while the entity is running. 
                 Unit: second
                "
            ::= { hwEntityStateEntry 10 }
        
        hwEntityTemperature OBJECT-TYPE
            SYNTAX Integer32
            MAX-ACCESS read-only
            STATUS current
            DESCRIPTION
                " The temperature for the entity. The value 0X7FFFFFF indicates invalid temperature. "
            ::= { hwEntityStateEntry 11 }
        
        hwEntityTemperatureThreshold OBJECT-TYPE
            SYNTAX Integer32
            MAX-ACCESS read-write
            STATUS current
            DESCRIPTION
                "The threshold for the temperature. When the temperature
                 exceeds the threshold, a notification will be sent. "
            ::= { hwEntityStateEntry 12 }
        
        hwEntityVoltage OBJECT-TYPE
            SYNTAX Integer32
            MAX-ACCESS read-only
            STATUS current
            DESCRIPTION
                " The voltage of the entity. "
            ::= { hwEntityStateEntry 13 }
        
        hwEntityVoltageLowThreshold OBJECT-TYPE
            SYNTAX Integer32
            MAX-ACCESS read-write
            STATUS current
            DESCRIPTION
                "The low-threshold for the voltage. Generally, there are two 
                 thresholds for the voltage. One is low-threshold and the other
                 is high-threshold. The normal voltage must be
                 greater than the low-threshold and lower than the high-threshold.
                 When the voltage is lower than the low-threshold, a notification
                 will be sent. "
            ::= { hwEntityStateEntry 14 }
        
        hwEntityVoltageHighThreshold OBJECT-TYPE
            SYNTAX Integer32
            MAX-ACCESS read-write
            STATUS current
            DESCRIPTION
                "The high-threshold for the voltage. there are two 
                 thresholds for the voltage. One is low-threshold and the other
                 is high-threshold. The normal voltage must be
                 greater than the low-threshold and lower than the high-threshold.
                 When the voltage is greater than the high-threshold, a notification
                 will be sent. "
            ::= { hwEntityStateEntry 15 }
            
        hwEntityTemperatureLowThreshold OBJECT-TYPE
            SYNTAX Integer32
            MAX-ACCESS read-write
            STATUS current
            DESCRIPTION
                "The low-threshold of temperature. If the temperature of the device is 
                 lower than the threshold, an alarm is generated. "
            ::= { hwEntityStateEntry 16 }
            
        hwEntityOpticalPower OBJECT-TYPE
            SYNTAX Integer32
            MAX-ACCESS read-only
            STATUS current
            DESCRIPTION
                "The optical power of the optical module.
                 Unit: uW"
            ::= { hwEntityStateEntry 17 }      
              
        hwRUModuleInfoTable OBJECT-TYPE
            SYNTAX SEQUENCE OF HwRUModuleInfoEntry
            MAX-ACCESS not-accessible
            STATUS current
            DESCRIPTION
                "This table contains one row per replaceable unit physical entity.
                The index of this table is entPhysicalIndex.The row with the field 'entPhysicalIsFRU' 
                sets to 'true' in table 'entPhysicalTable' will be mapped to one row in this 
                table."
            ::= { hwEntityState 2 }
        
        hwRUModuleInfoEntry OBJECT-TYPE
            SYNTAX HwRUModuleInfoEntry
            MAX-ACCESS not-accessible
            STATUS current
            DESCRIPTION
                "This table contains one row per replaceable unit physical entity.
                The index of this entry is entPhysicalIndex.The row with the field 'entPhysicalIsFRU' 
                sets to 'true' in table 'entPhysicalTable' will be mapped to one row in this 
                table."    	
            INDEX { entPhysicalIndex }
        	::= { hwRUModuleInfoTable 1 }
    
    	HwRUModuleInfoEntry ::=
	        SEQUENCE 
	        	{ 
	            hwEntityBomId
	                SnmpAdminString,
	            hwEntityBomEnDesc
	                SnmpAdminString,
	            hwEntityBomLocalDesc
	                SnmpAdminString,
	            hwEntityManufacturedDate
	                DateAndTime,
	            hwEntityManufactureCode
	                Integer32,
	            hwEntityCLEICode
	                SnmpAdminString,
	            hwEntityUpdateLog
	                SnmpAdminString,
	            hwEntityArchivesInfoVersion
	                SnmpAdminString,
	            hwEntityOpenBomId
	                SnmpAdminString,
	            hwEntityIssueNum
	                SnmpAdminString,
	            hwEntityBoardType
	                SnmpAdminString
	            }

        hwEntityBomId OBJECT-TYPE
            SYNTAX SnmpAdminString
            MAX-ACCESS read-only
            STATUS current
            DESCRIPTION
                "The identity of the Bill of Material about the replaceable 
                 unit that is coded by a vendor. This leaf is mapped to 'ITEM' 
                 in the information file.
                "
            ::= { hwRUModuleInfoEntry 1 }
        
        hwEntityBomEnDesc OBJECT-TYPE
            SYNTAX SnmpAdminString
            MAX-ACCESS read-only
            STATUS current
            DESCRIPTION
                "The English description of the Bill of Material about the 
                 replaceable unit.
                "
            ::= { hwRUModuleInfoEntry 2 }
        
        hwEntityBomLocalDesc OBJECT-TYPE
            SYNTAX SnmpAdminString
            MAX-ACCESS read-only
            STATUS obsolete
            DESCRIPTION
                "The local description of the Bill of Material about the 
                 replaceable unit.
                "
            ::= { hwRUModuleInfoEntry 3 }
        
        hwEntityManufacturedDate OBJECT-TYPE
            SYNTAX DateAndTime
            MAX-ACCESS read-only
            STATUS current
            DESCRIPTION
                "The date when this physical entity is manufactured.
                "
            ::= { hwRUModuleInfoEntry 4 }
        
        hwEntityManufactureCode OBJECT-TYPE
            SYNTAX Integer32
            MAX-ACCESS read-only
            STATUS obsolete
            DESCRIPTION
                "The code of the place where this physical entity is manufactured.
                "
            ::= { hwRUModuleInfoEntry 5 }
        
        hwEntityCLEICode OBJECT-TYPE
            SYNTAX SnmpAdminString
            MAX-ACCESS read-only
            STATUS current
            DESCRIPTION
                "The string code of CLEI which is granted by America.
                "
            ::= { hwRUModuleInfoEntry 6 }
        
        hwEntityUpdateLog OBJECT-TYPE
            SYNTAX SnmpAdminString
            MAX-ACCESS read-only
            STATUS obsolete
            DESCRIPTION
                "The maintenance log of the replaceable unit.
                "
            ::= { hwRUModuleInfoEntry 7 }
        
        hwEntityArchivesInfoVersion OBJECT-TYPE
            SYNTAX SnmpAdminString
            MAX-ACCESS read-only
            STATUS current
            DESCRIPTION
                "The version of archives information.
                "
            ::= { hwRUModuleInfoEntry 8 }
        
        hwEntityOpenBomId OBJECT-TYPE
            SYNTAX SnmpAdminString
            MAX-ACCESS read-only
            STATUS current
            DESCRIPTION
                "The BOM Id for distribution. It is different from hwEntityBomId."
            ::= { hwRUModuleInfoEntry 9 }
        
        hwEntityIssueNum OBJECT-TYPE
            SYNTAX SnmpAdminString
            MAX-ACCESS read-only
            STATUS current
            DESCRIPTION
                "The issue number for hardware change."
            ::= { hwRUModuleInfoEntry 10 }
        
        hwEntityBoardType OBJECT-TYPE
            SYNTAX SnmpAdminString
            MAX-ACCESS read-only
            STATUS current
            DESCRIPTION
                "The type code for entity."
            ::= { hwRUModuleInfoEntry 11 }
            
       hwEntityPhysicalSpecTable OBJECT IDENTIFIER  
       
       		::= { hwEntityExtObjects 2 }
      
       hwEntityPhysicalSpecRack OBJECT-TYPE
            SYNTAX Integer32
            MAX-ACCESS read-only
            STATUS current
            DESCRIPTION
                "The rack coefficient used for calculating the index of the physical entity. "
            ::= { hwEntityPhysicalSpecTable 1 }
            
       hwEntityPhysicalSpecFrame OBJECT-TYPE
           SYNTAX Integer32
           MAX-ACCESS read-only
           STATUS current
           DESCRIPTION
               "The frame coefficient used for calculating the index of the physical entity. "
           ::= { hwEntityPhysicalSpecTable 2 }
            
       hwEntityPhysicalSpecSlot OBJECT-TYPE
           SYNTAX Integer32
           MAX-ACCESS read-only
           STATUS current
           DESCRIPTION
               "The slot coefficient used for calculating the index of the physical entity. "
            ::= { hwEntityPhysicalSpecTable 3 }

       hwEntityPhysicalSpecBoard OBJECT-TYPE
           SYNTAX Integer32
           MAX-ACCESS read-only
           STATUS current
           DESCRIPTION
               "The board coefficient used for calculating the index of the physical entity. "
           ::= { hwEntityPhysicalSpecTable 4 }
 
       hwEntityPhysicalSpecSubSlot OBJECT-TYPE
           SYNTAX Integer32
           MAX-ACCESS read-only
           STATUS current
           DESCRIPTION
               "The sub slot coefficient used for calculating the index of the physical entity. "
           ::= { hwEntityPhysicalSpecTable 5 }

       hwEntityPhysicalSpecSubBoard OBJECT-TYPE
           SYNTAX Integer32
           MAX-ACCESS read-only
           STATUS current
           DESCRIPTION
               "The sub board coefficient used for calculating the index of the physical entity. "
           ::= { hwEntityPhysicalSpecTable 6 }

       hwEntityPhysicalSpecPort OBJECT-TYPE
           SYNTAX Integer32
           MAX-ACCESS read-only
           STATUS current
           DESCRIPTION
               "The port coefficient used for calculating the index of the physical entity.  "
           ::= { hwEntityPhysicalSpecTable 7 }
           
       hwEntityPhysicalSpecEmu OBJECT-TYPE
           SYNTAX Integer32
           MAX-ACCESS read-only
           STATUS current
           DESCRIPTION
               "The EMU(Environment monitoring unit) coefficient used for calculating the index of the physical entity.  "
           ::= { hwEntityPhysicalSpecTable 8 }    
           
       hwEntityPhysicalSpecPowerframe OBJECT-TYPE
           SYNTAX Integer32
           MAX-ACCESS read-only
           STATUS current
           DESCRIPTION
               "The power frame coefficient used for calculating the index of the physical entity.  "
           ::= { hwEntityPhysicalSpecTable 9 }    
           
       hwEntityPhysicalSpecPowermodule OBJECT-TYPE
           SYNTAX Integer32
           MAX-ACCESS read-only
           STATUS current
           DESCRIPTION
               "The power module coefficient used for calculating the index of the physical entity.  "
           ::= { hwEntityPhysicalSpecTable 10 }   
           
       hwEntityPhysicalSpecBattery OBJECT-TYPE
           SYNTAX Integer32
           MAX-ACCESS read-only
           STATUS current
           DESCRIPTION
               "The battery coefficient used for calculating the index of the physical entity.  "
           ::= { hwEntityPhysicalSpecTable 11 } 
               
-- Notifications
-- 
        hwEntityExtTraps OBJECT IDENTIFIER 
        
        	::= { hwEntityExtentMIB 2 }
        
        hwEntityExtTrapsPrefix OBJECT IDENTIFIER 
        
        	::= { hwEntityExtTraps 0 }
        
        hwEntityExtTemperatureThresholdNotification NOTIFICATION-TYPE
            OBJECTS 
            { 
            hwEntityTemperature, 
            hwEntityTemperatureThreshold, 
            hwEntityAdminStatus, 
            hwEntityAlarmLight
            }
            STATUS current
            DESCRIPTION 
                "hwEntityEnvTemperatureThresholdNotification
                 indicates that the temperature exceeds the threshold.
                 In this case, a user must check the hardware and the 
                 environment of the entity. Sometimes this fault happens due to the failture of air-condition. Anyway, the threshold
                 must be lower than the threshold so that most services run normally. "
                
            ::= { hwEntityExtTrapsPrefix 1 }
        
        hwEntityExtVoltageLowThresholdNotification NOTIFICATION-TYPE
            OBJECTS 
            { 
            hwEntityVoltage, 
            hwEntityVoltageLowThreshold, 
            hwEntityAdminStatus, 
            hwEntityAlarmLight 
            }
            STATUS current
            DESCRIPTION 
                "hwEntityExtVoltageLowThresholdNotification indicates that
                 the voltage is lower than the threshold. This may decrease
                 the usability of the entity. If the voltage is lower
                 than the required value of hardware, the entity will stop working. 
                 Anyway, the threshold must be higher than the threshold so that 
                 most services run normally. "  
                
            ::= { hwEntityExtTrapsPrefix 2 }
        
        hwEntityExtVoltageHighThresholdNotification NOTIFICATION-TYPE
            OBJECTS 
            { 
            hwEntityVoltage, 
            hwEntityVoltageHighThreshold, 
            hwEntityAdminStatus, 
            hwEntityAlarmLight 
            }
            STATUS current
            DESCRIPTION 
                "hwEntityExtVoltageHighThresholdNotification indicates that
                 the voltage is higher than the threshold. This may decrease
                 the usability of the entity. If the voltage is higher than the required value of hardware, the entity may be damaged by the high
                 voltage. Anyway, the threshold must be lower than the threshold so that 
                 most services run normally. "   
                
            ::= { hwEntityExtTrapsPrefix 3 }
        
        hwEntityExtCpuUsageThresholdNotfication NOTIFICATION-TYPE
            OBJECTS 
            { 
            hwEntityCpuUsage, 
            hwEntityCpuUsageThreshold, 
            hwEntityTemperature, 
            hwEntityTemperatureThreshold,
            hwEntityAdminStatus, 
            hwEntityAlarmLight 
            }
            STATUS current
            DESCRIPTION 
                "hwEntityExtCpuUsageThresholdNotfication indicates that 
                 the entity is overloaded. In this case, the services carried by the entity
                 does not as perform well as it should due to the CPU's 
                 performance. Anyway, the threshold must be lower than the specified 
                 value so that most services work normally. "  
                
            ::= { hwEntityExtTrapsPrefix 4 }
        
        hwEntityExtMemUsageThresholdNotification NOTIFICATION-TYPE
            OBJECTS 
            { 
            hwEntityMemUsage, 
            hwEntityMemUsageThreshold, 
            hwEntityMemSize, 
            hwEntityAdminStatus, 
            hwEntityAlarmLight
            }
            STATUS current
            DESCRIPTION 
                "hwEntityExtMemUsageThresholdNotification indicates that the entity is overloaded. In this case, the services carried by the entity
                 does not as perform well as it should due to lower 
                 memory. Anyway, the threshold must be lower than the specified 
                 value so that most services work normally. "  
                
            ::= { hwEntityExtTrapsPrefix 5 }
        
        hwEntityExtOperEnabled NOTIFICATION-TYPE
            OBJECTS 
            { 
            hwEntityAdminStatus, 
            hwEntityAlarmLight
            }
            STATUS current
            DESCRIPTION 
                "The entity is operational. The entity of this
                 notification reference can be identified by
                 extracting entPhysicalIndex from one of the
                 variable bindings." 
                
            ::= { hwEntityExtTrapsPrefix 6 }
        
        hwEntityExtOperDisabled NOTIFICATION-TYPE
            OBJECTS 
            { 
            hwEntityAdminStatus,
            hwEntityAlarmLight 
            }
            STATUS current
            DESCRIPTION 
                "The entity is operational. The entity of this
                 notification reference can be identified by
                 extracting entPhysicalIndex from one of the
                 variable bindings." 
                
            ::= { hwEntityExtTrapsPrefix 7 }
        
-- Conformance and Compliance
-- 
        hwEntityExtConformance OBJECT IDENTIFIER 
        	::= { hwEntityExtentMIB 3 }
        
        hwEntityExtCompliances OBJECT IDENTIFIER 
        	::= { hwEntityExtConformance 1 }
        
-- this module
        hwEntityExtCompliance MODULE-COMPLIANCE
            STATUS current
            DESCRIPTION 
                "The compliance statement for systems to support
                 the HUAWEI entity extent MIB."
            MODULE -- this module
            MANDATORY-GROUPS { hwEntityExtGroup }
            OBJECT hwEntityAdminStatus
                MIN-ACCESS read-only
                DESCRIPTION 
                    "Write access is not required."
            OBJECT hwEntityCpuUsageThreshold
                MIN-ACCESS read-only
                DESCRIPTION 
                    "Write access is not required."
            OBJECT hwEntityMemUsageThreshold
                MIN-ACCESS read-only
                DESCRIPTION 
                    "Write access is not required."
            OBJECT hwEntityTemperatureThreshold
                MIN-ACCESS read-only
                DESCRIPTION 
                    "Write access is not required."
            OBJECT hwEntityVoltageLowThreshold
                MIN-ACCESS read-only
                DESCRIPTION 
                    "Write access is not required."
            OBJECT hwEntityVoltageHighThreshold
                MIN-ACCESS read-only
                DESCRIPTION 
                    "Write access is not required."
            ::= { hwEntityExtCompliances 1 }
        
        hwEntityExtGroups OBJECT IDENTIFIER 
        	::= { hwEntityExtConformance 2 }
        
        hwEntityExtGroup OBJECT-GROUP
            OBJECTS 
            { 
            hwEntityAdminStatus,
            hwEntityOperStatus,
            hwEntityStandbyStatus, 
            hwEntityAlarmLight, 
            hwEntityCpuUsage, 
       	    hwEntityCpuUsageThreshold, 
       	    hwEntityMemUsage, 
       	    hwEntityMemUsageThreshold, 
       	    hwEntityMemSize, 
       	    hwEntityUpTime, 
       	    hwEntityTemperature, 
       	    hwEntityTemperatureThreshold, 
       	    hwEntityVoltage, 
       	    hwEntityVoltageLowThreshold,
       	    hwEntityVoltageHighThreshold,
       	    hwEntityTemperatureLowThreshold, 
       	    hwEntityOpticalPower 
            }
            STATUS current
            DESCRIPTION 
                "Standard HUAWEI entity extent group."
            ::= { hwEntityExtGroups 1 }
        
        hwEntityExtNotificationGroup NOTIFICATION-GROUP
            NOTIFICATIONS 
            { 
            hwEntityExtTemperatureThresholdNotification, 
            hwEntityExtVoltageLowThresholdNotification, 
            hwEntityExtVoltageHighThresholdNotification, 
            hwEntityExtCpuUsageThresholdNotfication, 
            hwEntityExtMemUsageThresholdNotification, 
            hwEntityExtOperEnabled,
            hwEntityExtOperDisabled 
            }
            STATUS current
            DESCRIPTION 
                "Standard HUAWEI entity extent notification group."
            ::= { hwEntityExtGroups 2 }
        
        hwRUModuleInfoGroup OBJECT-GROUP
            OBJECTS 
            { 
            hwEntityBomId, 
            hwEntityBomEnDesc, 
            hwEntityManufacturedDate, 
            hwEntityCLEICode, 
            hwEntityArchivesInfoVersion, 
            hwEntityOpenBomId, 
            hwEntityIssueNum, 
            hwEntityBoardType
            }
            STATUS current
            DESCRIPTION 
                "Standard HUAWEI entity extent group."
            ::= { hwEntityExtGroups 3 }
        
        hwEntityExtOldObjectsGroup OBJECT-GROUP
            OBJECTS 
            { 
            hwEntityBomLocalDesc, 
            hwEntityManufactureCode, 
            hwEntityUpdateLog 
            }
            STATUS obsolete
            DESCRIPTION 
                "Group for old objects that may be obsolete."
            ::= { hwEntityExtGroups 4 }
        
    
    END

--
-- HUAWEI-ENTITY-EXTENT-MIB.mib
--
