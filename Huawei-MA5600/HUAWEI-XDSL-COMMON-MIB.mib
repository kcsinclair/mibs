-- ============================================================================
-- Copyright (C) 2012 by  HUAWEI TECHNOLOGIES. All rights reserved.
-- Description:  This MIB is used for defining Huawei's XDSL common management MIB 
--               objects, which provides XDSL management NMS interfaces.
-- Reference:  
-- Version: V1.10
-- ============================================================================

    HUAWEI-XDSL-COMMON-MIB DEFINITIONS ::= BEGIN
        IMPORTS                         
            ifIndex                 
                FROM IF-MIB                     
            ifType
                FROM RFC1213-MIB        
             hwFrameIndex, hwSlotIndex,hwSubslotIndex,hwPortIndex,hwConfigChangeIP
                FROM HUAWEI-DEVICE-MIB                                  
            Integer32, Unsigned32, Gauge32, Counter32, OBJECT-TYPE, NOTIFICATION-TYPE, MODULE-IDENTITY              
                FROM SNMPv2-SMI                                                                         
            RowStatus, PhysAddress, DateAndTime,TEXTUAL-CONVENTION  
                FROM SNMPv2-TC
            huaweiUtility
                FROM HUAWEI-MIB
            hwAlarmId,hwAlarmTime,hwAlarmSn,hwCauseId,hwTrapType
                FROM HUAWEI-TC-MIB;                      
                
        hwXdslCommon MODULE-IDENTITY
           LAST-UPDATED "201306260000Z"
            ORGANIZATION "Huawei Technologies Co.,Ltd."
            CONTACT-INFO                                        
                         "Huawei Industrial Base                
                          Bantian, Longgang                     
                          Shenzhen 518129                       
                          People's Republic of China            
                          Website: http://www.huawei.com        
                          Email: support@huawei.com             
                         "                                      
            DESCRIPTION  "This MIB is used for defining Huawei's XDSL common management MIB objects,
                          which provides XDSL management NMS interfaces.
                         "     
	 --  Revision history
	   REVISION     "201306260000Z"
	   DESCRIPTION  "V1.10, Add leaf node hwXdslPortFrequentRetrainControlState, hwXdslPortFrequentRetrainControlRemainingTime
	   		 in table hwXdslPortFrequentRetrainControlTable for getting frequent retrain state.
	                "
	                
	   REVISION     "201209021000Z"
	   DESCRIPTION  "V1.09, Add the definition of the table hwXdslADSL1INPAdaptionConfig.
	                "
	 
	   REVISION     "201207021000Z"
	   DESCRIPTION  "V1.08, Add the definition of the table hwXdslPortFrequentRetrainControlTable.
	                 Add the definition of the table hwXdslAttndrConfig.
	                "
	   
	   REVISION     "201105030000Z"                                                 
           DESCRIPTION  "V1.07, add value shdslLineConfProfile(31), shdslAlarmConfProfile(32), vopINMConfProf(33) for 
                         hwXdslAutoDeleteProfUnusedProfType and modify the description.
                        "
	   REVISION     "201009300000Z"                                                 
           DESCRIPTION  "V1.06, add leaf node hwXdslSeltTestStartResult in table hwAdslTrapsVbOids for trap optimization.
                         Add the definition of the trap node: hwXdslSeltStartResultTrap.
                       " 

           REVISION     "201009150000Z"
           DESCRIPTION  "V1.05, add leaf node hwAllChActDataRateUs, hwAllChActDataRateDs
                         for the sum of net date rates that all bearer channels operating at.
                        "
			 
	   REVISION     "201008160000Z"                                                 
           DESCRIPTION  "V1.04, Modify data type of hwXdslDynamicCollectTime for trap notify."	   

	   REVISION     "201007270000Z"                                                 
           DESCRIPTION  "V1.03, Add the definition of the trap node: hwAdslProfIDChangeTrap, hwXdslAutoDeactivateLackLicensesAlarmTrap, hwXdslPortActRateLowerThresholdAlarmTrap.
                         Add leaf node hwAdslProfIDType, hwXdslProfName, hwXdslPortActualUpRate, hwXdslPortActualDownRate 
			 in table hwAdslTrapsVbOids for trap optimization.
                         Add the definition of the trap node: hwXdslProfDeleteTrap.
                         Add leaf node hwXdslDelProfIndex, hwXdslProfName, hwXdslPortActualUpRate, hwXdslPortActualDownRate 
			 in table hwAdslTrapsVbOids for trap optimization."
                          
            REVISION     "201003250000Z"                                                 
            DESCRIPTION  "V1.02, add leaf node hwXdslAutoDeleteProfUnusedProfType, hwvdslAutoDeleteProfUnusedOperType
                          for deleting unused profile.
                         "     
                         
            REVISION     "201003110000Z"                                                 
            DESCRIPTION  "V1.01, add the MIB for xDSL common use.
                         "          
                                                                                                                                         
            REVISION     "201001240000Z"                                                 
            DESCRIPTION  "V1.00, Initial version."                                        
                                   
            ::= { huaweiUtility 148 }     
    
        hwXdslCommonMib OBJECT IDENTIFIER ::= { hwXdslCommon 1 }
        hwXdslAutoDeleteProfUnused OBJECT IDENTIFIER ::= { hwXdslCommonMib 1 }      
        hwXdslAttndrConfig OBJECT IDENTIFIER ::= { hwXdslCommonMib 4 } 
        hwXdslADSL1INPAdaptionConfig OBJECT IDENTIFIER ::= { hwXdslCommonMib 5 }       
        hwXdslTrapsVbOids OBJECT IDENTIFIER ::= { hwXdslCommon 2 }      
        hwXdslTraps  OBJECT IDENTIFIER ::= { hwXdslCommon 3 }           
        hwXdslCommonTraps  OBJECT IDENTIFIER ::= { hwXdslTraps 1 }          
        hwXdslCommonTrapsPrefix  OBJECT IDENTIFIER ::= { hwXdslCommonTraps 0 }
        hwXdslAlarmTraps  OBJECT IDENTIFIER ::= { hwXdslTraps 2 }
        hwXdslAlarmTrapsPrefix  OBJECT IDENTIFIER ::= { hwXdslAlarmTraps 0 }
    
 -- hwXdslCommonMib

        hwXdslAutoDeleteProfUnusedProfType   OBJECT-TYPE        
            SYNTAX INTEGER        
                {        
                vdsl2LineConfTemplate(1),        
                vdsl2LineConfProf(2), 
                vdsl2ChConfProfile(3), 
                vdsl2LineAlarmConfTemplate(4), 
                vdsl2LineAlarmConfProfile(5), 
                vdsl2ChAlarmConfProfile(6), 
                vdsl2ServProf(7), 
                vdsl2SpectrumProf(8), 
                vdsl2DpboProf(9), 
                vdsl2UpboProf(10), 
                vdsl2NoiseMarginProf(11), 
                vdsl2DelayInpProf(12), 
                vopDataRateConfProf(13), 
                vopLineSpectrumConfProf(14), 
                vopUPBOConfProf(15), 
                vopDPBOConfProf(16), 
                vopRFIConfProf(17), 
                vopSNRMarginConfProf(18), 
                vopINPDelayConfProf(19), 
                vopVirtualNoiseConfProf(20), 
                vopModeSpecificPSDConfProf(21),
                adsl2LineConfTemplate(22),                        
                adsl2LineConfProf(23),               
                adsl2ChConfProfile(24),               
                adsl2LineAlarmConfTemplate(25),       
                adsl2LineAlarmConfProfile(26),        
                adsl2ChAlarmConfProfile(27),          
                adslLineConfProfile(28),     
                adslLineAlarmConfProfile(29),
                adslLineExtConfProfile(30),
                shdslLineConfProfile(31),
                shdslAlarmConfProfile(32),
                vopINMConfProf(33), 
                invalidValue(-1)        
                }        
            MAX-ACCESS  read-write        
            STATUS      current        
            DESCRIPTION        
                "The profile type of deleting unused XDSL profile.
                 Options:
                 1. vdsl2LineConfTemplate(1)        - Vdsl line template
                 2. vdsl2LineConfProf(2)            - Vdsl line profile
                 3. vdsl2ChConfProfile(3)           - Vdsl channel profile
                 4. vdsl2LineAlarmConfTemplate(4)   - Vdsl line alarm template
                 5. vdsl2LineAlarmConfProfile(5)    - Vdsl line alarm profile
                 6. vdsl2ChAlarmConfProfile(6)      - Vdsl channel alarm profile
                 7. vdsl2ServProf(7)                - Vdsl service profile (TI mode)
                 8. vdsl2SpectrumProf(8)            - Vdsl spectrum profile (TI mode)
                 9. vdsl2DpboProf(9)                - Vdsl DPBO profile (TI mode)
                 10. vdsl2UpboProf(10)              - Vdsl UPBO profile (TI mode)
                 11. vdsl2NoiseMarginProf(11)       - Vdsl noise-margin profile (TI mode)
                 12. vdsl2DelayInpProf(12)          - Vdsl delay-inp profile (TI mode)
                 13. vopDataRateConfProf(13)        - Xdsl data rate profile (TR165 mode)
                 14. vopLineSpectrumConfProf(14)    - Xdsl line spectrum profile (TR165 mode)
                 15. vopUPBOConfProf(15)            - Xdsl UPBO profile (TR165 mode)
                 16. vopDPBOConfProf(16)            - Xdsl DPBO profile (TR165 mode)
                 17. vopRFIConfProf(17)             - Xdsl RFI profile (TR165 mode)
                 18. vopSNRMarginConfProf(18)       - Xdsl SNR margin profile (TR165 mode)
                 19. vopINPDelayConfProf(19)        - Xdsl INP delay profile (TR165 mode)
                 20. vopVirtualNoiseConfProf(20)    - Xdsl virtual noise profile (TR165 mode)
                 21. vopModeSpecificPSDConfProf(21) - Xdsl mode specific PSD profile (TR165 mode)
                 22. adsl2LineConfTemplate(22)      - Adsl line template (RFC4706 mode)
                 23. adsl2LineConfProf(23)          - Adsl line profile (RFC4706 mode)
                 24. adsl2ChConfProfile(24)         - Adsl channel profile (RFC4706 mode)
                 25. adsl2LineAlarmConfTemplate(25) - Adsl line alarm template (RFC4706 mode)
                 26. adsl2LineAlarmConfProfile(26)  - Adsl line alarm profile (RFC4706 mode)
                 27. adsl2ChAlarmConfProfile(27)    - Adsl channel alarm profile (RFC4706 mode)
                 28. adslLineConfProfile(28)        - Adsl line profile (RFC2662 mode)
                 29. adslLineAlarmConfProfile(29)   - Adsl line alarm profile (RFC2662 mode)
                 30. adslLineExtConfProfile(30)     - Adsl line ext profile (RFC2662 mode)
                 31. shdslLineConfProfile(31)       - Shdsl line profile
                 32. shdslAlarmConfProfile(32)      - Shdsl alarm profile
                 33. vopINMConfProf(33)             - Xdsl INM profile (TR165 mode)
                 34. invalidValue(-1)               - Invalid value
                "        
           
            ::= { hwXdslAutoDeleteProfUnused 1 }       
    
        hwXdslAutoDeleteProfUnusedOperType  OBJECT-TYPE                           
            SYNTAX INTEGER                                       
                {                                                    
                first(1),                                            
                all(2),
                invalidValue(-1)                                               
                }                                                    
            MAX-ACCESS  read-write                               
            STATUS      current                                  
            DESCRIPTION                                          
                "The operation type of deleting unused xDSL profile.
                 Options:
                 1. first(1)         - Delete the first unused xDSL profile
                 2. all(2)           - Delete all the unused xDSL profile
                 3. invalidValue(-1) - Invalid value 
                "                    
                                                         
            ::= { hwXdslAutoDeleteProfUnused 2 }   
            
            
        hwXdslLineTable  OBJECT-TYPE
            SYNTAX      SEQUENCE  OF  HwXdslLineEntry
            MAX-ACCESS  not-accessible
            STATUS      current
            DESCRIPTION
                "The table hwXdslLineTable contains status
 	         parameters of xDSL line. The index of this table is
 	         ifIndex.
                "
            ::= { hwXdslCommonMib 2 }
        
        hwXdslLineEntry  OBJECT-TYPE
            SYNTAX      HwXdslLineEntry
            MAX-ACCESS  not-accessible
            STATUS      current
            DESCRIPTION
                "The table hwXdslLineTable contains status
 	         parameters of xDSL line. The index of this entry is ifIndex.
                "
            INDEX  { ifIndex }
            ::= { hwXdslLineTable 1 }
        
        HwXdslLineEntry  ::=
            SEQUENCE {
              hwAllChActDataRateDs            Unsigned32,
              hwAllChActDataRateUs            Unsigned32  
            }
        
        hwAllChActDataRateDs  OBJECT-TYPE
            SYNTAX      Unsigned32
            UNITS       "bits/second"
            MAX-ACCESS  read-only
            STATUS      current
            DESCRIPTION
                "The downstream actual net data rate that the bearer channel is operating
                 at, if in L0 power management state.  In L1 or L2 states, it
                 relates to the previous L0 state. This is the sum of net date rates 
                 that all bearer channels operating at. 
                "
            ::= { hwXdslLineEntry 1 }
        
        hwAllChActDataRateUs  OBJECT-TYPE
            SYNTAX      Unsigned32
            UNITS       "bits/second"
            MAX-ACCESS  read-only
            STATUS      current
            DESCRIPTION
                "The upstream actual net data rate that the bearer channel is operating
                 at, if in L0 power management state.  In L1 or L2 states, it
                 relates to the previous L0 state. This is the sum of net date rates 
                 that all bearer channels operating at.  
                "
            ::= { hwXdslLineEntry 2 }   

        hwXdslPortFrequentRetrainControlTable  OBJECT-TYPE
            SYNTAX      SEQUENCE  OF  HwXdslPortFrequentRetrainControlEntry
            MAX-ACCESS  not-accessible
            STATUS      current
            DESCRIPTION
                "The table hwXdslPortFrequentRetrainControlTable contains information
 	         of xDSL port frequent retrain control policy. 
 	         The index of this table is ifIndex.
                "
            ::= { hwXdslCommonMib 3 }
        
        hwXdslPortFrequentRetrainControlEntry  OBJECT-TYPE
            SYNTAX      HwXdslPortFrequentRetrainControlEntry
            MAX-ACCESS  not-accessible
            STATUS      current
            DESCRIPTION
                "The table hwXdslPortFrequentRetrainControlTable contains information
 	         of xDSL port frequent retrain control policy. 
 	         The index of this entry is ifIndex.
                "
            INDEX  { ifIndex }
            ::= { hwXdslPortFrequentRetrainControlTable 1 }
        
        HwXdslPortFrequentRetrainControlEntry  ::=
            SEQUENCE {
              hwXdslPortFrequentRetrainControlTimes          Unsigned32,
              hwXdslPortFrequentRetrainControlPolicy         INTEGER,
              hwXdslPortFrequentRetrainControlPostponedTime  Unsigned32,
              hwXdslPortFrequentRetrainControlState          INTEGER,
              hwXdslPortFrequentRetrainControlRemainingTime  Unsigned32
            }
            
        hwXdslPortFrequentRetrainControlTimes  OBJECT-TYPE
            SYNTAX      Unsigned32 (3..15 | 4294967295)
            MAX-ACCESS  read-write
            STATUS      current
            DESCRIPTION
                "The times that xDSL port frequent retrain.  
                 The invalid value is 4294967295. 
                 If board does not support the operation, the invalid value will be returned.
                "
            DEFVAL    { 5 }
            ::= { hwXdslPortFrequentRetrainControlEntry 1 } 
            
        hwXdslPortFrequentRetrainControlPolicy  OBJECT-TYPE
            SYNTAX      INTEGER
            {       
            lock(1),
            nolimit(2),
            postponed(3),
            invalidValue(-1)  
            }
            MAX-ACCESS  read-write
            STATUS      current
            DESCRIPTION
                "The control policy that xDSL port frequent retrain.
                 Options: 
                 1. lock(1)            - The port is not allowed to go online within 15 minutes
                 2. nolimit(2)         - The port can go online without the limitation of control policies
                 3. postponed(3)       - The port can go online after a postponed time when the number of frequent
                                         resynchronizations on the port reaches the threshold
                 4. invalidValue(-1)   - Invalid value
                "
            DEFVAL    { nolimit }
            ::= { hwXdslPortFrequentRetrainControlEntry 2 } 
            
        hwXdslPortFrequentRetrainControlPostponedTime  OBJECT-TYPE
            SYNTAX      Unsigned32 (5..3600 | 4294967295)
            UNITS       "minute"
            MAX-ACCESS  read-write
            STATUS      current
            DESCRIPTION
                "The postponed time when control policy of xDSL port frequent retrain is postponed.  
                 The invalid value is 4294967295. 
                 If board does not support the operation, the invalid value will be returned.
                "
            DEFVAL    { 5 }
            ::= { hwXdslPortFrequentRetrainControlEntry 3 }           

        hwXdslPortFrequentRetrainControlState  OBJECT-TYPE
            SYNTAX      INTEGER
            {       
            controlled(1),
            not-controlled(2)
            }
            MAX-ACCESS  read-only
            STATUS      current
            DESCRIPTION
                "The actual control state of the port. 
                 When the port is allowed to active in the current interval, the value of the
                 remaining time of the current control interval must be 4294967295.
                 Options: 
                 1. controlled(1)          - The port is not allowed to active in the current interval
                 2. not-controlled(2)      - The port is allowed to active in the current interval
                "
            ::= { hwXdslPortFrequentRetrainControlEntry 4 } 
            
        hwXdslPortFrequentRetrainControlRemainingTime  OBJECT-TYPE
            SYNTAX      Unsigned32 (0..3600 | 4294967295)
            UNITS       "minute"
            MAX-ACCESS  read-only
            STATUS      current
            DESCRIPTION
                "The remaining time of the current control interval, a special value 4294967295 indicates
                 there is no limit for the link currently.
                "
            ::= { hwXdslPortFrequentRetrainControlEntry 5 }             
            
        hwXdslAttndrMethod  OBJECT-TYPE
            SYNTAX  INTEGER
            {       
            attndrMethod0(0),
            attndrMethod1(1),
            attndrMethod2(2)
            }
            MAX-ACCESS  read-write
            STATUS      current
            DESCRIPTION
                "This parameter specifies the method to be used for the calculation of the ATTNDR 
                 in the downstream and upstream direction. The parameter can take three values 0, 1 and 2. 
                 Options: 
                 1. attndrMethod0(0)       - The basic Attainable Net Data Rate method
                 2. attndrMethod1(1)       - The improved Attainable Net Data Rate method, If the control 
                                             parameter attndr_method is set to a value of 1, the VTU-O and 
                                             VTU-R shall use the impulse noise protection limit INP_min0 with 
                                             value as indicated in O-TPS. If O-TPS configures for dual bearer 
                                             channel mode, then the highest INP_MINn over the bearer channels 
                                             shall be used 1
                 3. attndrMethod2(2)       - The improved Attainable Net Data Rate method, If the control parameter 
                                             attndr_method is set to a value of 2, the VTU-O and VTU-R shall use an 
                                             impulse noise protection limit INP_MIN0 = 0
                "
            REFERENCE    "ITU-T G.993.2, paragraph 11.4.1.1.7"
            ::= { hwXdslAttndrConfig 1 }
            
        hwXdslADSL1INPAdaption  OBJECT-TYPE
            SYNTAX  INTEGER
            {       
            enable(1),       
            disable(2)  
            }
            MAX-ACCESS  read-write
            STATUS      current
            DESCRIPTION
                "Enable/Disable the global ADSL1 INP Adaption configuration. This object is defaulted disable(2).
                 This configuration will take effect after port manually reactivated or board reset. 
                 Options: 
                 1. enable(1)        - Enable the ADSL1 INP Adaption configuration
                 2. disable(2)       - Disable the ADSL1 INP Adaption configuration
                "
            ::= { hwXdslADSL1INPAdaptionConfig 1 }       
                      
     -- Vboids           
        hwXdslDynamicCollectResult OBJECT-TYPE
            SYNTAX  INTEGER 
                {   
                noFail(0),
                memFull(1),
                otherCause(2)
                }
            MAX-ACCESS accessible-for-notify
            STATUS current
            DESCRIPTION
                "Dynamic information collecting result.
                 Options:
                 1. noFail(0)     - The dynamic info has been collected successful
                 2. memFull(1)    - The memory used for dynamic info collecting is full
                 3. otherCause(2) - Other collect failure reason
                "
            ::= { hwXdslTrapsVbOids 1 }  
    
        hwXdslDynamicCollectTime OBJECT-TYPE
            SYNTAX  DateAndTime
            MAX-ACCESS  accessible-for-notify
            STATUS     current
            DESCRIPTION                             
                "Time of the Dynamic information file."
            ::= { hwXdslTrapsVbOids 2 }
    
        hwXdslRequestID OBJECT-TYPE
            SYNTAX Integer32
            MAX-ACCESS accessible-for-notify
            STATUS current
            DESCRIPTION
                "Request ID."
            ::= { hwXdslTrapsVbOids 3 }
    
        hwXdslSeltCompleteResult OBJECT-TYPE
            SYNTAX INTEGER 
                {   
                success(1),
                fail(2)
                }
            MAX-ACCESS accessible-for-notify
            STATUS current
            DESCRIPTION
                "Selt test complete result.
                 Options:
                 1. success(1) - Selt test is successful
                 2. fail(2)    - Failed in selt test
                "
        ::= { hwXdslTrapsVbOids 4 }
        
        hwAdslProfIDType OBJECT-TYPE
            SYNTAX INTEGER 
                {   
                lineTemplate(1),
                alarmTemplate(2),
                extProfile(3)
                }
            MAX-ACCESS accessible-for-notify
            STATUS current
            DESCRIPTION
                "Type of the adsl template ID.
                 Options:
                 1. lineTemplate(1)  - Indicates line template ID
                 2. alarmTemplate(2) - Indicates alarm template ID
                 3. extProfile(3)    - Indicates ext profile ID
                "
            ::= { hwXdslTrapsVbOids 5 }
            
        hwXdslProfName OBJECT-TYPE
            SYNTAX OCTET STRING (SIZE (1..32))
            MAX-ACCESS accessible-for-notify
            STATUS current
            DESCRIPTION
                "The name of the XDSL profile."
            ::= { hwXdslTrapsVbOids 6}         
                   
        hwXdslPortActualUpRate OBJECT-TYPE
            SYNTAX Unsigned32
            MAX-ACCESS accessible-for-notify
            STATUS current
            DESCRIPTION
                "Xdsl port actual upstream rate."
            ::= { hwXdslTrapsVbOids 7}
              
        hwXdslPortActualDownRate OBJECT-TYPE
            SYNTAX Unsigned32
            MAX-ACCESS accessible-for-notify
            STATUS current
            DESCRIPTION
                "Xdsl port actual downstream rate."
            ::= { hwXdslTrapsVbOids 8}

        hwXdslDelProfIndex OBJECT-TYPE
            SYNTAX Unsigned32
            MAX-ACCESS accessible-for-notify
            STATUS current
            DESCRIPTION
                     "Index of the profile which is deleted.
                      If you delete all the profiles unused, this parameter will be 0xffffffff."
             ::= { hwXdslTrapsVbOids 9}

        hwXdslDelProfName OBJECT-TYPE
            SYNTAX OCTET STRING (SIZE (0..128))
            MAX-ACCESS accessible-for-notify
            STATUS current
            DESCRIPTION
                     "Name of the profile which is deleted.
                      If you delete all the profiles unused, this parameter will be a zero string."
             ::= { hwXdslTrapsVbOids 10}

    
        hwXdslSeltTestStartResult OBJECT-TYPE                        
            SYNTAX INTEGER 
                {   
                normal(1),
                failed(2)
                }                                        
            MAX-ACCESS accessible-for-notify                         
            STATUS current                                           
            DESCRIPTION                                              
                     "XDSL selt test start result.                 
                      Options:                                       
                      1. normal(1) - This notification indicates that a SELT task has been started successfully
                      2. failed(2) - This notification indicates that a SELT task failed to be started
                     "
             ::= { hwXdslTrapsVbOids 11 }                            

-- common trap        
        hwXdslDynamicCollectInfoTrap NOTIFICATION-TYPE
            OBJECTS 
                {
                hwXdslDynamicCollectResult,
                hwFrameIndex,
                hwSlotIndex,
                hwXdslDynamicCollectTime
                }
            STATUS current
            DESCRIPTION
                "XDSL dynamic collect trap.
                 This trap message is generated when XDSL dynamic collected.
                "
            ::= { hwXdslCommonTraps 0 1 }
    
        hwXdslSeltCompleteResultTrap NOTIFICATION-TYPE
            OBJECTS 
                {
                hwXdslRequestID,
                hwXdslSeltCompleteResult
                }
            STATUS current
            DESCRIPTION
                "Selt test complete result trap.
                 This trap message is generated when selt test completed.
                "
            ::= { hwXdslCommonTraps 0 2 }
        hwAdslProfIDChangeTrap NOTIFICATION-TYPE
            OBJECTS 
                {
                hwConfigChangeIP,
                hwAdslProfIDType,
                ifIndex,
                hwXdslProfName
                }
            STATUS current
            DESCRIPTION
                "Adsl profile ID change trap.
                 This trap message is generated when adsl profile ID changed.
                "
            ::= { hwXdslCommonTraps 0 3 }        
        hwXdslProfDeleteTrap NOTIFICATION-TYPE
            OBJECTS {
                       hwConfigChangeIP,
                       hwXdslAutoDeleteProfUnusedProfType,
                       hwXdslAutoDeleteProfUnusedOperType,
                       hwXdslDelProfIndex,
                       hwXdslDelProfName
    	            }
            STATUS current
            DESCRIPTION
                   "This trap message is generated when Xdsl unused profile trap deleted."
            ::= { hwXdslCommonTraps 0 4 }
            
        hwXdslSeltStartResultTrap NOTIFICATION-TYPE
             OBJECTS {
                     hwXdslSeltTestStartResult,
                     hwXdslRequestID
    	             }
        STATUS current
        DESCRIPTION 
            "XDSL selt test start trap.
             This notification indicates trap when xDSL selt test start.
            "
        ::= { hwXdslCommonTraps 0 5 }     

     -- alarm trap
        hwXdslAutoDeactivateLackLicensesAlarmTrap NOTIFICATION-TYPE
            OBJECTS 
                {
                hwFrameIndex,
                hwSlotIndex
                } 
            STATUS current
            DESCRIPTION
                "This trap message is generated when some xDSL ports or all the xDSL ports 
                 are automatically deactivated due to lack of licenses."
            ::= { hwXdslAlarmTraps 0 1 }
                  
        hwXdslPortActRateLowerThresholdAlarmTrap  NOTIFICATION-TYPE
            OBJECTS 
                {
                hwFrameIndex,
                hwSlotIndex,
                hwPortIndex,
                hwXdslPortActualDownRate,
                hwXdslPortActualUpRate
                } 
            STATUS current
            DESCRIPTION 
                "This trap message is generated when the activation rate 
                 of the xDSL line is lower than the threshold."
            ::= { hwXdslAlarmTraps 0 2 }
 
        END
