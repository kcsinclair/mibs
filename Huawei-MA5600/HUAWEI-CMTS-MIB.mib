-- ================================================================= 
-- Copyright (C) 2013 by HUAWEI TECHNOLOGIES. All rights reserved    
-- Description:  The mib is used for defining huawei's CMTS           
--               management in distributing mode MIB objects.                                     
-- Reference: 
-- Version: V1.11
-- ================================================================  


       HUAWEI-CMTS-MIB DEFINITIONS ::= BEGIN
       IMPORTS
           MODULE-IDENTITY, mib-2, OBJECT-TYPE, Counter32, Counter64,
           Unsigned32, Integer32, Gauge32, NOTIFICATION-TYPE, IpAddress
               FROM SNMPv2-SMI
           TruthValue, DateAndTime, RowStatus, MacAddress,TEXTUAL-CONVENTION, DisplayString
               FROM SNMPv2-TC
           ifIndex, InterfaceIndex, InterfaceIndexOrZero
               FROM IF-MIB
           docsIfCmtsModIndex, docsIfCmtsModIntervalUsageCode
                         FROM DOCS-IF-MIB
           docsIf3CmtsCmRegStatusId, docsIf3CmtsCmUsStatusChIfIndex
               FROM DOCS-IF3-MIB
           docsLoadbal3GeneralGrpCfgNodeName
               FROM DOCS-LOADBAL3-MIB
           MODULE-COMPLIANCE, OBJECT-GROUP
               FROM SNMPv2-CONF
           SnmpAdminString
               FROM SNMP-FRAMEWORK-MIB
           OwnerString, EntryStatus
               FROM RMON-MIB
           huaweiUtility
               FROM HUAWEI-MIB
           hwFrameIndex, hwSlotIndex, hwPortIndex, hwConfigChangeIP
               FROM HUAWEI-DEVICE-MIB
           docsIfDownChannelId, docsIfUpChannelId
               FROM DOCS-IF-MIB
           ifAdminStatus, ifOperStatus
               FROM HUAWEI-TC-MIB
           InetAddressType,InetAddress,InetAddressPrefixLength,InetPortNumber
               FROM INET-ADDRESS-MIB;
                 
   hwCmtsMIB MODULE-IDENTITY
            LAST-UPDATED "201306160000Z"
            ORGANIZATION "Huawei Technologies co.,Ltd."
            CONTACT-INFO
                "Floor 5 ,Block 4, R&D Building,
                Huawei Longgang Production Base,
                Shenzhen,  P.R.C.
                http://www.huawei.com
                Zip:518129
                Email:support@huawei.com
                "
            DESCRIPTION
                "The mib is used for defining huawei's CMTS management in distributing mode MIB objects.
                "
--  Revision history

       REVISION     "201306160000Z"
       DESCRIPTION  "V1.11, Added the following leaves for hwDocsIf3CmtsCmRegStatusTable: hwDocsIf3CmtsCmRegStatusGoodCodeWords, hwDocsIf3CmtsCmRegStatusGoodCodeWords,
                    hwDocsIf3CmtsCmRegStatusUncorrectedErrorCodeWords, hwDocsIf3CmtsCmRegStatusValue, hwDocsIf3CmtsCmCtrlOperStatus, hwDocsIf3CmtsCmRegStatusRemoteQuery.
                    hwDocsIf3CmtsCmRegStatusPrimaryDsRxPower, hwDocsIf3CmtsCmRegStatusPrimaryDsSnr, hwDocsIf3CmtsCmRegStatusSysDesc, hwDocsIf3CmtsCmRegStatusPortIfIndex, 
                    hwDocsIf3CmtsCmRegStatusPrimaryUsTxTimingOffset, hwDocsIf3CmtsCmRegStatusOfflineTime, hwDocsIf3CmtsCmRegStatusPreviousStatusValue.
                    Added the following leaves for hwDocsIf3CmtsCmUsStatusTable: hwDocsIf3CmtsCmUsGoodCodewords, hwDocsIf3CmtsCmUsCorrectedErrorCodewords,
                    hwDocsIf3CmtsCmUsUncorrectedErrorCodewords��hwDocsIf3CmtsCmRegStatusPrimaryUs, hwDocsIf3CmtsCmRegStatusPrimaryUsRxPower, hwDocsIf3CmtsCmUsStatusTxTimingOffset
                    hwDocsIf3CmtsCmRegStatusPrimaryUsTxPower, hwDocsIf3CmtsCmRegStatusPrimaryDsTxPower, hwDocsIf3CmtsCmRegStatusPrimaryUsSnr.
                    Added the following leaves for hwCmtsUpChannelTable: hwCmtsUpChannelMaxDataRate, hwCmtsUpChannelRealTimeDataRate, hwCmtsUpChannel20CmDataRateSum, hwCmtsUpChannel30CmDataRateSum.
                    Added the table of hwCmtsDownChannelTable.
                    Added the following leaves for hwCmtsUpChannelCurrTable: hwCmtsUpChannelCurr15MStartTime, hwCmtsUpChannelCurr15MElapsedTime,
                    hwCmtsUpChannelCurr1DayStartTime, hwCmtsUpChannelCurr1DayElapsedTime.
                    Added the following leaves for hwCmtsChannelHist15MinTable: hwCmtsUpChannelHist15MStartTime, hwCmtsUpChannelHist15MElapsedTime, hwCmtsUpChannelHist15MValidityFlag.
                    Added the following leaves for hwCmtsUpChannelHist1DayTable: hwCmtsUpChannelHist1DayStartTime, hwCmtsUpChannelHist1DayElapsedTime, hwCmtsUpChannelHist1DayValidityFlag.
                    Added the following tables for CMTS: hwCmtsSysCfgTable,hwCmtsSnrDetectTable, hwCmtsCmCurrTable, hwCmtsCmHist15MinTable, hwDocsIf3CmtsCmCpeStatTable,
                    hwCmtsCmHist1DayTable hwCmtsCmStatThresholdTable, hwDocsIfCmtsIPToCmTable, hwCmtsMtaInfoTable, hwDocsIfUpstreamChannelStatusTable, hwCmtsLoadBalanceTable.
                    Added the following leaves for hwDocsIf3CmtsCmRegStatusTable: hwDocsIf3CmtsCmRegStatusValue, hwDocsIf3CmtsCmCtrlOperStatus, hwDocsIf3CmtsCmRegStatusRemoteQuery.
                    Added  hwDocsIf3CmtsCmRemoteQueryTrap, hwCmtsMassUnstableConnCmNum, hwCmtsMassOfflineCmNum and hwcmtsTrapsVbOids for CMTS. 
                    Added the following leaves for hwCmtsSpectrumGroupTable:
                    hwCmtsSpectrumGroupSecondaryModulationType1, hwCmtsSpectrumGroupSecondaryModulationType2,
                    hwCmtsSpectrumGroupChannelWidth, hwCmtsSpectrumGroupFirstSnr, hwCmtsSpectrumGroupSecondSnr,
                    hwCmtsSpectrumGroupProtectPower, hwCmtsSpectrumGroupPriority.
                    Added leaves hwdocsIfUsChannelPreEqEnable and hwDocsIfUpstreamChannelRxPower in table hwdocsIfUpstreamChannelTable.
                    Added leaf hwdocsLoadbal3GeneralGrpInitTech in table hwdocsLoadbal3GeneralGrpCfgTable.
                    Modify leaf hwdocsIfUsChanneHopReset in hwdocsIfUpstreamChannelTable.
                    Delete the value of these leaves:hwCmtsSpectrumGroupId,hwdocsIfUsChanneSpectrumGroupId.
                    Added the table of hwCmtsCmNumSummaryTable, hwDocsIfDownstreamChannelTable.
                    Added leaf hwDocsIf3CmtsCmCpeInfoDeviceDesc in table hwDocsIf3CmtsCmCpeInfoTable.
                    Modify the description of the leaf node hwCmtsCmRegRemoteStatus
                    Added the following leaves for hwDocsIf3CmtsCmDownChannelInfoTable: hwDocsIf3CmtsCmDownChannelInfoSnr, hwDocsIf3CmtsCmDownChannelInfoRxPower,"

       REVISION     "201304150000Z"
       DESCRIPTION  "V1.10, Added the unit of node hwCmtsUpChannelSnr.
                     Add the table of hwCmtsAdmissionCtrlTable."

       REVISION     "201303300000Z"
       DESCRIPTION  "V1.09, Add object hwCmtsTrafficBurstConfigObject for traffic burst.
                     Add leaf hwCmtsTrafficBurstUpstreamEnable in object hwCmtsTrafficBurstConfigObject.
                     Add leaf hwCmtsTrafficBurstDownstreamEnable in object hwCmtsTrafficBurstConfigObject."

       REVISION     "201303210000Z"
       DESCRIPTION  "V1.08, Added the following tables for CMTS: hwCmtsCmOverCapaTable, hwCmtsAdmissionCtrlTypeTable,
                     hwCmtsAdmissionCtrlMappingTable, hwCmtsAdmissionCtrlPortBandwidthTable, hwCmtsAdmissionCtrlChannelBandwidthTable,
                     hwCmtsAdmissionCtrlStatisticsTable, hwCmtsMtaBasicTable."

       REVISION     "201303190000Z"
       DESCRIPTION  "V1.07, Add table hwPacketcableGateInfoTable and hwPacketcableGateStatisticsTable for PacketCable.
                     Add hwPacketCable1DotxSwitch, hwPacketCableMultimediaSwitch, hwPacketCableAuthorizeCommonMtaSwitch,
                     hwPacketCableMaxGateCount, hwPacketCable1DotxTimerT0, hwPacketCable1DotxTimerT1,
                     hwPacketCableMultimediaTimerT1, hwPacketCable1dotxSendSubscriberID in object hwPacketCableObject."

       REVISION     "201301310000Z"
       DESCRIPTION  "V1.06, Added the following table for CMTS: hwCmtsSpectrumGroupTable, hwdocsIfUpstreamChannelTable,
                     hwDocsIf3CmtsCmRegStatusTable, hwDocsIf3CmtsCmUsStatusTable, hwDocsIf3CmtsCmDownChannelInfoTable,
                     and hwDocsIf3CmtsCmCpeInfoTable."

       REVISION     "201302250000Z"
       DESCRIPTION  "V1.05, Added description of hwDocsCableModemMaxCpeNum."

       REVISION     "201212250000Z"
       DESCRIPTION  "V1.04, Added hwCmtsTraps objects."

       REVISION     "201212010000Z"
       DESCRIPTION  "V1.03, Added hwCmtsCfgTable to config tftp proxy option for CMTS."

       REVISION     "201211140000Z"
       DESCRIPTION  "V1.02, Added the following node for CMTS: hwDocsCableSchedulePriorityMappingMask, hwDocsCableModemMaxCpeNum."

       REVISION     "201207120000Z"
       DESCRIPTION  "V1.00, Initial version."
       ::= { huaweiUtility 180 }

   hwCmtsObjectMIB OBJECT IDENTIFIER ::= { hwCmtsMIB 1}
   hwCmtsTraps     OBJECT IDENTIFIER ::= { hwCmtsMIB 2 }
   hwcmtsTrapsVbOids      OBJECT IDENTIFIER ::= { hwCmtsMIB 3 }

   hwCmtsObject OBJECT IDENTIFIER ::= { hwCmtsObjectMIB  1}

   hwdocsIfCmtsTraps OBJECT IDENTIFIER ::= {hwCmtsTraps 1}
   hwdocsIfCmtsCommonTraps     OBJECT IDENTIFIER ::= { hwdocsIfCmtsTraps 0 }

   -- DOCSIS 3.0 OSSI specification
   DocsisVersion ::= TEXTUAL-CONVENTION
       STATUS          current
       DESCRIPTION
           "Indicates the DOCSIS Radio Frequency specification being
            referenced.
            'docsis10' indicates DOCSIS 1.0.
            'docsis11' indicates DOCSIS 1.1.
            'docsis20' indicates DOCSIS 2.0.
            'docsis30' indicates DOCSIS 3.0."
       REFERENCE
           "DOCSIS 3.0 MAC and Upper Layer Protocols Interface
            Specification CM-SP-MULPIv3.0-I03-070223, DOCSIS
            Version section of the Common Radio Frequency
            Interface Encodings Annex."
       SYNTAX        INTEGER {
            docsis10 (1),
            docsis11 (2),
            docsis20 (3),
            docsis30 (4)
       }

    -- Table hwCmtsUpChannelCurrTable
    hwCmtsUpChannelCurrTable OBJECT-TYPE
          SYNTAX     SEQUENCE OF HwCmtsUpChannelCurrEntry
          MAX-ACCESS not-accessible
          STATUS     current
          DESCRIPTION
               "Indicates the current statistics table of a CMTS upstream channel.
               The index of this table is ifIndex."
          ::= { hwCmtsObject 1 }

    hwCmtsUpChannelCurrEntry OBJECT-TYPE
          SYNTAX     HwCmtsUpChannelCurrEntry
          MAX-ACCESS not-accessible
          STATUS     current
          DESCRIPTION
               "Indicates the current statistics table of a CMTS upstream channel.
               The index of this entry is ifIndex."
          INDEX       { ifIndex }
          ::= { hwCmtsUpChannelCurrTable 1 }

    HwCmtsUpChannelCurrEntry ::=
          SEQUENCE {
                    hwCmtsUpChannelCurr15MUnerroredCodewords         Counter64,
                    hwCmtsUpChannelCurr15MCorrectedCodewords         Counter64,
                    hwCmtsUpChannelCurr15MUncorrectableCodewords     Counter64,
                    hwCmtsUpChannelCurr1DayUnerroredCodewords        Counter64,
                    hwCmtsUpChannelCurr1DayCorrectedCodewords        Counter64,
                    hwCmtsUpChannelCurr1DayUncorrectableCodewords    Counter64,
                    hwCmtsUpChannelEverBeforeUnerroredCodewords      Counter64,
                    hwCmtsUpChannelEverBeforeCorrectedCodewords      Counter64,
                    hwCmtsUpChannelEverBeforeUncorrectableCodewords  Counter64,
                    hwCmtsUpChannelCurr15MStartTime                  DateAndTime,
                    hwCmtsUpChannelCurr15MElapsedTime                Integer32,
                    hwCmtsUpChannelCurr1DayStartTime                 DateAndTime,
                    hwCmtsUpChannelCurr1DayElapsedTime               Integer32
                  }

    hwCmtsUpChannelCurr15MUnerroredCodewords OBJECT-TYPE
          SYNTAX     Counter64
          MAX-ACCESS read-only
          STATUS     current
          DESCRIPTION
               "Total number of unerrored codewords count during current 15 minutes."
          ::= { hwCmtsUpChannelCurrEntry 1 }

    hwCmtsUpChannelCurr15MCorrectedCodewords OBJECT-TYPE
          SYNTAX     Counter64
          MAX-ACCESS read-only
          STATUS     current
          DESCRIPTION
               "Total number of corrected codewords count during current 15 minutes."
          ::= { hwCmtsUpChannelCurrEntry 2 }

    hwCmtsUpChannelCurr15MUncorrectableCodewords OBJECT-TYPE
          SYNTAX     Counter64
          MAX-ACCESS read-only
          STATUS     current
          DESCRIPTION
               "Total number of uncorrectable codewords count during current 15 minutes."
          ::= { hwCmtsUpChannelCurrEntry 3 }

    hwCmtsUpChannelCurr1DayUnerroredCodewords OBJECT-TYPE
          SYNTAX     Counter64
          MAX-ACCESS read-only
          STATUS     current
          DESCRIPTION
               "Total number of unerrored codewords count during current day."
          ::= { hwCmtsUpChannelCurrEntry 4 }

    hwCmtsUpChannelCurr1DayCorrectedCodewords OBJECT-TYPE
          SYNTAX     Counter64
          MAX-ACCESS read-only
          STATUS     current
          DESCRIPTION
               "Total number of corrected codewords count during current day."
          ::= { hwCmtsUpChannelCurrEntry 5 }

    hwCmtsUpChannelCurr1DayUncorrectableCodewords OBJECT-TYPE
          SYNTAX     Counter64
          MAX-ACCESS read-only
          STATUS     current
          DESCRIPTION
               "Total number of uncorrectable codewords count during current day."
          ::= { hwCmtsUpChannelCurrEntry 6 }

    hwCmtsUpChannelEverBeforeUnerroredCodewords OBJECT-TYPE
          SYNTAX     Counter64
          MAX-ACCESS read-only
          STATUS     current
          DESCRIPTION
               "Total number of unerrored codewords count everbefore."
          ::= { hwCmtsUpChannelCurrEntry 7 }

    hwCmtsUpChannelEverBeforeCorrectedCodewords OBJECT-TYPE
          SYNTAX     Counter64
          MAX-ACCESS read-only
          STATUS     current
          DESCRIPTION
               "Total number of corrected codewords count everbefore."
          ::= { hwCmtsUpChannelCurrEntry 8 }

    hwCmtsUpChannelEverBeforeUncorrectableCodewords OBJECT-TYPE
          SYNTAX     Counter64
          MAX-ACCESS read-only
          STATUS     current
          DESCRIPTION
               "Total number of uncorrectable codewords count everbefore."
          ::= { hwCmtsUpChannelCurrEntry 9 }

   hwCmtsUpChannelCurr15MStartTime OBJECT-TYPE
          SYNTAX  DateAndTime
          MAX-ACCESS  read-only
          STATUS  current
          DESCRIPTION
                "
                Indicates the start time of the current 15-minute statistical period.
                "
          ::= { hwCmtsUpChannelCurrEntry 10 }


    hwCmtsUpChannelCurr15MElapsedTime OBJECT-TYPE
          SYNTAX  Integer32
          MAX-ACCESS  read-only
          STATUS  current
          DESCRIPTION
                "
                Indicates the elapsed time in the current 15-minute statistical period.
                Unit: s.
                "
          ::= { hwCmtsUpChannelCurrEntry 11 }

    hwCmtsUpChannelCurr1DayStartTime OBJECT-TYPE
          SYNTAX  DateAndTime
          MAX-ACCESS  read-only
          STATUS  current
          DESCRIPTION
                "
                Indicates the start time of the current 24-hour statistical period.
                "
          ::= { hwCmtsUpChannelCurrEntry 12 }


    hwCmtsUpChannelCurr1DayElapsedTime OBJECT-TYPE
          SYNTAX  Integer32
          MAX-ACCESS  read-only
          STATUS  current
          DESCRIPTION
                "
                Indicates the elapsed time in the current 24-hour statistical period.
                Unit: s.
                "
          ::= { hwCmtsUpChannelCurrEntry 13 }


    -- Table hwCmtsChannelHist15MinTable
    hwCmtsChannelHist15MinTable OBJECT-TYPE
          SYNTAX     SEQUENCE OF HwCmtsUpChannelHist15MinEntry
          MAX-ACCESS not-accessible
          STATUS     current
          DESCRIPTION
               "Indicates the statistics table of a CMTS upstream channel during history 15 minutes.
               The indexes of this table are ifIndex and hwCmtsUpChannelHist15MInterval."
          ::= { hwCmtsObject 2 }

    hwCmtsUpChannelHist15MinEntry OBJECT-TYPE
          SYNTAX     HwCmtsUpChannelHist15MinEntry
          MAX-ACCESS not-accessible
          STATUS     current
          DESCRIPTION
               "Indicates the statistics table of a CMTS upstream channel during history 15 minutes.
               The indexes of this entry are ifIndex and hwCmtsUpChannelHist15MInterval."
          INDEX       { ifIndex, hwCmtsUpChannelHist15MInterval }
          ::= { hwCmtsChannelHist15MinTable 1 }

    HwCmtsUpChannelHist15MinEntry ::=
          SEQUENCE {
                    hwCmtsUpChannelHist15MInterval               Integer32,
                    hwCmtsUpChannelHist15MUnerroredCodewords     Counter64,
                    hwCmtsUpChannelHist15MCorrectedCodewords     Counter64,
                    hwCmtsUpChannelHist15MUncorrectableCodewords Counter64,
                    hwCmtsUpChannelHist15MStartTime              DateAndTime,
                    hwCmtsUpChannelHist15MElapsedTime            Integer32,
                    hwCmtsUpChannelHist15MValidityFlag           Integer32
                  }

    hwCmtsUpChannelHist15MInterval OBJECT-TYPE
          SYNTAX  Integer32 (1..96)
                MAX-ACCESS  not-accessible
                STATUS  current
                DESCRIPTION
               "The type of the statistics table of a CMTS upstream channel during history 15 minutes,
                this leaf is essential."
          ::= { hwCmtsUpChannelHist15MinEntry 1 }

    hwCmtsUpChannelHist15MUnerroredCodewords OBJECT-TYPE
          SYNTAX     Counter64
          MAX-ACCESS read-only
          STATUS     current
          DESCRIPTION
               "Total number of unerrored codewords count during history 15 minutes."
          ::= { hwCmtsUpChannelHist15MinEntry 2 }

    hwCmtsUpChannelHist15MCorrectedCodewords OBJECT-TYPE
          SYNTAX     Counter64
          MAX-ACCESS read-only
          STATUS     current
          DESCRIPTION
               "Total number of corrected codewords count during history 15 minutes."
          ::= { hwCmtsUpChannelHist15MinEntry 3 }

    hwCmtsUpChannelHist15MUncorrectableCodewords OBJECT-TYPE
          SYNTAX     Counter64
          MAX-ACCESS read-only
          STATUS     current
          DESCRIPTION
               "Total number of uncorrectable codewords count during history 15 minutes."
          ::= { hwCmtsUpChannelHist15MinEntry 4 }

    hwCmtsUpChannelHist15MStartTime OBJECT-TYPE
          SYNTAX  DateAndTime
          MAX-ACCESS  read-only
          STATUS  current
          DESCRIPTION
                "
                Indicates the start time of a statistical period.
                "
          ::= { hwCmtsUpChannelHist15MinEntry 5 }

    hwCmtsUpChannelHist15MElapsedTime OBJECT-TYPE
          SYNTAX  Integer32
          MAX-ACCESS  read-only
          STATUS  current
          DESCRIPTION
                "
                Indicates the elapsed time in a statistical period.
                Unit: s.
                "
          ::= { hwCmtsUpChannelHist15MinEntry 6 }

    hwCmtsUpChannelHist15MValidityFlag OBJECT-TYPE
          SYNTAX  Integer32 (1..2)
          MAX-ACCESS  read-only
          STATUS  current
          DESCRIPTION
                "
                Indicates the flag for statistical information.
                Options:
                1-Yes
                2-No
                "
          ::= { hwCmtsUpChannelHist15MinEntry 7 }

    -- Table hwCmtsUpChannelHist1DayTable
    hwCmtsUpChannelHist1DayTable OBJECT-TYPE
          SYNTAX     SEQUENCE OF HwCmtsUpChannelHist1DayEntry
          MAX-ACCESS not-accessible
          STATUS     current
          DESCRIPTION
               "Indicates the statistics table of a CMTS upstream channel during history 1 day.
               The indexes of this table are ifIndex and hwCmtsUpChannelHist1DayInterval."
          ::= { hwCmtsObject 3 }

    hwCmtsUpChannelHist1DayEntry OBJECT-TYPE
          SYNTAX     HwCmtsUpChannelHist1DayEntry
          MAX-ACCESS not-accessible
          STATUS     current
          DESCRIPTION
               "Indicates the statistics table of a CMTS upstream channel during history 1 day.
               The indexes of this entry are ifIndex and hwCmtsUpChannelHist1DayInterval."
          INDEX       { ifIndex, hwCmtsUpChannelHist1DayInterval }
          ::= { hwCmtsUpChannelHist1DayTable 1 }

    HwCmtsUpChannelHist1DayEntry ::=
          SEQUENCE {
                    hwCmtsUpChannelHist1DayInterval                Integer32,
                    hwCmtsUpChannelHist1DayUnerroredCodewords      Counter64,
                    hwCmtsUpChannelHist1DayCorrectedCodewords        Counter64,
                    hwCmtsUpChannelHist1DayUncorrectableCodewords  Counter64,
                    hwCmtsUpChannelHist1DayStartTime               DateAndTime,
                    hwCmtsUpChannelHist1DayElapsedTime             Integer32,
                    hwCmtsUpChannelHist1DayValidityFlag            Integer32
                  }

    hwCmtsUpChannelHist1DayInterval OBJECT-TYPE
          SYNTAX  Integer32 (1..30)
                MAX-ACCESS  not-accessible
                STATUS  current
                DESCRIPTION
               "The type of the statistics table of a CMTS upstream channel during history 1 day,
                this leaf is essential."
          ::= { hwCmtsUpChannelHist1DayEntry 1 }

    hwCmtsUpChannelHist1DayUnerroredCodewords OBJECT-TYPE
          SYNTAX     Counter64
          MAX-ACCESS read-only
          STATUS     current
          DESCRIPTION
               "Total number of unerrored codewords count during history 1 day."
          ::= { hwCmtsUpChannelHist1DayEntry 2 }

    hwCmtsUpChannelHist1DayCorrectedCodewords OBJECT-TYPE
          SYNTAX     Counter64
          MAX-ACCESS read-only
          STATUS     current
          DESCRIPTION
               "Total number of corrected codewords count during history 1 day."
          ::= { hwCmtsUpChannelHist1DayEntry 3 }

    hwCmtsUpChannelHist1DayUncorrectableCodewords OBJECT-TYPE
          SYNTAX     Counter64
          MAX-ACCESS read-only
          STATUS     current
          DESCRIPTION
               "Total number of uncorrectable codewords count during history 1 day."
          ::= { hwCmtsUpChannelHist1DayEntry 4 }

    hwCmtsUpChannelHist1DayStartTime OBJECT-TYPE
          SYNTAX  DateAndTime
          MAX-ACCESS  read-only
          STATUS  current
          DESCRIPTION
                "
                Indicates the start time of a statistical period.
                "
          ::= { hwCmtsUpChannelHist1DayEntry 5 }

    hwCmtsUpChannelHist1DayElapsedTime OBJECT-TYPE
          SYNTAX  Integer32
          MAX-ACCESS  read-only
          STATUS  current
          DESCRIPTION
                "
                Indicates the elapsed time in a statistical period.
                Unit: s.
                "
          ::= { hwCmtsUpChannelHist1DayEntry 6 }

    hwCmtsUpChannelHist1DayValidityFlag OBJECT-TYPE
          SYNTAX  Integer32 (1..2)
          MAX-ACCESS  read-only
          STATUS  current
          DESCRIPTION
                "
                Indicates the flag for statistical information.
                Options:
                1-Yes
                2-No
                "
          ::= { hwCmtsUpChannelHist1DayEntry 7 }

    -- Table hwCmtsUpChannelTable
    hwCmtsUpChannelTable OBJECT-TYPE
          SYNTAX     SEQUENCE OF HwCmtsUpChannelEntry
          MAX-ACCESS not-accessible
          STATUS     current
          DESCRIPTION
               "Indicates the signal quality of a CMTS upstream channel.
               The index of this table is ifIndex."
          ::= { hwCmtsObject 4 }

    hwCmtsUpChannelEntry OBJECT-TYPE
          SYNTAX     HwCmtsUpChannelEntry
          MAX-ACCESS not-accessible
          STATUS     current
          DESCRIPTION
               "Indicates the signal quality of a CMTS upstream channel.
               The index of this entry is ifIndex."
          INDEX       { ifIndex }
          ::= { hwCmtsUpChannelTable 1 }

    HwCmtsUpChannelEntry ::=
          SEQUENCE {
                    hwCmtsUpChannelContentionFlag        INTEGER,
                    hwCmtsUpChannelSnr                   Integer32,
                    hwCmtsChannelMicroReflection	       Integer32,
                    hwCmtsUpChannelMaxDataRate           Integer32,
                    hwCmtsUpChannelRealTimeDataRate         Integer32,
                    hwCmtsUpChannelModulationType        INTEGER,
                    hwCmtsUpChannel20CmDataRateSum                       Unsigned32,
                    hwCmtsUpChannel30CmDataRateSum                       Unsigned32
                  }

    hwCmtsUpChannelContentionFlag OBJECT-TYPE
          SYNTAX     INTEGER
              {
              no(0),
              yes(1)
              }
          MAX-ACCESS read-only
          STATUS     current
          DESCRIPTION
               "Status of contention intervals for an upstream channel.
               Options:
               1. no(0) - No contention interval exists
               2. yes(1) - Contention intervals exist
               "
          ::= { hwCmtsUpChannelEntry 1 }

    hwCmtsUpChannelSnr OBJECT-TYPE
          SYNTAX     Integer32
          UNITS       "0.1dB"
          MAX-ACCESS read-only
          STATUS     current
          DESCRIPTION
               "The SNR of a upstream channel."
          ::= { hwCmtsUpChannelEntry 2 }

    hwCmtsChannelMicroReflection OBJECT-TYPE
          SYNTAX     Integer32
          MAX-ACCESS read-only
          STATUS     current
          DESCRIPTION
               "The total number Micro-reflections of a upstream channel."
          ::= { hwCmtsUpChannelEntry 3 }

    hwCmtsUpChannelMaxDataRate OBJECT-TYPE
          SYNTAX     Integer32
          MAX-ACCESS read-only
          STATUS     current
          DESCRIPTION
               "The max data rate.
                Unit: Kbps
               "
          ::= { hwCmtsUpChannelEntry 4 }

    hwCmtsUpChannelRealTimeDataRate OBJECT-TYPE
          SYNTAX     Integer32
          MAX-ACCESS read-only
          STATUS     current
          DESCRIPTION
               "The real time data rate.
                Unit: Kbps"
          ::= { hwCmtsUpChannelEntry 5 }

    hwCmtsUpChannelModulationType OBJECT-TYPE
          SYNTAX     INTEGER
              {
              other(1),
              qpsk(2),
              qam16(3),
              qam8(4),
              qam32(5),
              qam64(6),
              qam128(7),
              qam256(8)
              }
          MAX-ACCESS read-only
          STATUS     current
          DESCRIPTION
               "
               The modulation type of up channel.
               Options:
               1. other(1) - Indicates the other modulation type
               2. qpsk(2) - QPSK
               3. qam16(3) - QAM16
               4. qam8(4) - QAM8
               5. qam32(5) - QAM32
               6. qam64(6) - QAM64
               7. qam128(7) - QAM128
               8. qam256(8) - QAM256
               "
          ::= { hwCmtsUpChannelEntry 6 }

    hwCmtsUpChannel20CmDataRateSum OBJECT-TYPE
          SYNTAX     Unsigned32
          MAX-ACCESS read-only
          STATUS     current
          DESCRIPTION
               "Rate sum of all DOCSIS 2.0 cable modem on the channel.
                Unit: Kbps"
          ::= { hwCmtsUpChannelEntry 7 }

    hwCmtsUpChannel30CmDataRateSum OBJECT-TYPE
          SYNTAX     Unsigned32
          MAX-ACCESS read-only
          STATUS     current
          DESCRIPTION
               "Rate sum of all DOCSIS 3.0 cable modem on the channel.
                Unit: Kbps"
          ::= { hwCmtsUpChannelEntry 8 }

    -- Table hwdocsIfCmtsModulationTable
    hwdocsIfCmtsModulationTable OBJECT-TYPE
          SYNTAX     SEQUENCE OF HwdocsIfCmtsModulationEntry
          MAX-ACCESS not-accessible
          STATUS     current
          DESCRIPTION
               "Indicates the description of a Channel Modulation profile.
               The indexes of this table are docsIfCmtsModIndex and docsIfCmtsModIntervalUsageCode."
          ::= { hwCmtsObject 5 }

    hwdocsIfCmtsModulationEntry OBJECT-TYPE
          SYNTAX     HwdocsIfCmtsModulationEntry
          MAX-ACCESS not-accessible
          STATUS     current
          DESCRIPTION
               "Indicates the description of a Channel Modulation profile.
               The indexes of this entry are docsIfCmtsModIndex and docsIfCmtsModIntervalUsageCode."
          INDEX       { docsIfCmtsModIndex, docsIfCmtsModIntervalUsageCode }
          ::= { hwdocsIfCmtsModulationTable 1 }

    HwdocsIfCmtsModulationEntry ::=
          SEQUENCE {
                    hwdocsIfCmtsModDescription        OCTET STRING
                   }

    hwdocsIfCmtsModDescription OBJECT-TYPE
          SYNTAX  OCTET STRING (SIZE (1..32))
          MAX-ACCESS  read-write
          STATUS  current
          DESCRIPTION
                "The Channel Modulation description."
          ::= { hwdocsIfCmtsModulationEntry 1 }

  -- Table hwdocsLoadbal3GeneralGrpCfgTable
    hwdocsLoadbal3GeneralGrpCfgTable OBJECT-TYPE
          SYNTAX     SEQUENCE OF HwdocsLoadbal3GeneralGrpCfgEntry
          MAX-ACCESS not-accessible
          STATUS     current
          DESCRIPTION
               "Indicates the method of a Load Balancing Group.
               The indexes of this table are ifIndex and docsLoadbal3GeneralGrpCfgNodeName."
          ::= { hwCmtsObject 6 }

    hwdocsLoadbal3GeneralGrpCfgEntry OBJECT-TYPE
          SYNTAX     HwdocsLoadbal3GeneralGrpCfgEntry
          MAX-ACCESS not-accessible
          STATUS     current
          DESCRIPTION
               "Indicates the method of a Load Balancing Group.
               The indexes of this entry are ifIndex and docsLoadbal3GeneralGrpCfgNodeName."
          INDEX       { ifIndex, docsLoadbal3GeneralGrpCfgNodeName }
          ::= { hwdocsLoadbal3GeneralGrpCfgTable 1 }

    HwdocsLoadbal3GeneralGrpCfgEntry ::=
          SEQUENCE {
                    hwdocsLoadbal3GeneralGrpMethod        INTEGER,
                    hwdocsLoadbal3GeneralGrpInitTech      BITS
                   }

    hwdocsLoadbal3GeneralGrpMethod OBJECT-TYPE
          SYNTAX  INTEGER {
                           cm(1),
                           flow(2),
                           utilization(3)
                          }
          MAX-ACCESS  read-write
          STATUS  current
          DESCRIPTION
                "The method of a Load Balancing Group.
                Options:
                1. cm(1) - Load balancing based on the number of CMs
                2. flow(2) - Load balancing based on service flow bandwidth
                3. utilization(3) - Load balancing based on the bandwidth usage of upstream channels
                Default value: 2
                "
          ::= { hwdocsLoadbal3GeneralGrpCfgEntry 1 }

    hwdocsLoadbal3GeneralGrpInitTech OBJECT-TYPE
          SYNTAX  BITS {
            reInit(0),
            broadcast(1),
            unicast(2),
            initRang(3),
            direct(4)
          }
          MAX-ACCESS  read-write
          STATUS  current
          DESCRIPTION
                "This attribute defines the load balancing initialization
                technique for the General Load Balancing Group associated with this instance.
                Options:
                0 - reinitializeMac(Reinitialize the MAC)
                1 - broadcastInitRanging(Perform broadcast initial ranging on new channel before normal operation)
                2 - unicastInitRanging(Perform unicast ranging on new channel before normal operation)
                3 - initRanging(Perform either broadcast or unicast ranging on new channel before normal operation)
                4 - direct(Use the new channel(s) directly without reinitializing or ranging)
                Default value: 1
                "
          ::= { hwdocsLoadbal3GeneralGrpCfgEntry 2 }

        hwDocsCableSchedulePriorityMappingMask OBJECT-TYPE
                SYNTAX Integer32 (0..125239296)
                MAX-ACCESS read-write
                STATUS current
                DESCRIPTION
                       "The mapping mask of schedule type (RTPS, UGS-AD, UGS) and priority of 802.1p of upstream.
                        Each four bits of mask defines the priority of one schedule type:
                        0000 0110 0101 0100 0000 0000 0000 0000
                        7     6    5    4    3    2    1   0
                        Definition of schedule type:
                        0-3, reserved
                        4, RTPS
                        5, UGS-AD
                        6, UGS
                        7, reserved
                        Definition of 802.1p priority: 0~7
                        Default: 106168320
                        "
                ::= { hwCmtsObject 7 }

        hwDocsCableModemMaxCpeNum OBJECT-TYPE
                SYNTAX  Unsigned32 (0..4294967295)
                MAX-ACCESS read-write
                STATUS current
                DESCRIPTION
                       "The max CPE number on CM of CMTS.
                        The range of max CPE is 1 to 8.
                        4294967295 indicates no limit on the max CPE number.
                        "
                ::= { hwCmtsObject 8 }

    -- Table hwCmtsCfgTable
    hwCmtsCfgTable OBJECT-TYPE
          SYNTAX     SEQUENCE OF HwCmtsCfgEntry
          MAX-ACCESS not-accessible
          STATUS     current
          DESCRIPTION
               "The CMTS configration table.
                The index of this table is ifIndex."
          ::= { hwCmtsObject 9 }

    hwCmtsCfgEntry OBJECT-TYPE
          SYNTAX     HwCmtsCfgEntry
          MAX-ACCESS not-accessible
          STATUS     current
          DESCRIPTION
               "The CMTS configration table.
                The index of this entry is ifIndex."
          INDEX       { ifIndex }
          ::= { hwCmtsCfgTable 1 }

    HwCmtsCfgEntry ::=
          SEQUENCE {
                    hwCmtsProxyOption    INTEGER,
                    hwCmtsAuthKey        OCTET STRING
                   }

    hwCmtsProxyOption OBJECT-TYPE
          SYNTAX  INTEGER
              {
                  none(1),
                  mac(2),
                  ip(3)
              }
          MAX-ACCESS  read-write
          STATUS  current
          DESCRIPTION
                "
                Tftp proxy option. This attribute instructs the CMTS to insert the source
                IP address and/or MAC address of received TFTP packets into the TFTP option
                fields before forwarding the packets to the Config File server.
                Options:
                1. none(1) - With none TFTP option
                2. mac(2) - TFTP option with MAC address
                3. ip(3) -  TFTP option with IP address
                Default value: none(1)
                "
          ::= { hwCmtsCfgEntry 1 }

    hwCmtsAuthKey OBJECT-TYPE
          SYNTAX  OCTET STRING (SIZE (1..80))
          MAX-ACCESS  read-write
          STATUS  current
          DESCRIPTION
                "MIC authentication key.The key must be plain text consists of 8 to 80 characters.
                 Set the key to 0 means delete the current authentication key.
                "
          ::= { hwCmtsCfgEntry 2 }

    -- Table hwCmtsLoadBalanceTable begin
    hwCmtsLoadBalanceTable OBJECT-TYPE
          SYNTAX     SEQUENCE OF HwCmtsLoadBalanceEntry
          MAX-ACCESS not-accessible
          STATUS     current
          DESCRIPTION
               "The CMTS load balance parameter config table.
               The index of this table is ifIndex."
          ::= { hwCmtsObject 10 }

    hwCmtsLoadBalanceEntry OBJECT-TYPE
          SYNTAX     HwCmtsLoadBalanceEntry
          MAX-ACCESS not-accessible
          STATUS     current
          DESCRIPTION
               "The CMTS load balance parameter config table.
               The index of this entry is ifIndex."
          INDEX       { ifIndex }
          ::= { hwCmtsLoadBalanceTable 1 }

    HwCmtsLoadBalanceEntry ::=
          SEQUENCE {
                    hwCmtsLoadBalanceMaxMoveModems        Integer32,
                    hwCmtsLoadBalanceTriggerThreshold     Integer32,
                    hwCmtsLoadBalanceDifferenceThreshold  Integer32,
                    hwCmtsLoadBalanceCMMoveInterval       Integer32,
                    hwCmtsLoadBalanceNumofPeriod          Integer32
                   }

    hwCmtsLoadBalanceMaxMoveModems OBJECT-TYPE
          SYNTAX  Integer32 (1..32)
                MAX-ACCESS  read-write
                STATUS  current
                DESCRIPTION
               "Indicates maximum number of CMs adjusting to different channels during a period.
                Default value:32"
          ::= { hwCmtsLoadBalanceEntry 1 }

    hwCmtsLoadBalanceTriggerThreshold OBJECT-TYPE
          SYNTAX  Integer32 (1..100)
                MAX-ACCESS  read-write
                STATUS  current
                DESCRIPTION
               "Indicates the threshold for the channel bandwidth usage that triggers load balancing.
                Default value:60"
          ::= { hwCmtsLoadBalanceEntry 2 }


    hwCmtsLoadBalanceDifferenceThreshold OBJECT-TYPE
          SYNTAX  Integer32 (1..100)
                MAX-ACCESS  read-write
                STATUS  current
                DESCRIPTION
               "Indicates the threshold for channel bandwidth usage difference.
               Default value:10"
          ::= { hwCmtsLoadBalanceEntry 3 }

    hwCmtsLoadBalanceCMMoveInterval OBJECT-TYPE
          SYNTAX  Integer32 (60..86400)
                MAX-ACCESS  read-write
                STATUS  current
                DESCRIPTION
                "Indicates the minimum interval for CM adjusting to different channel.
                 Default value:240"
          ::= { hwCmtsLoadBalanceEntry 4 }

    hwCmtsLoadBalanceNumofPeriod OBJECT-TYPE
          SYNTAX  Integer32 (1..4)
                MAX-ACCESS  read-write
                STATUS  current
                DESCRIPTION
               "Indicates the period number for calculating the channel bandwidth usage.
                Default value:2"
          ::= { hwCmtsLoadBalanceEntry 5 }
    -- Table hwCmtsLoadBalanceTable  end

    hwCmtsAccessObject OBJECT IDENTIFIER ::= { hwCmtsObject  20}

    -- Table hwCmtsSpectrumGroupTable
    hwCmtsSpectrumGroupTable OBJECT-TYPE
          SYNTAX     SEQUENCE OF HwCmtsSpectrumGroupEntry
          MAX-ACCESS not-accessible
          STATUS     current
          DESCRIPTION
               "Indicates the configuration of a Spectrum Group.
               The index of this table is hwCmtsSpectrumGroupId."
          ::= { hwCmtsAccessObject 1 }

    hwCmtsSpectrumGroupEntry OBJECT-TYPE
          SYNTAX     HwCmtsSpectrumGroupEntry
          MAX-ACCESS not-accessible
          STATUS     current
          DESCRIPTION
               "Indicates the configuration of a Spectrum Group.
               The index of this entry is hwCmtsSpectrumGroupId."
          INDEX       { hwCmtsSpectrumGroupId }
          ::= { hwCmtsSpectrumGroupTable 1 }

    HwCmtsSpectrumGroupEntry ::=
          SEQUENCE {
                    hwCmtsSpectrumGroupId                   Integer32,
                    hwCmtsSpectrumGroupFrequencyList        OCTET STRING,
                    hwCmtsSpectrumGroupErrorCodeThreshold   Integer32,
                    hwCmtsSpectrumGroupHopPeriod            Integer32,
                    hwCmtsSpectrumGroupRowstatus            RowStatus,
                    hwCmtsSpectrumGroupSecondaryModulationType1     Integer32,
                    hwCmtsSpectrumGroupSecondaryModulationType2    Integer32,
                    hwCmtsSpectrumGroupChannelWidth                 Integer32,
                    hwCmtsSpectrumGroupFirstSnr                     Integer32,
                    hwCmtsSpectrumGroupSecondSnr                    Integer32,
                    hwCmtsSpectrumGroupProtectPower                 Integer32,
                    hwCmtsSpectrumGroupPriority                     Integer32

                   }

    hwCmtsSpectrumGroupId OBJECT-TYPE
          SYNTAX  Integer32
          MAX-ACCESS  not-accessible
          STATUS  current
          DESCRIPTION
                "The index of a Spectrum Group.
                -1 represent that the group id will be assigned by the host automatically."
          ::= { hwCmtsSpectrumGroupEntry 1 }

    hwCmtsSpectrumGroupFrequencyList OBJECT-TYPE
          SYNTAX  OCTET STRING (SIZE(0..35))
          MAX-ACCESS  read-write
          STATUS  current
          DESCRIPTION
                "The frequency list of a Spectrum Group.
                 It can contain as most as 4 frequencies.
                 Every 8 octets represent a frequency,
                 (,) used to indicate a separation of the different frequencies.
                 Only when set operation -1 represent that the frequency list are not assigned.
                 Range: 5000000-65000000 for AnnexA
                        5000000-42000000 for AnnexB
                 Unit: Hz
                "
          ::= { hwCmtsSpectrumGroupEntry 2 }

    hwCmtsSpectrumGroupErrorCodeThreshold OBJECT-TYPE
          SYNTAX  Integer32 (1..100)
          MAX-ACCESS  read-write
          STATUS  current
          DESCRIPTION
                "The threshold of a upstream channel average error code ratio
                 for the Spectrum Group.
                 Range: 1-100
                 Default: 5
                 Unit: %
                 "
          ::= { hwCmtsSpectrumGroupEntry 3 }

    hwCmtsSpectrumGroupHopPeriod OBJECT-TYPE
          SYNTAX  Integer32 (900..86400)
          MAX-ACCESS  read-write
          STATUS  current
          DESCRIPTION
                "The hop frequency period of the Spectrum Group.
                 Range: 900-86400
                 Default: 1800
                 Unit: s
                 "
          ::= { hwCmtsSpectrumGroupEntry 4 }

    hwCmtsSpectrumGroupRowstatus OBJECT-TYPE
          SYNTAX  RowStatus
          MAX-ACCESS  read-write
          STATUS  current
          DESCRIPTION
                "The row status of a Spectrum Group."
          ::= { hwCmtsSpectrumGroupEntry 5 }

    hwCmtsSpectrumGroupSecondaryModulationType1 OBJECT-TYPE
          SYNTAX  Integer32 (-1|1..16)
          MAX-ACCESS  read-write
          STATUS  current
          DESCRIPTION
                "The first standby modulation of a Spectrum Group.
                -1 represent that the modulation are not assigned."
          ::= { hwCmtsSpectrumGroupEntry 6 }

    hwCmtsSpectrumGroupSecondaryModulationType2 OBJECT-TYPE
          SYNTAX  Integer32 (-1|1..16)
          MAX-ACCESS  read-write
          STATUS  current
          DESCRIPTION
                "The second standby modulation of a Spectrum Group.
                -1 represent that the modulation are not assigned."
          ::= { hwCmtsSpectrumGroupEntry 7 }

    hwCmtsSpectrumGroupChannelWidth OBJECT-TYPE
          SYNTAX  Integer32 (-1|0..6400000)
          UNITS   "Hz"
          MAX-ACCESS  read-write
          STATUS  current
          DESCRIPTION
                "The channel width of a Spectrum Group.
                Only three width values are supported currently.
                -1 represent that the channel width is not assigned.
                Options:
                1600000,3200000,6400000"
          ::= { hwCmtsSpectrumGroupEntry 8 }

    hwCmtsSpectrumGroupFirstSnr OBJECT-TYPE
          SYNTAX  Integer32 (5..35)
          UNITS   "dB"
          MAX-ACCESS  read-write
          STATUS  current
          DESCRIPTION
                "The first snr threshold of a Spectrum Group.
                The first snr must be larger than the second snr.
                Default: 25.
                Unit: dB.
                "
          ::= { hwCmtsSpectrumGroupEntry 9 }

    hwCmtsSpectrumGroupSecondSnr OBJECT-TYPE
          SYNTAX  Integer32 (5..35)
          UNITS   "dB"
          MAX-ACCESS  read-write
          STATUS  current
          DESCRIPTION
                "The second snr threshold of a Spectrum Group.
                Default: 15.
                Unit: dB.
                "
          ::= { hwCmtsSpectrumGroupEntry 10 }

    hwCmtsSpectrumGroupProtectPower OBJECT-TYPE
          SYNTAX  Integer32 (0..10)
          UNITS   "dB"
          MAX-ACCESS  read-write
          STATUS  current
          DESCRIPTION
                "The snr protect power of a Spectrum Group.
                Default: 3.
                Unit: dB.
                "
          ::= { hwCmtsSpectrumGroupEntry 11 }

    hwCmtsSpectrumGroupPriority OBJECT-TYPE
          SYNTAX  Integer32 (1..3)
          MAX-ACCESS  read-write
          STATUS  current
          DESCRIPTION
                "The priority of a Spectrum Group.
                 Only three priorities are supported currently.
                 Options:
                 1.Frequency > Modulation-Profile > Channel-Width
                 2.Frequency > Channel-Width > Modulation-Profile
                 3.Modulation-Profile > Frequency > Channel-Width
                 Default: 1.
               "
          ::= { hwCmtsSpectrumGroupEntry 12 }

  -- Table hwdocsIfUpstreamChannelTable
    hwdocsIfUpstreamChannelTable OBJECT-TYPE
          SYNTAX     SEQUENCE OF HwdocsIfUpstreamChannelEntry
          MAX-ACCESS not-accessible
          STATUS     current
          DESCRIPTION
               "This table describes the attributes of upstream channels.
               The index of this table is ifIndex."
          ::= { hwCmtsAccessObject 2 }

    hwdocsIfUpstreamChannelEntry OBJECT-TYPE
          SYNTAX     HwdocsIfUpstreamChannelEntry
          MAX-ACCESS not-accessible
          STATUS     current
          DESCRIPTION
               "This table describes the attributes of upstream channels.
               The index of this entry is ifIndex."
          INDEX       { ifIndex }
          ::= { hwdocsIfUpstreamChannelTable 1 }

    HwdocsIfUpstreamChannelEntry ::=
          SEQUENCE {
                    hwdocsIfUsChanneSpectrumGroupId     Integer32,
                    hwdocsIfUsChanneNoisecanCellation   INTEGER,
                    hwdocsIfUsChanneHopReset            INTEGER,
                    hwdocsIfUsChannelPreEqEnable        INTEGER,
                    hwDocsIfUpstreamChannelRxPower      Integer32
                   }

    hwdocsIfUsChanneSpectrumGroupId OBJECT-TYPE
          SYNTAX  Integer32
          MAX-ACCESS  read-write
          STATUS  current
          DESCRIPTION
                "The ID of a Spectrum Group bound to the upstream channel.
                 -1 represent that the bonding between upstream channel and spectrum group
                 will be canceled.
                 Range: -1|1..16
                 Default: -1
                "
          ::= { hwdocsIfUpstreamChannelEntry 1 }

    hwdocsIfUsChanneNoisecanCellation OBJECT-TYPE
          SYNTAX  INTEGER {
                           enable(1),
                           disable(2)
                          }
          MAX-ACCESS  read-write
          STATUS  current
          DESCRIPTION
                "The switch for the noise suppression.
                Options:
                1. enable(1) - enable the noise suppression
                2. disable(2) - disable the noise suppression
                Default: enable
                "
          ::= { hwdocsIfUpstreamChannelEntry 2 }

    hwdocsIfUsChanneHopReset OBJECT-TYPE
          SYNTAX  INTEGER {
                           invalid(-1),
                           reset(1)
                          }
          MAX-ACCESS  read-write
          STATUS  current
          DESCRIPTION
                "Cancel the hop which has happened in the channel.
                If cancel the hop, the bonding between channel and
                spectrum group still exist.
                Options:
                1. invalid(-1) - Getting is invalid
                2. reset(1) - Cancel the hop
                "
          ::= { hwdocsIfUpstreamChannelEntry 3 }

    hwdocsIfUsChannelPreEqEnable OBJECT-TYPE
          SYNTAX  INTEGER {
                           true(1),
                           false(2)
                          }
          MAX-ACCESS  read-only
          STATUS  current
          DESCRIPTION
                "This object is used to enable or disable pre-equalization
                on the upstream channel represented by this table instance.
                Options:
                1. true(1) - enable the pre-equlization
                2. false(2) - disable the pre-equlization
                Default value: true(1)
                "
          ::= { hwdocsIfUpstreamChannelEntry 4 }

    hwDocsIfUpstreamChannelRxPower OBJECT-TYPE
          SYNTAX  Integer32
          UNITS   "0.1dBmv"
          MAX-ACCESS  read-write
          STATUS  current
          DESCRIPTION
                "This object indicates the receive power of the upstream channel. 
                 If -2147483647 is returned, the receive power is undefined or cannot be identified.
                 Value range: -2147483647|-130..230
                 Default value: 60
                "
          ::= { hwdocsIfUpstreamChannelEntry 5 }

  -- Table hwDocsIf3CmtsCmRegStatusTable
    hwDocsIf3CmtsCmRegStatusTable OBJECT-TYPE
          SYNTAX     SEQUENCE OF HwDocsIf3CmtsCmRegStatusEntry
          MAX-ACCESS not-accessible
          STATUS     current
          DESCRIPTION
               "This table describes the information of cable modem.
                The index of this table is docsIf3CmtsCmRegStatusId."
          ::= { hwCmtsAccessObject 3 }

    hwDocsIf3CmtsCmRegStatusEntry OBJECT-TYPE
          SYNTAX     HwDocsIf3CmtsCmRegStatusEntry
          MAX-ACCESS not-accessible
          STATUS     current
          DESCRIPTION
               "This table describes the information of cable modem.
                The index of this entry is docsIf3CmtsCmRegStatusId."
          INDEX       { docsIf3CmtsCmRegStatusId }
          ::= { hwDocsIf3CmtsCmRegStatusTable 1 }

    HwDocsIf3CmtsCmRegStatusEntry ::=
          SEQUENCE {
                    hwDocsIf3CmtsCmRegStatusPrimSid                      Integer32,
                    hwDocsIf3CmtsCmRegStatusHostInterface                InterfaceIndex,
                    hwDocsIf3CmtsCmRegStatusMacDomainDsSvcGroup          Integer32,
                    hwDocsIf3CmtsCmRegStatusMacDomainUsSvcGroup          Integer32,
                    hwDocsIf3CmtsCmRegStatusMacDomainCmSvcGroup          Integer32,
                    hwDocsIf3CmtsCmRegStatusPrimaryDs                    Integer32,
                    hwDocsIf3CmtsCmRegStatusMTC                          INTEGER,
                    hwDocsIf3CmtsCmRegStatusUpChannelNum                 Integer32,
                    hwDocsIf3CmtsCmRegStatusDOCSISVersion                DocsisVersion,
                    hwDocsIf3CmtsCmRegStatusEnableDocsisTwo              INTEGER,
                    hwDocsIf3CmtsCmRegStatusFragmentation                INTEGER,
                    hwDocsIf3CmtsCmRegStatusConcatenation                INTEGER,
                    hwDocsIf3CmtsCmRegStatusPhs                          INTEGER,
                    hwDocsIf3CmtsCmRegStatusBpi                          INTEGER,
                    hwDocsIf3CmtsCmRegStatusL2VPNCapabilities            INTEGER,
                    hwDocsIf3CmtsCmRegStatusSidLimit                     Integer32,
                    hwDocsIf3CmtsCmRegStatusSaidLimit                    Integer32,
                    hwDocsIf3CmtsCmRegStatusOptionalFilteringSupport     Integer32,
                    hwDocsIf3CmtsCmRegStatusTxEqTapsPerSymbol            Integer32,
                    hwDocsIf3CmtsCmRegStatusCpeNum                       Integer32,
                    hwDocsIf3CmtsCmRegStatusMaxCpe                       Integer32,
                    hwDocsIf3CmtsCmRegStatusUsSFIDCnt                    Integer32,
                    hwDocsIf3CmtsCmRegStatusDsSFIDCnt                    Integer32,
                    hwDocsIf3CmtsCmRegStatusTotalUsPkt                   Counter64,
                    hwDocsIf3CmtsCmRegStatusTotalUsBytes                 Counter64,
                    hwDocsIf3CmtsCmRegStatusTotalDsPkt                   Counter64,
                    hwDocsIf3CmtsCmRegStatusTotalDsBytes                 Counter64,
                    hwDocsIf3CmtsCmRegStatusLbGroupId                    Integer32,
                    hwDocsIf3CmtsCmRegStatusLbGroupIdinCfgFile           Integer32,
                    hwDocsIf3CmtsCmRegStatusValue                        INTEGER,
                    hwDocsIf3CmtsCmCtrlOperStatus                        INTEGER,
                    hwDocsIf3CmtsCmRegStatusRemoteQuery                  INTEGER,
                    hwDocsIf3CmtsCmRegStatusPrimaryDsRxPower             Integer32,
                    hwDocsIf3CmtsCmRegStatusPrimaryDsSnr                 Integer32,
                    hwDocsIf3CmtsCmRegStatusSysDesc                      OCTET STRING,
                    hwDocsIf3CmtsCmRegStatusPortIfIndex                  Integer32,
                    hwDocsIf3CmtsCmRegStatusPrimaryUsTxTimingOffset      Integer32,
                    hwDocsIf3CmtsCmRegStatusOfflineTime                  OCTET STRING,
                    hwDocsIf3CmtsCmRegStatusPreviousStatusValue          INTEGER,
                    hwDocsIf3CmtsCmRegStatusGoodCodeWords                Counter64,
                    hwDocsIf3CmtsCmRegStatusCorrectedErrorCodeWords      Counter64,
                    hwDocsIf3CmtsCmRegStatusUncorrectedErrorCodeWords    Counter64,
                    hwDocsIf3CmtsCmRegStatusConfigFilename               OCTET STRING,
                    hwDocsIf3CmtsCmRegStatusPrimaryUs                    Integer32,
                    hwDocsIf3CmtsCmRegStatusPrimaryUsRxPower             Integer32,
                    hwDocsIf3CmtsCmRegStatusPrimaryUsTxPower             Integer32,
                    hwDocsIf3CmtsCmRegStatusPrimaryDsTxPower             Integer32,
                    hwDocsIf3CmtsCmRegStatusPrimaryUsSnr                 Integer32
                   }

    hwDocsIf3CmtsCmRegStatusPrimSid OBJECT-TYPE
          SYNTAX  Integer32 (0..65535)
          MAX-ACCESS  read-only
          STATUS  current
          DESCRIPTION
                "The ID of the primary service flow which the cable modem using."
          ::= { hwDocsIf3CmtsCmRegStatusEntry 1 }

    hwDocsIf3CmtsCmRegStatusHostInterface OBJECT-TYPE
          SYNTAX  InterfaceIndex
          MAX-ACCESS  read-only
          STATUS  current
          DESCRIPTION
                "The Host Interface when a cable modem arrival."
          ::= { hwDocsIf3CmtsCmRegStatusEntry 2 }

    hwDocsIf3CmtsCmRegStatusMacDomainDsSvcGroup OBJECT-TYPE
          SYNTAX  Integer32 (0..255)
          MAX-ACCESS  read-only
          STATUS  current
          DESCRIPTION
                "The MAC domain downstream service group."
          ::= { hwDocsIf3CmtsCmRegStatusEntry 3 }

    hwDocsIf3CmtsCmRegStatusMacDomainUsSvcGroup OBJECT-TYPE
          SYNTAX  Integer32 (0..255)
          MAX-ACCESS  read-only
          STATUS  current
          DESCRIPTION
                "The MAC domain upstream service group."
          ::= { hwDocsIf3CmtsCmRegStatusEntry 4 }

    hwDocsIf3CmtsCmRegStatusMacDomainCmSvcGroup OBJECT-TYPE
          SYNTAX  Integer32 (0..65535)
          MAX-ACCESS  read-only
          STATUS  current
          DESCRIPTION
                "The mac domain cm service group."
          ::= { hwDocsIf3CmtsCmRegStatusEntry 5 }

    hwDocsIf3CmtsCmRegStatusPrimaryDs OBJECT-TYPE
          SYNTAX  Integer32 (0..255)
          MAX-ACCESS  read-only
          STATUS  current
          DESCRIPTION
                "The primary downstream channel which is a cable modem using.
                 Range: 0..255
                "
          ::= { hwDocsIf3CmtsCmRegStatusEntry 6 }

    hwDocsIf3CmtsCmRegStatusMTC OBJECT-TYPE
          SYNTAX  INTEGER {
                           enable(1),
                           disable(2)
                          }
          MAX-ACCESS  read-only
          STATUS  current
          DESCRIPTION
                "The status of the multi transmit channel.
                Options:
                1. enable(1) - enable the multi transmit channel
                2. disable(2) - disable the multi transmit channel
                "
          ::= { hwDocsIf3CmtsCmRegStatusEntry 7 }

    hwDocsIf3CmtsCmRegStatusUpChannelNum OBJECT-TYPE
          SYNTAX  Integer32 (0..4)
          MAX-ACCESS  read-write
          STATUS  current
          DESCRIPTION
                "The number of the CMC upstream bonding channels."
          ::= { hwDocsIf3CmtsCmRegStatusEntry 8 }

    hwDocsIf3CmtsCmRegStatusDOCSISVersion OBJECT-TYPE
          SYNTAX  DocsisVersion {
                                doc10(1),
                                doc11(2),
                                doc20(3),
                                doc30(4)
                               }
          MAX-ACCESS  read-only
          STATUS  current
          DESCRIPTION
                "The MAC version of the cable modem.
                Options:
                1. doc10(1) - docsis 1.0 version
                2. doc11(2) - docsis 1.1 version
                3. doc20(3) - docsis 2.0 version
                4. doc30(4) - docsis 3.0 version"
          ::= { hwDocsIf3CmtsCmRegStatusEntry 9 }

    hwDocsIf3CmtsCmRegStatusEnableDocsisTwo OBJECT-TYPE
          SYNTAX  INTEGER {
                           enable(1),
                           disable(2)
                          }
          MAX-ACCESS  read-only
          STATUS  current
          DESCRIPTION
                "The status of the DOCSIS2.0 Mode.
                Options:
                1. enable(1) - enable the DOCSIS2.0 Mode
                2. disable(2) - disable the DOCSIS2.0 Mode
                                                                "
          ::= { hwDocsIf3CmtsCmRegStatusEntry 10 }

    hwDocsIf3CmtsCmRegStatusFragmentation OBJECT-TYPE
          SYNTAX  INTEGER {
                           enable(1),
                           disable(2)
                          }
          MAX-ACCESS  read-only
          STATUS  current
          DESCRIPTION
                "The fragmentation capabilities.
                Options:
                1. enable(1) - enable the fragmentation capabilities
                2. disable(2) - disable the fragmentation capabilities
                                                                "
          ::= { hwDocsIf3CmtsCmRegStatusEntry 11 }

    hwDocsIf3CmtsCmRegStatusConcatenation OBJECT-TYPE
          SYNTAX  INTEGER {
                           enable(1),
                           disable(2)
                          }
          MAX-ACCESS  read-only
          STATUS  current
          DESCRIPTION
                "The concatenation capabilities.
                Options:
                1. enable(1) - enable the concatenation capabilities
                2. disable(2) - disable the concatenation capabilities
                                                                "
          ::= { hwDocsIf3CmtsCmRegStatusEntry 12 }

    hwDocsIf3CmtsCmRegStatusPhs OBJECT-TYPE
          SYNTAX  INTEGER {
                           enable(1),
                           disable(2)
                          }
          MAX-ACCESS  read-only
          STATUS  current
          DESCRIPTION
                "The packet header suppression capabilities.
                Options:
                1. enable(1) - enable the packet header suppression capabilities
                2. disable(2) - disable the packet header suppression capabilities
                                                                "
          ::= { hwDocsIf3CmtsCmRegStatusEntry 13 }

    hwDocsIf3CmtsCmRegStatusBpi OBJECT-TYPE
          SYNTAX  INTEGER {
                           disable(1),
                           bpi(2),
                           bpi-plus(3)
                          }
          MAX-ACCESS  read-only
          STATUS  current
          DESCRIPTION
                "The status of Baseline Privacy Interface.
                Options:
                1. disable(1) - disable the Baseline Privacy Interface
                2. bpi(2) - enable the Baseline Privacy Interface
                3. bpi-plus(3) - enable the Baseline Privacy Interface Plus
                "
          ::= { hwDocsIf3CmtsCmRegStatusEntry 14 }

    hwDocsIf3CmtsCmRegStatusL2VPNCapabilities OBJECT-TYPE
          SYNTAX  INTEGER {
                           enable(1),
                           disable(2)
                          }
          MAX-ACCESS  read-only
          STATUS  current
          DESCRIPTION
                "The Layer 2 Virtual Private Network capabilities.
                Options:
                1. enable(1) - enable the Layer 2 Virtual Private Network capabilities
                2. disable(2) - disable the Layer 2 Virtual Private Network capabilities
                                                                "
          ::= { hwDocsIf3CmtsCmRegStatusEntry 15 }

    hwDocsIf3CmtsCmRegStatusSidLimit OBJECT-TYPE
          SYNTAX  Integer32 (0..255)
          MAX-ACCESS  read-only
          STATUS  current
          DESCRIPTION
                "The limit of the Service Identifier when cable modem register."
          ::= { hwDocsIf3CmtsCmRegStatusEntry 16 }

    hwDocsIf3CmtsCmRegStatusSaidLimit OBJECT-TYPE
          SYNTAX  Integer32 (0..255)
          MAX-ACCESS  read-only
          STATUS  current
          DESCRIPTION
                "The limit of Security Association Identifiers when cable modem register."
          ::= { hwDocsIf3CmtsCmRegStatusEntry 17 }

    hwDocsIf3CmtsCmRegStatusOptionalFilteringSupport OBJECT-TYPE
          SYNTAX  Integer32 (0..255)
          MAX-ACCESS  read-only
          STATUS  current
          DESCRIPTION
                "Optional Filtering Support.
                Bit0 represent 802.1P, bit1 represent 802.1Q, bit2 represent DUT.
                "
          ::= { hwDocsIf3CmtsCmRegStatusEntry 18 }

    hwDocsIf3CmtsCmRegStatusTxEqTapsPerSymbol OBJECT-TYPE
          SYNTAX  Integer32 (0..255)
          MAX-ACCESS  read-only
          STATUS  current
          DESCRIPTION
                "Transmit Equalizer Support."
          ::= { hwDocsIf3CmtsCmRegStatusEntry 19 }

    hwDocsIf3CmtsCmRegStatusCpeNum OBJECT-TYPE
          SYNTAX  Integer32 (0..255)
          MAX-ACCESS  read-only
          STATUS  current
          DESCRIPTION
                "The number of CPE IPs."
          ::= { hwDocsIf3CmtsCmRegStatusEntry 20 }

    hwDocsIf3CmtsCmRegStatusMaxCpe OBJECT-TYPE
          SYNTAX  Integer32 (0..255)
          MAX-ACCESS  read-only
          STATUS  current
          DESCRIPTION
                "Configuration the max CPE number."
          ::= { hwDocsIf3CmtsCmRegStatusEntry 21 }

    hwDocsIf3CmtsCmRegStatusUsSFIDCnt OBJECT-TYPE
          SYNTAX  Integer32 (0..65535)
          MAX-ACCESS  read-only
          STATUS  current
          DESCRIPTION
                "The number of upstream service flow IDs setup for cable modem."
          ::= { hwDocsIf3CmtsCmRegStatusEntry 22 }

    hwDocsIf3CmtsCmRegStatusDsSFIDCnt OBJECT-TYPE
          SYNTAX  Integer32 (0..65535)
          MAX-ACCESS  read-only
          STATUS  current
          DESCRIPTION
                "The number of downstream service flow IDs setup for cable modem."
          ::= { hwDocsIf3CmtsCmRegStatusEntry 23 }

    hwDocsIf3CmtsCmRegStatusTotalUsPkt OBJECT-TYPE
          SYNTAX  Counter64
          MAX-ACCESS  read-only
          STATUS  current
          DESCRIPTION
                "Total upstream data."
          ::= { hwDocsIf3CmtsCmRegStatusEntry 24 }

    hwDocsIf3CmtsCmRegStatusTotalUsBytes OBJECT-TYPE
          SYNTAX  Counter64
          MAX-ACCESS  read-only
          STATUS  current
          DESCRIPTION
                "Total upstream throughput."
          ::= { hwDocsIf3CmtsCmRegStatusEntry 25 }

    hwDocsIf3CmtsCmRegStatusTotalDsPkt OBJECT-TYPE
          SYNTAX  Counter64
          MAX-ACCESS  read-only
          STATUS  current
          DESCRIPTION
                "Total downstream Data."
          ::= { hwDocsIf3CmtsCmRegStatusEntry 26 }

    hwDocsIf3CmtsCmRegStatusTotalDsBytes OBJECT-TYPE
          SYNTAX  Counter64
          MAX-ACCESS  read-only
          STATUS  current
          DESCRIPTION
                "Total downstream throughput."
          ::= { hwDocsIf3CmtsCmRegStatusEntry 27 }

    hwDocsIf3CmtsCmRegStatusLbGroupId OBJECT-TYPE
          SYNTAX  Integer32 (0..255)
          MAX-ACCESS  read-only
          STATUS  current
          DESCRIPTION
                "The load balance group ID assigned."
          ::= { hwDocsIf3CmtsCmRegStatusEntry 28 }

    hwDocsIf3CmtsCmRegStatusLbGroupIdinCfgFile OBJECT-TYPE
          SYNTAX  Integer32 (0..255)
          MAX-ACCESS  read-only
          STATUS  current
          DESCRIPTION
                "The load balance group ID in the configuration files."
          ::= { hwDocsIf3CmtsCmRegStatusEntry 29 }

    hwDocsIf3CmtsCmRegStatusValue OBJECT-TYPE
          SYNTAX  INTEGER {
                   other(1),
                           initialRanging(2),
                           rangingAutoAdjComplete(4),
                           dhcpv4Complete(5),
                           registrationComplete(6),
                           operational(8),
                           bpiInit(9),
                           startEae(10),
                           startDhcpv4(11),
                           startDhcpv6(12),
                           dhcpv6Complete(13),
                           startConfigFileDownload(14),
                           configFileDownloadComplete(15),
                           startRegistration(16),
                           forwardingDisabled(17),
                           rfMuteAll(18),
                           offline(31),
                           dhcpOffer(32),
                           dhcpRequest(33),
                           online(34),
                           onlineBpiSucc(35),
                           onlineBpiSuccAndNetAccessDisabled(36),
                           onlineNetAccessDisabled(37),
                           wonline(38),
                           wonlineBpiSucc(39),
                           wonlineBpiSuccAndNetAccessDisabled(40),
                           wonlineNetAccessDisabled(41),
                           ponline(42),
                           ponlineBpiSucc(43),
                           ponlineBpiSuccAndNetAccessDisabled(44),
                           ponlineNetAccessDisabled(45),
                           rejectMic(46),
                           rejectBpi(47),
                           rejectOther(48)
                          }
          MAX-ACCESS  read-only
          STATUS  current
          DESCRIPTION
                "
                Indicates current register status of the CM.
                Options:
                1. other(1) - other
                2. initialRanging(2) - initialRanging
                3. rangingAutoAdjComplete(4) - rangingAutoAdjComplete
                4. dhcpv4Complete(5) - dhcpv4Complete
                5. registrationComplete(6) - registrationComplete
                6. operational(8) - operational
                7. bpiInit(9) - bpiInit
                8. startEae(10) - startEae
                9. startDhcpv4(11) - startDhcpv4
                10. startDhcpv6(12) - startDhcpv6
                11. dhcpv6Complete(13) - dhcpv6Complete
                12. startConfigFileDownload(14) - startConfigFileDownload
                13. configFileDownloadComplete(15) - configFileDownloadComplete
                14. startRegistration(16) - startRegistration
                15. forwardingDisabled(17) - forwardingDisabled
                16. rfMuteAll(18) - rfMuteAll
                17. offline(31) - offline
                18. dhcpOffer(32) - dhcpOffer
                19. dhcpRequest(33) - dhcpRequest
                20. online(34) - online
                21. onlineBpiSucc(35) - onlineBpiSucc
                22. onlineBpiSuccAndNetAccessDisabled(36) - onlineBpiSuccAndNetAccessDisabled
                23. onlineNetAccessDisabled(37) - onlineNetAccessDisabled
                24. wonline(38) - wonline
                25. wonlineBpiSucc(39) - wonlineBpiSucc
                26. wonlineBpiSuccAndNetAccessDisabled(40) - wonlineBpiSuccAndNetAccessDisabled
                27. wonlineNetAccessDisabled(41) - wonlineNetAccessDisabled
                28. ponline(42) - ponline
                29. ponlineBpiSucc(43) - ponlineBpiSucc
                30. ponlineBpiSuccAndNetAccessDisabled(44) - ponlineBpiSuccAndNetAccessDisabled
                31. ponlineNetAccessDisabled(45) - ponlineNetAccessDisabled
                32. rejectMic(46) - rejectMic
                33. rejectBpi(47) - rejectBpi
                34. rejectOther(48) - rejectOther
                "
          ::= { hwDocsIf3CmtsCmRegStatusEntry 30 }

    hwDocsIf3CmtsCmCtrlOperStatus OBJECT-TYPE
          SYNTAX  INTEGER {
                           reset(1),
		           delete(2),
		           invalidValue(-1)
                          }
          MAX-ACCESS  read-write
          STATUS  current
          DESCRIPTION
                "
                Indicates the operating mode.
                Options:
                1. reset(1)  - Reset the operating mode
                2. delete(2) - Delete the operating mode
                3. invalidValue(-1) -Invalid value
                "
          ::= { hwDocsIf3CmtsCmRegStatusEntry 31 }

    hwDocsIf3CmtsCmRegStatusRemoteQuery OBJECT-TYPE
          SYNTAX  INTEGER {
                           start(1),
                           stop(2)
                          }
          MAX-ACCESS  read-write
          STATUS  current
          DESCRIPTION
                "Indicates querying the information about a remote CM.
                 Options:
                1. start(1) - Start querying the information about a remote CM
                2. stop(2)  - Stop querying the information about a remote CM
                "
          ::= { hwDocsIf3CmtsCmRegStatusEntry 32 }

    hwDocsIf3CmtsCmRegStatusPrimaryDsRxPower OBJECT-TYPE
          SYNTAX  Integer32
          UNITS       "0.1dBmV"
          MAX-ACCESS  read-only
          STATUS  current
          DESCRIPTION
                "
                Indicates the down stream receive power of cable modem.
                -2147483647 represent NULL.
                "
          ::= { hwDocsIf3CmtsCmRegStatusEntry 33 }

    hwDocsIf3CmtsCmRegStatusPrimaryDsSnr OBJECT-TYPE
          SYNTAX  Integer32
          UNITS       "0.1dB"
          MAX-ACCESS  read-only
          STATUS  current
          DESCRIPTION
                "
                The primary down stream snr of cable modem.
                -1 represent NULL.
                "
          ::= { hwDocsIf3CmtsCmRegStatusEntry 34 }

    hwDocsIf3CmtsCmRegStatusSysDesc OBJECT-TYPE
          SYNTAX  OCTET STRING(SIZE (0..255))
          MAX-ACCESS  read-only
          STATUS  current
          DESCRIPTION
                "
                The system description infomation of CM.
                "
          ::= { hwDocsIf3CmtsCmRegStatusEntry 35 }

    hwDocsIf3CmtsCmRegStatusPortIfIndex OBJECT-TYPE
          SYNTAX  Integer32
          MAX-ACCESS  read-only
          STATUS  current
          DESCRIPTION
                "
                The port ifindex of CM.
                "
          ::= { hwDocsIf3CmtsCmRegStatusEntry 36 }

    hwDocsIf3CmtsCmRegStatusPrimaryUsTxTimingOffset OBJECT-TYPE
          SYNTAX  Integer32
          MAX-ACCESS  read-only
          STATUS  current
          DESCRIPTION
                "
                The send time offset of the main up channel of CM.
                Unit:97.6ns(6.25/64 microseconds)
                -1 represent NULL.
                "
          ::= { hwDocsIf3CmtsCmRegStatusEntry 37 }

    hwDocsIf3CmtsCmRegStatusOfflineTime OBJECT-TYPE
          SYNTAX  OCTET STRING
          MAX-ACCESS  read-only
          STATUS  current
          DESCRIPTION
                "
                The value of this node is DateAndTime.
                "
          ::= { hwDocsIf3CmtsCmRegStatusEntry 38 }

    hwDocsIf3CmtsCmRegStatusPreviousStatusValue OBJECT-TYPE
          SYNTAX  INTEGER {
                           other(1),
                           initialRanging(2),
                           rangingAutoAdjComplete(4),
                           dhcpv4Complete(5),
                           registrationComplete(6),
                           operational(8),
                           bpiInit(9),
                           startEae(10),
                           startDhcpv4(11),
                           startDhcpv6(12),
                           dhcpv6Complete(13),
                           startConfigFileDownload(14),
                           configFileDownloadComplete(15),
                           startRegistration(16),
                           forwardingDisabled(17),
                           rfMuteAll(18),
                           offline(31),
                           dhcpOffer(32),
                           dhcpRequest(33),
                           online(34),
                           onlineBpiSucc(35),
                           onlineBpiSuccAndNetAccessDisabled(36),
                           onlineNetAccessDisabled(37),
                           wonline(38),
                           wonlineBpiSucc(39),
                           wonlineBpiSuccAndNetAccessDisabled(40),
                           wonlineNetAccessDisabled(41),
                           rejectMic(46),
                           rejectBpi(47),
                           rejectOther(48)
                          }
          MAX-ACCESS  read-only
          STATUS  current
          DESCRIPTION
                "
                Indicates current register status of the CM.
                Options:
                1. other(1) - other
                2. initialRanging(2) - initialRanging
                3. rangingAutoAdjComplete(4) - rangingAutoAdjComplete
                4. dhcpv4Complete(5) - dhcpv4Complete
                5. registrationComplete(6) - registrationComplete
                6. operational(8) - operational
                7. bpiInit(9) - bpiInit
                8. startEae(10) - startEae
                9. startDhcpv4(11) - startDhcpv4
                10. startDhcpv6(12) - startDhcpv6
                11. dhcpv6Complete(13) - dhcpv6Complete
                12. startConfigFileDownload(14) - startConfigFileDownload
                13. configFileDownloadComplete(15) - configFileDownloadComplete
                14. startRegistration(16) - startRegistration
                15. forwardingDisabled(17) - forwardingDisabled
                16. rfMuteAll(18) - rfMuteAll
                17. offline(31) - offline
                18. dhcpOffer(32) - dhcpOffer
                19. dhcpRequest(33) - dhcpRequest
                20. online(34) - online
                21. onlineBpiSucc(35) - onlineBpiSucc
                22. onlineBpiSuccAndNetAccessDisabled(36) - onlineBpiSuccAndNetAccessDisabled
                23. onlineNetAccessDisabled(37) - onlineNetAccessDisabled
                24. wonline(38) - wonline
                25. wonlineBpiSucc(39) - wonlineBpiSucc
                26. wonlineBpiSuccAndNetAccessDisabled(40) - wonlineBpiSuccAndNetAccessDisabled
                27. wonlineNetAccessDisabled(41) - wonlineNetAccessDisabled
                28. rejectMic(46) - rejectMic
                29. rejectBpi(47) - rejectBpi
                30. rejectOther(48) - rejectOther
                "
          ::= { hwDocsIf3CmtsCmRegStatusEntry 39 }

    hwDocsIf3CmtsCmRegStatusGoodCodeWords OBJECT-TYPE
          SYNTAX  Counter64
          MAX-ACCESS  read-only
          STATUS  current
          DESCRIPTION
                "
                This attribute represents the good codewords received
                from the CM on this interface.
                "
          ::= { hwDocsIf3CmtsCmRegStatusEntry 40 }

    hwDocsIf3CmtsCmRegStatusCorrectedErrorCodeWords OBJECT-TYPE
          SYNTAX  Counter64
          MAX-ACCESS  read-only
          STATUS  current
          DESCRIPTION
                "
                This attribute represents the codewords received
                with correctable errors from the CM on this interface.
                "
          ::= { hwDocsIf3CmtsCmRegStatusEntry 41 }

    hwDocsIf3CmtsCmRegStatusUncorrectedErrorCodeWords OBJECT-TYPE
          SYNTAX  Counter64
          MAX-ACCESS  read-only
          STATUS  current
          DESCRIPTION
                "
                This attribute represents the codewords received
                with uncorrectable errors from the CM on this interface.
                "
          ::= { hwDocsIf3CmtsCmRegStatusEntry 42 }

    hwDocsIf3CmtsCmRegStatusConfigFilename OBJECT-TYPE
          SYNTAX  OCTET STRING(SIZE (0..256))
          MAX-ACCESS  read-only
          STATUS  current
          DESCRIPTION
                "
                This attribute represents the CM config-file Name.
                "
          ::= { hwDocsIf3CmtsCmRegStatusEntry 43 }

    hwDocsIf3CmtsCmRegStatusPrimaryUs OBJECT-TYPE
          SYNTAX  Integer32
          MAX-ACCESS  read-only
          STATUS  current
          DESCRIPTION
                "This object indicates the ID of the CM's active upstream channel. 
                 If -1 is returned, the index is undefined or cannot be identified. 
                 Value range: -1|1..4.
                "
          ::= { hwDocsIf3CmtsCmRegStatusEntry 44 }

    hwDocsIf3CmtsCmRegStatusPrimaryUsRxPower OBJECT-TYPE
          SYNTAX  Integer32
          UNITS       "0.1dbmV"
          MAX-ACCESS  read-only
          STATUS  current
          DESCRIPTION
                "This object indicates the receive power of the CM's primary upstream channel."
          ::= { hwDocsIf3CmtsCmRegStatusEntry 45 }

    hwDocsIf3CmtsCmRegStatusPrimaryUsTxPower OBJECT-TYPE
          SYNTAX  Integer32
          UNITS       "0.1dbmV"
          MAX-ACCESS  read-only
          STATUS  current
          DESCRIPTION
                "This object indicates the transmit power of the CM's primary upstream channel."
          ::= { hwDocsIf3CmtsCmRegStatusEntry 46 }

    hwDocsIf3CmtsCmRegStatusPrimaryDsTxPower OBJECT-TYPE
          SYNTAX  Integer32
          UNITS       "0.1dbmV"
          MAX-ACCESS  read-only
          STATUS  current
          DESCRIPTION
                "This object indicates the transmit power of the CM's primary downstream channel."
          ::= { hwDocsIf3CmtsCmRegStatusEntry 47 }

    hwDocsIf3CmtsCmRegStatusPrimaryUsSnr OBJECT-TYPE
          SYNTAX  Integer32
          UNITS       "0.1dB"
          MAX-ACCESS  read-only
          STATUS  current
          DESCRIPTION
                "This object indicates the signal-to-noise ratio (SNR) of the CM's primary upstream channel."
          ::= { hwDocsIf3CmtsCmRegStatusEntry 48 }

  -- Table hwDocsIf3CmtsCmUsStatusTable
    hwDocsIf3CmtsCmUsStatusTable OBJECT-TYPE
          SYNTAX     SEQUENCE OF HwDocsIf3CmtsCmUsStatusEntry
          MAX-ACCESS not-accessible
          STATUS     current
          DESCRIPTION
               "This table describes the information of the upstream channel
                which the cable modem location.
                The indexes of this table are docsIf3CmtsCmRegStatusId
                and docsIf3CmtsCmUsStatusChIfIndex.
               "
          ::= { hwCmtsAccessObject 4 }

    hwDocsIf3CmtsCmUsStatusEntry OBJECT-TYPE
          SYNTAX     HwDocsIf3CmtsCmUsStatusEntry
          MAX-ACCESS not-accessible
          STATUS     current
          DESCRIPTION
               "This table describes the information of the upstream channel
                which the cable modem location.
                The indexes of this entry are docsIf3CmtsCmRegStatusId
                and docsIf3CmtsCmUsStatusChIfIndex.
               "
          INDEX       { docsIf3CmtsCmRegStatusId, docsIf3CmtsCmUsStatusChIfIndex }
          ::= { hwDocsIf3CmtsCmUsStatusTable 1 }

    HwDocsIf3CmtsCmUsStatusEntry ::=
          SEQUENCE {
                    hwDocsIf3CmtsCmUsStatusTxPower               Integer32,
                    hwDocsIf3CmtsCmUsStatusInitialTimingOffset   Unsigned32,
                    hwDocsIf3CmtsCmUsStatusPhyOperatingMode      INTEGER,
                    hwDocsIf3CmtsCmUsStatusTxTimingOffset        Integer32,
                    hwDocsIf3CmtsCmUsGoodCodewords                 Counter64,
                    hwDocsIf3CmtsCmUsCorrectedErrorCodewords       Counter64,
                    hwDocsIf3CmtsCmUsUncorrectedErrorCodewords     Counter64
                   }

    hwDocsIf3CmtsCmUsStatusTxPower OBJECT-TYPE
          SYNTAX  Integer32
          MAX-ACCESS  read-only
          STATUS  current
          DESCRIPTION
                "Upstream Transmit Power.
                 Unit: 0.1 dBmV
                 -2147483647 represent NULL.
                "
          ::= { hwDocsIf3CmtsCmUsStatusEntry 1 }

    hwDocsIf3CmtsCmUsStatusInitialTimingOffset OBJECT-TYPE
          SYNTAX  Unsigned32 (0..4294967295)
          MAX-ACCESS  read-only
          STATUS  current
          DESCRIPTION
                "Initial Timing Offset.
                4294967295 represent NULL"
          ::= { hwDocsIf3CmtsCmUsStatusEntry 2 }

    hwDocsIf3CmtsCmUsStatusPhyOperatingMode OBJECT-TYPE
          SYNTAX  INTEGER {
                           tdma(1),
                           atdma(2),
                           scdma(3),
                           tdmaandatdma(4)
                          }
          MAX-ACCESS  read-only
          STATUS  current
          DESCRIPTION
                "Phy Operating Mode.
                Options:
                1. tdma(1) - Time Division Multiple Access
                2. atdma(2) - Advanced Time Division Multiple Access
                3. scdma(3) - Synchronous Code Division Multiple Access
                4. tdmaandatdma(4) - Time Division Multiple Access and Advanced Time Division Multiple Access
                                                                "
          ::= { hwDocsIf3CmtsCmUsStatusEntry 3 }

    hwDocsIf3CmtsCmUsStatusTxTimingOffset OBJECT-TYPE
          SYNTAX  Integer32
          MAX-ACCESS  read-only
          STATUS  current
          DESCRIPTION
                "
                Indicates the send time offset of up channel of CM.
                Unit:97.6ns(6.25/64 microseconds).
                -1 represent NULL.
                "
           ::= { hwDocsIf3CmtsCmUsStatusEntry 4 }
    hwDocsIf3CmtsCmUsGoodCodewords OBJECT-TYPE
          SYNTAX  Counter64
          MAX-ACCESS  read-only
          STATUS  current
          DESCRIPTION
                "
                This attribute represents the codewords received
                without error from the CM on this channel.
                "
          ::= { hwDocsIf3CmtsCmUsStatusEntry 5 }

    hwDocsIf3CmtsCmUsCorrectedErrorCodewords OBJECT-TYPE
          SYNTAX  Counter64
          MAX-ACCESS  read-only
          STATUS  current
          DESCRIPTION
                "
                This attribute represents the codewords received
                with correctable errors from the CM on this channel.
                "
          ::= { hwDocsIf3CmtsCmUsStatusEntry 6 }

    hwDocsIf3CmtsCmUsUncorrectedErrorCodewords OBJECT-TYPE
          SYNTAX  Counter64
          MAX-ACCESS  read-only
          STATUS  current
          DESCRIPTION
                "
                This attribute represents the codewords received
                with uncorrectable errors from the CM on this channel.
                "
          ::= { hwDocsIf3CmtsCmUsStatusEntry 7 }
          
  -- Table hwDocsIf3CmtsCmDownChannelInfoTable
    hwDocsIf3CmtsCmDownChannelInfoTable OBJECT-TYPE
          SYNTAX     SEQUENCE OF HwDocsIf3CmtsCmDownChannelInfoEntry
          MAX-ACCESS not-accessible
          STATUS     current
          DESCRIPTION
               "This table describes the information of the downstream channel
                which the cable modem location.
                The indexes of this table are docsIf3CmtsCmRegStatusId
                and hwDocsIf3CmtsCmDownChannelInfoChannelId.
               "
          ::= { hwCmtsAccessObject 5 }

    hwDocsIf3CmtsCmDownChannelInfoEntry OBJECT-TYPE
          SYNTAX     HwDocsIf3CmtsCmDownChannelInfoEntry
          MAX-ACCESS not-accessible
          STATUS     current
          DESCRIPTION
               "This table describes the information of the downstream channel
                which the cable modem location.
                The indexes of this entry are docsIf3CmtsCmRegStatusId
                and hwDocsIf3CmtsCmDownChannelInfoChannelId.
               "
          INDEX       { docsIf3CmtsCmRegStatusId, hwDocsIf3CmtsCmDownChannelInfoChannelId }
          ::= { hwDocsIf3CmtsCmDownChannelInfoTable 1 }

    HwDocsIf3CmtsCmDownChannelInfoEntry ::=
          SEQUENCE {
                    hwDocsIf3CmtsCmDownChannelInfoChannelId  Integer32,
                    hwDocsIf3CmtsCmDownChannelInfoPower      Integer32,
                    hwDocsIf3CmtsCmDownChannelInfoRxPower    Integer32,
                    hwDocsIf3CmtsCmDownChannelInfoSnr        Integer32
                   }

    hwDocsIf3CmtsCmDownChannelInfoChannelId OBJECT-TYPE
          SYNTAX  Integer32 (1..16)
          MAX-ACCESS  not-accessible
          STATUS  current
          DESCRIPTION
                "The downstream channel ID.
                 Range: 1..16
                "
          ::= { hwDocsIf3CmtsCmDownChannelInfoEntry 1 }

    hwDocsIf3CmtsCmDownChannelInfoPower OBJECT-TYPE
          SYNTAX  Integer32
          MAX-ACCESS  read-only
          STATUS  current
          DESCRIPTION
                "Downstream Transmit Power.
                 Unit: 0.1 dBmV
                 -1 represent NULL.
                "
          ::= { hwDocsIf3CmtsCmDownChannelInfoEntry 2 }
    hwDocsIf3CmtsCmDownChannelInfoRxPower OBJECT-TYPE
          SYNTAX  Integer32
          UNITS   "0.1dBmV"
          MAX-ACCESS  read-only
          STATUS  current
          DESCRIPTION
                "
                Indicates the down stream receive power of cable modem.
                -2147483647 represent NULL.
                "
          ::= { hwDocsIf3CmtsCmDownChannelInfoEntry 3 }
    hwDocsIf3CmtsCmDownChannelInfoSnr OBJECT-TYPE
          SYNTAX  Integer32
          UNITS   "0.1dB"
          MAX-ACCESS  read-only
          STATUS  current
          DESCRIPTION
                "
                The primary down stream snr of cable modem.
                -1 represent NULL.
                "
          ::= { hwDocsIf3CmtsCmDownChannelInfoEntry 4 }

  -- Table hwDocsIf3CmtsCmCpeInfoTable
    hwDocsIf3CmtsCmCpeInfoTable OBJECT-TYPE
          SYNTAX     SEQUENCE OF HwDocsIf3CmtsCmCpeInfoEntry
          MAX-ACCESS not-accessible
          STATUS     current
          DESCRIPTION
               "This table describes the information of the CPE.
                The indexes of this table are docsIf3CmtsCmRegStatusId
                and hwDocsIf3CmtsCmCpeInfoCpeId.
               "
          ::= { hwCmtsAccessObject 6 }

    hwDocsIf3CmtsCmCpeInfoEntry OBJECT-TYPE
          SYNTAX     HwDocsIf3CmtsCmCpeInfoEntry
          MAX-ACCESS not-accessible
          STATUS     current
          DESCRIPTION
               "This table describes the information of the CPE.
                The indexes of this entry are docsIf3CmtsCmRegStatusId
                and hwDocsIf3CmtsCmCpeInfoCpeId.
               "
          INDEX       { docsIf3CmtsCmRegStatusId, hwDocsIf3CmtsCmCpeInfoCpeId }
          ::= { hwDocsIf3CmtsCmCpeInfoTable 1 }

    HwDocsIf3CmtsCmCpeInfoEntry ::=
          SEQUENCE {
                    hwDocsIf3CmtsCmCpeInfoCpeId       Integer32,
                    hwDocsIf3CmtsCmCpeInfoMacAddr     MacAddress,
                    hwDocsIf3CmtsCmCpeInfoIPv4Addr    IpAddress,
                    hwDocsIf3CmtsCmCpeInfoDeviceDesc  OCTET STRING
                   }

    hwDocsIf3CmtsCmCpeInfoCpeId OBJECT-TYPE
          SYNTAX  Integer32 (0..255)
          MAX-ACCESS  not-accessible
          STATUS  current
          DESCRIPTION
                "The CPE ID.
                 Range: 0..255
                "
          ::= { hwDocsIf3CmtsCmCpeInfoEntry 1 }

    hwDocsIf3CmtsCmCpeInfoMacAddr OBJECT-TYPE
          SYNTAX  MacAddress
          MAX-ACCESS  read-only
          STATUS  current
          DESCRIPTION
                "This attribute represents the MAC address of the CPE."
          ::= { hwDocsIf3CmtsCmCpeInfoEntry 2 }

    hwDocsIf3CmtsCmCpeInfoIPv4Addr OBJECT-TYPE
          SYNTAX  IpAddress
          MAX-ACCESS  read-only
          STATUS  current
          DESCRIPTION
                "This attribute represents the IPv4 address of the CPE."
          ::= { hwDocsIf3CmtsCmCpeInfoEntry 3 }

    hwDocsIf3CmtsCmCpeInfoDeviceDesc OBJECT-TYPE
          SYNTAX  OCTET STRING (SIZE(0..8))
          MAX-ACCESS  read-only
          STATUS  current
          DESCRIPTION
                "This object indicates the CPE description."
          ::= { hwDocsIf3CmtsCmCpeInfoEntry 4 }

  hwCmtsAdmissionCtrlTable OBJECT IDENTIFIER ::= { hwCmtsAccessObject  8}
    -- Table hwCmtsAdmissionCtrlTable
    hwCmtsAdmissionCtrlCmRegistrationSwitch OBJECT-TYPE
          SYNTAX  INTEGER {enable(1),disable(2)}
          MAX-ACCESS  read-write
          STATUS  current
          DESCRIPTION
                "Indicates the switch of cable modem register admission.
                Options:
                1. enable(1)     -Enable the cable modem registration switch
                2. disable(2)    -Disable the cable modem registration switch
                "
          ::= { hwCmtsAdmissionCtrlTable 1 }

    hwCmtsAdmissionCtrlDynamicServiceSwitch OBJECT-TYPE
          SYNTAX  INTEGER {enable(1),disable(2)}
          MAX-ACCESS  read-write
          STATUS  current
          DESCRIPTION
                "Indicates the switch of dynamic service admission control.
                Options:
                1. enable(1)     -Enable the dynamic service admission switch
                2. disable(2)    -Disable the dynamic service admission switch
                "
          ::= { hwCmtsAdmissionCtrlTable 2 }

 -- Table hwCmtsAdmissionCtrlTypeTable
    hwCmtsAdmissionCtrlTypeTable OBJECT-TYPE
          SYNTAX     SEQUENCE OF HwCmtsAdmissionCtrlTypeEntry
          MAX-ACCESS not-accessible
          STATUS     current
          DESCRIPTION
               "Indicates the admission control type configuration.
               The index of this table is hwCmtsAdmissionCtrlType.
               "
          ::= { hwCmtsAccessObject 9 }

    hwCmtsAdmissionCtrlTypeEntry OBJECT-TYPE
          SYNTAX     HwCmtsAdmissionCtrlTypeEntry
          MAX-ACCESS not-accessible
          STATUS     current
          DESCRIPTION
               "Indicates the admission control type configuration.
               The index of this entry is hwCmtsAdmissionCtrlType.
               "
          INDEX       { hwCmtsAdmissionCtrlType }
          ::= { hwCmtsAdmissionCtrlTypeTable 1 }

    HwCmtsAdmissionCtrlTypeEntry ::=
          SEQUENCE {
                    hwCmtsAdmissionCtrlType      Integer32,
                    hwCmtsAdmissionCtrlTypeName  OCTET STRING
                   }

    hwCmtsAdmissionCtrlType OBJECT-TYPE
          SYNTAX  Integer32 (0..7)
          MAX-ACCESS  not-accessible
          STATUS  current
          DESCRIPTION
                "Indicates the admission control type."
          ::= { hwCmtsAdmissionCtrlTypeEntry 1 }

    hwCmtsAdmissionCtrlTypeName OBJECT-TYPE
          SYNTAX      OCTET STRING(SIZE (0..32))
          MAX-ACCESS  read-write
          STATUS  current
          DESCRIPTION
                "Indicates the name of admission control type."
          ::= { hwCmtsAdmissionCtrlTypeEntry 2 }

  -- Table hwCmtsAdmissionCtrlMappingTable
    hwCmtsAdmissionCtrlMappingTable OBJECT-TYPE
          SYNTAX     SEQUENCE OF HwCmtsAdmissionCtrlMappingEntry
          MAX-ACCESS not-accessible
          STATUS     current
          DESCRIPTION
               "Indicates the admission control type mapping configuration.
               The index of this table is hwCmtsAdmissionCtrlMappingIndex.
               "
          ::= { hwCmtsAccessObject 10 }

    hwCmtsAdmissionCtrlMappingEntry OBJECT-TYPE
          SYNTAX     HwCmtsAdmissionCtrlMappingEntry
          MAX-ACCESS not-accessible
          STATUS     current
          DESCRIPTION
               "Indicates the admission control type mapping configuration.
               The index of this entry is hwCmtsAdmissionCtrlMappingIndex.
               "
          INDEX       { hwCmtsAdmissionCtrlMappingIndex }
          ::= { hwCmtsAdmissionCtrlMappingTable 1 }

    HwCmtsAdmissionCtrlMappingEntry ::=
          SEQUENCE {
                    hwCmtsAdmissionCtrlMappingIndex               Integer32,
                    hwCmtsAdmissionCtrlMappingType     Integer32,
                    hwCmtsAdmissionCtrlMappingTypeName OCTET STRING,
                    hwCmtsAdmissionCtrlMappingSubType             INTEGER,
                    hwCmtsAdmissionCtrlMappingPacketCablePriority INTEGER,
                    hwCmtsAdmissionCtrlMappingPcmmPriority        Integer32,
                    hwCmtsAdmissionCtrlMappingPcmmApplicationType Integer32,
                    hwCmtsAdmissionCtrlMappingSchedulingType      INTEGER,
                    hwCmtsAdmissionCtrlMappingServiceClassName    OCTET STRING,
                    hwCmtsAdmissionCtrlMappingRowStatus           RowStatus
                   }

    hwCmtsAdmissionCtrlMappingIndex OBJECT-TYPE
          SYNTAX     Integer32 (-1|0..31)
          MAX-ACCESS not-accessible
          STATUS     current
          DESCRIPTION
                "Indicates the index of admission control type mapping.
                 -1 is used only when a user adds admission control mapping.
                 "
          ::= { hwCmtsAdmissionCtrlMappingEntry 1 }

    hwCmtsAdmissionCtrlMappingType OBJECT-TYPE
          SYNTAX     Integer32(0..7)
          MAX-ACCESS read-write
          STATUS     current
          DESCRIPTION
                "Indicates the admission control type."
              DEFVAL      { 0 }
          ::= { hwCmtsAdmissionCtrlMappingEntry 2 }

    hwCmtsAdmissionCtrlMappingTypeName OBJECT-TYPE
          SYNTAX      OCTET STRING(SIZE (0..32))
          MAX-ACCESS  read-only
          STATUS  current
          DESCRIPTION
                "Indicates the name of admission control type."
          ::= { hwCmtsAdmissionCtrlMappingEntry 3 }

    hwCmtsAdmissionCtrlMappingSubType OBJECT-TYPE
          SYNTAX     INTEGER{pc-1dotx-priority(1),pcmm-priority(2),pcmm-application-type(3),scheduling-type(4),service-class-name(5)}
          MAX-ACCESS read-write
          STATUS     current
          DESCRIPTION
                "
                Indicates the admission control sub-type.
                Options:
                1. pc-1dotx-priority(1)     -Indicates PacketCable 1.x priority
                2. pcmm-priority(2)         -Indicates PacketCable multimedia priority
                3. pcmm-application-type(3) -Indicates PacketCable multimedia application type
                4. scheduling-type(4)       -Indicates scheduling type
                5. service-class-name(5)    -Indicates service class name
                "
              DEFVAL      { 1 }
          ::= { hwCmtsAdmissionCtrlMappingEntry 4 }

    hwCmtsAdmissionCtrlMappingPacketCablePriority OBJECT-TYPE
          SYNTAX     INTEGER{normal-priority(1),high-priority(2)}
          MAX-ACCESS read-write
          STATUS     current
          DESCRIPTION
                "
                Indicates the PacketCable priority.
                Options:
                1. normal-priority(1) -Indicates the PacketCable priority is normal
                2. high-priority(2)   -Indicates the PacketCable priority is high
                "
              DEFVAL      { 1 }
          ::= { hwCmtsAdmissionCtrlMappingEntry 5 }

    hwCmtsAdmissionCtrlMappingPcmmPriority OBJECT-TYPE
          SYNTAX     Integer32 (0..7)
          MAX-ACCESS read-write
          STATUS     current
          DESCRIPTION
                "Indicates the PacketCable Multimedia priority."
              DEFVAL      { 0 }
          ::= { hwCmtsAdmissionCtrlMappingEntry 6 }

    hwCmtsAdmissionCtrlMappingPcmmApplicationType OBJECT-TYPE
          SYNTAX     Integer32 (0..65535)
          MAX-ACCESS read-write
          STATUS     current
          DESCRIPTION
                "Indicates the PacketCable Multimedia application type."
              DEFVAL      { 0 }
          ::= { hwCmtsAdmissionCtrlMappingEntry 7 }

    hwCmtsAdmissionCtrlMappingSchedulingType OBJECT-TYPE
          SYNTAX     INTEGER{ugs(1),ugs-ad(2),rtps(3),nrtps(4),be(5)}
          MAX-ACCESS read-write
          STATUS     current
          DESCRIPTION
                "Indicates the scheduling type.
                Options:
                1. ugs(1)    -Indicates the scheduling type of unsolicited grant service
                2. ugs-ad(2) -Indicates the scheduling type of unsolicited grant service with activity detection
                3. rtps(3)   -Indicates the scheduling type of real-time polling service
                4. nrtps(4)  -Indicates the scheduling type of non-real-time polling service
                5. be(5)     -Indicates the scheduling type of best-effort
                "
              DEFVAL      { 1 }
          ::= { hwCmtsAdmissionCtrlMappingEntry 8 }

    hwCmtsAdmissionCtrlMappingServiceClassName OBJECT-TYPE
          SYNTAX     OCTET STRING(SIZE (0..15))
          MAX-ACCESS read-write
          STATUS     current
          DESCRIPTION
                "Indicates the service class name."
              DEFVAL      { 0 }
          ::= { hwCmtsAdmissionCtrlMappingEntry 9 }

    hwCmtsAdmissionCtrlMappingRowStatus OBJECT-TYPE
          SYNTAX     RowStatus
          MAX-ACCESS read-write
          STATUS     current
          DESCRIPTION
                "Indicates the row status to create or delete a admission control type mapping."
          ::= { hwCmtsAdmissionCtrlMappingEntry 10 }

  -- Table hwCmtsAdmissionCtrlPortBandwidthTable
    hwCmtsAdmissionCtrlPortBandwidthTable OBJECT-TYPE
          SYNTAX     SEQUENCE OF HwCmtsAdmissionCtrlPortBandwidthEntry
          MAX-ACCESS not-accessible
          STATUS     current
          DESCRIPTION
               "Indicates the admission control port bandwidth configuration.
               The indexes of this table are hwCmtsAdmissionCtrlPortBandwidthIfIndex and hwCmtsAdmissionCtrlPortBandwidthChannelType.
               "
          ::= { hwCmtsAccessObject 11 }

    hwCmtsAdmissionCtrlPortBandwidthEntry OBJECT-TYPE
          SYNTAX     HwCmtsAdmissionCtrlPortBandwidthEntry
          MAX-ACCESS not-accessible
          STATUS     current
          DESCRIPTION
               "Indicates the admission control port bandwidth configuration.
               The indexes of this entry are hwCmtsAdmissionCtrlPortBandwidthIfIndex and hwCmtsAdmissionCtrlPortBandwidthChannelType.
               "
          INDEX       { hwCmtsAdmissionCtrlPortBandwidthIfIndex, hwCmtsAdmissionCtrlPortBandwidthChannelType }
          ::= { hwCmtsAdmissionCtrlPortBandwidthTable 1 }

    HwCmtsAdmissionCtrlPortBandwidthEntry ::=
          SEQUENCE {
                    hwCmtsAdmissionCtrlPortBandwidthIfIndex       Integer32,
                    hwCmtsAdmissionCtrlPortBandwidthChannelType   INTEGER,
                    hwCmtsAdmissionCtrlPortBandwidthExclusiveList     OCTET STRING
                   }

    hwCmtsAdmissionCtrlPortBandwidthIfIndex OBJECT-TYPE
          SYNTAX  Integer32
          MAX-ACCESS  not-accessible
          STATUS  current
          DESCRIPTION
                "The index of admission control bandwidth table."
          ::= { hwCmtsAdmissionCtrlPortBandwidthEntry 1 }

    hwCmtsAdmissionCtrlPortBandwidthChannelType OBJECT-TYPE
          SYNTAX      INTEGER{uschannel(59),dschannel(60)}
          MAX-ACCESS  not-accessible
          STATUS  current
          DESCRIPTION
                "Indicates the channel type.
                Options:
                1. uschannel(59) -Indicates the channel type is upstream channel
                2. dschannel(60) -Indicates the channel type is downstream channel
                "
          ::= { hwCmtsAdmissionCtrlPortBandwidthEntry 2 }

    hwCmtsAdmissionCtrlPortBandwidthExclusiveList OBJECT-TYPE
          SYNTAX      OCTET STRING(SIZE (0..8))
          MAX-ACCESS  read-write
          STATUS  current
          DESCRIPTION
                "Indicates the exclusive threshold.Each byte represents an
                exclusive threshold for a admission control type.
                Bytes 0-7 indicate admission control types 0-7.
                The value for each byte is 0-100. Unit: %.
                When the value is 255, no exclusive threshold is
                configured for a admission control type. The sum of the
                exclusive thresholds of all the admission control types cannot exceed 100."
          ::= { hwCmtsAdmissionCtrlPortBandwidthEntry 3 }


   -- Table hwCmtsAdmissionCtrlChannelBandwidthTable
    hwCmtsAdmissionCtrlChannelBandwidthTable OBJECT-TYPE
          SYNTAX     SEQUENCE OF HwCmtsAdmissionCtrlChannelBandwidthEntry
          MAX-ACCESS not-accessible
          STATUS     current
          DESCRIPTION
               "Indicates the admission control channel bandwidth query.
               The indexes of this table are hwCmtsAdmissionCtrlChannelBandwidthIfIndex and hwCmtsAdmissionCtrlChannelBandwidthChannelType.
               "
          ::= { hwCmtsAccessObject 12 }

    hwCmtsAdmissionCtrlChannelBandwidthEntry OBJECT-TYPE
          SYNTAX     HwCmtsAdmissionCtrlChannelBandwidthEntry
          MAX-ACCESS not-accessible
          STATUS     current
          DESCRIPTION
               "Indicates the admission control channel bandwidth query.
               The indexes of this entry are hwCmtsAdmissionCtrlChannelBandwidthIfIndex and hwCmtsAdmissionCtrlChannelBandwidthChannelType.
               "
          INDEX       { hwCmtsAdmissionCtrlChannelBandwidthIfIndex,
                        hwCmtsAdmissionCtrlChannelBandwidthChannelType,
                        hwCmtsAdmissionCtrlChannelBandwidthChannelId }
          ::= { hwCmtsAdmissionCtrlChannelBandwidthTable 1 }

    HwCmtsAdmissionCtrlChannelBandwidthEntry ::=
          SEQUENCE {
                    hwCmtsAdmissionCtrlChannelBandwidthIfIndex       Integer32,
                    hwCmtsAdmissionCtrlChannelBandwidthChannelType   INTEGER,
                    hwCmtsAdmissionCtrlChannelBandwidthChannelId     Integer32,
                    hwCmtsAdmissionCtrlChannelBandwidthExclusiveList     OCTET STRING,
                    hwCmtsAdmissionCtrlChannelBandwidthCurrOccupyList    OCTET STRING
                   }

    hwCmtsAdmissionCtrlChannelBandwidthIfIndex OBJECT-TYPE
          SYNTAX  Integer32
          MAX-ACCESS  not-accessible
          STATUS  current
          DESCRIPTION
                "Indicates the the index of channel bandwidth table."
          ::= { hwCmtsAdmissionCtrlChannelBandwidthEntry 1 }

    hwCmtsAdmissionCtrlChannelBandwidthChannelType OBJECT-TYPE
          SYNTAX  INTEGER{uschannel(59),dschannel(60)}
          MAX-ACCESS  not-accessible
          STATUS  current
          DESCRIPTION
                "Indicates the channel type.
                Options:
                1. uschannel(59) -Indicates the channel type is upstream channel
                2. dschannel(60) -Indicates the channel type is downstream channel
                "
          ::= { hwCmtsAdmissionCtrlChannelBandwidthEntry 2 }

    hwCmtsAdmissionCtrlChannelBandwidthChannelId OBJECT-TYPE
          SYNTAX  Integer32(1..16)
          MAX-ACCESS  not-accessible
          STATUS  current
          DESCRIPTION
                "Indicates the channel ID.
                 Options:
                 Range is 1..4 if the channel type is upstream channel.
                 Range is 1..16 if the channel type is downstream channel.
                "
          ::= { hwCmtsAdmissionCtrlChannelBandwidthEntry 3 }

    hwCmtsAdmissionCtrlChannelBandwidthExclusiveList OBJECT-TYPE
          SYNTAX      OCTET STRING(SIZE (0..8))
          MAX-ACCESS  read-only
          STATUS  current
          DESCRIPTION
                "Indicates the exclusive threshold.
                Each byte represents an exclusive threshold for a
                admission control type.
                Bytes 0-7 indicate admission control types 0-7."
          ::= { hwCmtsAdmissionCtrlChannelBandwidthEntry 4 }

    hwCmtsAdmissionCtrlChannelBandwidthCurrOccupyList OBJECT-TYPE
          SYNTAX      OCTET STRING(SIZE (0..8))
          MAX-ACCESS  read-only
          STATUS  current
          DESCRIPTION
                " Indicates the usage of the minimum assured bandwidth."
          ::= { hwCmtsAdmissionCtrlChannelBandwidthEntry 5 }


  -- Table hwCmtsAdmissionCtrlStatisticsTable
    hwCmtsAdmissionCtrlStatisticsTable OBJECT-TYPE
          SYNTAX     SEQUENCE OF  HwCmtsAdmissionCtrlStatisticsEntry
          MAX-ACCESS not-accessible
          STATUS     current
          DESCRIPTION
               "Indicates the statistics of admission control admission.
               The indexes of this table are hwCmtsAdmissionCtrlStatisticsIfIndex,
               hwCmtsAdmissionCtrlStatisticsChannelType and hwCmtsAdmissionCtrlStatisticsChannelId.
               "
          ::= { hwCmtsAccessObject 13 }

    hwCmtsAdmissionCtrlStatisticsEntry OBJECT-TYPE
          SYNTAX     HwCmtsAdmissionCtrlStatisticsEntry
          MAX-ACCESS not-accessible
          STATUS     current
          DESCRIPTION
               "Indicates the statistics of admission control admission.
               The indexes of this entry are hwCmtsAdmissionCtrlStatisticsIfIndex,
               hwCmtsAdmissionCtrlStatisticsChannelType and hwCmtsAdmissionCtrlStatisticsChannelId.
               "
          INDEX       { hwCmtsAdmissionCtrlStatisticsIfIndex,
                        hwCmtsAdmissionCtrlStatisticsChannelType,
                        hwCmtsAdmissionCtrlStatisticsChannelId }
          ::= { hwCmtsAdmissionCtrlStatisticsTable 1 }

    HwCmtsAdmissionCtrlStatisticsEntry ::=
          SEQUENCE {
                    hwCmtsAdmissionCtrlStatisticsIfIndex                           Integer32,
                    hwCmtsAdmissionCtrlStatisticsChannelType                       INTEGER,
                    hwCmtsAdmissionCtrlStatisticsChannelId                         Integer32,
                    hwCmtsAdmissionCtrlExceedCmRegCountList                        OCTET STRING,
                    hwCmtsAdmissionCtrlExceedDynamicCountList                      OCTET STRING,
                    hwCmtsAdmissionCtrlCmRegRejectCountList                        OCTET STRING,
                    hwCmtsAdmissionCtrlDynamicRejectCountList                      OCTET STRING,
                    hwCmtsAdmissionCtrlStatisticsOper                               INTEGER
                   }

    hwCmtsAdmissionCtrlStatisticsIfIndex OBJECT-TYPE
          SYNTAX  Integer32
          MAX-ACCESS  not-accessible
          STATUS  current
          DESCRIPTION
                "Indicates the index of cable port."
          ::= { hwCmtsAdmissionCtrlStatisticsEntry 1 }

    hwCmtsAdmissionCtrlStatisticsChannelType OBJECT-TYPE
          SYNTAX  INTEGER{uschannel(59),dschannel(60)}
          MAX-ACCESS  not-accessible
          STATUS  current
          DESCRIPTION
                "Indicates the channel type of cable port.
                Options:
                1. uschannel(59) -Indicates the channel type of cable port is upstream channel
                2. dschannel(60) -Indicates the channel type of cable port is downstream channel
                "
          ::= { hwCmtsAdmissionCtrlStatisticsEntry 2 }

    hwCmtsAdmissionCtrlStatisticsChannelId OBJECT-TYPE
          SYNTAX  Integer32(1..16)
          MAX-ACCESS  not-accessible
          STATUS  current
          DESCRIPTION
                "Indicates the channel ID of cable port.
                 Options:
                 Range is 1..4 if the channel type is upstream channel.
                 Range is 1..16 if the channel type is downstream channel.
                "
          ::= { hwCmtsAdmissionCtrlStatisticsEntry 3 }

    hwCmtsAdmissionCtrlExceedCmRegCountList OBJECT-TYPE
          SYNTAX      OCTET STRING(SIZE (0..32))
          MAX-ACCESS  read-only
          STATUS  current
          DESCRIPTION
                "Indicates the number of CM registrations that exceed the exclusive threshold."
          ::= { hwCmtsAdmissionCtrlStatisticsEntry 4 }

    hwCmtsAdmissionCtrlExceedDynamicCountList OBJECT-TYPE
          SYNTAX      OCTET STRING(SIZE (0..32))
          MAX-ACCESS  read-only
          STATUS  current
          DESCRIPTION
                "Indicates the number of dynamic service flows that exceed the exclusive threshold."
          ::= { hwCmtsAdmissionCtrlStatisticsEntry 5 }

    hwCmtsAdmissionCtrlCmRegRejectCountList OBJECT-TYPE
          SYNTAX      OCTET STRING(SIZE (0..32))
          MAX-ACCESS  read-only
          STATUS  current
          DESCRIPTION
                "Indicates the Number of CM registrations rejected by the admission control entry mechanism."
          ::= { hwCmtsAdmissionCtrlStatisticsEntry 6 }

    hwCmtsAdmissionCtrlDynamicRejectCountList OBJECT-TYPE
          SYNTAX      OCTET STRING(SIZE (0..32))
          MAX-ACCESS  read-only
          STATUS  current
          DESCRIPTION
                "Indicates the number of dynamic service flows rejected by the admission control entry mechanism."
          ::= { hwCmtsAdmissionCtrlStatisticsEntry 7 }


    hwCmtsAdmissionCtrlStatisticsOper OBJECT-TYPE
          SYNTAX      INTEGER{clear(1) }
          MAX-ACCESS  read-write
          STATUS  current
          DESCRIPTION
                "Indicates the the operating mode.
                Options:
                1. clear(1) -Indicates clearing the statistics informations in the channel
                "
          ::= { hwCmtsAdmissionCtrlStatisticsEntry 8 }

  -- Table hwCmtsMtaBasicTable
    hwCmtsMtaBasicTable OBJECT-TYPE
          SYNTAX     SEQUENCE OF  HwCmtsMtaBasicEntry
          MAX-ACCESS not-accessible
          STATUS     current
          DESCRIPTION
               "Indicates the MTA info.
               The indexes of this table are hwCmtsMtaBasicIfIndex and hwCmtsMtaBasicMtaMacAddress."
          ::= { hwCmtsAccessObject 14 }

    hwCmtsMtaBasicEntry OBJECT-TYPE
          SYNTAX     HwCmtsMtaBasicEntry
          MAX-ACCESS not-accessible
          STATUS     current
          DESCRIPTION
               "Indicates the MTA info.
               The indexes of this entry are hwCmtsMtaBasicIfIndex and hwCmtsMtaBasicMtaMacAddress."
          INDEX       { hwCmtsMtaBasicIfIndex, hwCmtsMtaBasicMtaMacAddress }
          ::= { hwCmtsMtaBasicTable 1 }

    HwCmtsMtaBasicEntry ::=
          SEQUENCE {
                    hwCmtsMtaBasicIfIndex         Integer32,
                    hwCmtsMtaBasicMtaMacAddress   MacAddress,
                    hwCmtsMtaBasicCmIndex         Unsigned32,
                    hwCmtsMtaBasicCmMacAddress    MacAddress,
                    hwCmtsMtaBasicMtaIPAddress    IpAddress,
                    hwCmtsMtaBasicMtaPktcVersion        Integer32
                   }

    hwCmtsMtaBasicIfIndex OBJECT-TYPE
          SYNTAX  Integer32
          MAX-ACCESS  not-accessible
          STATUS  current
          DESCRIPTION
                "Indicates the index of cable port."
          ::= { hwCmtsMtaBasicEntry 1 }

    hwCmtsMtaBasicMtaMacAddress OBJECT-TYPE
          SYNTAX      MacAddress
          MAX-ACCESS  not-accessible
          STATUS  current
          DESCRIPTION
                "Indicates the MAC address of MTA."
          ::= { hwCmtsMtaBasicEntry 2 }

    hwCmtsMtaBasicCmIndex OBJECT-TYPE
          SYNTAX      Unsigned32 (1..4294967295)
          MAX-ACCESS  read-only
          STATUS  current
          DESCRIPTION
                "Indicates the index of CM."
          ::= { hwCmtsMtaBasicEntry 3 }

    hwCmtsMtaBasicCmMacAddress OBJECT-TYPE
          SYNTAX      MacAddress
          MAX-ACCESS  read-only
          STATUS  current
          DESCRIPTION
                "Indicates the MAC address of CM.
                The CM's MAC address cannot be a
                broadcast MAC address,multicast
                MAC address, or a MAC address
                consisting of all 0s."
          ::= { hwCmtsMtaBasicEntry 4 }

    hwCmtsMtaBasicMtaIPAddress OBJECT-TYPE
          SYNTAX      IpAddress
          MAX-ACCESS  read-only
          STATUS  current
          DESCRIPTION
                "Indicates the IP address of MTA."
          ::= { hwCmtsMtaBasicEntry 5 }

    hwCmtsMtaBasicMtaPktcVersion OBJECT-TYPE
          SYNTAX      Integer32(1..3)
          MAX-ACCESS  read-only
          STATUS  current
          DESCRIPTION
                "
		Indicates the version of PacketCable.
                1-PacketCable version 1.0
                2-PacketCable version 1.5
                3-PacketCable version 2.0
                -1 represent invalid version of PacketCable.
                "
          ::= { hwCmtsMtaBasicEntry 6 }


    -- Table hwCmtsCmOverCapaTable
    hwCmtsCmOverCapaTable OBJECT-TYPE
          SYNTAX     SEQUENCE OF HwCmtsCmOverCapaEntry
          MAX-ACCESS not-accessible
          STATUS     current
          DESCRIPTION
                "The table is used for the CMs that fail to go online
                 because the port has connected to the maximum number of CMs or the port is overloaded.
                 The index of this table is ifIndex.
                "
          ::= { hwCmtsAccessObject 15 }

    hwCmtsCmOverCapaEntry OBJECT-TYPE
          SYNTAX     HwCmtsCmOverCapaEntry
          MAX-ACCESS not-accessible
          STATUS     current
          DESCRIPTION
                "The table is used for the CMs that fail to go online
                 because the port has connected to the maximum number of CMs or the port is overloaded.
                 The index of this entry is ifIndex.
                "
          INDEX       { ifIndex }
          ::= { hwCmtsCmOverCapaTable 1 }

    HwCmtsCmOverCapaEntry ::=
          SEQUENCE {
                    hwCmtsCmOverCapaNum             Unsigned32,
                    hwCmtsCmOverCapaMacAddrList     OCTET STRING,
                    hwCmtsCmOverCapaTimeList        OCTET STRING,
                    hwCmtsCmOverCapaReasonList      OCTET STRING
                   }

    hwCmtsCmOverCapaNum OBJECT-TYPE
          SYNTAX  Unsigned32 (0..256)
          MAX-ACCESS  read-only
          STATUS  current
          DESCRIPTION
                "This node indicates the number of the CMs that fail to go online
                 because the port has connected to the maximum number of CMs or the port is overloaded.
                "
          ::= { hwCmtsCmOverCapaEntry 1 }

    hwCmtsCmOverCapaMacAddrList OBJECT-TYPE
          SYNTAX  OCTET STRING (SIZE (0..1536))
          MAX-ACCESS  read-only
          STATUS  current
          DESCRIPTION
                "This node indicates the MAC list. The MAC list records the MAC addresses of the CMs one by one.
                 The data type of the MAC address for each CM is MacAddress. Each record takes 6 bytes.
                "
          ::= { hwCmtsCmOverCapaEntry 2 }


    hwCmtsCmOverCapaTimeList OBJECT-TYPE
          SYNTAX  OCTET STRING (SIZE (0..3072))
          MAX-ACCESS  read-only
          STATUS  current
          DESCRIPTION
                "This node indicates the time list. The time list records the time of the CMs one by one.
                 The data type of the time for each CM is DateAndTime. Each record takes 11 bytes.
                "
          ::= { hwCmtsCmOverCapaEntry 3 }

    hwCmtsCmOverCapaReasonList OBJECT-TYPE
          SYNTAX  OCTET STRING (SIZE (0..512))
          MAX-ACCESS  read-only
          STATUS  current
          DESCRIPTION
                "This node indicates the reason list of the CMs that fail to go online
                 because the port has connected to the maximum number of CMs or the port is overloaded.
                 The reason list records the reason of the CMs one by one. Each record takes 1 bytes.
                 The value of the reason for each CM is
                 Option:
                 1: overspec(1)                   - The port has connected to the maximum number of CMs
                 2: overload(2)                   - The port is overloaded
                "
          ::= { hwCmtsCmOverCapaEntry 4 }

    hwCmtsSnrDetectTable OBJECT IDENTIFIER ::= { hwCmtsAccessObject  16 }
    -- Table hwCmtsSnrDetectTable

    hwCmtsSnrDetectPeriod OBJECT-TYPE
          SYNTAX  Integer32 (0..60000)
          UNITS   "ms"
          MAX-ACCESS  read-write
          STATUS  current
          DESCRIPTION
                "The snr detect period of a Spectrum Group.
                Set to 0 means close the snr detect. 1-999 is reserved
                Default: 0.
                Unit: ms."
          ::= { hwCmtsSnrDetectTable 1 }

    -- Table hwCmtsCmCurrTable
    hwCmtsCmCurrTable OBJECT-TYPE
          SYNTAX     SEQUENCE OF HwCmtsCmCurrEntry
          MAX-ACCESS not-accessible
          STATUS     current
          DESCRIPTION
                "
                Indicates the current performance statistics.
                The index of this table is hwCmtsCmCurrId.
                "
          ::= { hwCmtsAccessObject 17 }

    hwCmtsCmCurrEntry OBJECT-TYPE
          SYNTAX     HwCmtsCmCurrEntry
          MAX-ACCESS not-accessible
          STATUS     current
          DESCRIPTION
                "
                Indicates the current performance statistics.
                The index of this entry is hwCmtsCmCurrId.
                "
          INDEX       { hwCmtsCmCurrId }
          ::= { hwCmtsCmCurrTable 1 }

    HwCmtsCmCurrEntry ::=
          SEQUENCE {
                    hwCmtsCmCurrId                              Integer32,
                    hwCmtsCmCurr15MStartTime                    OCTET STRING,
                    hwCmtsCmCurr15MElapsedTime                  Integer32,
                    hwCmtsCmCurr15MValidityFlag                 Integer32,
                    hwCmtsCmCurr15MSuccessReg                   Counter32,
                    hwCmtsCmCurr15MFailReg                      Counter32,
                    hwCmtsCmCurr15MRepeatReg                    Counter32,
                    hwCmtsCmCurr15MSuccessPeriodRng             Counter32,
                    hwCmtsCmCurr15MPeriodRngLoss                Counter32,
                    hwCmtsCmCurr15MSeriousPeriodRngLoss         Counter32,
                    hwCmtsCmCurr15MPowerAdjust                  Counter32,
                    hwCmtsCmCurr15MSeriousPowerAdjust           Counter32,
                    hwCmtsCmCurr1DayStartTime                   OCTET STRING,
                    hwCmtsCmCurr1DayElapsedTime                 Integer32,
                    hwCmtsCmCurr1DayValidityFlag                Integer32,
                    hwCmtsCmCurr1DaySuccessReg                  Counter32,
                    hwCmtsCmCurr1DayFailReg                     Counter32,
                    hwCmtsCmCurr1DayRepeatReg                   Counter32,
                    hwCmtsCmCurr1DaySuccessPeriodRng            Counter32,
                    hwCmtsCmCurr1DayPeriodRngLoss               Counter32,
                    hwCmtsCmCurr1DaySeriousPeriodRngLoss        Counter32,
                    hwCmtsCmCurr1DayPowerAdjust                 Counter32,
                    hwCmtsCmCurr1DaySeriousPowerAdjust          Counter32,
                    hwCmtsCmCurrEverBeforeStartTime             OCTET STRING,
                    hwCmtsCmCurrEverBeforeElapsedTime           Integer32,
                    hwCmtsCmCurrEverBeforeValidityFlag          Integer32,
                    hwCmtsCmCurrEverBeforeSuccessReg            Counter32,
                    hwCmtsCmCurrEverBeforeFailReg               Counter32,
                    hwCmtsCmCurrEverBeforeRepeatReg             Counter32,
                    hwCmtsCmCurrEverBeforeSuccessPeriodRng      Counter32,
                    hwCmtsCmCurrEverBeforePeriodRngLoss         Counter32,
                    hwCmtsCmCurrEverBeforeSeriousPeriodRngLoss  Counter32,
                    hwCmtsCmCurrEverBeforePowerAdjust           Counter32,
                    hwCmtsCmCurrEverBeforeSeriousPowerAdjust    Counter32,
                    hwCmtsCmCurrEverBeforeUnstableConnectionCount     Integer32,
                    hwCmtsCmCurrEverBeforeLastUnstableConnectionTime  DateAndTime,
                    hwCmtsCmCurrEverBeforeFirstUnstableConnectionTime DateAndTime,
                    hwCmtsCmCurrEverBeforeLastRepeatRegTime     DateAndTime,
                    hwCmtsCmCurrEverBeforeFirstRepeatRegTime    DateAndTime,
                    hwCmtsCmCurrEverBeforeLastSeriousPeriodRngLossTime  DateAndTime,
                    hwCmtsCmCurrEverBeforeFirstSeriousPeriodRngLossTime DateAndTime,
                    hwCmtsCmCurrEverBeforeLastSeriousPowerAdjustTime    DateAndTime,
                    hwCmtsCmCurrEverBeforeFirstSeriousPowerAdjustTime   DateAndTime
                   }

    hwCmtsCmCurrId OBJECT-TYPE
          SYNTAX  Integer32 (1..16128)
          MAX-ACCESS   not-accessible
          STATUS  current
          DESCRIPTION
                "
                Indicates a CM index.
                "
          ::= { hwCmtsCmCurrEntry 1 }

    hwCmtsCmCurr15MStartTime OBJECT-TYPE
          SYNTAX  OCTET STRING
          MAX-ACCESS  read-only
          STATUS  current
          DESCRIPTION
                "
                Indicates the start time of the current 15-minute statistical period.
                "
          ::= { hwCmtsCmCurrEntry 2 }


    hwCmtsCmCurr15MElapsedTime OBJECT-TYPE
          SYNTAX  Integer32
          MAX-ACCESS  read-only
          STATUS  current
          DESCRIPTION
                "
                Indicates the elapsed time in the current 15-minute statistical period.
                Unit: s.
                "
          ::= { hwCmtsCmCurrEntry 3 }

    hwCmtsCmCurr15MValidityFlag OBJECT-TYPE
          SYNTAX  Integer32 (1..2)
          MAX-ACCESS  read-only
          STATUS  current
          DESCRIPTION
                "
                Indicates the flag for statistical information.
                Options:
                1-Yes
                2-No
                "
          ::= { hwCmtsCmCurrEntry 4 }

    hwCmtsCmCurr15MSuccessReg OBJECT-TYPE
          SYNTAX  Counter32
          MAX-ACCESS  read-only
          STATUS  current
          DESCRIPTION
                "
                Indicates the number of registration requests initiated by a CM during the current 15-minute.
                "
          ::= { hwCmtsCmCurrEntry 5 }

    hwCmtsCmCurr15MFailReg OBJECT-TYPE
          SYNTAX  Counter32
          MAX-ACCESS  read-only
          STATUS  current
          DESCRIPTION
                "
                Indicates the number of CM registration failures during the current 15-minute.
                "
          ::= { hwCmtsCmCurrEntry 6 }

    hwCmtsCmCurr15MRepeatReg OBJECT-TYPE
          SYNTAX  Counter32
          MAX-ACCESS  read-only
          STATUS  current
          DESCRIPTION
                "
                Indicates the number of repeated registrations during the current 15-minute.
                "
          ::= { hwCmtsCmCurrEntry 7 }

    hwCmtsCmCurr15MSuccessPeriodRng OBJECT-TYPE
          SYNTAX  Counter32
          MAX-ACCESS  read-only
          STATUS  current
          DESCRIPTION
                "
                Indicates the number of periodic ranging requests initiated by a CM during the current 15-minute.
                "
          ::= { hwCmtsCmCurrEntry 8 }

    hwCmtsCmCurr15MPeriodRngLoss OBJECT-TYPE
          SYNTAX  Counter32
          MAX-ACCESS  read-only
          STATUS  current
          DESCRIPTION
                "
                Indicates the number of lost periodic ranging requests initiated by a CM during the current 15-minute.
                "
          ::= { hwCmtsCmCurrEntry 9 }

    hwCmtsCmCurr15MSeriousPeriodRngLoss OBJECT-TYPE
          SYNTAX  Counter32
          MAX-ACCESS  read-only
          STATUS  current
          DESCRIPTION
                "
                Indicates the number of consecutive periodic ranging request failures during the current 15-minute.
                "
          ::= { hwCmtsCmCurrEntry 10 }

    hwCmtsCmCurr15MPowerAdjust OBJECT-TYPE
          SYNTAX  Counter32
          MAX-ACCESS  read-only
          STATUS  current
          DESCRIPTION
                "
                Indicates the number of CM transmit power adjustments during the current 15-minute.
                "
          ::= { hwCmtsCmCurrEntry 11 }

    hwCmtsCmCurr15MSeriousPowerAdjust OBJECT-TYPE
          SYNTAX  Counter32
          MAX-ACCESS  read-only
          STATUS  current
          DESCRIPTION
                "
                Indicates the number of severe CM transmit power adjustments during the current 15-minute.
                "
          ::= { hwCmtsCmCurrEntry 12 }


    hwCmtsCmCurr1DayStartTime OBJECT-TYPE
          SYNTAX  OCTET STRING
          MAX-ACCESS  read-only
          STATUS  current
          DESCRIPTION
                "
                Indicates the start time of the current 24-hour statistical period.
                "
          ::= { hwCmtsCmCurrEntry 13 }


    hwCmtsCmCurr1DayElapsedTime OBJECT-TYPE
          SYNTAX  Integer32
          MAX-ACCESS  read-only
          STATUS  current
          DESCRIPTION
                "
                Indicates the elapsed time in the current 24-hour statistical period.
                Unit: s.
                "
          ::= { hwCmtsCmCurrEntry 14 }

    hwCmtsCmCurr1DayValidityFlag OBJECT-TYPE
          SYNTAX  Integer32 (1..2)
          MAX-ACCESS  read-only
          STATUS  current
          DESCRIPTION
                "
                Indicates the flag for statistical information.
                Options:
                1-Yes
                2-No
                "
          ::= { hwCmtsCmCurrEntry 15 }

    hwCmtsCmCurr1DaySuccessReg OBJECT-TYPE
          SYNTAX  Counter32
          MAX-ACCESS  read-only
          STATUS  current
          DESCRIPTION
                "
                Indicates the number of registration requests initiated by a CM during the current 24-hour.
                "
          ::= { hwCmtsCmCurrEntry 16 }

    hwCmtsCmCurr1DayFailReg OBJECT-TYPE
          SYNTAX  Counter32
          MAX-ACCESS  read-only
          STATUS  current
          DESCRIPTION
                "
                Indicates the number of CM registration failures during the current 24-hour.
                "
          ::= { hwCmtsCmCurrEntry 17 }

    hwCmtsCmCurr1DayRepeatReg OBJECT-TYPE
          SYNTAX  Counter32
          MAX-ACCESS  read-only
          STATUS  current
          DESCRIPTION
                "
                Indicates the number of repeated registrations during the current 24-hour.
                "
          ::= { hwCmtsCmCurrEntry 18 }

    hwCmtsCmCurr1DaySuccessPeriodRng OBJECT-TYPE
          SYNTAX  Counter32
          MAX-ACCESS  read-only
          STATUS  current
          DESCRIPTION
                "
                Indicates the number of periodic ranging requests initiated by a CM during the current 24-hour.
                "
          ::= { hwCmtsCmCurrEntry 19 }

    hwCmtsCmCurr1DayPeriodRngLoss OBJECT-TYPE
          SYNTAX  Counter32
          MAX-ACCESS  read-only
          STATUS  current
          DESCRIPTION
                "
                Indicates the number of lost periodic ranging requests initiated by a CM during the current 24-hour.
                "
          ::= { hwCmtsCmCurrEntry 20 }

    hwCmtsCmCurr1DaySeriousPeriodRngLoss OBJECT-TYPE
          SYNTAX  Counter32
          MAX-ACCESS  read-only
          STATUS  current
          DESCRIPTION
                "
                Indicates the number of consecutive periodic ranging request failures during the current 24-hour.
                "
          ::= { hwCmtsCmCurrEntry 21 }

    hwCmtsCmCurr1DayPowerAdjust OBJECT-TYPE
          SYNTAX  Counter32
          MAX-ACCESS  read-only
          STATUS  current
          DESCRIPTION
                "
                Indicates the number of CM transmit power adjustments during the current 24-hour.
                "
          ::= { hwCmtsCmCurrEntry 22 }

    hwCmtsCmCurr1DaySeriousPowerAdjust OBJECT-TYPE
          SYNTAX  Counter32
          MAX-ACCESS  read-only
          STATUS  current
          DESCRIPTION
                "
                Indicates the number of severe CM transmit power adjustments during the current 24-hour.
                "
          ::= { hwCmtsCmCurrEntry 23 }

    hwCmtsCmCurrEverBeforeStartTime OBJECT-TYPE
          SYNTAX  OCTET STRING
          MAX-ACCESS  read-only
          STATUS  current
          DESCRIPTION
                "
                Indicates the start time of the statistical period.
                "
          ::= { hwCmtsCmCurrEntry 24 }


    hwCmtsCmCurrEverBeforeElapsedTime OBJECT-TYPE
          SYNTAX  Integer32
          MAX-ACCESS  read-only
          STATUS  current
          DESCRIPTION
                "
                Indicates the elapsed time in the statistical period.
                Unit: s.
                "
          ::= { hwCmtsCmCurrEntry 25 }

    hwCmtsCmCurrEverBeforeValidityFlag OBJECT-TYPE
          SYNTAX  Integer32 (1..2)
          MAX-ACCESS  read-only
          STATUS  current
          DESCRIPTION
                "
                Indicates the flag for statistical information.
                Options:
                1-Yes
                2-No
                "
          ::= { hwCmtsCmCurrEntry 26 }

    hwCmtsCmCurrEverBeforeSuccessReg OBJECT-TYPE
          SYNTAX  Counter32
          MAX-ACCESS  read-only
          STATUS  current
          DESCRIPTION
                "
                Indicates the number of previous successfully registered.
                "
          ::= { hwCmtsCmCurrEntry 27 }

    hwCmtsCmCurrEverBeforeFailReg OBJECT-TYPE
          SYNTAX  Counter32
          MAX-ACCESS  read-only
          STATUS  current
          DESCRIPTION
                "
                Indicates the number of previous registration failed.
                "
          ::= { hwCmtsCmCurrEntry 28 }

    hwCmtsCmCurrEverBeforeRepeatReg OBJECT-TYPE
          SYNTAX  Counter32
          MAX-ACCESS  read-only
          STATUS  current
          DESCRIPTION
                "
                Indicates the number of previous repeated registration.
                "
          ::= { hwCmtsCmCurrEntry 29 }

    hwCmtsCmCurrEverBeforeSuccessPeriodRng OBJECT-TYPE
          SYNTAX  Counter32
          MAX-ACCESS  read-only
          STATUS  current
          DESCRIPTION
                "
                Indicates the number of previous periodic ranging request.
                "
          ::= { hwCmtsCmCurrEntry 30 }

    hwCmtsCmCurrEverBeforePeriodRngLoss OBJECT-TYPE
          SYNTAX  Counter32
          MAX-ACCESS  read-only
          STATUS  current
          DESCRIPTION
                "
                Indicates the number of previous loss of periodic ranging request.
                "
          ::= { hwCmtsCmCurrEntry 31 }

    hwCmtsCmCurrEverBeforeSeriousPeriodRngLoss OBJECT-TYPE
          SYNTAX  Counter32
          MAX-ACCESS  read-only
          STATUS  current
          DESCRIPTION
                "
                Indicates the number of previous loss of the severe periodic ranging request.
                "
          ::= { hwCmtsCmCurrEntry 32 }

    hwCmtsCmCurrEverBeforePowerAdjust OBJECT-TYPE
          SYNTAX  Counter32
          MAX-ACCESS  read-only
          STATUS  current
          DESCRIPTION
                "
                Indicates the number of previous transmit power adjustment.
                "
          ::= { hwCmtsCmCurrEntry 33 }

    hwCmtsCmCurrEverBeforeSeriousPowerAdjust OBJECT-TYPE
          SYNTAX  Counter32
          MAX-ACCESS  read-only
          STATUS  current
          DESCRIPTION
                " 
                Indicates the number of previous severe power adjustment.
                "
          ::= { hwCmtsCmCurrEntry 34 } 	 
          
   hwCmtsCmCurrEverBeforeUnstableConnectionCount OBJECT-TYPE
          SYNTAX  Integer32
          MAX-ACCESS  read-only
          STATUS  current
          DESCRIPTION
                " 
                Indicates the number of previous unstable connection.
                "
          ::= { hwCmtsCmCurrEntry 35 } 
          
    hwCmtsCmCurrEverBeforeLastUnstableConnectionTime OBJECT-TYPE
          SYNTAX  DateAndTime
          MAX-ACCESS  read-only
          STATUS  current
          DESCRIPTION
                " 
                Indicates the time of the latest unstable connection.
                "
          ::= { hwCmtsCmCurrEntry 36 }
          
    hwCmtsCmCurrEverBeforeFirstUnstableConnectionTime OBJECT-TYPE
          SYNTAX  DateAndTime
          MAX-ACCESS  read-only
          STATUS  current
          DESCRIPTION
                " 
                Indicates the time of the first unstable connection.
                "
          ::= { hwCmtsCmCurrEntry 37 }
      
       hwCmtsCmCurrEverBeforeLastRepeatRegTime OBJECT-TYPE
          SYNTAX  DateAndTime
          MAX-ACCESS  read-only
          STATUS  current
          DESCRIPTION
                " 
                Indicates the time of the latest repeated registration.
                "
          ::= { hwCmtsCmCurrEntry 38 }
          
        hwCmtsCmCurrEverBeforeFirstRepeatRegTime OBJECT-TYPE
          SYNTAX  DateAndTime
          MAX-ACCESS  read-only
          STATUS  current
          DESCRIPTION
                " 
                Indicates the time of the first repeated registration.
                "
          ::= { hwCmtsCmCurrEntry 39 }
          
        hwCmtsCmCurrEverBeforeLastSeriousPeriodRngLossTime OBJECT-TYPE
          SYNTAX  DateAndTime
          MAX-ACCESS  read-only
          STATUS  current
          DESCRIPTION
                " 
                Indicates the time of the latest loss of the severe periodic ranging request.
                "
          ::= { hwCmtsCmCurrEntry 40 }
          
        hwCmtsCmCurrEverBeforeFirstSeriousPeriodRngLossTime OBJECT-TYPE
          SYNTAX  DateAndTime
          MAX-ACCESS  read-only
          STATUS  current
          DESCRIPTION
                " 
                 ndicates the time of the first loss of the severe periodic ranging request.
                "
          ::= { hwCmtsCmCurrEntry 41 }
          
         hwCmtsCmCurrEverBeforeLastSeriousPowerAdjustTime OBJECT-TYPE
          SYNTAX  DateAndTime
          MAX-ACCESS  read-only
          STATUS  current
          DESCRIPTION
                "
                Indicates the time of the lastest severe power adjustment.
                "
          ::= { hwCmtsCmCurrEntry 42 }
          
         hwCmtsCmCurrEverBeforeFirstSeriousPowerAdjustTime OBJECT-TYPE
          SYNTAX  DateAndTime
          MAX-ACCESS  read-only
          STATUS  current
          DESCRIPTION
                " 
                Indicates the time of the first severe power adjustment.
                "
          ::= { hwCmtsCmCurrEntry 43 }
        

    -- Table hwCmtsCmHist15MinTable
    hwCmtsCmHist15MinTable OBJECT-TYPE
          SYNTAX     SEQUENCE OF HwCmtsCmHist15MinEntry
          MAX-ACCESS not-accessible
          STATUS     current
          DESCRIPTION
                "
                Indicates the historical 15-minute performance statistics.
                The indexes of this table are hwCmtsCmHist15MId and hwCmtsCmHist15MInterval.
                "
          ::= { hwCmtsAccessObject 18 }

    hwCmtsCmHist15MinEntry OBJECT-TYPE
          SYNTAX     HwCmtsCmHist15MinEntry
          MAX-ACCESS not-accessible
          STATUS     current
          DESCRIPTION
                "
                Indicates the historical 15-minute performance statistics.
                The indexes of this entry are hwCmtsCmHist15MId and hwCmtsCmHist15MInterval.
                "
          INDEX       { hwCmtsCmHist15MId, hwCmtsCmHist15MInterval }
          ::= { hwCmtsCmHist15MinTable 1 }

    HwCmtsCmHist15MinEntry ::=
          SEQUENCE {
                    hwCmtsCmHist15MId                    Integer32,
                    hwCmtsCmHist15MInterval              Integer32,
                    hwCmtsCmHist15MStartTime             OCTET STRING,
                    hwCmtsCmHist15MElapsedTime           Integer32,
                    hwCmtsCmHist15MValidityFlag          Integer32,
                    hwCmtsCmHist15MSuccessReg            Counter32,
                    hwCmtsCmHist15MFailReg               Counter32,
                    hwCmtsCmHist15MRepeatReg             Counter32,
                    hwCmtsCmHist15MSuccessPeriodRng      Counter32,
                    hwCmtsCmHist15MPeriodRngLoss         Counter32,
                    hwCmtsCmHist15MSeriousPeriodRngLoss  Counter32,
                    hwCmtsCmHist15MPowerAdjust           Counter32,
                    hwCmtsCmHist15MSeriousPowerAdjust    Counter32
                   }



    hwCmtsCmHist15MId OBJECT-TYPE
          SYNTAX  Integer32 (1..16128)
          MAX-ACCESS   not-accessible
          STATUS  current
          DESCRIPTION
                "
                Indicates a CM index.
                "
          ::= { hwCmtsCmHist15MinEntry 1 }

    hwCmtsCmHist15MInterval OBJECT-TYPE
          SYNTAX  Integer32 (1..96)
          MAX-ACCESS   not-accessible
          STATUS  current
          DESCRIPTION
                "
                The previous 15 minutes are considered as the first range.
                The greater the value, the earlier the time.
                "
          ::= { hwCmtsCmHist15MinEntry 2 }

    hwCmtsCmHist15MStartTime OBJECT-TYPE
          SYNTAX  OCTET STRING
          MAX-ACCESS  read-only
          STATUS  current
          DESCRIPTION
                "
                Indicates the start time of a statistical period.
                "
          ::= { hwCmtsCmHist15MinEntry 3 }

    hwCmtsCmHist15MElapsedTime OBJECT-TYPE
          SYNTAX  Integer32
          MAX-ACCESS  read-only
          STATUS  current
          DESCRIPTION
                "
                Indicates the elapsed time in a statistical period.
                Unit: s.
                "
          ::= { hwCmtsCmHist15MinEntry 4 }

    hwCmtsCmHist15MValidityFlag OBJECT-TYPE
          SYNTAX  Integer32 (1..2)
          MAX-ACCESS  read-only
          STATUS  current
          DESCRIPTION
                "
                Indicates the flag for statistical information.
                Options:
                1-Yes
                2-No
                "
          ::= { hwCmtsCmHist15MinEntry 5 }





    hwCmtsCmHist15MSuccessReg OBJECT-TYPE
          SYNTAX  Counter32
          MAX-ACCESS  read-only
          STATUS  current
          DESCRIPTION
                "
                Indicates the number of registration requests initiated by a CM during the historical 15-minute.
                "
          ::= { hwCmtsCmHist15MinEntry 6 }

    hwCmtsCmHist15MFailReg OBJECT-TYPE
          SYNTAX  Counter32
          MAX-ACCESS  read-only
          STATUS  current
          DESCRIPTION
                "
                Indicates the number of CM registration failures during the historical 15-minute.
                "
          ::= { hwCmtsCmHist15MinEntry 7 }

    hwCmtsCmHist15MRepeatReg OBJECT-TYPE
          SYNTAX  Counter32
          MAX-ACCESS  read-only
          STATUS  current
          DESCRIPTION
                "
                Indicates the number of repeated registrations during the historical 15-minute.
                "
          ::= { hwCmtsCmHist15MinEntry 8 }

    hwCmtsCmHist15MSuccessPeriodRng OBJECT-TYPE
          SYNTAX  Counter32
          MAX-ACCESS  read-only
          STATUS  current
          DESCRIPTION
                "
                Indicates the number of periodic ranging requests initiated by a CM during the historical 15-minute.
                "
          ::= { hwCmtsCmHist15MinEntry 9 }

    hwCmtsCmHist15MPeriodRngLoss OBJECT-TYPE
          SYNTAX  Counter32
          MAX-ACCESS  read-only
          STATUS  current
          DESCRIPTION
                "
                Indicates the number of lost periodic ranging requests initiated by a CM during the historical 15-minute.
                "
          ::= { hwCmtsCmHist15MinEntry 10 }

    hwCmtsCmHist15MSeriousPeriodRngLoss OBJECT-TYPE
          SYNTAX  Counter32
          MAX-ACCESS  read-only
          STATUS  current
          DESCRIPTION
                "
                Indicates the number of consecutive periodic ranging request failures during the historical 15-minute.
                "
          ::= { hwCmtsCmHist15MinEntry 11 }

    hwCmtsCmHist15MPowerAdjust OBJECT-TYPE
          SYNTAX  Counter32
          MAX-ACCESS  read-only
          STATUS  current
          DESCRIPTION
                "
                Indicates the number of CM transmit power adjustments during the historical 15-minute.
                "
          ::= { hwCmtsCmHist15MinEntry 12 }

    hwCmtsCmHist15MSeriousPowerAdjust OBJECT-TYPE
          SYNTAX  Counter32
          MAX-ACCESS  read-only
          STATUS  current
          DESCRIPTION
                "
                Indicates the number of severe CM transmit power adjustments during the historical 15-minute.
                "
          ::= { hwCmtsCmHist15MinEntry 13 }




    -- Table hwCmtsCmHist1DayTable
    hwCmtsCmHist1DayTable OBJECT-TYPE
          SYNTAX     SEQUENCE OF HwCmtsCmHist1DayEntry
          MAX-ACCESS not-accessible
          STATUS     current
          DESCRIPTION
                "
                Indicates the historical 24-hour performance statistics.
                The indexes of this table are hwCmtsCmHist1DayId and hwCmtsCmHist1DayInterval.
                "
          ::= { hwCmtsAccessObject 19 }

    hwCmtsCmHist1DayEntry OBJECT-TYPE
          SYNTAX     HwCmtsCmHist1DayEntry
          MAX-ACCESS not-accessible
          STATUS     current
          DESCRIPTION
                "
                Indicates the historical 24-hour performance statistics.
                The indexes of this entry are hwCmtsCmHist1DayId and hwCmtsCmHist1DayInterval.
                 "
          INDEX       { hwCmtsCmHist1DayId, hwCmtsCmHist1DayInterval }
          ::= { hwCmtsCmHist1DayTable 1 }

    HwCmtsCmHist1DayEntry ::=
          SEQUENCE {
                    hwCmtsCmHist1DayId                    Integer32,
                    hwCmtsCmHist1DayInterval              Integer32,
                    hwCmtsCmHist1DayStartTime             OCTET STRING,
                    hwCmtsCmHist1DayElapsedTime           Integer32,
                    hwCmtsCmHist1DayValidityFlag          Integer32,
                    hwCmtsCmHist1DaySuccessReg            Counter32,
                    hwCmtsCmHist1DayFailReg               Counter32,
                    hwCmtsCmHist1DayRepeatReg             Counter32,
                    hwCmtsCmHist1DaySuccessPeriodRng      Counter32,
                    hwCmtsCmHist1DayPeriodRngLoss         Counter32,
                    hwCmtsCmHist1DaySeriousPeriodRngLoss  Counter32,
                    hwCmtsCmHist1DayPowerAdjust           Counter32,
                    hwCmtsCmHist1DaySeriousPowerAdjust    Counter32
                   }



    hwCmtsCmHist1DayId OBJECT-TYPE
          SYNTAX  Integer32 (1..16128)
          MAX-ACCESS   not-accessible
          STATUS  current
          DESCRIPTION
                "
                Indicates a CM index.
                "
          ::= { hwCmtsCmHist1DayEntry 1 }

    hwCmtsCmHist1DayInterval OBJECT-TYPE
          SYNTAX  Integer32 (1..30)
          MAX-ACCESS   not-accessible
          STATUS  current
          DESCRIPTION
                "
                The previous 24 hours are considered as the first range.
                The greater the value, the earlier the time.
                "
          ::= { hwCmtsCmHist1DayEntry 2 }

    hwCmtsCmHist1DayStartTime OBJECT-TYPE
          SYNTAX  OCTET STRING
          MAX-ACCESS  read-only
          STATUS  current
          DESCRIPTION
                "
                Indicates the start time of a statistical period.
                "
          ::= { hwCmtsCmHist1DayEntry 3 }

    hwCmtsCmHist1DayElapsedTime OBJECT-TYPE
          SYNTAX  Integer32
          MAX-ACCESS  read-only
          STATUS  current
          DESCRIPTION
                "
                Indicates the elapsed time in a statistical period.
                Unit: s.
                "
          ::= { hwCmtsCmHist1DayEntry 4 }

    hwCmtsCmHist1DayValidityFlag OBJECT-TYPE
          SYNTAX  Integer32 (1..2)
          MAX-ACCESS  read-only
          STATUS  current
          DESCRIPTION
                "
                Indicates the flag for statistical information.
                Options:
                1-Yes
                2-No
                "
          ::= { hwCmtsCmHist1DayEntry 5 }





    hwCmtsCmHist1DaySuccessReg OBJECT-TYPE
          SYNTAX  Counter32
          MAX-ACCESS  read-only
          STATUS  current
          DESCRIPTION
                "
                Indicates the number of registration requests initiated by a CM during the historical 24-hour.
                "
          ::= { hwCmtsCmHist1DayEntry 6 }

    hwCmtsCmHist1DayFailReg OBJECT-TYPE
          SYNTAX  Counter32
          MAX-ACCESS  read-only
          STATUS  current
          DESCRIPTION
                "
                Indicates the number of CM registration failures during the historical 24-hour.
                "
          ::= { hwCmtsCmHist1DayEntry 7 }

    hwCmtsCmHist1DayRepeatReg OBJECT-TYPE
          SYNTAX  Counter32
          MAX-ACCESS  read-only
          STATUS  current
          DESCRIPTION
                "
                Indicates the number of repeated registrations during the historical 24-hour.
                "
          ::= { hwCmtsCmHist1DayEntry 8 }

    hwCmtsCmHist1DaySuccessPeriodRng OBJECT-TYPE
          SYNTAX  Counter32
          MAX-ACCESS  read-only
          STATUS  current
          DESCRIPTION
                "
                Indicates the number of periodic ranging requests initiated by a CM during the historical 24-hour.
                "
          ::= { hwCmtsCmHist1DayEntry 9 }

    hwCmtsCmHist1DayPeriodRngLoss OBJECT-TYPE
          SYNTAX  Counter32
          MAX-ACCESS  read-only
          STATUS  current
          DESCRIPTION
                "
                Indicates the number of lost periodic ranging requests initiated by a CM during the historical 24-hour.
                "
          ::= { hwCmtsCmHist1DayEntry 10 }

    hwCmtsCmHist1DaySeriousPeriodRngLoss OBJECT-TYPE
          SYNTAX  Counter32
          MAX-ACCESS  read-only
          STATUS  current
          DESCRIPTION
                "
                Indicates the number of consecutive periodic ranging request failures during the historical 24-hour.
                "
          ::= { hwCmtsCmHist1DayEntry 11 }

    hwCmtsCmHist1DayPowerAdjust OBJECT-TYPE
          SYNTAX  Counter32
          MAX-ACCESS  read-only
          STATUS  current
          DESCRIPTION
                "
                Indicates the number of CM transmit power adjustments during the historical 24-hour.
                "
          ::= { hwCmtsCmHist1DayEntry 12 }

    hwCmtsCmHist1DaySeriousPowerAdjust OBJECT-TYPE
          SYNTAX  Counter32
          MAX-ACCESS  read-only
          STATUS  current
          DESCRIPTION
                "
                Indicates the number of severe CM transmit power adjustments during the historical 24-hour.
                "
          ::= { hwCmtsCmHist1DayEntry 13 }





  hwCmtsCmStatThresholdTable OBJECT IDENTIFIER ::= { hwCmtsAccessObject  20}
    -- Table hwCmtsCmStatThresholdTable

    hwCmtsCmStatThresholdRepeatReg OBJECT-TYPE
          SYNTAX  Integer32 (60..86400)
          MAX-ACCESS  read-write
          STATUS  current
          DESCRIPTION
                "
                Indicates the repeated registration interval.
                Unit: s.
                Default value: 180.
                "
          ::= { hwCmtsCmStatThresholdTable 1 }

    hwCmtsCmStatThresholdSeriousPeriodRngLoss OBJECT-TYPE
          SYNTAX  Integer32 (1..12)
          MAX-ACCESS  read-write
          STATUS  current
          DESCRIPTION
                "
                Indicates the severe loss threshold for periodic ranging requests.
                Default value: 6.
                "
          ::= { hwCmtsCmStatThresholdTable 2 }

    hwCmtsCmStatThresholdSeriousPowerAdjust OBJECT-TYPE
          SYNTAX  Integer32 (1..10)
          MAX-ACCESS  read-write
          STATUS  current
          DESCRIPTION
                "
                Indicates the severe power adjustment threshold.
                Unit: dB.
                Default value: 2.
                "
          ::= { hwCmtsCmStatThresholdTable 3 }


    -- Table hwDocsIfCmtsIPToCmTable
    hwDocsIfCmtsIPToCmTable OBJECT-TYPE
          SYNTAX     SEQUENCE OF HwDocsIfCmtsIPToCmEntry
          MAX-ACCESS not-accessible
          STATUS     current
          DESCRIPTION
                "
                Indicates the CM index queried by the IP address of a CM.
                The index of this table is hwDocsIfCmtsCmIPAddr.
                "
          ::= { hwCmtsAccessObject 21 }

    hwDocsIfCmtsIPToCmEntry OBJECT-TYPE
          SYNTAX     HwDocsIfCmtsIPToCmEntry
          MAX-ACCESS not-accessible
          STATUS     current
          DESCRIPTION
                "
                Indicates the CM index queried by the IP address of a CM.
                The index of this entry is hwDocsIfCmtsCmIPAddr.
                 "
          INDEX       { hwDocsIfCmtsCmIPAddr }
          ::= { hwDocsIfCmtsIPToCmTable 1 }

    HwDocsIfCmtsIPToCmEntry ::=
          SEQUENCE {
                    hwDocsIfCmtsCmIPAddr       IpAddress,
                    hwDocsIfCmtsCmPtr          Integer32
                   }

    hwDocsIfCmtsCmIPAddr OBJECT-TYPE
          SYNTAX  IpAddress
          MAX-ACCESS   not-accessible
          STATUS  current
          DESCRIPTION
                "
                Indicates the IP address of the CM.
                "
          ::= { hwDocsIfCmtsIPToCmEntry 1 }

    hwDocsIfCmtsCmPtr OBJECT-TYPE
          SYNTAX  Integer32 (1..12168)
          MAX-ACCESS   read-only
          STATUS  current
          DESCRIPTION
                "
                Indicates the CM index.
                "
          ::= { hwDocsIfCmtsIPToCmEntry 2 }


    -- Table hwCmtsMtaInfoTable
    hwCmtsMtaInfoTable OBJECT-TYPE
          SYNTAX     SEQUENCE OF HwCmtsMtaInfoEntry
          MAX-ACCESS not-accessible
          STATUS     current
          DESCRIPTION
                "
                Indicates the basic information about the media terminal adapter (MTA).
                The index of this table is hwCmtsMtaInfoCmId.
                "
          ::= { hwCmtsAccessObject 22 }

    hwCmtsMtaInfoEntry OBJECT-TYPE
          SYNTAX     HwCmtsMtaInfoEntry
          MAX-ACCESS not-accessible
          STATUS     current
          DESCRIPTION
                "
                Indicates the basic information about the media terminal adapter (MTA).
                The index of this entry is hwCmtsMtaInfoCmId.
                "
          INDEX       { hwCmtsMtaInfoCmId }
          ::= { hwCmtsMtaInfoTable 1 }

    HwCmtsMtaInfoEntry ::=
          SEQUENCE {
                    hwCmtsMtaInfoCmId       Integer32,
                    hwCmtsMtaMacAddress     MacAddress,
                    hwCmtsMtaIPAddress      IpAddress,
                    hwCmtsMtaPktcVersion    Integer32
                   }

    hwCmtsMtaInfoCmId OBJECT-TYPE
          SYNTAX  Integer32 (1..12168)
          MAX-ACCESS  not-accessible
          STATUS  current
          DESCRIPTION
                "
                Indicates a CM index.
                "
          ::= { hwCmtsMtaInfoEntry 1 }

    hwCmtsMtaMacAddress OBJECT-TYPE
          SYNTAX   MacAddress
          MAX-ACCESS  read-only
          STATUS  current
          DESCRIPTION
                "
                Indicates the MAC address of the MTA.
                "
          ::= { hwCmtsMtaInfoEntry 2 }

    hwCmtsMtaIPAddress OBJECT-TYPE
          SYNTAX  IpAddress
          MAX-ACCESS  read-only
          STATUS  current
          DESCRIPTION
                "
                Indicates the IP address of the MTA.
                "
          ::= { hwCmtsMtaInfoEntry 3 }

    hwCmtsMtaPktcVersion OBJECT-TYPE
          SYNTAX  Integer32  (-1|1..3)
          MAX-ACCESS  read-only
          STATUS  current
          DESCRIPTION
                "
                Indicates the version of PacketCable.
                Options:
                1-packetcable1.0
                2-packetcable1.5
                3-packetcable2.0
                -1 represent invalid version of PacketCable.
                "
          ::= { hwCmtsMtaInfoEntry 4 }


    -- Table hwDocsIfUpstreamChannelStatusTable

    hwDocsIfUpstreamChannelStatusTable OBJECT-TYPE
          SYNTAX     SEQUENCE OF HwCmtsUpChannelStatusEntry
          MAX-ACCESS not-accessible
          STATUS     current
          DESCRIPTION
               "Indicates the current status of a CMTS upstream channel.
               The index of this table is ifIndex."
          ::= { hwCmtsAccessObject 23 }

    hwDocsIfUpstreamChannelStatusEntry OBJECT-TYPE
          SYNTAX     HwCmtsUpChannelStatusEntry
          MAX-ACCESS not-accessible
          STATUS     current
          DESCRIPTION
               "Indicates the current status of a CMTS upstream channel.
               The index of this entry is ifIndex."
          INDEX       { ifIndex }
          ::= { hwDocsIfUpstreamChannelStatusTable 1 }

    HwCmtsUpChannelStatusEntry ::=
          SEQUENCE {
                    hwDocsIfUpstreamChannelStatusFrequency           Integer32,
                    hwDocsIfUpstreamChannelStatusWidth               Integer32,
                    hwDocsIfUpstreamChannelStatusModulationProfile   Unsigned32,
                    hwDocsIfUpstreamChannelStatusRxPower             Integer32
                  }

    hwDocsIfUpstreamChannelStatusFrequency OBJECT-TYPE
          SYNTAX     Integer32  (0..1000000000)
          MAX-ACCESS read-only
          STATUS     current
          DESCRIPTION
               "The current used center frequency of this upstream interface.
                This object returns 0 if the frequency is undefined or unknown.
                Range: 5000000-65000000 for AnnexA
                       5000000-42000000 for AnnexB
                Unit: Hz
                "
          ::= { hwDocsIfUpstreamChannelStatusEntry 1 }

    hwDocsIfUpstreamChannelStatusWidth OBJECT-TYPE
          SYNTAX     Integer32  (0..64000000)
          MAX-ACCESS read-only
          STATUS     current
          DESCRIPTION
               "The current used Channel Width of this upstream interface.
               This object returns 0 if the Width is undefined or unknown.
               now support 1600000, 3200000, 6400000, other is reserved
               Default: 3200000
               Unit: Hz
               "
          ::= { hwDocsIfUpstreamChannelStatusEntry 2 }


    hwDocsIfUpstreamChannelStatusModulationProfile OBJECT-TYPE
          SYNTAX     Unsigned32  (0..32)
          MAX-ACCESS read-only
          STATUS     current
          DESCRIPTION
               "The current used Modulation Profile of this upstream interface.
                This object returns 0 if the Modulation Profile is undefined or unknown."
          ::= { hwDocsIfUpstreamChannelStatusEntry 3 }

    hwDocsIfUpstreamChannelStatusRxPower OBJECT-TYPE
          SYNTAX     Integer32
          UNITS     "0.1dBmv"
          MAX-ACCESS read-only
          STATUS     current
          DESCRIPTION
               "This object indicates the receive power of the current upstream channel. 
                If -2147483647 is returned, the receive power is undefined or cannot be identified.
                Value range: -2147483647|-130..230
               "
          ::= { hwDocsIfUpstreamChannelStatusEntry 4 }

   -- Table hwCmtsDownChannelTable
    hwCmtsDownChannelTable OBJECT-TYPE
          SYNTAX     SEQUENCE OF HwCmtsDownChannelEntry
          MAX-ACCESS not-accessible
          STATUS     current
          DESCRIPTION
               "Indicates the signal quality of a CMTS downstream channel.
               The index of this table is ifIndex."
          ::= { hwCmtsAccessObject 24 }

    hwCmtsDownChannelEntry OBJECT-TYPE
          SYNTAX     HwCmtsDownChannelEntry
          MAX-ACCESS not-accessible
          STATUS     current
          DESCRIPTION
               "Indicates the signal quality of a CMTS downstream channel.
               The index of this entry is ifIndex."
          INDEX       { ifIndex }
          ::= { hwCmtsDownChannelTable 1 }

    HwCmtsDownChannelEntry ::=
          SEQUENCE {
                    hwCmtsDownChannelMaxDataRate           Integer32,
                    hwCmtsDownChannelRealTimeDataRate         Integer32,
                    hwCmtsDownChannel20CmDataRateSum                     Unsigned32,
                    hwCmtsDownChannel30CmDataRateSum                     Unsigned32
                   }

    hwCmtsDownChannelMaxDataRate OBJECT-TYPE
          SYNTAX     Integer32
          MAX-ACCESS read-only
          STATUS     current
          DESCRIPTION
               "The max data rate.
                Unit: Kbps"
          ::= { hwCmtsDownChannelEntry 1 }

    hwCmtsDownChannelRealTimeDataRate OBJECT-TYPE
          SYNTAX     Integer32
          MAX-ACCESS read-only
          STATUS     current
          DESCRIPTION
               "The real time data rate.
                Unit: Kbps"
          ::= { hwCmtsDownChannelEntry 2 }

    hwCmtsDownChannel20CmDataRateSum OBJECT-TYPE
          SYNTAX     Unsigned32
          MAX-ACCESS read-only
          STATUS     current
          DESCRIPTION
               "Rate sum of all DOCSIS 2.0 cable modem on the channel.
                Unit: Kbps"
          ::= { hwCmtsDownChannelEntry 3 }

    hwCmtsDownChannel30CmDataRateSum OBJECT-TYPE
          SYNTAX     Unsigned32
          MAX-ACCESS read-only
          STATUS     current
          DESCRIPTION
               "Rate sum of all DOCSIS 3.0 cable modem on the channel.
                Unit: Kbps"
          ::= { hwCmtsDownChannelEntry 4 }

  -- Table hwCmtsCmNumSummaryTable
    hwCmtsCmNumSummaryTable OBJECT-TYPE
          SYNTAX     SEQUENCE OF HwCmtsCmNumSummaryEntry
          MAX-ACCESS not-accessible
          STATUS     current
          DESCRIPTION
               "Indicates the number of cable modem by one port.
               The index of this table is hwCmtsCmNumSummaryIfIndex."
          ::= { hwCmtsAccessObject 25 }

    hwCmtsCmNumSummaryEntry OBJECT-TYPE
          SYNTAX     HwCmtsCmNumSummaryEntry
          MAX-ACCESS not-accessible
          STATUS     current
          DESCRIPTION
               "Indicates the number of cable modem by one port.
                The index of this entry is hwCmtsCmNumSummaryIfIndex."
          INDEX       { hwCmtsCmNumSummaryIfIndex }
          ::= { hwCmtsCmNumSummaryTable 1 }

    HwCmtsCmNumSummaryEntry ::=
          SEQUENCE {
                    hwCmtsCmNumSummaryIfIndex                Integer32,
                    hwCmtsCmNumSummaryPortIfIndex            Integer32,
                    hwCmtsCmNumSummaryIfType                 INTEGER,
                    hwCmtsCmNumSummaryTotalCmNum             Unsigned32,
                    hwCmtsCmNumSummaryOnlineCmNum            Unsigned32,
                    hwCmtsCmNumSummaryUnOnlineCmNum          Unsigned32,
                    hwCmtsCmNumSummaryOfflineCmNum           Unsigned32,
                    hwCmtsCmNumSummaryWidebandCmNum          Unsigned32,
                    hwCmtsCmNumSummaryRangingCompleteCmNum   Unsigned32,
                    hwCmtsCmNumSummaryStartDhcpV4CmNum       Unsigned32,
                    hwCmtsCmNumSummaryDhcpOfferCmNum         Unsigned32,
                    hwCmtsCmNumSummaryDhcpv4CompleteCmNum    Unsigned32
                   }
                   
    hwCmtsCmNumSummaryIfIndex OBJECT-TYPE
          SYNTAX  Integer32
          MAX-ACCESS  not-accessible
          STATUS  current
          DESCRIPTION
                "Indicates the index of CM summary information table.
                The ifIndex have three types 
                1. docsis port ifIndex
                2. upstream channel ifIndex, include channel type��docsis port index and channel index, if channel index is 0, indicates query cm that use multichannel
                3. downstream channel ifIndex, include channel type��docsis port index and channel index, if channel index is 0, indicates query cm that use multichannel"
          ::= { hwCmtsCmNumSummaryEntry 1 }

    hwCmtsCmNumSummaryPortIfIndex OBJECT-TYPE
          SYNTAX     Integer32
          MAX-ACCESS read-only
          STATUS     current
          DESCRIPTION
               "Indicates the docsis port IfIndex"
          ::= { hwCmtsCmNumSummaryEntry 2 }

    hwCmtsCmNumSummaryIfType OBJECT-TYPE
          SYNTAX  INTEGER{uschannel(59),dschannel(60),docsisport(62)}
          MAX-ACCESS read-only
          STATUS     current
          DESCRIPTION
                "Indicates the query type.
                Options:
                1. uschannel(59) -Indicates the type is upstream channel 
                2. dschannel(60) -Indicates the type is downstream channel 
                3. docsisport(62)-Indicates the type is docsis port 
                "
          ::= { hwCmtsCmNumSummaryEntry 3 }

    hwCmtsCmNumSummaryTotalCmNum OBJECT-TYPE
          SYNTAX     Unsigned32
          MAX-ACCESS read-only
          STATUS     current
          DESCRIPTION
               "The number of CM."
          ::= { hwCmtsCmNumSummaryEntry 4 }

    hwCmtsCmNumSummaryOnlineCmNum OBJECT-TYPE
          SYNTAX     Unsigned32
          MAX-ACCESS read-only
          STATUS     current
          DESCRIPTION
               "The number of registered CM."
          ::= { hwCmtsCmNumSummaryEntry 5 }

    hwCmtsCmNumSummaryUnOnlineCmNum OBJECT-TYPE
          SYNTAX     Unsigned32
          MAX-ACCESS read-only
          STATUS     current
          DESCRIPTION
               "The number of unregistered CM."
          ::= { hwCmtsCmNumSummaryEntry 6 }

    hwCmtsCmNumSummaryOfflineCmNum OBJECT-TYPE
          SYNTAX     Unsigned32
          MAX-ACCESS read-only
          STATUS     current
          DESCRIPTION
               "The number of CM in status of offline."
          ::= { hwCmtsCmNumSummaryEntry 7 }

    hwCmtsCmNumSummaryWidebandCmNum OBJECT-TYPE
          SYNTAX     Unsigned32
          MAX-ACCESS read-only
          STATUS     current
          DESCRIPTION
               "The number of widband CM."
          ::= { hwCmtsCmNumSummaryEntry 8 }

    hwCmtsCmNumSummaryRangingCompleteCmNum OBJECT-TYPE
          SYNTAX     Unsigned32
          MAX-ACCESS read-only
          STATUS     current
          DESCRIPTION
               "The number of ranging complete CM."
          ::= { hwCmtsCmNumSummaryEntry 9 }

    hwCmtsCmNumSummaryStartDhcpV4CmNum OBJECT-TYPE
          SYNTAX     Unsigned32
          MAX-ACCESS read-only
          STATUS     current
          DESCRIPTION
               "The number of CM in status of start DHCP V4."
          ::= { hwCmtsCmNumSummaryEntry 10 }

    hwCmtsCmNumSummaryDhcpOfferCmNum OBJECT-TYPE
          SYNTAX     Unsigned32
          MAX-ACCESS read-only
          STATUS     current
          DESCRIPTION
               "The number of CM in status of DHCP offe.r"
          ::= { hwCmtsCmNumSummaryEntry 11 }

    hwCmtsCmNumSummaryDhcpv4CompleteCmNum OBJECT-TYPE
          SYNTAX     Unsigned32
          MAX-ACCESS read-only
          STATUS     current
          DESCRIPTION
               "The number of CM in status of DHCP complete."
          ::= { hwCmtsCmNumSummaryEntry 12 }


    --Table hwCmtsSysCfgTable  begin
       hwCmtsSysCfgTable OBJECT IDENTIFIER ::= {hwCmtsAccessObject 26}
     hwCmtsSysCfgUnstableConnCmNumThreshold OBJECT-TYPE
          SYNTAX  Unsigned32(32..1024)
          MAX-ACCESS  read-write
          STATUS  current
          DESCRIPTION
                "
                Threshold for the number of cable modems with unstable connection.
                Range: 32..1024
                Default: 128
                "
          ::= { hwCmtsSysCfgTable 1 }

     hwCmtsSysCfgMassOfflineCmMonitorPeriod OBJECT-TYPE
          SYNTAX  Unsigned32(1..1440)
          MAX-ACCESS  read-write
          STATUS  current
          DESCRIPTION
                "
                Period for monitoring the number of offline cable modems.
                Range: 1..1440
                Default: 5
                Unit: minute
                "
          ::= { hwCmtsSysCfgTable 2 }

      hwCmtsSysCfgOfflineCmNumThreshold OBJECT-TYPE
          SYNTAX  Unsigned32(32..1024)
          MAX-ACCESS  read-write
          STATUS  current
          DESCRIPTION
                "
                Threshold for the number of offline cable modem.
                Range: 32..1024
                Default: 128
                "
          ::= { hwCmtsSysCfgTable 3 }

      --Table   hwCmtsSysCfgTable  end

   -- Table hwDocsIf3CmtsCmCpeStatTable begin
    hwDocsIf3CmtsCmCpeStatTable OBJECT-TYPE
          SYNTAX     SEQUENCE OF HwDocsIf3CmtsCmCpeStatEntry
          MAX-ACCESS not-accessible
          STATUS     current
          DESCRIPTION
               "This table indicates the statistics of each type CPE. 
                The index of this table is ifIndex."
          ::= { hwCmtsAccessObject 27 }

    hwDocsIf3CmtsCmCpeStatEntry OBJECT-TYPE
          SYNTAX     HwDocsIf3CmtsCmCpeStatEntry
          MAX-ACCESS not-accessible
          STATUS     current
          DESCRIPTION
               "This table indicates the statistics of each type CPE. 
                The index of this entry is ifIndex."
          INDEX       { ifIndex }
          ::= { hwDocsIf3CmtsCmCpeStatTable 1 }

    HwDocsIf3CmtsCmCpeStatEntry ::=
          SEQUENCE {
                    hwDocsIf3CmtsCmCpeStatMTANum              Integer32,
                    hwDocsIf3CmtsCmCpeStatSTBNum              Integer32,
                    hwDocsIf3CmtsCmCpeStatHostNum             Integer32,
                    hwDocsIf3CmtsCmCpeStatRouterNum           Integer32,
                    hwDocsIf3CmtsCmCpeStatUnclassifiedNum     Integer32
                   }

    hwDocsIf3CmtsCmCpeStatMTANum OBJECT-TYPE
          SYNTAX     Integer32
          MAX-ACCESS read-only
          STATUS     current
          DESCRIPTION
               "This object indicates the number of MTA type CPEs."
          ::= { hwDocsIf3CmtsCmCpeStatEntry 1 }

    hwDocsIf3CmtsCmCpeStatSTBNum OBJECT-TYPE
          SYNTAX     Integer32
          MAX-ACCESS read-only
          STATUS     current
          DESCRIPTION
               "This object indicates the number of STB type CPEs."
          ::= { hwDocsIf3CmtsCmCpeStatEntry 2 }

    hwDocsIf3CmtsCmCpeStatHostNum OBJECT-TYPE
          SYNTAX     Integer32
          MAX-ACCESS read-only
          STATUS     current
          DESCRIPTION
               "This object indicates the number of host type CPEs."
          ::= { hwDocsIf3CmtsCmCpeStatEntry 3 }

    hwDocsIf3CmtsCmCpeStatRouterNum OBJECT-TYPE
          SYNTAX     Integer32
          MAX-ACCESS read-only
          STATUS     current
          DESCRIPTION
               "This object indicates the number of router type CPEs."
          ::= { hwDocsIf3CmtsCmCpeStatEntry 4 }

    hwDocsIf3CmtsCmCpeStatUnclassifiedNum OBJECT-TYPE
          SYNTAX     Integer32
          MAX-ACCESS read-only
          STATUS     current
          DESCRIPTION
               "This object indicates the number of unclassified CPEs."
          ::= { hwDocsIf3CmtsCmCpeStatEntry 5 }
          
   -- Table hwDocsIf3CmtsCmCpeStatTable end
   
   -- Table hwDocsIfDownstreamChannelTable begin
          
    hwDocsIfDownstreamChannelTable OBJECT-TYPE
        SYNTAX      SEQUENCE OF HwDocsIfDownstreamChannelEntry
        MAX-ACCESS  not-accessible
        STATUS      current
        DESCRIPTION
            "This table describes the attributes of downstream
             channels (frequency bands).
             The index of this table is ifIndex."
        REFERENCE
            "Data-Over-Cable Service Interface Specifications: Radio
             Frequency Interface Specification SP-RFIv2.0-I10-051209,
             Tables 6-16, and 6-17. "
          ::= { hwCmtsAccessObject 28 }

   hwDocsIfDownstreamChannelEntry OBJECT-TYPE
        SYNTAX      HwDocsIfDownstreamChannelEntry
        MAX-ACCESS  not-accessible
        STATUS      current
        DESCRIPTION
            "This table describes the attributes of downstream
             channels (frequency bands).
             The index of this entry is ifIndex."
        INDEX { ifIndex }
        ::= { hwDocsIfDownstreamChannelTable 1 }

   HwDocsIfDownstreamChannelEntry ::= SEQUENCE {
            hwDocsIfDownChannelModulation       INTEGER
        }
        
   hwDocsIfDownChannelModulation OBJECT-TYPE
        SYNTAX      INTEGER {
            unknown(1),
            other(2),
            qam64(3),
            qam256(4),
            qam1024(5)
        }
        MAX-ACCESS  read-write
        STATUS      current
        DESCRIPTION
            "The modulation type associated with this downstream
             channel.  If the interface is down, this object either
             returns the configured value (CMTS), the most current
             value (CM), or the value of unknown(1).  See the
             associated conformance object for write conditions and
             limitations.  See the reference for specifics on the
             modulation profiles implied by qam64 qam256 and qam1024.
             Options:
             1. unknown(1) - unknown
             2. other(2)   - Indicates the other modulation type
             3. qam64(3)   - QAM64
             4. qam256(4)  - QAM256
             5. qam1024(5) - QAM1024"
        REFERENCE
            "Data-Over-Cable Service Interface Specifications: Radio
             Frequency Interface Specification SP-RFIv2.0-I10-051209,
             Table 6-17."
        ::= { hwDocsIfDownstreamChannelEntry 1 }
        
   -- Table hwDocsIfDownstreamChannelTable end
        
--        DOCSIF TRAP

        hwCmtsDownstreamChannelStatusChangeTrap NOTIFICATION-TYPE
            OBJECTS {
                    hwFrameIndex,
                    hwSlotIndex,
                    hwPortIndex,
                    docsIfDownChannelId,
                    ifAdminStatus,
                    ifOperStatus
             }
            STATUS current
            DESCRIPTION
                "CMTS downstream channel operation status change trap.
                 This trap message is generated when the operation status of downstream channel changes.
                "
            ::= { hwdocsIfCmtsTraps     0 1 }

        hwCmtsUpstreamChannelStatusChangeTrap NOTIFICATION-TYPE
            OBJECTS {
                    hwFrameIndex,
                    hwSlotIndex,
                    hwPortIndex,
                    docsIfUpChannelId,
                    ifAdminStatus,
                    ifOperStatus
             }
            STATUS current
            DESCRIPTION
                "CMTS upstream channel operation status change trap.
                 This trap message is generated when the operation status of upstream channel changes.
                "
            ::= { hwdocsIfCmtsTraps     0 2 }

        hwDocsIf3CmtsCmRemoteQueryTrap NOTIFICATION-TYPE
            OBJECTS {
                    docsIf3CmtsCmRegStatusId,
                    hwDocsIf3CmtsCmDsChannelIdList,
                    hwDocsIf3CmtsCmDsRxPowerList,
                    hwDocsIf3CmtsCmDsSnrList,
                    hwDocsIf3CmtsCmUsChannlIdList,
                    hwDocsIf3CmtsCmUsTxPowerList,
                    hwDocsIf3CmtsCmUsTxTimingOffsetList,
                    hwDocsIf3CmtsCmSysDesc,
                    hwCmtsCmRegRemoteStatus                    
             }
            STATUS current
            DESCRIPTION
                "
                CM remote query trap.
                This trap message is generated when quering the information about a remote CM.
                "
            ::= { hwdocsIfCmtsTraps     0 3 }

        hwCmtsCmDataChangeTrap NOTIFICATION-TYPE
            OBJECTS {
            	    hwConfigChangeIP,
                    hwCmtsCmDataChangeCmNum,
                    hwCmtsCmDataChangeCmIdList,
                    hwCmtsCmDataChangeCmOperTypeList,
                    hwCmtsCmDataChangeCmMacAddrList
             }
            STATUS current
            DESCRIPTION
                "CM data change trap.
                 This trap message is generated when the CM data changed.
                "
            ::= { hwdocsIfCmtsTraps     0 4 }

	    hwCmtsUnstableConnCmExceedThresholdAlarmTrap NOTIFICATION-TYPE
            OBJECTS {                                                  
                    hwFrameIndex,
                    hwSlotIndex,
                    hwPortIndex,
                    hwCmtsMassUnstableConnCmNum
             }
            STATUS current
            DESCRIPTION
                "
                The number of unstable cable modem exceed the threshold trap.
                This trap message is generated when the number of unstable cable modem exceed the threshold.
                "  
            ::= { hwdocsIfCmtsTraps     0 5 } 
	    
	    hwCmtsOfflineCmExceedThresholdAlarmTrap NOTIFICATION-TYPE
            OBJECTS {                                                  
                    hwFrameIndex,
                    hwSlotIndex,
                    hwPortIndex,
                    hwCmtsMassOfflineCmNum
             }
            STATUS current
            DESCRIPTION
                "
                The number of offline cable modem exceed the threshold trap.
                This trap message is generated when the number of offline cable modem exceed the threshold.
                "  
            ::= { hwdocsIfCmtsTraps     0 6 } 
	    
 --     hwcmtsTrapsVbOids

        hwDocsIf3CmtsCmDsChannelIdList OBJECT-TYPE
            SYNTAX      OCTET STRING
            MAX-ACCESS accessible-for-notify
            STATUS current
            DESCRIPTION
                "
                Indicates list of downstream channel indexes.
                "
            ::= { hwcmtsTrapsVbOids 1 }

        hwDocsIf3CmtsCmDsRxPowerList OBJECT-TYPE
            SYNTAX      OCTET STRING
            MAX-ACCESS accessible-for-notify
            STATUS current
            DESCRIPTION
                "
                Indicates list of the receiver power of downstream channels.
                Unit: 0.1 dBmV.
                "
            ::= { hwcmtsTrapsVbOids 2 }

        hwDocsIf3CmtsCmDsSnrList OBJECT-TYPE
            SYNTAX     OCTET STRING
            MAX-ACCESS accessible-for-notify
            STATUS current
            DESCRIPTION
                "
                Indicates list of the SNR of downstream channels.
                Unit: 0.1 dB.
                "
            ::= { hwcmtsTrapsVbOids 3 }

         hwDocsIf3CmtsCmUsChannlIdList OBJECT-TYPE
            SYNTAX      OCTET STRING
            MAX-ACCESS accessible-for-notify
            STATUS current
            DESCRIPTION
                "
                The up channel list of CM.
                "
            ::= { hwcmtsTrapsVbOids 4 }

       hwDocsIf3CmtsCmUsTxPowerList OBJECT-TYPE
            SYNTAX      OCTET STRING
            MAX-ACCESS accessible-for-notify
            STATUS current
            DESCRIPTION
                "
                The up channel power list of CM.
                "
            ::= { hwcmtsTrapsVbOids 5 }

       hwDocsIf3CmtsCmUsTxTimingOffsetList OBJECT-TYPE
            SYNTAX      OCTET STRING
            MAX-ACCESS accessible-for-notify
            STATUS current
            DESCRIPTION
                "
                The send time offset list of CM.
                "
            ::= { hwcmtsTrapsVbOids 6 }

       hwDocsIf3CmtsCmSysDesc OBJECT-TYPE
            SYNTAX      OCTET STRING
            MAX-ACCESS accessible-for-notify
            STATUS current
            DESCRIPTION
                "
                The system description of CM.
                "
            ::= { hwcmtsTrapsVbOids 7 }

       hwCmtsCmRegRemoteStatus OBJECT-TYPE
            SYNTAX      Integer32
            MAX-ACCESS accessible-for-notify
            STATUS current
            DESCRIPTION
                "
                The remote status of CM as indicated by the value of
                docsIf3CmStatusValue.
                "
            ::= { hwcmtsTrapsVbOids 8 }

         hwCmtsCmDataChangeCmNum OBJECT-TYPE
            SYNTAX      Integer32
            MAX-ACCESS accessible-for-notify
            STATUS current
            DESCRIPTION
                "
                The number of CM which has changed.
                "
            ::= { hwcmtsTrapsVbOids 9 }

        hwCmtsCmDataChangeCmIdList OBJECT-TYPE
            SYNTAX      OCTET STRING
            MAX-ACCESS accessible-for-notify
            STATUS current
            DESCRIPTION
                "
                The list of CM which has changed.
                "
            ::= { hwcmtsTrapsVbOids 10 }

        hwCmtsCmDataChangeCmOperTypeList OBJECT-TYPE
            SYNTAX     OCTET STRING
            MAX-ACCESS accessible-for-notify
            STATUS current
            DESCRIPTION
                "
                The operation type list of configuration changed CM.
                "
            ::= { hwcmtsTrapsVbOids 11 }

        hwCmtsCmDataChangeCmMacAddrList OBJECT-TYPE
            SYNTAX     OCTET STRING
            MAX-ACCESS accessible-for-notify
            STATUS current
            DESCRIPTION
                "
                The MAC address list of configuration changed CM.
                "
            ::= { hwcmtsTrapsVbOids 12 }
            
        hwCmtsMassUnstableConnCmNum OBJECT-TYPE
            SYNTAX     Integer32
            MAX-ACCESS accessible-for-notify
            STATUS current
            DESCRIPTION
                "
                The number of unstable connection cable modem.
                "
            ::= { hwcmtsTrapsVbOids 13 }
            
        hwCmtsMassOfflineCmNum OBJECT-TYPE
            SYNTAX     Integer32
            MAX-ACCESS accessible-for-notify
            STATUS current
            DESCRIPTION
                "
                The number of offline cable modem.
                "
            ::= { hwcmtsTrapsVbOids 14 }
                 	         	    

    hwCmtsServiceObject OBJECT IDENTIFIER ::= { hwCmtsObject  22}

    hwPacketCableObject OBJECT IDENTIFIER ::= { hwCmtsServiceObject  1}

    -- hwPacketCableObject   begin
      hwPacketCableConfigObject OBJECT IDENTIFIER ::= { hwPacketCableObject  1}

      -- hwPacketCableConfigObject   begin

        hwPacketCable1DotxSwitch OBJECT-TYPE
          SYNTAX  INTEGER
              {
                 enable(1),
                 disable(2)
              }
          MAX-ACCESS  read-write
          STATUS  current
          DESCRIPTION
                "
                The switch of PacketCable 1.x function.
                Options:
                1. enable(1)        - Indicates the switch is enable
                2. disable(2)       - Indicates the switch is disable
                Default: disable(2)
                "
          ::= { hwPacketCableConfigObject 1 }

        hwPacketCableMultimediaSwitch OBJECT-TYPE
          SYNTAX  INTEGER
              {
                 enable(1),
                 disable(2)
              }
          MAX-ACCESS  read-write
          STATUS  current
          DESCRIPTION
                "
                The switch of PacketCable Multimedia function.
                Options:
                1. enable(1)        - Indicates the switch is enable
                2. disable(2)       - Indicates the switch is disable
                Default: disable(2)
                "
          ::= { hwPacketCableConfigObject 2 }

        hwPacketCableAuthorizeCommonMtaSwitch OBJECT-TYPE
          SYNTAX  INTEGER
              {
                 enable(1),
                 disable(2)
              }
          MAX-ACCESS  read-write
          STATUS  current
          DESCRIPTION
                "
                This switch indicats that whether the Common DOCSIS MTA is authorized to create, modify or delete the dynamic service-flow.
                Options:
                1. enable(1)        - Indicates the switch is enable
                2. disable(2)       - Indicates the switch is disable
                Default: disable(2)
                "
          ::= { hwPacketCableConfigObject 3 }

        hwPacketCableMaxGateCount OBJECT-TYPE
          SYNTAX  Unsigned32
          MAX-ACCESS  read-write
          STATUS  current
          DESCRIPTION
                "
                The maximum count of the Gate in the system.
                The default value is the max value of this object, and the max value is specified in different systems.
                "
          ::= { hwPacketCableConfigObject 4 }

        hwPacketCable1DotxTimerT0 OBJECT-TYPE
          SYNTAX  Unsigned32(0 | 1..1000000)
          UNITS       "seconds"
          MAX-ACCESS  read-write
          STATUS  current
          DESCRIPTION
                "
                In PacketCable 1.x this timer is implemented in the CMTS in the Gate state machine, and limits the period of time that a gate
                may be allocated without the gate parameters being set.
                In the set operation, if is set to 0, it indicates that reset the timer to the default value.
                In the query operation, if it is not set, the value obtained is the default value.
                Range: 0 | 1..1000000
                Default: 30
                Unit: second
                "
          ::= { hwPacketCableConfigObject 5 }

        hwPacketCable1DotxTimerT1 OBJECT-TYPE
          SYNTAX  Unsigned32(0 | 1..1000000)
          UNITS       "seconds"
          MAX-ACCESS  read-write
          STATUS  current
          DESCRIPTION
                "
                In PacketCable 1.x this timer is implemented in the CMTS in the Gate state machine, and limits the period of time that may
                elapse between the authorization and a commit is performed.
                In the set operation, if is set to 0, it indicates that reset the timer to the default value.
                In the query operation, if it is not set, the value obtained is the default value.
                Range: 0 | 1..1000000
                Default: 200
                Unit: second
                "
          ::= { hwPacketCableConfigObject 6 }

        hwPacketCableMultimediaTimerT1 OBJECT-TYPE
          SYNTAX  Unsigned32(0 | 1..1000000)
          UNITS       "seconds"
          MAX-ACCESS  read-write
          STATUS  current
          DESCRIPTION
                "
                In PacketCable Multimedia this timer limits the amount of time the authorization remains valid.
                In the set operation, if is set to 0, it indicates that reset the timer to the default value.
                In the query operation, if it is not set, the value obtained is the default value.
                Range: 0 | 1..1000000
                Default: 200
                Unit: second
                "
          ::= { hwPacketCableConfigObject 7 }

        hwPacketCable1dotxSendSubscriberID OBJECT-TYPE
          SYNTAX  INTEGER
              {
                 enable(1),
                 disable(2)
              }
          MAX-ACCESS  read-write
          STATUS  current
          DESCRIPTION
                "
                In PacketCable 1.x this switch indicates that whether the SubscriberID is carried in Gate-Info, Gate-Delete, Gate-Open, Gate-Close packets.
                Options:
                1. enable(1)        - Indicates the switch is enable
                2. disable(2)       - Indicates the switch is disable
                Default: disable(2)
                "
          ::= { hwPacketCableConfigObject 8 }

        -- hwPacketCableConfigObject    end

      --Table   hwPacketcableGateInfoTable  begin

        hwPacketcableGateInfoTable OBJECT-TYPE
            SYNTAX     SEQUENCE OF HwPacketcableGateInfoEntry
            MAX-ACCESS not-accessible
            STATUS     current
            DESCRIPTION
                "
                Indicates the information of packetcable gate.
                The index of this table is hwPacketcableGateID.
                "
            ::= { hwPacketCableObject 2 }

        hwPacketcableGateInfoEntry OBJECT-TYPE
            SYNTAX     HwPacketcableGateInfoEntry
            MAX-ACCESS not-accessible
            STATUS     current
            DESCRIPTION
                "
                Indicates the information of packetcable gate.
                The index of this entry is hwPacketcableGateID.
                "
            INDEX       { hwPacketcableGateID }
            ::= { hwPacketcableGateInfoTable 1 }

        HwPacketcableGateInfoEntry ::=
            SEQUENCE {
                hwPacketcableGateID                      Unsigned32,
                hwPacketcableSubscriberIdType            InetAddressType,
                hwPacketcableSubscriberID                InetAddress,
                hwPacketcableGcAddressType               InetAddressType,
                hwPacketcableGcAddress                   InetAddress,
                hwPacketcableGateState                   INTEGER,
                hwPacketcableUpstreamServiceFlowId       Unsigned32,
                hwPacketcableDownstreamServiceFlowId     Unsigned32,
                hwPacketcableGateIfindex                 InterfaceIndexOrZero
            }

        hwPacketcableGateID  OBJECT-TYPE
            SYNTAX     Unsigned32
            MAX-ACCESS   not-accessible
            STATUS      current
            DESCRIPTION
                "
                The identifier of the Gate which identifies the Gate referenced in the command message, or referenced by the CMTS for a response message.
                The CMTS must ensure the GateID is unique. If the CMTS supports PacketCable 1.x and PacketCable Multimedia,
                the PacketCable Multimedia GateID must not duplicate a PacketCable 1.x GateID currently in use.
                "
            ::= { hwPacketcableGateInfoEntry 1 }

        hwPacketcableSubscriberIdType  OBJECT-TYPE
            SYNTAX     InetAddressType
            MAX-ACCESS   read-only
            STATUS      current
            DESCRIPTION
                "
                The type of the SubscriberID. There are two different versions of the SubscriberID object which differ in the IP version of the addresses that they
                contain. This object only supports ipv4(1) currently.
                "
            ::= { hwPacketcableGateInfoEntry 2 }

        hwPacketcableSubscriberID  OBJECT-TYPE
            SYNTAX     InetAddress
            MAX-ACCESS   read-only
            STATUS      current
            DESCRIPTION
                "
                The SubscriberID which identifies the user requesting the service. This object contains a value giving the IP address.
                example: 10.11.234.123.
                "
            ::= { hwPacketcableGateInfoEntry 3 }

        hwPacketcableGcAddressType  OBJECT-TYPE
            SYNTAX     InetAddressType
            MAX-ACCESS   read-only
            STATUS      current
            DESCRIPTION
                "
                This object indicats the type of internet address of the Gate Controller, but this object only support ipv4(1) currently.
                "
            ::= { hwPacketcableGateInfoEntry 4 }

        hwPacketcableGcAddress  OBJECT-TYPE
            SYNTAX     InetAddress
            MAX-ACCESS   read-only
            STATUS      current
            DESCRIPTION
                "
                The internet address of the Gate Controller. example: 10.11.234.123.

                An InetAddress value is always interpreted within the context
                of an InetAddressType value.  Every usage of the InetAddress
                extual convention is required to specify the InetAddressType
                object that provides the context.  It is suggested that the
                InetAddressType object be logically registered before the
                object(s) that use the InetAddress textual convention, if
                they appear in the same logical row.

                The value of an InetAddress object must always be
                consistent with the value of the associated InetAddressType
                object.  Attempts to set an InetAddress object to a value
                inconsistent with the associated InetAddressType
                must fail with an inconsistentValue error.

                When this textual convention is used as the syntax of an
                index object, there may be issues with the limit of 128
                sub-identifiers specified in SMIv2, STD 58.  In this case,
                the object definition MUST include a 'SIZE' clause to
                limit the number of potential instance sub-identifiers;
                otherwise the applicable constraints MUST be stated in
                the appropriate conceptual row DESCRIPTION clauses, or
                in the surrounding documentation if there is no single
                DESCRIPTION clause that is appropriate.
                "
            ::= { hwPacketcableGateInfoEntry 5 }

        hwPacketcableGateState  OBJECT-TYPE
            SYNTAX     INTEGER
            {
                allocated(1),
                authorized(2),
                reserved(3),
                committed(4),
                committedRecovery(5),
                idle(6)
            }
            MAX-ACCESS   read-only
            STATUS      current
            DESCRIPTION
                "
                The state of the Gate.
                Options:
                1. allocated(1)            - Indicates the allocated state
                2. authorized(2)           - Indicates the authorized state
                3. reserved(3)             - Indicates the reserved state
                4. committed(4)            - Indicates the committed state
                5. committedRecovery(5)    - Indicates the committed-recovery state
                6. idle(6)                 - Indicates the idle state
                "
            ::= { hwPacketcableGateInfoEntry 6 }

        hwPacketcableUpstreamServiceFlowId  OBJECT-TYPE
            SYNTAX     Unsigned32
            MAX-ACCESS   read-only
            STATUS      current
            DESCRIPTION
                "
                The index of the upstream service flow, which is obtained from docsQosServiceFlowId(OID:1.3.6.1.2.1.10.127.7.1.3.1.1).
                "
            ::= { hwPacketcableGateInfoEntry 7 }

        hwPacketcableDownstreamServiceFlowId  OBJECT-TYPE
            SYNTAX     Unsigned32
            MAX-ACCESS   read-only
            STATUS      current
            DESCRIPTION
                "
                The index of the downstream service flow, which is obtained from docsQosServiceFlowId(OID:1.3.6.1.2.1.10.127.7.1.3.1.1).
                "
            ::= { hwPacketcableGateInfoEntry 8 }

        hwPacketcableGateIfindex  OBJECT-TYPE
            SYNTAX     InterfaceIndexOrZero
            MAX-ACCESS   read-only
            STATUS      current
            DESCRIPTION
                "
                The ifIndex is an ifType of docsCableMaclayer(127).
                "
            ::= { hwPacketcableGateInfoEntry 9 }

      --Table   hwPacketcableGateInfoTable  begin

      --Table   hwPacketcableGateStatisticsTable  begin

        hwPacketcableGateStatisticsTable OBJECT-TYPE
            SYNTAX     SEQUENCE OF HwPacketcableGateStatisticsEntry
            MAX-ACCESS not-accessible
            STATUS     current
            DESCRIPTION
                "
                Indicates the statistics of the gate.
                The index of this table is hwPacketcableVersion.
                "
            ::= { hwPacketCableObject 3 }

        hwPacketcableGateStatisticsEntry OBJECT-TYPE
            SYNTAX     HwPacketcableGateStatisticsEntry
            MAX-ACCESS not-accessible
            STATUS     current
            DESCRIPTION
                "
                Indicates the statistics of the gate.
                The index of this entry is hwPacketcableVersion.
                "
            INDEX       { hwPacketcableVersion }
            ::= { hwPacketcableGateStatisticsTable 1 }

        HwPacketcableGateStatisticsEntry ::=
            SEQUENCE {
                hwPacketcableVersion               INTEGER,
                hwPacketcableGateAllocNum          Counter32,
                hwPacketcableGateAllocAckNum       Counter32,
                hwPacketcableGateAllocErrNum       Counter32,
                hwPacketcableGateSetNum            Counter32,
                hwPacketcableGateSetAckNum         Counter32,
                hwPacketcableGateSetErrNum         Counter32,
                hwPacketcableGateInfoNum           Counter32,
                hwPacketcableGateInfoAckNum        Counter32,
                hwPacketcableGateInfoErrNum        Counter32,
                hwPacketcableGateDeleteNum         Counter32,
                hwPacketcableGateDeleteAckNum      Counter32,
                hwPacketcableGateDeleteErrNum      Counter32,
                hwPacketcableGateOpenNum           Counter32,
                hwPacketcableGateCloseNum          Counter32,
                hwPacketcableGateReportStateNum    Counter32,
                hwPacketcableGateCmdErrNum         Counter32
            }

        hwPacketcableVersion  OBJECT-TYPE
            SYNTAX     INTEGER
            {
                packetcable1x(1),
                packetcableMultimedia(2)
            }
            MAX-ACCESS   not-accessible
            STATUS      current
            DESCRIPTION
                "
                The version of PacketCable.
                Options:
                1. packetcable1x(1)            - Indicates the PacketCable 1.x
                2. packetcableMultimedia(2)    - Indicates the PacketCable Multimedia
                "
            ::= { hwPacketcableGateStatisticsEntry 1 }

        hwPacketcableGateAllocNum  OBJECT-TYPE
            SYNTAX     Counter32
            MAX-ACCESS   read-only
            STATUS      current
            DESCRIPTION
                "
                The count of the received Gate-Alloc packet.
                "
            ::= { hwPacketcableGateStatisticsEntry 2 }

        hwPacketcableGateAllocAckNum  OBJECT-TYPE
            SYNTAX     Counter32
            MAX-ACCESS   read-only
            STATUS      current
            DESCRIPTION
                "
                The count of the received Gate-Alloc-Ack packet.
                "
            ::= { hwPacketcableGateStatisticsEntry 3 }

        hwPacketcableGateAllocErrNum  OBJECT-TYPE
            SYNTAX     Counter32
            MAX-ACCESS   read-only
            STATUS      current
            DESCRIPTION
                "
                The count of the received Gate-Alloc-Err packet.
                "
            ::= { hwPacketcableGateStatisticsEntry 4 }

        hwPacketcableGateSetNum  OBJECT-TYPE
            SYNTAX     Counter32
            MAX-ACCESS   read-only
            STATUS      current
            DESCRIPTION
                "
                The count of the received Gate-Set packet.
                "
            ::= { hwPacketcableGateStatisticsEntry 5 }

        hwPacketcableGateSetAckNum  OBJECT-TYPE
            SYNTAX     Counter32
            MAX-ACCESS   read-only
            STATUS      current
            DESCRIPTION
                "
                The count of the received Gate-Set-Ack packet.
                "
            ::= { hwPacketcableGateStatisticsEntry 6 }

        hwPacketcableGateSetErrNum  OBJECT-TYPE
            SYNTAX     Counter32
            MAX-ACCESS   read-only
            STATUS      current
            DESCRIPTION
                "
                The count of the received Gate-Set-Err packet.
                "
            ::= { hwPacketcableGateStatisticsEntry 7 }

        hwPacketcableGateInfoNum  OBJECT-TYPE
            SYNTAX     Counter32
            MAX-ACCESS   read-only
            STATUS      current
            DESCRIPTION
                "
                The count of the received Gate-Info packet.
                "
            ::= { hwPacketcableGateStatisticsEntry 8 }

        hwPacketcableGateInfoAckNum  OBJECT-TYPE
            SYNTAX     Counter32
            MAX-ACCESS   read-only
            STATUS      current
            DESCRIPTION
                "
                The count of the received Gate-Info-Ack packet.
                "
            ::= { hwPacketcableGateStatisticsEntry 9 }

        hwPacketcableGateInfoErrNum  OBJECT-TYPE
            SYNTAX     Counter32
            MAX-ACCESS   read-only
            STATUS      current
            DESCRIPTION
                "
                The count of the received Gate-Info-Err packet.
                "
            ::= { hwPacketcableGateStatisticsEntry 10 }

        hwPacketcableGateDeleteNum  OBJECT-TYPE
            SYNTAX     Counter32
            MAX-ACCESS   read-only
            STATUS      current
            DESCRIPTION
                "
                The count of the received Gate-Delete packet.
                "
            ::= { hwPacketcableGateStatisticsEntry 11 }

        hwPacketcableGateDeleteAckNum  OBJECT-TYPE
            SYNTAX     Counter32
            MAX-ACCESS   read-only
            STATUS      current
            DESCRIPTION
                "
                The count of the received Gate-Delete-Ack packet.
                "
            ::= { hwPacketcableGateStatisticsEntry 12 }

        hwPacketcableGateDeleteErrNum  OBJECT-TYPE
            SYNTAX     Counter32
            MAX-ACCESS   read-only
            STATUS      current
            DESCRIPTION
                "
                The count of the received Gate-Delete-Err packet.
                "
            ::= { hwPacketcableGateStatisticsEntry 13 }

        hwPacketcableGateOpenNum  OBJECT-TYPE
            SYNTAX     Counter32
            MAX-ACCESS   read-only
            STATUS      current
            DESCRIPTION
                "
                The count of the received Gate-Open packet.
                "
            ::= { hwPacketcableGateStatisticsEntry 14 }

        hwPacketcableGateCloseNum  OBJECT-TYPE
            SYNTAX     Counter32
            MAX-ACCESS   read-only
            STATUS      current
            DESCRIPTION
                "
                The count of the received Gate-Close packet.
                "
            ::= { hwPacketcableGateStatisticsEntry 15 }

        hwPacketcableGateReportStateNum  OBJECT-TYPE
            SYNTAX     Counter32
            MAX-ACCESS   read-only
            STATUS      current
            DESCRIPTION
                "
                The count of the received Gate-Report-State packet.
                "
            ::= { hwPacketcableGateStatisticsEntry 16 }

        hwPacketcableGateCmdErrNum  OBJECT-TYPE
            SYNTAX     Counter32
            MAX-ACCESS   read-only
            STATUS      current
            DESCRIPTION
                "
                The count of the received Gate-Cmd-Err packet.
                "
            ::= { hwPacketcableGateStatisticsEntry 17 }

      --Table   hwPacketcableGateStatisticsTable  begin

    -- hwPacketCableObject  end

    hwCmtsTrafficBurstConfigObject OBJECT IDENTIFIER ::= { hwCmtsServiceObject  2}

    --hwCmtsTrafficBurstConfigObject begin

      hwCmtsTrafficBurstUpstreamEnable OBJECT-TYPE
        SYNTAX TruthValue
        MAX-ACCESS read-write
        STATUS current
        DESCRIPTION
              "Indicates upstream traffic burst status.
               Options:
               1. true(1)  -enable upstream traffic burst
               2. false(2) -disable upstream traffic burst
               Default: false(2)
              "
        ::= { hwCmtsTrafficBurstConfigObject 1 }

      hwCmtsTrafficBurstDownstreamEnable OBJECT-TYPE
        SYNTAX TruthValue
        MAX-ACCESS read-write
        STATUS current
        DESCRIPTION
              "Indicates downstream traffic burst status.
               Options:
               1. true(1)  -enable downstream traffic burst
               2. false(2) -disable downstream traffic burst
               Default: false(2)
              "
        ::= { hwCmtsTrafficBurstConfigObject 2 }

    --hwCmtsTrafficBurstConfigObject end
    
    --Table hwCmtsCmTrafficTable begin
        
    hwCmtsCmTrafficTable OBJECT-TYPE
        SYNTAX     SEQUENCE OF HwCmtsCmTrafficEntry
        MAX-ACCESS not-accessible
        STATUS     current
        DESCRIPTION
            "Indicates the information of cm traffic.
            The index of this table is docsIf3CmtsCmRegStatusId."
        ::= { hwCmtsServiceObject 4 }

    hwCmtsCmTrafficEntry OBJECT-TYPE
        SYNTAX     HwCmtsCmTrafficEntry
        MAX-ACCESS not-accessible
        STATUS     current
        DESCRIPTION
            "Indicates the information of cm traffic.
            The index of this entry is docsIf3CmtsCmRegStatusId."
        INDEX       { docsIf3CmtsCmRegStatusId }
        ::= { hwCmtsCmTrafficTable 1 }

    HwCmtsCmTrafficEntry ::=
        SEQUENCE {
            hwCmtsCmTrafficUpStream                  Unsigned32,
            hwCmtsCmTrafficDownStream                Unsigned32,
            hwCmtsCmTrafficUpStreamMax               Unsigned32,
            hwCmtsCmTrafficDownStreamMax             Unsigned32
        }

    hwCmtsCmTrafficUpStream  OBJECT-TYPE
        SYNTAX     Unsigned32
        MAX-ACCESS read-only
        STATUS     current
        DESCRIPTION
            "This object indicats the cm traffic of up stream.
            Unit: bit/s"
        ::= { hwCmtsCmTrafficEntry 9 }

    hwCmtsCmTrafficDownStream  OBJECT-TYPE
        SYNTAX     Unsigned32
        MAX-ACCESS read-only
        STATUS     current
        DESCRIPTION
            "This object indicats the cm traffic of down stream.
            Unit: bit/s"
        ::= { hwCmtsCmTrafficEntry 10 }

    hwCmtsCmTrafficUpStreamMax  OBJECT-TYPE
        SYNTAX     Unsigned32
        MAX-ACCESS read-only
        STATUS     current
        DESCRIPTION
            "This object indicats the max cm traffic of up stream.
            Unit: bit/s"
        ::= { hwCmtsCmTrafficEntry 11 }

    hwCmtsCmTrafficDownStreamMax  OBJECT-TYPE
        SYNTAX     Unsigned32
        MAX-ACCESS read-only
        STATUS     current
        DESCRIPTION
            "This object indicats the max cm traffic of down stream.
            Unit: bit/s"
        ::= { hwCmtsCmTrafficEntry 12 }

    --Table hwCmtsCmTrafficTable end

END
