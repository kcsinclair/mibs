-- =================================================================
-- Copyright (C) 2013 by HUAWEI TECHNOLOGIES. All rights reserved.
-- Description:  The MIB is used for defining Huawei's ACCESS management common MIB objects.
-- Reference:
-- Version: V1.07
-- ================================================================

    HUAWEI-LINE-COMMON-MIB DEFINITIONS ::= BEGIN
        IMPORTS
            MODULE-IDENTITY, mib-2, OBJECT-TYPE, Counter32, Counter64,
            Unsigned32, Integer32, zeroDotZero, IpAddress, Gauge32, NOTIFICATION-TYPE
                FROM SNMPv2-SMI
            TruthValue, DateAndTime, RowStatus, MacAddress,TEXTUAL-CONVENTION
                FROM SNMPv2-TC
            ifIndex
                FROM IF-MIB
            MODULE-COMPLIANCE, OBJECT-GROUP
                FROM SNMPv2-CONF
            OwnerString, EntryStatus
                FROM RMON-MIB
           hwFrameIndex, hwSlotIndex,hwSubslotIndex,hwPortIndex,hwConfigChangeIP
                FROM HUAWEI-DEVICE-MIB
            huaweiMgmt, huaweiUtility
                FROM HUAWEI-MIB;

        hwAccessCommonMIB MODULE-IDENTITY
            LAST-UPDATED "201301150900Z"
            ORGANIZATION "Huawei Technologies Co.,Ltd."
            CONTACT-INFO                                       
                         "Huawei Industrial Base               
                          Bantian, Longgang                    
                          Shenzhen 518129                      
                          People's Republic of China           
                          Website: http://www.huawei.com       
                          Email: support@huawei.com            
                         "                                     
            DESCRIPTION
                 "The MIB is used for defining Huawei's ACCESS management common MIB objects."
       
        -- Revision history
            REVISION     "201301150900Z"
            DESCRIPTION  "V1.07,
                          -Modify the leaf of hwPortActualmode, add (65535) enum of the node 
                         "
        
            REVISION     "201105260900Z"
            DESCRIPTION  "V1.06,
                          -Modify the leaf nodes name of hwOpticsDdmInfoExRxPowerLow,hwXponOntDdmInfoExRxPowerLow to hwOpticsDdmInfoExRxPower,hwXponOntDdmInfoExRxPower
                          -Modify the postfix name of all the leaf nodes in the table hwOpticsDdmInfoExTable and hwXponDeviceOntDdmInfoExTable
                          from HighAlarm,LowAlarm,HighWarning,LowWarning to HighAlarmThreshold,LowAlarmThreshold,HighWarningThreshold,LowWarningThreshold
                          -Add the leaf nodes hwOpticsDdmInfoExCatvRxPowerLowAlarmThreshold,hwOpticsDdmInfoExCatvRxPowerHighAlarmThreshold,hwOpticsDdmInfoExModuleType,
                          hwOpticsDdmInfoExSubType,hwOpticsDdmInfoExPrecision,hwOpticsDdmInfoExEncapsulationType,hwOpticsDdmInfoExVendorPN,hwOpticsDdmInfoExUsedType
                          in table hwOpticsDdmInfoExTable. 
                          -Add the leaf nodes hwXponOntDdmInfoExCatvRxPowerLowAlarmThreshold,hwXponOntDdmInfoExCatvRxPowerHighAlarmThreshold,hwXponOntDdmInfoExModuleType,
                          hwXponOntDdmInfoExSubType,hwXponOntDdmInfoExPrecision,hwXponOntDdmInfoExEncapsulationType,hwXponOntDdmInfoExVendorPN,hwXponOntDdmInfoExUsedType
                          in table hwXponDeviceOntDdmInfoExTable.
                         "
        
            REVISION     "201103110900Z"
            DESCRIPTION  "V1.05, 
	                  Add a leaf hwOpticsDdmInfo10GTxBiasCurrent to HwOpticsDdmInfoExEntry
	                  Add a leaf hwOpticsDdmInfo10GTxPower to HwOpticsDdmInfoExEntry
	                  Add a leaf hwXponOntDdmInfoExOltRxOntPower to HwXponDeviceOntDdmInfoExEntry.
                         "
	
	
            REVISION     "201011170900Z"
            DESCRIPTION  "V1.04, modify the node name of hwProtTypeAdaptFaultAlarmTrap to hwPortTypeAdaptFaultAlarmTrap
                          modify the node name of hwProtTypeAdaptFaultRestoreAlarmTrap to hwPortTypeAdaptFaultRestoreAlarmTrap
                          modify the node name of hwProtTypeAdaptSucessAlarmTrap to hwPortTypeAdaptSuccessAlarmTrap.
                         "

            REVISION     "201009280900Z"
            DESCRIPTION  "V1.03, modify the description of the whole MIB file."
       
            REVISION     "201008220900Z"
            DESCRIPTION  "V1.02, modify the description of the temperature.
                          modify the node name of hwXponOntDdmInfoExTable to hwXponDeviceOntDdmInfoExEntry 
                          for clearing the compilation warning.
                         "
       
            REVISION     "201005200900Z"
            DESCRIPTION  "V1.01, add the definition of the trap node,include:
                          hwProtTypeAdaptFaultAlarmTrap
                          hwProtTypeAdaptFaultRestoreAlarmTrap
                          hwProtTypeAdaptSucessAlarmTrap
                          hwXponnniPortSwitchAlarmTrap
                          hwXponnniPortSwitchTrap
                         "
       
            REVISION     "200912300900Z"
            DESCRIPTION  "V1.00, Initial version."
            ::= { huaweiUtility  158 }

        hwAccessCommonObjectMIB        OBJECT IDENTIFIER ::= { hwAccessCommonMIB 1}
        hwLineCommonTrapsVbOids        OBJECT IDENTIFIER ::= { hwAccessCommonMIB 50}
        hwLineCommonTraps              OBJECT IDENTIFIER ::= { hwAccessCommonMIB 51}
        hwLineTraps                    OBJECT IDENTIFIER ::= { hwLineCommonTraps 1}
        hwLineTrapsPrefix              OBJECT IDENTIFIER ::= { hwLineTraps 0 }
        hwLineAlarmTraps               OBJECT IDENTIFIER ::= { hwLineCommonTraps 2}
        hwLineAlarmTrapsPrefix         OBJECT IDENTIFIER ::= { hwLineAlarmTraps 0 }
        hwAccessCommonObjects          OBJECT IDENTIFIER ::= { hwAccessCommonObjectMIB  1}
        hwAccessCommonControlObjects   OBJECT IDENTIFIER ::= { hwAccessCommonObjects 1}
        hwAccessCommonStatisticObjects OBJECT IDENTIFIER ::= { hwAccessCommonObjects 2}

        hwOpticsDdmInfoExTable OBJECT-TYPE
            SYNTAX     SEQUENCE OF HwOpticsDdmInfoExEntry
            MAX-ACCESS not-accessible
            STATUS     current
            DESCRIPTION
                "Table hwOpticsDdmInfoExTable supports the query of the information about the optical transceiver.
                 The index of this table is ifIndex.
                "
            ::= { hwAccessCommonControlObjects 1 }
        	
        hwOpticsDdmInfoExEntry OBJECT-TYPE
            SYNTAX     HwOpticsDdmInfoExEntry
            MAX-ACCESS not-accessible
            STATUS     current
            DESCRIPTION
                "Table hwOpticsDdmInfoExTable supports the query of the information about the optical transceiver.
                 The index of this entry is ifIndex.
                "
            INDEX       { ifIndex }
            ::= { hwOpticsDdmInfoExTable 1 }
        
        HwOpticsDdmInfoExEntry  ::=
            SEQUENCE {
                     hwOpticsDdmInfoExTemperature                            Integer32,
                     hwOpticsDdmInfoExTemperatureHighAlarmThreshold          Integer32,
                     hwOpticsDdmInfoExTemperatureLowAlarmThreshold           Integer32,
                     hwOpticsDdmInfoExTemperatureHighWarningThreshold        Integer32,
                     hwOpticsDdmInfoExTemperatureLowWarningThreshold         Integer32,
                     hwOpticsDdmInfoExSupplyVoltage                          Integer32,
                     hwOpticsDdmInfoExSupplyVoltageHighAlarmThreshold        Integer32,
                     hwOpticsDdmInfoExSupplyVoltageLowAlarmThreshold         Integer32,
                     hwOpticsDdmInfoExSupplyVoltageHighWarningThreshold      Integer32,
                     hwOpticsDdmInfoExSupplyVoltageLowWarningThreshold       Integer32, 
                     hwOpticsDdmInfoExTxBiasCurrent                          Integer32,
                     hwOpticsDdmInfoExTxBiasCurrentHighAlarmThreshold        Integer32,
                     hwOpticsDdmInfoExTxBiasCurrentLowAlarmThreshold         Integer32,
                     hwOpticsDdmInfoExTxBiasCurrentHighWarningThreshold      Integer32,
                     hwOpticsDdmInfoExTxBiasCurrentLowWarningThreshold       Integer32,
                     hwOpticsDdmInfoExTxPower                                Integer32,
                     hwOpticsDdmInfoExTxPowerHighAlarmThreshold              Integer32,
                     hwOpticsDdmInfoExTxPowerLowAlarmThreshold               Integer32,
                     hwOpticsDdmInfoExTxPowerHighWarningThreshold            Integer32,
                     hwOpticsDdmInfoExTxPowerLowWarningThreshold             Integer32,
                     hwOpticsDdmInfoExRxPower                                Integer32,
                     hwOpticsDdmInfoExRxPowerHighAlarmThreshold              Integer32,
                     hwOpticsDdmInfoExRxPowerLowAlarmThreshold               Integer32,
                     hwOpticsDdmInfoExRxPowerHighWarningThreshold            Integer32,
                     hwOpticsDdmInfoExRxPowerLowWarningThreshold             Integer32,
                     hwOpticsDdmInfo10GTxBiasCurrent                         Integer32,
                     hwOpticsDdmInfo10GTxPower                               Integer32,  
                     hwOpticsDdmInfoExCatvRxPowerHighAlarmThreshold          Integer32,                     
                     hwOpticsDdmInfoExCatvRxPowerLowAlarmThreshold           Integer32,
                     hwOpticsDdmInfoExModuleType                             INTEGER,
                     hwOpticsDdmInfoExSubType                                INTEGER,
                     hwOpticsDdmInfoExPrecision                              Integer32,
                     hwOpticsDdmInfoExEncapsulationType                      INTEGER,
                     hwOpticsDdmInfoExVendorPN                               OCTET STRING,
                     hwOpticsDdmInfoExUsedType                               INTEGER
                     }
             	
        hwOpticsDdmInfoExTemperature OBJECT-TYPE
            SYNTAX   Integer32
            UNITS       "0.000001 C(centigrade)"
            MAX-ACCESS  read-only
            STATUS      current
            DESCRIPTION
                "Temperature of the optical transceiver. 
                 Unit: 0.000001 C(centigrade)
                 Options:
                 1. invalid(0x7FFFFFFF)      - Indicates that the query fails or no information is detected                 
                "
            ::= { hwOpticsDdmInfoExEntry  1 }

        hwOpticsDdmInfoExTemperatureHighAlarmThreshold OBJECT-TYPE
            SYNTAX   Integer32
            UNITS       "0.000001 C(centigrade)"
            MAX-ACCESS  read-only
            STATUS      current
            DESCRIPTION
                "Upper alarm threshold of the temperature. 
                 Unit: 0.000001 C(centigrade)
                 Options:
                 1. invalid(0x7FFFFFFF)      - Indicates that the query fails or no information is detected
                "
            ::= { hwOpticsDdmInfoExEntry  2 }

        hwOpticsDdmInfoExTemperatureLowAlarmThreshold OBJECT-TYPE
            SYNTAX   Integer32
            UNITS       "0.000001 C(centigrade)"
            MAX-ACCESS  read-only
            STATUS      current
            DESCRIPTION
                "Lower alarm threshold of the temperature. 
                 Unit: 0.000001 C(centigrade) 
                 Options:
                 1. invalid(0x7FFFFFFF)      - Indicates that the query fails or no information is detected
                "
            ::= { hwOpticsDdmInfoExEntry  3 }

        hwOpticsDdmInfoExTemperatureHighWarningThreshold OBJECT-TYPE
            SYNTAX   Integer32
            UNITS       "0.000001 C(centigrade)"
            MAX-ACCESS  read-only
            STATUS      current
            DESCRIPTION
                "Upper warning threshold of the temperature. 
                 Unit: 0.000001 C(centigrade) 
                 Options:
                 1. invalid(0x7FFFFFFF)      - Indicates that the query fails or no information is detected
                "
            ::= { hwOpticsDdmInfoExEntry  4 }

        hwOpticsDdmInfoExTemperatureLowWarningThreshold OBJECT-TYPE
            SYNTAX   Integer32
            UNITS       "0.000001 C(centigrade)"
            MAX-ACCESS  read-only
            STATUS      current
            DESCRIPTION
                "Lower warning threshold of the temperature. 
                 Unit: 0.000001 C(centigrade)
                 Options:
                 1. invalid(0x7FFFFFFF)      - Indicates that the query fails or no information is detected
                "
            ::= { hwOpticsDdmInfoExEntry  5 }

        hwOpticsDdmInfoExSupplyVoltage OBJECT-TYPE
            SYNTAX   Integer32
            UNITS       "0.000001V"
            MAX-ACCESS  read-only
            STATUS      current
            DESCRIPTION
                "Voltage of the optical transceiver. 
                 Unit: 0.000001V
                 Options:
                 1. invalid(0x7FFFFFFF)      - Indicates that the query fails or no information is detected
                "
            ::= { hwOpticsDdmInfoExEntry  6 }

        hwOpticsDdmInfoExSupplyVoltageHighAlarmThreshold OBJECT-TYPE
            SYNTAX   Integer32
            UNITS       "0.000001V"
            MAX-ACCESS  read-only
            STATUS      current
            DESCRIPTION
                "Upper alarm threshold of the voltage. 
                 Unit: 0.000001V
                 Options:
                 1. invalid(0x7FFFFFFF)      - Indicates that the query fails or no information is detected
                "
            ::= { hwOpticsDdmInfoExEntry  7 }

        hwOpticsDdmInfoExSupplyVoltageLowAlarmThreshold OBJECT-TYPE
            SYNTAX   Integer32
            UNITS       "0.000001V"
            MAX-ACCESS  read-only
            STATUS      current
            DESCRIPTION
                "Lower alarm threshold of the voltage. 
                 Unit: 0.000001V
                 Options:
                 1. invalid(0x7FFFFFFF)      - Indicates that the query fails or no information is detected
                "
            ::= { hwOpticsDdmInfoExEntry  8 }

        hwOpticsDdmInfoExSupplyVoltageHighWarningThreshold OBJECT-TYPE
            SYNTAX   Integer32
            UNITS       "0.000001V"
            MAX-ACCESS  read-only
            STATUS      current
            DESCRIPTION
                "Upper warning threshold of the voltage.
                 Unit: 0.000001V
                 Options:
                 1. invalid(0x7FFFFFFF)      - Indicates that the query fails or no information is detected
                "
            ::= { hwOpticsDdmInfoExEntry  9 }

        hwOpticsDdmInfoExSupplyVoltageLowWarningThreshold OBJECT-TYPE
            SYNTAX   Integer32
            UNITS       "0.000001V"
            MAX-ACCESS  read-only
            STATUS      current
            DESCRIPTION
                "Lower warning threshold of the voltage. 
                 Unit: 0.000001V
                 Options:
                 1. invalid(0x7FFFFFFF)      - Indicates that the query fails or no information is detected
                "
            ::= { hwOpticsDdmInfoExEntry  10 }

        hwOpticsDdmInfoExTxBiasCurrent OBJECT-TYPE
            SYNTAX   Integer32
            UNITS       "0.000001A"
            MAX-ACCESS  read-only
            STATUS      current
            DESCRIPTION
                "Current of the optical transceiver. 
                 Unit: 0.000001A
                 Options:
                 1. invalid(-1)      - Indicates that the query fails or no information is detected                 
                "
            ::= { hwOpticsDdmInfoExEntry  11 }


        hwOpticsDdmInfoExTxBiasCurrentHighAlarmThreshold OBJECT-TYPE
            SYNTAX   Integer32
            UNITS       "0.000001A"
            MAX-ACCESS  read-only
            STATUS      current
            DESCRIPTION
                "Upper alarm threshold of the bias current. 
                 Unit: 0.000001A 
                 Options:
                 1. invalid(-1)      - Indicates that the query fails or no information is detected
                "
            ::= { hwOpticsDdmInfoExEntry  12 }

        hwOpticsDdmInfoExTxBiasCurrentLowAlarmThreshold OBJECT-TYPE
            SYNTAX   Integer32
            UNITS       "0.000001A"
            MAX-ACCESS  read-only
            STATUS      current
            DESCRIPTION
                "Lower alarm threshold of the bias current. 
                 Unit: 0.000001A
                 Options:
                 1. invalid(-1)      - Indicates that the query fails or no information is detected
                "
            ::= { hwOpticsDdmInfoExEntry  13 }

        hwOpticsDdmInfoExTxBiasCurrentHighWarningThreshold OBJECT-TYPE
            SYNTAX   Integer32
            UNITS       "0.000001A"
            MAX-ACCESS  read-only
            STATUS      current
            DESCRIPTION
                "Upper warning threshold of the bias current. 
                 Unit: 0.000001A
                 Options:
                 1. invalid(-1)      - Indicates that the query fails or no information is detected
                "
            ::= { hwOpticsDdmInfoExEntry  14 }

        hwOpticsDdmInfoExTxBiasCurrentLowWarningThreshold OBJECT-TYPE
            SYNTAX   Integer32
            UNITS       "0.000001A"
            MAX-ACCESS  read-only
            STATUS      current
            DESCRIPTION
                "Lower warning threshold of the bias current. 
                 Unit: 0.000001A 
                 Options:
                 1. invalid(-1)      - Indicates that the query fails or no information is detected
                "
            ::= { hwOpticsDdmInfoExEntry  15 }

        hwOpticsDdmInfoExTxPower OBJECT-TYPE
            SYNTAX   Integer32
            UNITS       "0.000001dBm"
            MAX-ACCESS  read-only
            STATUS      current
            DESCRIPTION
                "Tx optical power of the optical transceiver. 
                 Unit: 0.000001dBm
                 Options:
                 1. invalid(0x7FFFFFFF)      - Indicates that the query fails or no information is detected
                "
            ::= { hwOpticsDdmInfoExEntry  16 }

        hwOpticsDdmInfoExTxPowerHighAlarmThreshold OBJECT-TYPE
            SYNTAX   Integer32
            UNITS       "0.000001dBm"
            MAX-ACCESS  read-only
            STATUS      current
            DESCRIPTION
                "Upper alarm threshold of the Tx power. 
                 Unit: 0.000001dBm
                 Options:
                 1. invalid(0x7FFFFFFF)      - Indicates that the query fails or no information is detected
                "
            ::= { hwOpticsDdmInfoExEntry  17 }

        hwOpticsDdmInfoExTxPowerLowAlarmThreshold OBJECT-TYPE
            SYNTAX   Integer32
            UNITS       "0.000001dBm"
            MAX-ACCESS  read-only
            STATUS      current
            DESCRIPTION
                "Lower alarm threshold of the Tx power. 
                 Unit: 0.000001dBm
                 Options:
                 1. invalid(0x7FFFFFFF)      - Indicates that the query fails or no information is detected
                "
            ::= { hwOpticsDdmInfoExEntry  18 }

        hwOpticsDdmInfoExTxPowerHighWarningThreshold OBJECT-TYPE
            SYNTAX   Integer32
            UNITS       "0.000001dBm"
            MAX-ACCESS  read-only
            STATUS      current
            DESCRIPTION
                "Upper warning threshold of the Tx power. 
                 Unit: 0.000001dBm
                 Options:
                 1. invalid(0x7FFFFFFF)      - Indicates that the query fails or no information is detected
                "
            ::= { hwOpticsDdmInfoExEntry  19 }

        hwOpticsDdmInfoExTxPowerLowWarningThreshold OBJECT-TYPE
            SYNTAX   Integer32
            UNITS       "0.000001dBm"
            MAX-ACCESS  read-only
            STATUS      current
            DESCRIPTION
                "Lower warning threshold of the Tx power.
                 Unit: 0.000001dBm
                 Options:
                 1. invalid(0x7FFFFFFF)      - Indicates that the query fails or no information is detected
                "
            ::= { hwOpticsDdmInfoExEntry  20 }

        hwOpticsDdmInfoExRxPower OBJECT-TYPE
            SYNTAX   Integer32
            UNITS       "0.000001dBm"
            MAX-ACCESS  read-only
            STATUS      current
            DESCRIPTION
                "Rx optical power of the optical transceiver. 
                 Unit: 0.000001dBm
                 Options:
                 1. invalid(0x7FFFFFFF)      - Indicates that the query fails or no information is detected                 
                "
            ::= { hwOpticsDdmInfoExEntry  21 }

        hwOpticsDdmInfoExRxPowerHighAlarmThreshold   OBJECT-TYPE
            SYNTAX      Integer32
            UNITS       "0.000001dBm"
            MAX-ACCESS  read-only
            STATUS      current
            DESCRIPTION
                "Upper alarm threshold of the Rx power. 
                 Unit: 0.000001dBm
                 Options:
                 1. invalid(0x7FFFFFFF)      - Indicates that the query fails or no information is detected                 
                "
            ::= { hwOpticsDdmInfoExEntry  22 }

        hwOpticsDdmInfoExRxPowerLowAlarmThreshold OBJECT-TYPE
            SYNTAX   Integer32
            UNITS       "0.000001dBm"
            MAX-ACCESS  read-only
            STATUS      current
            DESCRIPTION
                "Lower alarm threshold of the Rx power. 
                 Unit: 0.000001dBm
                 Options:
                 1. invalid(0x7FFFFFFF)      - Indicates that the query fails or no information is detected                 
                "
            ::= { hwOpticsDdmInfoExEntry  23 }

        hwOpticsDdmInfoExRxPowerHighWarningThreshold OBJECT-TYPE
            SYNTAX   Integer32
            UNITS       "0.000001dBm"
            MAX-ACCESS  read-only
            STATUS      current
            DESCRIPTION
                "Upper warning threshold of the Rx power. 
                 Unit: 0.000001dBm
                 Options:
                 1. invalid(0x7FFFFFFF)      - Indicates that the query fails or no information is detected                 
                "
            ::= { hwOpticsDdmInfoExEntry  24 }

        hwOpticsDdmInfoExRxPowerLowWarningThreshold OBJECT-TYPE
            SYNTAX   Integer32
            UNITS       "0.000001dBm"
            MAX-ACCESS  read-only
            STATUS      current
            DESCRIPTION
                "Lower warning threshold of the Rx power. 
                 Unit: 0.000001dBm   
                 Options:
                 1. invalid(0x7FFFFFFF)      - Indicates that the query fails or no information is detected                 
                "
            ::= { hwOpticsDdmInfoExEntry  25 }
            
        hwOpticsDdmInfo10GTxBiasCurrent OBJECT-TYPE
            SYNTAX      Integer32
            UNITS       "0.000001A"
            MAX-ACCESS  read-only
            STATUS      current
            DESCRIPTION
                "Current of the 10g optical transceiver. 
                 Unit: 0.000001A
                 Options:
                 1. invalid(-1)      - Indicates that the query fails or no information is detected
                "
            ::= { hwOpticsDdmInfoExEntry  26 }

        hwOpticsDdmInfo10GTxPower OBJECT-TYPE
            SYNTAX      Integer32
            UNITS       "0.01dBm"
            MAX-ACCESS  read-only
            STATUS      current
            DESCRIPTION
                "Tx optical power of the 10g optical transceiver. 
                 Unit: 0.01dBm
                 Options:
                 1. invalid(0x7FFFFFFF)      - Indicates that the query fails or no information is detected
                "
            ::= { hwOpticsDdmInfoExEntry  27 }            

         hwOpticsDdmInfoExCatvRxPowerHighAlarmThreshold OBJECT-TYPE
            SYNTAX      Integer32
            UNITS       "0.000001dBm"
            MAX-ACCESS  read-only
            STATUS      current
            DESCRIPTION
                "Upper AlarmThreshold threshold of the CATV Rx power.
                 Unit: 0.000001dBm
                 Options:
                 1. invalid(0x7FFFFFFF)      - Indicates that the query fails or no information is detected
                "
            ::= { hwOpticsDdmInfoExEntry  28 } 

        hwOpticsDdmInfoExCatvRxPowerLowAlarmThreshold OBJECT-TYPE
            SYNTAX      Integer32
            UNITS       "0.000001dBm"
            MAX-ACCESS  read-only
            STATUS      current
            DESCRIPTION
                "Lower AlarmThreshold threshold of the CATV Rx power.
                 Unit: 0.000001dBm
                 Options:
                 1. invalid(0x7FFFFFFF)      - Indicates that the query fails or no information is detected
                "
            ::= { hwOpticsDdmInfoExEntry  29 } 
            
            
        hwOpticsDdmInfoExModuleType OBJECT-TYPE
            SYNTAX INTEGER
            {
                gpon(1),
                epon(2),
                epon10g(3),
                gpon10g(4),
                wdmpon(5),
                hybridpon(6),
                gponepon(7),
                unknown(8),
                invalid(-1)
            }
            MAX-ACCESS read-only
            STATUS current
            DESCRIPTION
            "Options:
             1. gpon(1)          - GPON
             2. epon(2)          - EPON
             3. epon10g(3)       - 10G EPON
             4. gpon10g(4)       - 10G GPON
             5. wdmpon(5)        - WDM PON
             6. hybridpon(6)     - hybrid PON
             7. gponepon(7)      - GPON/EPON 
             8. unknown(8)       - Unknown
             9. invalid(-1)      - Indicates that the query fails or no information is detected
            "
            ::= { hwOpticsDdmInfoExEntry  30 } 
            
        hwOpticsDdmInfoExSubType OBJECT-TYPE
            SYNTAX INTEGER
            {
                classbplus(1),
                classcplus(2),
                classb(3),
                n2a(33),
                n2b(34),
                n1(35),
                px20(65),
                px20plus(66),
                pr30(97),
                pr20(98),
                prx30(99),
                prx20(100),
                classbPlusAndPx20Plus(129),
                classbAndPx20(130),
                unknown(145),
                invalid(-1)
            }
            MAX-ACCESS read-only
            STATUS current
            DESCRIPTION
            "Options:
             1.  classbplus(1)              - CLASS B+
             2.  classcplus(2)              - CLASS C+
             3.  classb(3)                  - CLASS B
             4.  n2a(33)                    - N2a  
             5.  n2b(34)                    - N2b
             6.  n1(35)                     - N1
             7.  px20(65)                   - PX20
             8.  px20plus(66)               - PX20+
             9.  pr30(97)                   - PR30
             10. pr20(98)                   - PR20
             11. prx30(99)                  - PRX30
             12. prx20(100)                 - PRX20
             13. classbPlusAndPx20Plus(129) - GPON CLASS B+/EPON PX20+
             14. classbAndPx20(130)         - GPON CLASS B/EPON PX20
             15. unknown(145)               - Unknown
             16. invalid(-1)                - Indicates that the query fails or no information is detected
            "
            ::= { hwOpticsDdmInfoExEntry  31 } 
            
        hwOpticsDdmInfoExPrecision OBJECT-TYPE
            SYNTAX      Integer32
            UNITS       "0.1dBm"
            MAX-ACCESS  read-only
            STATUS      current
            DESCRIPTION
                "This object indicates the precision of optical power. 
                 Unit: 0.1dBm
                 Options:
                 1. invalid(-1)      - Indicates that the query fails or no information is detected
                "
            ::= { hwOpticsDdmInfoExEntry  32 } 
      
        hwOpticsDdmInfoExEncapsulationType OBJECT-TYPE
            SYNTAX INTEGER
            {
                sff2x5(1),
                sff2x10(2),
                sfp(3),
                xfp(4),
                lxfp(5),
                bosaonboard(6),
                unknown(7),
                invalid(-1)
            }
            MAX-ACCESS read-only
            STATUS current
            DESCRIPTION
            "Options:
             1. sff2x5(1)               - SFF 2x5
             2. sff2x10(2)              - SFF 2x10
             3. sfp(3)                  - SFP
             4. xfp(4)                  - XFP
             5. lxfp(5)                 - LXFP
             6. bosaonboard(6)          - BOSA ON BOARD  
             7. unknown(7)              - Unknown
             8. invalid(-1)             - Indicates that the query fails or no information is detected
            "
            ::= { hwOpticsDdmInfoExEntry  33 } 
            
        hwOpticsDdmInfoExVendorPN OBJECT-TYPE
            SYNTAX OCTET STRING (SIZE (0..17))
            MAX-ACCESS read-only
            STATUS current
            DESCRIPTION
                "This object indicates the part number."
            ::= { hwOpticsDdmInfoExEntry  34 } 
                    
        hwOpticsDdmInfoExUsedType OBJECT-TYPE
            SYNTAX INTEGER {
                olt(1),
                onu(3),
                catvtriplex(4), 
                unknown(5),
                invalid(-1)
            }
            MAX-ACCESS read-only
            STATUS current
            DESCRIPTION
                "This object indicates the application scenario of the optical transceiver.
                 Options:
                 1. olt(1)                 - OLT
                 2. onu(3)                 - ONU
                 3. catvtriplex(4)         - CATV TriPlex
                 4. unknown(5)             - Unknown
                 5. invalid(-1)            - Indicates that the query fails or no information is detected
                "
            ::= { hwOpticsDdmInfoExEntry  35 } 
                                                                        
  --Table hwXponDeviceOntDdmInfoExTable	    
        hwXponDeviceOntDdmInfoExTable OBJECT-TYPE
            SYNTAX     SEQUENCE OF HwXponDeviceOntDdmInfoExEntry
            MAX-ACCESS not-accessible
            STATUS     current
            DESCRIPTION
                "Table hwXponDeviceOntDdmInfoExTable supports the query of the
                 information about the optical transceiver of the ONT port. 
                 The index of this table is a combination of ifIndex and hwXponOntDdmInfoExOntIndex.
                "
            ::= { hwAccessCommonControlObjects 2 }

        hwXponDeviceOntDdmInfoExEntry OBJECT-TYPE
            SYNTAX     HwXponDeviceOntDdmInfoExEntry
            MAX-ACCESS not-accessible
            STATUS     current
            DESCRIPTION
                "Table hwXponDeviceOntDdmInfoExTable supports the query of the
                 information about the optical transceiver of the ONT port. 
                 The index of this entry is a combination of ifIndex and hwXponOntDdmInfoExOntIndex.
                "
            INDEX       { ifIndex, hwXponOntDdmInfoExOntIndex}
            ::= { hwXponDeviceOntDdmInfoExTable 1 }

        HwXponDeviceOntDdmInfoExEntry  ::=
            SEQUENCE {
                      hwXponOntDdmInfoExOntIndex                          Integer32,
                      hwXponOntDdmInfoExTemperature                       Integer32,
                      hwXponOntDdmInfoExTemperatureHighAlarmThreshold     Integer32,
                      hwXponOntDdmInfoExTemperatureLowAlarmThreshold      Integer32,
                      hwXponOntDdmInfoExTemperatureHighWarningThreshold   Integer32,
                      hwXponOntDdmInfoExTemperatureLowWarningThreshold    Integer32,
                      hwXponOntDdmInfoExSupplyVoltage                     Integer32,
                      hwXponOntDdmInfoExSupplyVoltageHighAlarmThreshold   Integer32,
                      hwXponOntDdmInfoExSupplyVoltageLowAlarmThreshold    Integer32,
                      hwXponOntDdmInfoExSupplyVoltageHighWarningThreshold Integer32,
                      hwXponOntDdmInfoExSupplyVoltageLowWarningThreshold  Integer32,
                      hwXponOntDdmInfoExTxBiasCurrent                     Integer32,
                      hwXponOntDdmInfoExTxBiasCurrentHighAlarmThreshold   Integer32,
                      hwXponOntDdmInfoExTxBiasCurrentLowAlarmThreshold    Integer32,
                      hwXponOntDdmInfoExTxBiasCurrentHighWarningThreshold Integer32,
                      hwXponOntDdmInfoExTxBiasCurrentLowWarningThreshold  Integer32,
                      hwXponOntDdmInfoExTxPower                           Integer32,
                      hwXponOntDdmInfoExTxPowerHighAlarmThreshold         Integer32,
                      hwXponOntDdmInfoExTxPowerLowAlarmThreshold          Integer32,
                      hwXponOntDdmInfoExTxPowerHighWarningThreshold       Integer32,
                      hwXponOntDdmInfoExTxPowerLowWarningThreshold        Integer32,
                      hwXponOntDdmInfoExRxPower                           Integer32,
                      hwXponOntDdmInfoExRxPowerHighAlarmThreshold         Integer32,
                      hwXponOntDdmInfoExRxPowerLowAlarmThreshold          Integer32,
                      hwXponOntDdmInfoExRxPowerHighWarningThreshold       Integer32,
                      hwXponOntDdmInfoExRxPowerLowWarningThreshold        Integer32,
                      hwXponOntDdmInfoExOltRxOntPower                     Integer32,
                      hwXponOntDdmInfoExCatvRxPowerHighAlarmThreshold     Integer32,                      
                      hwXponOntDdmInfoExCatvRxPowerLowAlarmThreshold      Integer32,
                      hwXponOntDdmInfoExModuleType                        INTEGER,
                      hwXponOntDdmInfoExSubType                           INTEGER,
                      hwXponOntDdmInfoExPrecision                         Integer32,
                      hwXponOntDdmInfoExEncapsulationType                 INTEGER,
                      hwXponOntDdmInfoExVendorPN                          OCTET STRING,
                      hwXponOntDdmInfoExUsedType                          INTEGER
                     }
             	 
        hwXponOntDdmInfoExOntIndex  OBJECT-TYPE
            SYNTAX     Integer32
            MAX-ACCESS   not-accessible
            STATUS      current
            DESCRIPTION
                "ONT ID, range: 0-127"
            ::= { hwXponDeviceOntDdmInfoExEntry 1 }

        hwXponOntDdmInfoExTemperature OBJECT-TYPE
            SYNTAX   Integer32
            UNITS       "0.000001 C(centigrade)"
            MAX-ACCESS  read-only
            STATUS      current
            DESCRIPTION
                "Temperature of the optical transceiver on the ONT. 
                 Unit: 0.000001 C(centigrade)
                 Options:
                 1. invalid(0x7FFFFFFF)      - Indicates that the query fails or no information is detected                 
                "
            ::= { hwXponDeviceOntDdmInfoExEntry  2 }

        hwXponOntDdmInfoExTemperatureHighAlarmThreshold OBJECT-TYPE
            SYNTAX   Integer32
            UNITS       "0.000001 C(centigrade)"
            MAX-ACCESS  read-only
            STATUS      current
            DESCRIPTION
                "Upper alarm threshold of the temperature. 
                 Unit: 0.000001 C(centigrade)
                 Options:
                 1. invalid(0x7FFFFFFF)      - Indicates that the query fails or no information is detected                  
                "
            ::= { hwXponDeviceOntDdmInfoExEntry  3 }

        hwXponOntDdmInfoExTemperatureLowAlarmThreshold OBJECT-TYPE
            SYNTAX   Integer32
            UNITS       "0.000001 C(centigrade)"
            MAX-ACCESS  read-only
            STATUS      current
            DESCRIPTION
                "Lower alarm threshold of the temperature. 
                 Unit: 0.000001 C(centigrade)
                 Options:
                 1. invalid(0x7FFFFFFF)      - Indicates that the query fails or no information is detected                  
                "
            ::= { hwXponDeviceOntDdmInfoExEntry  4 }

        hwXponOntDdmInfoExTemperatureHighWarningThreshold OBJECT-TYPE
            SYNTAX   Integer32
            UNITS       "0.000001 C(centigrade)"
            MAX-ACCESS  read-only
            STATUS      current
            DESCRIPTION
                "Upper warning threshold of the temperature.
                 Unit: 0.000001 C(centigrade)
                 Options:
                 1. invalid(0x7FFFFFFF)      - Indicates that the query fails or no information is detected                  
                "
            ::= { hwXponDeviceOntDdmInfoExEntry  5 }

        hwXponOntDdmInfoExTemperatureLowWarningThreshold OBJECT-TYPE
            SYNTAX   Integer32
            UNITS       "0.000001 C(centigrade)"
            MAX-ACCESS  read-only
            STATUS      current
            DESCRIPTION
                "Lower warning threshold of the temperature. 
                 Unit: 0.000001 C(centigrade)
                 Options:
                 1. invalid(0x7FFFFFFF)      - Indicates that the query fails or no information is detected                  
                "
            ::= { hwXponDeviceOntDdmInfoExEntry  6 }

        hwXponOntDdmInfoExSupplyVoltage OBJECT-TYPE
            SYNTAX   Integer32
            UNITS       "0.000001V"
            MAX-ACCESS  read-only
            STATUS      current
            DESCRIPTION
                "Voltage of the optical transceiver on the ONT. 
                 Unit: 0.000001V
                 Options:
                 1. invalid(0x7FFFFFFF)      - Indicates that the query fails or no information is detected                  
                "
            ::= { hwXponDeviceOntDdmInfoExEntry  7 }

        hwXponOntDdmInfoExSupplyVoltageHighAlarmThreshold OBJECT-TYPE
            SYNTAX   Integer32
            UNITS       "0.000001V"
            MAX-ACCESS  read-only
            STATUS      current
            DESCRIPTION
                "Upper alarm threshold of the voltage. 
                 Unit: 0.000001V
                 Options:
                 1. invalid(0x7FFFFFFF)      - Indicates that the query fails or no information is detected                  
                "
            ::= { hwXponDeviceOntDdmInfoExEntry  8 }

        hwXponOntDdmInfoExSupplyVoltageLowAlarmThreshold OBJECT-TYPE
            SYNTAX   Integer32
            UNITS       "0.000001V"
            MAX-ACCESS  read-only
            STATUS      current
            DESCRIPTION
                "Lower alarm threshold of the voltage. 
                 Unit: 0.000001V
                 Options:
                 1. invalid(0x7FFFFFFF)      - Indicates that the query fails or no information is detected                 
                "
            ::= { hwXponDeviceOntDdmInfoExEntry  9 }

        hwXponOntDdmInfoExSupplyVoltageHighWarningThreshold OBJECT-TYPE
            SYNTAX   Integer32
            UNITS       "0.000001V"
            MAX-ACCESS  read-only
            STATUS      current
            DESCRIPTION
                "Upper warning threshold of the voltage.
                 Unit: 0.000001V
                 Options:
                 1. invalid(0x7FFFFFFF)      - Indicates that the query fails or no information is detected                  
                "
            ::= { hwXponDeviceOntDdmInfoExEntry  10 }

        hwXponOntDdmInfoExSupplyVoltageLowWarningThreshold OBJECT-TYPE
            SYNTAX   Integer32
            UNITS       "0.000001V"
            MAX-ACCESS  read-only
            STATUS      current
            DESCRIPTION
                "Lower warning threshold of the voltage. 
                 Unit: 0.000001V
                 Options:
                 1. invalid(0x7FFFFFFF)      - Indicates that the query fails or no information is detected                  
                "
            ::= { hwXponDeviceOntDdmInfoExEntry  11 }

        hwXponOntDdmInfoExTxBiasCurrent OBJECT-TYPE
            SYNTAX   Integer32
            UNITS       "0.000001A"
            MAX-ACCESS  read-only
            STATUS      current
            DESCRIPTION
                "Current of the optical transceiver on the ONT. 
                 Unit: 0.000001A
                 Options:
                 1. invalid(-1)      - Indicates that the query fails or no information is detected                  
                "
            ::= { hwXponDeviceOntDdmInfoExEntry  12 }

        hwXponOntDdmInfoExTxBiasCurrentHighAlarmThreshold OBJECT-TYPE
            SYNTAX   Integer32
            UNITS       "0.000001A"
            MAX-ACCESS  read-only
            STATUS      current
            DESCRIPTION
                "Upper alarm threshold of the bias current. 
                 Unit: 0.000001A
                 Options:
                 1. invalid(-1)      - Indicates that the query fails or no information is detected
                "
            ::= { hwXponDeviceOntDdmInfoExEntry  13 }

        hwXponOntDdmInfoExTxBiasCurrentLowAlarmThreshold OBJECT-TYPE
            SYNTAX   Integer32
            UNITS       "0.000001A"
            MAX-ACCESS  read-only
            STATUS      current
            DESCRIPTION
                "Lower alarm threshold of the bias current. 
                 Unit: 0.000001A
                 Options:
                 1. invalid(-1)      - Indicates that the query fails or no information is detected                 
                "
            ::= { hwXponDeviceOntDdmInfoExEntry  14 }

        hwXponOntDdmInfoExTxBiasCurrentHighWarningThreshold OBJECT-TYPE
            SYNTAX   Integer32
            UNITS       "0.000001A"
            MAX-ACCESS  read-only
            STATUS      current
            DESCRIPTION
                "Upper warning threshold of the bias current. 
                 Unit: 0.000001A
                 Options:
                 1. invalid(-1)      - Indicates that the query fails or no information is detected                 
                "
            ::= { hwXponDeviceOntDdmInfoExEntry  15 }

        hwXponOntDdmInfoExTxBiasCurrentLowWarningThreshold OBJECT-TYPE
            SYNTAX   Integer32
            UNITS       "0.000001A"
            MAX-ACCESS  read-only
            STATUS      current
            DESCRIPTION
                "Lower warning threshold of the bias current. 
                 Unit: 0.000001A
                 Options:
                 1. invalid(-1)      - Indicates that the query fails or no information is detected                 
                "
            ::= { hwXponDeviceOntDdmInfoExEntry  16 }

        hwXponOntDdmInfoExTxPower OBJECT-TYPE
            SYNTAX   Integer32
            UNITS       "0.000001dBm"
            MAX-ACCESS  read-only
            STATUS      current
            DESCRIPTION
                "Tx optical power of the optical transceiver on the ONT. 
                 Unit: 0.000001dBm
                 Options:
                 1. invalid(0x7FFFFFFF)      - Indicates that the query fails or no information is detected                 
                "
            ::= { hwXponDeviceOntDdmInfoExEntry  17 }

        hwXponOntDdmInfoExTxPowerHighAlarmThreshold OBJECT-TYPE
            SYNTAX   Integer32
            UNITS       "0.000001dBm"
            MAX-ACCESS  read-only
            STATUS      current
            DESCRIPTION
                "Upper alarm threshold of the Tx power. 
                 Unit: 0.000001dBm
                 Options:
                 1. invalid(0x7FFFFFFF)      - Indicates that the query fails or no information is detected                  
                "
            ::= { hwXponDeviceOntDdmInfoExEntry  18 }

        hwXponOntDdmInfoExTxPowerLowAlarmThreshold OBJECT-TYPE
            SYNTAX   Integer32
            UNITS       "0.000001dBm"
            MAX-ACCESS  read-only
            STATUS      current
            DESCRIPTION
                "Lower alarm threshold of the Tx power. 
                 Unit: 0.000001dBm
                 Options:
                 1. invalid(0x7FFFFFFF)      - Indicates that the query fails or no information is detected                  
                "
            ::= { hwXponDeviceOntDdmInfoExEntry  19 }

        hwXponOntDdmInfoExTxPowerHighWarningThreshold OBJECT-TYPE
            SYNTAX   Integer32
            UNITS       "0.000001dBm"
            MAX-ACCESS  read-only
            STATUS      current
            DESCRIPTION
                "Upper warning threshold of the Tx power. 
                 Unit: 0.000001dBm
                 Options:
                 1. invalid(0x7FFFFFFF)      - Indicates that the query fails or no information is detected                  
                "
            ::= { hwXponDeviceOntDdmInfoExEntry  20 }

        hwXponOntDdmInfoExTxPowerLowWarningThreshold OBJECT-TYPE
            SYNTAX   Integer32
            UNITS       "0.000001dBm"
            MAX-ACCESS  read-only
            STATUS      current
            DESCRIPTION
                "Lower warning threshold of the Tx power.
                 Unit: 0.000001dBm
                 Options:
                 1. invalid(0x7FFFFFFF)      - Indicates that the query fails or no information is detected                  
                "
            ::= { hwXponDeviceOntDdmInfoExEntry  21 }

        hwXponOntDdmInfoExRxPower OBJECT-TYPE
            SYNTAX   Integer32
            UNITS       "0.000001dBm"
            MAX-ACCESS  read-only
            STATUS      current
            DESCRIPTION
                "Rx optical power of the optical transceiver on the ONT.
                 Unit: 0.000001dBm
                 Options:
                 1. invalid(0x7FFFFFFF)      - Indicates that the query fails or no information is detected                   
                "
            ::= { hwXponDeviceOntDdmInfoExEntry  22 }

        hwXponOntDdmInfoExRxPowerHighAlarmThreshold   OBJECT-TYPE
            SYNTAX      Integer32
            UNITS       "0.000001dBm"
            MAX-ACCESS  read-only
            STATUS      current
            DESCRIPTION
                "Upper alarm threshold of the Rx power. 
                 Unit: 0.000001dBm
                 Options:
                 1. invalid(0x7FFFFFFF)      - Indicates that the query fails or no information is detected                  
                "
            ::= { hwXponDeviceOntDdmInfoExEntry  23 }

        hwXponOntDdmInfoExRxPowerLowAlarmThreshold OBJECT-TYPE
            SYNTAX   Integer32
            UNITS       "0.000001dBm"
            MAX-ACCESS  read-only
            STATUS      current
            DESCRIPTION
                "Lower alarm threshold of the Rx power. 
                 Unit: 0.000001dBm
                 Options:
                 1. invalid(0x7FFFFFFF)      - Indicates that the query fails or no information is detected                  
                "
            ::= { hwXponDeviceOntDdmInfoExEntry  24 }

        hwXponOntDdmInfoExRxPowerHighWarningThreshold OBJECT-TYPE
            SYNTAX   Integer32
            UNITS       "0.000001dBm"
            MAX-ACCESS  read-only
            STATUS      current
            DESCRIPTION
                "Upper warning threshold of the Rx power.
                 Unit: 0.000001dBm
                 Options:
                 1. invalid(0x7FFFFFFF)      - Indicates that the query fails or no information is detected                  
                "
            ::= { hwXponDeviceOntDdmInfoExEntry  25 }

        hwXponOntDdmInfoExRxPowerLowWarningThreshold OBJECT-TYPE
            SYNTAX   Integer32
            UNITS       "0.000001dBm"
            MAX-ACCESS  read-only
            STATUS      current
            DESCRIPTION
                "Lower warning threshold of the Rx power. 
                 Unit: 0.000001dBm
                 Options:
                 1. invalid(0x7FFFFFFF)      - Indicates that the query fails or no information is detected                  
                "
            ::= { hwXponDeviceOntDdmInfoExEntry  26 }
            
        hwXponOntDdmInfoExOltRxOntPower OBJECT-TYPE
            SYNTAX   Integer32
            UNITS       "0.000001dBm"
            MAX-ACCESS  read-only
            STATUS      current
            DESCRIPTION
                "threshold of the ont Tx power. 
                 Unit: 0.000001dBm
                 Options:
                 1. invalid(0x7FFFFFFF)      - Indicates that the query fails or no information is detected                  
                "
            ::= { hwXponDeviceOntDdmInfoExEntry  27 }            
 
         hwXponOntDdmInfoExCatvRxPowerHighAlarmThreshold OBJECT-TYPE
            SYNTAX      Integer32
            UNITS       "0.000001dBm"
            MAX-ACCESS  read-only
            STATUS      current
            DESCRIPTION
                "Upper AlarmThreshold threshold of the CATV Rx power.
                 Unit: 0.000001dBm
                 Options:
                 1. invalid(0x7FFFFFFF)      - Indicates that the query fails or no information is detected
                "
            ::= { hwXponDeviceOntDdmInfoExEntry  28 } 
             
        hwXponOntDdmInfoExCatvRxPowerLowAlarmThreshold OBJECT-TYPE
            SYNTAX      Integer32
            UNITS       "0.000001dBm"
            MAX-ACCESS  read-only
            STATUS      current
            DESCRIPTION
                "Lower AlarmThreshold threshold of the CATV Rx power.
                 Unit: 0.000001dBm
                 Options:
                 1. invalid(0x7FFFFFFF)      - Indicates that the query fails or no information is detected
                "
            ::= { hwXponDeviceOntDdmInfoExEntry  29 } 
            
        hwXponOntDdmInfoExModuleType OBJECT-TYPE
           SYNTAX INTEGER
            {
                gpon(1),
                epon(2),
                epon10g(3),
                gpon10g(4),
                wdmpon(5),
                hybridpon(6),
                gponepon(7),
                unknown(8),
                invalid(-1)
            }
            MAX-ACCESS read-only
            STATUS current
            DESCRIPTION
            "Options:
             1. gpon(1)          - GPON
             2. epon(2)          - EPON
             3. epon10g(3)       - 10G EPON
             4. gpon10g(4)       - 10G GPON
             5. wdmpon(5)        - WDM PON
             6. hybridpon(6)     - hybrid PON
             7. gponepon(7)      - GPON/EPON 
             8. unknown(8)       - Unknown
             9. invalid(-1) - Indicates that the query fails or no information is detected
            "
            ::= { hwXponDeviceOntDdmInfoExEntry  30 } 
            
        hwXponOntDdmInfoExSubType OBJECT-TYPE
            SYNTAX INTEGER
            {
                classbplus(1),
                classcplus(2),
                classb(3),
                n2a(33),
                n2b(34),
                n1(35),
                px20(65),
                px20plus(66),
                pr30(97),
                pr20(98),
                prx30(99),
                prx20(100),
                classbPlusAndPx20Plus(129),
                classbAndPx20(130),
                unknown(145),
                invalid(-1)
            }
            MAX-ACCESS read-only
            STATUS current
            DESCRIPTION
            "Options:
             1.  classbplus(1)              - CLASS B+
             2.  classcplus(2)              - CLASS C+
             3.  classb(3)                  - CLASS B
             4.  n2a(33)                    - N2a  
             5.  n2b(34)                    - N2b
             6.  n1(35)                     - N1
             7.  px20(65)                   - PX20
             8.  px20plus(66)               - PX20+
             9.  pr30(97)                   - PR30
             10. pr20(98)                   - PR20
             11. prx30(99)                  - PRX30
             12. prx20(100)                 - PRX20
             13. classbPlusAndPx20Plus(129) - GPON CLASS B+/EPON PX20+
             14. classbAndPx20(130)         - GPON CLASS B/EPON PX20
             15. unknown(145)               - Unknown
             16. invalid(-1)                - Indicates that the query fails or no information is detected
            "
            ::= { hwXponDeviceOntDdmInfoExEntry  31 } 
            
        hwXponOntDdmInfoExPrecision OBJECT-TYPE
            SYNTAX      Integer32
            UNITS       "0.1dBm"
            MAX-ACCESS  read-only
            STATUS      current
            DESCRIPTION
                "This object indicates the precision of optical power. 
                 Unit: 0.1dBm
                 Options:
                 1. invalid(-1)      - Indicates that the query fails or no information is detected
                "
            ::= { hwXponDeviceOntDdmInfoExEntry  32 } 
      
        hwXponOntDdmInfoExEncapsulationType OBJECT-TYPE
            SYNTAX INTEGER
            {
                sff2x5(1),
                sff2x10(2),
                sfp(3),
                xfp(4),
                lxfp(5),
                bosaonboard(6),
                unknown(7),
                invalid(-1)
            }
            MAX-ACCESS read-only
            STATUS current
            DESCRIPTION
            "Options:
             1. sff2x5(1)               - SFF 2x5
             2. sff2x10(2)              - SFF 2x10
             3. sfp(3)                  - SFP
             4. xfp(4)                  - XFP
             5. lxfp(5)                 - LXFP
             6. bosaonboard(6)          - BOSA ON BOARD  
             7. unknown(7)              - Unknown
             8. invalid(-1)             - Indicates that the query fails or no information is detected
            "
            ::= { hwXponDeviceOntDdmInfoExEntry  33 } 
            
        hwXponOntDdmInfoExVendorPN OBJECT-TYPE
            SYNTAX OCTET STRING (SIZE (0..17))
            MAX-ACCESS read-only
            STATUS current
            DESCRIPTION
                "This object indicates the part number."
            ::= { hwXponDeviceOntDdmInfoExEntry  34 }

        hwXponOntDdmInfoExUsedType OBJECT-TYPE
            SYNTAX INTEGER {
                olt(1),
                onu(3),
                catvtriplex(4), 
                unknown(5),
                invalid(-1)
            }
            MAX-ACCESS read-only
            STATUS current
            DESCRIPTION
                "This object indicates the application scenario of the optical transceiver.
                 Options:
                 1. olt(1)                 - OLT
                 2. onu(3)                 - ONU
                 3. catvtriplex(4)         - CATV TriPlex
                 4. unknown(5)             - Unknown
                 5. invalid(-1)            - Indicates that the query fails or no information is detected
                "
            ::= { hwXponDeviceOntDdmInfoExEntry  35 }
                                                                       
        -- trapVboids define
        hwPortHostmode OBJECT-TYPE
            SYNTAX  INTEGER {
                                 geMode(7),
                                 adaptMode(27),
                                 gponMode(114),
                                 eponMode(115)
                              }
            MAX-ACCESS accessible-for-notify
            STATUS current
            DESCRIPTION
                "The port host mode.
                 Options:
                 1. geMode(7)     - Ge mode
                 2. adaptMode(27) - Adapt mode
                 3. gponMode(114) - Gpon mode
                 4. eponMode(115) - Epon mode
                "
            ::= { hwLineCommonTrapsVbOids 1 }
     
        hwPortActualmode OBJECT-TYPE
            SYNTAX  INTEGER {
                  geMode(7),
                  adaptMode(27),
                  gponMode(114),
                  eponMode(115),
                  unknown(65535)
            }
            MAX-ACCESS accessible-for-notify
            STATUS current
            DESCRIPTION
                "The port actual mode.
                 Options:
                 1. geMode(7)     - Ge mode
                 2. adaptMode(27) - Adapt mode
                 3. gponMode(114) - Gpon mode
                 4. eponMode(115) - Epon mode
                 5. unknown(65535) - Unknown mode
                "
            ::= { hwLineCommonTrapsVbOids 2 }
     
        hwReservedValue OBJECT-TYPE
            SYNTAX   Integer32
            MAX-ACCESS   accessible-for-notify
            STATUS       current
            DESCRIPTION
                   "Reserved value."
            ::= { hwLineCommonTrapsVbOids   3 }
     
        -- alarm trap define
        hwPortTypeAdaptFaultAlarmTrap NOTIFICATION-TYPE
            OBJECTS {
                hwFrameIndex,
                hwSlotIndex,
                hwPortIndex,
                hwPortHostmode,
                hwPortActualmode
            }
            STATUS current
            DESCRIPTION
                "Port type adaptation fault alarm trap.
                 This trap message is generated when the uplink port on the ONU is set to work in adaptive mode,
                 the type of the OLT downlink port transmitting the optical signal is different from the type of 
                 the uplink port on the ONU. As a result, the uplink port on the ONU is faulty.
                "
            ::= { hwLineAlarmTraps 0 1 }
     
        hwPortTypeAdaptFaultRestoreAlarmTrap NOTIFICATION-TYPE
            OBJECTS {
                hwFrameIndex,
                hwSlotIndex,
                hwPortIndex,
                hwPortHostmode,
                hwPortActualmode
                }
            STATUS current
            DESCRIPTION
                "Port type adaptation fault recovery alarm trap.
                 This trap message is generated when the uplink port on the ONU is set to work in adaptive mode, 
                 the type of the OLT downlink port transmitting the optical signal is the same as the type of 
                 the uplink port on the ONU, and the service on the uplink port is restored.
                "
            ::= { hwLineAlarmTraps 0 2 }
     
        hwPortTypeAdaptSuccessAlarmTrap NOTIFICATION-TYPE
            OBJECTS {
                 hwFrameIndex,
                 hwSlotIndex,
                 hwPortIndex,
                 hwPortHostmode,
                 hwPortActualmode
                 }
            STATUS current
            DESCRIPTION
                "Port type adaptation success alarm trap.
                 This trap message is generated when the type of the OLT downlink port transmitting the optical signal changes, 
                 the adaptation of the uplink port on the ONU is successful.                
                "
            ::= { hwLineAlarmTraps 0 3 }
     
        hwXponnniPortSwitchAlarmTrap NOTIFICATION-TYPE
            OBJECTS {
                hwFrameIndex,
                hwSlotIndex,
                hwPortIndex,
                hwPortIndex
                }
            STATUS current
            DESCRIPTION
                "Protection switchover occurs on the PON port and it has no effect on the service.
                 The first hwPortIndex is the source port index,
                 the second hwPortIndex is the destination port index.
                "
            ::= { hwLineAlarmTraps 0 4 }
     
        -- common trap define
        hwXponnniPortSwitchTrap NOTIFICATION-TYPE
            OBJECTS {
                hwReservedValue,
                ifIndex,
                ifIndex
                }
            STATUS current
            DESCRIPTION
                "TypeC or TypeD port switch trap.
                 The first ifIndex is the active one after switching over.
                 The second ifIndex is the standby one after switching over.
                "
            ::= { hwLineTraps 0 1 }
     
  END
