--  =================================================================
-- Copyright (C) 2012 by  HUAWEI TECHNOLOGIES. All rights reserved.
-- Description: HUAWEI TNLPOLICY management MIB for access network device.
-- Reference:
-- Version: V1.01
-- =================================================================
    HUAWEI-DSLAM-TNLPOLICY-MIB DEFINITIONS ::= BEGIN

        IMPORTS
            Unsigned32,
            OBJECT-TYPE, MODULE-IDENTITY, NOTIFICATION-TYPE
                FROM SNMPv2-SMI
            RowStatus
                FROM SNMPv2-TC
            huaweiMgmt
                FROM HUAWEI-MIB
            hwRmExt FROM HUAWEI-RM-EXT-MIB;

        hwDslamTnlPolicyMib MODULE-IDENTITY

            LAST-UPDATED "201201100000Z"
            ORGANIZATION "Huawei Technologies Co.,Ltd."
            CONTACT-INFO
                "Huawei Industrial Base
                 Bantian, Longgang
                 Shenzhen 518129
                 People's Republic of China
                 Website: http://www.huawei.com
                 Email: support@huawei.com
                "
            DESCRIPTION
                "HUAWEI TNLPOLICY management MIB for access network device.
                "
                --  Revision history

                REVISION    "201201100000Z"
                DESCRIPTION "V1.01, initial revision."
            ::= { huaweiMgmt 116 }

        hwTunnelExtObjects OBJECT IDENTIFIER ::= { hwRmExt 3 }
--
-- The Tunnel Policy Table
--
        hwTnlPolicyTable OBJECT-TYPE
            SYNTAX SEQUENCE OF HwTnlPolicyEntry
            MAX-ACCESS not-accessible
            STATUS current
            DESCRIPTION
                "This table is used to create a tunnel policy.
                 The index of this table is hwTnlPolicyName.
                "
            ::= { hwTunnelExtObjects 6 }

        hwTnlPolicyEntry OBJECT-TYPE
            SYNTAX HwTnlPolicyEntry
            MAX-ACCESS not-accessible
            STATUS current
            DESCRIPTION
                "This table is used to create a tunnel policy.
                 The index of this entry is hwTnlPolicyName.
                "
            INDEX { hwTnlPolicyName }
            ::= { hwTnlPolicyTable 1 }

        HwTnlPolicyEntry ::=
            SEQUENCE {
                hwTnlPolicyName
                    OCTET STRING,
                hwTnlPolicyDescription
                    OCTET STRING,
                hwTnlPolicySelectSeq
                    OCTET STRING,
                hwTnlPolicyLoadBalance
                    Unsigned32,
                hwTnlPolicyRowStatus
                    RowStatus
            }

        hwTnlPolicyName OBJECT-TYPE
            SYNTAX OCTET STRING (SIZE (1..39))
            MAX-ACCESS not-accessible
            STATUS current
            DESCRIPTION
            "
            Indicates the name of the tunnel policy.
            "
            ::= { hwTnlPolicyEntry 1 }

        hwTnlPolicyDescription OBJECT-TYPE
            SYNTAX OCTET STRING (SIZE (0..80))
            MAX-ACCESS read-write
            STATUS current
            DESCRIPTION
                "The description of the tunnel policy."
            ::= { hwTnlPolicyEntry 2 }

        hwTnlPolicySelectSeq OBJECT-TYPE
            SYNTAX        OCTET STRING (SIZE (1..4))
            MAX-ACCESS    read-create
            STATUS current
            DESCRIPTION
                "
                Used to configure the sequence for selecting tunnels that are involved in the load sharing.
                "
                ::= { hwTnlPolicyEntry 3 }

        hwTnlPolicyLoadBalance OBJECT-TYPE
            SYNTAX Unsigned32  (1..64)
            MAX-ACCESS    read-create
            STATUS current
            DESCRIPTION
              "
              Indicates load balancing value.
              "
              DEFVAL { 1 }
              ::= { hwTnlPolicyEntry 4 }

        hwTnlPolicyRowStatus OBJECT-TYPE
            SYNTAX RowStatus
            MAX-ACCESS read-create
            STATUS current
            DESCRIPTION
                "For creating and modifying this row. None of the
                 read-create objects in the conceptual rows may be changed
                 when this object is in the active(1) state.
                 Options:
                 1. active(1)      -indicates query operation
                 2. createAndGo(4) -indicates creating a tunnel policy
                 3. destroy(6)     -indicates deleting a tunnel policy
                "
            ::= { hwTnlPolicyEntry 5 }

    END
