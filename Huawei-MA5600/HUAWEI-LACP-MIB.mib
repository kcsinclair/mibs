-- =============================================================================================================
-- Copyright (C) 2013 by  HUAWEI TECHNOLOGIES. All rights reserved.
-- Description: This mib module defines the Link Aggregation Control Protocol (LACP) MIB objects. 
--               LACP is the control protocol for implementing the link aggregation in the IEEE 802.3ad standard. 
--               By using this protocol, the ports between devices are automatically aggregated, port 
--               failure detection at layer 2 is performed, line aggregation protocol control is performed, 
--               and protection switchover function is triggered.
-- Reference:      
-- Version: V1.13 
-- ==============================================================================================================
    HUAWEI-LACP-MIB DEFINITIONS ::= BEGIN
 
        IMPORTS 
            dot1dStpPortEntry            
                FROM BRIDGE-MIB            
            huaweiMgmt            
                FROM HUAWEI-MIB            
            Integer32, Counter32, Gauge32, OBJECT-TYPE, MODULE-IDENTITY, NOTIFICATION-TYPE             
                FROM SNMPv2-SMI            
            MacAddress, TruthValue, RowStatus, DisplayString, TEXTUAL-CONVENTION        
                FROM SNMPv2-TC
            OBJECT-GROUP, MODULE-COMPLIANCE    , NOTIFICATION-GROUP        
                FROM SNMPv2-CONF  
            hwFrameIndex, hwSlotIndex, hwPortIndex
                FROM HUAWEI-DEVICE-MIB ;            
            
        hwLacpExt MODULE-IDENTITY
            LAST-UPDATED "201303070000Z"           
            ORGANIZATION "Huawei Technologies Co.,Ltd."
            CONTACT-INFO                                       
                "Huawei Industrial Base
                 Bantian, Longgang
                 Shenzhen 518129
                 People's Republic of China
                 Website: http://www.huawei.com
                 Email: support@huawei.com
                "                                     
            DESCRIPTION 
                "This mib module defines the Link Aggregation Control Protocol (LACP) MIB objects. 
                 LACP is the control protocol for implementing the link aggregation in the IEEE 802.3ad standard. 
                 By using this protocol, the ports between devices are automatically aggregated, port 
                 failure detection at layer 2 is performed, line aggregation protocol control is performed, 
                 and protection switchover function is triggered."
                
            --  Revision history
            REVISION     "201303070000Z"
            DESCRIPTION  "V1.13, modified the description."

            REVISION     "201301100000Z"
            DESCRIPTION  "V1.12, deleted hwAggLinkUndoActorSystemPriority and hwAggPortUndoActorPortPriority."

            REVISION     "201107290000Z"
            DESCRIPTION  "V1.11, modified the description."
                        
            REVISION     "201107160000Z"
            DESCRIPTION  "V1.10, Added hwAggPreempt."
            
            REVISION     "201011200000Z"
            DESCRIPTION  "V1.09, modified the descriptions of this MIB file and leaves."
 
            REVISION     "201008150000Z"
            DESCRIPTION  "V1.08, modified the description of leaves.
                          Added hwLacpPortStateForwarding and hwLacpPortStateDiscarding. Added hwAggLinkGroupID in hwLacpAlarmTrapsPrefix."
            
            REVISION     "201007160000Z"
            DESCRIPTION  "V1.07, modified the description."
            
            REVISION     "201003160000Z"
            DESCRIPTION  "V1.06, modified enumeration format."
            
            REVISION     "200912301600Z"
            DESCRIPTION  "V1.05, modified data type definition,Add hwLacpTrapsVbOids in hwLacpExt.Add hwLacpTraps in hwLacpExt.
                         Added hwLacpAlarmTraps in hwLacpTraps."
                        
            REVISION     "200905210000Z"
            DESCRIPTION  "V1.04, modified the scope of hwAggLinkNumber from (1, 728) to (1, 2147483647), added the description of 
                          hwAggLinkName and hwAggLinkNumber, and modify the description of hwAggPortRole, hwAggPortType and hwAggPortStatus."
               
            REVISION     "200607310000Z"
            DESCRIPTION  "V1.00, initial version."
                
            ::= { huaweiMgmt 102 }

        hwLacpMibObjects OBJECT IDENTIFIER ::= { hwLacpExt 1 }
        
        hwAggLinkTable OBJECT-TYPE
            SYNTAX SEQUENCE OF HwAggLinkEntry
            MAX-ACCESS not-accessible
            STATUS current
            DESCRIPTION
                "Describes the configuration of static LAGs.
                 The index of this table is hwAggLinkNumber.
                "
            ::= { hwLacpMibObjects 1 }
        
        hwAggLinkEntry OBJECT-TYPE
            SYNTAX HwAggLinkEntry
            MAX-ACCESS not-accessible
            STATUS current
            DESCRIPTION
                "Describes the configuration of static LAGs.
                 The index of this entry is hwAggLinkNumber.
                "
            INDEX { hwAggLinkNumber }
            ::= { hwAggLinkTable 1 }
        
        HwAggLinkEntry ::=
            SEQUENCE 
                { 
                hwAggLinkNumber
                    Integer32,
                hwAggLinkName
                    OCTET STRING,
                hwAggLinkMode
                    INTEGER,
                hwAggLinkPortList
                    Integer32,
                hwAggLinkState
                    RowStatus,
                hwAggPortListSelectedPorts
                    Integer32,
                hwAggPortListSamePartnerPorts
                    Integer32,
                hwAggLinkShareType
                    INTEGER,
                hwAggLinkProtectType
                    INTEGER,
                hwAggLinkSelectPorts
                    Integer32,
                hwAggLinkUnselectPorts
                    Integer32,
                hwAggLinkMasterPort
                    Integer32
                }

        hwAggLinkNumber OBJECT-TYPE
            SYNTAX Integer32 (1..2147483647)
            MAX-ACCESS accessible-for-notify
            STATUS current
            DESCRIPTION
                "Indicates the index of each LAG. The index uniquely identifies a LAG and equals 
                 the ifindex value of the master port.
                "
            ::= { hwAggLinkEntry 1 }
        
        hwAggLinkName OBJECT-TYPE
            SYNTAX OCTET STRING  (SIZE (0..32))
            MAX-ACCESS read-create
            STATUS current
            DESCRIPTION
                "The name of an aggregation group
                "
            ::= { hwAggLinkEntry 2 }
        
        hwAggLinkMode OBJECT-TYPE
            SYNTAX INTEGER
                {
                manual(1),
                static(2),
                dynamic(3)
                }
            MAX-ACCESS read-create
            STATUS current
            DESCRIPTION
                "Type of aggregation. 1 => Manual 
                 aggregation, no LACP 2 => Membership 
                 specified by user, LACP is used to 
                 validate 3 => Completely dynamic 
                 aggregation detected by LACP
                 Options:
                 1. manual(1)  -indicates the type of aggregation is manual
                 2. static(2) -indicates the type of aggregation is static
                 3. dynamic(3) -indicates the type of aggregation is dynamic
                "
            ::= { hwAggLinkEntry 3 }
        
        hwAggLinkPortList OBJECT-TYPE
            SYNTAX Integer32
            MAX-ACCESS read-create
            STATUS current
            DESCRIPTION
                "List of ports in this AL, by bridge port number. 
                 If the type is manual or static, you can update 
                 this list to your hearts content. If, however, 
                 the AL is dynamic, then the system will maintain it.
                 You are NOT permitted to set the value of this to all 
                 zeroes.
                "
            ::= { hwAggLinkEntry 4 }
        
        hwAggLinkState OBJECT-TYPE
            SYNTAX RowStatus
            MAX-ACCESS read-create
            STATUS current
            DESCRIPTION
                "RowStatus
                "
            ::= { hwAggLinkEntry 5 }
        
        hwAggPortListSelectedPorts OBJECT-TYPE
            SYNTAX Integer32
            MAX-ACCESS read-only
            STATUS current
            DESCRIPTION
                "A PortList of physical ports that have selected
                 to this aggregator, but which have not yet attached.
                "
            ::= { hwAggLinkEntry 6 }
        
        hwAggPortListSamePartnerPorts OBJECT-TYPE
            SYNTAX Integer32
            MAX-ACCESS read-only
            STATUS current
            DESCRIPTION
                "PortList of physical ports that the same Actor 
                 SystemID and partner systemID as this aggregator,
                 but have differing actor and partner keys.
                "
            ::= { hwAggLinkEntry 7 }
        
        hwAggLinkShareType OBJECT-TYPE
            SYNTAX INTEGER
                {
                loadSharing(1), 
                nonLoadSharing(2)
                }
            MAX-ACCESS read-only
            STATUS current
            DESCRIPTION
                "Indicates the load sharing type of links. 
                 Options: 
                 1. loadSharing(1)    -indicates sharing the link load
                 2. nonLoadSharing(2) -indicates not sharing the link load
                 Currently, the system supports only loadsharing(1).
                "
            ::= { hwAggLinkEntry 8 }
        
        hwAggLinkProtectType OBJECT-TYPE
            SYNTAX INTEGER
                {
                backupProtect(1),
                nonBackupProtect(2)
                }
            MAX-ACCESS read-only
            STATUS current
            DESCRIPTION
                "Indicates the protection type of links. 
                 Options: 
                 1. backupProtect(1)    -indicates the backup aggregation protection
                 2. nonBackupProtect(2) -indicates the non-backup aggregation protection
                "
            ::= { hwAggLinkEntry 9 }
        
        hwAggLinkSelectPorts OBJECT-TYPE
            SYNTAX Integer32 (0..65535)
            MAX-ACCESS read-only
            STATUS current
            DESCRIPTION
                "Indicates the number of selected ports in the LAG.
                "
            ::= { hwAggLinkEntry 10 }
        
        hwAggLinkUnselectPorts OBJECT-TYPE
            SYNTAX Integer32 (0..65535)
            MAX-ACCESS read-only
            STATUS current
            DESCRIPTION
                "Indicates the number of unselected ports in the LAG.
                "
            ::= { hwAggLinkEntry 11 }
        
        hwAggLinkMasterPort OBJECT-TYPE
            SYNTAX Integer32
            MAX-ACCESS read-only
            STATUS current
            DESCRIPTION
                "Indicates the ifindex of the master port in the LAG.
                "
            ::= { hwAggLinkEntry 12 }
        
        hwAggPortTable OBJECT-TYPE
            SYNTAX SEQUENCE OF HwAggPortEntry
            MAX-ACCESS not-accessible
            STATUS current
            DESCRIPTION
                "Describes the configuration of the ports in static LAGs.
                 The index of this table is hwAggPortIndex.
                "
            ::= { hwLacpMibObjects 2 }
        
        hwAggPortEntry OBJECT-TYPE
            SYNTAX HwAggPortEntry
            MAX-ACCESS not-accessible
            STATUS current
            DESCRIPTION
                "Describes the configuration of the ports in static LAGs.
                 The index of this entry is hwAggPortIndex.
                "
            INDEX { hwAggPortIndex }
            ::= { hwAggPortTable 1 }
        
        HwAggPortEntry ::=
            SEQUENCE 
                { 
                hwAggPortIndex
                    Gauge32,
                hwAggPortNotAttachedReason
                    Integer32,
                hwAggPortLacpState
                    TruthValue,
                hwAggPortNotAttachedString
                    DisplayString,
                hwAggPortRole
                    INTEGER,
                hwAggPortType
                    INTEGER,
                hwAggPortStatus
                    INTEGER
                }

        hwAggPortIndex OBJECT-TYPE
            SYNTAX Gauge32
            MAX-ACCESS not-accessible
            STATUS current
            DESCRIPTION
                "Indicates the index of the port in a LAG. The index uniquely identifies a port 
                 in a LAG and equals the ifIndex value of the port.
                "
            ::= { hwAggPortEntry 1 }
        
        hwAggPortNotAttachedReason OBJECT-TYPE
            SYNTAX Integer32 (0..4)
            MAX-ACCESS read-write
            STATUS current
            DESCRIPTION
                "Indicates why this port is selected for an aggregator
                 but not attached,-- 1 - all active ports are already
                 in-use for this aggregator.-- 2 - all aggregation 
                 resources are already being used.-- 3 - the port's 
                 configuration is not appropriate. -- 4 - the port's 
                 partner is not appropriate
                "
            ::= { hwAggPortEntry 2 }
        
        hwAggPortLacpState OBJECT-TYPE
            SYNTAX TruthValue
            MAX-ACCESS read-write
            STATUS current
            DESCRIPTION
                "Control lacp enable or disable
                "
            ::= { hwAggPortEntry 3 }
        
        hwAggPortNotAttachedString OBJECT-TYPE
            SYNTAX DisplayString
            MAX-ACCESS read-write
            STATUS current
            DESCRIPTION
                "Indicates why this 
                 port is selected for an aggregator 
                 but not attached
                "
            ::= { hwAggPortEntry 4 }
        
        hwAggPortRole OBJECT-TYPE
            SYNTAX INTEGER
                {
                selected(1),
                unselected(2)
                }
            MAX-ACCESS read-only
            STATUS current
            DESCRIPTION
                "Indicates the port role. 
                 Options: 
                 1. selected(1)   -indicates the port is selected
                 2. unselected(2) -indicates the port is not selected
                "
            ::= { hwAggPortEntry 5 }
        
        hwAggPortType OBJECT-TYPE
            SYNTAX INTEGER
                {
                mastPort(1),
                nonMastPort(2)
                }
            MAX-ACCESS read-only
            STATUS current
            DESCRIPTION
                "Indicates the port type. 
                 Options: 
                 1. mastPort(1)    -indicates the port is a primary port
                 2. nonMastPort(2) -indicates the port is a secondary port
                "
            ::= { hwAggPortEntry 6 }
        
        hwAggPortStatus OBJECT-TYPE
            SYNTAX INTEGER
                {
                forwarding(1),
                block(2)
                }
            MAX-ACCESS read-only
            STATUS current
            DESCRIPTION
                "Indicates the port status. 
                 Options: 
                 1. forwarding(1) -indicates packets on the port can be forwarded
                 2. block(2)     -indicates the port is blocked
                "
            ::= { hwAggPortEntry 7 }
        
        hwAggResourceAllocationValue OBJECT-TYPE
            SYNTAX Integer32
            MAX-ACCESS read-only
            STATUS current
            DESCRIPTION
                "The priority value calculated to decide 
                 which aggregations have first call on the
                 load-sharing aggregation resources in the hardware.
                 DEFVAL { 0 }
                "
            ::= { hwLacpMibObjects 3 }     
 
        hwAggShortPeriod OBJECT-TYPE
            SYNTAX Integer32 (0..10)
            MAX-ACCESS read-write
            STATUS current
            DESCRIPTION
                "Indicates the value of the short period for link aggregation.
                 Range: 0-10
                 Default: 1
                 Unit: second
                 When set to 0, the short period is restored to the default value.
                "
            ::= { hwLacpMibObjects 4 }
        
        hwAggLongPeriod OBJECT-TYPE
            SYNTAX Integer32 (0 | 20..40)
            MAX-ACCESS read-write
            STATUS current
            DESCRIPTION
                "Indicates the value of the long period for link aggregation. 
                 Range: 0, 20-40
                 Default: 30
                 Unit: second
                 When set to 0, the long period is restored to the default value.
                "
            ::= { hwLacpMibObjects 5 }
            
        hwAggPreempt OBJECT-TYPE
            SYNTAX INTEGER
	            {
	            enable(1),
	            disable(2)
	            }
            MAX-ACCESS read-write
            STATUS current
            DESCRIPTION
                "This object enables/disables LACP priority preemption function.
                 Options:
                 1. enable(1)  -indicates the LACP priority preemption function is enable
                 2. disable(2) -indicates the LACP priority preemption function is disable
                 Default: disable(2)
                "
            ::= { hwLacpMibObjects 6 }    

        hwLacpMibNotifications OBJECT IDENTIFIER ::= { hwLacpExt 2 }
        
        hwAggSpeedChangedNotification NOTIFICATION-TYPE
            OBJECTS { hwAggLinkNumber }
            STATUS current
            DESCRIPTION 
                "This event will be triggered whenever an aggregation changes its speed.
                "
            ::= { hwLacpMibNotifications 1 }
        
        hwAggPortInactiveNotification NOTIFICATION-TYPE
            OBJECTS { hwAggLinkNumber }
            STATUS current
            DESCRIPTION 
                "This event will be triggered whenever any port in aggregator is made inactive
                "
            ::= { hwLacpMibNotifications 4 }
        
        hwLacpMibConformance OBJECT IDENTIFIER ::= { hwLacpExt 4 }
        
        hwLacpMibCompliances OBJECT IDENTIFIER ::= { hwLacpMibConformance 1 }
        
        hwLacpMibCompliance MODULE-COMPLIANCE
            STATUS current
            DESCRIPTION 
                "The compliance statement for SNMP entities which implement
                 the Lacp MIB.
                "
            MODULE 
                MANDATORY-GROUPS { hwLacpMibObjectGroup, hwLacpMibNotificationGroup }
            ::= { hwLacpMibCompliances 1 }
        
        hwLacpMibGroup OBJECT IDENTIFIER ::= { hwLacpMibConformance 2 }
        
        hwLacpMibObjectGroup OBJECT-GROUP
            OBJECTS 
                { 
                hwAggLinkName, 
                hwAggLinkMode, 
                hwAggLinkPortList, 
                hwAggLinkState, 
                hwAggPortListSelectedPorts, 
                hwAggPortListSamePartnerPorts, 
                hwAggLinkShareType, 
                hwAggLinkProtectType, 
                hwAggLinkSelectPorts, 
                hwAggLinkUnselectPorts, 
                hwAggLinkMasterPort, 
                hwAggPortNotAttachedReason, 
                hwAggPortLacpState, 
                hwAggPortNotAttachedString, 
                hwAggPortRole, 
                hwAggPortType, hwAggPortStatus,   
                hwAggResourceAllocationValue, 
                hwAggShortPeriod, 
                hwAggLongPeriod
                }
            STATUS current
            DESCRIPTION 
                "The collection of objects which are used to represent Lacp objects.
                "
            ::= { hwLacpMibGroup 1 }
        
        hwLacpMibNotificationGroup NOTIFICATION-GROUP
            NOTIFICATIONS 
                { 
                hwAggSpeedChangedNotification, 
                hwAggPortInactiveNotification 
                }
            STATUS current
            DESCRIPTION 
                "The collection of objects which are used to represent notifications.
                "
            ::= { hwLacpMibGroup 2 }
        
        hwLacpTrapsVbOids OBJECT IDENTIFIER ::= { hwLacpExt 5 }
        
        hwOldUpLinkMACAddress OBJECT-TYPE
            SYNTAX MacAddress
            MAX-ACCESS accessible-for-notify
            STATUS current
            DESCRIPTION
                "Indicates the old up link mac-address. 
                "
            ::= { hwLacpTrapsVbOids 1 }  

        hwNewUpLinkMACAddress OBJECT-TYPE
            SYNTAX MacAddress
            MAX-ACCESS accessible-for-notify
            STATUS current
            DESCRIPTION
                "Indicates the new up link mac-address. 
                "
            ::= { hwLacpTrapsVbOids 2 }
            
        hwAggLinkGroupID OBJECT-TYPE
            SYNTAX Integer32
            MAX-ACCESS accessible-for-notify
            STATUS current
            DESCRIPTION
                "Indicates the aggregation link group ID. 
                "
            ::= { hwLacpTrapsVbOids 3 }
                        
        hwLacpTraps OBJECT IDENTIFIER ::= { hwLacpExt 6 } 
                   
        hwLacpAlarmTraps OBJECT IDENTIFIER ::= { hwLacpTraps 1 }  
        
        hwLacpAlarmTrapsPrefix OBJECT IDENTIFIER ::= { hwLacpAlarmTraps 0 }
        
        hwLacpCommonTraps OBJECT IDENTIFIER ::= { hwLacpTraps 2 }    
    
        hwLacpCommonTrapsPrefix OBJECT IDENTIFIER ::= { hwLacpCommonTraps 0 }
        
        hwLacpPortLinkFaultTrap NOTIFICATION-TYPE
            OBJECTS  
                { 
                hwFrameIndex, 
                hwSlotIndex, 
                hwPortIndex 
                }
            STATUS   current
            DESCRIPTION
                "The SNMP trap that is generated when LACP link is faulty.
                "
            ::= { hwLacpAlarmTraps 0 1 }
        
        hwLacpPortLinkRecoverTrap NOTIFICATION-TYPE
            OBJECTS  { hwFrameIndex, hwSlotIndex, hwPortIndex }
            STATUS   current
            DESCRIPTION
               "The SNMP trap that is generated when the port receives the LACP packet normally.
               "
            ::= { hwLacpAlarmTraps 0 2 }
                    
        hwLacpGroupMacChangeTrap NOTIFICATION-TYPE
            OBJECTS  { hwOldUpLinkMACAddress, hwNewUpLinkMACAddress, hwAggLinkGroupID }
            STATUS   current
            DESCRIPTION
                "The SNMP trap that is generated when LACP up link switch over.
                "
            ::= { hwLacpAlarmTraps 0 3 }
            
        hwLacpPortStateForwarding NOTIFICATION-TYPE
            OBJECTS  
                { 
                hwFrameIndex, 
                hwSlotIndex, 
                hwPortIndex 
                }
            STATUS   current
            DESCRIPTION
                "The SNMP trap that is generated when a port turns into 
                 forwarding state from other state.
                "
            ::= { hwLacpCommonTraps 0 1 }
            
        hwLacpPortStateDiscarding NOTIFICATION-TYPE
            OBJECTS  
                { 
                hwFrameIndex, 
                hwSlotIndex, 
                hwPortIndex 
                }
            STATUS   current
            DESCRIPTION
                "The SNMP trap that is generated when a port turns into 
                 discarding state from forwarding state.
                "
            ::= { hwLacpCommonTraps 0 2 }
            
            
    END
